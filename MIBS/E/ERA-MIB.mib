-----------------------------------------------------------------------
--  ERA MSS MIB version 0.1
-----------------------------------------------------------------------

-----------------------------------------------------------------------
-- $Author:   DMA  $
-- $Revision$
-- $Modtime$
-- $Workfile$
-----------------------------------------------------------------------

ERA-MIB DEFINITIONS ::= BEGIN


IMPORTS
    MODULE-IDENTITY, OBJECT-TYPE , Integer32, NOTIFICATION-TYPE, enterprises
								FROM SNMPv2-SMI
    MODULE-COMPLIANCE, OBJECT-GROUP, NOTIFICATION-GROUP
								FROM SNMPv2-CONF
    DisplayString					FROM SNMPv2-TC;

era MODULE-IDENTITY
    LAST-UPDATED "200612121345Z"
    ORGANIZATION "www.era.cz"
    CONTACT-INFO
	 "postal:
      email:"
    DESCRIPTION
	"Management Information Base for ERA surveilance systems"
    REVISION     "200612120000Z"
    DESCRIPTION  "Not-revised edition (V0.1)"
    ::= { enterprises 11588}


--    main branches enumeration
systems         OBJECT IDENTIFIER ::= { era 1 }
-- utility         OBJECT IDENTIFIER ::= { era 2 }

--    era.software.systems enumeration
-- pss             OBJECT IDENTIFIER ::= { systems 1 }
-- fd              OBJECT IDENTIFIER ::= { systems 2 }
mss             OBJECT IDENTIFIER ::= { systems 3 }

--
-- Type definitions
--
StatusValue ::= TEXTUAL-CONVENTION
    STATUS       current
    DESCRIPTION
            "Represents a MSS status."
    SYNTAX      INTEGER {
                            unknown(0),
                            ok(1),
                            degraded(2),
                            error(3)
                        }

--
-- MSS status
--

mssStatus           OBJECT IDENTIFIER ::= { mss 1 }

mssStatusSystem           OBJECT IDENTIFIER ::= { mssStatus 1 }

mssStatusSystem1 OBJECT-TYPE
    SYNTAX StatusValue
    MAX-ACCESS  read-only
    STATUS      current
    DESCRIPTION
        "MSS sensor 1 status"
    ::= { mssStatusSystem 1  }

mssStatusSystem2 OBJECT-TYPE
    SYNTAX StatusValue
    MAX-ACCESS  read-only
    STATUS      current
    DESCRIPTION
        "MSS sensor 2 status"
    ::= { mssStatusSystem 2  }

mssStatusSystem3 OBJECT-TYPE
    SYNTAX StatusValue
    MAX-ACCESS  read-only
    STATUS      current
    DESCRIPTION
        "MSS sensor 3 status"
    ::= { mssStatusSystem 3  }

mssStatusSystem4 OBJECT-TYPE
    SYNTAX StatusValue
    MAX-ACCESS  read-only
    STATUS      current
    DESCRIPTION
        "MSS sensor 4 status"
    ::= { mssStatusSystem 4  }

mssStatusOverall OBJECT-TYPE
    SYNTAX StatusValue
    MAX-ACCESS  read-only
    STATUS      current
    DESCRIPTION
        "The overall MSS system status"
    ::= { mssStatus 2 }

mssStatusTP OBJECT-TYPE
    SYNTAX StatusValue
    MAX-ACCESS  read-only
    STATUS      current
    DESCRIPTION
        "MSS target processors status"
    ::= { mssStatus 3  }

mssStatusTP1 OBJECT-TYPE
    SYNTAX StatusValue
    MAX-ACCESS  read-only
    STATUS      current
    DESCRIPTION
        "MSS TP1 status"
    ::= { mssStatusTP 1  }

mssStatusTP2 OBJECT-TYPE
    SYNTAX StatusValue
    MAX-ACCESS  read-only
    STATUS      current
    DESCRIPTION
        "MSS TP2 status"
    ::= { mssStatusTP 2  }

mssStatusMS OBJECT-TYPE
    SYNTAX StatusValue
    MAX-ACCESS  read-only
    STATUS      current
    DESCRIPTION
        "MSS management servers status"
    ::= { mssStatus 4  }

mssStatusMS1 OBJECT-TYPE
    SYNTAX StatusValue
    MAX-ACCESS  read-only
    STATUS      current
    DESCRIPTION
        "MSS MS1 status"
    ::= { mssStatusMS 1  }

mssStatusMS2 OBJECT-TYPE
    SYNTAX StatusValue
    MAX-ACCESS  read-only
    STATUS      current
    DESCRIPTION
        "MSS MS2 status"
    ::= { mssStatusMS 1  }

mssStatusRPU OBJECT-TYPE
    SYNTAX StatusValue
    MAX-ACCESS  read-only
    STATUS      current
    DESCRIPTION
        "MSS remote processing units status"
    ::= { mssStatus 5  }

mssStatusComm OBJECT-TYPE
    SYNTAX StatusValue
    MAX-ACCESS  read-only
    STATUS      current
    DESCRIPTION
        "MSS communications status"
    ::= { mssStatus 6  }

mssStatusTime OBJECT-TYPE
    SYNTAX StatusValue
    MAX-ACCESS  read-only
    STATUS      current
    DESCRIPTION
        "MSS time subsystem status"
    ::= { mssStatus 7  }

mssStatusLoad OBJECT-TYPE
    SYNTAX StatusValue
    MAX-ACCESS  read-only
    STATUS      current
    DESCRIPTION
        "MSS load status"
    ::= { mssStatus 8  }

mssStatusRX OBJECT-TYPE
    SYNTAX StatusValue
    MAX-ACCESS  read-only
    STATUS      current
    DESCRIPTION
        "MSS receiving subsystem status"
    ::= { mssStatus 9  }

mssStatusTX OBJECT-TYPE
    SYNTAX StatusValue
    MAX-ACCESS  read-only
    STATUS      current
    DESCRIPTION
        "MSS transmitting subsystem status"
    ::= { mssStatus 10  }

mssStatusHW OBJECT-TYPE
    SYNTAX StatusValue
    MAX-ACCESS  read-only
    STATUS      current
    DESCRIPTION
        "MSS hardware status"
    ::= { mssStatus 11  }

mssStatusTestTarget OBJECT-TYPE
    SYNTAX INTEGER { none(0), operational(1) }
    MAX-ACCESS  read-only
    STATUS      current
    DESCRIPTION
        "MSS test target status"
    ::= { mssStatus 12  }

mssStatusCOTS OBJECT-TYPE
    SYNTAX StatusValue
    MAX-ACCESS  read-only
    STATUS      current
    DESCRIPTION
        "COTS status"
    ::= { mssStatus 13  }



--
-- MSS SNMP trap definitions
--

mssTraps           OBJECT IDENTIFIER ::= { mss 10 }


mssTrapStatusSystemError NOTIFICATION-TYPE
    STATUS      current
    DESCRIPTION
        "Trap to be sent when status of any system changes to error. "
    ::= { mssTraps 1 }

mssTrapStatusSystemDegraded NOTIFICATION-TYPE
    STATUS      current
    DESCRIPTION
        "Trap to be sent when status of any system changes to degraded. "
    ::= { mssTraps 2 }

mssTrapStatusSystemWarning NOTIFICATION-TYPE
    STATUS      current
    DESCRIPTION
        "Trap to be sent when status of any system changes to wraning. "
    ::= { mssTraps 3 }

mssTrapStatusSystemOK NOTIFICATION-TYPE
    STATUS      current
    DESCRIPTION
        "Trap to be sent when status of any system changes to OK. "
    ::= { mssTraps 4 }

mssTrapStatusSystemUnknown NOTIFICATION-TYPE
    STATUS      current
    DESCRIPTION
        "Trap to be sent when status of any system changes to unknown. "
    ::= { mssTraps 5 }

mssTrapLoadHigh NOTIFICATION-TYPE
    STATUS      current
    DESCRIPTION
        "Trap to be sent when load becomes too high. "
    ::= { mssTraps 6 }

mssTrapLoadCritical NOTIFICATION-TYPE
    STATUS      current
    DESCRIPTION
        "Trap to be sent when load becomes critical. "
    ::= { mssTraps 7 }

mssTrapLoadNormal NOTIFICATION-TYPE
    STATUS      current
    DESCRIPTION
        "Trap to be sent when load becomes normal. "
    ::= { mssTraps 8 }

mssTrapPowerSourceFailed NOTIFICATION-TYPE
    STATUS      current
    DESCRIPTION
        "Trap to be sent when some power source has failed. "
    ::= { mssTraps 9 }

mssTrapTestTargetOperational NOTIFICATION-TYPE
    STATUS      current
    DESCRIPTION
        "Trap to be sent when a test target becomes poerational."
    ::= { mssTraps 10 }

mssTrapGeneralNotification NOTIFICATION-TYPE
    STATUS      current
    DESCRIPTION
        "When this trap is sent, watch the MSS management system."
    ::= { mssTraps 98 }

mssTrapTestNotification NOTIFICATION-TYPE
    STATUS      current
    DESCRIPTION
        "Trap to be sent when a test notification has been requested."
    ::= { mssTraps 99 }

END
