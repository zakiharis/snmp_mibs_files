--
-- This MIB defines Tandem Ethernet Subagent configuration related objects.
--

EthernetSubagentPvt-MIB DEFINITIONS ::= BEGIN


IMPORTS
        private, Counter
                FROM RFC1155-SMI
        OBJECT-TYPE
                FROM RFC-1212
        TRAP-TYPE
                FROM RFC-1215
        DisplayString
                FROM RFC1213-MIB;

--
--  ZESAMIB
--
--   private         OBJECT IDENTIFIER ::= { iso(1) org(3) dod(6) internet(1) 4}
   enterprises     OBJECT IDENTIFIER ::= {private 1}

-- iso             OBJECT IDENTIFIER ::= { 1 }
-- org             OBJECT IDENTIFIER ::= { iso 3 }
-- dod             OBJECT IDENTIFIER ::= { org 6 }
-- internet        OBJECT IDENTIFIER ::= { dod 1 }
-- private         OBJECT IDENTIFIER ::= { internet 4 }
-- enterprises     OBJECT IDENTIFIER ::= { private 1 }

   tandem          OBJECT IDENTIFIER ::= { enterprises 169 }
   nonstopsystems   OBJECT IDENTIFIER ::= { tandem 3 }
   zesa            OBJECT IDENTIFIER ::= { nonstopsystems 217}

--
-- agent        reflects -a startup parameter
--

zesaAgentName OBJECT-TYPE
   SYNTAX      DisplayString (SIZE (0..32))
   ACCESS      read-only
   STATUS      mandatory
   DESCRIPTION
   "The name of the SNMP Agent process."
   ::= { zesa 1 }

zesaAgentState OBJECT-TYPE
   SYNTAX      INTEGER {
                        connected   (1),
                        disconnected(2)
                       }
   ACCESS      read-only
   STATUS      mandatory

  DESCRIPTION
  "Current status of the agent interface. The state of this variable
  will always be connected(1) when returned in a management request"
   ::= { zesa 2 }

--
-- subagent process control area
--
zesaProcessName OBJECT-TYPE
   SYNTAX      DisplayString (SIZE (0..49))
   ACCESS      read-only
   STATUS      mandatory
   DESCRIPTION
"The fully qualified NSK process name of this subagent."
   ::= {zesa  3 }

zesaProcessVersion OBJECT-TYPE
   SYNTAX      DisplayString (SIZE (0..32))
   ACCESS      read-only
   STATUS      mandatory
   DESCRIPTION
"The version of this subagent process object file."
   ::= {zesa  4 }

zesaProgramFile OBJECT-TYPE
   SYNTAX      DisplayString (SIZE (0..32))
   ACCESS      read-only
   STATUS      mandatory
   DESCRIPTION
"The Ethernet subagent program file name."
   ::= {zesa  5 }

zesaProcessPriority  OBJECT-TYPE
   SYNTAX      INTEGER (0..199)
   ACCESS      read-write
   STATUS      mandatory
   DESCRIPTION
"The current NSK process priority of this subagent process."
   ::= {zesa  6 }

zesaProcessGroupID  OBJECT-TYPE
   SYNTAX      INTEGER (0..255)
   ACCESS      read-only
   STATUS      mandatory
   DESCRIPTION
"the NSK process group ID part of the PAID for this subagent process."
   ::= {zesa  7 }

zesaProcessUserID  OBJECT-TYPE
   SYNTAX      INTEGER (0..255)
   ACCESS      read-only
   STATUS      mandatory
   DESCRIPTION
"the NSK process user ID part of the PAID for this subagent process."
   ::= {zesa  8 }

zesaPrimaryCPU  OBJECT-TYPE
   SYNTAX      INTEGER (0..255)
   ACCESS      read-only
   STATUS      mandatory
   DESCRIPTION
"The CPU number of the primary process of this subagent"
   ::= {zesa  9 }

zesaPrimaryPIN  OBJECT-TYPE
   SYNTAX      INTEGER (0..255)
   ACCESS      read-only
   STATUS      mandatory
   DESCRIPTION
"The process number of the primary process of this subagent"
   ::= {zesa  10 }

--
-- reflects -b startup parameter at startup
--
zesaBackupCPU  OBJECT-TYPE
   SYNTAX      INTEGER (-1..255)
   ACCESS      read-write
   STATUS      mandatory
   DESCRIPTION
"The CPU, the backup process will start in or is running in. A value of
-1 indicates the backup is not configured. zesaBackupState must be set
to disabled(3) prior to setting this object"
   ::= {zesa  11 }

zesaBackupPIN  OBJECT-TYPE
   SYNTAX      INTEGER (-1..255)
   ACCESS      read-only
   STATUS      mandatory
   DESCRIPTION
"The process number of the backup process of this subagent. Its value
is -1 when the backup is not running"
   ::= {zesa  12 }

zesaBackupState OBJECT-TYPE
   SYNTAX      INTEGER {
                        connected   (1),
                        disconnected(2),
                        disabled    (3),
                        enabled(4)
                       }
   ACCESS      read-write
   STATUS      mandatory
   DESCRIPTION
"The state of the backup process of this subagent"
   ::= {zesa  13 }

zesaSwitchToBackupNow  OBJECT-TYPE
   SYNTAX      INTEGER {
                        autoProcessPairControl(0),
                        forceBackupTakeover   (1)
                       }
   ACCESS      read-write
   STATUS      mandatory
   DESCRIPTION                                                  --233
  "This object normally reads 0 (autoProcessPairControl) .  Setting this
  object to 1 (forceBackupTakeover) causes the subagent to switch to its
  backup process immediately after replying OK. Setting this object is
  only permitted if the zesaBackupState is connected(1)"
     ::= {zesa  14 }

--
-- reflects -c startup parameter
--

zesaEmsCollectorName  OBJECT-TYPE
   SYNTAX      DisplayString (SIZE (0..15))
   ACCESS      read-write
   STATUS      mandatory
   DESCRIPTION
  "The process of the EMS Collector the subagent should send
  its EMS events to. zesaEmsCollectorState must be set to disabled(3)
  prior to setting this object"
     ::= {zesa  15 }

zesaEmsCollectorState  OBJECT-TYPE
   SYNTAX      INTEGER {
                        connected   (1),
                        disconnected(2),
                        disabled    (3),
                        enabled(4)
                        }
   ACCESS      read-write
   STATUS      mandatory
   DESCRIPTION
"The state of the connection to the EMS Collector. The settable
values for this object are disabled(3) and enabled(4).  The
connected(1) and disconnected(2) states are set by the subagent to
reflect the running state of the EMS collector interface."
   ::= {zesa  16 }

--
-- reflects -k startup parameter
--

zesaKeepAliveTimer  OBJECT-TYPE
   SYNTAX      INTEGER (0..32000)
   ACCESS      read-write
   STATUS      mandatory
   DESCRIPTION
"The number of seconds between attempts the subagent makes to connect
to an SNMP Agent, TCP/IP process, SCP process, Collector
process and restart the backup process."
   ::= {zesa  17 }

zesaRefreshNow  OBJECT-TYPE
   SYNTAX      INTEGER {
                       autoDynamicRefresh (0),
                       forceDynamicRefresh(1)
                       }
   ACCESS      read-write
   STATUS      mandatory
   DESCRIPTION
"This object normally reads 0 (autoDynamicRefresh).  Setting this object to
1 (forceDynamicRefresh) causes the subagent to update the MIB tables and
generate traps (if needed)."
   ::= {zesa  18 }


--
-- reflects the -r startup parameter
--

zesaRefreshTimer OBJECT-TYPE
   SYNTAX      INTEGER (0..32000)
   ACCESS      read-write
   STATUS      mandatory
   DESCRIPTION
"The cache update interval for the MIB objects.  Value 0 disables
cache timing such that updates occur to objects only when the
zesaRefreshNow object is set"
   ::= { zesa  19 }

--
-- reflects the -t startup parameter
--

zesaTcpIpProcess OBJECT-TYPE
   SYNTAX      DisplayString  (SIZE (0..15))
   ACCESS      read-write
   STATUS      mandatory
   DESCRIPTION
"The TCP/IP process whose Ethernet interfaces are monitored by
the subagent. zesaTcpIpState must be set to disabled(3) prior to
setting this object"
   ::= { zesa  20 }

zesaTcpIpState OBJECT-TYPE
   SYNTAX      INTEGER {
                        connected   (1),
                        disconnected(2),
                        disabled    (3),
                        enabled(4)
                       }
   ACCESS      read-write
   STATUS      mandatory
   DESCRIPTION
"The state of the connection to the monitored TCP/IP
process. The settable values for this object are disabled(3 )
and enabled(4).  The connected(1) and disconnected(2)
states are set by the subagent to reflect the running state of
the TCP/IP resource interface."
   ::= {zesa 21}

--
-- reflects the -s startup parameter
--

zesaSCPProcess OBJECT-TYPE
   SYNTAX      DisplayString (SIZE (0..15))
   ACCESS      read-only
   STATUS      mandatory
   DESCRIPTION
"The SCP process used for SPI requests. Value is set by the
-s startup parameter. Default is $ZNET. "
   ::= { zesa  22 }

zesaTrap OBJECT-TYPE
   SYNTAX      DisplayString (SIZE (0..15))
   ACCESS      read-only
   STATUS      mandatory
   DESCRIPTION
"String contains the information about the name and status of the line."
   ::= { zesa  23 }

zesalinkUp TRAP-TYPE
   ENTERPRISE zesa
   VARIABLES { zesaTrap }
   DESCRIPTION
" A LinkUp trap signiifies that the status of the line has changed from
STOPPED to STARTED state."
   ::= 2

zesalinkDown TRAP-TYPE
   ENTERPRISE zesa
   VARIABLES { zesaTrap }
   DESCRIPTION
" A LinkDown trap signiifies that the status of the line has changed from
STARTED to STOPPED state."
  ::= 3

END
