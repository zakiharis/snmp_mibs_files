ELFIQ-INC-MIB DEFINITIONS ::= BEGIN
       
-- IMPORTS: Include definitions from other mibs here, which is always
-- the first item in a MIB file.
       
   IMPORTS
      MODULE-IDENTITY, OBJECT-TYPE,
		NOTIFICATION-TYPE,enterprises  	FROM SNMPv2-SMI 
		DisplayString		      			FROM SNMPv2-TC;
       
--
-- A brief description and update information about this mib.
--
elfiqInc                     MODULE-IDENTITY
    LAST-UPDATED "200811190000Z"            -- 11 Nov 2008, midnight
    ORGANIZATION "Elfiq Inc."
    CONTACT-INFO "
              Author:     Elfiq Network
              postal:     Montreal, QC H3B3A7
                                     CANADA
              email:      support@elfiq.com
              phone:      +1-514-667-0611
                        "
    DESCRIPTION  "This is the standard mib of elfiq products"
    ::= { enterprises 19713 }


-- Define typical elfiq mib nodes

elfiqMIBProducts    OBJECT IDENTIFIER ::= { elfiqInc 1 }
elfiqMIBConformance OBJECT IDENTIFIER ::= { elfiqInc 2 }

-- Define the sections of the mib them selves:

--
-- 1) Defines the product in elfiqInc
--
common					OBJECT IDENTIFIER	::= { elfiqMIBProducts 1 }
linkBalancer	    	OBJECT IDENTIFIER ::= { elfiqMIBProducts 2 }


--
-- 2) Defines the conformance
--
commonConformance 		OBJECT IDENTIFIER ::= { elfiqMIBConformance 1 }
linkBalancerConformance OBJECT IDENTIFIER ::= { elfiqMIBConformance 2 }


-- The above definitions produce a section of the mib tree 
-- include in the enterprises sections
-- Elfiq reserved OID is 19713
-- 
--   +-private(4)
--     |
--     +-enterprises(1)
--       |
--			+-elfiqInc(19713)
--			  	|
--			  	+-elfiqMIBProducts(1)
--         	|	|
--         	|	+-common(1)
--         	|  		|
--				|			
--         	+-elfiqMIBConformance(2)
--
--
END
