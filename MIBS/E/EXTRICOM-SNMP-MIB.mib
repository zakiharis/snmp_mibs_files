EXTRICOM-SNMP-MIB DEFINITIONS ::= BEGIN


IMPORTS
    MODULE-IDENTITY,Integer32,Counter32,enterprises,IpAddress,NOTIFICATION-TYPE,OBJECT-TYPE
    	FROM SNMPv2-SMI
    NOTIFICATION-GROUP,OBJECT-GROUP
    	FROM SNMPv2-CONF
    DisplayString,RowStatus,TruthValue,MacAddress
    	FROM SNMPv2-TC;

extricomSnmpMIB MODULE-IDENTITY

LAST-UPDATED "201005170000Z"
ORGANIZATION "www.extricom.com"
CONTACT-INFO    
"info@extricom.com"
DESCRIPTION
"Octopus Wireless switch MIB"
::= { octopus 1 }



-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }
octopus           OBJECT IDENTIFIER ::= { enterprises 23937  }




-- =====================================================================
--
--
--
	
SeverityLevel ::= INTEGER {
  info(1),
  error(2),
  fatal(3)
} 

RedundancyRole ::= INTEGER {
  main(1),
  backup(2)
}

DeviceType ::= INTEGER {
  static(1),
  dynamic(2)
}

FileOperationOption ::= INTEGER {
  upload(1),
  download(2),
  clear(3),
  swap(4)
}

mibTraps                OBJECT IDENTIFIER ::= { octopus 0 }
mibObjects              OBJECT IDENTIFIER ::= { octopus 2 }
mibConformance          OBJECT IDENTIFIER ::= { octopus 3 }
generalParams           OBJECT IDENTIFIER ::= { octopus 4 }
fwUpdateGroup           OBJECT IDENTIFIER ::= { octopus 5 }
platformInfo            OBJECT IDENTIFIER ::= { octopus 6 }
rtcInfo                 OBJECT IDENTIFIER ::= { octopus 7 }
ntp                     OBJECT IDENTIFIER ::= { octopus 8 }
maintenance             OBJECT IDENTIFIER ::= { octopus 9 }
general                 OBJECT IDENTIFIER ::= { octopus 10 }
capivePortal            OBJECT IDENTIFIER ::= { octopus 11 }
ibm                     OBJECT IDENTIFIER ::= { octopus 12 }
redundancyParameters    OBJECT IDENTIFIER ::= { octopus 13 }
coreRedundancy         OBJECT IDENTIFIER ::= { octopus 14 }
nomadicBssid           OBJECT IDENTIFIER ::= { octopus 15 }
snmp                    OBJECT IDENTIFIER ::= { octopus 16 }
regulatory              OBJECT IDENTIFIER ::= { octopus 17 }
reuse                   OBJECT IDENTIFIER ::= { octopus 18 }
groups                  OBJECT IDENTIFIER ::= { mibConformance 1 }



-- =====================================================================
--
--	Traps
--


trapMibTrapDescription OBJECT-TYPE
	SYNTAX INTEGER {  
	  notify(1),
	  minor(2),
      major(3)
	} 
	MAX-ACCESS read-only
	STATUS current
	DESCRIPTION 	 "Trap description."
	::= { mibObjects 1 }       
	
trapMibTrapSeverity OBJECT-TYPE
	SYNTAX INTEGER {  
	  info(1),
	  error(2),
      fatal(3)
	}    
	MAX-ACCESS read-only
	STATUS current
	DESCRIPTION 	 "Trap severity."
	::= { mibObjects 2 }

clientAssociate  NOTIFICATION-TYPE
             OBJECTS   { trapMibTrapSeverity,trapMibTrapDescription}
             STATUS  current
             DESCRIPTION
                  "Client Associated"
              ::= { mibTraps 1 }               
 
clientDisassociate  NOTIFICATION-TYPE
             OBJECTS   { trapMibTrapSeverity,trapMibTrapDescription}
             STATUS  current
             DESCRIPTION
                  "Client disassociated"
              ::= { mibTraps 2 }               
 
unknownAP  NOTIFICATION-TYPE
             OBJECTS   { trapMibTrapSeverity,trapMibTrapDescription}
             STATUS  current
             DESCRIPTION
                  "Unknown AP"
              ::= { mibTraps 3 }               
 
keyError  NOTIFICATION-TYPE
             OBJECTS   { trapMibTrapSeverity,trapMibTrapDescription}
             STATUS  current
             DESCRIPTION
                  "Key Error"
              ::= { mibTraps 4 }               
 
downlinkRetry  NOTIFICATION-TYPE
             OBJECTS   { trapMibTrapSeverity,trapMibTrapDescription}
             STATUS  current
             DESCRIPTION
                  "Downlink retry"
              ::= { mibTraps 5 }               


configurationChanged  NOTIFICATION-TYPE
             OBJECTS   { trapMibTrapSeverity,trapMibTrapDescription}
             STATUS  current
             DESCRIPTION
                  "Configuration Changed"
              ::= { mibTraps 6 }               

poeError  NOTIFICATION-TYPE
             OBJECTS   { trapMibTrapSeverity,trapMibTrapDescription}
             STATUS  current
             DESCRIPTION
                  "POE failed"
              ::= { mibTraps 7 }               

fanError  NOTIFICATION-TYPE
             OBJECTS   { trapMibTrapSeverity,trapMibTrapDescription}
             STATUS  current
             DESCRIPTION
                  "FAN failed"
              ::= { mibTraps 8 }               

powerError  NOTIFICATION-TYPE
             OBJECTS   { trapMibTrapSeverity,trapMibTrapDescription}
             STATUS  current
             DESCRIPTION
                  "Power failed"
              ::= { mibTraps 9 }               

clockError  NOTIFICATION-TYPE
             OBJECTS   { trapMibTrapSeverity,trapMibTrapDescription}
             STATUS  current
             DESCRIPTION
                  "Clock failed"
              ::= { mibTraps 10}               

upstremReport  NOTIFICATION-TYPE
             OBJECTS   { trapMibTrapSeverity,trapMibTrapDescription}
             STATUS  current
             DESCRIPTION
                  "Upstrem report"
              ::= { mibTraps 11}               

apDisconnected  NOTIFICATION-TYPE
             OBJECTS   { trapMibTrapSeverity,trapMibTrapDescription}
             STATUS  current
             DESCRIPTION
                  "AP Physical dissconnected"
              ::= { mibTraps 12}               

apReconnected  NOTIFICATION-TYPE
             OBJECTS   { trapMibTrapSeverity,trapMibTrapDescription}
             STATUS  current
             DESCRIPTION
             "AP Reconnected"
              ::= { mibTraps 13}               

apTurnOFF  NOTIFICATION-TYPE
             OBJECTS   { trapMibTrapSeverity,trapMibTrapDescription}
             STATUS  current
             DESCRIPTION
             "AP Turen OFF"
              ::= { mibTraps 14}               

apMalfunction  NOTIFICATION-TYPE
             OBJECTS   { trapMibTrapSeverity,trapMibTrapDescription}
             STATUS  current
             DESCRIPTION
             "AP Malfunction"
              ::= { mibTraps 15}               

apConfigured  NOTIFICATION-TYPE
             OBJECTS   { trapMibTrapSeverity,trapMibTrapDescription}
             STATUS  current
             DESCRIPTION
             "AP configured"
              ::= { mibTraps 16}               

radioMulfanction  NOTIFICATION-TYPE
             OBJECTS   { trapMibTrapSeverity,trapMibTrapDescription}
             STATUS  current
             DESCRIPTION
             "Radio Malfunction"
              ::= { mibTraps 17}               

wpaAttack  NOTIFICATION-TYPE
             OBJECTS   { trapMibTrapSeverity,trapMibTrapDescription}
             STATUS  current
             DESCRIPTION
             "Wpa Attack detection"
              ::= { mibTraps 18}               

redPeerConnectionUp  NOTIFICATION-TYPE
             OBJECTS   { trapMibTrapSeverity,trapMibTrapDescription}
             STATUS  current
             DESCRIPTION
             "Red Peer connection up"
              ::= { mibTraps 19}               

redPeerConnectionDown  NOTIFICATION-TYPE
             OBJECTS   { trapMibTrapSeverity,trapMibTrapDescription}
             STATUS  current
             DESCRIPTION
             "Red Peer connection down"
              ::= { mibTraps 20}               

redKeepAliveConnectionUp  NOTIFICATION-TYPE
             OBJECTS   { trapMibTrapSeverity,trapMibTrapDescription}
             STATUS  current
             DESCRIPTION
             "Red Keep alive connection Up"
              ::= { mibTraps 21}               

redKeepAliveConnectionDown  NOTIFICATION-TYPE
             OBJECTS   { trapMibTrapSeverity,trapMibTrapDescription}
             STATUS  current
             DESCRIPTION
             "Red Keep alive connection down"
              ::= { mibTraps 22}               

redBeaconStatusUp  NOTIFICATION-TYPE
             OBJECTS   { trapMibTrapSeverity,trapMibTrapDescription}
             STATUS  current
             DESCRIPTION
             "Red Beacon Status Up"
              ::= { mibTraps 23}               

redBeaconStatusDown  NOTIFICATION-TYPE
             OBJECTS   { trapMibTrapSeverity,trapMibTrapDescription}
             STATUS  current
             DESCRIPTION
             "Red Beacon Status Down"
              ::= { mibTraps 24}               

redStatusUp  NOTIFICATION-TYPE
             OBJECTS   { trapMibTrapSeverity,trapMibTrapDescription}
             STATUS  current
             DESCRIPTION
             "Red Status Up"
              ::= { mibTraps 25}               

redStatusDown  NOTIFICATION-TYPE
             OBJECTS   { trapMibTrapSeverity,trapMibTrapDescription}
             STATUS  current
             DESCRIPTION
             "Red Status Down"
              ::= { mibTraps 26}               

rogueApStatus  NOTIFICATION-TYPE
             OBJECTS   { trapMibTrapSeverity,trapMibTrapDescription}
             STATUS  current
             DESCRIPTION
             "Rogue AP Status"
              ::= { mibTraps 27}               

rogueApLost  NOTIFICATION-TYPE
             OBJECTS   { trapMibTrapSeverity,trapMibTrapDescription}
             STATUS  current
             DESCRIPTION
             "Rogue AP Lost"
              ::= { mibTraps 28}               

rogueApFound  NOTIFICATION-TYPE
             OBJECTS   { trapMibTrapSeverity,trapMibTrapDescription}
             STATUS  current
             DESCRIPTION
             "Rogue AP Found"
              ::= { mibTraps 29}               

rogueApUpdate  NOTIFICATION-TYPE
             OBJECTS   { trapMibTrapSeverity,trapMibTrapDescription}
             STATUS  current
             DESCRIPTION
             "Rogue AP Update"
              ::= { mibTraps 30}               

idsTrapStart  NOTIFICATION-TYPE
             OBJECTS   { trapMibTrapSeverity,trapMibTrapDescription}
             STATUS  current
             DESCRIPTION
             "IDS Trap Start"
              ::= { mibTraps 31}               

authenticated  NOTIFICATION-TYPE
             OBJECTS   { trapMibTrapSeverity,trapMibTrapDescription}
             STATUS  current
             DESCRIPTION
             "Authenticated"
              ::= { mibTraps 32}               

authenticatedFail  NOTIFICATION-TYPE
             OBJECTS   { trapMibTrapSeverity,trapMibTrapDescription}
             STATUS  current
             DESCRIPTION
             "Authenticated Failed"
              ::= { mibTraps 33}               

deauthenticated  NOTIFICATION-TYPE
             OBJECTS   { trapMibTrapSeverity,trapMibTrapDescription}
             STATUS  current
             DESCRIPTION
             "Deauthenticated "
              ::= { mibTraps 34}               

reauthenticated  NOTIFICATION-TYPE
             OBJECTS   { trapMibTrapSeverity,trapMibTrapDescription}
             STATUS  current
             DESCRIPTION
             "Reauthenticated "
              ::= { mibTraps 35}               

associationReq  NOTIFICATION-TYPE
             OBJECTS   { trapMibTrapSeverity,trapMibTrapDescription}
             STATUS  current
             DESCRIPTION
             "Association Request "
              ::= { mibTraps 36}               

disassociationReq  NOTIFICATION-TYPE
             OBJECTS   { trapMibTrapSeverity,trapMibTrapDescription}
             STATUS  current
             DESCRIPTION
             "Disassociation Request "
              ::= { mibTraps 37}               

reassociationReq  NOTIFICATION-TYPE
             OBJECTS   { trapMibTrapSeverity,trapMibTrapDescription}
             STATUS  current
             DESCRIPTION
             "Reassociation Request "
              ::= { mibTraps 38}               

eapolStart  NOTIFICATION-TYPE
             OBJECTS   { trapMibTrapSeverity,trapMibTrapDescription}
             STATUS  current
             DESCRIPTION
             "EAPOL Start "
              ::= { mibTraps 39}               

eapolLogoff  NOTIFICATION-TYPE
             OBJECTS   { trapMibTrapSeverity,trapMibTrapDescription}
             STATUS  current
             DESCRIPTION
             "EAPOL Logoff "
              ::= { mibTraps 40}               

navDuration  NOTIFICATION-TYPE
             OBJECTS   { trapMibTrapSeverity,trapMibTrapDescription}
             STATUS  current
             DESCRIPTION
             "NAV Duration "
              ::= { mibTraps 41}               

idsTrapEnd  NOTIFICATION-TYPE
             OBJECTS   { trapMibTrapSeverity,trapMibTrapDescription}
             STATUS  current
             DESCRIPTION
             "IDS Trap End "
              ::= { mibTraps 42}               



idsDurationAttack  NOTIFICATION-TYPE
             OBJECTS   { trapMibTrapSeverity,trapMibTrapDescription}
             STATUS  current
             DESCRIPTION
             "IDS Duration Attack "
              ::= { mibTraps 43}               

idsAssociationFloodAttack  NOTIFICATION-TYPE
             OBJECTS   { trapMibTrapSeverity,trapMibTrapDescription}
             STATUS  current
             DESCRIPTION
             "IDS Association Flood Attack "
              ::= { mibTraps 44}               

idsDisassociationFloodAttack  NOTIFICATION-TYPE
             OBJECTS   { trapMibTrapSeverity,trapMibTrapDescription}
             STATUS  current
             DESCRIPTION
             "IDS Disassociation Flood Attack "
              ::= { mibTraps 45}               

idsAuthenticationFailureAttack  NOTIFICATION-TYPE
             OBJECTS   { trapMibTrapSeverity,trapMibTrapDescription}
             STATUS  current
             DESCRIPTION
             "IDS Authentication failur Attack "
              ::= { mibTraps 46}               

idsInvalidAuthenticationAttack  NOTIFICATION-TYPE
             OBJECTS   { trapMibTrapSeverity,trapMibTrapDescription}
             STATUS  current
             DESCRIPTION
             "IDS Invalid Authentication attack "
              ::= { mibTraps 47}               

idsAuthenticationFloodAttack  NOTIFICATION-TYPE
             OBJECTS   { trapMibTrapSeverity,trapMibTrapDescription}
             STATUS  current
             DESCRIPTION
             "IDS Authentication flood attack "
              ::= { mibTraps 48}               

idsDeauthenticationFloodAttack  NOTIFICATION-TYPE
             OBJECTS   { trapMibTrapSeverity,trapMibTrapDescription}
             STATUS  current
             DESCRIPTION
             "IDS Deauthentication flood attack "
              ::= { mibTraps 49}               

idsRfJammingAttack  NOTIFICATION-TYPE
             OBJECTS   { trapMibTrapSeverity,trapMibTrapDescription}
             STATUS  current
             DESCRIPTION
             "IDS RF Jamming attack "
              ::= { mibTraps 50}               

idsEapolStartAttack  NOTIFICATION-TYPE
             OBJECTS   { trapMibTrapSeverity,trapMibTrapDescription}
             STATUS  current
             DESCRIPTION
             "IDS Eapol start attack "
              ::= { mibTraps 51}               

idsEapolLogoffAttack  NOTIFICATION-TYPE
             OBJECTS   { trapMibTrapSeverity,trapMibTrapDescription}
             STATUS  current
             DESCRIPTION
             "IDS Eapol Logoff attack "
              ::= { mibTraps 52}               

idsDeauthBcastAttack  NOTIFICATION-TYPE
             OBJECTS   { trapMibTrapSeverity,trapMibTrapDescription}
             STATUS  current
             DESCRIPTION
             "IDS Deauthentication broadcast attack "
              ::= { mibTraps 53}               

radiusAttack  NOTIFICATION-TYPE
             OBJECTS   { trapMibTrapSeverity,trapMibTrapDescription}
             STATUS  current
             DESCRIPTION
             "Radius attack "
              ::= { mibTraps 54}               

radiusChangedSelection  NOTIFICATION-TYPE
             OBJECTS   { trapMibTrapSeverity,trapMibTrapDescription}
             STATUS  current
             DESCRIPTION
             "Radius changed selection"
              ::= { mibTraps 55}               

lastRadiusFailed  NOTIFICATION-TYPE
             OBJECTS   { trapMibTrapSeverity,trapMibTrapDescription}
             STATUS  current
             DESCRIPTION
             "Last Radius failed"
              ::= { mibTraps 56}               

rfLocalizationFailed  NOTIFICATION-TYPE
             OBJECTS   { trapMibTrapSeverity,trapMibTrapDescription}
             STATUS  current
             DESCRIPTION
             "RF Localization failed"
              ::= { mibTraps 57}               
 
 
unmatchedApHwDetection NOTIFICATION-TYPE
             OBJECTS   { trapMibTrapSeverity,trapMibTrapDescription}
             STATUS  current
             DESCRIPTION
             "Access Point HW type detection error"
              ::= { mibTraps 58}   
 
fwUpgradeStart NOTIFICATION-TYPE
             OBJECTS   { trapMibTrapSeverity,trapMibTrapDescription}
             STATUS  current
             DESCRIPTION
	     "Firmware upgrade has started"
	     ::= { mibTraps 59}

fwUpgradeEnded NOTIFICATION-TYPE
	OBJECTS   { trapMibTrapSeverity,trapMibTrapDescription}
	STATUS  current
	DESCRIPTION
	"Firmware upgrade has endded"
	::= { mibTraps 60}

fwUpgradeProgress NOTIFICATION-TYPE
	OBJECTS   { trapMibTrapSeverity,trapMibTrapDescription}
	STATUS  current
	DESCRIPTION
	"Firmware upgrade progress OK"
	::= { mibTraps 61}

fwUpgradeFailed NOTIFICATION-TYPE
	OBJECTS   { trapMibTrapSeverity,trapMibTrapDescription}
	STATUS  current
	DESCRIPTION
	"Firmware upgrade has failed"
	::= { mibTraps 62}

fwReconfigureEnded NOTIFICATION-TYPE
	OBJECTS   { trapMibTrapSeverity,trapMibTrapDescription}
	STATUS  current
	DESCRIPTION
	"Reconfigure procedire has ended"
	::= { mibTraps 63}

diagnosticReport  NOTIFICATION-TYPE
	OBJECTS   { trapMibTrapSeverity,trapMibTrapDescription}
	STATUS  current
	DESCRIPTION
	"Diadnostic report"
	::= { mibTraps 64}


apIncompatibility NOTIFICATION-TYPE
	OBJECTS   { trapMibTrapSeverity,trapMibTrapDescription}
	STATUS  current
	DESCRIPTION
	"Access Point incompatibility."
	::= { mibTraps 65}

apCompatibility NOTIFICATION-TYPE
	OBJECTS   { trapMibTrapSeverity,trapMibTrapDescription}
	STATUS  current
	DESCRIPTION
	"Access Point compatibility."
	::= { mibTraps 66}
 
clientIgnoreMtu NOTIFICATION-TYPE
	OBJECTS   { trapMibTrapSeverity,trapMibTrapDescription}
	STATUS  current
	DESCRIPTION
	"Wireless Client ignored MTU ."
	::= { mibTraps 67}

redundancySwitchOver NOTIFICATION-TYPE
	OBJECTS   { trapMibTrapSeverity,trapMibTrapDescription}
	STATUS  current
	DESCRIPTION
	"Switch Cascading redundancy activated on EDGE."
	::= { mibTraps 68}

fwReconfigureStarted NOTIFICATION-TYPE
	OBJECTS   { trapMibTrapSeverity,trapMibTrapDescription}
	STATUS  current
	DESCRIPTION
	"Notify reconfigure started."
	::= { mibTraps 69}

edgeConnected NOTIFICATION-TYPE
        OBJECTS   { trapMibTrapSeverity,trapMibTrapDescription}
        STATUS  current
        DESCRIPTION
        "Edge Connected."
        ::= { mibTraps 70}

edgeDisconnected NOTIFICATION-TYPE
        OBJECTS   { trapMibTrapSeverity,trapMibTrapDescription}
        STATUS  current
        DESCRIPTION
        "Edge Disconnected."
        ::= { mibTraps 71}




clientSepIP NOTIFICATION-TYPE
        OBJECTS   { trapMibTrapSeverity,trapMibTrapDescription}
        STATUS  current
        DESCRIPTION
        "Set Client IP."
        ::= { mibTraps 72}

startShStarted NOTIFICATION-TYPE
        OBJECTS   { trapMibTrapSeverity,trapMibTrapDescription}
        STATUS  current
        DESCRIPTION
        "Start.sh Started."
        ::= { mibTraps 73}

startShEnded NOTIFICATION-TYPE
        OBJECTS   { trapMibTrapSeverity,trapMibTrapDescription}
        STATUS  current
        DESCRIPTION
        "Start.sh Ended."
        ::= { mibTraps 74}

bootStarted NOTIFICATION-TYPE
        OBJECTS   { trapMibTrapSeverity,trapMibTrapDescription}
        STATUS  current
        DESCRIPTION
        "Starting Boot."
        ::= { mibTraps 75}

wirelessStatusAction NOTIFICATION-TYPE
        OBJECTS   { trapMibTrapSeverity,trapMibTrapDescription}
        STATUS  current
        DESCRIPTION
        "Changed Wireless Status (On/Off)."
        ::= { mibTraps 76}

radioReset NOTIFICATION-TYPE
        OBJECTS   { trapMibTrapSeverity,trapMibTrapDescription}
        STATUS  current
        DESCRIPTION
        "Reset Radio"
        ::= { mibTraps 77}

apReset NOTIFICATION-TYPE
        OBJECTS   { trapMibTrapSeverity,trapMibTrapDescription}
        STATUS  current
        DESCRIPTION
        "Reset AP"
        ::= { mibTraps 78}

poeReset NOTIFICATION-TYPE
        OBJECTS   { trapMibTrapSeverity,trapMibTrapDescription}
        STATUS  current
        DESCRIPTION
        "Reset POE"
        ::= { mibTraps 79}

licenseValidityFailed NOTIFICATION-TYPE
        OBJECTS   { trapMibTrapSeverity,trapMibTrapDescription}
        STATUS  current
        DESCRIPTION
        "License validity failed"
        ::= { mibTraps 80}


-- ================================================================
--
-- Global parameters               

stdoutLevelBitmap OBJECT-TYPE
SYNTAX Integer32 (0..255)
MAX-ACCESS read-write
STATUS  current
DESCRIPTION
"n/a"
::= { generalParams 1  }

apRetry OBJECT-TYPE
SYNTAX Integer32 (0..1)
MAX-ACCESS read-write
STATUS  current
DESCRIPTION
"n/a"
::= { generalParams 2  }

devRetry OBJECT-TYPE
SYNTAX Integer32 (0..1)
MAX-ACCESS read-write
STATUS  current
DESCRIPTION
"n/a"
::= { generalParams 3  }

switchFpgaDesign OBJECT-TYPE
SYNTAX DisplayString
MAX-ACCESS read-write
STATUS  current
DESCRIPTION
"n/a"
::= { generalParams 4  }

xmlFormat OBJECT-TYPE
SYNTAX DisplayString
MAX-ACCESS read-write
STATUS  current
DESCRIPTION
"n/a"
::= { generalParams 5  }


rateAdaptationInterval OBJECT-TYPE
SYNTAX Integer32 (0..1000)
MAX-ACCESS read-write
STATUS  current
DESCRIPTION
"n/a"
::= { generalParams 6 }

fastHandoff OBJECT-TYPE
SYNTAX Integer32 (0..1)
MAX-ACCESS read-write
STATUS  current
DESCRIPTION
"n/a"
::= { generalParams 7 }


iapp OBJECT-TYPE
SYNTAX Integer32 (0..1)
MAX-ACCESS read-write
STATUS  current
DESCRIPTION
"n/a"
::= { generalParams 8 }

beaconInt OBJECT-TYPE
SYNTAX Integer32 (100..10000)
MAX-ACCESS read-write
STATUS  current
DESCRIPTION
"n/a"
::= { generalParams 9 }

beaconsInBand OBJECT-TYPE
SYNTAX Integer32 (0..1)
MAX-ACCESS read-write
STATUS  current
DESCRIPTION
"n/a"
::= { generalParams 10 }

accessListAuth OBJECT-TYPE
SYNTAX Integer32 (0..1)
MAX-ACCESS read-write
STATUS  current
DESCRIPTION
"n/a"
::= { generalParams 11 }

atherosTimestamp OBJECT-TYPE
SYNTAX Integer32 
MAX-ACCESS read-write
STATUS  current
DESCRIPTION
"n/a"
::= { generalParams 12 }

maxHwKeys OBJECT-TYPE
SYNTAX Integer32 (0..256)
MAX-ACCESS read-write
STATUS  current
DESCRIPTION
"n/a"
::= { generalParams 13 }

offloadTableSize OBJECT-TYPE
SYNTAX Integer32 (0..2007)
MAX-ACCESS read-write
STATUS  current
DESCRIPTION
"n/a"
::= { generalParams 14 }

wlessIface OBJECT-TYPE
SYNTAX DisplayString
MAX-ACCESS read-write
STATUS  current
DESCRIPTION
"n/a"
::= { generalParams 15 }

fhoPkc OBJECT-TYPE
SYNTAX Integer32 (0..1)
MAX-ACCESS read-write
STATUS  current
DESCRIPTION
"n/a"
::= { generalParams 16 }

fhoPreauth OBJECT-TYPE
SYNTAX Integer32 (0..1)
MAX-ACCESS read-write
STATUS  current
DESCRIPTION
"n/a"
::= { generalParams 17 }

fhoAging OBJECT-TYPE
SYNTAX Integer32 (0..1)
MAX-ACCESS read-write
STATUS  current
DESCRIPTION
"n/a"
::= { generalParams 18 }

vsNumber OBJECT-TYPE
SYNTAX Integer32 (1..3)
MAX-ACCESS read-write
STATUS  current
DESCRIPTION
"Number of configure Virtual switches. "
::= { generalParams 19 }


rapdFilter OBJECT-TYPE
SYNTAX Integer32 (0..1)
MAX-ACCESS read-write
STATUS  current
DESCRIPTION
"Rogue AP Message filter flag. "
::= { generalParams 20 }

fpga4ChannelsCap OBJECT-TYPE
SYNTAX Integer32 (0..1)
MAX-ACCESS read-write
STATUS  current
DESCRIPTION
"FPGA Working mode support for single/dual CPUS. "
::= { generalParams 21 }

busiestClientAid OBJECT-TYPE
SYNTAX Integer32 (1..2007)
MAX-ACCESS read-only
STATUS  current
DESCRIPTION
"The Switch busiest client (by tx octet per interval). "
::= { generalParams 22 }


truereuseDisplay OBJECT-TYPE
SYNTAX Integer32 (1..2007)
MAX-ACCESS read-only
STATUS  current
DESCRIPTION
"N/A). "
::= { generalParams 23 }

useSmartBeaconsLogic OBJECT-TYPE
SYNTAX Integer32 (1..2007)
MAX-ACCESS read-only
STATUS  current
DESCRIPTION
"The Switch global smart beacons flag Enable/Disable "
::= { generalParams 24 }

apWatchDog OBJECT-TYPE
SYNTAX Integer32 (1..2007)
MAX-ACCESS read-only
STATUS  current
DESCRIPTION
"Flsg to enable/Disable AP wotchdog. "
::= { generalParams 25 }

productType OBJECT-TYPE
SYNTAX Integer32 (0..7)
MAX-ACCESS read-only
STATUS  current
DESCRIPTION
"The Switch product type 0 xScale, 2 freeScale standalon, 3 freeScale Edge, 4 Controller, 5 Mega, 6 Cascading"
::= { generalParams 26 }

allowNonAckRssi OBJECT-TYPE
SYNTAX Integer32 (1..2007)
MAX-ACCESS read-only
STATUS  current
DESCRIPTION
"N/A "
::= { generalParams 27 }

filterNonAckRssi OBJECT-TYPE
SYNTAX Integer32 (1..2007)
MAX-ACCESS read-only
STATUS  current
DESCRIPTION
"N/A "
::= { generalParams 28 }

sameBandSize OBJECT-TYPE
SYNTAX Integer32 (1..16)
MAX-ACCESS read-only
STATUS  current
DESCRIPTION
"The Switch same band size - number of channels in the same band. "
::= { generalParams 29 }

redundancyStatus OBJECT-TYPE
SYNTAX Integer32 (0..1)
MAX-ACCESS read-only
STATUS  current
DESCRIPTION
"The Switch redundancy status Active/Not Active. "
::= { generalParams 30 }

enable80211d OBJECT-TYPE
SYNTAX Integer32 (0..1)
MAX-ACCESS read-only
STATUS  current
DESCRIPTION
"Enable / Disable 80211d global feature flag. "
::= { generalParams 31 }

enableAllEssid80211d OBJECT-TYPE
SYNTAX Integer32 (0..1)
MAX-ACCESS read-only
STATUS  current
DESCRIPTION
"N/A. "
::= { generalParams 32 }

enablePerEssid80211d OBJECT-TYPE
SYNTAX Integer32 (0..1)
MAX-ACCESS read-only
STATUS  current
DESCRIPTION
"N/A. "
::= { generalParams 33 }

enableAS OBJECT-TYPE
SYNTAX Integer32 (0..1)
MAX-ACCESS read-only
STATUS  current
DESCRIPTION
"N/A. "
::= { generalParams 34 }

aeroscoutSupport OBJECT-TYPE
SYNTAX Integer32 (0..1)
MAX-ACCESS read-only
STATUS  current
DESCRIPTION
"N/A. "
::= { generalParams 35 }

aeroscoutTagSupport OBJECT-TYPE
SYNTAX Integer32 (0..1)
MAX-ACCESS read-only
STATUS  current
DESCRIPTION
"N/A. "
::= { generalParams 36 }

aeroscoutAll OBJECT-TYPE
SYNTAX Integer32 (0..1)
MAX-ACCESS read-only
STATUS  current
DESCRIPTION
"N/A. "
::= { generalParams 37 }

aeroscoutPer OBJECT-TYPE
SYNTAX Integer32 (0..1)
MAX-ACCESS read-only
STATUS  current
DESCRIPTION
"N/A. "
::= { generalParams 38 }

enableMacAuth OBJECT-TYPE
SYNTAX Integer32 (0..1)
MAX-ACCESS read-only
STATUS  current
DESCRIPTION
"Enable the MAC authentication feature. "
::= { generalParams 39 }

rateAdaptationRssiAging OBJECT-TYPE
SYNTAX Integer32 (0..1)
MAX-ACCESS read-only
STATUS  current
DESCRIPTION
"N/A. "
::= { generalParams 40 }

cyc1EnhancedMode OBJECT-TYPE
SYNTAX Integer32 (0..1)
MAX-ACCESS read-only
STATUS  current
DESCRIPTION
"N/A. "
::= { generalParams 41 }

rateAdaptationOffset OBJECT-TYPE
SYNTAX Integer32 (0..1)
MAX-ACCESS read-only
STATUS  current
DESCRIPTION
"N/A. "
::= { generalParams 42 }

cmdMode OBJECT-TYPE
SYNTAX Integer32 (0..1)
MAX-ACCESS read-only
STATUS  current
DESCRIPTION
"N/A. "
::= { generalParams 43 }

smartBeaconsCalcInterval OBJECT-TYPE
SYNTAX Integer32 
MAX-ACCESS read-only
STATUS  current
DESCRIPTION
"N/A. "
::= { generalParams 44 }

smartBeaconsMulticastCalcInterval OBJECT-TYPE
SYNTAX Integer32
MAX-ACCESS read-only
STATUS  current
DESCRIPTION
"N/A. "
::= { generalParams 45 }

aeroscoutDebugPrint OBJECT-TYPE
SYNTAX Integer32 
MAX-ACCESS read-only
STATUS  current
DESCRIPTION
"N/A. "
::= { generalParams 46 }

aeroscoutSupportCompoundedMessage OBJECT-TYPE
SYNTAX Integer32
MAX-ACCESS read-only
STATUS  current
DESCRIPTION
"N/A. "
::= { generalParams 47 }

aeroscoutCalcRssi OBJECT-TYPE
SYNTAX Integer32 (0..1)
MAX-ACCESS read-only
STATUS  current
DESCRIPTION
"N/A. "
::= { generalParams 48 }

aeroscout2Xscale OBJECT-TYPE
SYNTAX Integer32 
MAX-ACCESS read-only
STATUS  current
DESCRIPTION
"N/A. "
::= { generalParams 49 }

ignorePsbitInMgmt OBJECT-TYPE
SYNTAX Integer32 
MAX-ACCESS read-only
STATUS  current
DESCRIPTION
"N/A. "
::= { generalParams 50 }


apEncryption OBJECT-TYPE
SYNTAX Integer32 
MAX-ACCESS read-only
STATUS  current
DESCRIPTION
"N/A. "
::= { generalParams 51 }

ekcTimeout OBJECT-TYPE
SYNTAX Integer32 
MAX-ACCESS read-only
STATUS  current
DESCRIPTION
"N/A. "
::= { generalParams 52 }

baTimeout OBJECT-TYPE
SYNTAX Integer32 
MAX-ACCESS read-only
STATUS  current
DESCRIPTION
"N/A. "
::= { generalParams 53 }

filterMulticast OBJECT-TYPE
SYNTAX Integer32 
MAX-ACCESS read-only
STATUS  current
DESCRIPTION
"N/A. "
::= { generalParams 54 }

greTunnelRemoteIp OBJECT-TYPE
SYNTAX Integer32 
MAX-ACCESS read-only
STATUS  current
DESCRIPTION
"N/A. "
::= { generalParams 55 }

greTunnelLocalIp OBJECT-TYPE
SYNTAX Integer32 
MAX-ACCESS read-only
STATUS  current
DESCRIPTION
"N/A. "
::= { generalParams 56 }

greTunnelNetmask OBJECT-TYPE
SYNTAX Integer32 
MAX-ACCESS read-only
STATUS  current
DESCRIPTION
"N/A. "
::= { generalParams 57 }

greTunnelNextHop OBJECT-TYPE
SYNTAX Integer32 
MAX-ACCESS read-only
STATUS  current
DESCRIPTION
"N/A. "
::= { generalParams 58 }

greTunnelVlan OBJECT-TYPE
SYNTAX Integer32 
MAX-ACCESS read-only
STATUS  current
DESCRIPTION
"N/A. "
::= { generalParams 59 }

systemMtu OBJECT-TYPE
SYNTAX Integer32 
MAX-ACCESS read-only
STATUS  current
DESCRIPTION
"N/A. "
::= { generalParams 60 }

icmpInterval OBJECT-TYPE
SYNTAX Integer32
MAX-ACCESS read-only
STATUS  current
DESCRIPTION
"N/A. "
::= { generalParams 61 }

maxLargePackets OBJECT-TYPE
SYNTAX Integer32 
MAX-ACCESS read-only
STATUS  current
DESCRIPTION
"N/A. "
::= { generalParams 62 }

enableOffload OBJECT-TYPE
SYNTAX Integer32 
MAX-ACCESS read-only
STATUS  current
DESCRIPTION
"N/A. "
::= { generalParams 63 }

enableDownzeap OBJECT-TYPE
SYNTAX Integer32 
MAX-ACCESS read-only
STATUS  current
DESCRIPTION
"N/A. "
::= { generalParams 64 }

enableUpzeap OBJECT-TYPE
SYNTAX Integer32 
MAX-ACCESS read-only
STATUS  current
DESCRIPTION
"N/A. "
::= { generalParams 65 }

macAuthSeparator OBJECT-TYPE
SYNTAX Integer32 
MAX-ACCESS read-only
STATUS  current
DESCRIPTION
"N/A. "
::= { generalParams 66 }

macAuthCase OBJECT-TYPE
SYNTAX Integer32 
MAX-ACCESS read-only
STATUS  current
DESCRIPTION
"N/A. "
::= { generalParams 67 }

enablePri OBJECT-TYPE
SYNTAX Integer32 
MAX-ACCESS read-only
STATUS  current
DESCRIPTION
"N/A. "
::= { generalParams 68 }

-- =====================================================================
--
--   FW update parameters group

fwuServerIpAddress OBJECT-TYPE
SYNTAX DisplayString
MAX-ACCESS read-write
STATUS  current
DESCRIPTION
"Remote host IP address"
::= { fwUpdateGroup 1 }

fwuUserName OBJECT-TYPE
SYNTAX DisplayString
MAX-ACCESS read-write
STATUS  current
DESCRIPTION
"User name of remote host session."
::= { fwUpdateGroup 2 }

fwuFilePath OBJECT-TYPE
SYNTAX DisplayString
MAX-ACCESS read-write
STATUS  current
DESCRIPTION
"File path in remote host."
::= { fwUpdateGroup 3 }

fwuFileName OBJECT-TYPE
SYNTAX DisplayString
MAX-ACCESS read-write
STATUS  current
DESCRIPTION
"File name to to read from remote host"
::= { fwUpdateGroup 4 }

fwuVersionName OBJECT-TYPE
SYNTAX DisplayString
MAX-ACCESS read-write
STATUS  current
DESCRIPTION
"File name to to read from remote host"
::= { fwUpdateGroup 5 }

fwuStatusDescription OBJECT-TYPE
SYNTAX DisplayString
MAX-ACCESS read-only
STATUS  current
DESCRIPTION
"Firmware upgrade progress status description"
::= { fwUpdateGroup 6 }

fwuStatusProgress OBJECT-TYPE
SYNTAX Integer32 (0..100)
MAX-ACCESS read-only
STATUS  current
DESCRIPTION
"Firmware upgrade progress status ID."
::= { fwUpdateGroup 7 }

fwuDelay OBJECT-TYPE
SYNTAX Integer32 (0..100000)
MAX-ACCESS read-write
STATUS  current
DESCRIPTION
"Procedure delay interval in secounds"
::= { fwUpdateGroup 8 }

fwuParam OBJECT-TYPE
SYNTAX Integer32
MAX-ACCESS read-write
STATUS  current
DESCRIPTION
"Genral int parameter, use for the operation type"
::= { fwUpdateGroup 9 }

fwuIndex OBJECT-TYPE
SYNTAX Integer32 (0..32)
MAX-ACCESS read-write
STATUS  current
DESCRIPTION
"The object index to write the file content"
::= { fwUpdateGroup 10 }





-- =====================================================================
--
-- Platform parameters
--
inventoryBaseMac OBJECT-TYPE
SYNTAX DisplayString
MAX-ACCESS read-only
STATUS  current
DESCRIPTION
"The platform base MAC address"
::= { platformInfo 1 }

inventoryRegDomain OBJECT-TYPE
SYNTAX DisplayString
MAX-ACCESS read-only
STATUS  current
DESCRIPTION
"Platform regulatory domain"
::= { platformInfo 2 }

inventoryMacRange OBJECT-TYPE
SYNTAX Integer32 (0..32)
MAX-ACCESS read-only
STATUS  current
DESCRIPTION
"Platform regulatory domain"
::= { platformInfo 3 }

inventorySerialNum OBJECT-TYPE
SYNTAX DisplayString
MAX-ACCESS read-only
STATUS  current
DESCRIPTION
"Platform serial number"
::= { platformInfo 4 }

inventoryCatalogNum OBJECT-TYPE
SYNTAX DisplayString
MAX-ACCESS read-only
STATUS  current
DESCRIPTION
"Platform catalog number"
::= { platformInfo 5 }

inventoryHwPcbVer OBJECT-TYPE
SYNTAX DisplayString
MAX-ACCESS read-only
STATUS  current
DESCRIPTION
"Platform catalog number"
::= { platformInfo 6 }


inventoryHwAssemblyVer OBJECT-TYPE
SYNTAX DisplayString
MAX-ACCESS read-only
STATUS  current
DESCRIPTION
"Platform catalog number"
::= { platformInfo 7 }

inventoryStratixKey OBJECT-TYPE
SYNTAX Integer32 (0..4)
MAX-ACCESS read-only
STATUS  current
DESCRIPTION
"Platform stratix key"
::= { platformInfo 8 }

inventoryCpyType OBJECT-TYPE
SYNTAX DisplayString
MAX-ACCESS read-only
STATUS  current
DESCRIPTION
"Platform CPU type - Master/Slave"
::= { platformInfo 9 }

inventoryCompanyName OBJECT-TYPE
SYNTAX DisplayString
MAX-ACCESS read-only
STATUS  current
DESCRIPTION
"Platform company name"
::= { platformInfo 10 }

inventorySwVer OBJECT-TYPE
SYNTAX DisplayString
MAX-ACCESS read-only
STATUS  current
DESCRIPTION
"Platform software version"
::= { platformInfo 11 }




-- =====================================================================
--
-- RTC Real Time Clock
--

rtcSetMM OBJECT-TYPE
SYNTAX DisplayString
MAX-ACCESS read-write
STATUS  current
DESCRIPTION
"Month value to set 01 - 12 "
::= { rtcInfo 1 }

rtcSetDD OBJECT-TYPE
SYNTAX DisplayString
MAX-ACCESS read-write
STATUS  current
DESCRIPTION
"Day value to set 01-31"
::= { rtcInfo 2 }

rtcSetHh OBJECT-TYPE
SYNTAX DisplayString
MAX-ACCESS read-write
STATUS  current
DESCRIPTION
"Houre value to set 00-23"
::= { rtcInfo 3 }

rtcSetMm OBJECT-TYPE
SYNTAX DisplayString
MAX-ACCESS read-write
STATUS  current
DESCRIPTION
"Minuts Value to set 00-59"
::= { rtcInfo 4 }

rtcSetYear OBJECT-TYPE
SYNTAX DisplayString
MAX-ACCESS read-write
STATUS  current
DESCRIPTION
"Current platform year"
::= { rtcInfo 5 }


rtcStatus OBJECT-TYPE
SYNTAX DisplayString
MAX-ACCESS read-only
STATUS  current
DESCRIPTION
"Current platform time"
::= { rtcInfo 6 }



-- =====================================================================
--
-- ntp

gmtIndex OBJECT-TYPE
SYNTAX Integer32 
MAX-ACCESS read-write
STATUS current
DESCRIPTION
"A gmt index for (internal uses)"
::= { ntp 1 }


gmtOffset OBJECT-TYPE
SYNTAX DisplayString 
MAX-ACCESS read-write
STATUS current
DESCRIPTION
"The time zone offset format +/-HH:MM"
::= { ntp 2 }


ntpActive OBJECT-TYPE
SYNTAX Integer32
MAX-ACCESS read-write
STATUS current
DESCRIPTION
"The NTP status flag enable/disable"
::= { ntp 3 }


interval OBJECT-TYPE
SYNTAX Integer32
MAX-ACCESS read-write
STATUS current
DESCRIPTION
"NTP update internal 1- 168"
::= { ntp 4 }

use OBJECT-TYPE
SYNTAX Integer32
MAX-ACCESS read-write
STATUS current
DESCRIPTION
"Use IP address for the Main server"
::= { ntp 5 }


use2 OBJECT-TYPE
SYNTAX Integer32
MAX-ACCESS read-write
STATUS current
DESCRIPTION
"Use IP address for the backup server"
::= { ntp 6 }


server OBJECT-TYPE
SYNTAX DisplayString
MAX-ACCESS read-write
STATUS current
DESCRIPTION
"Main server IP/DNS address"
::= { ntp 7 }


bserver OBJECT-TYPE
SYNTAX DisplayString
MAX-ACCESS read-write
STATUS current
DESCRIPTION
"Backup server IP/DNS address"
::= { ntp 8 }


ntpUpdateStatus OBJECT-TYPE
SYNTAX Integer32
MAX-ACCESS read-only
STATUS current
DESCRIPTION
"NTP Update Request Status"
::= { ntp 9 }


-- =====================================================================
--
-- maintenance

reconfigure OBJECT-TYPE
SYNTAX Integer32 
MAX-ACCESS read-write
STATUS current
DESCRIPTION
"Reconfigure switch - new configuration will be set and run"
::= { maintenance 1 }


reboot OBJECT-TYPE
SYNTAX Integer32 
MAX-ACCESS read-write
STATUS current
DESCRIPTION
"Rebbot the switch"
::= { maintenance 2 }

restorConfig OBJECT-TYPE
SYNTAX Integer32 
MAX-ACCESS read-write
STATUS current
DESCRIPTION
"Resor default configuration action."
::= { maintenance 3 }

stationStatAdd OBJECT-TYPE
SYNTAX Integer32 
MAX-ACCESS read-write
STATUS current
DESCRIPTION
"Add station to statistics collection."
::= { maintenance 4 }

stationStatRemove OBJECT-TYPE
SYNTAX Integer32 
MAX-ACCESS read-write
STATUS current
DESCRIPTION
"Remove station from statistics collection."
::= { maintenance 5 }

snmpdReload OBJECT-TYPE
SYNTAX Integer32 
MAX-ACCESS read-write
STATUS current
DESCRIPTION
"Reload SNMP Daemon."
::= { maintenance 6 }

fileOperation OBJECT-TYPE
SYNTAX FileOperationOption 
MAX-ACCESS read-write
STATUS current
DESCRIPTION
"N/A"
::= { maintenance 7 }

firmwareStart OBJECT-TYPE
SYNTAX Integer32 
MAX-ACCESS read-write
STATUS current
DESCRIPTION
"N/A"
::= { maintenance 8 }

updateMACACL OBJECT-TYPE
SYNTAX Integer32 
MAX-ACCESS read-write
STATUS current
DESCRIPTION
"N/A"
::= { maintenance 9 }

restorDefaultMACACL OBJECT-TYPE
SYNTAX Integer32 
MAX-ACCESS read-write
STATUS current
DESCRIPTION
"Resor default Mac Access List ."
::= { maintenance 10 }

setRTC OBJECT-TYPE
SYNTAX Integer32 
MAX-ACCESS read-write
STATUS current
DESCRIPTION
"Activate RTC procedire"
::= { maintenance 11 }

clearDot11Client OBJECT-TYPE
SYNTAX DisplayString 
MAX-ACCESS read-write
STATUS current
DESCRIPTION
"Force disconnection of assiciated station - {MACADDRESS: XX:XX:XX:XX:XX:XX}"
::= { maintenance 12 }

clearClientByName OBJECT-TYPE
SYNTAX DisplayString
MAX-ACCESS read-write
STATUS current
DESCRIPTION
"Force disconnection of assiciated station - {User Name}"
::= { maintenance 13 }

setNTP OBJECT-TYPE
SYNTAX Integer32 
MAX-ACCESS read-write
STATUS current
DESCRIPTION
"Activate NTP procedire"
::= { maintenance 14 }

setEdgeHostName OBJECT-TYPE
SYNTAX Integer32 
MAX-ACCESS read-write
STATUS current
DESCRIPTION
"Update Mega/Cascading Edge slave Host Name"
::= { maintenance 15 }

setCommand OBJECT-TYPE
SYNTAX Integer32 
MAX-ACCESS read-write
STATUS current
DESCRIPTION
"A general action activation command "
::= { maintenance 16 }



-- =====================================================================
--
-- General Commands

generalCommand OBJECT-TYPE
SYNTAX DisplayString
MAX-ACCESS read-write
STATUS  current
DESCRIPTION
"A general command activation allowed at remote switch. "
::= { general 1 }

generalParam OBJECT-TYPE
SYNTAX DisplayString
MAX-ACCESS read-write
STATUS  current
DESCRIPTION
"Input param for the general command. "
::= { general 2 }

generalParam OBJECT-TYPE
SYNTAX Integer32
MAX-ACCESS read-write
STATUS  current
DESCRIPTION
"Input for general integer param. "
::= { general 3 }

generalStatus OBJECT-TYPE
SYNTAX Integer32
MAX-ACCESS read-write
STATUS  current
DESCRIPTION
"Input for general status. "
::= { general 4 }

generalPortStatusString OBJECT-TYPE
SYNTAX DisplayString
MAX-ACCESS read-only
STATUS  current
DESCRIPTION
"Port Status Code String"
::= { general 5 }


-- =====================================================================
--
-- Captive Portal

enableCp OBJECT-TYPE
SYNTAX Integer32 (0..1)
MAX-ACCESS read-write
STATUS  current
DESCRIPTION
"Captive portal global feature flag. "
::= { capivePortal 1 }

vid OBJECT-TYPE
SYNTAX Integer32 (0..4095)
MAX-ACCESS read-write
STATUS  current
DESCRIPTION
"Configration of VLAN for captive portal. "
::= { capivePortal 2 }

cptRule OBJECT-TYPE
SYNTAX Integer32
MAX-ACCESS read-write
STATUS  current
DESCRIPTION
"N/A. "
::= { capivePortal 3 }

secured OBJECT-TYPE
SYNTAX Integer32
MAX-ACCESS read-write
STATUS  current
DESCRIPTION
"N/A. "
::= { capivePortal 4 }

multipleClientsPerUser OBJECT-TYPE
SYNTAX Integer32
MAX-ACCESS read-write
STATUS  current
DESCRIPTION
"N/A. "
::= { capivePortal 5 }

ssl OBJECT-TYPE
SYNTAX Integer32
MAX-ACCESS read-write
STATUS  current
DESCRIPTION
"N/A. "
::= { capivePortal 6 }

cptIpAddress OBJECT-TYPE
SYNTAX Integer32
MAX-ACCESS read-write
STATUS  current
DESCRIPTION
"N/A. "
::= { capivePortal 7 }

cptIpMask OBJECT-TYPE
SYNTAX Integer32
MAX-ACCESS read-write
STATUS  current
DESCRIPTION
"N/A. "
::= { capivePortal 8 }

cptProtocol OBJECT-TYPE
SYNTAX Integer32
MAX-ACCESS read-write
STATUS  current
DESCRIPTION
"N/A. "
::= { capivePortal 9 }

cptPortsFrom OBJECT-TYPE
SYNTAX Integer32
MAX-ACCESS read-write
STATUS  current
DESCRIPTION
"N/A. "
::= { capivePortal 10 }

cptPortsTo OBJECT-TYPE
SYNTAX Integer32
MAX-ACCESS read-write
STATUS  current
DESCRIPTION
"N/A. "
::= { capivePortal 11 }


-- =====================================================================
--
-- Inband Management

enableIbm OBJECT-TYPE
SYNTAX Integer32 (0..1)
MAX-ACCESS read-write
STATUS  current
DESCRIPTION
"Global flag to Enable/Disable the In band management feature. "
::= { ibm 1 }



-- =====================================================================
--
-- redundancy Parameters


status OBJECT-TYPE
SYNTAX Integer32 
MAX-ACCESS read-write
STATUS current
DESCRIPTION
"The redundancy status"
::= { redundancyParameters 1 }


monitoredIp OBJECT-TYPE
SYNTAX DisplayString 
MAX-ACCESS read-write
STATUS current
DESCRIPTION
"The ip address of the monitored device"
::= { redundancyParameters 2 }


checkFrequency OBJECT-TYPE
SYNTAX Integer32
MAX-ACCESS read-write
STATUS current
DESCRIPTION
"The frequency of the lifeliness checks"
::= { redundancyParameters 3 }


checkThreshold OBJECT-TYPE
SYNTAX Integer32
MAX-ACCESS read-write
STATUS current
DESCRIPTION
"The check threshold"
::= { redundancyParameters 4 }



role OBJECT-TYPE
SYNTAX DisplayString
MAX-ACCESS read-write
STATUS current
DESCRIPTION
"The role of the device in redundancy"
::= { redundancyParameters 5 }


keepAliveTarget OBJECT-TYPE
SYNTAX DisplayString
MAX-ACCESS read-write
STATUS current
DESCRIPTION
"The keepalive target ip address"
::= { redundancyParameters 6 }

cascadingEdge OBJECT-TYPE
SYNTAX DisplayString
MAX-ACCESS read-write
STATUS current
DESCRIPTION
"The Cascading edge ip address"
::= { redundancyParameters 7 }


-- =====================================================================
--
-- Core Redundancy

coreRedundancyMode OBJECT-TYPE
SYNTAX Integer32 (0..1)
MAX-ACCESS read-write
STATUS  current
DESCRIPTION
"Flag to Enable/Disable thecascading Core redundancy feature. "
::= { coreRedundancy 1 }

coreRedundancyInterval OBJECT-TYPE
SYNTAX Integer32 (1..30)
MAX-ACCESS read-write
STATUS  current
DESCRIPTION
"The Interval of core connection sample. "
::= { coreRedundancy 2 }

coreRedundancyTimeout OBJECT-TYPE
SYNTAX Integer32 (1..30)
MAX-ACCESS read-write
STATUS  current
DESCRIPTION
"The maximum down time allow befor redundancy is activated (sec). "
::= { coreRedundancy 3 }

edgeSlaveIp OBJECT-TYPE
SYNTAX DisplayString
MAX-ACCESS read-write
STATUS  current
DESCRIPTION
"The cascading Edge IP address. "
::= { coreRedundancy 4 }


-- =====================================================================
--
-- Nomadic BSSID

enable OBJECT-TYPE
SYNTAX Integer32
MAX-ACCESS read-write
STATUS  current
DESCRIPTION
"N/A. "
::= { nomadicBssid 1 }


oui OBJECT-TYPE
SYNTAX DisplayString
MAX-ACCESS read-write
STATUS  current
DESCRIPTION
"N/A. "
::= { nomadicBssid 2 }





-- =====================================================================
--
-- snmp

snmpTrapStatus OBJECT-TYPE
SYNTAX Integer32 (0..1)
MAX-ACCESS read-write
STATUS current
DESCRIPTION
"The trap status"
::= { snmp 1 }


snmpManagerIp OBJECT-TYPE
SYNTAX DisplayString 
MAX-ACCESS read-write
STATUS current
DESCRIPTION
"The manager ip address"
::= { snmp 2 }


snmpTrapCommunity OBJECT-TYPE
SYNTAX DisplayString
MAX-ACCESS read-write
STATUS current
DESCRIPTION
"The trap community"
::= { snmp 3 }




-- =====================================================================
--
--
-- regulatory

country OBJECT-TYPE
SYNTAX DisplayString 
MAX-ACCESS read-write
STATUS current
DESCRIPTION
"The Gegulatiry Domain Country"
::= { regulatory 1 }

domain OBJECT-TYPE
SYNTAX DisplayString 
MAX-ACCESS read-write
STATUS current
DESCRIPTION
"The Gegulatiry Domain"
::= { regulatory 2 }

userDomain OBJECT-TYPE
SYNTAX DisplayString 
MAX-ACCESS read-write
STATUS current
DESCRIPTION
"The Regulatiry User selection "
::= { regulatory 3 }







-- ====================================================================
-- True Reuse 
--

maxLinks OBJECT-TYPE
SYNTAX Integer32 
MAX-ACCESS read-write
STATUS current
DESCRIPTION
"Reuse man linkks"
::= { reuse 1 }

rssiDetectionMargin OBJECT-TYPE
SYNTAX Integer32 
MAX-ACCESS read-write
STATUS current
DESCRIPTION
"N/A"
::= { reuse 2 }

ap2apCalcInt OBJECT-TYPE
SYNTAX Integer32 
MAX-ACCESS read-write
STATUS current
DESCRIPTION
"N/A"
::= { reuse 3 }

apBlockListCalcInt OBJECT-TYPE
SYNTAX Integer32 
MAX-ACCESS read-write
STATUS current
DESCRIPTION
"N/A"
::= { reuse 4 }

ap2apPrintInt OBJECT-TYPE
SYNTAX Integer32 
MAX-ACCESS read-write
STATUS current
DESCRIPTION
"N/A"
::= { reuse 5 }

apBlockListPrintInt OBJECT-TYPE
SYNTAX Integer32 
MAX-ACCESS read-write
STATUS current
DESCRIPTION
"N/A"
::= { reuse 6 }

sta2apPrintInt OBJECT-TYPE
SYNTAX Integer32 
MAX-ACCESS read-write
STATUS current
DESCRIPTION
"N/A"
::= { reuse 7 }

setsPrintInt OBJECT-TYPE
SYNTAX Integer32 
MAX-ACCESS read-write
STATUS current
DESCRIPTION
"N/A"
::= { reuse 8 }

linkDiffMargin OBJECT-TYPE
SYNTAX Integer32 
MAX-ACCESS read-write
STATUS current
DESCRIPTION
"N/A"
::= { reuse 9 }

allowUplinkPrints OBJECT-TYPE
SYNTAX Integer32 
MAX-ACCESS read-write
STATUS current
DESCRIPTION
"N/A"
::= { reuse 10 }






-- =====================================================================
--
-- channel table
--

channel OBJECT-TYPE
SYNTAX SEQUENCE OF ChannelEntry
MAX-ACCESS not-accessible
STATUS current
DESCRIPTION
"A table that contains information about every channel"
::= { mibObjects 3 }

channelEntry OBJECT-TYPE
SYNTAX ChannelEntry
MAX-ACCESS not-accessible
STATUS current
DESCRIPTION
"A list of the channel parameters. This is indexed
by the index of the channel."
INDEX { channelIndex }
::= { channel 1 }

ChannelEntry ::=
SEQUENCE {
  channelIndex 		                        Integer32,
  mode                                      Integer32,
  channelNum      	                        Integer32,
  retriesNum                               Integer32, 
  macAddress                               DisplayString,   
  bssidMask                                DisplayString,
  disabledChannel	                        Integer32,     
  basicRates                               DisplayString,
  optionalRates                            DisplayString,
  reuseIndex                               Integer32,     
  adaptationRates                          DisplayString,
  rateAdaptationDll                       Integer32,     
  useShortPreamble                        Integer32,     
  forceShortPreamble                      Integer32,  
  rts                                       Integer32,
  extBasicRates                           DisplayString,
  extOptionalRates                        DisplayString,
  vsRadioIndex                            Integer32,
  vsApBitmap                              DisplayString,
  ht40m                                    Integer32,
  htSecondaryChannelOffset               Integer32,
  htNOnly                                 Integer32,
  htSgi                                    Integer32,
  htTxMcs                                 Integer32,
  useWmmCh                                Integer32,
  wmmAckPolicyCh                         Integer32,
  loadBalancing                            Integer32,
  loadBalancingAllowedDiff               Integer32,
  loadBalancingRetiresBeforeFreepass    Integer32,
  noHwTkip                                Integer32,
  noHwRc4                                 Integer32,
  dscp                                      Integer32,
  wmmToDscp                               Integer32,
  htProtection                             Integer32,
  olbcRssi                                 Integer32,
  allowTripleChain                        Integer32,
  legacyChainMask                         Integer32,
  singleStreamChainMask                  Integer32,
  dualStreamChainMask                    Integer32,
  ignoreRatesNum                          Integer32,
  addBRates                               Integer32,  
  channelRowStatus                        RowStatus
}


channelIndex OBJECT-TYPE
SYNTAX Integer32 (1..6)
MAX-ACCESS not-accessible
STATUS current
DESCRIPTION
"The unique identifier of the channel."
::= { channelEntry 1 }


mode OBJECT-TYPE
SYNTAX Integer32 (0..10)
MAX-ACCESS read-write
STATUS current
DESCRIPTION
"The mode of the channel."
::= { channelEntry 2 }

channelNum OBJECT-TYPE
SYNTAX Integer32 (0..256)
MAX-ACCESS read-write
STATUS current
DESCRIPTION
"The channel number."
::= { channelEntry 3 }

retriesNum OBJECT-TYPE
SYNTAX Integer32 (0..15)
MAX-ACCESS read-write
STATUS current
DESCRIPTION
"The channel retries number."
::= { channelEntry 4 }

macAddress OBJECT-TYPE
SYNTAX DisplayString 
MAX-ACCESS read-only
STATUS current
DESCRIPTION
"The channel MAC address."
::= { channelEntry 5 }
                            
bssidMask OBJECT-TYPE
SYNTAX DisplayString 
MAX-ACCESS read-only
STATUS current
DESCRIPTION
"The channel bssid MAC address."
::= { channelEntry 6 }
                                                                 
disabledChannel OBJECT-TYPE
SYNTAX Integer32 (0..1)
MAX-ACCESS read-write
STATUS current
DESCRIPTION
"The disabled channel number."
::= { channelEntry 7 }
               
basicRates OBJECT-TYPE
SYNTAX DisplayString 
MAX-ACCESS read-write
STATUS current
DESCRIPTION
"The basic rates"
::= { channelEntry 8 }

optionalRates OBJECT-TYPE
SYNTAX DisplayString 
MAX-ACCESS read-write
STATUS current
DESCRIPTION
"The optional rates"
::= { channelEntry 9 }
     
reuseIndex OBJECT-TYPE
SYNTAX Integer32
MAX-ACCESS read-write
STATUS current
DESCRIPTION
"Channel Reuse Index option"
::= { channelEntry 10 }
             
adaptationRates OBJECT-TYPE
SYNTAX DisplayString
MAX-ACCESS read-write
STATUS current
DESCRIPTION
"Channel adaptation rates list"
::= { channelEntry 11 }
  
rateAdaptationDll OBJECT-TYPE
SYNTAX Integer32 (0..1)
MAX-ACCESS read-write
STATUS current
DESCRIPTION
"Rate adaptation flag for this essid"
::= { channelEntry 12 }
     
useShortPreamble OBJECT-TYPE
SYNTAX Integer32
MAX-ACCESS read-write
STATUS current
DESCRIPTION
"Channel flag for short preamble use"
::= { channelEntry 13 }
  
forceShortPreamble OBJECT-TYPE
SYNTAX Integer32
MAX-ACCESS read-write
STATUS current
DESCRIPTION
"Channel flag for forcing short preamble use"
::= { channelEntry 14 }
  
rts OBJECT-TYPE
SYNTAX Integer32
MAX-ACCESS read-write
STATUS current
DESCRIPTION
"Channel RTS flag"
::= { channelEntry 15 }
 
extBasicRates OBJECT-TYPE
SYNTAX DisplayString
MAX-ACCESS read-write
STATUS current
DESCRIPTION
"Channel Rate adaptations extended basic rates"
::= { channelEntry 16 }
            
extOptionalRates OBJECT-TYPE
SYNTAX DisplayString
MAX-ACCESS read-write
STATUS current
DESCRIPTION
"Channel Rate adaptations extended optional rates"
::= { channelEntry 17 }

vsRadioIndex OBJECT-TYPE
SYNTAX Integer32
MAX-ACCESS read-write
STATUS current
DESCRIPTION
"Virtual switch real radio index. "
::= { channelEntry 18 }

vsApBitmap OBJECT-TYPE
SYNTAX DisplayString
MAX-ACCESS read-write
STATUS current
DESCRIPTION
"Virtual switch access point bitmap. "
::= { channelEntry 19 }

ht40m OBJECT-TYPE
SYNTAX Integer32
MAX-ACCESS read-write
STATUS current
DESCRIPTION
"N/A. "
::= { channelEntry 20 }

htSecondaryChannelOffset OBJECT-TYPE
SYNTAX Integer32
MAX-ACCESS read-write
STATUS current
DESCRIPTION
"N/A. "
::= { channelEntry 21 }

htNOnly OBJECT-TYPE
SYNTAX Integer32
MAX-ACCESS read-write
STATUS current
DESCRIPTION
"N/A. "
::= { channelEntry 22 }

htSgi OBJECT-TYPE
SYNTAX  Integer32
MAX-ACCESS read-write
STATUS current
DESCRIPTION
"N/A. "
::= { channelEntry 23 }

htTxMcs OBJECT-TYPE
SYNTAX Integer32
MAX-ACCESS read-write
STATUS current
DESCRIPTION
"N/A. "
::= { channelEntry 24 }

useWmmCh OBJECT-TYPE
SYNTAX Integer32
MAX-ACCESS read-write
STATUS current
DESCRIPTION
"N/A. "
::= { channelEntry 25 }

wmmAckPolicyCh OBJECT-TYPE
SYNTAX  Integer32
MAX-ACCESS read-write
STATUS current
DESCRIPTION
"N/A. "
::= { channelEntry 26 }

loadBalancing  OBJECT-TYPE
SYNTAX Integer32
MAX-ACCESS read-write
STATUS current
DESCRIPTION
"N/A. "
::= { channelEntry 27 }

loadBalancingAllowedDiff OBJECT-TYPE
SYNTAX  Integer32
MAX-ACCESS read-write
STATUS current
DESCRIPTION
"N/A. "
::= { channelEntry 28 }

loadBalancingRetiresBeforeFreepass OBJECT-TYPE
SYNTAX  Integer32
MAX-ACCESS read-write
STATUS current
DESCRIPTION
"N/A. "
::= { channelEntry 29 }

noHwTkip OBJECT-TYPE
SYNTAX Integer32
MAX-ACCESS read-write
STATUS current
DESCRIPTION
"N/A. "
::= { channelEntry 30 }

noHwRc4  OBJECT-TYPE
SYNTAX Integer32
MAX-ACCESS read-write
STATUS current
DESCRIPTION
"N/A. "
::= { channelEntry 31 }

dscp OBJECT-TYPE
SYNTAX   Integer32
MAX-ACCESS read-write
STATUS current
DESCRIPTION
"N/A. "
::= { channelEntry 32 }

wmmToDscp OBJECT-TYPE
SYNTAX Integer32
MAX-ACCESS read-write
STATUS current
DESCRIPTION
"N/A. "
::= { channelEntry 33 }

htProtection OBJECT-TYPE
SYNTAX   Integer32
MAX-ACCESS read-write
STATUS current
DESCRIPTION
"N/A. "
::= { channelEntry 34 }

olbcRssi OBJECT-TYPE
SYNTAX   Integer32
MAX-ACCESS read-write
STATUS current
DESCRIPTION
"N/A. "
::= { channelEntry 35 }

allowTripleChain OBJECT-TYPE
SYNTAX  Integer32
MAX-ACCESS read-write
STATUS current
DESCRIPTION
"N/A. "
::= { channelEntry 36 }

legacyChainMask OBJECT-TYPE
SYNTAX  Integer32
MAX-ACCESS read-write
STATUS current
DESCRIPTION
"N/A. "
::= { channelEntry 37 }

singleStreamChainMask OBJECT-TYPE
SYNTAX   Integer32
MAX-ACCESS read-write
STATUS current
DESCRIPTION
"N/A. "
::= { channelEntry 38 }

dualStreamChainMask OBJECT-TYPE
SYNTAX   Integer32
MAX-ACCESS read-write
STATUS current
DESCRIPTION
"N/A. "
::= { channelEntry 39 }

ignoreRatesNum OBJECT-TYPE
SYNTAX   Integer32
MAX-ACCESS read-write
STATUS current
DESCRIPTION
"N/A. "
::= { channelEntry 40 }

addBRates OBJECT-TYPE
SYNTAX   Integer32
MAX-ACCESS read-write
STATUS current
DESCRIPTION
"N/A. "
::= { channelEntry 41 }

channelRowStatus OBJECT-TYPE
SYNTAX RowStatus 
MAX-ACCESS read-write
STATUS current
DESCRIPTION
"Addind - 4 Delete - 6 Row from channel table."
::= { channelEntry 42 }




-- =====================================================================
--
-- essid table
--

essid OBJECT-TYPE
SYNTAX SEQUENCE OF EssidEntry
MAX-ACCESS not-accessible
STATUS current
DESCRIPTION
"A table that contains information about every essid"
::= { mibObjects 4 }


essidEntry OBJECT-TYPE
SYNTAX EssidEntry
MAX-ACCESS not-accessible
STATUS current
DESCRIPTION
"A list of the essid parameters. This is indexed
by the index of the essid."
INDEX { essidIndex }
::= { essid 1 }

EssidEntry ::=
SEQUENCE {
  essidIndex                Integer32,
  name                      DisplayString,
  channelIndex             Integer32,
  bssid                     DisplayString,
  vlanIndex                Integer32,
  useTimPeriod            Integer32,
  disassocTime             Integer32,
  allowAnyEssid           Integer32,
  bcastEssid               Integer32,
  allowStoreAndForward   Integer32,
  allowInterEssForward   Integer32,
  arpCaching               Integer32,
  enableMulticastDup      Integer32,
  enableDynamicBssid      Integer32,
  usePwrMnt               Integer32,
  usPsQMaxSize          Integer32,
  voice                     Integer32,
  useAccessList           Integer32,
  authServer1              Integer32,
  authServer2              Integer32,
  authServer3              Integer32,
  authServer4              Integer32,
  useSecurity              Integer32,
  cipherWep                Integer32,
  cipherWep104             Integer32,
  cipherTkip               Integer32,
  cipherCcmp               Integer32,
  useCipher                Integer32,
  useCrypt                 Integer32,
  useAuth                  Integer32,
  groupCipher              Integer32,
  useWpa                   Integer32,
  auth1x                   Integer32,
  authForce1x              Integer32,
  authWpa                  Integer32,
  authPsk                  Integer32,
  defaultBcastKeyid       Integer32,
  wpa2Only                 Integer32,
  useWpa2                  Integer32,
  aesOnly                  Integer32,
  groupKeyTtl             Integer32,  
  essidEnable80211d       Integer32,
  requiredBeaconsPercentage Integer32,
  aeroscoutMuSupport      Integer32,
  useWmm                   Integer32,
  wmmAckPolicy            Integer32,
  newEssid                 Integer32,
  inBandManagement        Integer32,
  captivePortalEnable     Integer32,
  macAuthServer           Integer32,
  useGre                   Integer32,
  pinpointDhcpClient      Integer32,
  eapolLowestRateEnable  Integer32,
  secMode                  Integer32,
  allowGroupRekey         Integer32,
  handleEapolStart        Integer32,
  handleEapolDelay        Integer32,
  handleEapolPending      Integer32,
  allowEapolData          Integer32,
  allowCountermeasures     Integer32,  
  essRowStatus            RowStatus
}

essidIndex OBJECT-TYPE
SYNTAX Integer32 (0..32)
MAX-ACCESS read-write
STATUS current
DESCRIPTION
"The unique identifier of the essid entry."
::= { essidEntry 1 }

name OBJECT-TYPE
SYNTAX DisplayString
MAX-ACCESS read-write
STATUS current
DESCRIPTION
"ESSID Name - Network name."
::= { essidEntry 2 }
                  
channelIndex OBJECT-TYPE
SYNTAX Integer32 (0..6)
MAX-ACCESS read-write
STATUS current
DESCRIPTION
"ESSID Channel Index."
::= { essidEntry 3 }
          
bssid OBJECT-TYPE
SYNTAX DisplayString
MAX-ACCESS read-only
STATUS current
DESCRIPTION
"BSSID for this ESSID."
::= { essidEntry 4 }
  
vlanIndex OBJECT-TYPE
SYNTAX Integer32 
MAX-ACCESS read-write
STATUS current
DESCRIPTION
"VLAN flag index."
::= { essidEntry 5 }
  
useTimPeriod OBJECT-TYPE
SYNTAX Integer32
MAX-ACCESS read-write
STATUS current
DESCRIPTION
"ESSID Time period."
::= { essidEntry 6 }
  
disassocTime OBJECT-TYPE
SYNTAX Integer32
MAX-ACCESS read-write
STATUS current
DESCRIPTION
"Clients Disassociate time for this ESSID."
::= { essidEntry 7 }
           
allowAnyEssid OBJECT-TYPE
SYNTAX Integer32 (0..1)
MAX-ACCESS read-write
STATUS current
DESCRIPTION
"N/A."
::= { essidEntry 8 }
              
bcastEssid OBJECT-TYPE
SYNTAX Integer32
MAX-ACCESS read-write
STATUS current
DESCRIPTION
"Allowing Bcast flag on this ESSID."
::= { essidEntry 9 }
                   
allowStoreAndForward OBJECT-TYPE
SYNTAX Integer32 (0..1)
MAX-ACCESS read-write
STATUS current
DESCRIPTION
"Store And Forward flag."
::= { essidEntry 10 }
  
allowInterEssForward OBJECT-TYPE
SYNTAX Integer32 (0..1)
MAX-ACCESS read-write
STATUS current
DESCRIPTION
"N/A."
::= { essidEntry 11 }
       
arpCaching OBJECT-TYPE
SYNTAX Integer32 (0..1)
MAX-ACCESS read-write
STATUS current
DESCRIPTION
"Arp Caching flag - Enable/Disable."
::= { essidEntry 12 }
       
enableMulticastDup OBJECT-TYPE
SYNTAX Integer32 (0..1)
MAX-ACCESS read-write
STATUS current
DESCRIPTION
"Multicast duplication flag - Enable/Disable."
::= { essidEntry 13 }
       
enableDynamicBssid OBJECT-TYPE
SYNTAX Integer32 (0..1)
MAX-ACCESS read-write
STATUS current
DESCRIPTION
"Enable dynamic allocation of bssid for each client."
::= { essidEntry 14 }

usePwrMnt OBJECT-TYPE
SYNTAX Integer32 (0..1)
MAX-ACCESS read-write
STATUS current
DESCRIPTION
"Use poer management procedure."
::= { essidEntry 15 }

usPsQMaxSize OBJECT-TYPE
SYNTAX Integer32
MAX-ACCESS read-only
STATUS current
DESCRIPTION
"n/a."
::= { essidEntry 16 }

voice OBJECT-TYPE
SYNTAX Integer32 (0..1)
MAX-ACCESS read-only
STATUS current
DESCRIPTION
"n/a."
::= { essidEntry 17 }

useAccessList OBJECT-TYPE
SYNTAX Integer32 (0..1)
MAX-ACCESS read-write
STATUS current
DESCRIPTION
"Use clients Access list for this ESSID ."
::= { essidEntry 18 }
       
authServer1 OBJECT-TYPE
SYNTAX Integer32
MAX-ACCESS not-accessible
STATUS current
DESCRIPTION
"Authentication server used for this essid"
::= { essidEntry 19 }

authServer2 OBJECT-TYPE
SYNTAX Integer32
MAX-ACCESS not-accessible
STATUS current
DESCRIPTION
"Authentication server used for this essid"
::= { essidEntry 20 }

authServer3 OBJECT-TYPE
SYNTAX Integer32
MAX-ACCESS not-accessible
STATUS current
DESCRIPTION
"Authentication server used for this essid"
::= { essidEntry 21 }

authServer4 OBJECT-TYPE
SYNTAX Integer32
MAX-ACCESS not-accessible
STATUS current
DESCRIPTION
"Authentication server used for this essid  ."
::= { essidEntry 22 }
              
useSecurity OBJECT-TYPE
SYNTAX Integer32
MAX-ACCESS not-accessible
STATUS current
DESCRIPTION
"Security flag for this ESSID."
::= { essidEntry 23 }
                
cipherWep OBJECT-TYPE
SYNTAX Integer32
MAX-ACCESS not-accessible
STATUS current
DESCRIPTION
"N/A."
::= { essidEntry 24 }
                  
cipherWep104 OBJECT-TYPE
SYNTAX Integer32
MAX-ACCESS not-accessible
STATUS current
DESCRIPTION
"N/A."
::= { essidEntry 25 }
  
cipherTkip OBJECT-TYPE
SYNTAX Integer32
MAX-ACCESS not-accessible
STATUS current
DESCRIPTION
"N/A."
::= { essidEntry 26 }
                 
cipherCcmp OBJECT-TYPE
SYNTAX Integer32
MAX-ACCESS not-accessible
STATUS current
DESCRIPTION
"N/A."
::= { essidEntry 27 }
                 
useCipher OBJECT-TYPE
SYNTAX Integer32
MAX-ACCESS not-accessible
STATUS current
DESCRIPTION
"N/A."
::= { essidEntry 28 }
                  
useCrypt OBJECT-TYPE
SYNTAX Integer32
MAX-ACCESS not-accessible
STATUS current
DESCRIPTION
"N/A."
::= { essidEntry 29 }
                   
useAuth OBJECT-TYPE
SYNTAX Integer32
MAX-ACCESS not-accessible
STATUS current
DESCRIPTION
"N/A."
::= { essidEntry 30 }
    
groupCipher OBJECT-TYPE
SYNTAX Integer32
MAX-ACCESS not-accessible
STATUS current
DESCRIPTION
"N/A."
::= { essidEntry 31 }
                
useWpa OBJECT-TYPE
SYNTAX Integer32 (0..1)
MAX-ACCESS read-write
STATUS current
DESCRIPTION
"N/A."
::= { essidEntry 32 }
                      
auth1x OBJECT-TYPE
SYNTAX Integer32 (0..1)
MAX-ACCESS read-write
STATUS current
DESCRIPTION
"The unique identifier of the essid entry."
::= { essidEntry 33 }
                     
authForce1x OBJECT-TYPE
SYNTAX Integer32 (0..1)
MAX-ACCESS read-write
STATUS current
DESCRIPTION
"N/A."
::= { essidEntry 34 }
                
authWpa OBJECT-TYPE
SYNTAX Integer32 (0..1)
MAX-ACCESS read-write
STATUS current
DESCRIPTION
"N/A."
::= { essidEntry 35 }
                
authPsk OBJECT-TYPE
SYNTAX Integer32 (0..1)
MAX-ACCESS read-write
STATUS current
DESCRIPTION
"N/A."
::= { essidEntry 36 }
                
defaultBcastKeyid OBJECT-TYPE
SYNTAX Integer32
MAX-ACCESS read-write
STATUS current
DESCRIPTION
"N/A."
::= { essidEntry 37 }
          
wpa2Only OBJECT-TYPE
SYNTAX Integer32
MAX-ACCESS read-write
STATUS current
DESCRIPTION
"N/A."
::= { essidEntry 38 }
   
useWpa2 OBJECT-TYPE
SYNTAX Integer32
MAX-ACCESS read-write
STATUS current
DESCRIPTION
"N/A."
::= { essidEntry 39 }
               
aesOnly OBJECT-TYPE
SYNTAX Integer32
MAX-ACCESS read-write
STATUS current
DESCRIPTION
"N/A."
::= { essidEntry 40 }                                    

groupKeyTtl OBJECT-TYPE
SYNTAX Integer32
MAX-ACCESS read-write
STATUS current
DESCRIPTION
"N/A."
::= { essidEntry 41 }

essidEnable80211d OBJECT-TYPE
SYNTAX Integer32
MAX-ACCESS read-write
STATUS current
DESCRIPTION
"N/A."
::= { essidEntry 42 }

requiredBeaconsPercentage OBJECT-TYPE
SYNTAX Integer32
MAX-ACCESS read-write
STATUS current
DESCRIPTION
"N/A."
::= { essidEntry 43 }

aeroscoutMuSupport OBJECT-TYPE
SYNTAX Integer32
MAX-ACCESS read-write
STATUS current
DESCRIPTION
"N/A."
::= { essidEntry 44 }

useWmm OBJECT-TYPE
SYNTAX Integer32
MAX-ACCESS read-write
STATUS current
DESCRIPTION
"N/A."
::= { essidEntry 45 }

wmmAckPolicy OBJECT-TYPE
SYNTAX Integer32
MAX-ACCESS read-write
STATUS current
DESCRIPTION
"N/A."
::= { essidEntry 46 }

newEssid OBJECT-TYPE
SYNTAX Integer32
MAX-ACCESS read-write
STATUS current
DESCRIPTION
"N/A."
::= { essidEntry 47 }

inBandManagement OBJECT-TYPE
SYNTAX Integer32
MAX-ACCESS read-write
STATUS current
DESCRIPTION
"N/A."
::= { essidEntry 48 }

captivePortalEnable OBJECT-TYPE
SYNTAX Integer32
MAX-ACCESS read-write
STATUS current
DESCRIPTION
"N/A."
::= { essidEntry 49 }

macAuthServer OBJECT-TYPE
SYNTAX Integer32
MAX-ACCESS read-write
STATUS current
DESCRIPTION
"N/A."
::= { essidEntry 50 }

useGre OBJECT-TYPE
SYNTAX Integer32
MAX-ACCESS read-write
STATUS current
DESCRIPTION
"N/A."
::= { essidEntry 51 }

pinpointDhcpClient OBJECT-TYPE
SYNTAX Integer32
MAX-ACCESS read-write
STATUS current
DESCRIPTION
"N/A."
::= { essidEntry 52 }

eapolLowestRateEnable OBJECT-TYPE
SYNTAX Integer32
MAX-ACCESS read-write
STATUS current
DESCRIPTION
"N/A."
::= { essidEntry 53 }

secMode OBJECT-TYPE
SYNTAX Integer32
MAX-ACCESS read-write
STATUS current
DESCRIPTION
"N/A."
::= { essidEntry 54 }

allowGroupRekey OBJECT-TYPE
SYNTAX Integer32
MAX-ACCESS read-write
STATUS current
DESCRIPTION
"N/A."
::= { essidEntry 55 }

handleEapolStart OBJECT-TYPE
SYNTAX Integer32
MAX-ACCESS read-write
STATUS current
DESCRIPTION
"N/A."
::= { essidEntry 56 }

handleEapolDelay OBJECT-TYPE
SYNTAX Integer32
MAX-ACCESS read-write
STATUS current
DESCRIPTION
"N/A."
::= { essidEntry 57 }

handleEapolPending OBJECT-TYPE
SYNTAX Integer32
MAX-ACCESS read-write
STATUS current
DESCRIPTION
"N/A."
::= { essidEntry 58 }

allowEapolData OBJECT-TYPE
SYNTAX Integer32
MAX-ACCESS read-write
STATUS current
DESCRIPTION
"N/A."
::= { essidEntry 59 }

allowCountermeasures OBJECT-TYPE
SYNTAX Integer32
MAX-ACCESS read-write
STATUS current
DESCRIPTION
"N/A."
::= { essidEntry 60 }
                
essRowStatus OBJECT-TYPE
SYNTAX RowStatus
MAX-ACCESS read-write
STATUS current
DESCRIPTION
"Add - 4 Delete -6 Row from ESS table."
::= { essidEntry 61 }






-- =====================================================================
-- Authentication Server table
--

authServer OBJECT-TYPE
SYNTAX SEQUENCE OF AuthServerEntry
MAX-ACCESS not-accessible
STATUS current
DESCRIPTION
"A table that contains the Authentication server information"
::= { mibObjects 5 }


authServerEntry OBJECT-TYPE
SYNTAX AuthServerEntry
MAX-ACCESS not-accessible
STATUS current
DESCRIPTION
"A list of the server parameters."
INDEX { authServerIndex }
::= { authServer 1 }

AuthServerEntry ::=
SEQUENCE {       
  authServerIndex	        Integer32,
  authServerIp            DisplayString,
  authServerPort          Integer32,
  authServerSecret        DisplayString,
  authServerTimeout       Integer32,
  authServerRowStatus    RowStatus
}


authServerIndex OBJECT-TYPE
SYNTAX Integer32 (1..4)
MAX-ACCESS read-write
STATUS current
DESCRIPTION
"The authentication server index entry"
::= { authServerEntry 1 }

authServerIp OBJECT-TYPE
SYNTAX DisplayString
MAX-ACCESS read-write
STATUS current
DESCRIPTION
"The authentication server IP address"
::= { authServerEntry 2 }

authServerPort OBJECT-TYPE
SYNTAX Integer32 
MAX-ACCESS read-write
STATUS current
DESCRIPTION
"The authentication server port"
::= { authServerEntry 3 }
  
authServerSecret OBJECT-TYPE
SYNTAX DisplayString
MAX-ACCESS read-write
STATUS current
DESCRIPTION
"The authentication server passward"
::= { authServerEntry 4 }

authServerTimeout OBJECT-TYPE
SYNTAX Integer32 
MAX-ACCESS read-write
STATUS current
DESCRIPTION
"The authentication server connection timeout"
::= { authServerEntry 5 }
      
authServerRowStatus OBJECT-TYPE
SYNTAX RowStatus 
MAX-ACCESS read-write
STATUS current
DESCRIPTION
"Add/Remove table entry"
::= { authServerEntry 6 }



-- =====================================================================
--
-- LAN table

lan OBJECT-TYPE
SYNTAX SEQUENCE OF DeviceEntry
MAX-ACCESS not-accessible
STATUS current
DESCRIPTION
"A table that contains information about devices"
::= { mibObjects 6 }

deviceEntry OBJECT-TYPE
SYNTAX DeviceEntry
MAX-ACCESS not-accessible
STATUS current
DESCRIPTION
"A list of the device parameters."
INDEX { deviceIndex }
::= { lan 1 }

DeviceEntry ::=
SEQUENCE {       
  deviceIndex          Integer32,
  ipAddress           DisplayString,  
  ipMask              DisplayString,  
  defaultGateway      DisplayString,  
  lanVid              Integer32,
  vlanAddr            DisplayString,
  vlanName            DisplayString,
  slaveIpAddress     DisplayString,
  webSlaveIpAddress DisplayString,
  slaveEnable         Integer32
}

    
deviceIndex OBJECT-TYPE
SYNTAX Integer32 (1..16) 
MAX-ACCESS read-write
STATUS current
DESCRIPTION
"The project catalog number of the device"
::= { deviceEntry 1 }

ipAddress OBJECT-TYPE
SYNTAX DisplayString 
MAX-ACCESS read-write
STATUS current
DESCRIPTION
"The IP address of the device"
::= { deviceEntry 2 }

ipMask OBJECT-TYPE
SYNTAX DisplayString 
MAX-ACCESS read-write
STATUS current
DESCRIPTION
"The IP MASK of device"
::= { deviceEntry 3 }

defaultGateway OBJECT-TYPE
SYNTAX DisplayString 
MAX-ACCESS read-write
STATUS current
DESCRIPTION
"The IP default gateway of device"
::= { deviceEntry 4 }
                       
lanVid OBJECT-TYPE
SYNTAX Integer32 
MAX-ACCESS read-write
STATUS current
DESCRIPTION
"Vlan Index"
::= { deviceEntry 5 }
  
                    
vlanAddr OBJECT-TYPE
SYNTAX DisplayString 
MAX-ACCESS read-write
STATUS current
DESCRIPTION
"Vlan IP Address"
::= { deviceEntry 6 }

vlanName OBJECT-TYPE
SYNTAX DisplayString 
MAX-ACCESS read-write
STATUS current
DESCRIPTION
"The Vlan name"
::= { deviceEntry 7 }


slaveIpAddress OBJECT-TYPE
SYNTAX DisplayString 
MAX-ACCESS read-write
STATUS current
DESCRIPTION
"Slave IP Address"
::= { deviceEntry 8 }


webSlaveIpAddress OBJECT-TYPE
SYNTAX DisplayString 
MAX-ACCESS read-write
STATUS current
DESCRIPTION
"Slave IP Address"
::= { deviceEntry 9 }

slaveEnable OBJECT-TYPE
SYNTAX Integer32
MAX-ACCESS read-write
STATUS current
DESCRIPTION
"Flage indicate slave mode working/not working. "
::= { deviceEntry 10 }


-- ====================================================================
-- Logs table 
--

logs OBJECT-TYPE
SYNTAX SEQUENCE OF LogsEntry
MAX-ACCESS not-accessible
STATUS current
DESCRIPTION
"A table that contains log configuration parameters"
::= { mibObjects 7 }


logsEntry OBJECT-TYPE
SYNTAX LogsEntry
MAX-ACCESS not-accessible
STATUS current
DESCRIPTION
"A list of the log parameters."
INDEX { logsIndex }
::= { logs 1 }

LogsEntry ::=
SEQUENCE {       
  logsIndex 	      Integer32,
  syslogOn           Integer32,
  levelBitmap        Integer32,
  syslogServer       DisplayString,
  syslogInterval     Integer32
}


logsIndex OBJECT-TYPE
SYNTAX Integer32 (1..16)
MAX-ACCESS read-write
STATUS current
DESCRIPTION
"The index of the log entry"
::= { logsEntry 1 }


syslogOn OBJECT-TYPE
SYNTAX Integer32 (0..1)
MAX-ACCESS read-write
STATUS current
DESCRIPTION
"The syslog status of the log entry"
::= { logsEntry 2 }


levelBitmap OBJECT-TYPE
SYNTAX Integer32 (0..255) 
MAX-ACCESS read-write
STATUS current
DESCRIPTION
"The bitmap of the log entry"
::= { logsEntry 3 }

               
syslogServer OBJECT-TYPE
SYNTAX DisplayString
MAX-ACCESS read-write
STATUS current
DESCRIPTION
"The syslog Server"
::= { logsEntry 4 }

             
syslogInterval OBJECT-TYPE
SYNTAX Integer32 (0..100000)
MAX-ACCESS read-write
STATUS current
DESCRIPTION
"The syslog interval"
::= { logsEntry 5 }





-- ====================================================================
-- Trap Destination table 
--

trapDestination OBJECT-TYPE
SYNTAX SEQUENCE OF TrapEntry
MAX-ACCESS not-accessible
STATUS current
DESCRIPTION
"A table that contains wireless stations information"
::= { mibObjects 13 }


trapDestinationEntry OBJECT-TYPE
SYNTAX TrapEntry
MAX-ACCESS not-accessible
STATUS current
DESCRIPTION
"A list of the Traps destination servers/machines."
INDEX { destinationIndex }
::= { trapDestination 1 }

TrapEntry ::=
SEQUENCE {       
  destinationIndex 	    Integer32,
  destinationAddress       DisplayString,
  destinationName          DisplayString,
  destinationRowStatus    RowStatus
}


destinationIndex OBJECT-TYPE
SYNTAX Integer32 
MAX-ACCESS read-write
STATUS current
DESCRIPTION
"Trap Destination index"
::= { trapDestinationEntry 1 }

destinationAddress OBJECT-TYPE
SYNTAX DisplayString 
MAX-ACCESS read-write
STATUS current
DESCRIPTION
"Trap Destination machine address"
::= { trapDestinationEntry 2 }

destinationName OBJECT-TYPE
SYNTAX DisplayString 
MAX-ACCESS read-write
STATUS current
DESCRIPTION
"Trap Destination machine name"
::= { trapDestinationEntry 3 }
    
destinationRowStatus OBJECT-TYPE
SYNTAX RowStatus 
MAX-ACCESS read-write
STATUS current
DESCRIPTION
"Add/Remove table entry"
::= { trapDestinationEntry 4 }




-- ====================================================================
-- Access List table 
--

accessList OBJECT-TYPE
SYNTAX SEQUENCE OF AccessListEntry
MAX-ACCESS not-accessible
STATUS current
DESCRIPTION
"A table that contains wireless stations information"
::= { mibObjects 14 }


accessListEntry OBJECT-TYPE
SYNTAX AccessListEntry
MAX-ACCESS not-accessible
STATUS current
DESCRIPTION
"A list of the Traps destination servers/machines."
INDEX { accessListIndex }
::= { accessList 1 }

AccessListEntry ::=
SEQUENCE {       
  accessListIndex 	       Integer32,
  accessListAddress          DisplayString,
  accessListRoCommunity     DisplayString,
  accessListRwCommunity     DisplayString,
  accessRowStatus            RowStatus
}


accessListIndex OBJECT-TYPE
SYNTAX Integer32 
MAX-ACCESS read-write
STATUS current
DESCRIPTION
"Access List allowed index"
::= { accessListEntry 1 }

accessListAddress OBJECT-TYPE
SYNTAX DisplayString 
MAX-ACCESS read-write
STATUS current
DESCRIPTION
"Access List allowed machine address"
::= { accessListEntry 2 }

accessListRoCommunity OBJECT-TYPE
SYNTAX DisplayString 
MAX-ACCESS read-write
STATUS current
DESCRIPTION
"N/A"
::= { accessListEntry 3 }

accessListRwCommunity OBJECT-TYPE
SYNTAX DisplayString 
MAX-ACCESS read-write
STATUS current
DESCRIPTION
"N/A"
::= { accessListEntry 4 }

accessRowStatus OBJECT-TYPE
SYNTAX RowStatus 
MAX-ACCESS read-write
STATUS current
DESCRIPTION
"Add/Remove table Entry"
::= { accessListEntry 5 }




-- ====================================================================
-- POE Control table 
--

poeControl OBJECT-TYPE
SYNTAX SEQUENCE OF PoeControlEntry
MAX-ACCESS not-accessible
STATUS current
DESCRIPTION
"A table that contains the switch POE status"
::= { mibObjects 15 }


poeControlEntry OBJECT-TYPE
SYNTAX PoeControlEntry
MAX-ACCESS not-accessible
STATUS current
DESCRIPTION
"A list of the POE Port status."
INDEX { poeControlIndex }
::= { poeControl 1 }

PoeControlEntry ::=
SEQUENCE {       
  poeControlIndex 	Integer32,
  poePortStatus       Integer32
}


poeControlIndex OBJECT-TYPE
SYNTAX Integer32 
MAX-ACCESS read-write
STATUS current
DESCRIPTION
"POE Port index"
::= { poeControlEntry 1 }

poePortStatus OBJECT-TYPE
SYNTAX Integer32 
MAX-ACCESS read-write
STATUS current
DESCRIPTION
"POE Status , 0= power off, 6 Power ON no link , 4 Power On link On"
::= { poeControlEntry 2 }



-- ====================================================================
-- Rogue AP White List
--

rapdWhiteMac OBJECT-TYPE
SYNTAX SEQUENCE OF WhiteListEntry
MAX-ACCESS not-accessible
STATUS current
DESCRIPTION
"A table that contains Rapd White List BSSIDs configuration parameters"
::= { mibObjects 16 }


whiteListEntry OBJECT-TYPE
SYNTAX WhiteListEntry
MAX-ACCESS not-accessible
STATUS current
DESCRIPTION
"A list of the White List BSSIDs parameters."
INDEX { whiteListIndex }
::= { rapdWhiteMac 1 }

WhiteListEntry ::=
SEQUENCE {
  whiteListIndex                  Integer32,
  allowApMac                    DisplayString,
  whiteListRowStatus   RowStatus
}


whiteListIndex OBJECT-TYPE
SYNTAX Integer32 (1..128)
MAX-ACCESS read-write
STATUS current
DESCRIPTION
"The index of the White List BSSID entry"
::= { whiteListEntry 1 }


allowApMac OBJECT-TYPE
SYNTAX DisplayString
MAX-ACCESS read-write
STATUS current
DESCRIPTION
"The BSSID entry"
::= { whiteListEntry 2 }

whiteListRowStatus OBJECT-TYPE
SYNTAX RowStatus
MAX-ACCESS read-write
STATUS current
DESCRIPTION
"Add -4 Delete - 6 White list entry"
::= { whiteListEntry 3 }



-- ===================================
-- 
-- stationsMacAcl
--

stationsMacAcl OBJECT-TYPE
SYNTAX SEQUENCE OF StationsAclEntry
MAX-ACCESS not-accessible
STATUS current
DESCRIPTION
"A table that contains allowed stations per essid "
::= { mibObjects 17 }


stationsAclEntry OBJECT-TYPE
SYNTAX StationsAclEntry
MAX-ACCESS not-accessible
STATUS current
DESCRIPTION
"A list of the station list parameters."
INDEX { aclIndex }
::= { stationsMacAcl 1 }

StationsAclEntry::=
SEQUENCE {
  aclIndex                     Integer32,
  clientMac                    DisplayString,
  clientName                   DisplayString,
  clientEssIndex              Integer32,
  clientACLRowStatus         RowStatus  
}


aclIndex OBJECT-TYPE
SYNTAX Integer32 (1..2007)
MAX-ACCESS read-write
STATUS current
DESCRIPTION
"The index of the allowed clients"
::= { stationsAclEntry 1 }


clientMac OBJECT-TYPE
SYNTAX DisplayString
MAX-ACCESS read-write
STATUS current
DESCRIPTION
"The client MAC address"
::= { stationsAclEntry 2 }

clientName OBJECT-TYPE
SYNTAX DisplayString
MAX-ACCESS read-write
STATUS current
DESCRIPTION
"The client name/description"
::= { stationsAclEntry 3 }

clientEssIndex OBJECT-TYPE
SYNTAX Integer32 (1..32)
MAX-ACCESS read-write
STATUS current
DESCRIPTION
"The index of the essid this client is allowed"
::= { stationsAclEntry 4 }

clientACLRowStatus OBJECT-TYPE
SYNTAX RowStatus
MAX-ACCESS read-write
STATUS current
DESCRIPTION
"Add -4 Delete - 6 this client from list"
::= { stationsAclEntry 5 }













-- ================================================================================
--
--  Statistics


-- ====================================================================
-- Clients Table
--
clientStat OBJECT-TYPE
SYNTAX SEQUENCE OF ClientStatEntry
MAX-ACCESS not-accessible
STATUS current
DESCRIPTION
"A table that contains assiciated stations statistics"
::= { mibObjects 18 }

clientStatEntry OBJECT-TYPE
SYNTAX ClientStatEntry
MAX-ACCESS not-accessible
STATUS current
DESCRIPTION
"N/A"
INDEX { clientStatIndex }
::= { clientStat 1 }

ClientStatEntry ::=
SEQUENCE {     
  clientStatIndex 	        Integer32,
  clientAid					Integer32,			  
  clientAssocTime			INTEGER,
  clientRssiAvg				Integer32,
  clientVlanNumber          Integer32,
  clientEncMethod			Integer32,
  clientMacPHY              Integer32, 
  clientRxPacket			Counter32,
  clientRxOctet				Counter32,
  clientTxPacket			Counter32,
  clientTxOctet				Counter32,
  clientTxRetansFail		Counter32,
  clientTxRetansFailOctet	Counter32,
  clientTxDropedCount	    Counter32,
  clientAdminStatus			Integer32,
  clientOperStatus			Integer32,
  clientEssidIdx			Integer32,
  clientChannelIdx			Integer32,
  clientBssidIdx			Integer32,
  clientModeStr				Integer32,
  clientHT					Integer32,
  clientTxRate				Integer32,
  clientLastAuth			Integer32,
  clientLastAssoc			Integer32,
  clientAuth				Integer32,
  clientEapolAuth			Integer32,
  clientEapolState			Integer32,
  clientCipher				Integer32,
  clientTxAp				Integer32,
  clientRxAp				Integer32,
  clientIsDynamicVlan		Integer32,
  clientCaptive				Integer32,
  clientTimeStamp			Integer32,
  staIp					IpAddress,
  gre						Integer32,
  greStatus				Integer32,
  clientEssidConfig			Integer32,
  clientMac					DisplayString
}


clientStatIndex OBJECT-TYPE
SYNTAX Integer32 
MAX-ACCESS read-only
STATUS current
DESCRIPTION
"N/A"
::= { clientStatEntry 1 }


clientAid OBJECT-TYPE
SYNTAX Integer32 
MAX-ACCESS read-only
STATUS current
DESCRIPTION
"Client AID 1 -2007"
::= { clientStatEntry 2 }

clientAssocTime OBJECT-TYPE
SYNTAX INTEGER 
MAX-ACCESS read-only
STATUS current
DESCRIPTION
"Time since association start in sec"
::= { clientStatEntry 3 }

clientRssiAvg OBJECT-TYPE
SYNTAX Integer32 
MAX-ACCESS read-only
STATUS current
DESCRIPTION
"Avrage of RSS from last call 1-99"
::= { clientStatEntry 4 }

clientVlanNumber OBJECT-TYPE
SYNTAX Integer32 
MAX-ACCESS read-only
STATUS current
DESCRIPTION
"Client VLAN 0-4095"
::= { clientStatEntry 5 }

clientEncMethod OBJECT-TYPE
SYNTAX Integer32 
MAX-ACCESS read-only
STATUS current
DESCRIPTION
"0=no, 1= wep, 2=wpa ..."
::= { clientStatEntry 6 }

clientMacPHY OBJECT-TYPE
SYNTAX Integer32 
MAX-ACCESS read-only
STATUS current
DESCRIPTION
"Client Radio mode a,b,g or mixed b/g - 1 2 3 4"
::= { clientStatEntry 7 }

clientRxPacket OBJECT-TYPE
SYNTAX Counter32 (0..2147483647)
MAX-ACCESS read-only
STATUS current
DESCRIPTION
"N/A"
::= { clientStatEntry 8 }

clientRxOctet OBJECT-TYPE
SYNTAX Counter32 (0..2147483647)
MAX-ACCESS read-only
STATUS current
DESCRIPTION
"N/A"
::= { clientStatEntry 9 }

clientTxPacket OBJECT-TYPE
SYNTAX Counter32 (0..2147483647)
MAX-ACCESS read-only
STATUS current
DESCRIPTION
"N/A"
::= { clientStatEntry 10 }

clientTxOctet OBJECT-TYPE
SYNTAX Counter32 (0..2147483647)
MAX-ACCESS read-only
STATUS current
DESCRIPTION
"N/A"
::= { clientStatEntry 11 }

clientTxRetansFail OBJECT-TYPE
SYNTAX Counter32 (0..2147483647)
MAX-ACCESS read-only
STATUS current
DESCRIPTION
"N/A"
::= { clientStatEntry 12 }

clientTxRetansFailOctet OBJECT-TYPE
SYNTAX Counter32 (0..2147483647)
MAX-ACCESS read-only
STATUS current
DESCRIPTION
"N/A"
::= { clientStatEntry 13 }

clientTxDropedCount OBJECT-TYPE
SYNTAX Counter32 (0..2147483647)
MAX-ACCESS read-only
STATUS current
DESCRIPTION
"N/A"
::= { clientStatEntry 14 }

clientAdminStatus OBJECT-TYPE
SYNTAX Integer32 
MAX-ACCESS read-only
STATUS current
DESCRIPTION
"Administration status of this client- Last trap severity"
::= { clientStatEntry 15 }

clientOperStatus OBJECT-TYPE
SYNTAX Integer32 
MAX-ACCESS read-only
STATUS current
DESCRIPTION
"Operetional status of this client - On/Off/Standby"
::= { clientStatEntry 16 }

clientEssidIdx OBJECT-TYPE
SYNTAX Integer32 (0..64)
MAX-ACCESS read-only
STATUS current
DESCRIPTION
"Client ESS Index (configuration index of ESSID) "
::= { clientStatEntry 17 }

clientChannelIdx OBJECT-TYPE
SYNTAX Integer32 (0..7)
MAX-ACCESS read-only
STATUS current
DESCRIPTION
"Client Channel index (configuration index of the Channel this client is assigned to)"
::= { clientStatEntry 18 }

clientBssidIdx OBJECT-TYPE
SYNTAX Integer32 (0..32)
MAX-ACCESS read-only
STATUS current
DESCRIPTION
"Client BSS Index (index of the internal BSS index this client is assigned to)"
::= { clientStatEntry 19 }

clientModeStr OBJECT-TYPE
SYNTAX Integer32 
MAX-ACCESS read-only
STATUS current
DESCRIPTION
"Client 80211 Radio mode"
::= { clientStatEntry 20 }

clientHT OBJECT-TYPE
SYNTAX Integer32 
MAX-ACCESS read-only
STATUS current
DESCRIPTION
"N/A"
::= { clientStatEntry 21 }

clientTxRate OBJECT-TYPE
SYNTAX Integer32 
MAX-ACCESS read-only
STATUS current
DESCRIPTION
"N/A"
::= { clientStatEntry 22 }

clientLastAuth OBJECT-TYPE
SYNTAX Integer32 
MAX-ACCESS read-only
STATUS current
DESCRIPTION
"N/A"
::= { clientStatEntry 23 }

clientLastAssoc OBJECT-TYPE
SYNTAX Integer32 
MAX-ACCESS read-only
STATUS current
DESCRIPTION
"N/A"
::= { clientStatEntry 24 }

clientAuth OBJECT-TYPE
SYNTAX Integer32 
MAX-ACCESS read-only
STATUS current
DESCRIPTION
"N/A"
::= { clientStatEntry 25 }

clientEapolAuth OBJECT-TYPE
SYNTAX Integer32 
MAX-ACCESS read-only
STATUS current
DESCRIPTION
"N/A"
::= { clientStatEntry 26 }

clientEapolState OBJECT-TYPE
SYNTAX Integer32 
MAX-ACCESS read-only
STATUS current
DESCRIPTION
"N/A"
::= { clientStatEntry 27 }

clientCipher OBJECT-TYPE
SYNTAX Integer32 
MAX-ACCESS read-only
STATUS current
DESCRIPTION
"N/A"
::= { clientStatEntry 28 }

clientTxAp OBJECT-TYPE
SYNTAX Integer32 
MAX-ACCESS read-only
STATUS current
DESCRIPTION
"Current TX AP for this client"
::= { clientStatEntry 29 }

clientRxAp OBJECT-TYPE
SYNTAX Integer32 
MAX-ACCESS read-only
STATUS current
DESCRIPTION
"Current RX AP for this client"
::= { clientStatEntry 30 }

clientIsDynamicVlan OBJECT-TYPE
SYNTAX Integer32 
MAX-ACCESS read-only
STATUS current
DESCRIPTION
"Indication flag for dynamic VLAN assigment for this client on/off"
::= { clientStatEntry 31 }

clientCaptive OBJECT-TYPE
SYNTAX Integer32 
MAX-ACCESS read-only
STATUS current
DESCRIPTION
"Indication flag for Captive portal status on/off. "
::= { clientStatEntry 32 }

staIp OBJECT-TYPE
SYNTAX IpAddress 
MAX-ACCESS read-only
STATUS current
DESCRIPTION
"Station current IP Address. "
::= { clientStatEntry 33 }

clientTimeStamp OBJECT-TYPE
SYNTAX Integer32 
MAX-ACCESS read-only
STATUS current
DESCRIPTION
"Statistics interval time stamp - sec from last monitored "
::= { clientStatEntry 34 }

gre OBJECT-TYPE
SYNTAX Integer32 
MAX-ACCESS read-only
STATUS current
DESCRIPTION
"Station GRE Enable flag "
::= { clientStatEntry 35 }

greStatus OBJECT-TYPE
SYNTAX Integer32 
MAX-ACCESS read-only
STATUS current
DESCRIPTION
"Station GRE Status (done = 0, ip cahnged = 1, ack = 2) "
::= { clientStatEntry 36 }

clientEssidConfig OBJECT-TYPE
SYNTAX Integer32 (0..32)
MAX-ACCESS read-only
STATUS current
DESCRIPTION
"The client essid configured index."
::= { clientStatEntry 37 }

clientMac OBJECT-TYPE
SYNTAX DisplayString 
MAX-ACCESS read-only
STATUS current
DESCRIPTION
"Client MAC Address XX:XX:XX:XX:XX"
::= { clientStatEntry 38 }



-- =======================================================================
--
--  Access Point Statistics
--

apStat OBJECT-TYPE
SYNTAX SEQUENCE OF ApStatEntry
MAX-ACCESS not-accessible
STATUS current
DESCRIPTION
"A table that contains Access Point statistics"
::= { mibObjects 19 }


apStatEntry OBJECT-TYPE
SYNTAX ApStatEntry
MAX-ACCESS not-accessible
STATUS current
DESCRIPTION
"N/A"
INDEX { apStatIndex }
::= { apStat 1 }

ApStatEntry ::=
SEQUENCE {       
  apStatIndex 	                 Integer32,
  apRtsSucces                    Integer32,
  apRtsFailed                    Integer32,
  apRxPacketRadio1               Integer32,
  apTxPcketRadio1                Integer32,
  apRxOctetRadio1                Integer32,
  apTxOctetRadio1                Integer32,
  apRtsSuccesRadio1              Integer32,
  apRtsFailedRadio1              Integer32, 
  apTxFailedOctetRadio1          Integer32,
  apTxFailedPacketRadio1         Integer32,
  apTxRetansFailRadio1           Integer32,
  apTxRetansFailOctetRadio1      Integer32,  
  apRxMcastOctetRadio1           Integer32,
  apRxMcastPacketRadio1          Integer32,
  apTxMcastPacketRadio1          Integer32,
  apTxMcastOctetRadio1           Integer32,
  apTxDropedCountRadio1          Integer32,
  apAdminStatusRadio1            Integer32,  
  apOperStatusRadio1             Integer32, 
  apLEDStatusRadio1              Integer32,
  apRxPacketRadio2               Integer32, 
  apTxPcketRadio2                Integer32,
  apRxOctetRadio2                Integer32,
  apTxOctetRadio2                Integer32,   
  apRtsSuccesRadio2              Integer32,
  apRtsFailedRadio2              Integer32,
  apTxFailedOctetRadio2          Integer32,
  apTxFailedPacketRadio2         Integer32,
  apTxRetansFailRadio2           Integer32,
  apTxRetansFailOctetRadio2      Integer32, 
  apRxMcastOctetRadio2           Integer32,
  apRxMcastPacketRadio2          Integer32,
  apTxMcastPacketRadio2          Integer32,
  apTxMcastOctetRadio2           Integer32,
  apTxDropedCountRadio2          Integer32,
  apAdminStatusRadio2            Integer32, 
  apOperStatusRadio2             Integer32,
  apLEDStatusRadio2              Integer32,
  apRxPacketRadio3               Integer32,  
  apTxPcketRadio3                Integer32, 
  apRxOctetRadio3                Integer32,
  apTxOctetRadio3                Integer32,    
  apRtsSuccesRadio3              Integer32,
  apRtsFailedRadio3              Integer32, 
  apTxFailedOctetRadio3          Integer32,
  apTxFailedPacketRadio3         Integer32,
  apTxRetansFailRadio3           Integer32,
  apTxRetansFailOctetRadio3      Integer32,  
  apRxMcastOctetRadio3           Integer32,
  apRxMcastPacketRadio3          Integer32,
  apTxMcastPacketRadio3          Integer32,
  apTxMcastOctetRadio3           Integer32,
  apTxDropedCountRadio3          Integer32,
  apAdminStatusRadio3            Integer32, 
  apOperStatusRadio3             Integer32,
  apLEDStatusRadio3              Integer32, 
  apRxPacketRadio4               Integer32,
  apTxPcketRadio4                Integer32,
  apRxOctetRadio4                Integer32,
  apTxOctetRadio4                Integer32,
  apRtsSuccesRadio4              Integer32,
  apRtsFailedRadio4              Integer32,
  apTxFailedOctetRadio4          Integer32,
  apTxFailedPacketRadio4         Integer32,
  apTxRetansFailRadio4           Integer32,
  apTxRetansFailOctetRadio4      Integer32,
  apRxMcastOctetRadio4           Integer32,
  apRxMcastPacketRadio4          Integer32,
  apTxMcastPacketRadio4          Integer32,
  apTxMcastOctetRadio4           Integer32,
  apTxDropedCountRadio4          Integer32,
  apAdminStatusRadio4            Integer32,
  apOperStatusRadio4             Integer32,
  apLEDStatusRadio4              Integer32,
  apOperStatus                   Integer32 
}

apStatIndex OBJECT-TYPE
SYNTAX Integer32 
MAX-ACCESS read-only
STATUS current
DESCRIPTION
"N/A"
::= { apStatEntry 1 }

apRtsSucces OBJECT-TYPE
SYNTAX Integer32 
MAX-ACCESS read-only
STATUS current
DESCRIPTION
"N/A"
::= { apStatEntry 2 }

apRtsFailed OBJECT-TYPE
SYNTAX Integer32 
MAX-ACCESS read-only
STATUS current
DESCRIPTION
"N/A"
::= { apStatEntry 3 }

apRxPacketRadio1 OBJECT-TYPE
SYNTAX Integer32 (0..2147483647)
MAX-ACCESS read-only
STATUS current
DESCRIPTION
"N/A"
::= { apStatEntry 4 }

apTxPcketRadio1 OBJECT-TYPE
SYNTAX Integer32 (0..2147483647)
MAX-ACCESS read-only
STATUS current
DESCRIPTION
"N/A"
::= { apStatEntry 5 }

apRxOctetRadio1 OBJECT-TYPE
SYNTAX Integer32 (0..2147483647)
MAX-ACCESS read-only
STATUS current
DESCRIPTION
"N/A"
::= { apStatEntry 6 }

apTxOctetRadio1 OBJECT-TYPE
SYNTAX Integer32 (0..2147483647)
MAX-ACCESS read-only
STATUS current
DESCRIPTION
"N/A"
::= { apStatEntry 7 }

apRtsSuccesRadio1 OBJECT-TYPE
SYNTAX Integer32 
MAX-ACCESS read-only
STATUS current
DESCRIPTION
"N/A"
::= { apStatEntry 8 }

apRtsFailedRadio1 OBJECT-TYPE
SYNTAX Integer32 
MAX-ACCESS read-only
STATUS current
DESCRIPTION
"N/A"
::= { apStatEntry 9 }

apTxFailedOctetRadio1 OBJECT-TYPE
SYNTAX Integer32 (0..2147483647)
MAX-ACCESS read-only
STATUS current
DESCRIPTION
"N/A"
::= { apStatEntry 10 }

apTxFailedPacketRadio1 OBJECT-TYPE
SYNTAX Integer32 (0..2147483647)
MAX-ACCESS read-only
STATUS current
DESCRIPTION
"N/A"
::= { apStatEntry 11 }

apTxRetansFailRadio1 OBJECT-TYPE
SYNTAX Integer32 (0..2147483647)
MAX-ACCESS read-only
STATUS current
DESCRIPTION
"N/A"
::= { apStatEntry 12 }

apTxRetansFailOctetRadio1 OBJECT-TYPE
SYNTAX Integer32 (0..2147483647)
MAX-ACCESS read-only
STATUS current
DESCRIPTION
"N/A"
::= { apStatEntry 13 }

apRxMcastOctetRadio1  OBJECT-TYPE
SYNTAX Integer32 (0..2147483647)
MAX-ACCESS read-only
STATUS current
DESCRIPTION
"N/A"
::= { apStatEntry 14 }

apRxMcastPacketRadio1  OBJECT-TYPE
SYNTAX Integer32 (0..2147483647)
MAX-ACCESS read-only
STATUS current
DESCRIPTION
"N/A"
::= { apStatEntry 15 }

apTxMcastPacketRadio1  OBJECT-TYPE
SYNTAX Integer32 (0..2147483647)
MAX-ACCESS read-only
STATUS current
DESCRIPTION
"N/A"
::= { apStatEntry 16 }

apTxMcastOctetRadio1 OBJECT-TYPE
SYNTAX Integer32 (0..2147483647)
MAX-ACCESS read-only
STATUS current
DESCRIPTION
"N/A"
::= { apStatEntry 17 }

apTxDropedCountRadio1 OBJECT-TYPE
SYNTAX Integer32 (0..2147483647)
MAX-ACCESS read-only
STATUS current
DESCRIPTION
"N/A"
::= { apStatEntry 18 }
 
apAdminStatusRadio1 OBJECT-TYPE
SYNTAX Integer32 
MAX-ACCESS read-only
STATUS current
DESCRIPTION
"N/A"
::= { apStatEntry 19 }
   
apOperStatusRadio1 OBJECT-TYPE
SYNTAX Integer32 
MAX-ACCESS read-only
STATUS current
DESCRIPTION
"N/A"
::= { apStatEntry 20 }
   
apLEDStatusRadio1 OBJECT-TYPE
SYNTAX Integer32 
MAX-ACCESS read-only
STATUS current
DESCRIPTION
"N/A"
::= { apStatEntry 21 }
    
apRxPacketRadio2 OBJECT-TYPE
SYNTAX Integer32 (0..2147483647)
MAX-ACCESS read-only
STATUS current
DESCRIPTION
"N/A"
::= { apStatEntry 22 }
     
apTxPcketRadio2 OBJECT-TYPE
SYNTAX Integer32 (0..2147483647)
MAX-ACCESS read-only
STATUS current
DESCRIPTION
"N/A"
::= { apStatEntry 23 }
      
apRxOctetRadio2 OBJECT-TYPE
SYNTAX Integer32 (0..2147483647)
MAX-ACCESS read-only
STATUS current
DESCRIPTION
"N/A"
::= { apStatEntry 24 }
       
apTxOctetRadio2 OBJECT-TYPE
SYNTAX Integer32 (0..2147483647)
MAX-ACCESS read-only
STATUS current
DESCRIPTION
"N/A"
::= { apStatEntry 25 }
       
apRtsSuccesRadio2 OBJECT-TYPE
SYNTAX Integer32 (0..2147483647)
MAX-ACCESS read-only
STATUS current
DESCRIPTION
"N/A"
::= { apStatEntry 26 }
     
apRtsFailedRadio2 OBJECT-TYPE
SYNTAX Integer32 (0..2147483647)
MAX-ACCESS read-only
STATUS current
DESCRIPTION
"N/A"
::= { apStatEntry 27 }
     
apTxFailedOctetRadio2 OBJECT-TYPE
SYNTAX Integer32 (0..2147483647)
MAX-ACCESS read-only
STATUS current
DESCRIPTION
"N/A"
::= { apStatEntry 28 }
 
apTxFailedPacketRadio2 OBJECT-TYPE
SYNTAX Integer32 (0..2147483647)
MAX-ACCESS read-only
STATUS current
DESCRIPTION
"N/A"
::= { apStatEntry 29 }

apTxRetansFailRadio2 OBJECT-TYPE
SYNTAX Integer32 (0..2147483647)
MAX-ACCESS read-only
STATUS current
DESCRIPTION
"N/A"
::= { apStatEntry 30 }

apTxRetansFailOctetRadio2 OBJECT-TYPE
SYNTAX Integer32 (0..2147483647)
MAX-ACCESS read-only
STATUS current
DESCRIPTION
"N/A"
::= { apStatEntry 31 }
  

apRxMcastOctetRadio2 OBJECT-TYPE
SYNTAX Integer32 (0..2147483647)
MAX-ACCESS read-only
STATUS current
DESCRIPTION
"N/A"
::= { apStatEntry 32 }

apRxMcastPacketRadio2 OBJECT-TYPE
SYNTAX Integer32 (0..2147483647)
MAX-ACCESS read-only
STATUS current
DESCRIPTION
"N/A"
::= { apStatEntry 33 }
       
apTxMcastPacketRadio2 OBJECT-TYPE
SYNTAX Integer32 (0..2147483647)
MAX-ACCESS read-only
STATUS current
DESCRIPTION
"N/A"
::= { apStatEntry 34 }
       
apTxMcastOctetRadio2 OBJECT-TYPE
SYNTAX Integer32 (0..2147483647)
MAX-ACCESS read-only
STATUS current
DESCRIPTION
"N/A"
::= { apStatEntry 35 }
       
apTxDropedCountRadio2 OBJECT-TYPE
SYNTAX Integer32 (0..2147483647)
MAX-ACCESS read-only
STATUS current
DESCRIPTION
"N/A"
::= { apStatEntry 36 }
       
apAdminStatusRadio2 OBJECT-TYPE
SYNTAX Integer32 
MAX-ACCESS read-only
STATUS current
DESCRIPTION
"N/A"
::= { apStatEntry 37 }
       
apOperStatusRadio2 OBJECT-TYPE
SYNTAX Integer32 
MAX-ACCESS read-only
STATUS current
DESCRIPTION
"N/A"
::= { apStatEntry 38 }
         
apLEDStatusRadio2 OBJECT-TYPE
SYNTAX Integer32 
MAX-ACCESS read-only
STATUS current
DESCRIPTION
"N/A"
::= { apStatEntry 39 }
          
apRxPacketRadio3 OBJECT-TYPE
SYNTAX Integer32 (0..2147483647)
MAX-ACCESS read-only
STATUS current
DESCRIPTION
"N/A"
::= { apStatEntry 40 }
           
apTxPcketRadio3 OBJECT-TYPE
SYNTAX Integer32 (0..2147483647)
MAX-ACCESS read-only
STATUS current
DESCRIPTION
"N/A"
::= { apStatEntry 41 }
            
apRxOctetRadio3 OBJECT-TYPE
SYNTAX Integer32 (0..2147483647)
MAX-ACCESS read-only
STATUS current
DESCRIPTION
"N/A"
::= { apStatEntry 42 }
             
apTxOctetRadio3 OBJECT-TYPE
SYNTAX Integer32 (0..2147483647)
MAX-ACCESS read-only
STATUS current
DESCRIPTION
"N/A"
::= { apStatEntry 43 }
             
apRtsSuccesRadio3 OBJECT-TYPE
SYNTAX Integer32 (0..2147483647)
MAX-ACCESS read-only
STATUS current
DESCRIPTION
"N/A"
::= { apStatEntry 44 }
         
apRtsFailedRadio3 OBJECT-TYPE
SYNTAX Integer32 (0..2147483647)
MAX-ACCESS read-only
STATUS current
DESCRIPTION
"N/A"
::= { apStatEntry 45 }
         
apTxFailedOctetRadio3 OBJECT-TYPE
SYNTAX Integer32 (0..2147483647)
MAX-ACCESS read-only
STATUS current
DESCRIPTION
"N/A"
::= { apStatEntry 46 }
     
apTxFailedPacketRadio3 OBJECT-TYPE
SYNTAX Integer32 (0..2147483647)
MAX-ACCESS read-only
STATUS current
DESCRIPTION
"N/A"
::= { apStatEntry 47 }

apTxRetansFailRadio3 OBJECT-TYPE
SYNTAX Integer32 (0..2147483647)
MAX-ACCESS read-only
STATUS current
DESCRIPTION
"N/A"
::= { apStatEntry 48 }
      
apTxRetansFailOctetRadio3 OBJECT-TYPE
SYNTAX Integer32 (0..2147483647)
MAX-ACCESS read-only
STATUS current
DESCRIPTION
"N/A"
::= { apStatEntry 49 }

apRxMcastOctetRadio3 OBJECT-TYPE
SYNTAX Integer32 (0..2147483647)
MAX-ACCESS read-only
STATUS current
DESCRIPTION
"N/A"
::= { apStatEntry 50 }
  
apRxMcastPacketRadio3 OBJECT-TYPE
SYNTAX Integer32 (0..2147483647)
MAX-ACCESS read-only
STATUS current
DESCRIPTION
"N/A"
::= { apStatEntry 51 }
         
apTxMcastPacketRadio3 OBJECT-TYPE
SYNTAX Integer32 (0..2147483647)
MAX-ACCESS read-only
STATUS current
DESCRIPTION
"N/A"
::= { apStatEntry 52 }
         
apTxMcastOctetRadio3 OBJECT-TYPE
SYNTAX Integer32 (0..2147483647)
MAX-ACCESS read-only
STATUS current
DESCRIPTION
"N/A"
::= { apStatEntry 53 }
         
apTxDropedCountRadio3 OBJECT-TYPE
SYNTAX Integer32 (0..2147483647)
MAX-ACCESS read-only
STATUS current
DESCRIPTION
"N/A"
::= { apStatEntry 54 }
         
apAdminStatusRadio3 OBJECT-TYPE
SYNTAX Integer32 
MAX-ACCESS read-only
STATUS current
DESCRIPTION
"N/A"
::= { apStatEntry 55 }
         
apOperStatusRadio3 OBJECT-TYPE
SYNTAX Integer32 
MAX-ACCESS read-only
STATUS current
DESCRIPTION
"N/A"
::= { apStatEntry 56 }
           
apLEDStatusRadio3 OBJECT-TYPE
SYNTAX Integer32 
MAX-ACCESS read-only
STATUS current
DESCRIPTION
"N/A"
::= { apStatEntry 57 }
            
apRxPacketRadio4 OBJECT-TYPE
SYNTAX Integer32 (0..2147483647)
MAX-ACCESS read-only
STATUS current
DESCRIPTION
"N/A"
::= { apStatEntry 58 }
             
apTxPcketRadio4 OBJECT-TYPE
SYNTAX Integer32 (0..2147483647)
MAX-ACCESS read-only
STATUS current
DESCRIPTION
"N/A"
::= { apStatEntry 59 }
              
apRxOctetRadio4 OBJECT-TYPE
SYNTAX Integer32 (0..2147483647)
MAX-ACCESS read-only
STATUS current
DESCRIPTION
"N/A"
::= { apStatEntry 60 }
               
apTxOctetRadio4 OBJECT-TYPE
SYNTAX Integer32 (0..2147483647)
MAX-ACCESS read-only
STATUS current
DESCRIPTION
"N/A"
::= { apStatEntry 61 }
               
apRtsSuccesRadio4 OBJECT-TYPE
SYNTAX Integer32 (0..2147483647)
MAX-ACCESS read-only
STATUS current
DESCRIPTION
"N/A"
::= { apStatEntry 62 }
             
apRtsFailedRadio4 OBJECT-TYPE
SYNTAX Integer32 (0..2147483647)
MAX-ACCESS read-only
STATUS current
DESCRIPTION
"N/A"
::= { apStatEntry 63 }
             
apTxFailedOctetRadio4 OBJECT-TYPE
SYNTAX Integer32 (0..2147483647)
MAX-ACCESS read-only
STATUS current
DESCRIPTION
"N/A"
::= { apStatEntry 64 }

apTxFailedPacketRadio4 OBJECT-TYPE
SYNTAX Integer32 (0..2147483647)
MAX-ACCESS read-only
STATUS current
DESCRIPTION
"N/A"
::= { apStatEntry 65 }
        
apTxRetansFailRadio4 OBJECT-TYPE
SYNTAX Integer32 (0..2147483647)
MAX-ACCESS read-only
STATUS current
DESCRIPTION
"N/A"
::= { apStatEntry 66 }
          
apTxRetansFailOctetRadio4 OBJECT-TYPE
SYNTAX Integer32 (0..2147483647)
MAX-ACCESS read-only
STATUS current
DESCRIPTION
"N/A"
::= { apStatEntry 67 }
       
apRxMcastOctetRadio4 OBJECT-TYPE
SYNTAX Integer32 (0..2147483647)
MAX-ACCESS read-only
STATUS current
DESCRIPTION
"N/A"
::= { apStatEntry 68 }
          
apRxMcastPacketRadio4 OBJECT-TYPE
SYNTAX Integer32 (0..2147483647)
MAX-ACCESS read-only
STATUS current
DESCRIPTION
"N/A"
::= { apStatEntry 69 }
         
apTxMcastPacketRadio4 OBJECT-TYPE
SYNTAX Integer32 (0..2147483647)
MAX-ACCESS read-only
STATUS current
DESCRIPTION
"N/A"
::= { apStatEntry 70 }
         
apTxMcastOctetRadio4 OBJECT-TYPE
SYNTAX Integer32 (0..2147483647)
MAX-ACCESS read-only
STATUS current
DESCRIPTION
"N/A"
::= { apStatEntry 71 }
          
apTxDropedCountRadio4 OBJECT-TYPE
SYNTAX Integer32 (0..2147483647)
MAX-ACCESS read-only
STATUS current
DESCRIPTION
"N/A"
::= { apStatEntry 72 }
         
apAdminStatusRadio4 OBJECT-TYPE
SYNTAX Integer32 
MAX-ACCESS read-only
STATUS current
DESCRIPTION
"N/A"
::= { apStatEntry 73 }
           
apOperStatusRadio4 OBJECT-TYPE
SYNTAX Integer32 
MAX-ACCESS read-only
STATUS current
DESCRIPTION
"N/A"
::= { apStatEntry 74 }
            
apLEDStatusRadio4 OBJECT-TYPE
SYNTAX Integer32 
MAX-ACCESS read-only
STATUS current
DESCRIPTION
"N/A"
::= { apStatEntry 75 }
             
apOperStatus OBJECT-TYPE
SYNTAX Integer32 
MAX-ACCESS read-only
STATUS current
DESCRIPTION
"N/A"
::= { apStatEntry 76 }





-- ===============================================================================
--
--  CHANNEL Statistics
--

channelStat OBJECT-TYPE
SYNTAX SEQUENCE OF ChannelStatEntry
MAX-ACCESS not-accessible
STATUS current
DESCRIPTION
"A table that contains Channel Entity statistics"
::= { mibObjects 20 }


channelStatEntry OBJECT-TYPE
SYNTAX ChannelStatEntry
MAX-ACCESS not-accessible
STATUS current
DESCRIPTION
"N/A"
INDEX { channelStatIndex }
::= { channelStat 1 }

ChannelStatEntry ::=
SEQUENCE {      
  channelStatIndex 	      Integer32,
  channelRxPacket             Integer32,
  channelTxPcket              Integer32,  
  channelRxOctet              Integer32,
  channelTxOctet              Integer32,
  channelTxFailedOctet        Integer32,
  channelTxFailedPacket       Integer32,
  channelTxRetansFail         Integer32,
  channelTxRetansFailOctet    Integer32,
  channelTxDropedCount        Integer32,
  channelTxMcastOctet         Integer32,
  channelTxMcastPacket        Integer32,
  channelRxMcastPacket        Integer32,
  channelRxMcastOctet         Integer32,
  channelClientsCount         Integer32,
  channelOperStatus           Integer32
}     
      
channelStatIndex OBJECT-TYPE
SYNTAX Integer32 
MAX-ACCESS read-only
STATUS current
DESCRIPTION
"N/A"
::= { channelStatEntry 1 }
      

channelRxPacket OBJECT-TYPE
SYNTAX Integer32 (0..2147483647)
MAX-ACCESS read-only
STATUS current
DESCRIPTION
"N/A"
::= { channelStatEntry 2 }

channelTxPcket OBJECT-TYPE
SYNTAX Integer32 (0..2147483647)
MAX-ACCESS read-only
STATUS current
DESCRIPTION
"N/A"
::= { channelStatEntry 3 }

channelRxOctet OBJECT-TYPE
SYNTAX Integer32 (0..2147483647)
MAX-ACCESS read-only
STATUS current
DESCRIPTION
"N/A"
::= { channelStatEntry 4 }

channelTxOctet OBJECT-TYPE
SYNTAX Integer32 (0..2147483647)
MAX-ACCESS read-only
STATUS current
DESCRIPTION
"N/A"
::= { channelStatEntry 5 }



channelTxFailedOctet OBJECT-TYPE
SYNTAX Integer32 (0..2147483647)
MAX-ACCESS read-only
STATUS current
DESCRIPTION
"N/A"
::= { channelStatEntry 6 }


channelTxFailedPacket OBJECT-TYPE
SYNTAX Integer32 (0..2147483647)
MAX-ACCESS read-only
STATUS current
DESCRIPTION
"N/A"
::= { channelStatEntry 7 }

channelTxRetansFail OBJECT-TYPE
SYNTAX Integer32 (0..2147483647)
MAX-ACCESS read-only
STATUS current
DESCRIPTION
"N/A"
::= { channelStatEntry 8 }

channelTxRetansFailOctet OBJECT-TYPE
SYNTAX Integer32 (0..2147483647)
MAX-ACCESS read-only
STATUS current
DESCRIPTION
"N/A"
::= { channelStatEntry 9 }


channelTxDropedCount OBJECT-TYPE
SYNTAX Integer32 (0..2147483647)
MAX-ACCESS read-only
STATUS current
DESCRIPTION
"N/A"
::= { channelStatEntry 10 }

channelTxMcastOctet  OBJECT-TYPE
SYNTAX Integer32 (0..2147483647)
MAX-ACCESS read-only
STATUS current
DESCRIPTION
"N/A"
::= { channelStatEntry 11 }

channelTxMcastPacket OBJECT-TYPE
SYNTAX Integer32 (0..2147483647)
MAX-ACCESS read-only
STATUS current
DESCRIPTION
"N/A"
::= { channelStatEntry 12 }

channelRxMcastPacket OBJECT-TYPE
SYNTAX Integer32 (0..2147483647)
MAX-ACCESS read-only
STATUS current
DESCRIPTION
"N/A"
::= { channelStatEntry 13 }

channelRxMcastOctet OBJECT-TYPE
SYNTAX Integer32 (0..2147483647)
MAX-ACCESS read-only
STATUS current
DESCRIPTION
"N/A"
::= { channelStatEntry 14 }

channelClientsCount OBJECT-TYPE
SYNTAX Integer32 (0..2147483647)
MAX-ACCESS read-only
STATUS current
DESCRIPTION
"N/A"
::= { channelStatEntry 15 }

channelOperStatus OBJECT-TYPE
SYNTAX Integer32 
MAX-ACCESS read-only
STATUS current
DESCRIPTION
"N/A"
::= { channelStatEntry 16 }







-- ===============================================================================
--
--  ESSID Statistics
--

essidStat OBJECT-TYPE
SYNTAX SEQUENCE OF EssidStatEntry
MAX-ACCESS not-accessible
STATUS current
DESCRIPTION
"A table that contains ESS Entity statistics"
::= { mibObjects 21 }


essidStatEntry OBJECT-TYPE
SYNTAX EssidStatEntry
MAX-ACCESS not-accessible
STATUS current
DESCRIPTION
"N/A"
INDEX { essidStatIndex }
::= { essidStat 1 }

EssidStatEntry ::=
SEQUENCE {       
  essidStatIndex 	          Integer32,
  essRxPacket                 Integer32,
  essTxPacket                 Integer32,
  essRxOctet                  Integer32,
  essTxOctet                  Integer32,
  essTxFailedOctet            Integer32,
  essTxFailedPacket           Integer32,
  essTxRetansFail             Integer32,
  essTxRetansFailOctet        Integer32,
  essTxMcastOctet             Integer32,
  essTxMcastPacket            Integer32,
  essRxMcastPacket            Integer32,
  essRxMcastOctet             Integer32,
  essTxDropedCount            Integer32,
  essClientsCount             Integer32,
  essAdminStatus              Integer32,
  essOperStatus               Integer32,
  essConfigIndex              Integer32
}     
      
essidStatIndex OBJECT-TYPE
SYNTAX Integer32 
MAX-ACCESS read-only
STATUS current
DESCRIPTION
"N/A"
::= { essidStatEntry 1 }
      
essRxPacket OBJECT-TYPE
SYNTAX Integer32 (0..2147483647)
MAX-ACCESS read-only
STATUS current
DESCRIPTION
"N/A"
::= { essidStatEntry 2 }
 
essTxPacket OBJECT-TYPE
SYNTAX Integer32 (0..2147483647)
MAX-ACCESS read-only
STATUS current
DESCRIPTION
"N/A"
::= { essidStatEntry 3 }
 
essRxOctet OBJECT-TYPE
SYNTAX Integer32 (0..2147483647)
MAX-ACCESS read-only
STATUS current
DESCRIPTION
"N/A"
::= { essidStatEntry 4 }
 
essTxOctet OBJECT-TYPE
SYNTAX Integer32 (0..2147483647)
MAX-ACCESS read-only
STATUS current
DESCRIPTION
"N/A"
::= { essidStatEntry 5 }
 
essTxFailedOctet OBJECT-TYPE
SYNTAX Integer32 (0..2147483647)
MAX-ACCESS read-only
STATUS current
DESCRIPTION
"N/A"
::= { essidStatEntry 6 }
 
essTxFailedPacket OBJECT-TYPE
SYNTAX Integer32 (0..2147483647)
MAX-ACCESS read-only
STATUS current
DESCRIPTION
"N/A"
::= { essidStatEntry 7 }
 
essTxRetansFail OBJECT-TYPE
SYNTAX Integer32 (0..2147483647)
MAX-ACCESS read-only
STATUS current
DESCRIPTION
"N/A"
::= { essidStatEntry 8 }
 
essTxRetansFailOctet OBJECT-TYPE
SYNTAX Integer32 (0..2147483647)
MAX-ACCESS read-only
STATUS current
DESCRIPTION
"N/A"
::= { essidStatEntry 9 }
 
 
essTxMcastOctet OBJECT-TYPE
SYNTAX Integer32 (0..2147483647)
MAX-ACCESS read-only
STATUS current
DESCRIPTION
"N/A"
::= { essidStatEntry 10 }
 
essTxMcastPacket OBJECT-TYPE
SYNTAX Integer32 (0..2147483647)
MAX-ACCESS read-only
STATUS current
DESCRIPTION
"N/A"
::= { essidStatEntry 11 }
 
essRxMcastPacket OBJECT-TYPE
SYNTAX Integer32 (0..2147483647)
MAX-ACCESS read-only
STATUS current
DESCRIPTION
"N/A"
::= { essidStatEntry 12 }
        
essRxMcastOctet OBJECT-TYPE
SYNTAX Integer32 (0..2147483647)
MAX-ACCESS read-only
STATUS current
DESCRIPTION
"N/A"
::= { essidStatEntry 13 }
        
essTxDropedCount OBJECT-TYPE
SYNTAX Integer32 (0..2147483647)
MAX-ACCESS read-only
STATUS current
DESCRIPTION
"N/A"
::= { essidStatEntry 14 }
        
essClientsCount OBJECT-TYPE
SYNTAX Integer32 (0..2007)
MAX-ACCESS read-only
STATUS current
DESCRIPTION
"N/A"
::= { essidStatEntry 15 }
        
essAdminStatus  OBJECT-TYPE
SYNTAX Integer32 
MAX-ACCESS read-only
STATUS current
DESCRIPTION
"N/A"
::= { essidStatEntry 16 }
        
essOperStatus OBJECT-TYPE
SYNTAX Integer32 
MAX-ACCESS read-only
STATUS current
DESCRIPTION
"N/A"
::= { essidStatEntry 17 }
         
essConfigIndex OBJECT-TYPE
SYNTAX Integer32 
MAX-ACCESS read-only
STATUS current
DESCRIPTION
"N/A"
::= { essidStatEntry 18 }     







-- =====================================================================
--
--
--

switchStat  OBJECT IDENTIFIER ::= { mibObjects 22 }


rxPacket OBJECT-TYPE
SYNTAX Integer32
MAX-ACCESS read-only
STATUS current
DESCRIPTION
"N/A"
::= { switchStat 1 }

txPacket OBJECT-TYPE
SYNTAX Integer32 (0..2147483647)
MAX-ACCESS read-only
STATUS current
DESCRIPTION
"N/A"
::= { switchStat 2 }

rxOctet OBJECT-TYPE
SYNTAX Integer32 (0..2147483647)
MAX-ACCESS read-only
STATUS current
DESCRIPTION
"N/A"
::= { switchStat 3 }

txOctet OBJECT-TYPE
SYNTAX Integer32 (0..2147483647)
MAX-ACCESS read-only
STATUS current
DESCRIPTION
"N/A"
::= { switchStat 4 }

txFailedOctet OBJECT-TYPE
SYNTAX Integer32 (0..2147483647)
MAX-ACCESS read-only
STATUS current
DESCRIPTION
"N/A"
::= { switchStat 5 }

txFailedPacket OBJECT-TYPE
SYNTAX Integer32 (0..2147483647)
MAX-ACCESS read-only
STATUS current
DESCRIPTION
"N/A"
::= { switchStat 6 }

txRetansFail OBJECT-TYPE
SYNTAX Integer32 (0..2147483647)
MAX-ACCESS read-only
STATUS current
DESCRIPTION
"N/A"
::= { switchStat 7 }

txRetansFailOctet OBJECT-TYPE
SYNTAX Integer32 (0..2147483647)
MAX-ACCESS read-only
STATUS current
DESCRIPTION
"N/A"
::= { switchStat 8 }


rxMcastOctet OBJECT-TYPE
SYNTAX Integer32 (0..2147483647)
MAX-ACCESS read-only
STATUS current
DESCRIPTION
"N/A"
::= { switchStat 9 }

rxMcastPacket OBJECT-TYPE
SYNTAX Integer32 (0..2147483647)
MAX-ACCESS read-only
STATUS current
DESCRIPTION
"N/A"
::= { switchStat 10 }

txMcastPacket OBJECT-TYPE
SYNTAX Integer32 (0..2147483647)
MAX-ACCESS read-only
STATUS current
DESCRIPTION
"N/A"
::= { switchStat 11 }

txMcastOctet OBJECT-TYPE
SYNTAX Integer32 (0..2147483647)
MAX-ACCESS read-only
STATUS current
DESCRIPTION
"N/A"
::= { switchStat 12 }

txDropedCount OBJECT-TYPE
SYNTAX Integer32 (0..2147483647)
MAX-ACCESS read-only
STATUS current
DESCRIPTION
"N/A"
::= { switchStat 13 }

clientsCount OBJECT-TYPE
SYNTAX Integer32 (0..2007)
MAX-ACCESS read-only
STATUS current
DESCRIPTION
"N/A"
::= { switchStat 14 }

rtsSucces OBJECT-TYPE
SYNTAX Integer32
MAX-ACCESS read-only
STATUS current
DESCRIPTION
"N/A"
::= { switchStat 15 }

rtsFailed OBJECT-TYPE
SYNTAX Integer32
MAX-ACCESS read-only
STATUS current
DESCRIPTION
"N/A"
::= { switchStat 16 }

rxLanPacket OBJECT-TYPE
SYNTAX Integer32 (0..2147483647)
MAX-ACCESS read-only
STATUS current
DESCRIPTION
"N/A"
::= { switchStat 17 }

txLanPacket OBJECT-TYPE
SYNTAX Integer32 (0..2147483647)
MAX-ACCESS read-only
STATUS current
DESCRIPTION
"N/A"
::= { switchStat 18 }

rxLanOctet OBJECT-TYPE
SYNTAX Integer32 (0..2147483647)
MAX-ACCESS read-only
STATUS current
DESCRIPTION
"N/A"
::= { switchStat 19 }

txLanOctet OBJECT-TYPE
SYNTAX Integer32 (0..2147483647)
MAX-ACCESS read-only
STATUS current
DESCRIPTION
"N/A"
::= { switchStat 20 }

rxLanMcastPacket OBJECT-TYPE
SYNTAX Integer32 (0..2147483647)
MAX-ACCESS read-only
STATUS current
DESCRIPTION
"N/A"
::= { switchStat 21 }

txLanError OBJECT-TYPE
SYNTAX Integer32 (0..2147483647)
MAX-ACCESS read-only
STATUS current
DESCRIPTION
"N/A"
::= { switchStat 22 }

txLanDropped OBJECT-TYPE
SYNTAX Integer32 (0..2147483647)
MAX-ACCESS read-only
STATUS current
DESCRIPTION
"N/A"
::= { switchStat 23 }

rxLanDropped OBJECT-TYPE
SYNTAX Integer32 (0..2147483647)
MAX-ACCESS read-only
STATUS current
DESCRIPTION
"N/A"
::= { switchStat 24 }

txLanCollission OBJECT-TYPE
SYNTAX Integer32 (0..2147483647)
MAX-ACCESS read-only
STATUS current
DESCRIPTION
"N/A"
::= { switchStat 25 }

rxLanFrame OBJECT-TYPE
SYNTAX Integer32 (0..2147483647)
MAX-ACCESS read-only
STATUS current
DESCRIPTION
"N/A"
::= { switchStat 26 }

txLanCarrier OBJECT-TYPE
SYNTAX Integer32 (0..2147483647)
MAX-ACCESS read-only
STATUS current
DESCRIPTION
"N/A"
::= { switchStat 27 }

switchTimeStamp OBJECT-TYPE
SYNTAX Integer32 (0..2147483647)
MAX-ACCESS read-only
STATUS current
DESCRIPTION
"Switch statistics interval collecting (delta from last interval)"
::= { switchStat 28 }

-- =======================================================================
--
--  15min Performance
--                              
performance15min  OBJECT IDENTIFIER ::= { mibObjects 23 }

pm15minapStat  OBJECT IDENTIFIER  ::= { performance15min 1 }

pm15minapStatTable OBJECT-TYPE
SYNTAX SEQUENCE OF Pm15minApStatEntry
MAX-ACCESS not-accessible
STATUS current
DESCRIPTION
"A table that contains Access Point statistics"
::= { pm15minapStat 1 }

pm15minApStatEntry OBJECT-TYPE
SYNTAX Pm15minApStatEntry
MAX-ACCESS not-accessible
STATUS current
DESCRIPTION
"N/A"
INDEX { pm15minapStatIndex,pm15mintimeIx }
::= { pm15minapStatTable 1 }
Pm15minApStatEntry ::=
SEQUENCE {       
  pm15minapStatIndex                    Integer32,
  pm15mintimeIx                         Integer32,
  pm15minapRtsSucces                    Integer32,
  pm15minapRtsFailed                    Integer32,
  pm15minapRxPacketRadio1               Integer32,
  pm15minapTxPcketRadio1                Integer32,
  pm15minapRxOctetRadio1                Integer32,
  pm15minapTxOctetRadio1                Integer32,
  pm15minapRtsSuccesRadio1              Integer32,
  pm15minapRtsFailedRadio1              Integer32, 
  pm15minapTxFailedOctetRadio1          Integer32,
  pm15minapTxFailedPacketRadio1         Integer32,
  pm15minapTxRetansFailRadio1           Integer32,
  pm15minapTxRetansFailOctetRadio1      Integer32,  
  pm15minapTxRetansSuccessRadio1        Integer32,
  pm15minapTxRetansSuccessOctetRadio1   Integer32, 
  pm15minapRxMcastOctetRadio1           Integer32,
  pm15minapRxMcastPacketRadio1          Integer32,
  pm15minapTxMcastPacketRadio1          Integer32,
  pm15minapTxMcastOctetRadio1           Integer32,
  pm15minapTxDropedCountRadio1          Integer32,
  pm15minapAdminStatusRadio1            Integer32,  
  pm15minapOperStatusRadio1             Integer32, 
  pm15minapLEDStatusRadio1              Integer32,
  pm15minapRxPacketRadio2               Integer32, 
  pm15minapTxPcketRadio2                Integer32,
  pm15minapRxOctetRadio2                Integer32,
  pm15minapTxOctetRadio2                Integer32,   
  pm15minapRtsSuccesRadio2              Integer32,
  pm15minapRtsFailedRadio2              Integer32,
  pm15minapTxFailedOctetRadio2          Integer32,
  pm15minapTxFailedPacketRadio2         Integer32,
  pm15minapTxRetansFailRadio2           Integer32,
  pm15minapTxRetansFailOctetRadio2      Integer32, 
  pm15minapTxRetansSuccessRadio2        Integer32,
  pm15minapTxRetansSuccessOctetRadio2   Integer32,
  pm15minapRxMcastOctetRadio2           Integer32,
  pm15minapRxMcastPacketRadio2          Integer32,
  pm15minapTxMcastPacketRadio2          Integer32,
  pm15minapTxMcastOctetRadio2           Integer32,
  pm15minapTxDropedCountRadio2          Integer32,
  pm15minapAdminStatusRadio2            Integer32, 
  pm15minapOperStatusRadio2             Integer32,
  pm15minapLEDStatusRadio2              Integer32,
  pm15minapRxPacketRadio3               Integer32,  
  pm15minapTxPcketRadio3                Integer32, 
  pm15minapRxOctetRadio3                Integer32,
  pm15minapTxOctetRadio3                Integer32,    
  pm15minapRtsSuccesRadio3              Integer32,
  pm15minapRtsFailedRadio3              Integer32, 
  pm15minapTxFailedOctetRadio3          Integer32,
  pm15minapTxFailedPacketRadio3         Integer32,
  pm15minapTxRetansFailRadio3           Integer32,
  pm15minapTxRetansFailOctetRadio3      Integer32,  
  pm15minapTxRetansSuccessRadio3        Integer32,
  pm15minapTxRetansSuccessOctetRadio3   Integer32,    
  pm15minapRxMcastOctetRadio3           Integer32,
  pm15minapRxMcastPacketRadio3          Integer32,
  pm15minapTxMcastPacketRadio3          Integer32,
  pm15minapTxMcastOctetRadio3           Integer32,
  pm15minapTxDropedCountRadio3          Integer32,
  pm15minapAdminStatusRadio3            Integer32, 
  pm15minapOperStatusRadio3             Integer32,
  pm15minapLEDStatusRadio3              Integer32, 
  pm15minapRxPacketRadio4               Integer32,
  pm15minapTxPcketRadio4                Integer32,
  pm15minapRxOctetRadio4                Integer32,
  pm15minapTxOctetRadio4                Integer32,
  pm15minapRtsSuccesRadio4              Integer32,
  pm15minapRtsFailedRadio4              Integer32,
  pm15minapTxFailedOctetRadio4          Integer32,
  pm15minapTxFailedPacketRadio4         Integer32,
  pm15minapTxRetansFailRadio4           Integer32,
  pm15minapTxRetansFailOctetRadio4      Integer32,
  pm15minapTxRetansSuccessRadio4        Integer32,
  pm15minapTxRetansSuccessOctetRadio4   Integer32, 
  pm15minapRxMcastOctetRadio4           Integer32,
  pm15minapRxMcastPacketRadio4          Integer32,
  pm15minapTxMcastPacketRadio4          Integer32,
  pm15minapTxMcastOctetRadio4           Integer32,
  pm15minapTxDropedCountRadio4          Integer32,
  pm15minapAdminStatusRadio4            Integer32,
  pm15minapOperStatusRadio4             Integer32,
  pm15minapLEDStatusRadio4              Integer32,
  pm15minapOperStatus                   Integer32,
  pm15minTimeStamp                      Integer32
}

pm15minapStatIndex OBJECT-TYPE
SYNTAX Integer32 
MAX-ACCESS read-only
STATUS current
DESCRIPTION
"N/A"
::= { pm15minApStatEntry 1 }

pm15mintimeIx OBJECT-TYPE
SYNTAX Integer32 
MAX-ACCESS read-only
STATUS current
DESCRIPTION
"N/A"
::= { pm15minApStatEntry 2 }

pm15minapRtsSucces OBJECT-TYPE
SYNTAX Integer32 
MAX-ACCESS read-only
STATUS current
DESCRIPTION
"N/A"
::= { pm15minApStatEntry 3 }

pm15minapRtsFailed OBJECT-TYPE
SYNTAX Integer32 
MAX-ACCESS read-only
STATUS current
DESCRIPTION
"N/A"
::= { pm15minApStatEntry 4 }

pm15minapRxPacketRadio1 OBJECT-TYPE
SYNTAX Integer32 
MAX-ACCESS read-only
STATUS current
DESCRIPTION
"N/A"
::= { pm15minApStatEntry 5 }

pm15minapTxPcketRadio1 OBJECT-TYPE
SYNTAX Integer32 
MAX-ACCESS read-only
STATUS current
DESCRIPTION
"N/A"
::= { pm15minApStatEntry 6 }

pm15minapRxOctetRadio1 OBJECT-TYPE
SYNTAX Integer32 
MAX-ACCESS read-only
STATUS current
DESCRIPTION
"N/A"
::= { pm15minApStatEntry 7 }

pm15minapTxOctetRadio1 OBJECT-TYPE
SYNTAX Integer32 
MAX-ACCESS read-only
STATUS current
DESCRIPTION
"N/A"
::= { pm15minApStatEntry 8 }

pm15minapRtsSuccesRadio1 OBJECT-TYPE
SYNTAX Integer32 
MAX-ACCESS read-only
STATUS current
DESCRIPTION
"N/A"
::= { pm15minApStatEntry 9 }

pm15minapRtsFailedRadio1 OBJECT-TYPE
SYNTAX Integer32 
MAX-ACCESS read-only
STATUS current
DESCRIPTION
"N/A"
::= { pm15minApStatEntry 10 }

pm15minapTxFailedOctetRadio1 OBJECT-TYPE
SYNTAX Integer32 
MAX-ACCESS read-only
STATUS current
DESCRIPTION
"N/A"
::= { pm15minApStatEntry 11 }

pm15minapTxFailedPacketRadio1 OBJECT-TYPE
SYNTAX Integer32 
MAX-ACCESS read-only
STATUS current
DESCRIPTION
"N/A"
::= { pm15minApStatEntry 12 }

pm15minapTxRetansFailRadio1 OBJECT-TYPE
SYNTAX Integer32 
MAX-ACCESS read-only
STATUS current
DESCRIPTION
"N/A"
::= { pm15minApStatEntry 13 }

pm15minapTxRetansFailOctetRadio1 OBJECT-TYPE
SYNTAX Integer32 
MAX-ACCESS read-only
STATUS current
DESCRIPTION
"N/A"
::= { pm15minApStatEntry 14 }

pm15minapTxRetansSuccessRadio1 OBJECT-TYPE
SYNTAX Integer32 
MAX-ACCESS read-only
STATUS current
DESCRIPTION
"N/A"
::= { pm15minApStatEntry 15 }

pm15minapTxRetansSuccessOctetRadio1 OBJECT-TYPE
SYNTAX Integer32 
MAX-ACCESS read-only
STATUS current
DESCRIPTION
"N/A"
::= { pm15minApStatEntry 16 }

pm15minapRxMcastOctetRadio1  OBJECT-TYPE
SYNTAX Integer32 
MAX-ACCESS read-only
STATUS current
DESCRIPTION
"N/A"
::= { pm15minApStatEntry 17 }

pm15minapRxMcastPacketRadio1  OBJECT-TYPE
SYNTAX Integer32 
MAX-ACCESS read-only
STATUS current
DESCRIPTION
"N/A"
::= { pm15minApStatEntry 18 }

pm15minapTxMcastPacketRadio1  OBJECT-TYPE
SYNTAX Integer32 
MAX-ACCESS read-only
STATUS current
DESCRIPTION
"N/A"
::= { pm15minApStatEntry 19 }

pm15minapTxMcastOctetRadio1 OBJECT-TYPE
SYNTAX Integer32 
MAX-ACCESS read-only
STATUS current
DESCRIPTION
"N/A"
::= { pm15minApStatEntry 20 }

pm15minapTxDropedCountRadio1 OBJECT-TYPE
SYNTAX Integer32 
MAX-ACCESS read-only
STATUS current
DESCRIPTION
"N/A"
::= { pm15minApStatEntry 21 }
 
pm15minapAdminStatusRadio1 OBJECT-TYPE
SYNTAX Integer32 
MAX-ACCESS read-only
STATUS current
DESCRIPTION
"N/A"
::= { pm15minApStatEntry 22 }
   
pm15minapOperStatusRadio1 OBJECT-TYPE
SYNTAX Integer32 
MAX-ACCESS read-only
STATUS current
DESCRIPTION
"N/A"
::= { pm15minApStatEntry 23 }
   
pm15minapLEDStatusRadio1 OBJECT-TYPE
SYNTAX Integer32 
MAX-ACCESS read-only
STATUS current
DESCRIPTION
"N/A"
::= { pm15minApStatEntry 24 }
    
pm15minapRxPacketRadio2 OBJECT-TYPE
SYNTAX Integer32 
MAX-ACCESS read-only
STATUS current
DESCRIPTION
"N/A"
::= { pm15minApStatEntry 25 }
     
pm15minapTxPcketRadio2 OBJECT-TYPE
SYNTAX Integer32 
MAX-ACCESS read-only
STATUS current
DESCRIPTION
"N/A"
::= { pm15minApStatEntry 26 }
      
pm15minapRxOctetRadio2 OBJECT-TYPE
SYNTAX Integer32 
MAX-ACCESS read-only
STATUS current
DESCRIPTION
"N/A"
::= { pm15minApStatEntry 27 }
       
pm15minapTxOctetRadio2 OBJECT-TYPE
SYNTAX Integer32 
MAX-ACCESS read-only
STATUS current
DESCRIPTION
"N/A"
::= { pm15minApStatEntry 28 }
       
pm15minapRtsSuccesRadio2 OBJECT-TYPE
SYNTAX Integer32 
MAX-ACCESS read-only
STATUS current
DESCRIPTION
"N/A"
::= { pm15minApStatEntry 29 }
     
pm15minapRtsFailedRadio2 OBJECT-TYPE
SYNTAX Integer32 
MAX-ACCESS read-only
STATUS current
DESCRIPTION
"N/A"
::= { pm15minApStatEntry 30 }
     
pm15minapTxFailedOctetRadio2 OBJECT-TYPE
SYNTAX Integer32 
MAX-ACCESS read-only
STATUS current
DESCRIPTION
"N/A"
::= { pm15minApStatEntry 31 }
 
pm15minapTxFailedPacketRadio2 OBJECT-TYPE
SYNTAX Integer32 
MAX-ACCESS read-only
STATUS current
DESCRIPTION
"N/A"
::= { pm15minApStatEntry 32 }

pm15minapTxRetansFailRadio2 OBJECT-TYPE
SYNTAX Integer32 
MAX-ACCESS read-only
STATUS current
DESCRIPTION
"N/A"
::= { pm15minApStatEntry 33 }

pm15minapTxRetansFailOctetRadio2 OBJECT-TYPE
SYNTAX Integer32 
MAX-ACCESS read-only
STATUS current
DESCRIPTION
"N/A"
::= { pm15minApStatEntry 34 }
  
pm15minapTxRetansSuccessRadio2 OBJECT-TYPE
SYNTAX Integer32 
MAX-ACCESS read-only
STATUS current
DESCRIPTION
"N/A"
::= { pm15minApStatEntry 35 }
  
pm15minapTxRetansSuccessOctetRadio2 OBJECT-TYPE
SYNTAX Integer32 
MAX-ACCESS read-only
STATUS current
DESCRIPTION
"N/A"
::= { pm15minApStatEntry 36 }

pm15minapRxMcastOctetRadio2 OBJECT-TYPE
SYNTAX Integer32 
MAX-ACCESS read-only
STATUS current
DESCRIPTION
"N/A"
::= { pm15minApStatEntry 37 }

pm15minapRxMcastPacketRadio2 OBJECT-TYPE
SYNTAX Integer32 
MAX-ACCESS read-only
STATUS current
DESCRIPTION
"N/A"
::= { pm15minApStatEntry 38 }
       
pm15minapTxMcastPacketRadio2 OBJECT-TYPE
SYNTAX Integer32 
MAX-ACCESS read-only
STATUS current
DESCRIPTION
"N/A"
::= { pm15minApStatEntry 39 }
       
pm15minapTxMcastOctetRadio2 OBJECT-TYPE
SYNTAX Integer32 
MAX-ACCESS read-only
STATUS current
DESCRIPTION
"N/A"
::= { pm15minApStatEntry 40 }
       
pm15minapTxDropedCountRadio2 OBJECT-TYPE
SYNTAX Integer32 
MAX-ACCESS read-only
STATUS current
DESCRIPTION
"N/A"
::= { pm15minApStatEntry 41 }
       
pm15minapAdminStatusRadio2 OBJECT-TYPE
SYNTAX Integer32 
MAX-ACCESS read-only
STATUS current
DESCRIPTION
"N/A"
::= { pm15minApStatEntry 42 }
       
pm15minapOperStatusRadio2 OBJECT-TYPE
SYNTAX Integer32 
MAX-ACCESS read-only
STATUS current
DESCRIPTION
"N/A"
::= { pm15minApStatEntry 43 }
         
pm15minapLEDStatusRadio2 OBJECT-TYPE
SYNTAX Integer32 
MAX-ACCESS read-only
STATUS current
DESCRIPTION
"N/A"
::= { pm15minApStatEntry 44 }
          
pm15minapRxPacketRadio3 OBJECT-TYPE
SYNTAX Integer32 
MAX-ACCESS read-only
STATUS current
DESCRIPTION
"N/A"
::= { pm15minApStatEntry 45 }
           
pm15minapTxPcketRadio3 OBJECT-TYPE
SYNTAX Integer32 
MAX-ACCESS read-only
STATUS current
DESCRIPTION
"N/A"
::= { pm15minApStatEntry 46 }
            
pm15minapRxOctetRadio3 OBJECT-TYPE
SYNTAX Integer32 
MAX-ACCESS read-only
STATUS current
DESCRIPTION
"N/A"
::= { pm15minApStatEntry 47 }
             
pm15minapTxOctetRadio3 OBJECT-TYPE
SYNTAX Integer32 
MAX-ACCESS read-only
STATUS current
DESCRIPTION
"N/A"
::= { pm15minApStatEntry 48 }
             
pm15minapRtsSuccesRadio3 OBJECT-TYPE
SYNTAX Integer32 
MAX-ACCESS read-only
STATUS current
DESCRIPTION
"N/A"
::= { pm15minApStatEntry 49 }
         
pm15minapRtsFailedRadio3 OBJECT-TYPE
SYNTAX Integer32 
MAX-ACCESS read-only
STATUS current
DESCRIPTION
"N/A"
::= { pm15minApStatEntry 50 }
         
pm15minapTxFailedOctetRadio3 OBJECT-TYPE
SYNTAX Integer32 
MAX-ACCESS read-only
STATUS current
DESCRIPTION
"N/A"
::= { pm15minApStatEntry 51 }
     
pm15minapTxFailedPacketRadio3 OBJECT-TYPE
SYNTAX Integer32 
MAX-ACCESS read-only
STATUS current
DESCRIPTION
"N/A"
::= { pm15minApStatEntry 52 }

pm15minapTxRetansFailRadio3 OBJECT-TYPE
SYNTAX Integer32 
MAX-ACCESS read-only
STATUS current
DESCRIPTION
"N/A"
::= { pm15minApStatEntry 53 }
      
pm15minapTxRetansFailOctetRadio3 OBJECT-TYPE
SYNTAX Integer32 
MAX-ACCESS read-only
STATUS current
DESCRIPTION
"N/A"
::= { pm15minApStatEntry 54 }

pm15minapTxRetansSuccessRadio3 OBJECT-TYPE
SYNTAX Integer32 
MAX-ACCESS read-only
STATUS current
DESCRIPTION
"N/A"
::= { pm15minApStatEntry 55 }
 
pm15minapTxRetansSuccessOctetRadio3 OBJECT-TYPE
SYNTAX Integer32 
MAX-ACCESS read-only
STATUS current
DESCRIPTION
"N/A"
::= { pm15minApStatEntry 56 }

pm15minapRxMcastOctetRadio3 OBJECT-TYPE
SYNTAX Integer32 
MAX-ACCESS read-only
STATUS current
DESCRIPTION
"N/A"
::= { pm15minApStatEntry 57 }
  
pm15minapRxMcastPacketRadio3 OBJECT-TYPE
SYNTAX Integer32 
MAX-ACCESS read-only
STATUS current
DESCRIPTION
"N/A"
::= { pm15minApStatEntry 58 }
         
pm15minapTxMcastPacketRadio3 OBJECT-TYPE
SYNTAX Integer32 
MAX-ACCESS read-only
STATUS current
DESCRIPTION
"N/A"
::= { pm15minApStatEntry 59 }
         
pm15minapTxMcastOctetRadio3 OBJECT-TYPE
SYNTAX Integer32 
MAX-ACCESS read-only
STATUS current
DESCRIPTION
"N/A"
::= { pm15minApStatEntry 60 }
         
pm15minapTxDropedCountRadio3 OBJECT-TYPE
SYNTAX Integer32 
MAX-ACCESS read-only
STATUS current
DESCRIPTION
"N/A"
::= { pm15minApStatEntry 61 }
         
pm15minapAdminStatusRadio3 OBJECT-TYPE
SYNTAX Integer32 
MAX-ACCESS read-only
STATUS current
DESCRIPTION
"N/A"
::= { pm15minApStatEntry 62 }
         
pm15minapOperStatusRadio3 OBJECT-TYPE
SYNTAX Integer32 
MAX-ACCESS read-only
STATUS current
DESCRIPTION
"N/A"
::= { pm15minApStatEntry 63 }
           
pm15minapLEDStatusRadio3 OBJECT-TYPE
SYNTAX Integer32 
MAX-ACCESS read-only
STATUS current
DESCRIPTION
"N/A"
::= { pm15minApStatEntry 64 }
            
pm15minapRxPacketRadio4 OBJECT-TYPE
SYNTAX Integer32 
MAX-ACCESS read-only
STATUS current
DESCRIPTION
"N/A"
::= { pm15minApStatEntry 65 }
             
pm15minapTxPcketRadio4 OBJECT-TYPE
SYNTAX Integer32 
MAX-ACCESS read-only
STATUS current
DESCRIPTION
"N/A"
::= { pm15minApStatEntry 66 }
              
pm15minapRxOctetRadio4 OBJECT-TYPE
SYNTAX Integer32 
MAX-ACCESS read-only
STATUS current
DESCRIPTION
"N/A"
::= { pm15minApStatEntry 67 }
               
pm15minapTxOctetRadio4 OBJECT-TYPE
SYNTAX Integer32 
MAX-ACCESS read-only
STATUS current
DESCRIPTION
"N/A"
::= { pm15minApStatEntry 68 }
               
pm15minapRtsSuccesRadio4 OBJECT-TYPE
SYNTAX Integer32 
MAX-ACCESS read-only
STATUS current
DESCRIPTION
"N/A"
::= { pm15minApStatEntry 69 }
             
pm15minapRtsFailedRadio4 OBJECT-TYPE
SYNTAX Integer32 
MAX-ACCESS read-only
STATUS current
DESCRIPTION
"N/A"
::= { pm15minApStatEntry 70 }
             
pm15minapTxFailedOctetRadio4 OBJECT-TYPE
SYNTAX Integer32 
MAX-ACCESS read-only
STATUS current
DESCRIPTION
"N/A"
::= { pm15minApStatEntry 71 }

pm15minapTxFailedPacketRadio4 OBJECT-TYPE
SYNTAX Integer32 
MAX-ACCESS read-only
STATUS current
DESCRIPTION
"N/A"
::= { pm15minApStatEntry 72 }
        
pm15minapTxRetansFailRadio4 OBJECT-TYPE
SYNTAX Integer32 
MAX-ACCESS read-only
STATUS current
DESCRIPTION
"N/A"
::= { pm15minApStatEntry 73 }
          
pm15minapTxRetansFailOctetRadio4 OBJECT-TYPE
SYNTAX Integer32 
MAX-ACCESS read-only
STATUS current
DESCRIPTION
"N/A"
::= { pm15minApStatEntry 74 }
     
pm15minapTxRetansSuccessRadio4 OBJECT-TYPE
SYNTAX Integer32 
MAX-ACCESS read-only
STATUS current
DESCRIPTION
"N/A"
::= { pm15minApStatEntry 75 }
       
pm15minapTxRetansSuccessOctetRadio4 OBJECT-TYPE
SYNTAX Integer32 
MAX-ACCESS read-only
STATUS current
DESCRIPTION
"N/A"
::= { pm15minApStatEntry 76 }
  
pm15minapRxMcastOctetRadio4 OBJECT-TYPE
SYNTAX Integer32 
MAX-ACCESS read-only
STATUS current
DESCRIPTION
"N/A"
::= { pm15minApStatEntry 77 }
          
pm15minapRxMcastPacketRadio4 OBJECT-TYPE
SYNTAX Integer32 
MAX-ACCESS read-only
STATUS current
DESCRIPTION
"N/A"
::= { pm15minApStatEntry 78 }
         
pm15minapTxMcastPacketRadio4 OBJECT-TYPE
SYNTAX Integer32 
MAX-ACCESS read-only
STATUS current
DESCRIPTION
"N/A"
::= { pm15minApStatEntry 79 }
         
pm15minapTxMcastOctetRadio4 OBJECT-TYPE
SYNTAX Integer32 
MAX-ACCESS read-only
STATUS current
DESCRIPTION
"N/A"
::= { pm15minApStatEntry 80 }
          
pm15minapTxDropedCountRadio4 OBJECT-TYPE
SYNTAX Integer32 
MAX-ACCESS read-only
STATUS current
DESCRIPTION
"N/A"
::= { pm15minApStatEntry 81 }
         
pm15minapAdminStatusRadio4 OBJECT-TYPE
SYNTAX Integer32 
MAX-ACCESS read-only
STATUS current
DESCRIPTION
"N/A"
::= { pm15minApStatEntry 82 }
           
pm15minapOperStatusRadio4 OBJECT-TYPE
SYNTAX Integer32 
MAX-ACCESS read-only
STATUS current
DESCRIPTION
"N/A"
::= { pm15minApStatEntry 83 }
            
pm15minapLEDStatusRadio4 OBJECT-TYPE
SYNTAX Integer32 
MAX-ACCESS read-only
STATUS current
DESCRIPTION
"N/A"
::= { pm15minApStatEntry 84 }
             
pm15minapOperStatus OBJECT-TYPE
SYNTAX Integer32 
MAX-ACCESS read-only
STATUS current
DESCRIPTION
"N/A"
::= { pm15minApStatEntry 85 }

pm15minTimeStamp OBJECT-TYPE
SYNTAX Integer32 
MAX-ACCESS read-only
STATUS current
DESCRIPTION
"N/A"
::= { pm15minApStatEntry 86 }

-- 15min Client Statistics
pm15minclientStat  OBJECT IDENTIFIER  ::= { performance15min 2 }

pm15minclientStatTable OBJECT-TYPE
SYNTAX SEQUENCE OF Pm15minClientStatEntry
MAX-ACCESS not-accessible
STATUS current
DESCRIPTION
"A table that contains Clients statistics"
::= { pm15minclientStat 1 }

pm15minClientStatEntry OBJECT-TYPE
SYNTAX Pm15minClientStatEntry
MAX-ACCESS not-accessible
STATUS current
DESCRIPTION
"N/A"
INDEX { pm15minclientStatIndex,pm15minCltimeIx }
::= { pm15minclientStatTable 1 }

Pm15minClientStatEntry ::=
SEQUENCE {       
  pm15minclientStatIndex            Integer32,
  pm15minCltimeIx	             Integer32,
  pm15minclientRxPacket              Integer32,
  pm15minclientTxPcket               Integer32,
  pm15minclientRxOctet               Integer32,
  pm15minclientTxOctet               Integer32,    
  pm15minclientTxFailedOctet         Integer32,
  pm15minclientTxFailedPacket        Integer32,
  pm15minclientTxRetansFail          Integer32,
  pm15minclientTxRetansFailOctet     Integer32,
  pm15minclientTxRetansSuccess       Integer32,
  pm15minclientTxRetansSuccessOctet  Integer32,
  pm15minclientTxDropedCount         Integer32,
  pm15minclientAid                   Integer32,
  pm15minclientMACAddress            DisplayString,
  pm15minclientAssociatedTime        Integer32,
  pm15minclientRssiAvg               Integer32, 
  pm15minclientVlanNumber            Integer32,
  pm15minclientESSID                 Integer32,
  pm15minclientEncMethod             Integer32,
  pm15minclientMacPHY                DisplayString,            
  pm15minclientAminStatus            Integer32,
  pm15minclientOperStatus            Integer32,
  pm15minClTimeStamp		     Integer32
}

pm15minclientStatIndex OBJECT-TYPE
SYNTAX Integer32 
MAX-ACCESS read-only
STATUS current
DESCRIPTION
"N/A"
::= { pm15minClientStatEntry 1 }

pm15minCltimeIx OBJECT-TYPE
SYNTAX Integer32 
MAX-ACCESS read-only
STATUS current
DESCRIPTION
"N/A"
::= { pm15minClientStatEntry 2 }

pm15minclientRxPacket OBJECT-TYPE
SYNTAX Integer32 
MAX-ACCESS read-only
STATUS current
DESCRIPTION
"N/A"
::= { pm15minClientStatEntry 3 }

pm15minclientTxPcket OBJECT-TYPE
SYNTAX Integer32 
MAX-ACCESS read-only
STATUS current
DESCRIPTION
"N/A"
::= { pm15minClientStatEntry 4 }

pm15minclientRxOctet OBJECT-TYPE
SYNTAX Integer32 
MAX-ACCESS read-only
STATUS current
DESCRIPTION
"N/A"
::= { pm15minClientStatEntry 5 }

pm15minclientTxOctet OBJECT-TYPE
SYNTAX Integer32 
MAX-ACCESS read-only
STATUS current
DESCRIPTION
"N/A"
::= { pm15minClientStatEntry 6 }

pm15minclientTxFailedOctet OBJECT-TYPE
SYNTAX Integer32 
MAX-ACCESS read-only
STATUS current
DESCRIPTION
"N/A"
::= { pm15minClientStatEntry 7 }

pm15minclientTxFailedPacket OBJECT-TYPE
SYNTAX Integer32 
MAX-ACCESS read-only
STATUS current
DESCRIPTION
"N/A"
::= { pm15minClientStatEntry 8 }

pm15minclientTxRetansFail OBJECT-TYPE
SYNTAX Integer32 
MAX-ACCESS read-only
STATUS current
DESCRIPTION
"N/A"
::= { pm15minClientStatEntry 9 }

pm15minclientTxRetansFailOctet OBJECT-TYPE
SYNTAX Integer32 
MAX-ACCESS read-only
STATUS current
DESCRIPTION
"N/A"
::= { pm15minClientStatEntry 10 }

pm15minclientTxRetansSuccess OBJECT-TYPE
SYNTAX Integer32 
MAX-ACCESS read-only
STATUS current
DESCRIPTION
"N/A"
::= { pm15minClientStatEntry 11 }

pm15minclientTxRetansSuccessOctet OBJECT-TYPE
SYNTAX Integer32 
MAX-ACCESS read-only
STATUS current
DESCRIPTION
"N/A"
::= { pm15minClientStatEntry 12 }

pm15minclientTxDropedCount OBJECT-TYPE
SYNTAX Integer32 
MAX-ACCESS read-only
STATUS current
DESCRIPTION
"N/A"
::= { pm15minClientStatEntry 13 }

pm15minclientAid OBJECT-TYPE
SYNTAX Integer32 
MAX-ACCESS read-only
STATUS current
DESCRIPTION
"N/A"
::= { pm15minClientStatEntry 14 }

pm15minclientMACAddress OBJECT-TYPE
SYNTAX DisplayString 
MAX-ACCESS read-only
STATUS current
DESCRIPTION
"N/A"
::= { pm15minClientStatEntry 15 }

pm15minclientAssociatedTime OBJECT-TYPE
SYNTAX Integer32 
MAX-ACCESS read-only
STATUS current
DESCRIPTION
"N/A"
::= { pm15minClientStatEntry 16 }

pm15minclientRssiAvg OBJECT-TYPE
SYNTAX Integer32 
MAX-ACCESS read-only
STATUS current
DESCRIPTION
"N/A"
::= { pm15minClientStatEntry 17 }

pm15minclientVlanNumber OBJECT-TYPE
SYNTAX Integer32 
MAX-ACCESS read-only
STATUS current
DESCRIPTION
"N/A"
::= { pm15minClientStatEntry 18 }

pm15minclientESSID OBJECT-TYPE
SYNTAX Integer32 
MAX-ACCESS read-only
STATUS current
DESCRIPTION
"N/A"
::= { pm15minClientStatEntry 19 }

pm15minclientEncMethod OBJECT-TYPE
SYNTAX Integer32 
MAX-ACCESS read-only
STATUS current
DESCRIPTION
"N/A"
::= { pm15minClientStatEntry 20 }

pm15minclientMacPHY OBJECT-TYPE
SYNTAX DisplayString 
MAX-ACCESS read-only
STATUS current
DESCRIPTION
"N/A"
::= { pm15minClientStatEntry 21 }
          
pm15minclientAminStatus OBJECT-TYPE
SYNTAX Integer32 
MAX-ACCESS read-only
STATUS current
DESCRIPTION
"N/A"
::= { pm15minClientStatEntry 22 }

pm15minclientOperStatus OBJECT-TYPE
SYNTAX Integer32 
MAX-ACCESS read-only
STATUS current
DESCRIPTION
"N/A"
::= { pm15minClientStatEntry 23 }

pm15minClTimeStamp OBJECT-TYPE
SYNTAX Integer32 
MAX-ACCESS read-only
STATUS current
DESCRIPTION
"N/A"
::= { pm15minClientStatEntry 24 }

-- 15min Channel Statistics
pm15minchannelStat  OBJECT IDENTIFIER  ::= { performance15min 3 }

pm15minchannelStatTable OBJECT-TYPE
SYNTAX SEQUENCE OF Pm15minChannelStatEntry
MAX-ACCESS not-accessible
STATUS current
DESCRIPTION
"A table that contains Clients statistics"
::= { pm15minchannelStat 1 }

pm15minChannelStatEntry OBJECT-TYPE
SYNTAX Pm15minChannelStatEntry
MAX-ACCESS not-accessible
STATUS current
DESCRIPTION
"N/A"
INDEX { pm15minchannelStatIndex,pm15minChtimeIx }
::= { pm15minchannelStatTable 1 }

Pm15minChannelStatEntry ::=
SEQUENCE {       
  pm15minchannelStatIndex             Integer32,
  pm15minChtimeIx	                   Integer32,  
  pm15minchannelRxPacket               Integer32,
  pm15minchannelTxPcket                Integer32,  
  pm15minchannelRxOctet                Integer32,
  pm15minchannelTxOctet                Integer32,
  pm15minchannelTxFailedOctet          Integer32,
  pm15minchannelTxFailedPacket         Integer32,
  pm15minchannelTxRetansFail           Integer32,
  pm15minchannelTxRetansFailOctet      Integer32,
  pm15minchannelTxRetansSuccess        Integer32,
  pm15minchannelTxRetansSuccessOctet   Integer32,
  pm15minchannelTxDropedCount          Integer32,
  pm15minchannelTxMcastOctet           Integer32,
  pm15minchannelTxMcastPacket          Integer32,
  pm15minchannelRxMcastPacket          Integer32,
  pm15minchannelRxMcastOctet           Integer32,
  pm15minchannelClientsCount           Integer32,
  pm15minchannelOperStatus             Integer32,
  pm15minChTimeStamp		           Integer32
}
pm15minchannelStatIndex OBJECT-TYPE
SYNTAX Integer32 
MAX-ACCESS read-only
STATUS current
DESCRIPTION
"N/A"
::= { pm15minChannelStatEntry 1 }

pm15minChtimeIx OBJECT-TYPE
SYNTAX Integer32 
MAX-ACCESS read-only
STATUS current
DESCRIPTION
"N/A"
::= { pm15minChannelStatEntry 2 }
      

pm15minchannelRxPacket OBJECT-TYPE
SYNTAX Integer32 
MAX-ACCESS read-only
STATUS current
DESCRIPTION
"N/A"
::= { pm15minChannelStatEntry 3 }

pm15minchannelTxPcket OBJECT-TYPE
SYNTAX Integer32 
MAX-ACCESS read-only
STATUS current
DESCRIPTION
"N/A"
::= { pm15minChannelStatEntry 4 }

pm15minchannelRxOctet OBJECT-TYPE
SYNTAX Integer32 
MAX-ACCESS read-only
STATUS current
DESCRIPTION
"N/A"
::= { pm15minChannelStatEntry 5 }

pm15minchannelTxOctet OBJECT-TYPE
SYNTAX Integer32 
MAX-ACCESS read-only
STATUS current
DESCRIPTION
"N/A"
::= { pm15minChannelStatEntry 6 }

pm15minchannelTxFailedOctet OBJECT-TYPE
SYNTAX Integer32 
MAX-ACCESS read-only
STATUS current
DESCRIPTION
"N/A"
::= { pm15minChannelStatEntry 7 }

pm15minchannelTxFailedPacket OBJECT-TYPE
SYNTAX Integer32 
MAX-ACCESS read-only
STATUS current
DESCRIPTION
"N/A"
::= { pm15minChannelStatEntry 8 }

pm15minchannelTxRetansFail  OBJECT-TYPE
SYNTAX Integer32 
MAX-ACCESS read-only
STATUS current
DESCRIPTION
"N/A"
::= { pm15minChannelStatEntry 9 }

pm15minchannelTxRetansFailOctet  OBJECT-TYPE
SYNTAX Integer32 
MAX-ACCESS read-only
STATUS current
DESCRIPTION
"N/A"
::= { pm15minChannelStatEntry 10 }

pm15minchannelTxRetansSuccess  OBJECT-TYPE
SYNTAX Integer32 
MAX-ACCESS read-only
STATUS current
DESCRIPTION
"N/A"
::= { pm15minChannelStatEntry 11 }

pm15minchannelTxRetansSuccessOctet  OBJECT-TYPE
SYNTAX Integer32 
MAX-ACCESS read-only
STATUS current
DESCRIPTION
"N/A"
::= { pm15minChannelStatEntry 12 }

pm15minchannelTxDropedCount  OBJECT-TYPE
SYNTAX Integer32 
MAX-ACCESS read-only
STATUS current
DESCRIPTION
"N/A"
::= { pm15minChannelStatEntry 13 }

pm15minchannelTxMcastOctet OBJECT-TYPE
SYNTAX Integer32 
MAX-ACCESS read-only
STATUS current
DESCRIPTION
"N/A"
::= { pm15minChannelStatEntry 14 }

pm15minchannelTxMcastPacket  OBJECT-TYPE
SYNTAX Integer32 
MAX-ACCESS read-only
STATUS current
DESCRIPTION
"N/A"
::= { pm15minChannelStatEntry 15 }

pm15minchannelRxMcastPacket OBJECT-TYPE
SYNTAX Integer32 
MAX-ACCESS read-only
STATUS current
DESCRIPTION
"N/A"
::= { pm15minChannelStatEntry 16 }

pm15minchannelRxMcastOctet  OBJECT-TYPE
SYNTAX Integer32 
MAX-ACCESS read-only
STATUS current
DESCRIPTION
"N/A"
::= { pm15minChannelStatEntry 17 }

pm15minchannelClientsCount OBJECT-TYPE
SYNTAX Integer32 
MAX-ACCESS read-only
STATUS current
DESCRIPTION
"N/A"
::= { pm15minChannelStatEntry 18 }

pm15minchannelOperStatus OBJECT-TYPE
SYNTAX Integer32 
MAX-ACCESS read-only
STATUS current
DESCRIPTION
"N/A"

::= { pm15minChannelStatEntry 19 }
pm15minChTimeStamp OBJECT-TYPE
SYNTAX Integer32 
MAX-ACCESS read-only
STATUS current
DESCRIPTION
"N/A"
::= { pm15minChannelStatEntry 20 }



-- 15min ESS Statistics

pm15minessStat  OBJECT IDENTIFIER  ::= { performance15min 4 }

pm15minessStatTable OBJECT-TYPE
SYNTAX SEQUENCE OF Pm15minEssStatEntry
MAX-ACCESS not-accessible
STATUS current
DESCRIPTION
"A table that contains Clients statistics"
::= { pm15minessStat 1 }

pm15minEssStatEntry OBJECT-TYPE
SYNTAX Pm15minEssStatEntry
MAX-ACCESS not-accessible
STATUS current
DESCRIPTION
"N/A"
INDEX { pm15minessStatIndex,pm15minEsstimeIx }
::= { pm15minessStatTable 1 }

Pm15minEssStatEntry ::=
SEQUENCE {       
  pm15minessStatIndex               Integer32,
  pm15minEsstimeIx	             Integer32,  
  pm15minessRxPacket                 Integer32,
  pm15minessTxPacket                 Integer32,
  pm15minessRxOctet                  Integer32,
  pm15minessTxOctet                  Integer32,
  pm15minessTxFailedOctet            Integer32,
  pm15minessTxFailedPacket           Integer32,
  pm15minessTxRetansFail             Integer32,
  pm15minessTxRetansFailOctet        Integer32,
  pm15minessTxRetansSuccess          Integer32,
  pm15minessTxRetansSuccessOctet     Integer32,
  pm15minessTxMcastOctet             Integer32,
  pm15minessTxMcastPacket            Integer32,
  pm15minessRxMcastPacket            Integer32,
  pm15minessRxMcastOctet             Integer32,
  pm15minessTxDropedCount            Integer32,
  pm15minessClientsCount             Integer32,
  pm15minessAdminStatus              Integer32,
  pm15minessOperStatus               Integer32,
  pm15minessConfigIndex              Integer32,
  pm15minEssTimeStamp                Integer32
}     
pm15minessStatIndex OBJECT-TYPE
SYNTAX Integer32 
MAX-ACCESS read-only
STATUS current
DESCRIPTION
"N/A"
::= { pm15minEssStatEntry 1 }

pm15minEsstimeIx OBJECT-TYPE
SYNTAX Integer32 
MAX-ACCESS read-only
STATUS current
DESCRIPTION
"N/A"
::= { pm15minEssStatEntry 2 }
            
pm15minessRxPacket OBJECT-TYPE
SYNTAX Integer32 
MAX-ACCESS read-only
STATUS current
DESCRIPTION
"N/A"
::= { pm15minEssStatEntry 3 }
 
pm15minessTxPacket OBJECT-TYPE
SYNTAX Integer32 
MAX-ACCESS read-only
STATUS current
DESCRIPTION
"N/A"
::= { pm15minEssStatEntry 4 }
 
pm15minessRxOctet OBJECT-TYPE
SYNTAX Integer32 
MAX-ACCESS read-only
STATUS current
DESCRIPTION
"N/A"
::= { pm15minEssStatEntry 5 }
 
pm15minessTxOctet OBJECT-TYPE
SYNTAX Integer32 
MAX-ACCESS read-only
STATUS current
DESCRIPTION
"N/A"
::= { pm15minEssStatEntry 6 }
 
pm15minessTxFailedOctet OBJECT-TYPE
SYNTAX Integer32 
MAX-ACCESS read-only
STATUS current
DESCRIPTION
"N/A"
::= { pm15minEssStatEntry 7 }
 
pm15minessTxFailedPacket OBJECT-TYPE
SYNTAX Integer32 
MAX-ACCESS read-only
STATUS current
DESCRIPTION
"N/A"
::= { pm15minEssStatEntry 8 }
 
pm15minessTxRetansFail OBJECT-TYPE
SYNTAX Integer32 
MAX-ACCESS read-only
STATUS current
DESCRIPTION
"N/A"
::= { pm15minEssStatEntry 9 }
 
pm15minessTxRetansFailOctet OBJECT-TYPE
SYNTAX Integer32 
MAX-ACCESS read-only
STATUS current
DESCRIPTION
"N/A"
::= { pm15minEssStatEntry 10 }
 
pm15minessTxRetansSuccess OBJECT-TYPE
SYNTAX Integer32 
MAX-ACCESS read-only
STATUS current
DESCRIPTION
"N/A"
::= { pm15minEssStatEntry 11 }
  
pm15minessTxRetansSuccessOctet OBJECT-TYPE
SYNTAX Integer32 
MAX-ACCESS read-only
STATUS current
DESCRIPTION
"N/A"
::= { pm15minEssStatEntry 12 }
 
pm15minessTxMcastOctet OBJECT-TYPE
SYNTAX Integer32 
MAX-ACCESS read-only
STATUS current
DESCRIPTION
"N/A"
::= { pm15minEssStatEntry 13 }
 
pm15minessTxMcastPacket OBJECT-TYPE
SYNTAX Integer32
MAX-ACCESS read-only
STATUS current
DESCRIPTION
"N/A"
::= { pm15minEssStatEntry 14 }
 
pm15minessRxMcastPacket OBJECT-TYPE
SYNTAX Integer32 
MAX-ACCESS read-only
STATUS current
DESCRIPTION
"N/A"
::= { pm15minEssStatEntry 15 }
        
pm15minessRxMcastOctet OBJECT-TYPE
SYNTAX Integer32 
MAX-ACCESS read-only
STATUS current
DESCRIPTION              
"N/A"
::= { pm15minEssStatEntry 16 }
        
pm15minessTxDropedCount OBJECT-TYPE
SYNTAX Integer32 
MAX-ACCESS read-only
STATUS current
DESCRIPTION
"N/A"
::= { pm15minEssStatEntry 17 }
        
pm15minessClientsCount OBJECT-TYPE
SYNTAX Integer32 
MAX-ACCESS read-only
STATUS current
DESCRIPTION
"N/A"
::= { pm15minEssStatEntry 18 }
        
pm15minessAdminStatus  OBJECT-TYPE
SYNTAX Integer32 
MAX-ACCESS read-only
STATUS current
DESCRIPTION
"N/A"
::= { pm15minEssStatEntry 19 }
         
pm15minessOperStatus OBJECT-TYPE
SYNTAX Integer32 
MAX-ACCESS read-only
STATUS current
DESCRIPTION
"N/A"
::= { pm15minEssStatEntry 20 }
    
pm15minessConfigIndex  OBJECT-TYPE
SYNTAX Integer32 
MAX-ACCESS read-only
STATUS current
DESCRIPTION
"N/A"
::= { pm15minEssStatEntry 21 }

pm15minEssTimeStamp OBJECT-TYPE
SYNTAX Integer32 
MAX-ACCESS read-only
STATUS current
DESCRIPTION
"N/A"
::= { pm15minEssStatEntry 22 }

-- 15min Switch Statistics

pm15minswitchStat  OBJECT IDENTIFIER  ::= { performance15min 5 } 

pm15minswitchStatTable OBJECT-TYPE
SYNTAX SEQUENCE OF Pm15minSwitchStatEntry
MAX-ACCESS not-accessible
STATUS current
DESCRIPTION
"A table that contains Switch global statistics"
::= { pm15minswitchStat 1 }

pm15minSwitchStatEntry OBJECT-TYPE
SYNTAX Pm15minSwitchStatEntry
MAX-ACCESS not-accessible
STATUS current
DESCRIPTION
"N/A"
INDEX { pm15minSwtimeIx }
::= { pm15minswitchStatTable 1 }

-- INDEX { pm15minswitchStatIndex, pm15minSwtimeIx }


Pm15minSwitchStatEntry ::=
SEQUENCE {
  pm15minswitchStatIndex               Integer32,
  pm15minSwtimeIx	               	Integer32,
  pm15minRxPacket			Integer32,
  pm15minTxPacket 			Integer32,
  pm15minRxOctet 			Integer32,
  pm15minTxOctet 			Integer32,
  pm15minTxFailedOctet 			Integer32,
  pm15minTxFailedPacket 		Integer32,
  pm15minTxRetansFail 			Integer32,
  pm15minTxRetansFailOctet 		Integer32,
  pm15minTxRetansSuccess 		Integer32,
  pm15minTxRetansSuccessOctet 		Integer32,
  pm15minRxMcastOctet 			Integer32,
  pm15minRxMcastPacket 			Integer32,
  pm15minTxMcastPacket 			Integer32,
  pm15minTxMcastOctet 			Integer32,
  pm15minTxDropedCount 			Integer32,
  pm15minClientsCount 			Integer32,
  pm15minRtsSucces 			Integer32,
  pm15minRtsFailed 			Integer32,
  pm15minRxLanPacket			Integer32,
  pm15minTxLanPacket			Integer32,
  pm15minRxLanOctet			Integer32,
  pm15minTxLanOctet			Integer32,
  pm15minRxLanMcastPacket		Integer32,
  pm15minTxLanError			Integer32,
  pm15minTxLanDropped 			Integer32,
  pm15minRxLanDropped 			Integer32,
  pm15minTxLanCollission 		Integer32,
  pm15minRxLanFrame 			Integer32,
  pm15minTxLanCarrier 			Integer32,
  pm15minSwTimeStamp		        Integer32
}
pm15minswitchStatIndex OBJECT-TYPE
SYNTAX Integer32
MAX-ACCESS read-only
STATUS current
DESCRIPTION
"N/A"
::= { pm15minSwitchStatEntry 1 }


pm15minSwtimeIx	OBJECT-TYPE
SYNTAX Integer32
MAX-ACCESS read-only
STATUS current
DESCRIPTION
"N/A"
::= { pm15minSwitchStatEntry 2 }

pm15minRxPacket	OBJECT-TYPE
SYNTAX Integer32
MAX-ACCESS read-only
STATUS current
DESCRIPTION
"N/A"
::= { pm15minSwitchStatEntry 3 }

pm15minTxPacket	 OBJECT-TYPE
SYNTAX Integer32
MAX-ACCESS read-only
STATUS current
DESCRIPTION
"N/A"
::= { pm15minSwitchStatEntry 4 }
   			
pm15minRxOctet	 OBJECT-TYPE
SYNTAX Integer32
MAX-ACCESS read-only
STATUS current
DESCRIPTION
"N/A"
::= { pm15minSwitchStatEntry 5 }

pm15minTxOctet OBJECT-TYPE
SYNTAX Integer32
MAX-ACCESS read-only
STATUS current
DESCRIPTION
"N/A"
::= { pm15minSwitchStatEntry 6 }
		
pm15minTxFailedOctet OBJECT-TYPE
SYNTAX Integer32
MAX-ACCESS read-only
STATUS current
DESCRIPTION
"N/A"
::= { pm15minSwitchStatEntry 7 }
   			
pm15minTxFailedPacket OBJECT-TYPE
SYNTAX Integer32
MAX-ACCESS read-only
STATUS current
DESCRIPTION
"N/A"
::= { pm15minSwitchStatEntry 8 }


pm15minTxRetansFail OBJECT-TYPE
SYNTAX Integer32
MAX-ACCESS read-only
STATUS current
DESCRIPTION
"N/A"
::= { pm15minSwitchStatEntry 9 }
   			

pm15minTxRetansFailOctet OBJECT-TYPE
SYNTAX Integer32
MAX-ACCESS read-only
STATUS current
DESCRIPTION
"N/A"
::= { pm15minSwitchStatEntry 10 }
	
pm15minTxRetansSuccess  OBJECT-TYPE
SYNTAX Integer32
MAX-ACCESS read-only
STATUS current
DESCRIPTION
"N/A"
::= { pm15minSwitchStatEntry 11 }

pm15minTxRetansSuccessOctet  OBJECT-TYPE
SYNTAX Integer32
MAX-ACCESS read-only
STATUS current
DESCRIPTION
"N/A"
::= { pm15minSwitchStatEntry 12 }

pm15minRxMcastOctet  OBJECT-TYPE
SYNTAX Integer32
MAX-ACCESS read-only
STATUS current
DESCRIPTION
"N/A"
::= { pm15minSwitchStatEntry 13 }

pm15minRxMcastPacket  OBJECT-TYPE
SYNTAX Integer32
MAX-ACCESS read-only
STATUS current
DESCRIPTION
"N/A"
::= { pm15minSwitchStatEntry 14 }

pm15minTxMcastPacket  OBJECT-TYPE
SYNTAX Integer32
MAX-ACCESS read-only
STATUS current
DESCRIPTION
"N/A"
::= { pm15minSwitchStatEntry 15 }

pm15minTxMcastOctet  OBJECT-TYPE
SYNTAX Integer32
MAX-ACCESS read-only
STATUS current
DESCRIPTION
"N/A"
::= { pm15minSwitchStatEntry 16 }

pm15minTxDropedCount  OBJECT-TYPE
SYNTAX Integer32
MAX-ACCESS read-only
STATUS current
DESCRIPTION
"N/A"
::= { pm15minSwitchStatEntry 17 }

pm15minClientsCount  OBJECT-TYPE
SYNTAX Integer32
MAX-ACCESS read-only
STATUS current
DESCRIPTION
"N/A"
::= { pm15minSwitchStatEntry 18 }

pm15minRtsSucces  OBJECT-TYPE
SYNTAX Integer32
MAX-ACCESS read-only
STATUS current
DESCRIPTION
"N/A"
::= { pm15minSwitchStatEntry 19 }

pm15minRtsFailed  OBJECT-TYPE
SYNTAX Integer32
MAX-ACCESS read-only
STATUS current
DESCRIPTION
"N/A"
::= { pm15minSwitchStatEntry 20 }

pm15minRxLanPacket  OBJECT-TYPE
SYNTAX Integer32
MAX-ACCESS read-only
STATUS current
DESCRIPTION
"N/A"
::= { pm15minSwitchStatEntry 21 }

pm15minTxLanPacket  OBJECT-TYPE
SYNTAX Integer32
MAX-ACCESS read-only
STATUS current
DESCRIPTION
"N/A"
::= { pm15minSwitchStatEntry 22 }

pm15minRxLanOctet  OBJECT-TYPE
SYNTAX Integer32
MAX-ACCESS read-only
STATUS current
DESCRIPTION
"N/A"
::= { pm15minSwitchStatEntry 23 }

pm15minTxLanOctet  OBJECT-TYPE
SYNTAX Integer32
MAX-ACCESS read-only
STATUS current
DESCRIPTION
"N/A"
::= { pm15minSwitchStatEntry 24 }

pm15minRxLanMcastPacket  OBJECT-TYPE
SYNTAX Integer32
MAX-ACCESS read-only
STATUS current
DESCRIPTION
"N/A"
::= { pm15minSwitchStatEntry 25 }

pm15minTxLanError  OBJECT-TYPE
SYNTAX Integer32
MAX-ACCESS read-only
STATUS current
DESCRIPTION
"N/A"
::= { pm15minSwitchStatEntry 26 }

pm15minTxLanDropped  OBJECT-TYPE
SYNTAX Integer32
MAX-ACCESS read-only
STATUS current
DESCRIPTION
"N/A"
::= { pm15minSwitchStatEntry 27 }

pm15minRxLanDropped  OBJECT-TYPE
SYNTAX Integer32
MAX-ACCESS read-only
STATUS current
DESCRIPTION
"N/A"
::= { pm15minSwitchStatEntry 28 }

pm15minTxLanCollission  OBJECT-TYPE
SYNTAX Integer32
MAX-ACCESS read-only
STATUS current
DESCRIPTION
"N/A"
::= { pm15minSwitchStatEntry 29 }

pm15minRxLanFrame  OBJECT-TYPE
SYNTAX Integer32
MAX-ACCESS read-only
STATUS current
DESCRIPTION
"N/A"
::= { pm15minSwitchStatEntry 30 }

pm15minTxLanCarrier  OBJECT-TYPE
SYNTAX Integer32
MAX-ACCESS read-only
STATUS current
DESCRIPTION
"N/A"
::= { pm15minSwitchStatEntry 31 }

pm15minSwTimeStamp  OBJECT-TYPE
SYNTAX Integer32
MAX-ACCESS read-only
STATUS current
DESCRIPTION
"N/A"
::= { pm15minSwitchStatEntry 32 }






-- =======================================================================
--
--  24hr Performance  
--                              

-- 24 Hr AP statistics
performance24hr  OBJECT IDENTIFIER ::= { mibObjects 24 }

pm24hrapStat  OBJECT IDENTIFIER  ::= { performance24hr 1 }

pm24hrapStatTable OBJECT-TYPE
SYNTAX SEQUENCE OF Pm24hrApStatEntry
MAX-ACCESS not-accessible
STATUS current
DESCRIPTION
"A table that contains Access Point statistics"
::= { pm24hrapStat 1 }

pm24hrApStatEntry OBJECT-TYPE
SYNTAX Pm24hrApStatEntry
MAX-ACCESS not-accessible
STATUS current
DESCRIPTION
"N/A"
INDEX { pm24hrapStatIndex,pm24hrtimeIx }
::= { pm24hrapStatTable 1 }
Pm24hrApStatEntry ::=
SEQUENCE {       
  pm24hrapStatIndex                    Integer32,
  pm24hrtimeIx                         Integer32,
  pm24hrapRtsSucces                    Integer32,
  pm24hrapRtsFailed                    Integer32,
  pm24hrapRxPacketRadio1               Integer32,
  pm24hrapTxPcketRadio1                Integer32,
  pm24hrapRxOctetRadio1                Integer32,
  pm24hrapTxOctetRadio1                Integer32,
  pm24hrapRtsSuccesRadio1              Integer32,
  pm24hrapRtsFailedRadio1              Integer32, 
  pm24hrapTxFailedOctetRadio1          Integer32,
  pm24hrapTxFailedPacketRadio1         Integer32,
  pm24hrapTxRetansFailRadio1           Integer32,
  pm24hrapTxRetansFailOctetRadio1      Integer32,  
  pm24hrapRxMcastOctetRadio1           Integer32,
  pm24hrapRxMcastPacketRadio1          Integer32,
  pm24hrapTxMcastPacketRadio1          Integer32,
  pm24hrapTxMcastOctetRadio1           Integer32,
  pm24hrapTxDropedCountRadio1          Integer32,
  pm24hrapAdminStatusRadio1            Integer32,  
  pm24hrapOperStatusRadio1             Integer32, 
  pm24hrapLEDStatusRadio1              Integer32,
  pm24hrapRxPacketRadio2               Integer32, 
  pm24hrapTxPcketRadio2                Integer32,
  pm24hrapRxOctetRadio2                Integer32,
  pm24hrapTxOctetRadio2                Integer32,   
  pm24hrapRtsSuccesRadio2              Integer32,
  pm24hrapRtsFailedRadio2              Integer32,
  pm24hrapTxFailedOctetRadio2          Integer32,
  pm24hrapTxFailedPacketRadio2         Integer32,
  pm24hrapTxRetansFailRadio2           Integer32,
  pm24hrapTxRetansFailOctetRadio2      Integer32, 
  pm24hrapRxMcastOctetRadio2           Integer32,
  pm24hrapRxMcastPacketRadio2          Integer32,
  pm24hrapTxMcastPacketRadio2          Integer32,
  pm24hrapTxMcastOctetRadio2           Integer32,
  pm24hrapTxDropedCountRadio2          Integer32,
  pm24hrapAdminStatusRadio2            Integer32, 
  pm24hrapOperStatusRadio2             Integer32,
  pm24hrapLEDStatusRadio2              Integer32,
  pm24hrapRxPacketRadio3               Integer32,  
  pm24hrapTxPcketRadio3                Integer32, 
  pm24hrapRxOctetRadio3                Integer32,
  pm24hrapTxOctetRadio3                Integer32,    
  pm24hrapRtsSuccesRadio3              Integer32,
  pm24hrapRtsFailedRadio3              Integer32, 
  pm24hrapTxFailedOctetRadio3          Integer32,
  pm24hrapTxFailedPacketRadio3         Integer32,
  pm24hrapTxRetansFailRadio3           Integer32,
  pm24hrapTxRetansFailOctetRadio3      Integer32,  
  pm24hrapRxMcastOctetRadio3           Integer32,
  pm24hrapRxMcastPacketRadio3          Integer32,
  pm24hrapTxMcastPacketRadio3          Integer32,
  pm24hrapTxMcastOctetRadio3           Integer32,
  pm24hrapTxDropedCountRadio3          Integer32,
  pm24hrapAdminStatusRadio3            Integer32, 
  pm24hrapOperStatusRadio3             Integer32,
  pm24hrapLEDStatusRadio3              Integer32, 
  pm24hrapRxPacketRadio4               Integer32,
  pm24hrapTxPcketRadio4                Integer32,
  pm24hrapRxOctetRadio4                Integer32,
  pm24hrapTxOctetRadio4                Integer32,
  pm24hrapRtsSuccesRadio4              Integer32,
  pm24hrapRtsFailedRadio4              Integer32,
  pm24hrapTxFailedOctetRadio4          Integer32,
  pm24hrapTxFailedPacketRadio4         Integer32,
  pm24hrapTxRetansFailRadio4           Integer32,
  pm24hrapTxRetansFailOctetRadio4      Integer32,
  pm24hrapRxMcastOctetRadio4           Integer32,
  pm24hrapRxMcastPacketRadio4          Integer32,
  pm24hrapTxMcastPacketRadio4          Integer32,
  pm24hrapTxMcastOctetRadio4           Integer32,
  pm24hrapTxDropedCountRadio4          Integer32,
  pm24hrapAdminStatusRadio4            Integer32,
  pm24hrapOperStatusRadio4             Integer32,
  pm24hrapLEDStatusRadio4              Integer32,
  pm24hrapOperStatus                   Integer32,
  pm24hrTimeStamp                      Integer32
}

pm24hrapStatIndex OBJECT-TYPE
SYNTAX Integer32 
MAX-ACCESS read-only
STATUS current
DESCRIPTION
"N/A"
::= { pm24hrApStatEntry 1 }

pm24hrtimeIx OBJECT-TYPE
SYNTAX Integer32 
MAX-ACCESS read-only
STATUS current
DESCRIPTION
"N/A"
::= { pm24hrApStatEntry 2 }

pm24hrapRtsSucces OBJECT-TYPE
SYNTAX Integer32 
MAX-ACCESS read-only
STATUS current
DESCRIPTION
"N/A"
::= { pm24hrApStatEntry 3 }

pm24hrapRtsFailed OBJECT-TYPE
SYNTAX Integer32 
MAX-ACCESS read-only
STATUS current
DESCRIPTION
"N/A"
::= { pm24hrApStatEntry 4 }

pm24hrapRxPacketRadio1 OBJECT-TYPE
SYNTAX Integer32 (0..2147483647)
MAX-ACCESS read-only
STATUS current
DESCRIPTION
"N/A"
::= { pm24hrApStatEntry 5 }

pm24hrapTxPcketRadio1 OBJECT-TYPE
SYNTAX Integer32 (0..2147483647)
MAX-ACCESS read-only
STATUS current
DESCRIPTION
"N/A"
::= { pm24hrApStatEntry 6 }

pm24hrapRxOctetRadio1 OBJECT-TYPE
SYNTAX Integer32 (0..2147483647)
MAX-ACCESS read-only
STATUS current
DESCRIPTION
"N/A"
::= { pm24hrApStatEntry 7 }

pm24hrapTxOctetRadio1 OBJECT-TYPE
SYNTAX Integer32 (0..2147483647)
MAX-ACCESS read-only
STATUS current
DESCRIPTION
"N/A"
::= { pm24hrApStatEntry 8 }

pm24hrapRtsSuccesRadio1 OBJECT-TYPE
SYNTAX Integer32 (0..2147483647)
MAX-ACCESS read-only
STATUS current
DESCRIPTION
"N/A"
::= { pm24hrApStatEntry 9 }

pm24hrapRtsFailedRadio1 OBJECT-TYPE
SYNTAX Integer32 
MAX-ACCESS read-only
STATUS current
DESCRIPTION
"N/A"
::= { pm24hrApStatEntry 10 }

pm24hrapTxFailedOctetRadio1 OBJECT-TYPE
SYNTAX Integer32 (0..2147483647)
MAX-ACCESS read-only
STATUS current
DESCRIPTION
"N/A"
::= { pm24hrApStatEntry 11 }

pm24hrapTxFailedPacketRadio1 OBJECT-TYPE
SYNTAX Integer32 (0..2147483647)
MAX-ACCESS read-only
STATUS current
DESCRIPTION
"N/A"
::= { pm24hrApStatEntry 12 }

pm24hrapTxRetansFailRadio1 OBJECT-TYPE
SYNTAX Integer32 (0..2147483647)
MAX-ACCESS read-only
STATUS current
DESCRIPTION
"N/A"
::= { pm24hrApStatEntry 13 }

pm24hrapTxRetansFailOctetRadio1 OBJECT-TYPE
SYNTAX Integer32 (0..2147483647)
MAX-ACCESS read-only
STATUS current
DESCRIPTION
"N/A"
::= { pm24hrApStatEntry 14 }

pm24hrapRxMcastOctetRadio1  OBJECT-TYPE
SYNTAX Integer32 (0..2147483647)
MAX-ACCESS read-only
STATUS current
DESCRIPTION
"N/A"
::= { pm24hrApStatEntry 15 }

pm24hrapRxMcastPacketRadio1  OBJECT-TYPE
SYNTAX Integer32 (0..2147483647)
MAX-ACCESS read-only
STATUS current
DESCRIPTION
"N/A"
::= { pm24hrApStatEntry 16 }

pm24hrapTxMcastPacketRadio1  OBJECT-TYPE
SYNTAX Integer32 (0..2147483647)
MAX-ACCESS read-only
STATUS current
DESCRIPTION
"N/A"
::= { pm24hrApStatEntry 17 }

pm24hrapTxMcastOctetRadio1 OBJECT-TYPE
SYNTAX Integer32 (0..2147483647)
MAX-ACCESS read-only
STATUS current
DESCRIPTION
"N/A"
::= { pm24hrApStatEntry 18 }

pm24hrapTxDropedCountRadio1 OBJECT-TYPE
SYNTAX Integer32 (0..2147483647)
MAX-ACCESS read-only
STATUS current
DESCRIPTION
"N/A"
::= { pm24hrApStatEntry 19 }
 
pm24hrapAdminStatusRadio1 OBJECT-TYPE
SYNTAX Integer32 
MAX-ACCESS read-only
STATUS current
DESCRIPTION
"N/A"
::= { pm24hrApStatEntry 20 }
   
pm24hrapOperStatusRadio1 OBJECT-TYPE
SYNTAX Integer32 
MAX-ACCESS read-only
STATUS current
DESCRIPTION
"N/A"
::= { pm24hrApStatEntry 21 }
   
pm24hrapLEDStatusRadio1 OBJECT-TYPE
SYNTAX Integer32 
MAX-ACCESS read-only
STATUS current
DESCRIPTION
"N/A"
::= { pm24hrApStatEntry 22 }
    
pm24hrapRxPacketRadio2 OBJECT-TYPE
SYNTAX Integer32 (0..2147483647)
MAX-ACCESS read-only
STATUS current
DESCRIPTION
"N/A"
::= { pm24hrApStatEntry 23 }
     
pm24hrapTxPcketRadio2 OBJECT-TYPE
SYNTAX Integer32 (0..2147483647)
MAX-ACCESS read-only
STATUS current
DESCRIPTION
"N/A"
::= { pm24hrApStatEntry 24 }
      
pm24hrapRxOctetRadio2 OBJECT-TYPE
SYNTAX Integer32 (0..2147483647)
MAX-ACCESS read-only
STATUS current
DESCRIPTION
"N/A"
::= { pm24hrApStatEntry 25 }
       
pm24hrapTxOctetRadio2 OBJECT-TYPE
SYNTAX Integer32 (0..2147483647)
MAX-ACCESS read-only
STATUS current
DESCRIPTION
"N/A"
::= { pm24hrApStatEntry 26 }
       
pm24hrapRtsSuccesRadio2 OBJECT-TYPE
SYNTAX Integer32 (0..2147483647)
MAX-ACCESS read-only
STATUS current
DESCRIPTION
"N/A"
::= { pm24hrApStatEntry 27 }
     
pm24hrapRtsFailedRadio2 OBJECT-TYPE
SYNTAX Integer32 (0..2147483647)
MAX-ACCESS read-only
STATUS current
DESCRIPTION
"N/A"
::= { pm24hrApStatEntry 28 }
     
pm24hrapTxFailedOctetRadio2 OBJECT-TYPE
SYNTAX Integer32 (0..2147483647)
MAX-ACCESS read-only
STATUS current
DESCRIPTION
"N/A"
::= { pm24hrApStatEntry 29 }
 
pm24hrapTxFailedPacketRadio2 OBJECT-TYPE
SYNTAX Integer32 (0..2147483647)
MAX-ACCESS read-only
STATUS current
DESCRIPTION
"N/A"
::= { pm24hrApStatEntry 30 }

pm24hrapTxRetansFailRadio2 OBJECT-TYPE
SYNTAX Integer32 (0..2147483647)
MAX-ACCESS read-only
STATUS current
DESCRIPTION
"N/A"
::= { pm24hrApStatEntry 31 }

pm24hrapTxRetansFailOctetRadio2 OBJECT-TYPE
SYNTAX Integer32 (0..2147483647)
MAX-ACCESS read-only
STATUS current
DESCRIPTION
"N/A"
::= { pm24hrApStatEntry 32 }
  

pm24hrapRxMcastOctetRadio2 OBJECT-TYPE
SYNTAX Integer32 (0..2147483647)
MAX-ACCESS read-only
STATUS current
DESCRIPTION
"N/A"
::= { pm24hrApStatEntry 33 }

pm24hrapRxMcastPacketRadio2 OBJECT-TYPE
SYNTAX Integer32 (0..2147483647)
MAX-ACCESS read-only
STATUS current
DESCRIPTION
"N/A"
::= { pm24hrApStatEntry 34 }
       
pm24hrapTxMcastPacketRadio2 OBJECT-TYPE
SYNTAX Integer32 (0..2147483647)
MAX-ACCESS read-only
STATUS current
DESCRIPTION
"N/A"
::= { pm24hrApStatEntry 35 }
       
pm24hrapTxMcastOctetRadio2 OBJECT-TYPE
SYNTAX Integer32 (0..2147483647)
MAX-ACCESS read-only
STATUS current
DESCRIPTION
"N/A"
::= { pm24hrApStatEntry 36 }
       
pm24hrapTxDropedCountRadio2 OBJECT-TYPE
SYNTAX Integer32 (0..2147483647)
MAX-ACCESS read-only
STATUS current
DESCRIPTION
"N/A"
::= { pm24hrApStatEntry 37 }
       
pm24hrapAdminStatusRadio2 OBJECT-TYPE
SYNTAX Integer32 
MAX-ACCESS read-only
STATUS current
DESCRIPTION
"N/A"
::= { pm24hrApStatEntry 38 }
       
pm24hrapOperStatusRadio2 OBJECT-TYPE
SYNTAX Integer32 
MAX-ACCESS read-only
STATUS current
DESCRIPTION
"N/A"
::= { pm24hrApStatEntry 39 }
         
pm24hrapLEDStatusRadio2 OBJECT-TYPE
SYNTAX Integer32 
MAX-ACCESS read-only
STATUS current
DESCRIPTION
"N/A"
::= { pm24hrApStatEntry 40 }
          
pm24hrapRxPacketRadio3 OBJECT-TYPE
SYNTAX Integer32 (0..2147483647)
MAX-ACCESS read-only
STATUS current
DESCRIPTION
"N/A"
::= { pm24hrApStatEntry 41 }
           
pm24hrapTxPcketRadio3 OBJECT-TYPE
SYNTAX Integer32 (0..2147483647)
MAX-ACCESS read-only
STATUS current
DESCRIPTION
"N/A"
::= { pm24hrApStatEntry 42 }
            
pm24hrapRxOctetRadio3 OBJECT-TYPE
SYNTAX Integer32 (0..2147483647)
MAX-ACCESS read-only
STATUS current
DESCRIPTION
"N/A"
::= { pm24hrApStatEntry 43 }
             
pm24hrapTxOctetRadio3 OBJECT-TYPE
SYNTAX Integer32 (0..2147483647)
MAX-ACCESS read-only
STATUS current
DESCRIPTION
"N/A"
::= { pm24hrApStatEntry 44 }
             
pm24hrapRtsSuccesRadio3 OBJECT-TYPE
SYNTAX Integer32 (0..2147483647)
MAX-ACCESS read-only
STATUS current
DESCRIPTION
"N/A"
::= { pm24hrApStatEntry 45 }
         
pm24hrapRtsFailedRadio3 OBJECT-TYPE
SYNTAX Integer32 (0..2147483647)
MAX-ACCESS read-only
STATUS current
DESCRIPTION
"N/A"
::= { pm24hrApStatEntry 46 }
         
pm24hrapTxFailedOctetRadio3 OBJECT-TYPE
SYNTAX Integer32 (0..2147483647)
MAX-ACCESS read-only
STATUS current
DESCRIPTION
"N/A"
::= { pm24hrApStatEntry 47 }
     
pm24hrapTxFailedPacketRadio3 OBJECT-TYPE
SYNTAX Integer32 (0..2147483647)
MAX-ACCESS read-only
STATUS current
DESCRIPTION
"N/A"
::= { pm24hrApStatEntry 48 }

pm24hrapTxRetansFailRadio3 OBJECT-TYPE
SYNTAX Integer32 (0..2147483647)
MAX-ACCESS read-only
STATUS current
DESCRIPTION
"N/A"
::= { pm24hrApStatEntry 49 }
      
pm24hrapTxRetansFailOctetRadio3 OBJECT-TYPE
SYNTAX Integer32 (0..2147483647)
MAX-ACCESS read-only
STATUS current
DESCRIPTION
"N/A"
::= { pm24hrApStatEntry 50 }


pm24hrapRxMcastOctetRadio3 OBJECT-TYPE
SYNTAX Integer32 (0..2147483647)
MAX-ACCESS read-only
STATUS current
DESCRIPTION
"N/A"
::= { pm24hrApStatEntry 51 }
  
pm24hrapRxMcastPacketRadio3 OBJECT-TYPE
SYNTAX Integer32 (0..2147483647)
MAX-ACCESS read-only
STATUS current
DESCRIPTION
"N/A"
::= { pm24hrApStatEntry 52 }
         
pm24hrapTxMcastPacketRadio3 OBJECT-TYPE
SYNTAX Integer32 (0..2147483647)
MAX-ACCESS read-only
STATUS current
DESCRIPTION
"N/A"
::= { pm24hrApStatEntry 53 }
         
pm24hrapTxMcastOctetRadio3 OBJECT-TYPE
SYNTAX Integer32 (0..2147483647)
MAX-ACCESS read-only
STATUS current
DESCRIPTION
"N/A"
::= { pm24hrApStatEntry 54 }
         
pm24hrapTxDropedCountRadio3 OBJECT-TYPE
SYNTAX Integer32 (0..2147483647)
MAX-ACCESS read-only
STATUS current
DESCRIPTION
"N/A"
::= { pm24hrApStatEntry 55 }
         
pm24hrapAdminStatusRadio3 OBJECT-TYPE
SYNTAX Integer32 
MAX-ACCESS read-only
STATUS current
DESCRIPTION
"N/A"
::= { pm24hrApStatEntry 56 }
         
pm24hrapOperStatusRadio3 OBJECT-TYPE
SYNTAX Integer32 
MAX-ACCESS read-only
STATUS current
DESCRIPTION
"N/A"
::= { pm24hrApStatEntry 57 }
           
pm24hrapLEDStatusRadio3 OBJECT-TYPE
SYNTAX Integer32 (0..2147483647)
MAX-ACCESS read-only
STATUS current
DESCRIPTION
"N/A"
::= { pm24hrApStatEntry 58 }
            
pm24hrapRxPacketRadio4 OBJECT-TYPE
SYNTAX Integer32 (0..2147483647)
MAX-ACCESS read-only
STATUS current
DESCRIPTION
"N/A"
::= { pm24hrApStatEntry 59 }
             
pm24hrapTxPcketRadio4 OBJECT-TYPE
SYNTAX Integer32 (0..2147483647)
MAX-ACCESS read-only
STATUS current
DESCRIPTION
"N/A"
::= { pm24hrApStatEntry 60 }
              
pm24hrapRxOctetRadio4 OBJECT-TYPE
SYNTAX Integer32 (0..2147483647)
MAX-ACCESS read-only
STATUS current
DESCRIPTION
"N/A"
::= { pm24hrApStatEntry 61 }
               
pm24hrapTxOctetRadio4 OBJECT-TYPE
SYNTAX Integer32 (0..2147483647)
MAX-ACCESS read-only
STATUS current
DESCRIPTION
"N/A"
::= { pm24hrApStatEntry 62 }
               
pm24hrapRtsSuccesRadio4 OBJECT-TYPE
SYNTAX Integer32 (0..2147483647)
MAX-ACCESS read-only
STATUS current
DESCRIPTION
"N/A"
::= { pm24hrApStatEntry 63 }
             
pm24hrapRtsFailedRadio4 OBJECT-TYPE
SYNTAX Integer32 (0..2147483647)
MAX-ACCESS read-only
STATUS current
DESCRIPTION
"N/A"
::= { pm24hrApStatEntry 64 }
             
pm24hrapTxFailedOctetRadio4 OBJECT-TYPE
SYNTAX Integer32 (0..2147483647)
MAX-ACCESS read-only
STATUS current
DESCRIPTION
"N/A"
::= { pm24hrApStatEntry 65 }

pm24hrapTxFailedPacketRadio4 OBJECT-TYPE
SYNTAX Integer32 (0..2147483647)
MAX-ACCESS read-only
STATUS current
DESCRIPTION
"N/A"
::= { pm24hrApStatEntry 66 }
        
pm24hrapTxRetansFailRadio4 OBJECT-TYPE
SYNTAX Integer32 (0..2147483647)
MAX-ACCESS read-only
STATUS current
DESCRIPTION
"N/A"
::= { pm24hrApStatEntry 67 }
          
pm24hrapTxRetansFailOctetRadio4 OBJECT-TYPE
SYNTAX Integer32 (0..2147483647)
MAX-ACCESS read-only
STATUS current
DESCRIPTION
"N/A"
::= { pm24hrApStatEntry 68 }
     
pm24hrapRxMcastOctetRadio4 OBJECT-TYPE
SYNTAX Integer32 (0..2147483647)
MAX-ACCESS read-only
STATUS current
DESCRIPTION
"N/A"
::= { pm24hrApStatEntry 69 }
          
pm24hrapRxMcastPacketRadio4 OBJECT-TYPE
SYNTAX Integer32 (0..2147483647)
MAX-ACCESS read-only
STATUS current
DESCRIPTION
"N/A"
::= { pm24hrApStatEntry 70 }
         
pm24hrapTxMcastPacketRadio4 OBJECT-TYPE
SYNTAX Integer32 (0..2147483647)
MAX-ACCESS read-only
STATUS current
DESCRIPTION
"N/A"
::= { pm24hrApStatEntry 71 }
         
pm24hrapTxMcastOctetRadio4 OBJECT-TYPE
SYNTAX Integer32 (0..2147483647)
MAX-ACCESS read-only
STATUS current
DESCRIPTION
"N/A"
::= { pm24hrApStatEntry 72 }
          
pm24hrapTxDropedCountRadio4 OBJECT-TYPE
SYNTAX Integer32 (0..2147483647)
MAX-ACCESS read-only
STATUS current
DESCRIPTION
"N/A"
::= { pm24hrApStatEntry 73 }
         
pm24hrapAdminStatusRadio4 OBJECT-TYPE
SYNTAX Integer32 
MAX-ACCESS read-only
STATUS current
DESCRIPTION
"N/A"
::= { pm24hrApStatEntry 74 }
           
pm24hrapOperStatusRadio4 OBJECT-TYPE
SYNTAX Integer32 
MAX-ACCESS read-only
STATUS current
DESCRIPTION
"N/A"
::= { pm24hrApStatEntry 75 }
            
pm24hrapLEDStatusRadio4 OBJECT-TYPE
SYNTAX Integer32 
MAX-ACCESS read-only
STATUS current
DESCRIPTION
"N/A"
::= { pm24hrApStatEntry 76 }
             
pm24hrapOperStatus OBJECT-TYPE
SYNTAX Integer32 
MAX-ACCESS read-only
STATUS current
DESCRIPTION
"N/A"
::= { pm24hrApStatEntry 77 }

pm24hrTimeStamp OBJECT-TYPE
SYNTAX Integer32 
MAX-ACCESS read-only
STATUS current
DESCRIPTION
"N/A"
::= { pm24hrApStatEntry 78 }


-- 24 Hr Client Statistics

pm24hrclientStat  OBJECT IDENTIFIER  ::= { performance24hr 2 }

pm24hrclientStatTable OBJECT-TYPE
SYNTAX SEQUENCE OF Pm24hrClientStatEntry
MAX-ACCESS not-accessible
STATUS current
DESCRIPTION
"A table that contains Clients statistics"
::= { pm24hrclientStat 1 }

pm24hrClientStatEntry OBJECT-TYPE
SYNTAX Pm24hrClientStatEntry
MAX-ACCESS not-accessible
STATUS current
DESCRIPTION
"N/A"
INDEX { pm24hrclientStatIndex,pm24hrCltimeIx }
::= { pm24hrclientStatTable 1 }

Pm24hrClientStatEntry ::=
SEQUENCE {       
  pm24hrclientStatIndex            Integer32,
  pm24hrCltimeIx	            Integer32,
  pm24hrclientRxPacket              Integer32,
  pm24hrclientTxPcket               Integer32,
  pm24hrclientRxOctet               Integer32,
  pm24hrclientTxOctet               Integer32,    
  pm24hrclientTxFailedOctet         Integer32,
  pm24hrclientTxFailedPacket        Integer32,
  pm24hrclientTxRetansFail          Integer32,
  pm24hrclientTxRetansFailOctet     Integer32,
  pm24hrclientTxDropedCount         Integer32,
  pm24hrclientAid                   Integer32,
  pm24hrclientMACAddress            DisplayString,
  pm24hrclientAssociatedTime        Integer32,
  pm24hrclientRssiAvg               Integer32, 
  pm24hrclientVlanNumber            Integer32,
  pm24hrclientESSID                 Integer32,
  pm24hrclientEncMethod             Integer32,
  pm24hrclientMacPHY                DisplayString,            
  pm24hrclientAminStatus            Integer32,
  pm24hrclientOperStatus            Integer32,
  pm24hrClTimeStamp		    Integer32
}

pm24hrclientStatIndex OBJECT-TYPE
SYNTAX Integer32 
MAX-ACCESS read-only
STATUS current
DESCRIPTION
"N/A"
::= { pm24hrClientStatEntry 1 }

pm24hrCltimeIx OBJECT-TYPE
SYNTAX Integer32 
MAX-ACCESS read-only
STATUS current
DESCRIPTION
"N/A"
::= { pm24hrClientStatEntry 2 }

pm24hrclientRxPacket OBJECT-TYPE
SYNTAX Integer32 (0..2147483647)
MAX-ACCESS read-only
STATUS current
DESCRIPTION
"N/A"
::= { pm24hrClientStatEntry 3 }

pm24hrclientTxPcket OBJECT-TYPE
SYNTAX Integer32 (0..2147483647)
MAX-ACCESS read-only
STATUS current
DESCRIPTION
"N/A"
::= { pm24hrClientStatEntry 4 }

pm24hrclientRxOctet OBJECT-TYPE
SYNTAX Integer32 (0..2147483647)
MAX-ACCESS read-only
STATUS current
DESCRIPTION
"N/A"
::= { pm24hrClientStatEntry 5 }

pm24hrclientTxOctet OBJECT-TYPE
SYNTAX Integer32 (0..2147483647)
MAX-ACCESS read-only
STATUS current
DESCRIPTION
"N/A"
::= { pm24hrClientStatEntry 6 }

pm24hrclientTxFailedOctet OBJECT-TYPE
SYNTAX Integer32 (0..2147483647)
MAX-ACCESS read-only
STATUS current
DESCRIPTION
"N/A"
::= { pm24hrClientStatEntry 7 }

pm24hrclientTxFailedPacket OBJECT-TYPE
SYNTAX Integer32 (0..2147483647)
MAX-ACCESS read-only
STATUS current
DESCRIPTION
"N/A"
::= { pm24hrClientStatEntry 8 }

pm24hrclientTxRetansFail OBJECT-TYPE
SYNTAX Integer32 (0..2147483647)
MAX-ACCESS read-only
STATUS current
DESCRIPTION
"N/A"
::= { pm24hrClientStatEntry 9 }

pm24hrclientTxRetansFailOctet OBJECT-TYPE
SYNTAX Integer32 (0..2147483647)
MAX-ACCESS read-only
STATUS current
DESCRIPTION
"N/A"
::= { pm24hrClientStatEntry 10 }


pm24hrclientTxDropedCount OBJECT-TYPE
SYNTAX Integer32 (0..2147483647)
MAX-ACCESS read-only
STATUS current
DESCRIPTION
"N/A"
::= { pm24hrClientStatEntry 11 }

pm24hrclientAid OBJECT-TYPE
SYNTAX Integer32 
MAX-ACCESS read-only
STATUS current
DESCRIPTION
"N/A"
::= { pm24hrClientStatEntry 12 }

pm24hrclientMACAddress OBJECT-TYPE
SYNTAX DisplayString 
MAX-ACCESS read-only
STATUS current
DESCRIPTION
"N/A"
::= { pm24hrClientStatEntry 13 }

pm24hrclientAssociatedTime OBJECT-TYPE
SYNTAX Integer32 
MAX-ACCESS read-only
STATUS current
DESCRIPTION
"N/A"
::= { pm24hrClientStatEntry 14 }

pm24hrclientRssiAvg OBJECT-TYPE
SYNTAX Integer32 
MAX-ACCESS read-only
STATUS current
DESCRIPTION
"N/A"
::= { pm24hrClientStatEntry 15 }

pm24hrclientVlanNumber OBJECT-TYPE
SYNTAX Integer32 
MAX-ACCESS read-only
STATUS current
DESCRIPTION
"N/A"
::= { pm24hrClientStatEntry 16 }

pm24hrclientESSID OBJECT-TYPE
SYNTAX Integer32 
MAX-ACCESS read-only
STATUS current
DESCRIPTION
"N/A"
::= { pm24hrClientStatEntry 17 }

pm24hrclientEncMethod OBJECT-TYPE
SYNTAX Integer32 
MAX-ACCESS read-only
STATUS current
DESCRIPTION
"N/A"
::= { pm24hrClientStatEntry 18 }

pm24hrclientMacPHY OBJECT-TYPE
SYNTAX DisplayString 
MAX-ACCESS read-only
STATUS current
DESCRIPTION
"N/A"
::= { pm24hrClientStatEntry 19 }
          
pm24hrclientAminStatus OBJECT-TYPE
SYNTAX Integer32 
MAX-ACCESS read-only
STATUS current
DESCRIPTION
"N/A"
::= { pm24hrClientStatEntry 20 }

pm24hrclientOperStatus OBJECT-TYPE
SYNTAX Integer32 
MAX-ACCESS read-only
STATUS current
DESCRIPTION
"N/A"
::= { pm24hrClientStatEntry 21 }

pm24hrClTimeStamp OBJECT-TYPE
SYNTAX Integer32 
MAX-ACCESS read-only
STATUS current
DESCRIPTION
"N/A"
::= { pm24hrClientStatEntry 22 }



-- 24 Hr Channel Statistics

pm24hrchannelStat  OBJECT IDENTIFIER  ::= { performance24hr 3 }

pm24hrchannelStatTable OBJECT-TYPE
SYNTAX SEQUENCE OF Pm24hrChannelStatEntry
MAX-ACCESS not-accessible
STATUS current
DESCRIPTION
"A table that contains Clients statistics"
::= { pm24hrchannelStat 1 }

pm24hrChannelStatEntry OBJECT-TYPE
SYNTAX Pm24hrChannelStatEntry
MAX-ACCESS not-accessible
STATUS current
DESCRIPTION
"N/A"
INDEX { pm24hrchannelStatIndex,pm24hrChtimeIx }
::= { pm24hrchannelStatTable 1 }

Pm24hrChannelStatEntry ::=
SEQUENCE {       
  pm24hrchannelStatIndex            Integer32,
  pm24hrChtimeIx	                 Integer32,  
  pm24hrchannelRxPacket              Integer32,
  pm24hrchannelTxPcket               Integer32,  
  pm24hrchannelRxOctet               Integer32,
  pm24hrchannelTxOctet               Integer32,
  pm24hrchannelTxFailedOctet         Integer32,
  pm24hrchannelTxFailedPacket        Integer32,
  pm24hrchannelTxRetansFail          Integer32,
  pm24hrchannelTxRetansFailOctet     Integer32,
  pm24hrchannelTxDropedCount         Integer32,
  pm24hrchannelTxMcastOctet          Integer32,
  pm24hrchannelTxMcastPacket         Integer32,
  pm24hrchannelRxMcastPacket         Integer32,
  pm24hrchannelRxMcastOctet          Integer32,
  pm24hrchannelClientsCount          Integer32,
  pm24hrchannelOperStatus            Integer32,
  pm24hrChTimeStamp	                 Integer32
}
pm24hrchannelStatIndex OBJECT-TYPE
SYNTAX Integer32 
MAX-ACCESS read-only
STATUS current
DESCRIPTION
"N/A"
::= { pm24hrChannelStatEntry 1 }

pm24hrChtimeIx OBJECT-TYPE
SYNTAX Integer32 
MAX-ACCESS read-only
STATUS current
DESCRIPTION
"N/A"
::= { pm24hrChannelStatEntry 2 }
      

pm24hrchannelRxPacket OBJECT-TYPE
SYNTAX Integer32 (0..2147483647)
MAX-ACCESS read-only
STATUS current
DESCRIPTION
"N/A"
::= { pm24hrChannelStatEntry 3 }

pm24hrchannelTxPcket OBJECT-TYPE
SYNTAX Integer32 (0..2147483647)
MAX-ACCESS read-only
STATUS current
DESCRIPTION
"N/A"
::= { pm24hrChannelStatEntry 4 }

pm24hrchannelRxOctet OBJECT-TYPE
SYNTAX Integer32 (0..2147483647)
MAX-ACCESS read-only
STATUS current
DESCRIPTION
"N/A"
::= { pm24hrChannelStatEntry 5 }

pm24hrchannelTxOctet OBJECT-TYPE
SYNTAX Integer32 (0..2147483647)
MAX-ACCESS read-only
STATUS current
DESCRIPTION
"N/A"
::= { pm24hrChannelStatEntry 6 }

pm24hrchannelTxFailedOctet OBJECT-TYPE
SYNTAX Integer32 (0..2147483647)
MAX-ACCESS read-only
STATUS current
DESCRIPTION
"N/A"
::= { pm24hrChannelStatEntry 7 }

pm24hrchannelTxFailedPacket OBJECT-TYPE
SYNTAX Integer32 (0..2147483647)
MAX-ACCESS read-only
STATUS current
DESCRIPTION
"N/A"
::= { pm24hrChannelStatEntry 8 }

pm24hrchannelTxRetansFail OBJECT-TYPE
SYNTAX Integer32 (0..2147483647)
MAX-ACCESS read-only
STATUS current
DESCRIPTION
"N/A"
::= { pm24hrChannelStatEntry 9 }

pm24hrchannelTxRetansFailOctet  OBJECT-TYPE
SYNTAX Integer32 (0..2147483647)
MAX-ACCESS read-only
STATUS current
DESCRIPTION
"N/A"
::= { pm24hrChannelStatEntry 10 }

pm24hrchannelTxDropedCount OBJECT-TYPE
SYNTAX Integer32 (0..2147483647)
MAX-ACCESS read-only
STATUS current
DESCRIPTION
"N/A"
::= { pm24hrChannelStatEntry 12 }

pm24hrchannelTxMcastOctet OBJECT-TYPE
SYNTAX Integer32 (0..2147483647)
MAX-ACCESS read-only
STATUS current
DESCRIPTION
"N/A"
::= { pm24hrChannelStatEntry 13 }

pm24hrchannelTxMcastPacket  OBJECT-TYPE
SYNTAX Integer32 (0..2147483647)
MAX-ACCESS read-only
STATUS current
DESCRIPTION
"N/A"
::= { pm24hrChannelStatEntry 14 }

pm24hrchannelRxMcastPacket   OBJECT-TYPE
SYNTAX Integer32 (0..2147483647)
MAX-ACCESS read-only
STATUS current
DESCRIPTION
"N/A"
::= { pm24hrChannelStatEntry 15 }

pm24hrchannelRxMcastOctet  OBJECT-TYPE
SYNTAX Integer32 (0..2147483647)
MAX-ACCESS read-only
STATUS current
DESCRIPTION
"N/A"
::= { pm24hrChannelStatEntry 16 }

pm24hrchannelClientsCount   OBJECT-TYPE
SYNTAX Integer32 (0..2007)
MAX-ACCESS read-only
STATUS current
DESCRIPTION
"N/A"
::= { pm24hrChannelStatEntry 17 }

pm24hrchannelOperStatus OBJECT-TYPE
SYNTAX Integer32 
MAX-ACCESS read-only
STATUS current
DESCRIPTION
"N/A"
::= { pm24hrChannelStatEntry 18 }

pm24hrChTimeStamp OBJECT-TYPE
SYNTAX Integer32 
MAX-ACCESS read-only
STATUS current
DESCRIPTION
"N/A"
::= { pm24hrChannelStatEntry 19 }




-- 24 hr ESS Statistics

pm24hressStat  OBJECT IDENTIFIER  ::= { performance24hr 4 }

pm24hressStatTable OBJECT-TYPE
SYNTAX SEQUENCE OF Pm24hrEssStatEntry
MAX-ACCESS not-accessible
STATUS current
DESCRIPTION
"A table that contains Clients statistics"
::= { pm24hressStat 1 }

pm24hrEssStatEntry OBJECT-TYPE
SYNTAX Pm24hrEssStatEntry
MAX-ACCESS not-accessible
STATUS current
DESCRIPTION
"N/A"
INDEX { pm24hressStatIndex,pm24hrEsstimeIx }
::= { pm24hressStatTable 1 }

Pm24hrEssStatEntry ::=
SEQUENCE {       
  pm24hressStatIndex               Integer32,
  pm24hrEsstimeIx	            	Integer32,  
  pm24hressRxPacket                 Integer32,
  pm24hressTxPacket                 Integer32,
  pm24hressRxOctet                  Integer32,
  pm24hressTxOctet                  Integer32,
  pm24hressTxFailedOctet            Integer32,
  pm24hressTxFailedPacket           Integer32,
  pm24hressTxRetansFail             Integer32,
  pm24hressTxRetansFailOctet        Integer32,
  pm24hressTxMcastOctet             Integer32,
  pm24hressTxMcastPacket            Integer32,
  pm24hressRxMcastPacket            Integer32,
  pm24hressRxMcastOctet             Integer32,
  pm24hressTxDropedCount            Integer32,
  pm24hressClientsCount             Integer32,
  pm24hressAdminStatus              Integer32,
  pm24hressOperStatus               Integer32,
  pm24hressConfigIndex              Integer32,
  pm24hrEssTimeStamp                Integer32
}     
pm24hressStatIndex OBJECT-TYPE
SYNTAX Integer32 
MAX-ACCESS read-only
STATUS current
DESCRIPTION
"N/A"
::= { pm24hrEssStatEntry 1 }

pm24hrEsstimeIx OBJECT-TYPE
SYNTAX Integer32 
MAX-ACCESS read-only
STATUS current
DESCRIPTION
"N/A"
::= { pm24hrEssStatEntry 2 }
            
pm24hressRxPacket OBJECT-TYPE
SYNTAX Integer32 (0..2147483647)
MAX-ACCESS read-only
STATUS current
DESCRIPTION
"N/A"
::= { pm24hrEssStatEntry 3 }
 
pm24hressTxPacket OBJECT-TYPE
SYNTAX Integer32 (0..2147483647)
MAX-ACCESS read-only
STATUS current
DESCRIPTION
"N/A"
::= { pm24hrEssStatEntry 4 }
 
pm24hressRxOctet OBJECT-TYPE
SYNTAX Integer32 (0..2147483647)
MAX-ACCESS read-only
STATUS current
DESCRIPTION
"N/A"
::= { pm24hrEssStatEntry 5 }
 
pm24hressTxOctet OBJECT-TYPE
SYNTAX Integer32 (0..2147483647)
MAX-ACCESS read-only
STATUS current
DESCRIPTION
"N/A"
::= { pm24hrEssStatEntry 6 }
 
pm24hressTxFailedOctet OBJECT-TYPE
SYNTAX Integer32 (0..2147483647)
MAX-ACCESS read-only
STATUS current
DESCRIPTION
"N/A"
::= { pm24hrEssStatEntry 7 }
 
pm24hressTxFailedPacket OBJECT-TYPE
SYNTAX Integer32 (0..2147483647)
MAX-ACCESS read-only
STATUS current
DESCRIPTION
"N/A"
::= { pm24hrEssStatEntry 8 }
 
pm24hressTxRetansFail OBJECT-TYPE
SYNTAX Integer32 (0..2147483647)
MAX-ACCESS read-only
STATUS current
DESCRIPTION
"N/A"
::= { pm24hrEssStatEntry 9 }
 
pm24hressTxRetansFailOctet OBJECT-TYPE
SYNTAX Integer32 (0..2147483647)
MAX-ACCESS read-only
STATUS current
DESCRIPTION
"N/A"
::= { pm24hrEssStatEntry 10 }
 
 
pm24hressTxMcastOctet OBJECT-TYPE
SYNTAX Integer32 (0..2147483647)
MAX-ACCESS read-only
STATUS current
DESCRIPTION
"N/A"
::= { pm24hrEssStatEntry 11 }
 
pm24hressTxMcastPacket OBJECT-TYPE
SYNTAX Integer32 (0..2147483647)
MAX-ACCESS read-only
STATUS current
DESCRIPTION
"N/A"
::= { pm24hrEssStatEntry 12 }
 
pm24hressRxMcastPacket OBJECT-TYPE
SYNTAX Integer32 (0..2147483647)
MAX-ACCESS read-only
STATUS current
DESCRIPTION
"N/A"
::= { pm24hrEssStatEntry 13 }
        
pm24hressRxMcastOctet OBJECT-TYPE
SYNTAX Integer32 (0..2147483647)
MAX-ACCESS read-only
STATUS current
DESCRIPTION              
"N/A"
::= { pm24hrEssStatEntry 14 }
        
pm24hressTxDropedCount OBJECT-TYPE
SYNTAX Integer32 (0..2147483647)
MAX-ACCESS read-only
STATUS current
DESCRIPTION
"N/A"
::= { pm24hrEssStatEntry 15 }
        
pm24hressClientsCount OBJECT-TYPE
SYNTAX Integer32 (0..2007)
MAX-ACCESS read-only
STATUS current
DESCRIPTION
"N/A"
::= { pm24hrEssStatEntry 16 }
        
pm24hressAdminStatus  OBJECT-TYPE
SYNTAX Integer32 
MAX-ACCESS read-only
STATUS current
DESCRIPTION
"N/A"
::= { pm24hrEssStatEntry 17 }
         
pm24hressOperStatus OBJECT-TYPE
SYNTAX Integer32 
MAX-ACCESS read-only
STATUS current
DESCRIPTION
"N/A"
::= { pm24hrEssStatEntry 18 }
   
pm24hressConfigIndex   OBJECT-TYPE
SYNTAX Integer32 
MAX-ACCESS read-only
STATUS current
DESCRIPTION
"N/A"
::= { pm24hrEssStatEntry 20 }   
     
pm24hrEssTimeStamp OBJECT-TYPE
SYNTAX Integer32 
MAX-ACCESS read-only
STATUS current
DESCRIPTION
"The Index of this ESS Statistics in the configuration file "
::= { pm24hrEssStatEntry 21 }

-- 24hr Switch Statistics

pm24hrswitchStat  OBJECT IDENTIFIER  ::= { performance24hr 5 } 

pm24hrswitchStatTable OBJECT-TYPE
SYNTAX SEQUENCE OF Pm24hrSwitchStatEntry
MAX-ACCESS not-accessible
STATUS current
DESCRIPTION
"A table that contains Switch global statistics"
::= { pm24hrswitchStat 1 }

pm24hrSwitchStatEntry OBJECT-TYPE
SYNTAX Pm24hrSwitchStatEntry
MAX-ACCESS not-accessible
STATUS current
DESCRIPTION
"N/A"
INDEX { pm24hrSwtimeIx }
::= { pm24hrswitchStatTable 1 }

-- INDEX { pm24hrswitchStatIndex, pm24hrSwtimeIx }


Pm24hrSwitchStatEntry ::=
SEQUENCE {
  pm24hrswitchStatIndex               Integer32,
  pm24hrSwtimeIx	               	Integer32,
  pm24hrRxPacket			Integer32,
  pm24hrTxPacket 			Integer32,
  pm24hrRxOctet 			Integer32,
  pm24hrTxOctet 			Integer32,
  pm24hrTxFailedOctet 			Integer32,
  pm24hrTxFailedPacket 			Integer32,
  pm24hrTxRetansFail 			Integer32,
  pm24hrTxRetansFailOctet 		Integer32,
  pm24hrRxMcastOctet 			Integer32,
  pm24hrRxMcastPacket 			Integer32,
  pm24hrTxMcastPacket 			Integer32,
  pm24hrTxMcastOctet 			Integer32,
  pm24hrTxDropedCount 			Integer32,
  pm24hrClientsCount 			Integer32,
  pm24hrRtsSucces 			Integer32,
  pm24hrRtsFailed 			Integer32,
  pm24hrRxLanPacket			Integer32,
  pm24hrTxLanPacket			Integer32,
  pm24hrRxLanOctet			Integer32,
  pm24hrTxLanOctet			Integer32,
  pm24hrRxLanMcastPacket		Integer32,
  pm24hrTxLanError			Integer32,
  pm24hrTxLanDropped 			Integer32,
  pm24hrRxLanDropped 			Integer32,
  pm24hrTxLanCollission 		Integer32,
  pm24hrRxLanFrame 			Integer32,
  pm24hrTxLanCarrier 			Integer32,
  pm24hrSwTimeStamp		        Integer32
}
m24hrswitchStatIndex OBJECT-TYPE
SYNTAX Integer32
MAX-ACCESS read-only
STATUS current
DESCRIPTION
"N/A"
::= { pm24hrSwitchStatEntry 1 }


pm24hrSwtimeIx	OBJECT-TYPE
SYNTAX Integer32
MAX-ACCESS read-only
STATUS current
DESCRIPTION
"N/A"
::= { pm24hrSwitchStatEntry 2 }

pm24hrRxPacket	OBJECT-TYPE
SYNTAX Integer32 (0..2147483647)
MAX-ACCESS read-only
STATUS current
DESCRIPTION
"N/A"
::= { pm24hrSwitchStatEntry 3 }

pm24hrTxPacket	 OBJECT-TYPE
SYNTAX Integer32 (0..2147483647)
MAX-ACCESS read-only
STATUS current
DESCRIPTION
"N/A"
::= { pm24hrSwitchStatEntry 4 }
   			
pm24hrRxOctet	 OBJECT-TYPE
SYNTAX Integer32 (0..2147483647)
MAX-ACCESS read-only
STATUS current
DESCRIPTION
"N/A"
::= { pm24hrSwitchStatEntry 5 }

pm24hrTxOctet OBJECT-TYPE
SYNTAX Integer32 (0..2147483647)
MAX-ACCESS read-only
STATUS current
DESCRIPTION
"N/A"
::= { pm24hrSwitchStatEntry 6 }
		
pm24hrTxFailedOctet OBJECT-TYPE
SYNTAX Integer32 (0..2147483647)
MAX-ACCESS read-only
STATUS current
DESCRIPTION
"N/A"
::= { pm24hrSwitchStatEntry 7 }
   			
pm24hrTxFailedPacket OBJECT-TYPE
SYNTAX Integer32 (0..2147483647)
MAX-ACCESS read-only
STATUS current
DESCRIPTION
"N/A"
::= { pm24hrSwitchStatEntry 8 }


pm24hrTxRetansFail OBJECT-TYPE
SYNTAX Integer32 (0..2147483647)
MAX-ACCESS read-only
STATUS current
DESCRIPTION
"N/A"
::= { pm24hrSwitchStatEntry 9 }
   			

pm24hrTxRetansFailOctet OBJECT-TYPE
SYNTAX Integer32 (0..2147483647)
MAX-ACCESS read-only
STATUS current
DESCRIPTION
"N/A"
::= { pm24hrSwitchStatEntry 10 }
	

pm24hrRxMcastOctet  OBJECT-TYPE
SYNTAX Integer32 (0..2147483647)
MAX-ACCESS read-only
STATUS current
DESCRIPTION
"N/A"
::= { pm24hrSwitchStatEntry 11 }

pm24hrRxMcastPacket  OBJECT-TYPE
SYNTAX Integer32 (0..2147483647)
MAX-ACCESS read-only
STATUS current
DESCRIPTION
"N/A"
::= { pm24hrSwitchStatEntry 12 }

pm24hrTxMcastPacket  OBJECT-TYPE
SYNTAX Integer32 (0..2147483647)
MAX-ACCESS read-only
STATUS current
DESCRIPTION
"N/A"
::= { pm24hrSwitchStatEntry 13 }

pm24hrTxMcastOctet  OBJECT-TYPE
SYNTAX Integer32 (0..2147483647)
MAX-ACCESS read-only
STATUS current
DESCRIPTION
"N/A"
::= { pm24hrSwitchStatEntry 14 }

pm24hrTxDropedCount  OBJECT-TYPE
SYNTAX Integer32 (0..2147483647)
MAX-ACCESS read-only
STATUS current
DESCRIPTION
"N/A"
::= { pm24hrSwitchStatEntry 15 }


pm24hrClientsCount  OBJECT-TYPE
SYNTAX Integer32 (0..2007)
MAX-ACCESS read-only
STATUS current
DESCRIPTION
"N/A"
::= { pm24hrSwitchStatEntry 16 }

pm24hrRtsSucces  OBJECT-TYPE
SYNTAX Integer32 (0..2147483647)
MAX-ACCESS read-only
STATUS current
DESCRIPTION
"N/A"
::= { pm24hrSwitchStatEntry 17 }

pm24hrRtsFailed  OBJECT-TYPE
SYNTAX Integer32 (0..2147483647)
MAX-ACCESS read-only
STATUS current
DESCRIPTION
"N/A"
::= { pm24hrSwitchStatEntry 18 }

pm24hrRxLanPacket  OBJECT-TYPE
SYNTAX Integer32 (0..2147483647)
MAX-ACCESS read-only
STATUS current
DESCRIPTION
"N/A"
::= { pm24hrSwitchStatEntry 19 }

pm24hrTxLanPacket  OBJECT-TYPE
SYNTAX Integer32 (0..2147483647)
MAX-ACCESS read-only
STATUS current
DESCRIPTION
"N/A"
::= { pm24hrSwitchStatEntry 20 }

pm24hrRxLanOctet  OBJECT-TYPE
SYNTAX Integer32 (0..2147483647)
MAX-ACCESS read-only
STATUS current
DESCRIPTION
"N/A"
::= { pm24hrSwitchStatEntry 21 }

pm24hrTxLanOctet  OBJECT-TYPE
SYNTAX Integer32 (0..2147483647)
MAX-ACCESS read-only 
STATUS current
DESCRIPTION
"N/A"
::= { pm24hrSwitchStatEntry 22 }

pm24hrRxLanMcastPacket  OBJECT-TYPE
SYNTAX Integer32 (0..2147483647)
MAX-ACCESS read-only
STATUS current
DESCRIPTION
"N/A"
::= { pm24hrSwitchStatEntry 23 }


pm24hrTxLanError  OBJECT-TYPE
SYNTAX Integer32 (0..2147483647)
MAX-ACCESS read-only
STATUS current
DESCRIPTION
"N/A"
::= { pm24hrSwitchStatEntry 24 }

pm24hrTxLanDropped  OBJECT-TYPE
SYNTAX Integer32 (0..2147483647)
MAX-ACCESS read-only
STATUS current
DESCRIPTION
"N/A"
::= { pm24hrSwitchStatEntry 25 }

pm24hrRxLanDropped  OBJECT-TYPE
SYNTAX Integer32 (0..2147483647)
MAX-ACCESS read-only
STATUS current
DESCRIPTION
"N/A"
::= { pm24hrSwitchStatEntry 26 }

pm24hrTxLanCollission  OBJECT-TYPE
SYNTAX Integer32 (0..2147483647)
MAX-ACCESS read-only
STATUS current
DESCRIPTION
"N/A"
::= { pm24hrSwitchStatEntry 27 }

pm24hrRxLanFrame  OBJECT-TYPE
SYNTAX Integer32 (0..2147483647)
MAX-ACCESS read-only
STATUS current
DESCRIPTION
"N/A"
::= { pm24hrSwitchStatEntry 28 }

pm24hrTxLanCarrier  OBJECT-TYPE
SYNTAX Integer32 (0..2147483647)
MAX-ACCESS read-only
STATUS current
DESCRIPTION
"N/A"
::= { pm24hrSwitchStatEntry 29 }

pm24hrSwTimeStamp  OBJECT-TYPE
SYNTAX Integer32 
MAX-ACCESS read-only
STATUS current
DESCRIPTION
"N/A"
::= { pm24hrSwitchStatEntry 30 }



END
