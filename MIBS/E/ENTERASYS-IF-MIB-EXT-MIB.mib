ENTERASYS-IF-MIB-EXT-MIB DEFINITIONS ::= BEGIN

--  enterasys-if-mib-ext-mib.txt
--
--  Part Number:
--
--

--  This module provides authoritative definitions for Enterasys 
--  Networks' Interface MIB Extensions functionality.

--
--  This module will be extended, as needed.

--  Extreme Networks reserves the right to make changes in this
--  specification and other information contained in this document
--  without prior notice.  The reader should consult Extreme Networks
--  to determine whether any such changes have been made.
--
--  In no event shall Extreme Networks be liable for any incidental,
--  indirect, special, or consequential damages whatsoever (including
--  but not limited to lost profits) arising out of or related to this
--  document or the information contained in it, even if Extreme
--  Networks has been advised of, known, or should have known, the
--  possibility of such damages.
--
--  Extreme Networks grants vendors, end-users, and other interested
--  parties a non-exclusive license to use this Specification in 
--  connection with the management of Extreme Networks products.

--  Copyright (2005-2013) Enterasys Networks, Inc.
--  Copyright 2015 Extreme Networks, Inc.

IMPORTS
    MODULE-IDENTITY, OBJECT-TYPE
        FROM SNMPv2-SMI
    TEXTUAL-CONVENTION
        FROM SNMPv2-TC
    MODULE-COMPLIANCE, OBJECT-GROUP
        FROM SNMPv2-CONF
    ifEntry
        FROM IF-MIB
    EnabledStatus
        FROM P-BRIDGE-MIB
    etsysModules
        FROM ENTERASYS-MIB-NAMES;

etsysIfMibExtMIB MODULE-IDENTITY
    LAST-UPDATED "201504141239Z"  -- Tue Apr 14 12:39 UTC 2015
    ORGANIZATION "Extreme Networks, Inc."
    CONTACT-INFO
        "Postal:  Extreme Networks, Inc.
                  145 Rio Robles
                  San Jose, CA 95134 USA

         Phone:   +1 408 579-2800
         E-mail:  support@extremenetworks.com
         WWW:     http://www.extremenetworks.com"
   
    DESCRIPTION
        "This MIB module defines a portion of the SNMP MIB under
         the Enterasys Networks enterprise OID that provide 
         extensions to the industry standard IF-MIB."

    REVISION    "201504141239Z"  -- Tue Apr 14 12:39 UTC 2015
    DESCRIPTION
        "Addition of MACSEC cause to the EtsysIfOperStatusCauses 
         textual convention."

    REVISION    "201407241322Z"  -- Thu Jul 24 13:22 UTC 2014
    DESCRIPTION
        "Addition of Priority Flow Control cause to the 
         EtsysIfOperStatusCauses textual convention."

    REVISION    "201304121314Z"  -- Fri Apr 12 13:14 UTC 2013
    DESCRIPTION
        "Update CONTACT-INFO clause."
   
    REVISION    "201302111814Z"  -- Mon Feb 11 18:14 UTC 2013
    DESCRIPTION
        "Addition of Transmit Queue Monitor cause to the 
         EtsysIfOperStatusCauses textual convention."

    REVISION    "201202022008Z"  -- Thu Feb  2 20:08 UTC 2012
    DESCRIPTION 
        "Addition of Ethernet OAM ULD cause to the EtsysIfOperStatusCauses
         textual convention."

    REVISION    "201112071558Z"  -- Wed Dec  7 15:58 UTC 2011
    DESCRIPTION 
        "Addition of Link-state cause to the EtsysIfOperStatusCauses
         textual convention."

    REVISION    "201110251948Z"  -- Tue Oct 25 19:48 UTC 2011
    DESCRIPTION 
        "Addition of Chassis Bonding cause to the EtsysIfOperStatusCauses
         textual convention."

    REVISION    "201106081212Z"  -- Wed Jun  8 12:12 UTC 2011
    DESCRIPTION 
        "Addition of MAC Locking cause to the EtsysIfOperStatusCauses
         textual convention."

    REVISION    "201105121415Z"  -- Thu May 12 16:15:05 GMT 2011
    DESCRIPTION 
        "Addition of Ethernet OAM and Ethernet OAM Loopback
         causes to the EtsysIfOperStatusCauses textual convention."
        
    REVISION    "200501132135Z"  -- Thu Jan 13 21:35 GMT 2005
    DESCRIPTION 
        "The initial version of this MIB module."
    ::= { etsysModules 57 } 


-- Textual Conventions

EtsysIfOperStatusCauses ::= TEXTUAL-CONVENTION
    STATUS       current
    DESCRIPTION
        "This convention specifies the variety of functionalities that
         may cause an interface's ifOperStatus to be have a value other
         than up(1).  A set bit indicates that the associated cause is 
         influencing the interface's current ifOperStatus.

         adminStatus(0)
          - The ifAdminStatus for the interface is not up(1).

         linkLoss(1) 
          - The interface has physically lost link with its partner.

         linkFlap(2) 
          - The interface has been brought down by the Link Flap
            feature as defined by etsysLinkFlapMIB.

         self(3)     
          - The interface has brought itself down.  

         initialization(4)
          - The system or interface is still in the process of
            initializing itself.

         flowLimiting(5)
          - The interface has been brought down by the Flow Limiting 
            feature as defined by etsysFlowLimitingMIB.

         policy(6)
          - The interface has been brought down by the Policy feature
            as defined by etsysPolicyProfileMIB.

         classOfService(7)
          - The interface has been brought down by the rate limiting
            feature defined by etsysCosMIB.

         ieee8021x(8)
          - The interface has been made dormant awaiting successful 
            authentication by 802.1X.

         ieee8023lag(9)
          - The interface has been made dormant as a result of being
            an underlying physical port in a Link Aggregation.
            
         enetOam(10)
          - The interface has been brought down by the Ethernet OAM
            feature as defined by etsysEthOamExtMIB.
            
         enetOamLb(11)
          - The interface has been brought down by the Ethernet OAM
            loopback feature as defined by dot3OamMIB.

         macLock(12)
          - The interface has been brought down by the MAC Lock
            feature as defined in etsysMACLockingMIB.
 
         chassisBonding(13)
          - The interface has been brought down by the Chassis Bonding
            feature as defined in etsysVirtualSwitchBondingMIB.

         linkState(14)
          - The interface has been brought down by the Link-state
            application as defined in etsysLinkstateMIB.
            
         enetOamUld(15)
          - The interface has been brought down by the Ethernet OAM
            Unidirectional Link Detection (ULD) feature as defined by
            etsysEthOamExtMIB.
            
         txqMonitor(16)
          - The interface has been brought down by the Transmit Queue
            Monitor feature as defined in etsysTxqMonitorMIB.

         priorityFlowControl(17)
          - The interface has been brought down by the Priority Flow
            Control feature as defined in ieee8021PFCMib as it
            undergoes temporary buffer changes.

         macSec(18)
          - The interface has been brought down by the MACsec
            feature as defined by IEEE802.1X-2010 port based
            Network Access Control."

            
    REFERENCE
        "RFC 2863, 'The Interfaces Group MIB'
         ENTERASYS-LINK-FLAP-MIB
         ENTERASYS-FLOW-LIMITING-MIB
         ENTERASYS-POLICY-PROFILE-MIB
         ENTERASYS-CLASS-OF-SERVICE-MIB
         ENTERASYS-ETH-OAM-EXT-MIB
         ENTERASYS-MAC-LOCKING-MIB
         IEEE Std. 802.1X-2001
         IEEE Std. 802.3-2002
         ENTERASYS-VIRTUAL-SWITCH-BONDING-MIB
         ENTERASYS-LINKSTATE-MIB
         ENTERASYS-ETH-OAM-EXT-MIB
         ENTERASYS-TRANSMIT-QUEUE-MONITOR-MIB
         IEEE Std. 802.1Qbb-2011
         IEEE Std. 802.1X-2010"
    SYNTAX       BITS {
                   adminStatus(0),
                   linkLoss(1),
                   linkFlap(2),
                   self(3),
                   initialization(4),
                   flowLimiting(5),
                   policy(6),
                   classOfService(7),
                   ieee8021x(8),
                   ieee8023lag(9),
                   enetOam(10),
                   enetOamLb(11),
                   macLock(12),
                   chassisBonding(13),
                   linkState(14),
                   enetOamUld(15),
                   txqMonitor(16),
                   priorityFlowControl(17),
                   macSec(18)
                 }


-- -------------------------------------------------------------
-- MIB Objects
-- -------------------------------------------------------------

etsysIfMibExtObjects      OBJECT IDENTIFIER 
                           ::= { etsysIfMibExtMIB 1 }

etsysIfMibExtSystem       OBJECT IDENTIFIER 
                           ::= { etsysIfMibExtObjects 1 }

etsysIfMibExtInterface    OBJECT IDENTIFIER 
                           ::= { etsysIfMibExtObjects 2 }


-- -------------------------------------------------------------
-- The Interface MIB Extension System Group
-- -------------------------------------------------------------

etsysIfOperStateLinkChange OBJECT-TYPE
    SYNTAX       EnabledStatus
    MAX-ACCESS   read-write
    STATUS       current
    DESCRIPTION
        "This object controls the system wide ability to manipulate
         the physical link state of an interface when the interface's
         ifOperStatus transitions into or out of the down(2) state.
         A value of enabled(1) will cause an interface to drop physical
         link when its ifOperStatus transitions to down(2).  If the 
         interface would transition out of the down(2) state, assuming
         it did have link, then physical link will be restored to the 
         interface.  A value of disabled(2) will cause an interface to 
         not alter its physical link regardless of the value of 
         ifOperStatus.  This object only affects those interfaces which
         have a concept of physical link."
    DEFVAL      { disabled }
    ::= { etsysIfMibExtSystem 1 }


-- -------------------------------------------------------------
-- The Interface MIB Extension Interface Group
-- -------------------------------------------------------------

etsysInterfaceExtTable OBJECT-TYPE
    SYNTAX       SEQUENCE OF EtsysInterfaceExtEntry
    MAX-ACCESS   not-accessible
    STATUS       current
    DESCRIPTION
        "A table of per interface information that extends the base
         ifTable defined in RFC2863."
    ::= {  etsysIfMibExtInterface 1 }

etsysInterfaceExtEntry OBJECT-TYPE
    SYNTAX       EtsysInterfaceExtEntry
    MAX-ACCESS   not-accessible
    STATUS       current
    DESCRIPTION
        "An entry containing per interface information."
    AUGMENTS  { ifEntry }
    ::= { etsysInterfaceExtTable 1 }

EtsysInterfaceExtEntry ::=
    SEQUENCE { 
        etsysIfOperStatusCause
            EtsysIfOperStatusCauses
    }

etsysIfOperStatusCause OBJECT-TYPE
    SYNTAX       EtsysIfOperStatusCauses
    MAX-ACCESS   read-only
    STATUS       current
    DESCRIPTION
        "This object indicates the various features that could
         cause the ifOperStatus of an interface to not be up(1)."
    ::= { etsysInterfaceExtEntry 1 }


-- -------------------------------------------------------------
-- Conformance Information
-- -------------------------------------------------------------

etsysIfMibExtConformance OBJECT IDENTIFIER
    ::= { etsysIfMibExtMIB 2 }

etsysIfMibExtGroups      OBJECT IDENTIFIER
    ::= { etsysIfMibExtConformance 1 }

etsysIfMibExtCompliances OBJECT IDENTIFIER
    ::= { etsysIfMibExtConformance 2 }


-- -------------------------------------------------------------
-- Units of conformance
-- -------------------------------------------------------------

etsysIfMibExtOperLinkGroup OBJECT-GROUP
    OBJECTS { etsysIfOperStateLinkChange }
    STATUS     current
    DESCRIPTION
        "The group that controls physical link manipulation as a result
         of ifOperStatus changes."
    ::= { etsysIfMibExtGroups 1 }

etsysIfMibExtOperStatusGroup OBJECT-GROUP
    OBJECTS { etsysIfOperStatusCause }
    STATUS     current
    DESCRIPTION
        "The group that provides the cause of the current ifOperStatus
         value for a given interface."
    ::= { etsysIfMibExtGroups 2 }


-- -------------------------------------------------------------
-- Compliance statements
-- -------------------------------------------------------------

etsysIfMibExtCompliance MODULE-COMPLIANCE
    STATUS     current
    DESCRIPTION
        "The compliance statement for devices that support IF-MIB
         extensions."

    MODULE
        GROUP       etsysIfMibExtOperLinkGroup
        DESCRIPTION
            "This group is mandatory for all devices that support
             manipulating the physical link state of an interface
             in response to ifOperStatus changes."

        GROUP       etsysIfMibExtOperStatusGroup
        DESCRIPTION
            "This group is mandatory for all devices that support
             reporting of the underlying cause for the current
             ifOperStatus value associated with an interface."
    ::= { etsysIfMibExtCompliances 1 }

END
