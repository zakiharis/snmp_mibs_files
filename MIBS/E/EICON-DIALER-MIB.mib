-- #############################################################################
--		DIALER
--  History :
--  modified by Cazimir, in order to accomodate ISDN, 15/06/1994
--  direct dialer status changed to adapt to new tech. 68302. DIRECTA.
-- #############################################################################


EICON-DIALER-MIB DEFINITIONS ::= BEGIN

IMPORTS
	TimeTicks,
	enterprises
		FROM RFC1155-SMI
	OBJECT-TYPE
		FROM RFC-1212
	DisplayString
		FROM RFC1213-MIB;

eicon		OBJECT IDENTIFIER  ::= { enterprises 434 }
management	OBJECT IDENTIFIER  ::= { eicon 2 }
mibv2		OBJECT IDENTIFIER  ::= { management 2 }
module		OBJECT IDENTIFIER  ::= { mibv2 4 }

--	Local definitions

PortRef	::= INTEGER (1..48)	-- Port reference on the server.

ActionState ::= INTEGER {
	done (1),
	failed (2),
	in-progress (3)
	}

DataEncoding ::= INTEGER {
		nrz (1),
		nrzi (2),
		fm0 (3),
		fm1 (4)
	   }

ClockType ::= INTEGER {
		external (1),
		internal (2),
		ext-dpll (3),
		int-dpll (4)
	}
	
OnOff ::= INTEGER {
		on (1),
		off (2)
	}

FalseTrue ::= INTEGER {
		false (1),
		true (2)
	}

DisEnable ::= INTEGER {
		disable (1),
		enable (2)
	}

PrimBitRate ::= INTEGER {
		speed1200 (1),
		speed2400 (2),
		speed4800 (3),
		speed7200 (4),
		speed9600 (5),
		speed12000 (6),
		speed14400 (7),
		not-supported (8)
	}

PrimCfg ::= INTEGER {
		v22bis  (1),
		v32	(2),
		v32tcm  (3),
		v32bis  (4),
		not-supported (5)
	}

IsdnSpidStatus ::= INTEGER  {
		uninit (1),
		init (2),
		blocked (3),
		illegal (4)
	}

IsdnDnType ::= INTEGER {
		unknown (1),
		international (2),
		national (3),
		net-specific (4),
		subscriber (5),
		abbreviated (6),
		illegal (7)
	}

IsdnDnPlan ::= INTEGER {
		unknown (1),
		isdn-numbering (2),
		data-numbering (3),
		private-net (4),
		telex-numbering (5),
		nat-numbering (6),
		illegal (7)
	}

IsdnSubType ::= INTEGER {
		nsap (1),
		user-specified (2),
		osi (3),
		illegal (4)
	}

IsdnTnsNetId ::= INTEGER {
		user-specified (1),
		national (2),
		international (3),
		illegal (4)
	}

IsdnTnsIdPlan ::= INTEGER {
		unknown (1),
		interlata (2),
		data (3),
		illegal (4)
	}

IsdnCallType ::= INTEGER {
		circuit-switched (1),
		packet-switched (2),
		nailed-packet (3),
		circuit-spv (4),		-- added 4-9, 16/06/94
		fax-3 (5),
		fax-4 (6),
		btx (7),
		teletex (8),
		videotex (9),
		illegal (10)
	}

IsdnCallSpeed ::= INTEGER {
		speed-56k (1),
		speed-64k (2),
		speed-illegal (3)
	}

IsdnBChannels ::= INTEGER {
		b1-channel (1),
		b2-channel (2),
		illegal (3)
	}


IsdnAnsEnable ::= INTEGER {
		disabled (1),
		enabled (2),
		enabled-illegal (3)
	}


IsdnScrStatus ::= INTEGER {
		disabled (1),
		enabled (2),
		illegal (3)
	}

IsdnCallOpt ::= INTEGER {
		opt (1),
		option (2),
		call-opt (3)
	}

IsdnStoDefined ::= INTEGER {
		stored (1)
	}

IsdnTeiStatus ::= INTEGER {
		unassigned (1),
		outstanding (2),
		assigned (3),
		illegal (4)
	}

IsdnL2State	::= INTEGER {
		null-state(1),
		tei-unassigned (2),
		assign-awaiting-tei (3),
		establish-awaiting-tei (4),
		tei-assigned (5),
		awaiting-established (6),
		awaiting-release (7),
		mutiple-frame-established (8),
		timer-recovery	(9),
		illegal (10)
	}

IsdnL3State ::= INTEGER {
		null-state (1),
		call-init (2),
		overlap-sending (3),
		out-call-proc (4),
		call-delivered (5),
		undefined-state-5 (6),
		call-present (7),
		call-received (8),
		connect-request (9),
		in-call-proc (10),
		call-active (11),
		disconnect-request (12),
		disconnect-ind (13),
		undefined-state-13 (14),
		call-passive (15),
		suspend-request (16),
		undefined-state-16 (17),
		resume-request (18),
		undefined-state-18 (19),
		release-request (20),
		register-request (21),
		cancel-request (22),
		undefined-state-22 (23),
		undefined-state-23 (24),
		undefined-state-24 (25),
		overlap-receive (26),
		idle-state (27),
		establish-wait (28),
		asai-tr1-state (29),
		u10-hold-request (30),
		u10-transfer-request (31),
		u10-conference-request (32),
		u10-reconnect-request (33),
		u10-awaiting-disc (34),
		u10-call-on-hold (35),
		broadcast-state (36),
		illegal (37)
	}	

IsdnP3State ::= INTEGER {
		closed (1),
		opening (2),
		opened (3),
		tei-establishment (4),
		sw-activation (5),
		activated (6),
		deactivated (7),
		closing (8),
		illegal (9)
	}

IsdnActState ::= INTEGER {
		deactivated (1),
		activating (2),
		active (3),
		call-failed (4),
		activ-failed (5),
		illegal (6)
	}

IsdnNI1BCcState ::= INTEGER {
		null-state (1),
		idle (2),
		ringing (3),
		connected (4),
		dialing (5),
		lockout (6),
		offhook-releasing (7),
		onhook-releasing (8),
		originate (9),
		routing (10),
		call-queued (11),
		illegal (12)
	} 	

IsdnTR6BCcState ::= INTEGER {
		null-state (1),
		idle (2),
		ringing (3),
		connecting (4),
		connected (5),
		lockout (6),
		offhook-releasing (7),
		onhook-releasing (8),
		originate (9),
		routing (10),
		call-queued (11),
		illegal (12)
	}

IsdnVN3BCcState ::= INTEGER {
		null-state (1),
		idle (2),
		ringing (3),
		connecting (4),
		connected (5),
		lockout (6),
		offhook-releasing (7),
		onhook-releasing (8),
		originate (9),
		routing (10),
		call-queued (11),
		illegal (12)
	}

IsdnNET3BCcState ::= INTEGER {
		null-state (1),
		idle (2),
		ringing (3),
		connecting (4),
		connected (5),
		lockout (6),
		offhook-releasing (7),
		onhook-releasing (8),
		originate (9),
		routingout (10),
		call-queued (11),
		bell-releasing (12),
		illegal (13)
	}

IsdnTPHBCcState	::= INTEGER {
		null-state (1),
		idle (2),
		ringing (3),
		connected (4),
		dialing (5),
		lockout (6),
		offhook-releasing (7),
		onhook-releasing (8),
		originate (9),
		routing (10),
		call-queued (11),
		illegal (12)
	}
--		 		
-- IsdnEUROBCcState ::= INTEGER {
--		null-state (1),
--		idle (2),
--		ringing (3),
--		connecting (4),
--		connected (5),
--		lockout (6),
--		offhook-releasing (7),
--		onhook-releasing (8),
--		originate (9),
--		routing (10),
--		call-queued (11)
--	}
--
--	Title

dialer	OBJECT IDENTIFIER ::= { module 16 }

--	The DIALER MIB is composed of  the following tables:
--      dialerInfoTable              General status information for each port.
--	dialerDirectInfoTable	     Status information for Direct dialer.
--	dialerDirectRs232InfoTable   Status information for Direct dialer with
--   				     physical interface type RS232.
--	dialerDirectInfoTable	     Status information for Direct dialer with
--				     physical interface type X21.
--	dialerV25bisInfoTable	     Status information for V25BIS dialer.
--	dialerAtCmdInfoTable	     Status information for AT-CMD dialer.
--	dialerV22BisDnaInfoTable     Status information for V22BISDNA dialer.
--	dialerV22BisImcInfoTable     Status information for V22BISIMC dialer.
--	dialerV32BisInfoTable	     Status information for V32BIS dialer.
--      dialerControlTable           Control objects for each port.
--      dialerIsdnStatusTable
--	dialerIsdnNI1BChannelTable
--	dialerIsdnNI1DChannelTable
--	dialerIsdnTr6BChannelTable
--      dialerIsdnVN3BChannelTable
--      dialerIsdnVN3DChannelTable
--      dialerIsdnNET3BChannelTable
--      dialerIsdnTPHBChannelTable
--      dialerIsdnTPHDChannelTable
--      dialerIsdnEUROBChannelTable
--      dialerIsdnEURODChannelTable

-- ****************************************************************************
--		Dialer General Status Info
-- ****************************************************************************

dialerInfoTable		OBJECT-TYPE
	SYNTAX	SEQUENCE OF DialerInfoEntry 
	ACCESS	not-accessible
	STATUS	mandatory
	DESCRIPTION	
		"General Information Table for dailer."
	::= { dialer 1 }

dialerInfoEntry		OBJECT-TYPE
	SYNTAX	DialerInfoEntry
	ACCESS	not-accessible
	STATUS	mandatory
	DESCRIPTION	
		"The set of dialer configuration attributes for one port."
	INDEX		{ dialerInfoPortRef }
	::= { dialerInfoTable 1 }

DialerInfoEntry ::= SEQUENCE {
	dialerInfoPortRef
		PortRef,
	dialerInfoType
		INTEGER,
	dialerInfoTimeStart
		TimeTicks,
	dialerInfoTimeConnect	
		TimeTicks,
	dialerInfoLineSpeed	
		INTEGER,
	dialerInfoDataEncoding
		DataEncoding,
	dialerInfoClockType
		ClockType
	}

dialerInfoPortRef	OBJECT-TYPE
	SYNTAX	PortRef
	ACCESS	read-only 
	STATUS	mandatory
	DESCRIPTION	
		"The id of the port, equal to portIndex from the port group. 
	It identifies the port to which the configuration parameters apply."
	::= { dialerInfoEntry 1 }

dialerInfoType	OBJECT-TYPE
	SYNTAX	INTEGER {
		direct (1),
		v25bis (2),
		v22bis (3),
		at-cmd (4),
		isdn-stat (5),
		v32bis (6),
		none (7),
		other (8)
		}
	ACCESS	read-only 
	STATUS	mandatory
	DESCRIPTION	
		" Type of interface connecting the gateway to local or
	remote host computers."
	::= { dialerInfoEntry 2 }

dialerInfoTimeStart	OBJECT-TYPE
	SYNTAX	TimeTicks
	ACCESS	read-only 
	STATUS	mandatory
	DESCRIPTION	
		"The time elapsed since the dialer was statrted."
	::= { dialerInfoEntry 3 }

dialerInfoTimeConnect		OBJECT-TYPE
	SYNTAX	TimeTicks
	ACCESS	read-only 
	STATUS	mandatory
	DESCRIPTION	
		"The time elapsed since the dialer established the current
	connection."
	::= { dialerInfoEntry 4 }

dialerInfoLineSpeed		OBJECT-TYPE
	SYNTAX	INTEGER (0..99999)
	ACCESS	read-only 
	STATUS	mandatory
	DESCRIPTION	
		"The speed setting of the driver (line speed), or the
	dialer (modem speed)."
	::= { dialerInfoEntry 5 }

dialerInfoDataEncoding	OBJECT-TYPE
	SYNTAX	DataEncoding
	ACCESS	read-only 
	STATUS	mandatory
	DESCRIPTION	
		"The type of data encoding used on the connection."
	::= { dialerInfoEntry 6 }

dialerInfoClockType	OBJECT-TYPE
	SYNTAX	ClockType
	ACCESS	read-only 
	STATUS	mandatory
	DESCRIPTION	
		"The type of clocking used by the modem."
	::= { dialerInfoEntry 7 }

-- ****************************************************************************
--		Direct dialer General Status Info
-- ****************************************************************************

dialerDirectInfoTable		OBJECT-TYPE
	SYNTAX	SEQUENCE OF DialerDirectInfoEntry 
	ACCESS	not-accessible
	STATUS	mandatory
	DESCRIPTION	
		"General Information Table for Direct dialer."
	::= { dialer 2 }

dialerDirectInfoEntry		OBJECT-TYPE
	SYNTAX	DialerDirectInfoEntry
	ACCESS	not-accessible
	STATUS	mandatory
	DESCRIPTION	
		"The set of dialer configuration attributes for one port."
	INDEX		{ dialerDirectPortRef }
	::= { dialerDirectInfoTable 1 }

DialerDirectInfoEntry ::= SEQUENCE {
	dialerDirectPortRef
		PortRef,
	dialerDirectIfType
		INTEGER,
	dialerDirectMode
		INTEGER,
	dialerDirectConnDelay
		INTEGER,
	dialerDirectRtsDelay
		INTEGER,
	dialerDirectState
		INTEGER
	}

dialerDirectPortRef	OBJECT-TYPE
	SYNTAX	PortRef
	ACCESS	read-only 
	STATUS	mandatory
	DESCRIPTION	
		"The id of the port, equal to portIndex from the port group. 
	It identifies the port to which the configuration parameters apply."
	::= { dialerDirectInfoEntry 1 }

dialerDirectIfType	OBJECT-TYPE
	SYNTAX	INTEGER {
		rs232 (1),
		v35 (2),
		x21 (3)
	}
	ACCESS	read-only 
	STATUS	mandatory
	DESCRIPTION	
		" Interface type of the Dialer"
	::= { dialerDirectInfoEntry 2 }

dialerDirectMode	OBJECT-TYPE
	SYNTAX	INTEGER  {
		leased (1),
		dial (2)
	}
	ACCESS	read-only 
	STATUS	mandatory
	DESCRIPTION	
		"States whether the modem is connected to a Leased or
	Dial-Up phone line."
	::= { dialerDirectInfoEntry 3 }

dialerDirectConnDelay	OBJECT-TYPE
	SYNTAX	INTEGER
	ACCESS	read-only 
	STATUS	mandatory
	DESCRIPTION	
		" Max time for connection in seconds."
	::= { dialerDirectInfoEntry 4 }

dialerDirectRtsDelay	OBJECT-TYPE
	SYNTAX	INTEGER
	ACCESS	read-only 
	STATUS	mandatory
	DESCRIPTION	
		" Delay between arrival of DSR and activation of RTS 
	circuit in msec."
	::= { dialerDirectInfoEntry 5 }

dialerDirectState	OBJECT-TYPE
	SYNTAX	INTEGER {
		closed (1),
		opening (2),
		answering (3),
		delaying (4),
		opened (5),
		closing (6),
                ringing (7),
                answer-wait (8),
                originating (9),
                connecting (10),
                connect-delay (11),
                connected (12),
                disconnecting (13),
                remote-disc (14),
                local-disc (15),
                connect-req (16),
                incomming-call (17),
                outgoing-call (18),
                outgoing-delay (19)
	}
	ACCESS	read-only 
	STATUS	mandatory
	DESCRIPTION	
	"State of the Direct dialer:
		closed(1)    -  Modem signals on a dial modem were lost.
		opening(2)   -  Link is being set up (modem dialing).
		asnwering(3) -  Accepting call from remote.
		delaying(4)  -  Waiting for a timer to expire.
		opened(5)    -  Physical link is established.
		Closing(6)   -  Disconnecting the physical link. 
                ringing (7)             -
                answer-wait (8)         -
                originating (9)         -
                connecting (10)         -
                connect-delay (11)      -
                connected (12)          -
                disconnecting (13)      -
                remote-disc (14)        -
                local-disc (15)         -
                connect-req (16)        -
                incomming-call (17)     -
                outgoing-call (18)      -
                outgoing-delay (19)     -                       "
	::= { dialerDirectInfoEntry 6 }



-- ****************************************************************************
--		Direct dialer  RS232 Interface Info
-- ****************************************************************************

dialerDirectRs232InfoTable		OBJECT-TYPE
	SYNTAX	SEQUENCE OF DialerDirectRs232InfoEntry 
	ACCESS	not-accessible
	STATUS	mandatory
	DESCRIPTION	
		"General Information Table for Direct dialer RS232."
	::= { dialer 3 }

dialerDirectRs232InfoEntry		OBJECT-TYPE
	SYNTAX	DialerDirectRs232InfoEntry
	ACCESS	not-accessible
	STATUS	mandatory
	DESCRIPTION	
		"The set of dialer configuration attributes for one port."
	INDEX		{ dialerDirectRs232PortRef }
	::= { dialerDirectRs232InfoTable 1 }

DialerDirectRs232InfoEntry ::= SEQUENCE {
	dialerDirectRs232PortRef
		PortRef,
	dialerDirectRs232DbounceDelay
		INTEGER,
	dialerDirectRs232DtrSignal
		OnOff,
	dialerDirectRs232DsrSignal
		OnOff,
	dialerDirectRs232RiSignal
		OnOff
	}

dialerDirectRs232PortRef	OBJECT-TYPE
	SYNTAX	PortRef
	ACCESS	read-only 
	STATUS	mandatory
	DESCRIPTION	
		"The id of the port, equal to portIndex from the port group. 
	It identifies the port to which the configuration parameters apply."
	::= { dialerDirectRs232InfoEntry 1 }

dialerDirectRs232DbounceDelay	OBJECT-TYPE
	SYNTAX	INTEGER
	ACCESS	read-only 
	STATUS	mandatory
	DESCRIPTION	
		" This applies to Leased line only. It is the amount of time,
	expressed in msecs, that DSR signal stays on."
	::= { dialerDirectRs232InfoEntry 2 }

dialerDirectRs232DtrSignal	OBJECT-TYPE
	SYNTAX	OnOff
	ACCESS	read-only 
	STATUS	mandatory
	DESCRIPTION	
		" The current status of the DTR signal. "
	::= { dialerDirectRs232InfoEntry 3 }

dialerDirectRs232DsrSignal	OBJECT-TYPE
	SYNTAX	OnOff
        ACCESS  read-write
	STATUS	mandatory
	DESCRIPTION	
		" The current status of the DSR signal."
	::= { dialerDirectRs232InfoEntry 4 }

dialerDirectRs232RiSignal	OBJECT-TYPE
	SYNTAX	OnOff
	ACCESS	read-only 
	STATUS	mandatory
	DESCRIPTION	
		" The current status of the RI signal. This is set to
	ON when there is an incoming call."
	::= { dialerDirectRs232InfoEntry 5 }


-- ****************************************************************************
--		Direct dialer  X21 Interface Info
-- ****************************************************************************

dialerDirectX21InfoTable		OBJECT-TYPE
	SYNTAX	SEQUENCE OF DialerDirectX21InfoEntry 
	ACCESS	not-accessible
	STATUS	mandatory
	DESCRIPTION	
		"General Information Table for Direct dialer X21."
	::= { dialer 4 }

dialerDirectX21InfoEntry		OBJECT-TYPE
	SYNTAX	DialerDirectX21InfoEntry
	ACCESS	not-accessible
	STATUS	mandatory
	DESCRIPTION	
		"The set of dialer configuration attributes for one port."
	INDEX		{ dialerDirectX21PortRef }
	::= { dialerDirectX21InfoTable 1 }

DialerDirectX21InfoEntry ::= SEQUENCE {
	dialerDirectX21PortRef
		PortRef,
	dialerDirectX21CtrlSignal
		OnOff,
	dialerDirectX21IndicSignal
		OnOff
	}


dialerDirectX21PortRef	OBJECT-TYPE
	SYNTAX	PortRef
	ACCESS	read-only 
	STATUS	mandatory
	DESCRIPTION	
		"The id of the port, equal to portIndex from the port group. 
	It identifies the port to which the configuration parameters apply."
	::= { dialerDirectX21InfoEntry 1 }

dialerDirectX21CtrlSignal	OBJECT-TYPE
	SYNTAX	OnOff
	ACCESS	read-only 
	STATUS	mandatory
	DESCRIPTION	
		" The control circuit status."
	::= { dialerDirectX21InfoEntry 2 }

dialerDirectX21IndicSignal	OBJECT-TYPE
	SYNTAX	OnOff
	ACCESS	read-only 
	STATUS	mandatory
	DESCRIPTION	
		"The indication circuit status."
	::= { dialerDirectX21InfoEntry 3 }


-- ****************************************************************************
--		V25BIS dialer General Status Info
-- ****************************************************************************

dialerV25bisInfoTable		OBJECT-TYPE
	SYNTAX	SEQUENCE OF DialerV25bisInfoEntry 
	ACCESS	not-accessible
	STATUS	mandatory
	DESCRIPTION	
		"General Information Table for V25Bis dialer."
	::= { dialer 5 }

dialerV25bisInfoEntry		OBJECT-TYPE
	SYNTAX	DialerV25bisInfoEntry
	ACCESS	not-accessible
	STATUS	mandatory
	DESCRIPTION	
		"The set of dialer configuration attributes for one port."
	INDEX		{ dialerV25bisPortRef }
	::= { dialerV25bisInfoTable 1 }

DialerV25bisInfoEntry ::= SEQUENCE {
	dialerV25bisPortRef
		PortRef,
	dialerV25bisPrimaryNum
		DisplayString,
	dialerV25bisSecondaryNum
		DisplayString,
	dialerV25bisAnsEnable
		FalseTrue,
	dialerV25bisRetryAllowed
		FalseTrue,
	dialerV25bisMaxRetries
		INTEGER,
	dialerV25bisRetryDelay
		INTEGER,
	dialerV25bisConnDelay
		INTEGER,
	dialerV25bisOnOffDelay
		INTEGER,
	dialerV25bisLossDelay
		INTEGER,
	dialerV25bisMinDsrOnDelay
		INTEGER,
	dialerV25bisRiDtrDelay
		INTEGER,
	dialerV25bisHangupDelay
		INTEGER,
	dialerV25bisDeltaRiDelay
		INTEGER,
	dialerV25bisCtsOnDelay
		INTEGER,
	dialerV25bisDtrSignal
		OnOff,
	dialerV25bisDsrSignal
		OnOff,
	dialerV25bisCtsSignal
		OnOff,
	dialerV25bisRiSignal
		OnOff,
	dialerV25bisState
		INTEGER
	}

dialerV25bisPortRef	OBJECT-TYPE
	SYNTAX	PortRef
	ACCESS	read-only 
	STATUS	mandatory
	DESCRIPTION	
		"The Port Number."
	::= { dialerV25bisInfoEntry 1 }

dialerV25bisPrimaryNum	OBJECT-TYPE
	SYNTAX	DisplayString (SIZE(0..50))
	ACCESS	read-write
	STATUS	mandatory
	DESCRIPTION
		"The main telephone number stored in the dialer."
	::= { dialerV25bisInfoEntry 2 }

dialerV25bisSecondaryNum	OBJECT-TYPE
	SYNTAX	DisplayString (SIZE(0..50))
	ACCESS	read-write
	STATUS	mandatory
	DESCRIPTION
		"The alternate telephone number stored in the dialer. This
	number is dialed if the main number is busy of if there is no
	answer."
	::= { dialerV25bisInfoEntry 3 }

dialerV25bisAnsEnable	OBJECT-TYPE
	SYNTAX	FalseTrue
	ACCESS	read-write
	STATUS	mandatory
	DESCRIPTION
		"States whether or not the dialer answers incoming calls."
	::= { dialerV25bisInfoEntry 4 }

dialerV25bisRetryAllowed	OBJECT-TYPE
	SYNTAX	FalseTrue
	ACCESS	read-only
	STATUS	mandatory
	DESCRIPTION
		"Indicates whether or not the dialer will try to redial
	a number that is busy or does not answer."
	::= { dialerV25bisInfoEntry 5 }

dialerV25bisMaxRetries	OBJECT-TYPE
	SYNTAX	INTEGER
	ACCESS	read-only 
	STATUS	mandatory
	DESCRIPTION	
		"Specifies how many times a number will be redialed if it is 
		 busy or otherwise unresponsive."
	::= { dialerV25bisInfoEntry 6 }

dialerV25bisRetryDelay	OBJECT-TYPE
	SYNTAX	INTEGER
	ACCESS	read-only 
	STATUS	mandatory
	DESCRIPTION
		"The amount of time in msecs between redial attempts."
	::= { dialerV25bisInfoEntry 7 }

dialerV25bisConnDelay	OBJECT-TYPE
	SYNTAX	INTEGER
	ACCESS	read-only 
	STATUS	mandatory
	DESCRIPTION	
		"Maximum delay for connection establishment (secs)."
	::= { dialerV25bisInfoEntry 8 }

dialerV25bisOnOffDelay	OBJECT-TYPE
	SYNTAX	INTEGER
	ACCESS	read-only 
	STATUS	mandatory
	DESCRIPTION	
		"The delay allowed in seconds for the DSR to go off
	before hangup."
	::= { dialerV25bisInfoEntry 9 }

dialerV25bisLossDelay	OBJECT-TYPE
	SYNTAX	INTEGER
	ACCESS	read-only 
	STATUS	mandatory
	DESCRIPTION	
		"Amount of delay in msecs before DSR debouncing for
	         OFF."
	::= { dialerV25bisInfoEntry 10 }

dialerV25bisMinDsrOnDelay	OBJECT-TYPE
	SYNTAX	INTEGER
	ACCESS	read-only 
	STATUS	mandatory
	DESCRIPTION	
		"Amount of delay in msecs before DSR debouncing for ON."
	::= { dialerV25bisInfoEntry 11 }

dialerV25bisRiDtrDelay	OBJECT-TYPE
	SYNTAX	INTEGER
	ACCESS	read-only 
	STATUS	mandatory
	DESCRIPTION	
		"Amount of delay in msec before raising DTR when 
	RING occurs."
	::= { dialerV25bisInfoEntry 12 }

dialerV25bisHangupDelay	OBJECT-TYPE
	SYNTAX	INTEGER
	ACCESS	read-only 
	STATUS	mandatory
	DESCRIPTION	
		"Amount of delay in secs before hangup, if DSR goes
	OFF in connected state."
	::= { dialerV25bisInfoEntry 13 }

dialerV25bisDeltaRiDelay	OBJECT-TYPE
	SYNTAX	INTEGER
	ACCESS	read-only 
	STATUS	mandatory
	DESCRIPTION	
		"Delay in msecs before rings are no longer occur."
	::= { dialerV25bisInfoEntry 14 }

dialerV25bisCtsOnDelay	OBJECT-TYPE
	SYNTAX	INTEGER
	ACCESS	read-only 
	STATUS	mandatory
	DESCRIPTION	
		"Maximum delay in msecs for sending a message to the modem."
	::= { dialerV25bisInfoEntry 15 }

dialerV25bisDtrSignal	OBJECT-TYPE
	SYNTAX	OnOff
	ACCESS	read-only 
	STATUS	mandatory
	DESCRIPTION	
		"DTR status."
	::= { dialerV25bisInfoEntry 16 }

dialerV25bisDsrSignal	OBJECT-TYPE
	SYNTAX	OnOff
	ACCESS	read-only
	STATUS	mandatory
	DESCRIPTION	
		"DSR status."
	::= { dialerV25bisInfoEntry 17 }

dialerV25bisCtsSignal	OBJECT-TYPE
	SYNTAX	OnOff
	ACCESS	read-only 
	STATUS	mandatory
	DESCRIPTION	
		"CTS status."
	::= { dialerV25bisInfoEntry 18 }

dialerV25bisRiSignal	OBJECT-TYPE
	SYNTAX	OnOff
	ACCESS	read-only
	STATUS	mandatory
	DESCRIPTION
		"RI status."
	::= { dialerV25bisInfoEntry 19 }

dialerV25bisState	OBJECT-TYPE
	SYNTAX	INTEGER {
		on-hook (1),
		ready (2),
		dialing (3),
		connect (4),
		data-tran (5),
		retrying (6),
		ringing (7),
		ans-start (8),
		ans-cplt (9),
		hanging-up (10),
		ignore-ring (11),
		collision (12),
		ans-accepting (13),
		prog-rdy (14),
		program (15),
		prog-ring (16),
		prog-not-rdy (17)
	}
	ACCESS	read-only
	STATUS	mandatory
	DESCRIPTION
	" The status  of the V.25bis modem:
		on-hook (1)	- Modem not active
		ready (2)	- Connection established
		dialing (3)	- Dialing a number
		connect (4)	- Successful dial attemp
		data-tran (5)	- Data transfer state enabled
		retrying (6)	- Awaiting call attempt
		ringing (7)	- Incoming call present
		ans-start (8)	- Connect request received
		ans-cplt (9)	- Call establised.
		hanging-up (10)	- Dialer disconnecting from DCE
		ignore-ring (11) - Ringing signal ignored
		collision (12)	- Collision between connection request
				and incoming call
		ans-accepting (13) - Accepted incoming call
		prog-rdy (14)	- Dialer ready to communicate with modem
		program (15)	- Modem ready to communicate with dialer
		prog-ring (16) 	- Signal detected from DCE
		prog-not-rdy (17) - Dialer not ready to communicate with
					modem.
	"
	::= { dialerV25bisInfoEntry 20 }

-- ****************************************************************************
--		AT-CMD dialer General Status Info
-- ****************************************************************************

dialerAtCmdInfoTable		OBJECT-TYPE
	SYNTAX	SEQUENCE OF DialerAtCmdInfoEntry
	ACCESS	not-accessible
	STATUS	mandatory
	DESCRIPTION
		"General Information Table for AT-CMD dialer."
	::= { dialer 6 }

dialerAtCmdInfoEntry		OBJECT-TYPE
	SYNTAX	DialerAtCmdInfoEntry
	ACCESS	not-accessible
	STATUS	mandatory
	DESCRIPTION	
		"The set of dialer configuration attributes for one port."
	INDEX		{ dialerAtCmdPortRef }
	::= { dialerAtCmdInfoTable 1 }

DialerAtCmdInfoEntry ::= SEQUENCE {
	dialerAtCmdPortRef
		PortRef,
	dialerAtCmdPrimaryNum
		DisplayString,
	dialerAtCmdSecondaryNum
		DisplayString,
	dialerAtCmdAnsEnable
		FalseTrue,
	dialerAtCmdRetryAllowed
		FalseTrue,
	dialerAtCmdMaxRetries	
		INTEGER,
	dialerAtCmdRetryDelay	
		INTEGER,
	dialerAtCmdConnDelay
		INTEGER,
	dialerAtCmdOnOffDelay
		INTEGER,
	dialerAtCmdLossDelay
		INTEGER,
	dialerAtCmdMinDsrOnDelay
		INTEGER,
	dialerAtCmdRiDtrDelay
		INTEGER,
	dialerAtCmdHangupDelay	
		INTEGER,
	dialerAtCmdDeltaRiDelay	
		INTEGER,
	dialerAtCmdParity	
		INTEGER,
	dialerAtCmdBitsPerByte	
		INTEGER,
	dialerAtCmdModemSpeed	
		INTEGER,
	dialerAtCmdDtrSignal
		OnOff,
	dialerAtCmdDsrSignal
		OnOff,
	dialerAtCmdRiSignal
		OnOff,
	dialerAtCmdState
		INTEGER
	}

dialerAtCmdPortRef	OBJECT-TYPE
	SYNTAX	PortRef
	ACCESS	read-only
	STATUS	mandatory
	DESCRIPTION
		"The Port Number."
	::= { dialerAtCmdInfoEntry 1 }

dialerAtCmdPrimaryNum	OBJECT-TYPE
	SYNTAX	DisplayString (SIZE(0..50))
	ACCESS	read-write
	STATUS	mandatory
	DESCRIPTION
		"The main telephone number stored in the dialer."
	::= { dialerAtCmdInfoEntry 2 }

dialerAtCmdSecondaryNum	OBJECT-TYPE
	SYNTAX	DisplayString (SIZE(0..50))
	ACCESS	read-write
	STATUS	mandatory
	DESCRIPTION
		"The alternate telephone number stored in the dialer. This
	number is dialed if the main number is busy or if there is no
	answer."
	::= { dialerAtCmdInfoEntry 3 }

dialerAtCmdAnsEnable	OBJECT-TYPE
	SYNTAX	FalseTrue
	ACCESS	read-write
	STATUS	mandatory
	DESCRIPTION
		"States whether or not the dialer answers incoming calls."
	::= { dialerAtCmdInfoEntry 4 }

dialerAtCmdRetryAllowed	OBJECT-TYPE
	SYNTAX	FalseTrue
	ACCESS	read-only 
	STATUS	mandatory
	DESCRIPTION	
		"Indicates whether or not the dialer will try to redial
	a number that is busy or does not answer."
	::= { dialerAtCmdInfoEntry 5 }

dialerAtCmdMaxRetries	OBJECT-TYPE
	SYNTAX	INTEGER
	ACCESS	read-only 
	STATUS	mandatory
	DESCRIPTION	
		"Specifies how many times a number will be redialed if it is
		busy or otherwise unresponsive."
	::= { dialerAtCmdInfoEntry 6 }

dialerAtCmdRetryDelay	OBJECT-TYPE
	SYNTAX	INTEGER
	ACCESS	read-only 
	STATUS	mandatory
	DESCRIPTION	
		"The amount of time in msecs between redial attempts."
	::= { dialerAtCmdInfoEntry 7 }

dialerAtCmdConnDelay	OBJECT-TYPE
	SYNTAX	INTEGER
	ACCESS	read-only 
	STATUS	mandatory
	DESCRIPTION	
		"Maximum delay for connection establishment (secs)."
	::= { dialerAtCmdInfoEntry 8 }

dialerAtCmdOnOffDelay	OBJECT-TYPE
	SYNTAX	INTEGER
	ACCESS	read-only 
	STATUS	mandatory
	DESCRIPTION	
		"The delay allowed in seconds for the DSR signal to go off
	before hangup."
	::= { dialerAtCmdInfoEntry 9 }

dialerAtCmdLossDelay	OBJECT-TYPE
	SYNTAX	INTEGER
	ACCESS	read-only 
	STATUS	mandatory
	DESCRIPTION	
		"Number of msecs allowed before DSR debouncing for OFF."
	::= { dialerAtCmdInfoEntry 10 }

dialerAtCmdMinDsrOnDelay	OBJECT-TYPE
	SYNTAX	INTEGER
	ACCESS	read-only 
	STATUS	mandatory
	DESCRIPTION	
		"msecs DSR debouncing for ON before going OFF."
	::= { dialerAtCmdInfoEntry 11 }

dialerAtCmdRiDtrDelay	OBJECT-TYPE
	SYNTAX	INTEGER
	ACCESS	read-only 
	STATUS	mandatory
	DESCRIPTION	
		"Amount of delay in msec, before raising DTR when 
	RING occurs."
	::= { dialerAtCmdInfoEntry 12 }

dialerAtCmdHangupDelay	OBJECT-TYPE
	SYNTAX	INTEGER
	ACCESS	read-only 
	STATUS	mandatory
	DESCRIPTION	
		"Amount of delay in secs before hangup, if DSR goes
	OFF in connected state."
	::= { dialerAtCmdInfoEntry 13 }

dialerAtCmdDeltaRiDelay	OBJECT-TYPE
	SYNTAX	INTEGER
	ACCESS	read-only 
	STATUS	mandatory
	DESCRIPTION	
		"delay in msecs before rings no longer occur."
	::= { dialerAtCmdInfoEntry 14 }

dialerAtCmdParity	OBJECT-TYPE
	SYNTAX	INTEGER {
		none (1),
		odd (2),
		even (3)
	}
	ACCESS	read-only 
	STATUS	mandatory
	DESCRIPTION	
		"The parity."
	::= { dialerAtCmdInfoEntry 15 }

dialerAtCmdBitsPerByte	OBJECT-TYPE
	SYNTAX	INTEGER {
		data7 (1),
		data8 (2)
	}
	ACCESS	read-only 
	STATUS	mandatory
	DESCRIPTION	
		"The number of data bits per byte."
	::= { dialerAtCmdInfoEntry 16 }

dialerAtCmdModemSpeed	OBJECT-TYPE
	SYNTAX	INTEGER
	ACCESS	read-only 
	STATUS	mandatory
	DESCRIPTION	
		"Modem Speed."
	::= { dialerAtCmdInfoEntry 17 }

dialerAtCmdDtrSignal	OBJECT-TYPE
	SYNTAX	OnOff
	ACCESS	read-only 
	STATUS	mandatory
	DESCRIPTION	
		"DTR status."
	::= { dialerAtCmdInfoEntry 18 }

dialerAtCmdDsrSignal	OBJECT-TYPE
	SYNTAX	OnOff
	ACCESS	read-only 
	STATUS	mandatory
	DESCRIPTION	
		"DSR status."
	::= { dialerAtCmdInfoEntry 19 }

dialerAtCmdRiSignal	OBJECT-TYPE
	SYNTAX	OnOff
	ACCESS	read-only 
	STATUS	mandatory
	DESCRIPTION	
		"RI status."
	::= { dialerAtCmdInfoEntry 20 }

dialerAtCmdState	OBJECT-TYPE
	SYNTAX	INTEGER {
		on-hook (1),
		dialing (2),
		answering (3),
		ringing (4),
		retrying (5),
		off-hook (6),
		hanging-up (7)
	}
	ACCESS	read-only 
	STATUS	mandatory
	DESCRIPTION	
	" The status  of the AT modem:
		on-hook (1) - modem not active
		dialing (2) - dialing a number
		answering (3) - accepting call from remote
		ringing (4) - incoming call present
		retrying (5) - awaiting new call attempt
		off-hook (6) - Modem active
		hanging-up (7) - Disconnecting from DCE
	"
	::= { dialerAtCmdInfoEntry 21 }

-- ****************************************************************************
--		V22BISDNA dialer General Status Info
-- ****************************************************************************
-- This Table is not supported by the Eicon SNMP Agent

dialerV22BisDnaInfoTable		OBJECT-TYPE
	SYNTAX	SEQUENCE OF DialerV22BisDnaInfoEntry 
	ACCESS	not-accessible
	STATUS	mandatory
	DESCRIPTION	
		"General Information Table for V22BISDNA dialer."
	::= { dialer 7 }

dialerV22BisDnaInfoEntry		OBJECT-TYPE
	SYNTAX	DialerV22BisDnaInfoEntry
	ACCESS	not-accessible
	STATUS	mandatory
	DESCRIPTION	
		"The set of dialer configuration attributes for one port."
	INDEX		{ dialerV22BisDnaPortRef }
	::= { dialerV22BisDnaInfoTable 1 }

DialerV22BisDnaInfoEntry ::= SEQUENCE {
	dialerV22BisDnaPortRef
		PortRef,
	dialerV22BisDnaPrimaryNum
		DisplayString,
	dialerV22BisDnaSecondaryNum
		DisplayString,
	dialerV22BisDnaAnsEnable
		FalseTrue,
	dialerV22BisDnaRetryAllowed
		FalseTrue,
	dialerV22BisDnaMaxRetries	
		INTEGER,
	dialerV22BisDnaCallProgress	
		FalseTrue,
	dialerV22BisDnaDecadic	
		FalseTrue,
	dialerV22BisDnaMakeBreakRatio	
		INTEGER,
	dialerV22BisDnaRetryDelay	
		INTEGER,
	dialerV22BisDnaMinDialDelay
		INTEGER,
	dialerV22BisDnaWaitDialTone
		INTEGER,
	dialerV22BisDnaWaitCarrier
		INTEGER,
	dialerV22BisDnaHndshkAbortTimer
		INTEGER,
	dialerV22BisDnaGuardTone
		INTEGER,
	dialerV22BisDnaPulseDelay
		INTEGER,
	dialerV22BisDnaDTMFDuration
		INTEGER,
	dialerV22BisDnaDTMFDelay
		INTEGER,
	dialerV22BisDnaDTMFLevel
		INTEGER,
	dialerV22BisDnaTxLevel
		INTEGER,
	dialerV22BisDnaRxLevel
		FalseTrue,
	dialerV22BisDnaRiNbr
		INTEGER,
	dialerV22BisDnaDeltaRiDelay	
		INTEGER,
	dialerV22BisDnaRiDtrDelay	
		INTEGER,
	dialerV22BisDnaDsrRtsDelay	
		INTEGER,
	dialerV22BisDnaModemSpeed	
		INTEGER,
	dialerV22BisDnaDtrSignal	
		OnOff,
	dialerV22BisDnaDsrSignal	
		OnOff,
	dialerV22BisDnaRiSignal	
		OnOff,
	dialerV22BisDnaCdSignal
		OnOff,
	dialerV22BisDnaToneInd
		OnOff,
	dialerV22BisDnaDloInd
		OnOff,
	dialerV22BisDnaState
		INTEGER
	}

dialerV22BisDnaPortRef	OBJECT-TYPE
	SYNTAX	PortRef
	ACCESS	read-only
	STATUS	mandatory
	DESCRIPTION
		"The Port Number."
	::= { dialerV22BisDnaInfoEntry 1 }

dialerV22BisDnaPrimaryNum	OBJECT-TYPE
	SYNTAX	DisplayString (SIZE(0..50))
	ACCESS	read-write
	STATUS	mandatory
	DESCRIPTION
		"The main telephone number stored in the dialer."
	::= { dialerV22BisDnaInfoEntry 2 }

dialerV22BisDnaSecondaryNum	OBJECT-TYPE
	SYNTAX	DisplayString (SIZE(0..50))
	ACCESS	read-write
	STATUS	mandatory
	DESCRIPTION
		"The alternate telephone number stored in the dialer. This
	number is dialed if the main number is busy or if there is no
	answer."
	::= { dialerV22BisDnaInfoEntry 3 }

dialerV22BisDnaAnsEnable	OBJECT-TYPE
	SYNTAX	FalseTrue
	ACCESS	read-write
	STATUS	mandatory
	DESCRIPTION
		"States whether or not the dialer answers incoming calls."
	::= { dialerV22BisDnaInfoEntry 4 }

dialerV22BisDnaRetryAllowed	OBJECT-TYPE
	SYNTAX	FalseTrue
	ACCESS	read-only 
	STATUS	mandatory
	DESCRIPTION	
		"Indicates whether or not the dialer will try to redial
	a number that is busy or does not answer."
	::= { dialerV22BisDnaInfoEntry 5 }

dialerV22BisDnaMaxRetries	OBJECT-TYPE
	SYNTAX	INTEGER
	ACCESS	read-only 
	STATUS	mandatory
	DESCRIPTION	
		"Specifies how many times a number will be redialed if it is
		busy or otherwise unresponsive."
	::= { dialerV22BisDnaInfoEntry 6 }

dialerV22BisDnaCallProgress	OBJECT-TYPE
	SYNTAX	FalseTrue
	ACCESS	read-only 
	STATUS	mandatory
	DESCRIPTION	
		"Call progress tone detection."
	::= { dialerV22BisDnaInfoEntry 7 }

dialerV22BisDnaDecadic	OBJECT-TYPE
	SYNTAX	FalseTrue
	ACCESS	read-only 
	STATUS	mandatory
	DESCRIPTION	
		"Indicates whether Decadic dialing is active or not.
	Decadic dialing does the following: each digit you dial is 
	subtracted from 10, and the result is the number actually
	dialed."
	::= { dialerV22BisDnaInfoEntry 8 }

dialerV22BisDnaMakeBreakRatio	OBJECT-TYPE
	SYNTAX	INTEGER
	ACCESS	read-only 
	STATUS	mandatory
	DESCRIPTION	
		"Ratio for PULSE and DIAL make and break time."
	::= { dialerV22BisDnaInfoEntry 9 }

dialerV22BisDnaRetryDelay	OBJECT-TYPE
	SYNTAX	INTEGER
	ACCESS	read-only 
	STATUS	mandatory
	DESCRIPTION	
		"The amount of time in msecs between redial attempts."
	::= { dialerV22BisDnaInfoEntry 10 }

dialerV22BisDnaMinDialDelay	OBJECT-TYPE
	SYNTAX	INTEGER
	ACCESS	read-only 
	STATUS	mandatory
	DESCRIPTION	
		"The length of delay (msec) associated with a comma
	placed in a dialing command."
	::= { dialerV22BisDnaInfoEntry 11 }

dialerV22BisDnaWaitDialTone	OBJECT-TYPE
	SYNTAX	INTEGER
	ACCESS	read-only 
	STATUS	mandatory
	DESCRIPTION	
		"The amount of time (msec) the modem waits when it 
	encounters the wait for dial tone modifier in dial string."
	::= { dialerV22BisDnaInfoEntry 12 }

dialerV22BisDnaWaitCarrier	OBJECT-TYPE
	SYNTAX	INTEGER
	ACCESS	read-only 
	STATUS	mandatory
	DESCRIPTION	
		"The amount of time (msec) the  modem waits for valid 
	carrier after completing a dial."
	::= { dialerV22BisDnaInfoEntry 13 }

dialerV22BisDnaHndshkAbortTimer	OBJECT-TYPE
	SYNTAX	INTEGER
	ACCESS	read-only 
	STATUS	mandatory
	DESCRIPTION	
		"The amount of time (sec) allowed before the call is
	aborted if DSR does not go ON."
	::= { dialerV22BisDnaInfoEntry 14 }

dialerV22BisDnaGuardTone	OBJECT-TYPE
	SYNTAX	INTEGER
	ACCESS	read-only 
	STATUS	mandatory
	DESCRIPTION	
		"Indicates a guard tone frequency. "
	::= { dialerV22BisDnaInfoEntry 15 }

dialerV22BisDnaPulseDelay	OBJECT-TYPE
	SYNTAX	INTEGER
	ACCESS	read-only 
	STATUS	mandatory
	DESCRIPTION	
		"The delay (msec) between digits dialed on a pulse line."
	::= { dialerV22BisDnaInfoEntry 16 }

dialerV22BisDnaDTMFDuration	OBJECT-TYPE
	SYNTAX	INTEGER
	ACCESS	read-only 
	STATUS	mandatory
	DESCRIPTION	
		"The tone duration (msec) used in DMTF dialing."
	::= { dialerV22BisDnaInfoEntry 17 }

dialerV22BisDnaDTMFDelay	OBJECT-TYPE
	SYNTAX	INTEGER
	ACCESS	read-only 
	STATUS	mandatory
	DESCRIPTION	
		"The delay (msec) between digits dialed when in tone
	dial mode."
	::= { dialerV22BisDnaInfoEntry 18 }

dialerV22BisDnaDTMFLevel	OBJECT-TYPE
	SYNTAX	INTEGER
	ACCESS	read-only 
	STATUS	mandatory
	DESCRIPTION	
		"The  tone dialing level attenuation in dB."
	::= { dialerV22BisDnaInfoEntry 19 }

dialerV22BisDnaTxLevel	OBJECT-TYPE
	SYNTAX	INTEGER
	ACCESS	read-only 
	STATUS	mandatory
	DESCRIPTION	
		"The attenuation level (Db) on data transmission, once the
	handshake is completed with the remote modem."
	::= { dialerV22BisDnaInfoEntry 20 }

dialerV22BisDnaRxLevel	OBJECT-TYPE
	SYNTAX	FalseTrue
	ACCESS	read-only 
	STATUS	mandatory
	DESCRIPTION	
		"Minimum acceptable receiver threshold value. This indicates
	whether a 3dB attenuation is used on the receive signal at line
	input."
	::= { dialerV22BisDnaInfoEntry 21 }

dialerV22BisDnaRiNbr	OBJECT-TYPE
	SYNTAX	INTEGER
	ACCESS	read-only 
	STATUS	mandatory
	DESCRIPTION	
		"The number of rings required before the modem answers, if
	it is set to auto-answer mode."
	::= { dialerV22BisDnaInfoEntry 22 }

dialerV22BisDnaDeltaRiDelay	OBJECT-TYPE
	SYNTAX	INTEGER
	ACCESS	read-only 
	STATUS	mandatory
	DESCRIPTION	
		"delay in msecs before rings no longer occur."
	::= { dialerV22BisDnaInfoEntry 23 }

dialerV22BisDnaRiDtrDelay	OBJECT-TYPE
	SYNTAX	INTEGER
	ACCESS	read-only 
	STATUS	mandatory
	DESCRIPTION	
		"Amount of delay in msec, before raising DTR when 
	RING occurs."
	::= { dialerV22BisDnaInfoEntry 24 }

dialerV22BisDnaDsrRtsDelay	OBJECT-TYPE
	SYNTAX	INTEGER
	ACCESS	read-only 
	STATUS	mandatory
	DESCRIPTION	
		" Delay between arrival of DSR and activation of RTS 
	circuit in msec."
	::= { dialerV22BisDnaInfoEntry 25 }

dialerV22BisDnaModemSpeed	OBJECT-TYPE
	SYNTAX	INTEGER
	ACCESS	read-only 
	STATUS	mandatory
	DESCRIPTION	
		"Modem Speed."
	::= { dialerV22BisDnaInfoEntry 26 }

dialerV22BisDnaDtrSignal	OBJECT-TYPE
	SYNTAX	OnOff
	ACCESS	read-only 
	STATUS	mandatory
	DESCRIPTION	
		"DTR status."
	::= { dialerV22BisDnaInfoEntry 27 }

dialerV22BisDnaDsrSignal	OBJECT-TYPE
	SYNTAX	OnOff
	ACCESS	read-only 
	STATUS	mandatory
	DESCRIPTION	
		"DSR status."
	::= { dialerV22BisDnaInfoEntry 28 }

dialerV22BisDnaRiSignal	OBJECT-TYPE
	SYNTAX	OnOff
	ACCESS	read-only 
	STATUS	mandatory
	DESCRIPTION	
		"RI status."
	::= { dialerV22BisDnaInfoEntry 29 }

dialerV22BisDnaCdSignal	OBJECT-TYPE
	SYNTAX	OnOff
	ACCESS	read-only 
	STATUS	mandatory
	DESCRIPTION	
		"Carrier detect status."
	::= { dialerV22BisDnaInfoEntry 30 }

dialerV22BisDnaToneInd	OBJECT-TYPE
	SYNTAX	OnOff
	ACCESS	read-only 
	STATUS	mandatory
	DESCRIPTION	
		"Tone indication."
	::= { dialerV22BisDnaInfoEntry 31 }

dialerV22BisDnaDloInd	OBJECT-TYPE
	SYNTAX	OnOff
	ACCESS	read-only 
	STATUS	mandatory
	DESCRIPTION	
		"Dial line occupied indication."
	::= { dialerV22BisDnaInfoEntry 32 }

dialerV22BisDnaState	OBJECT-TYPE
	SYNTAX	INTEGER {
		dialing-phone (1),
		dialing-mdm (2),
		retrying (3),
		ringing (4),
		line-busy (5),
		off-hook (6),
		on-hook (7),
		answering (8),
		delaying (9),
		voice-com (10),
		handshaking (11),
		wait-ringback (12),
		initialising (13)
	}
	ACCESS	read-only 
	STATUS	mandatory
	DESCRIPTION	
	" Status of the V22bis Dna modem:
		dialing-phone (1) - Dialing a number on the phone attached
					to the DNA phone plug.
		dialing-mdm (2)   - Dialing a remote modem
		retrying (3)      - Awaiting call attempt
		ringing (4)       - Incoming call present
		line-busy (5)     - Busy signal encountered
		off-hook (6)      - Modem active
		on-hook (7)	  - Modem not active
		answering (8)     - Accepting call from remote
		delaying (9)      - Waiting for timer to expire
		voice-com (10)    - the line is already used by a voice
					connection.
		handshaking (11)  - Synchronizing calls with remote
		wait-ringback (12) - Awaiting remote response
		initialising (13) - initializing modem
	"
	::= { dialerV22BisDnaInfoEntry 33 }

-- ****************************************************************************
--		V22BISIMC dialer General Status Info
-- ****************************************************************************

dialerV22BisImcInfoTable		OBJECT-TYPE
	SYNTAX	SEQUENCE OF DialerV22BisImcInfoEntry
	ACCESS	not-accessible
	STATUS	mandatory
	DESCRIPTION	
		"General Information Table for V22BISIMC dialer."
	::= { dialer 8 }

dialerV22BisImcInfoEntry		OBJECT-TYPE
	SYNTAX	DialerV22BisImcInfoEntry
	ACCESS	not-accessible
	STATUS	mandatory
	DESCRIPTION	
		"The set of dialer configuration attributes for one port."
	INDEX		{ dialerV22BisImcPortRef }
	::= { dialerV22BisImcInfoTable 1 }

DialerV22BisImcInfoEntry ::= SEQUENCE {
	dialerV22BisImcPortRef
		PortRef,
	dialerV22BisImcPrimaryNum
		DisplayString,
	dialerV22BisImcSecondaryNum
		DisplayString,
	dialerV22BisImcAnsEnable
		FalseTrue,
	dialerV22BisImcRetryAllowed
		FalseTrue,
	dialerV22BisImcMaxRetries	
		INTEGER,
	dialerV22BisImcCallProgress	
		FalseTrue,
	dialerV22BisImcDecadic	
		FalseTrue,
	dialerV22BisImcMakeBreakRatio	
		INTEGER,
	dialerV22BisImcRetryDelay	
		INTEGER,
	dialerV22BisImcMinDialDelay
		INTEGER,
	dialerV22BisImcWaitDialTone
		INTEGER,
	dialerV22BisImcWaitCarrier
		INTEGER,
	dialerV22BisImcHndshkAbortTimer
		INTEGER,
	dialerV22BisImcGuardTone
		INTEGER,
	dialerV22BisImcPulseDelay
		INTEGER,
	dialerV22BisImcDTMFDuration
		INTEGER,
	dialerV22BisImcDTMFDelay
		INTEGER,
	dialerV22BisImcDTMFLevel
		INTEGER,
	dialerV22BisImcTxLevel
		INTEGER,
	dialerV22BisImcRxLevel
		INTEGER,
	dialerV22BisImcRiNbr
		INTEGER,
	dialerV22BisImcDeltaRiDelay	
		INTEGER,
	dialerV22BisImcRiDtrDelay	
		INTEGER,
	dialerV22BisImcDsrRtsDelay	
		INTEGER,
	dialerV22BisImcModemSpeed	
		INTEGER,
	dialerV22BisImcDtrSignal	
		OnOff,
	dialerV22BisImcDsrSignal	
		OnOff,
	dialerV22BisImcRiSignal	
		OnOff,
	dialerV22BisImcCdSignal	
		OnOff,
	dialerV22BisImcToneInd	
		OnOff,
	dialerV22BisImcDloInd	
		OnOff,
	dialerV22BisImcLineType
		INTEGER,
	dialerV22BisImcLeasedOpertn
		INTEGER,
	dialerV22BisImcSpeakerLevel
		INTEGER,
	dialerV22BisImcState
		INTEGER
	}

dialerV22BisImcPortRef	OBJECT-TYPE
	SYNTAX	PortRef
	ACCESS	read-only 
	STATUS	mandatory
	DESCRIPTION	
		"The Port Number."
	::= { dialerV22BisImcInfoEntry 1 }

dialerV22BisImcPrimaryNum	OBJECT-TYPE
	SYNTAX	DisplayString (SIZE(0..50))
	ACCESS	read-write
	STATUS	mandatory
	DESCRIPTION
		"The main telephone number stored in the dialer."
	::= { dialerV22BisImcInfoEntry 2 }

dialerV22BisImcSecondaryNum	OBJECT-TYPE
	SYNTAX	DisplayString (SIZE(0..50))
	ACCESS	read-write
	STATUS	mandatory
	DESCRIPTION
		"The alternate telephone number stored in the dialer. This
	number is dialed if the main number is busy or if there is no
	answer."
	::= { dialerV22BisImcInfoEntry 3 }

dialerV22BisImcAnsEnable	OBJECT-TYPE
	SYNTAX	FalseTrue
	ACCESS	read-write
	STATUS	mandatory
	DESCRIPTION
		"States whether or not the dialer answers incoming calls."
	::= { dialerV22BisImcInfoEntry 4 }

dialerV22BisImcRetryAllowed	OBJECT-TYPE
	SYNTAX	FalseTrue
	ACCESS	read-only 
	STATUS	mandatory
	DESCRIPTION	
		"Indicates whether or not the dialer will try to redial
	a number that is busy or does not answer."
	::= { dialerV22BisImcInfoEntry 5 }

dialerV22BisImcMaxRetries	OBJECT-TYPE
	SYNTAX	INTEGER
	ACCESS	read-only 
	STATUS	mandatory
	DESCRIPTION	
		"Specifies how many times a number will be redialed if it is
		busy or otherwise unresponsive."
	::= { dialerV22BisImcInfoEntry 6 }

dialerV22BisImcCallProgress	OBJECT-TYPE
	SYNTAX	FalseTrue
	ACCESS	read-only 
	STATUS	mandatory
	DESCRIPTION	
		"Call progress tone detection."
	::= { dialerV22BisImcInfoEntry 7 }

dialerV22BisImcDecadic	OBJECT-TYPE
	SYNTAX	FalseTrue
	ACCESS	read-only 
	STATUS	mandatory
	DESCRIPTION	
		"Indicates whether Decadic dialing is active or not.
	Decadic dialing does the following: each digit you dial is 
	subtracted from 10, and the result is the number actually
	dialed."
	::= { dialerV22BisImcInfoEntry 8 }

dialerV22BisImcMakeBreakRatio	OBJECT-TYPE
	SYNTAX	INTEGER
	ACCESS	read-only 
	STATUS	mandatory
	DESCRIPTION	
		"Ratio of PULSE and DIAL make and break time."
	::= { dialerV22BisImcInfoEntry 9 }

dialerV22BisImcRetryDelay	OBJECT-TYPE
	SYNTAX	INTEGER
	ACCESS	read-only 
	STATUS	mandatory
	DESCRIPTION	
		"The amount of time in msecs between redial attempts."
	::= { dialerV22BisImcInfoEntry 10 }

dialerV22BisImcMinDialDelay	OBJECT-TYPE
	SYNTAX	INTEGER
	ACCESS	read-only 
	STATUS	mandatory
	DESCRIPTION	
		"The length of delay (msec) associated with a comma
	placed in a dialing command."
	::= { dialerV22BisImcInfoEntry 11 }

dialerV22BisImcWaitDialTone	OBJECT-TYPE
	SYNTAX	INTEGER
	ACCESS	read-only 
	STATUS	mandatory
	DESCRIPTION	
		"The amount of time (msec) the modem waits when it 
	encounters the wait for dial tone modifier in dial string."
	::= { dialerV22BisImcInfoEntry 12 }

dialerV22BisImcWaitCarrier	OBJECT-TYPE
	SYNTAX	INTEGER
	ACCESS	read-only 
	STATUS	mandatory
	DESCRIPTION	
		"The amount of time (msec) the  modem waits for valid 
	carrier after completing a dial."
	::= { dialerV22BisImcInfoEntry 13 }

dialerV22BisImcHndshkAbortTimer	OBJECT-TYPE
	SYNTAX	INTEGER
	ACCESS	read-only 
	STATUS	mandatory
	DESCRIPTION	
		"The amount of time (sec) allowed before the call is
	aborted if DSR does not go ON."
	::= { dialerV22BisImcInfoEntry 14 }

dialerV22BisImcGuardTone	OBJECT-TYPE
	SYNTAX	INTEGER
	ACCESS	read-only 
	STATUS	mandatory
	DESCRIPTION	
		"Indicates a guard tone frequency. "
	::= { dialerV22BisImcInfoEntry 15 }

dialerV22BisImcPulseDelay	OBJECT-TYPE
	SYNTAX	INTEGER
	ACCESS	read-only 
	STATUS	mandatory
	DESCRIPTION	
		"The delay between (msec) digits dialed on a pulse line."
	::= { dialerV22BisImcInfoEntry 16 }

dialerV22BisImcDTMFDuration	OBJECT-TYPE
	SYNTAX	INTEGER
	ACCESS	read-only 
	STATUS	mandatory
	DESCRIPTION	
		"The tone (msec) duration used in DMTF dialing."
	::= { dialerV22BisImcInfoEntry 17 }

dialerV22BisImcDTMFDelay	OBJECT-TYPE
	SYNTAX	INTEGER
	ACCESS	read-only 
	STATUS	mandatory
	DESCRIPTION	
		"The delay (msec) between digits dialed when in tone
	dial mode."
	::= { dialerV22BisImcInfoEntry 18 }

dialerV22BisImcDTMFLevel	OBJECT-TYPE
	SYNTAX	INTEGER
	ACCESS	read-only 
	STATUS	mandatory
	DESCRIPTION	
		"The  tone dialing level attenuation in dB."
	::= { dialerV22BisImcInfoEntry 19 }

dialerV22BisImcTxLevel	OBJECT-TYPE
	SYNTAX	INTEGER
	ACCESS	read-only 
	STATUS	mandatory
	DESCRIPTION	
		"The attenuation level (Db) on data transmission, once the
	handshake is completed with the remote modem."
	::= { dialerV22BisImcInfoEntry 20 }

dialerV22BisImcRxLevel	OBJECT-TYPE
	SYNTAX	INTEGER
	ACCESS	read-only 
	STATUS	mandatory
	DESCRIPTION	
		"Minimum acceptable receiver threshold value. This indicates
	whether a 3dB attenuation is used on the receive signal at line
	input."
	::= { dialerV22BisImcInfoEntry 21 }

dialerV22BisImcRiNbr	OBJECT-TYPE
	SYNTAX	INTEGER
	ACCESS	read-only 
	STATUS	mandatory
	DESCRIPTION	
		"The numbet of rings required before the modem answers, if
	it is set to auto-answer mode."
	::= { dialerV22BisImcInfoEntry 22 }

dialerV22BisImcDeltaRiDelay	OBJECT-TYPE
	SYNTAX	INTEGER
	ACCESS	read-only 
	STATUS	mandatory
	DESCRIPTION	
		"delay in msecs before rings no longer occur."
	::= { dialerV22BisImcInfoEntry 23 }

dialerV22BisImcRiDtrDelay	OBJECT-TYPE
	SYNTAX	INTEGER
	ACCESS	read-only 
	STATUS	mandatory
	DESCRIPTION	
		"Amount of delay in msec, before raising DTR when 
	RING occurs."
	::= { dialerV22BisImcInfoEntry 24 }

dialerV22BisImcDsrRtsDelay	OBJECT-TYPE
	SYNTAX	INTEGER
	ACCESS	read-only 
	STATUS	mandatory
	DESCRIPTION	
		" Delay between arrival of DSR and activation of RTS 
	circuit in msec."
	::= { dialerV22BisImcInfoEntry 25 }

dialerV22BisImcModemSpeed	OBJECT-TYPE
	SYNTAX	INTEGER
	ACCESS	read-only 
	STATUS	mandatory
	DESCRIPTION	
		"Modem Speed."
	::= { dialerV22BisImcInfoEntry 26 }

dialerV22BisImcDtrSignal	OBJECT-TYPE
	SYNTAX	OnOff
	ACCESS	read-only 
	STATUS	mandatory
	DESCRIPTION	
		"DTR status."
	::= { dialerV22BisImcInfoEntry 27 }

dialerV22BisImcDsrSignal	OBJECT-TYPE
	SYNTAX	OnOff
	ACCESS	read-only 
	STATUS	mandatory
	DESCRIPTION	
		"DSR status."
	::= { dialerV22BisImcInfoEntry 28 }

dialerV22BisImcRiSignal	OBJECT-TYPE
	SYNTAX	OnOff
	ACCESS	read-only 
	STATUS	mandatory
	DESCRIPTION	
		"RI status."
	::= { dialerV22BisImcInfoEntry 29 }

dialerV22BisImcCdSignal	OBJECT-TYPE
	SYNTAX	OnOff
	ACCESS	read-only 
	STATUS	mandatory
	DESCRIPTION	
		"Carrier Detect status."
	::= { dialerV22BisImcInfoEntry 30 }

dialerV22BisImcToneInd	OBJECT-TYPE
	SYNTAX	OnOff
	ACCESS	read-only 
	STATUS	mandatory
	DESCRIPTION	
		"Tone indication."
	::= { dialerV22BisImcInfoEntry 31 }

dialerV22BisImcDloInd	OBJECT-TYPE
	SYNTAX	OnOff
	ACCESS	read-only 
	STATUS	mandatory
	DESCRIPTION	
		"Dial line occupied indication."
	::= { dialerV22BisImcInfoEntry 32 }

dialerV22BisImcLineType	OBJECT-TYPE
	SYNTAX	INTEGER {
		dial (1),
		leased (2)
	}
	ACCESS	read-only 
	STATUS	mandatory
	DESCRIPTION	
		"States whether the modem is connected to a Leased or
	Dial-Up phone line."
	::= { dialerV22BisImcInfoEntry 33 }

dialerV22BisImcLeasedOpertn	OBJECT-TYPE
	SYNTAX	INTEGER {
		answer (1),
		originate (2)
	}
	ACCESS	read-only 
	STATUS	mandatory
	DESCRIPTION	
		"This applies to Leased line type only. This field states
	whether the dialer will go off-hook in Originate or Answer mode."
	::= { dialerV22BisImcInfoEntry 34 }

dialerV22BisImcSpeakerLevel	OBJECT-TYPE
	SYNTAX	INTEGER {
		low (1),
		high (2)
	}
	ACCESS	read-only 
	STATUS	mandatory
	DESCRIPTION	
		"The volume level of the Eiconcard's speaker."
	::= { dialerV22BisImcInfoEntry 35 }


dialerV22BisImcState	OBJECT-TYPE
	SYNTAX	INTEGER {
		dialing-phone (1),
		dialing-mdm (2),
		retrying (3),
		ringing (4),
		line-busy (5),
		off-hook (6),
		on-hook (7),
		answering (8),
		delaying (9),
		voice-com (10),
		handshaking (11),
		wait-ringback (12),
		initialising (13)
	}
	ACCESS	read-only 
	STATUS	mandatory
	DESCRIPTION	
	" Status of the V22bis Imc modem:
		dialing-phone (1) - Dialing a number on the phone attached
					to the DNA phone plug.
		dialing-mdm (2)   - Dialing a remote modem
		retrying (3)      - Awaiting call attempt
		ringing (4)       - Incoming call present
		line-busy (5)     - Busy signal encountered
		off-hook (6)      - Modem active
		on-hook (7)	  - Modem not active
		answering (8)     - Accepting call from remote
		delaying (9)      - Waiting for timer to expire
		voice-com (10)    - the line is already used by a voice
					connection.
		handshaking (11)  - Syncronizing calls with remote
		wait-ringback (12) - Awaiting remote response
		initialising (13) - initializing modem
	"
	::= { dialerV22BisImcInfoEntry 36 }


-- ****************************************************************************
--		V32BIS dialer General Status Info
-- ****************************************************************************

dialerV32BisInfoTable		OBJECT-TYPE
	SYNTAX	SEQUENCE OF DialerV32BisInfoEntry
	ACCESS	not-accessible
	STATUS	mandatory
	DESCRIPTION	
		"General Information Table for V32Bis dialer."
	::= { dialer 9 }

dialerV32BisInfoEntry		OBJECT-TYPE
	SYNTAX	DialerV32BisInfoEntry
	ACCESS	not-accessible
	STATUS	mandatory
	DESCRIPTION	
		"The set of dialer configuration attributes for one port."
	INDEX		{ dialerV32BisPortRef }
	::= { dialerV32BisInfoTable 1 }

DialerV32BisInfoEntry ::= SEQUENCE {
	dialerV32BisPortRef
		PortRef,
	dialerV32BisPrimNum
		DisplayString,
	dialerV32BisSecNum
		DisplayString,
	dialerV32BisOverrNum
		DisplayString,
	dialerV32BisCurrNum
		DisplayString,
	dialerV32BisPrimBitRate
		PrimBitRate,
	dialerV32BisSecBitRate
		PrimBitRate,
	dialerV32BisOverrBitRate
		PrimBitRate,
	dialerV32BisCurrBitRate
		PrimBitRate,
	dialerV32BisPrimConfig
		PrimCfg,
	dialerV32BisSecConfig
		PrimCfg,
	dialerV32BisOverrConfig
		PrimCfg,
	dialerV32BisCurrConfig
		PrimCfg,
	dialerV32BisCurrRetry
		INTEGER,
	dialerV32BisRingCount
		INTEGER,
	dialerV32BisAnsEnable
		FalseTrue,
	dialerV32BisDialMethod
		INTEGER,
	dialerV32BisRetry
		FalseTrue,
	dialerV32BisCallFailure
		INTEGER,
	dialerV32BisCarrierDetect
		INTEGER,
	dialerV32BisCarrierWait
		INTEGER,
	dialerV32BisHangupVerify
		INTEGER,
	dialerV32BisHangupSignal
		DisEnable,
	dialerV32BisTxLevel
		INTEGER,
	dialerV32BisRxLevel
		INTEGER,
	dialerV32BisGuardTone
		INTEGER,
	dialerV32BisLeasedLine
		INTEGER,
	dialerV32BisLeaseMode
		INTEGER,
	dialerV32BisLLTxLevel
		INTEGER,
	dialerV32BisLLConfig
		PrimCfg,
	dialerV32BisLLBitRate
		PrimBitRate,
	dialerV32BisCallingTone
		DisEnable,
	dialerV32BisAutoMode
		DisEnable,
	dialerV32BisRetryAllowed
		DisEnable,
	dialerV32BisMaxRetry
		INTEGER,
	dialerV32BisDialTone
		DisEnable,
	dialerV32BisDialToneWait
		INTEGER,
	dialerV32BisRetryWait
		INTEGER,
	dialerV32BisHangupWait
		INTEGER,
	dialerV32BisDialPauseWait
		INTEGER,
	dialerV32BisDeltaRiWait
		INTEGER,
	dialerV32BisDTMFDuration
		INTEGER,
	dialerV32BisDTMFDelay
		INTEGER,
	dialerV32BisDTMFFreq1Level
		INTEGER,
	dialerV32BisDTMFFreq2Level
		INTEGER,
	dialerV32BisPulseMakeTime
		INTEGER,
	dialerV32BisPulseBreakTime
		INTEGER,
	dialerV32BisPulseDelay
		INTEGER,
	dialerV32BisSpeakerLevel
		INTEGER,
	dialerV32BisRiToAnswer
		INTEGER,
	dialerV32BisAnswerBitRate
		PrimBitRate,
	dialerV32BisAnswerConfig
		PrimCfg,
	dialerV32BisRetrain
		OnOff,
	dialerV32BisEqmLevel
		INTEGER,
	dialerV32BisRiOnOffDetect
		OnOff,
	dialerV32BisCdDetect
		OnOff,
	dialerV32BisRingbackDetect
		OnOff,
	dialerV32BisAnswerDetect
		OnOff,
	dialerV32BisBusyDetect
		OnOff,
	dialerV32BisDiscDetect
		OnOff,
	dialerV32BisCdSignal
		OnOff,
	dialerV32BisDsrSignal
		OnOff,
	dialerV32BisState
		INTEGER
	}

dialerV32BisPortRef	OBJECT-TYPE
	SYNTAX	PortRef
	ACCESS	read-only 
	STATUS	mandatory
	DESCRIPTION	
		"The Port Number."
	::= { dialerV32BisInfoEntry 1 }

dialerV32BisPrimNum	OBJECT-TYPE
	SYNTAX	DisplayString (SIZE(0..50))
	ACCESS	read-write
	STATUS	mandatory
	DESCRIPTION	
		"The main telephone number stored in the dialer."
	::= { dialerV32BisInfoEntry 2 }

dialerV32BisSecNum	OBJECT-TYPE
	SYNTAX	DisplayString (SIZE(0..50))
	ACCESS	read-write
	STATUS	mandatory
	DESCRIPTION
		"The alternate telephone number stored in the dialer. This
	number is dialed if the main number is busy or if there is no
	answer."
	::= { dialerV32BisInfoEntry 3 }

dialerV32BisOverrNum	OBJECT-TYPE
	SYNTAX	DisplayString (SIZE(0..50))
	ACCESS	read-only 
	STATUS	mandatory
	DESCRIPTION	
		"Override number."
	::= { dialerV32BisInfoEntry 4 }

dialerV32BisCurrNum	OBJECT-TYPE
	SYNTAX	DisplayString (SIZE(0..50))
	ACCESS	read-only 
	STATUS	mandatory
	DESCRIPTION	
		"Current number."
	::= { dialerV32BisInfoEntry 5 }

dialerV32BisPrimBitRate	OBJECT-TYPE
	SYNTAX	PrimBitRate
	ACCESS	read-only 
	STATUS	mandatory
	DESCRIPTION	
		"Default bit rate for primary number."
	::= { dialerV32BisInfoEntry 6 }

dialerV32BisSecBitRate	OBJECT-TYPE
	SYNTAX	PrimBitRate
	ACCESS	read-only 
	STATUS	mandatory
	DESCRIPTION	
		"Default bit rate for secondary number."
	::= { dialerV32BisInfoEntry 7 }

dialerV32BisOverrBitRate	OBJECT-TYPE
	SYNTAX	PrimBitRate
	ACCESS	read-only 
	STATUS	mandatory
	DESCRIPTION	
		"Default bit rate for override number."
	::= { dialerV32BisInfoEntry 8 }

dialerV32BisCurrBitRate	OBJECT-TYPE
	SYNTAX	PrimBitRate
	ACCESS	read-only 
	STATUS	mandatory
	DESCRIPTION	
		"Default bit rate for current number."
	::= { dialerV32BisInfoEntry 9 }

dialerV32BisPrimConfig	OBJECT-TYPE
	SYNTAX	PrimCfg
	ACCESS	read-only 
	STATUS	mandatory
	DESCRIPTION	
		"Dial modem primary configuration"
	::= { dialerV32BisInfoEntry 10 }

dialerV32BisSecConfig	OBJECT-TYPE
	SYNTAX	PrimCfg
	ACCESS	read-only 
	STATUS	mandatory
	DESCRIPTION	
		"Dial modem secondary configuration"
	::= { dialerV32BisInfoEntry 11 }

dialerV32BisOverrConfig	OBJECT-TYPE
	SYNTAX	PrimCfg
	ACCESS	read-only 
	STATUS	mandatory
	DESCRIPTION	
		"Dial modem override configuration"
	::= { dialerV32BisInfoEntry 12 }

dialerV32BisCurrConfig	OBJECT-TYPE
	SYNTAX	PrimCfg
	ACCESS	read-only 
	STATUS	mandatory
	DESCRIPTION	
		"Dial modem current configuration"
	::= { dialerV32BisInfoEntry 13 }

dialerV32BisCurrRetry	OBJECT-TYPE
	SYNTAX	INTEGER
	ACCESS	read-only 
	STATUS	mandatory
	DESCRIPTION	
		"Current number of retries."
	::= { dialerV32BisInfoEntry 14 }

dialerV32BisRingCount	OBJECT-TYPE
	SYNTAX	INTEGER
	ACCESS	read-only 
	STATUS	mandatory
	DESCRIPTION	
		"Incoming ring counter."
	::= { dialerV32BisInfoEntry 15 }

dialerV32BisAnsEnable	OBJECT-TYPE
	SYNTAX	FalseTrue
	ACCESS	read-write
	STATUS	mandatory
	DESCRIPTION	
		"States whether or not the dialer answers incoming calls."
	::= { dialerV32BisInfoEntry 16 }

dialerV32BisDialMethod	OBJECT-TYPE
	SYNTAX	INTEGER {
		dtmf (1),
		pulse (2)
	}
	ACCESS	read-only 
	STATUS	mandatory
	DESCRIPTION	
		"The method used for dialing."
	::= { dialerV32BisInfoEntry 17 }

dialerV32BisRetry	OBJECT-TYPE
	SYNTAX	FalseTrue
	ACCESS	read-only 
	STATUS	mandatory
	DESCRIPTION	
		"Indicates whether or not the dialer will try to redial a 
	number that is busy or does not answer."
	::= { dialerV32BisInfoEntry 18 }

dialerV32BisCallFailure	OBJECT-TYPE
	SYNTAX	INTEGER
	ACCESS	read-only 
	STATUS	mandatory
	DESCRIPTION	
		"Reason for last call failure."
	::= { dialerV32BisInfoEntry 19 }

dialerV32BisCarrierDetect	OBJECT-TYPE
	SYNTAX	INTEGER
	ACCESS	read-only 
	STATUS	mandatory
	DESCRIPTION	
		"Delay in msec to wait for verification of carrier detect."
	::= { dialerV32BisInfoEntry 20 }

dialerV32BisCarrierWait	OBJECT-TYPE
	SYNTAX	INTEGER
	ACCESS	read-only 
	STATUS	mandatory
	DESCRIPTION	
		"Delay in msec to wait for carrier detect."
	::= { dialerV32BisInfoEntry 21 }

dialerV32BisHangupVerify	OBJECT-TYPE
	SYNTAX	INTEGER
	ACCESS	read-only 
	STATUS	mandatory
	DESCRIPTION	
		"Delay in msec to wait to verify for hangup."
	::= { dialerV32BisInfoEntry 22 }

dialerV32BisHangupSignal	OBJECT-TYPE
	SYNTAX	DisEnable
	ACCESS	read-only 
	STATUS	mandatory
	DESCRIPTION	
		"Hangup signal state."
	::= { dialerV32BisInfoEntry 23 }

dialerV32BisTxLevel	OBJECT-TYPE
	SYNTAX	INTEGER
	ACCESS	read-only 
	STATUS	mandatory
	DESCRIPTION	
		"The attenuation level (Db) on data transmission, once the
	handshake is completed with the remote modem."
	::= { dialerV32BisInfoEntry 24 }

dialerV32BisRxLevel	OBJECT-TYPE
	SYNTAX	INTEGER
	ACCESS	read-only 
	STATUS	mandatory
	DESCRIPTION	
		"Minimum acceptable receiver threshold value. This indicates
	whether a 3dB attenuation is used on the receive signal at line
	input."
	::= { dialerV32BisInfoEntry 25 }

dialerV32BisGuardTone	OBJECT-TYPE
	SYNTAX	INTEGER
	ACCESS	read-only 
	STATUS	mandatory
	DESCRIPTION	
		"Indicates a guard tone frequency. "
	::= { dialerV32BisInfoEntry 26 }

dialerV32BisLeasedLine	OBJECT-TYPE
	SYNTAX	INTEGER {
--		pstn (0),
		two-w-ll (1),
		four-w-ll (2)
	}
	ACCESS	read-only 
	STATUS	mandatory
	DESCRIPTION	
		"Dial or leased line."
	::= { dialerV32BisInfoEntry 27 }

dialerV32BisLeaseMode	OBJECT-TYPE
	SYNTAX	INTEGER {
		answer (1),
		originate (2)
	}
	ACCESS	read-only 
	STATUS	mandatory
	DESCRIPTION	
		"This applies to Leased line type only. This field states
	whether the dialer will go off-hook in Originate or Answer mode."
	::= { dialerV32BisInfoEntry 28 }

dialerV32BisLLTxLevel	OBJECT-TYPE
	SYNTAX	INTEGER
	ACCESS	read-only 
	STATUS	mandatory
	DESCRIPTION	
		"The attenuation level (Db) on data transmission once the
	handshake is completed with the remote modem (for leased line)."
	::= { dialerV32BisInfoEntry 29 }

dialerV32BisLLConfig	OBJECT-TYPE
	SYNTAX	PrimCfg
	ACCESS	read-only 
	STATUS	mandatory
	DESCRIPTION	
		"Leased line configuration"
	::= { dialerV32BisInfoEntry 30 }

dialerV32BisLLBitRate	OBJECT-TYPE
	SYNTAX	PrimBitRate
	ACCESS	read-only 
	STATUS	mandatory
	DESCRIPTION	
		"Leased line bit rate."
	::= { dialerV32BisInfoEntry 31 }

dialerV32BisCallingTone	OBJECT-TYPE
	SYNTAX	DisEnable
	ACCESS	read-only 
	STATUS	mandatory
	DESCRIPTION	
		"Calling tone state."
	::= { dialerV32BisInfoEntry 32 }

dialerV32BisAutoMode	OBJECT-TYPE
	SYNTAX	DisEnable
	ACCESS	read-only 
	STATUS	mandatory
	DESCRIPTION	
		"Auto mode state (fallback/forward)."
	::= { dialerV32BisInfoEntry 33 }

dialerV32BisRetryAllowed	OBJECT-TYPE
	SYNTAX	DisEnable
	ACCESS	read-only 
	STATUS	mandatory
	DESCRIPTION	
		"Indicates whether or not the dialer will try to redial
	a number that is busy or does not answer."
	::= { dialerV32BisInfoEntry 34 }

dialerV32BisMaxRetry	OBJECT-TYPE
	SYNTAX	INTEGER
	ACCESS	read-only 
	STATUS	mandatory
	DESCRIPTION	
		"Specifies how many times a number will be redialed if it is
		busy or otherwise unresponsive."
	::= { dialerV32BisInfoEntry 35 }

dialerV32BisDialTone	OBJECT-TYPE
	SYNTAX	DisEnable
	ACCESS	read-only 
	STATUS	mandatory
	DESCRIPTION	
		"The dial tone state."
	::= { dialerV32BisInfoEntry 36 }

dialerV32BisDialToneWait	OBJECT-TYPE
	SYNTAX	INTEGER
	ACCESS	read-only 
	STATUS	mandatory
	DESCRIPTION	
		"The amount of time (msec) the modem waits when it 
	encounters the wait for dial tone modifier in dial string."
	::= { dialerV32BisInfoEntry 37 }

dialerV32BisRetryWait	OBJECT-TYPE
	SYNTAX	INTEGER
	ACCESS	read-only 
	STATUS	mandatory
	DESCRIPTION	
		"Retry timer delay."
	::= { dialerV32BisInfoEntry 38 }

dialerV32BisHangupWait	OBJECT-TYPE
	SYNTAX	INTEGER
	ACCESS	read-only 
	STATUS	mandatory
	DESCRIPTION	
		"Hangup timer delay."
	::= { dialerV32BisInfoEntry 39 }

dialerV32BisDialPauseWait	OBJECT-TYPE
	SYNTAX	INTEGER
	ACCESS	read-only 
	STATUS	mandatory
	DESCRIPTION	
		"maximum delay before dial."
	::= { dialerV32BisInfoEntry 40 }

dialerV32BisDeltaRiWait	OBJECT-TYPE
	SYNTAX	INTEGER
	ACCESS	read-only 
	STATUS	mandatory
	DESCRIPTION	
		"Maximum delay (msec) between 2 rings."
	::= { dialerV32BisInfoEntry 41 }

dialerV32BisDTMFDuration	OBJECT-TYPE
	SYNTAX	INTEGER
	ACCESS	read-only 
	STATUS	mandatory
	DESCRIPTION	
		"The tone duration (msec) used in DMTF dialing."
	::= { dialerV32BisInfoEntry 42 }

dialerV32BisDTMFDelay	OBJECT-TYPE
	SYNTAX	INTEGER
	ACCESS	read-only 
	STATUS	mandatory
	DESCRIPTION	
		"The delay (msec) between digits dialed when in tone
	dial mode."
	::= { dialerV32BisInfoEntry 43 }

dialerV32BisDTMFFreq1Level	OBJECT-TYPE
	SYNTAX	INTEGER
	ACCESS	read-only 
	STATUS	mandatory
	DESCRIPTION	
		"DTMF high frequency power level."
	::= { dialerV32BisInfoEntry 44 }

dialerV32BisDTMFFreq2Level	OBJECT-TYPE
	SYNTAX	INTEGER
	ACCESS	read-only 
	STATUS	mandatory
	DESCRIPTION	
		"DTMF low frequency power level."
	::= { dialerV32BisInfoEntry 45 }

dialerV32BisPulseMakeTime	OBJECT-TYPE
	SYNTAX	INTEGER
	ACCESS	read-only 
	STATUS	mandatory
	DESCRIPTION	
		"Pulse make time (msec)."
	::= { dialerV32BisInfoEntry 46 }

dialerV32BisPulseBreakTime	OBJECT-TYPE
	SYNTAX	INTEGER
	ACCESS	read-only 
	STATUS	mandatory
	DESCRIPTION	
		"Pulse break time (msec)."
	::= { dialerV32BisInfoEntry 47 }

dialerV32BisPulseDelay	OBJECT-TYPE
	SYNTAX	INTEGER
	ACCESS	read-only 
	STATUS	mandatory
	DESCRIPTION	
		"Pulse interdigit delay (msec)."
	::= { dialerV32BisInfoEntry 48 }

dialerV32BisSpeakerLevel	OBJECT-TYPE
	SYNTAX	INTEGER {
		low (1),
		high (2)
	}
	ACCESS	read-only 
	STATUS	mandatory
	DESCRIPTION	
		"The volume level of the Eiconcard's speaker."
	::= { dialerV32BisInfoEntry 49 }

dialerV32BisRiToAnswer	OBJECT-TYPE
	SYNTAX	INTEGER
	ACCESS	read-only 
	STATUS	mandatory
	DESCRIPTION	
		"Number of rings befor answering."
	::= { dialerV32BisInfoEntry 50 }

dialerV32BisAnswerBitRate	OBJECT-TYPE
	SYNTAX	PrimBitRate
	ACCESS	read-only 
	STATUS	mandatory
	DESCRIPTION	
		"Answer bit rate."
	::= { dialerV32BisInfoEntry 51 }

dialerV32BisAnswerConfig	OBJECT-TYPE
	SYNTAX	PrimCfg
	ACCESS	read-only 
	STATUS	mandatory
	DESCRIPTION	
		"Answer configuration."
	::= { dialerV32BisInfoEntry 52 }

dialerV32BisRetrain	OBJECT-TYPE
	SYNTAX	OnOff
	ACCESS	read-only 
	STATUS	mandatory
	DESCRIPTION	
		"."
	::= { dialerV32BisInfoEntry 53 }

dialerV32BisEqmLevel	OBJECT-TYPE
	SYNTAX	INTEGER {
		disable (1),
		low-quality (2),
		medium-quality (3),
		high-quality (4)
	}
	ACCESS	read-only 
	STATUS	mandatory
	DESCRIPTION	
		"."
	::= { dialerV32BisInfoEntry 54 }

dialerV32BisRiOnOffDetect	OBJECT-TYPE
	SYNTAX	OnOff
	ACCESS	read-only 
	STATUS	mandatory
	DESCRIPTION	
		"Ring signal status."
	::= { dialerV32BisInfoEntry 55 }

dialerV32BisCdDetect	OBJECT-TYPE
	SYNTAX	OnOff
	ACCESS	read-only 
	STATUS	mandatory
	DESCRIPTION	
		"Carrier detect status."
	::= { dialerV32BisInfoEntry 56 }

dialerV32BisRingbackDetect	OBJECT-TYPE
	SYNTAX	OnOff
	ACCESS	read-only 
	STATUS	mandatory
	DESCRIPTION	
		"Ringback signal detect status."
	::= { dialerV32BisInfoEntry 57 }

dialerV32BisAnswerDetect	OBJECT-TYPE
	SYNTAX	OnOff
	ACCESS	read-only 
	STATUS	mandatory
	DESCRIPTION	
		"Answer tone detect status."
	::= { dialerV32BisInfoEntry 58 }

dialerV32BisBusyDetect	OBJECT-TYPE
	SYNTAX	OnOff
	ACCESS	read-only 
	STATUS	mandatory
	DESCRIPTION	
		"Busy tone detect status."
	::= { dialerV32BisInfoEntry 59 }

dialerV32BisDiscDetect	OBJECT-TYPE
	SYNTAX	OnOff
	ACCESS	read-only 
	STATUS	mandatory
	DESCRIPTION	
		"Disconnect detect status."
	::= { dialerV32BisInfoEntry 60 }

dialerV32BisCdSignal	OBJECT-TYPE
	SYNTAX	OnOff
	ACCESS	read-only 
	STATUS	mandatory
	DESCRIPTION	
		"CD signal status."
	::= { dialerV32BisInfoEntry 61 }

dialerV32BisDsrSignal	OBJECT-TYPE
	SYNTAX	OnOff
	ACCESS	read-only 
	STATUS	mandatory
	DESCRIPTION	
		"DSR signal status."
	::= { dialerV32BisInfoEntry 62 }

dialerV32BisState	OBJECT-TYPE
	SYNTAX	INTEGER {
		m-closed (1),
		m-opened (2),
		m-local-test (3),
		m-ringing (4),
		m-dialing (5),
		m-answering (6),
		m-originating (7),
		m-retrying (8),
		m-connected (9),
		m-retraining (10),
		m-remote-test (11),
		m-remote-disc (12),
		m-local-disc (13),
		m-hangup-idle (14),
		m-closing (15),
		m-offhook-idle (16)
	}
	ACCESS	read-only 
	STATUS	mandatory
	DESCRIPTION	
	" State of the V32bis dialer:
		m-closed (1)		- Dialer not active
		m-opened (2)		- No connection establised
		m-local-test (3)	- Local analog loopback
		m-ringing (4)		- Incoming call present
		m-dialing (5)		- Dialing a number
		m-answering (6)		- Call answer in progress
		m-originating (7)	- Call originate in progress
		m-retrying (8)		- Awaiting call attempt
		m-connected (9)		- connection present
		m-retraining (10)	- performing retrain
		m-remote-test (11)	- Remote digital loopback
		m-remote-disc (12)	- Remote has disconnected
		m-local-disc (13)	- Local has disconnected
		m-hangup-idle (14)	- Idle after hangup
		m-closing (15)		- Awaiting local disconnect
		m-offhook-idle (16)	- Modem goes off hook on command
	"
	::= { dialerV32BisInfoEntry 63 }

-- ****************************************************************************
--		Dialer Control Table
-- ****************************************************************************

dialerControlTable		OBJECT-TYPE
	SYNTAX	SEQUENCE OF  DialerControlEntry
	ACCESS	not-accessible
	STATUS	mandatory
	DESCRIPTION	
		"The table for dynamic dialing entries."
	::= { dialer 10 }

dialerControlEntry		OBJECT-TYPE
	SYNTAX	DialerControlEntry
	ACCESS	not-accessible
	STATUS	mandatory
	DESCRIPTION	
		"The set of attributes for one entry per port."
	INDEX		{ dialerCtrlPortRef }
	::= { dialerControlTable 1 }
   
DialerControlEntry ::= SEQUENCE {
	dialerCtrlPortRef
		PortRef,
	dialerCtrlAction
		INTEGER,
	dialerCtrlAnsEnable
		FalseTrue,
	dialerCtrlDirectDSROnOff
		OnOff,
        dialerCtrlNumber
		DisplayString,
	dialerCtrlScriptFile
                DisplayString,
        dialerCtrlActionState
                ActionState,
        dialerCtrlActionError
                INTEGER,
        dialerCtrlConfig
                PrimCfg,
        dialerCtrlBitRate
                PrimBitRate,

--  DEFINED ONLY FOR TESTS
        dialerCtrlType
		IsdnDnType,
	dialerCtrlPlan
		IsdnDnPlan,
        dialerCtrlSub
		DisplayString,
        dialerCtrlSubType
		IsdnSubType,
        dialerCtrlTns
		DisplayString,
        dialerCtrlNumberTemp
		DisplayString,
	dialerCtrlDialMask
		INTEGER,
	dialerCtrlCallSpeed
		INTEGER	
	}

dialerCtrlPortRef	OBJECT-TYPE
	SYNTAX	PortRef
	ACCESS	read-only 
	STATUS	mandatory
	DESCRIPTION	
		"The Port number of the dialer."
	::= { dialerControlEntry 1 }

dialerCtrlAction	OBJECT-TYPE
	SYNTAX	INTEGER {
		exec (1),
		dial (2),
		hangup (3),
		start (4),
		idle (5),
                store(6),
		other (7)
	}
	ACCESS	read-write 
	STATUS	mandatory
	DESCRIPTION	
		"The Action states.
		exec (1) - This action executes the script file which 
			would be set in dialerCtrlScriptFile.
		dial (2) - This action dials the number stored in
			dialerCtrlMainNumber. if dialerCtrlMainNumber is
			not set then the dialerCtrlPrimary number is 
			dialed by the dialer.
  			ISDN dialer dials the number stored by the card.
		hangup (3) - This action hangs-up the current connection.
    		store (6) - This action stores the parameters in the card.
			ISDN dialer only. 
		"
	::= { dialerControlEntry 2 }

dialerCtrlAnsEnable	OBJECT-TYPE
	SYNTAX	FalseTrue
	ACCESS	read-write
	STATUS	mandatory
	DESCRIPTION
	"States whether or not the dialer answers incoming calls."
	::= { dialerControlEntry 3 }

dialerCtrlDirectDSROnOff	OBJECT-TYPE
	SYNTAX	OnOff
	ACCESS	read-write
	STATUS	mandatory
	DESCRIPTION
		"Defines the setting of the Data Rate Select signal. 
		Setting this mib is valid only if the dialer type is 
		Direct and the interface is RS-232."
	::= { dialerControlEntry 4 }

dialerCtrlNumber OBJECT-TYPE
	SYNTAX	DisplayString (SIZE(0..50))
	ACCESS	read-write 
	STATUS	mandatory
	DESCRIPTION	
		"The primary Phone Number"
	::= { dialerControlEntry 5 }
 
dialerCtrlScriptFile	OBJECT-TYPE
	SYNTAX	DisplayString (SIZE(0..80))
	ACCESS	read-write 
	STATUS	mandatory
	DESCRIPTION	
		"The Complete path where the Dialer Script file resides."
        ::= { dialerControlEntry 6 }

dialerCtrlActionState OBJECT-TYPE
	SYNTAX  ActionState
	ACCESS	read-only
	STATUS	mandatory
	DESCRIPTION	
		"The state of the action operation performed  by the Agent 
		as a result of setting the values to the dialerCtrlAction. 
		The Management station will poll that variable after initiating
		an action.  The value done(1) indicates that the 
		action terminated successfully. The value failed(2) indicates 
		that the action terminated with an error. The 
		variable dialerCtrlActionError indicates the error code."
        ::= { dialerControlEntry 7 }

dialerCtrlActionError   OBJECT-TYPE
	SYNTAX	INTEGER 
	ACCESS	read-only
	STATUS	mandatory
	DESCRIPTION	
		"If the value is 0, this means no error. Otherwise, the value 
		indicates the error code returned after the action operation."
        ::= { dialerControlEntry 8 }

dialerCtrlConfig   OBJECT-TYPE
        SYNTAX  PrimCfg
        ACCESS  read-write
	STATUS	mandatory
	DESCRIPTION	
                "The config to which the V32 dialer will have to be set.
                 This information is only used when using a V32 dialer."
        ::= { dialerControlEntry 9 }

dialerCtrlBitRate   OBJECT-TYPE
        SYNTAX  PrimBitRate
        ACCESS  read-write
	STATUS	mandatory
	DESCRIPTION	
                "The Bit Rate to which the V32 dialer will have to be set.
                 This information is only used when using a V32 dialer."
        ::= { dialerControlEntry 10 }

-- DEFINED ONLY FOR TESTS
dialerCtrlType	    OBJECT-TYPE
        SYNTAX  IsdnDnType
        ACCESS  read-write
	STATUS	mandatory
	DESCRIPTION
		"The remote directory number type. Used by ISDN dialer only.
		 DEFINED ONLY FOR TESTS. "
        ::= { dialerControlEntry 11 }

dialerCtrlPlan	    OBJECT-TYPE
        SYNTAX  IsdnDnPlan
        ACCESS  read-write
	STATUS	mandatory
	DESCRIPTION
		"The remote directory number plan. Used by ISDN dialer only.
		 DEFINED ONLY FOR TESTS. "
        ::= { dialerControlEntry 12 }

dialerCtrlSub     OBJECT-TYPE
        SYNTAX  DisplayString (SIZE (0..21))	
        ACCESS  read-write
	STATUS	mandatory
	DESCRIPTION
		"The remote subaddress. When in the connected state, the
		 remote subaddress dialer is displayed. Otherwise, the stored
		 subaddress is displayed. Used by ISDN dialer only. 
		 DEFINED ONLY FOR TESTS. "	
        ::= { dialerControlEntry 13 }

dialerCtrlSubType    OBJECT-TYPE
	SYNTAX	IsdnSubType
	ACCESS  read-write		     
	STATUS  mandatory
	DESCRIPTION
		"The local subaddress type. Used by ISDN dialer only.
		 DEFINED ONLY FOR TESTS. "
	::= { dialerControlEntry 14 }

dialerCtrlTns	     OBJECT-TYPE
	SYNTAX	DisplayString (SIZE (0..16))
	ACCESS	read-write
	STATUS	mandatory
	DESCRIPTION	
		"The string identifying the selected long distance carrier. 
	        In ISDN	terms, it is called the Transit Network Selection. 
		This string is usually made of 3 digits and is assigned by 
                Bellcore. Used by ISDN dialer only. DEFINED ONLY FOR TESTS. "
	::= { dialerControlEntry 15 }

dialerCtrlNumberTemp  OBJECT-TYPE
	SYNTAX	DisplayString (SIZE(0..50))
	ACCESS	read-only 
	STATUS	mandatory
	DESCRIPTION	
		"The temporary Phone Number. DEFINED ONLY FOR ISDN TESTS."
	::= { dialerControlEntry 16 }

dialerCtrlDialMask    OBJECT-TYPE
	SYNTAX	INTEGER
	ACCESS	read-only 
	STATUS	mandatory
	DESCRIPTION	
		"Read the mask state. DEFINED ONLY FOR TESTS."
	::= { dialerControlEntry 17 }

dialerCtrlCallSpeed   OBJECT-TYPE
	SYNTAX	INTEGER
	ACCESS	read-only 
	STATUS	mandatory
	DESCRIPTION	
		"Read the mask state. DEFINED ONLY FOR TESTS."
	::= { dialerControlEntry 18 }


-- ****************************************************************************
--		Dialer ISDN Status Table
-- ****************************************************************************


dialerIsdnStatusTable		OBJECT-TYPE    
	SYNTAX	SEQUENCE OF  DialerIsdnStatusEntry
	ACCESS	not-accessible
	STATUS	mandatory
	DESCRIPTION	
		"The table for ISDN dialer Status."
	::= { dialer 11 }

dialerIsdnStatusEntry		OBJECT-TYPE
	SYNTAX	DialerIsdnStatusEntry
	ACCESS	not-accessible
	STATUS	mandatory
	DESCRIPTION	
		"The set of attributes for one port."
	INDEX		{ dialerIsdnStatusPortRef }
	::= { dialerIsdnStatusTable 1 }
   
DialerIsdnStatusEntry ::= SEQUENCE {
	dialerIsdnStatusPortRef
		PortRef,
	dialerIsdnStatusSwitchType
		INTEGER,
	dialerIsdnStatusChType
		INTEGER,
	dialerIsdnStatusL1State
                INTEGER,
        dialerIsdnStatusState
		INTEGER
	}

dialerIsdnStatusPortRef	OBJECT-TYPE
	SYNTAX	PortRef
	ACCESS	read-only 
	STATUS	mandatory
	DESCRIPTION	
		"The port number for which isdn status is displayed."
	::= { dialerIsdnStatusEntry 1 }

dialerIsdnStatusSwitchType  OBJECT-TYPE	
	SYNTAX	INTEGER {
		ni1 (1),
		nt (2),
		att (3),
		tr6 (4),
		vn3 (5),
		net3 (6),
		tph (7),
		illegal (8)
	}
	ACCESS	read-only 
	STATUS	mandatory
	DESCRIPTION	
		"The current switch type in use for isdn. "
	::= { dialerIsdnStatusEntry 2 }

dialerIsdnStatusChType OBJECT-TYPE	
	SYNTAX	INTEGER {
		b-channel (1),
		d-channel (2),
		illegal (3),
		unused (4)
	}
	ACCESS	read-only 
	STATUS	mandatory
	DESCRIPTION	
		"The isdn channel type, B channel or D channel. "
	::= { dialerIsdnStatusEntry 3 }

dialerIsdnStatusL1State	  OBJECT-TYPE
	SYNTAX	INTEGER {
		deactivated (1),
		await-info2 (2),
		await-info4 (3),
		activate (4),
		illegal (5)
	}
	ACCESS	read-only 
	STATUS	mandatory
	DESCRIPTION	
		" The current state of layer 1 subsystem. "
	::= { dialerIsdnStatusEntry 4 }

dialerIsdnStatusState   OBJECT-TYPE
	SYNTAX	INTEGER {
                isdn-deact-closed (1),
                isdn-deact-opened (2),
                isdn-wait-act-closed (3),
                isdn-wait-act-opened (4),
                isdn-release-closed (5),
                isdn-release-opened (6),
                isdn-closed (7),
                isdn-opened (8),
                isdn-connecting (9),
                isdn-connected (10),
                isdn-ringing (11),
                isdn-disconnecting (12),
                isdn-closing (13),
                isdn-loopback (14),
                isdn-linking-deact (15),
		isdn-linking-act (16),
		isdn-test (17),
		isdn-linking-ring (18),
		isdn-illegal (19)
	}
	ACCESS	read-only
	STATUS	mandatory
	DESCRIPTION
		" The current state of the ISDN dialer. "
	::= { dialerIsdnStatusEntry 5 }

-- ****************************************************************************
--		Dialer ISDN NI1B Channel Table
-- ****************************************************************************

dialerIsdnNI1BChTable		OBJECT-TYPE
	SYNTAX	SEQUENCE OF  DialerIsdnNI1BChEntry
	ACCESS	not-accessible
	STATUS	mandatory
	DESCRIPTION
		"The table for the ISDN NI1 BChannel dialer."
	::= { dialer 12 }

dialerIsdnNI1BChEntry		OBJECT-TYPE
	SYNTAX	DialerIsdnNI1BChEntry
	ACCESS	not-accessible
	STATUS	mandatory
	DESCRIPTION	
		"The set of attributes for one port."
	INDEX		{ dialerIsdnNI1BChPortRef }
	::= { dialerIsdnNI1BChTable 1 }
   
DialerIsdnNI1BChEntry ::= SEQUENCE {
	dialerIsdnNI1BChPortRef
		PortRef,
	dialerIsdnNI1BChSpid
		DisplayString, 
	dialerIsdnNI1BChSpidStatus
		IsdnSpidStatus, 
	dialerIsdnNI1BChLocalDn
		DisplayString, 
	dialerIsdnNI1BChLocalSub
		DisplayString, 
	dialerIsdnNI1BChTnsDigs
		DisplayString, 
	dialerIsdnNI1BChRemoteDn
		DisplayString, 
	dialerIsdnNI1BChRemoteSub
		DisplayString, 
	dialerIsdnNI1BChCallType
		IsdnCallType,
	dialerIsdnNI1BChCallSpeed
		IsdnCallSpeed,
	dialerIsdnNI1BChBChannel
		IsdnBChannels, 
	dialerIsdnNI1BChAnsEnable
		IsdnAnsEnable,
	dialerIsdnNI1BChCcState
		IsdnNI1BCcState, 
	dialerIsdnNI1BChCcNbCause
		INTEGER, 
	dialerIsdnNI1BChCcCause
		OCTET STRING, 
	dialerIsdnNI1BChL3State
		IsdnL3State, 
	dialerIsdnNI1BChL2State
		IsdnL2State, 
	dialerIsdnNI1BChTeiValue
		INTEGER,
	dialerIsdnNI1BChTeiStatus
		IsdnTeiStatus,
	dialerIsdnNI1BChLocalDnType
		IsdnDnType,
	dialerIsdnNI1BChLocalDnPlan
		IsdnDnPlan,
	dialerIsdnNI1BChLocalSubType
		IsdnSubType,
	dialerIsdnNI1BChTnsNetId
		IsdnTnsNetId,
	dialerIsdnNI1BChTnsIdPlan
		IsdnTnsIdPlan,
	dialerIsdnNI1BChRemoteDnType
		IsdnDnType,
	dialerIsdnNI1BChRemoteDnPlan
		IsdnDnPlan,
	dialerIsdnNI1BChRemoteSubType
		IsdnSubType,
	dialerIsdnNI1BChScrStatus
		IsdnScrStatus,
	dialerIsdnNI1BChCallOpt
		IsdnCallOpt,
	dialerIsdnNI1BChStoDefined
		IsdnStoDefined,
	dialerIsdnNI1BChStoDnType
		INTEGER,
	dialerIsdnNI1BChStoDnPlan
		INTEGER,
	dialerIsdnNI1BChStoDn
		DisplayString, 
	dialerIsdnNI1BChStoSubType
		INTEGER,
	dialerIsdnNI1BChStoSub
		DisplayString,
	dialerIsdnNI1BChStoTnsNetId
		INTEGER,
	dialerIsdnNI1BChStoTnsPlan
		INTEGER,
	dialerIsdnNI1BChStoDigs
		DisplayString, 
	dialerIsdnNI1BChStoBcType
		INTEGER,
	dialerIsdnNI1BChStoBcOpt
		INTEGER
	}

dialerIsdnNI1BChPortRef	OBJECT-TYPE
	SYNTAX	PortRef	
	ACCESS	read-only 
	STATUS	mandatory
	DESCRIPTION	
		" The port number which is configured for NI1-BChannel."
	::= { dialerIsdnNI1BChEntry 1 }

dialerIsdnNI1BChSpid	OBJECT-TYPE
	SYNTAX	DisplayString (SIZE (0..21))
	ACCESS	read-only 
	STATUS	mandatory
	DESCRIPTION	
		" The Terminal's Service Profile IDentification."
	::= { dialerIsdnNI1BChEntry 2 }

dialerIsdnNI1BChSpidStatus	OBJECT-TYPE
	SYNTAX 	IsdnSpidStatus
	ACCESS	read-only 
	STATUS	mandatory
	DESCRIPTION	
		"The current SPID status. "
	::= { dialerIsdnNI1BChEntry 3 }

dialerIsdnNI1BChLocalDn	OBJECT-TYPE
	SYNTAX	DisplayString (SIZE (0..21))
	ACCESS	read-only 
	STATUS	mandatory
	DESCRIPTION	
		"The local directory number type. "
	::= { dialerIsdnNI1BChEntry 4 }


dialerIsdnNI1BChLocalSub	OBJECT-TYPE
	SYNTAX	DisplayString (SIZE (0..21))
	ACCESS	read-only 
	STATUS	mandatory
	DESCRIPTION	
		"The local subaddress. "
	::= { dialerIsdnNI1BChEntry 5 }

dialerIsdnNI1BChTnsDigs OBJECT-TYPE
	SYNTAX	DisplayString (SIZE (0..16))
	ACCESS	read-write 
	STATUS	mandatory
	DESCRIPTION	
		"The string identifying the selected long distance carrier. In ISDN 
		terms, it is called the Transit Network Selection. This string 
		is usually made of 3 digits and is assigned by Bellcore."
	::= { dialerIsdnNI1BChEntry 6 }

dialerIsdnNI1BChRemoteDn	OBJECT-TYPE
	SYNTAX	DisplayString (SIZE (0..21))
	ACCESS	read-write 
	STATUS	mandatory
	DESCRIPTION	
		"When in the connected state, the number dialed is displayed.
		 Otherwise, the stored number is displayed."
	::= { dialerIsdnNI1BChEntry 7 }

dialerIsdnNI1BChRemoteSub	OBJECT-TYPE
	SYNTAX	DisplayString (SIZE (0..21))	
	ACCESS	read-write 		      	
	STATUS	mandatory
	DESCRIPTION	
		"When in the connected state, the remote subaddress dialer is
		 displayed. Otherwise, the stored subaddress is displayed."
	::= { dialerIsdnNI1BChEntry 8 }

dialerIsdnNI1BChCallType	OBJECT-TYPE
	SYNTAX	IsdnCallType
	ACCESS	read-only 
	STATUS	mandatory
	DESCRIPTION	
		"The current call type. "
	::= { dialerIsdnNI1BChEntry 9 }

dialerIsdnNI1BChCallSpeed	OBJECT-TYPE
	SYNTAX	IsdnCallSpeed
	ACCESS	read-write 
	STATUS	mandatory
	DESCRIPTION	
		"The current call speed. "
	::= { dialerIsdnNI1BChEntry 10 }

dialerIsdnNI1BChBChannel	OBJECT-TYPE
	SYNTAX	IsdnBChannels
	ACCESS	read-only 
	STATUS	mandatory
	DESCRIPTION	
		" The current B channel connected to."
	::= { dialerIsdnNI1BChEntry 11 }

dialerIsdnNI1BChAnsEnable	OBJECT-TYPE
	SYNTAX	IsdnAnsEnable
	ACCESS	read-only 
	STATUS	mandatory
	DESCRIPTION	
		" Answer Enable Status."
	::= { dialerIsdnNI1BChEntry 12 }

dialerIsdnNI1BChCcState	OBJECT-TYPE
	SYNTAX 	IsdnNI1BCcState
	ACCESS	read-only 
	STATUS	mandatory
	DESCRIPTION	
		"The state of call control subsystem. "
	::= { dialerIsdnNI1BChEntry 13 }

dialerIsdnNI1BChCcNbCause	OBJECT-TYPE
	SYNTAX	INTEGER 	
	ACCESS	read-only 
	STATUS	mandatory
	DESCRIPTION	
		"The number of causes saved. "
	::= { dialerIsdnNI1BChEntry 14 }

dialerIsdnNI1BChCcCause	OBJECT-TYPE
	SYNTAX	OCTET STRING  (SIZE (0..10)) 	
	ACCESS	read-only 
	STATUS	mandatory
	DESCRIPTION	
		"Last causes saved. "
	::= { dialerIsdnNI1BChEntry 15 }

dialerIsdnNI1BChL3State	OBJECT-TYPE
	SYNTAX	IsdnL3State 	
	ACCESS	read-only 
	STATUS	mandatory
	DESCRIPTION	
		"The state of layer 3 subsystem. "
	::= { dialerIsdnNI1BChEntry 16 }

dialerIsdnNI1BChL2State	OBJECT-TYPE
	SYNTAX	IsdnL2State 	
	ACCESS	read-only 
	STATUS	mandatory
	DESCRIPTION	
		"The state of layer 2 subsystem. "
	::= { dialerIsdnNI1BChEntry 17 }

dialerIsdnNI1BChTeiValue	OBJECT-TYPE
	SYNTAX	INTEGER	
	ACCESS	read-only 				
	STATUS	mandatory
	DESCRIPTION	
		"The value of the terminal is dynamic TEI. "
	::= { dialerIsdnNI1BChEntry 18 }

dialerIsdnNI1BChTeiStatus	OBJECT-TYPE
	SYNTAX	IsdnTeiStatus	
	ACCESS	read-only 
	STATUS	mandatory
	DESCRIPTION	
		"The status of the terminal's dynamic TEI. "
	::= { dialerIsdnNI1BChEntry 19 }

dialerIsdnNI1BChLocalDnType	OBJECT-TYPE
	SYNTAX	IsdnDnType
	ACCESS  read-only
	STATUS  mandatory
	DESCRIPTION
		"The local directory number type. "
	::= { dialerIsdnNI1BChEntry 20 }

dialerIsdnNI1BChLocalDnPlan       OBJECT-TYPE
	SYNTAX	IsdnDnPlan
	ACCESS  read-only
	STATUS  mandatory
	DESCRIPTION
		"The local directory number plan. "
	::= { dialerIsdnNI1BChEntry 21 }

dialerIsdnNI1BChLocalSubType     OBJECT-TYPE
	SYNTAX	IsdnSubType
	ACCESS  read-only
	STATUS  mandatory
	DESCRIPTION
		"The local subaddress type. "
	::= { dialerIsdnNI1BChEntry 22 }

dialerIsdnNI1BChTnsNetId      	 OBJECT-TYPE
	SYNTAX 	IsdnTnsNetId
	ACCESS  read-only
	STATUS  mandatory
	DESCRIPTION
		"The transit network id. "
	::= { dialerIsdnNI1BChEntry 23 }

dialerIsdnNI1BChTnsIdPlan  	OBJECT-TYPE
	SYNTAX 	IsdnTnsIdPlan
	ACCESS  read-only
	STATUS  mandatory
	DESCRIPTION
		"The transit network plan. "
	::= { dialerIsdnNI1BChEntry 24 }

dialerIsdnNI1BChRemoteDnType	OBJECT-TYPE
	SYNTAX	IsdnDnType
	ACCESS  read-write		   
	STATUS  mandatory
	DESCRIPTION
		"The remote directory number type. "
	::= { dialerIsdnNI1BChEntry 25 }
  
dialerIsdnNI1BChRemoteDnPlan    OBJECT-TYPE
	SYNTAX	IsdnDnPlan
	ACCESS  read-write		    
	STATUS  mandatory
	DESCRIPTION
		"The remote directory number plan. "
	::= { dialerIsdnNI1BChEntry 26 }

dialerIsdnNI1BChRemoteSubType   OBJECT-TYPE
	SYNTAX	IsdnSubType
	ACCESS  read-write 		     
	STATUS  mandatory
	DESCRIPTION
		"The local subaddress type. "
	::= { dialerIsdnNI1BChEntry 27 }

dialerIsdnNI1BChScrStatus  	OBJECT-TYPE
	SYNTAX 	IsdnScrStatus
	ACCESS  read-only
	STATUS  mandatory
	DESCRIPTION
		"The status of call screening. " 
	::= { dialerIsdnNI1BChEntry 28 }

dialerIsdnNI1BChCallOpt  	OBJECT-TYPE
	SYNTAX 	IsdnCallOpt
	ACCESS  read-only
	STATUS  mandatory
	DESCRIPTION
		"The current call option. " 
	::= { dialerIsdnNI1BChEntry 29 }

dialerIsdnNI1BChStoDefined	OBJECT-TYPE
	SYNTAX  IsdnStoDefined
	ACCESS  read-only
	STATUS  mandatory
	DESCRIPTION
		"The validity of  sto- elements. " 
	::= { dialerIsdnNI1BChEntry 30 }

dialerIsdnNI1BChStoDnType	OBJECT-TYPE
	SYNTAX 	INTEGER
	ACCESS  read-only
	STATUS  mandatory
	DESCRIPTION
		"The stored directory number type. " 
	::= { dialerIsdnNI1BChEntry 31 }

dialerIsdnNI1BChStoDnPlan	OBJECT-TYPE
	SYNTAX 	INTEGER
	ACCESS  read-only
	STATUS  mandatory
	DESCRIPTION
		"The stored directory number plan. " 
	::= { dialerIsdnNI1BChEntry 32 }

dialerIsdnNI1BChStoDn		OBJECT-TYPE
	SYNTAX 	DisplayString (SIZE (0..21))	
	ACCESS  read-only
	STATUS  mandatory
	DESCRIPTION
		"The stored directory number. " 
	::= { dialerIsdnNI1BChEntry 33 }

dialerIsdnNI1BChStoSubType	OBJECT-TYPE
	SYNTAX 	INTEGER
	ACCESS  read-only
	STATUS  mandatory
	DESCRIPTION
		"The stored subaddress type. " 
	::= { dialerIsdnNI1BChEntry 34 }

dialerIsdnNI1BChStoSub		OBJECT-TYPE
	SYNTAX 	DisplayString (SIZE (0..21))	
	ACCESS  read-only
	STATUS  mandatory
	DESCRIPTION
		"The stored subaddress. " 
	::= { dialerIsdnNI1BChEntry 35 }

dialerIsdnNI1BChStoTnsNetId	 OBJECT-TYPE
	SYNTAX 	INTEGER
	ACCESS  read-only
	STATUS  mandatory
	DESCRIPTION
		"The stored transit network id. " 
	::= { dialerIsdnNI1BChEntry 36 }

dialerIsdnNI1BChStoTnsPlan	 OBJECT-TYPE
	SYNTAX 	INTEGER
	ACCESS  read-only
	STATUS  mandatory
	DESCRIPTION
		"The stored transit network plan. " 
	::= { dialerIsdnNI1BChEntry 37 }

dialerIsdnNI1BChStoDigs		 OBJECT-TYPE
	SYNTAX 	DisplayString (SIZE (0..16))	
	ACCESS  read-only
	STATUS  mandatory
	DESCRIPTION
		"The stored transit network address. " 
	::= { dialerIsdnNI1BChEntry 38 }

dialerIsdnNI1BChStoBcType	OBJECT-TYPE
	SYNTAX 	INTEGER
	ACCESS  read-only
	STATUS  mandatory
	DESCRIPTION
		"The stored bearer cap. type. " 
	::= { dialerIsdnNI1BChEntry 39 }

dialerIsdnNI1BChStoBcOpt	OBJECT-TYPE
	SYNTAX 	INTEGER
	ACCESS  read-only
	STATUS  mandatory
	DESCRIPTION
		"The stored bearer cap. option. " 
	::= { dialerIsdnNI1BChEntry 40 }

-- ****************************************************************************
--		Dialer ISDN NI1D Channel Table
-- ****************************************************************************

dialerIsdnNI1DChTable		OBJECT-TYPE    
	SYNTAX	SEQUENCE OF  DialerIsdnNI1DChEntry
	ACCESS	not-accessible
	STATUS	mandatory
	DESCRIPTION	
		"The table for the ISDN NI1 DChannel dialer."
	::= { dialer 13 }

dialerIsdnNI1DChEntry		OBJECT-TYPE
	SYNTAX	DialerIsdnNI1DChEntry
	ACCESS	not-accessible
	STATUS	mandatory
	DESCRIPTION	
		"The set of attributes for one port."
	INDEX		{ dialerIsdnNI1DChPortRef }
	::= { dialerIsdnNI1DChTable 1 }
   
DialerIsdnNI1DChEntry ::= SEQUENCE {
	dialerIsdnNI1DChPortRef
		PortRef,
	dialerIsdnNI1DChTeiValue
		INTEGER,
	dialerIsdnNI1DChTeiStatus
		IsdnTeiStatus,
	dialerIsdnNI1DChL2State
		IsdnL2State, 
	dialerIsdnNI1DChP3State
		IsdnP3State,
	dialerIsdnNI1DChActState
		IsdnActState
	}

dialerIsdnNI1DChPortRef  OBJECT-TYPE	
	SYNTAX  PortRef	
	ACCESS	read-only 
	STATUS	mandatory
	DESCRIPTION	
		"The port number configured for the NI1 DChannel."
	::= { dialerIsdnNI1DChEntry 1 }

dialerIsdnNI1DChTeiValue	OBJECT-TYPE	
	SYNTAX  INTEGER	
	ACCESS	read-only 
	STATUS	mandatory
	DESCRIPTION	
		" The static TEI value on the D Channel for data communications."																	 
	::= { dialerIsdnNI1DChEntry 2 }

dialerIsdnNI1DChTeiStatus	OBJECT-TYPE	
	SYNTAX  IsdnTeiStatus	
	ACCESS	read-only 
	STATUS	mandatory
	DESCRIPTION	
		" The status of TEI - always ASSIGNED."
	::= { dialerIsdnNI1DChEntry 3 }

dialerIsdnNI1DChL2State	OBJECT-TYPE	
	SYNTAX  IsdnL2State 	
	ACCESS	read-only 
	STATUS	mandatory
	DESCRIPTION	
		"The current layer 2 state. "
	::= { dialerIsdnNI1DChEntry 4 }

dialerIsdnNI1DChP3State	OBJECT-TYPE	
	SYNTAX  IsdnP3State  	
	ACCESS	read-only 
	STATUS	mandatory
	DESCRIPTION	
		"The current Packet layer state. "
	::= { dialerIsdnNI1DChEntry 5 }

dialerIsdnNI1DChActState OBJECT-TYPE	
	SYNTAX  IsdnActState
	ACCESS	read-only 
	STATUS	mandatory
	DESCRIPTION	
		"The current activation FSM state. "
	::= { dialerIsdnNI1DChEntry 6 }

-- ****************************************************************************
--		Dialer ISDN TR6 BChannel Table
-- ****************************************************************************

dialerIsdnTR6BChTable		OBJECT-TYPE    
	SYNTAX	SEQUENCE OF  DialerIsdnTR6BChEntry
	ACCESS	not-accessible
	STATUS	mandatory
	DESCRIPTION	
		"The table for the ISDN TR6 BChannel dialer."
	::= { dialer 14 }

dialerIsdnTR6BChEntry		OBJECT-TYPE
	SYNTAX	DialerIsdnTR6BChEntry
	ACCESS	not-accessible
	STATUS	mandatory
	DESCRIPTION	
		"The set of attributes for one port."
	INDEX		{ dialerIsdnTR6BChPortRef }
	::= { dialerIsdnTR6BChTable 1 }
   
DialerIsdnTR6BChEntry ::= SEQUENCE {
	dialerIsdnTR6BChPortRef
		PortRef,
	dialerIsdnTR6BChLocalDn
		DisplayString,
	dialerIsdnTR6BChRemoteDn
		DisplayString,
	dialerIsdnTR6BChCallType
		IsdnCallType, 
	dialerIsdnTR6BChCallSpeed
		IsdnCallSpeed, 
	dialerIsdnTR6BChBChannel
		IsdnBChannels, 
	dialerIsdnTR6BChAnsEnable
 		IsdnAnsEnable,				 
	dialerIsdnTR6BChCcState
		IsdnTR6BCcState,		
	dialerIsdnTR6BChCcNbCause
		INTEGER, 
	dialerIsdnTR6BChCcCause
		OCTET STRING, 
	dialerIsdnTR6BChL3State
		IsdnL3State, 
	dialerIsdnTR6BChL2State
		IsdnL2State, 
	dialerIsdnTR6BChLocalDnType
		IsdnDnType, 
	dialerIsdnTR6BChLocalDnPlan
	        IsdnDnPlan,
	dialerIsdnTR6BChRemoteDnType
		IsdnDnType, 
	dialerIsdnTR6BChRemoteDnPlan
	        IsdnDnPlan,
	dialerIsdnTR6BChScrStatus
	        IsdnScrStatus,
	dialerIsdnTR6BChCallOpt
		IsdnCallOpt,
	dialerIsdnTR6BChTeiValue		
		INTEGER,
	dialerIsdnTR6BChTeiStatus
		IsdnTeiStatus,
	dialerIsdnTR6BChStoDefined
		IsdnStoDefined,
	dialerIsdnTR6BChStoDnType
		INTEGER,
	dialerIsdnTR6BChStoDnPlan
		INTEGER,
	dialerIsdnTR6BChStoDn
		DisplayString, 
	dialerIsdnTR6BChStoBcType
		INTEGER,
	dialerIsdnTR6BChStoBcOpt
		INTEGER
   }

dialerIsdnTR6BChPortRef  OBJECT-TYPE
	SYNTAX  PortRef
	ACCESS	read-only 
	STATUS	mandatory
	DESCRIPTION	
		"The port number for which the 1TR6 BChannel info is displayed. "
	::= { dialerIsdnTR6BChEntry 1 }

dialerIsdnTR6BChLocalDn  OBJECT-TYPE	
	SYNTAX  DisplayString (SIZE (0..21))
	ACCESS	read-only 
	STATUS	mandatory
	DESCRIPTION	
		"The local directory number type. "
	::= { dialerIsdnTR6BChEntry 2 }

dialerIsdnTR6BChRemoteDn OBJECT-TYPE	
	SYNTAX  DisplayString  (SIZE (0..21))
	ACCESS	read-write 
	STATUS	mandatory
	DESCRIPTION	
		"When in the connected state, the number dialed is displayed.
		 Otherwise, the stored number is displayed."
	::= { dialerIsdnTR6BChEntry 3 }

dialerIsdnTR6BChCallType OBJECT-TYPE	
	SYNTAX  IsdnCallType
	ACCESS	read-only 
	STATUS	mandatory
	DESCRIPTION	
		"The current call type. "
	::= { dialerIsdnTR6BChEntry 4 }

dialerIsdnTR6BChCallSpeed OBJECT-TYPE	
	SYNTAX  IsdnCallSpeed
	ACCESS	read-write 
	STATUS	mandatory
	DESCRIPTION	
		"The current call speed. "
	::= { dialerIsdnTR6BChEntry 5 }

dialerIsdnTR6BChBChannel  OBJECT-TYPE	
	SYNTAX  IsdnBChannels
	ACCESS	read-only 
	STATUS	mandatory
	DESCRIPTION	
		"The current B Channel connected to. "
	::= { dialerIsdnTR6BChEntry 6 }

dialerIsdnTR6BChAnsEnable OBJECT-TYPE	
	SYNTAX 	IsdnAnsEnable
	ACCESS	read-only 
	STATUS	mandatory
	DESCRIPTION	
		"Answer enable status. "
	::= { dialerIsdnTR6BChEntry 7 }

dialerIsdnTR6BChCcState   OBJECT-TYPE
	SYNTAX  IsdnTR6BCcState	 
	ACCESS	read-only 
	STATUS	mandatory
	DESCRIPTION	
		"The state of call control subsystem."
	::= { dialerIsdnTR6BChEntry 8 }

dialerIsdnTR6BChCcNbCause OBJECT-TYPE	
	SYNTAX  INTEGER
	ACCESS	read-only 
	STATUS	mandatory
	DESCRIPTION	
		"The number of causes saved."
	::= { dialerIsdnTR6BChEntry 9 }

dialerIsdnTR6BChCcCause   OBJECT-TYPE	
	SYNTAX  OCTET STRING  (SIZE (0..10))
	ACCESS	read-only 
	STATUS	mandatory
	DESCRIPTION	
		"Last causes saved. "
	::= { dialerIsdnTR6BChEntry 10 }

dialerIsdnTR6BChL3State   OBJECT-TYPE	
	SYNTAX  IsdnL3State
	ACCESS	read-only 
	STATUS	mandatory
	DESCRIPTION	
		"The state of layer 3 subsystem. "
	::= { dialerIsdnTR6BChEntry 11 }

dialerIsdnTR6BChL2State   OBJECT-TYPE	
 	SYNTAX  IsdnL2State 	
	ACCESS	read-only 
	STATUS	mandatory
	DESCRIPTION	
		"The state of layer 2 subsystem. "
	::= { dialerIsdnTR6BChEntry 12 }

dialerIsdnTR6BChLocalDnType OBJECT-TYPE	
	SYNTAX  IsdnDnType 	      
	ACCESS	read-only 
	STATUS	mandatory
	DESCRIPTION	
		"The local directory number type. "
	::= { dialerIsdnTR6BChEntry 13 }


dialerIsdnTR6BChLocalDnPlan OBJECT-TYPE	
	SYNTAX  IsdnDnPlan
	ACCESS	read-only 
	STATUS	mandatory
	DESCRIPTION	
		"The local directory number plan. "
	::= { dialerIsdnTR6BChEntry 14 }

dialerIsdnTR6BChRemoteDnType OBJECT-TYPE	
	SYNTAX  IsdnDnType 	      
	ACCESS	read-write 
	STATUS	mandatory
	DESCRIPTION	
		"The remote directory number type. "
	::= { dialerIsdnTR6BChEntry 15 }

dialerIsdnTR6BChRemoteDnPlan OBJECT-TYPE	
	SYNTAX  IsdnDnPlan
	ACCESS	read-write 
	STATUS	mandatory
	DESCRIPTION	
		"The remote directory number plan. "
	::= { dialerIsdnTR6BChEntry 16 }

dialerIsdnTR6BChScrStatus OBJECT-TYPE	
	SYNTAX  IsdnScrStatus
	ACCESS	read-only 
	STATUS	mandatory
	DESCRIPTION	
		"The status of call screening. "
	::= { dialerIsdnTR6BChEntry 17 }

dialerIsdnTR6BChCallOpt  	OBJECT-TYPE
	SYNTAX 	IsdnCallOpt
	ACCESS  read-only
	STATUS  mandatory
	DESCRIPTION
		"The current call option. " 
	::= { dialerIsdnTR6BChEntry 18 }

dialerIsdnTR6BChTeiValue     	OBJECT-TYPE	
	SYNTAX  INTEGER	
	ACCESS	read-only 
	STATUS	mandatory
	DESCRIPTION	
		" The static TEI value on the D Channel for data communications."																	 
	::= { dialerIsdnTR6BChEntry 19 }

dialerIsdnTR6BChTeiStatus	OBJECT-TYPE	
	SYNTAX  IsdnTeiStatus	
	ACCESS	read-only 
	STATUS	mandatory
	DESCRIPTION	
		" The status of TEI - always ASSIGNED."
	::= { dialerIsdnTR6BChEntry 20 }

dialerIsdnTR6BChStoDefined	OBJECT-TYPE
	SYNTAX  IsdnStoDefined
	ACCESS  read-only
	STATUS  mandatory
	DESCRIPTION
		"The validity of  sto- elements. " 
	::= { dialerIsdnTR6BChEntry 21 }

dialerIsdnTR6BChStoDnType	OBJECT-TYPE
	SYNTAX 	INTEGER
	ACCESS  read-only
	STATUS  mandatory
	DESCRIPTION
		"The stored directory number type. " 
	::= { dialerIsdnTR6BChEntry 22 }

dialerIsdnTR6BChStoDnPlan	OBJECT-TYPE
	SYNTAX 	INTEGER
	ACCESS  read-only
	STATUS  mandatory
	DESCRIPTION
		"The stored directory number plan. " 
	::= { dialerIsdnTR6BChEntry 23 }

dialerIsdnTR6BChStoDn		OBJECT-TYPE
	SYNTAX 	DisplayString (SIZE (0..21))	
	ACCESS  read-only
	STATUS  mandatory
	DESCRIPTION
		"The stored directory number. " 
	::= { dialerIsdnTR6BChEntry 24 }

dialerIsdnTR6BChStoBcType	OBJECT-TYPE
	SYNTAX 	INTEGER
	ACCESS  read-only
	STATUS  mandatory
	DESCRIPTION
		"The stored bearer cap. type. " 
	::= { dialerIsdnTR6BChEntry 25 }

dialerIsdnTR6BChStoBcOpt	OBJECT-TYPE
	SYNTAX 	INTEGER
	ACCESS  read-only
	STATUS  mandatory
	DESCRIPTION
		"The stored bearer cap. option. " 
	::= { dialerIsdnTR6BChEntry 26 }

-- ****************************************************************************
--		Dialer ISDN VN3 BChannel Table
-- ****************************************************************************

dialerIsdnVN3BChTable		OBJECT-TYPE    
	SYNTAX	SEQUENCE OF  DialerIsdnVN3BChEntry
	ACCESS	not-accessible
	STATUS	mandatory
	DESCRIPTION	
		"The table for the ISDN VN3 BChannel dialer."
	::= { dialer 15 }

dialerIsdnVN3BChEntry		OBJECT-TYPE
	SYNTAX	DialerIsdnVN3BChEntry
	ACCESS	not-accessible
	STATUS	mandatory
	DESCRIPTION	
		"The set of attributes for one port."
	INDEX		{ dialerIsdnVN3BChPortRef }
	::= { dialerIsdnVN3BChTable 1 }

DialerIsdnVN3BChEntry ::= SEQUENCE {
  	dialerIsdnVN3BChPortRef
		PortRef,
	dialerIsdnVN3BChLocalDnType
		IsdnDnType,
	dialerIsdnVN3BChLocalDnPlan
		IsdnDnPlan,
	dialerIsdnVN3BChLocalDn
		DisplayString,
	dialerIsdnVN3BChLocalSubType
		IsdnSubType,
	dialerIsdnVN3BChLocalSub
		DisplayString, 
	dialerIsdnVN3BChRemoteDnType
		IsdnDnType,
	dialerIsdnVN3BChRemoteDnPlan
		IsdnDnPlan,
	dialerIsdnVN3BChRemoteDn
		DisplayString,
	dialerIsdnVN3BChRemoteSubType
		IsdnSubType,
	dialerIsdnVN3BChRemoteSub
		DisplayString, 
	dialerIsdnVN3BChCallType
		IsdnCallType, 
	dialerIsdnVN3BChCallSpeed
		IsdnCallSpeed, 
	dialerIsdnVN3BChBChannel
		IsdnBChannels, 
	dialerIsdnVN3BChAnsEnable
		IsdnAnsEnable,			 
	dialerIsdnVN3BChScrStatus
	        IsdnScrStatus,
	dialerIsdnVN3BChCallOpt
		IsdnCallOpt,
	dialerIsdnVN3BChCcState
		IsdnVN3BCcState,
	dialerIsdnVN3BChCcNbCause
		INTEGER, 
	dialerIsdnVN3BChCcCause
		OCTET STRING, 
	dialerIsdnVN3BChL3State	
		IsdnL3State,
	dialerIsdnVN3BChL2State 
		IsdnL2State,
	dialerIsdnVN3BChTeiValue 
		INTEGER,
	dialerIsdnVN3BChTeiStatus	
       		IsdnTeiStatus,
	dialerIsdnVN3BChStoDefined
		IsdnStoDefined,
	dialerIsdnVN3BChStoDnType
		INTEGER,
	dialerIsdnVN3BChStoDnPlan
		INTEGER,
	dialerIsdnVN3BChStoDn
		DisplayString, 
	dialerIsdnVN3BChStoSubType
		INTEGER,
	dialerIsdnVN3BChStoSub
		DisplayString,
	dialerIsdnVN3BChStoBcType
		INTEGER,
	dialerIsdnVN3BChStoBcOpt
		INTEGER
       }

dialerIsdnVN3BChPortRef  	OBJECT-TYPE
	SYNTAX  PortRef
	ACCESS	read-only 
	STATUS	mandatory
	DESCRIPTION	
		"The port number for which the VN3 BChannel info is displayed. "
	::= { dialerIsdnVN3BChEntry 1 }

dialerIsdnVN3BChLocalDnType 	OBJECT-TYPE	
	SYNTAX  IsdnDnType 	      
	ACCESS	read-only 
	STATUS	mandatory
	DESCRIPTION	
		"The local directory number type. "
	::= { dialerIsdnVN3BChEntry 2 }

dialerIsdnVN3BChLocalDnPlan 	OBJECT-TYPE	
	SYNTAX  IsdnDnPlan
	ACCESS	read-only 
	STATUS	mandatory
	DESCRIPTION	
		"The local directory number plan. "
	::= { dialerIsdnVN3BChEntry 3 }

dialerIsdnVN3BChLocalDn  	OBJECT-TYPE	
	SYNTAX  DisplayString (SIZE (0..21))
	ACCESS	read-only 
	STATUS	mandatory
	DESCRIPTION	
		"The local directory number type. "
	::= { dialerIsdnVN3BChEntry 4 }

dialerIsdnVN3BChLocalSubType    OBJECT-TYPE
	SYNTAX	IsdnSubType
	ACCESS  read-only
	STATUS  mandatory
	DESCRIPTION
		"The local subaddress type. "
	::= { dialerIsdnVN3BChEntry 5 }

dialerIsdnVN3BChLocalSub	OBJECT-TYPE	
	SYNTAX  DisplayString (SIZE (0..21))
	ACCESS	read-only 
	STATUS	mandatory
	DESCRIPTION	
		"The local directory number type. "
	::= { dialerIsdnVN3BChEntry 6 }

dialerIsdnVN3BChRemoteDnType	OBJECT-TYPE	
	SYNTAX  IsdnDnType 	      
	ACCESS	read-write 
	STATUS	mandatory
	DESCRIPTION	
		"The local directory number type. "
	::= { dialerIsdnVN3BChEntry 7 }

dialerIsdnVN3BChRemoteDnPlan 	OBJECT-TYPE	
	SYNTAX  IsdnDnPlan
	ACCESS	read-write
	STATUS	mandatory
	DESCRIPTION	
		"The local directory number plan. "
	::= { dialerIsdnVN3BChEntry 8 }

dialerIsdnVN3BChRemoteDn  	OBJECT-TYPE	
	SYNTAX  DisplayString (SIZE (0..21))
	ACCESS	read-write           
	STATUS	mandatory
	DESCRIPTION	
		"The local directory number type. "
	::= { dialerIsdnVN3BChEntry 9 }

dialerIsdnVN3BChRemoteSubType     OBJECT-TYPE
	SYNTAX	IsdnSubType
	ACCESS  read-write
	STATUS  mandatory
	DESCRIPTION
		"The local subaddress type. "
	::= { dialerIsdnVN3BChEntry 10 }

dialerIsdnVN3BChRemoteSub	OBJECT-TYPE	
	SYNTAX  DisplayString (SIZE (0..21))
	ACCESS	read-write
	STATUS	mandatory
	DESCRIPTION	
		"The local directory number type. "
	::= { dialerIsdnVN3BChEntry 11 }

dialerIsdnVN3BChCallType 	OBJECT-TYPE	
	SYNTAX  IsdnCallType
	ACCESS	read-only 
	STATUS	mandatory
	DESCRIPTION	
		"The current call type. "
	::= { dialerIsdnVN3BChEntry 12 }

dialerIsdnVN3BChCallSpeed 	OBJECT-TYPE	
	SYNTAX  IsdnCallSpeed
	ACCESS	read-write 
	STATUS	mandatory
	DESCRIPTION	
		"The current call speed. "
	::= { dialerIsdnVN3BChEntry 13 }

dialerIsdnVN3BChBChannel  	OBJECT-TYPE	
	SYNTAX  IsdnBChannels
	ACCESS	read-only 
	STATUS	mandatory
	DESCRIPTION	
		"The current B Channel connected to. "
	::= { dialerIsdnVN3BChEntry 14 }

dialerIsdnVN3BChAnsEnable 	OBJECT-TYPE	
	SYNTAX 	IsdnAnsEnable
	ACCESS	read-only 
	STATUS	mandatory
	DESCRIPTION	
		"Answer enable status. "
	::= { dialerIsdnVN3BChEntry 15 }

dialerIsdnVN3BChScrStatus	 OBJECT-TYPE	
	SYNTAX  IsdnScrStatus
	ACCESS	read-only 
	STATUS	mandatory
	DESCRIPTION	
		"The status of call screening. "
	::= { dialerIsdnVN3BChEntry 16 }

dialerIsdnVN3BChCallOpt  	OBJECT-TYPE
	SYNTAX 	IsdnCallOpt
	ACCESS  read-only
	STATUS  mandatory
	DESCRIPTION
		"The current call option. " 
	::= { dialerIsdnVN3BChEntry 17 }

dialerIsdnVN3BChCcState  	OBJECT-TYPE
	SYNTAX 	IsdnVN3BCcState
	ACCESS  read-only
	STATUS  mandatory
	DESCRIPTION
		"The state of call control subsystem."
	::= { dialerIsdnVN3BChEntry 18 }
		
dialerIsdnVN3BChCcNbCause	OBJECT-TYPE	
	SYNTAX  INTEGER
	ACCESS	read-only 
	STATUS	mandatory
	DESCRIPTION	
		"The number of causes saved."
	::= { dialerIsdnVN3BChEntry 19 }

dialerIsdnVN3BChCcCause		OBJECT-TYPE	
	SYNTAX  OCTET STRING  (SIZE (0..10))
	ACCESS	read-only 
	STATUS	mandatory
	DESCRIPTION	
		"Last causes saved. "
	::= { dialerIsdnVN3BChEntry 20 }

dialerIsdnVN3BChL3State   	OBJECT-TYPE	
	SYNTAX  IsdnL3State
	ACCESS	read-only 
	STATUS	mandatory
	DESCRIPTION	
		"The state of layer 3 subsystem. "
	::= { dialerIsdnVN3BChEntry 21 }

dialerIsdnVN3BChL2State   	OBJECT-TYPE	
	SYNTAX  IsdnL2State 	
	ACCESS	read-only 
	STATUS	mandatory
	DESCRIPTION	
		"The state of layer 2 subsystem. "
	::= { dialerIsdnVN3BChEntry 22 }

dialerIsdnVN3BChTeiValue     	OBJECT-TYPE	
	SYNTAX  INTEGER	
	ACCESS	read-only 
	STATUS	mandatory
	DESCRIPTION	
		" The static TEI value on the D Channel for data communications."
	::= { dialerIsdnVN3BChEntry 23 }

dialerIsdnVN3BChTeiStatus	OBJECT-TYPE	
	SYNTAX  IsdnTeiStatus	
	ACCESS	read-only 
	STATUS	mandatory
	DESCRIPTION	
		" The status of TEI - always ASSIGNED."
	::= { dialerIsdnVN3BChEntry 24 }

dialerIsdnVN3BChStoDefined	OBJECT-TYPE
	SYNTAX  IsdnStoDefined
	ACCESS  read-only
	STATUS  mandatory
	DESCRIPTION
		"The validity of  sto- elements. " 
	::= { dialerIsdnVN3BChEntry 25 }

dialerIsdnVN3BChStoDnType	OBJECT-TYPE
	SYNTAX 	INTEGER
	ACCESS  read-only
	STATUS  mandatory
	DESCRIPTION
		"The stored directory number type. " 
	::= { dialerIsdnVN3BChEntry 26 }

dialerIsdnVN3BChStoDnPlan	OBJECT-TYPE
	SYNTAX 	INTEGER
	ACCESS  read-only
	STATUS  mandatory
	DESCRIPTION
		"The stored directory number plan. " 
	::= { dialerIsdnVN3BChEntry 27 }

dialerIsdnVN3BChStoDn		OBJECT-TYPE
	SYNTAX 	DisplayString (SIZE (0..21))	
	ACCESS  read-only
	STATUS  mandatory
	DESCRIPTION
		"The stored directory number. " 
	::= { dialerIsdnVN3BChEntry 28 }

dialerIsdnVN3BChStoSubType	OBJECT-TYPE
	SYNTAX 	INTEGER
	ACCESS  read-only
	STATUS  mandatory
	DESCRIPTION
		"The stored subaddress type. " 
	::= { dialerIsdnVN3BChEntry 29 }

dialerIsdnVN3BChStoSub		OBJECT-TYPE
	SYNTAX 	DisplayString (SIZE (0..21))	
	ACCESS  read-only
	STATUS  mandatory
	DESCRIPTION
		"The stored subaddress. " 
	::= { dialerIsdnVN3BChEntry 30 }

dialerIsdnVN3BChStoBcType	OBJECT-TYPE
	SYNTAX 	INTEGER
	ACCESS  read-only
	STATUS  mandatory
	DESCRIPTION
		"The stored bearer cap type. " 
	::= { dialerIsdnVN3BChEntry 31 }

dialerIsdnVN3BChStoBcOpt	OBJECT-TYPE
	SYNTAX 	INTEGER
	ACCESS  read-only
	STATUS  mandatory
	DESCRIPTION
		"The stored bearer cap option. " 
	::= { dialerIsdnVN3BChEntry 32 }

-- ****************************************************************************
--		Dialer ISDN VN3 DChannel Table
-- ****************************************************************************

dialerIsdnVN3DChTable		OBJECT-TYPE    
	SYNTAX	SEQUENCE OF  DialerIsdnVN3DChEntry
	ACCESS	not-accessible
	STATUS	mandatory
	DESCRIPTION	
		"The table for the ISDN VN3 DChannel dialer."
	::= { dialer 16 }

dialerIsdnVN3DChEntry		OBJECT-TYPE
	SYNTAX	DialerIsdnVN3DChEntry
	ACCESS	not-accessible
	STATUS	mandatory
	DESCRIPTION	
		"The set of attributes for one port."
	INDEX		{ dialerIsdnVN3DChPortRef }
	::= { dialerIsdnVN3DChTable 1 }

DialerIsdnVN3DChEntry ::= SEQUENCE {
	dialerIsdnVN3DChPortRef
		PortRef,
	dialerIsdnVN3DChTeiValue 
		INTEGER,
	dialerIsdnVN3DChTeiStatus	
       		IsdnTeiStatus,
	dialerIsdnVN3DChL2State 
		IsdnL2State,
	dialerIsdnVN3DChP3State
		IsdnP3State
	}

dialerIsdnVN3DChPortRef  	OBJECT-TYPE
	SYNTAX  PortRef
	ACCESS	read-only 
	STATUS	mandatory
	DESCRIPTION	
		"The port number for which the VN3 DChannel info is displayed. "
	::= { dialerIsdnVN3DChEntry 1 }

dialerIsdnVN3DChTeiValue     	OBJECT-TYPE	
	SYNTAX  INTEGER	
	ACCESS	read-only 
	STATUS	mandatory
	DESCRIPTION	
		" The static TEI value on the D Channel for data communications."																	 
	::= { dialerIsdnVN3DChEntry 2 }

dialerIsdnVN3DChTeiStatus	OBJECT-TYPE	
	SYNTAX  IsdnTeiStatus	
	ACCESS	read-only 
	STATUS	mandatory
	DESCRIPTION	
		" The status of TEI - always ASSIGNED."
	::= { dialerIsdnVN3DChEntry 3 }

dialerIsdnVN3DChL2State   	OBJECT-TYPE	
	SYNTAX  IsdnL2State 	
	ACCESS	read-only 
	STATUS	mandatory
	DESCRIPTION	
		"The state of layer 2 subsystem. "
	::= { dialerIsdnVN3DChEntry 4 }
	
dialerIsdnVN3DChP3State		OBJECT-TYPE	
	SYNTAX  IsdnP3State  	
	ACCESS	read-only 
	STATUS	mandatory
	DESCRIPTION	
		"The current Packet layer state. "
	::= { dialerIsdnVN3DChEntry 5 }

-- ****************************************************************************
--		Dialer ISDN NET3 BChannel Table
-- ****************************************************************************

dialerIsdnNET3BChTable		OBJECT-TYPE    
	SYNTAX	SEQUENCE OF  DialerIsdnNET3BChEntry
	ACCESS	not-accessible
	STATUS	mandatory
	DESCRIPTION	
		"The table for the ISDN NET3 BChannel dialer."
	::= { dialer 17 }

dialerIsdnNET3BChEntry		OBJECT-TYPE
	SYNTAX	DialerIsdnNET3BChEntry
	ACCESS	not-accessible
	STATUS	mandatory
	DESCRIPTION	
		"The set of attributes for one port."
	INDEX		{ dialerIsdnNET3BChPortRef }
	::= { dialerIsdnNET3BChTable 1 }

DialerIsdnNET3BChEntry ::= SEQUENCE {
	dialerIsdnNET3BChPortRef
		PortRef,
	dialerIsdnNET3BChLocalDnType
		IsdnDnType,
	dialerIsdnNET3BChLocalDnPlan
		IsdnDnPlan,
	dialerIsdnNET3BChLocalDn
		DisplayString,
	dialerIsdnNET3BChLocalSubType
		IsdnSubType,
	dialerIsdnNET3BChLocalSub
		DisplayString, 
	dialerIsdnNET3BChRemoteDnType
		IsdnDnType,
	dialerIsdnNET3BChRemoteDnPlan
		IsdnDnPlan,
	dialerIsdnNET3BChRemoteDn
		DisplayString,
	dialerIsdnNET3BChRemoteSubType
		IsdnSubType,
	dialerIsdnNET3BChRemoteSub
		DisplayString, 
	dialerIsdnNET3BChCallType  
		IsdnCallType,
	dialerIsdnNET3BChCallSpeed  
		IsdnCallSpeed,
	dialerIsdnNET3BChBChannel
		IsdnBChannels,
	dialerIsdnNET3BChAnsEnable
		IsdnAnsEnable,	 
	dialerIsdnNET3BChTnsNetId
		IsdnTnsNetId,
	dialerIsdnNET3BChTnsIdPlan
		IsdnTnsIdPlan,
	dialerIsdnNET3BChTnsDigs
		DisplayString,
	dialerIsdnNET3BChScrStatus
	        IsdnScrStatus,
	dialerIsdnNET3BChCallOpt
 		IsdnCallOpt,
	dialerIsdnNET3BChCcState
		IsdnNET3BCcState,
	dialerIsdnNET3BChCcNbCause
		INTEGER, 
	dialerIsdnNET3BChCcCause
		OCTET STRING,
	dialerIsdnNET3BChL3State	
		IsdnL3State,
	dialerIsdnNET3BChL2State 
		IsdnL2State,
	dialerIsdnNET3BChTeiValue 
		INTEGER,
	dialerIsdnNET3BChTeiStatus	
       		IsdnTeiStatus,
	dialerIsdnNET3BChStoDefined
		IsdnStoDefined,
	dialerIsdnNET3BChStoDnType
		INTEGER,
	dialerIsdnNET3BChStoDnPlan
		INTEGER,
	dialerIsdnNET3BChStoDn
		DisplayString, 
	dialerIsdnNET3BChStoSubType
		INTEGER,
	dialerIsdnNET3BChStoSub
		DisplayString,
	dialerIsdnNET3BChStoTnsNetId
		INTEGER,
	dialerIsdnNET3BChStoTnsPlan
		INTEGER,
	dialerIsdnNET3BChStoDigs
		DisplayString, 
	dialerIsdnNET3BChStoBcType
		INTEGER,
	dialerIsdnNET3BChStoBcOpt
		INTEGER
       }

dialerIsdnNET3BChPortRef  	OBJECT-TYPE
	SYNTAX  PortRef
	ACCESS	read-only 
	STATUS	mandatory
	DESCRIPTION	
		"The port number for which the NET3 BChannel info is displayed. "
	::= { dialerIsdnNET3BChEntry 1 }

dialerIsdnNET3BChLocalDnType 	OBJECT-TYPE	
	SYNTAX  IsdnDnType 	      
	ACCESS	read-only 
	STATUS	mandatory
	DESCRIPTION	
		"The local directory number type. "
	::= { dialerIsdnNET3BChEntry 2 }

dialerIsdnNET3BChLocalDnPlan 	OBJECT-TYPE	
	SYNTAX  IsdnDnPlan
	ACCESS	read-only 
	STATUS	mandatory
	DESCRIPTION	
		"The local directory number plan. "
	::= { dialerIsdnNET3BChEntry 3 }

dialerIsdnNET3BChLocalDn  	OBJECT-TYPE	
	SYNTAX  DisplayString (SIZE (0..21))
	ACCESS	read-only 
	STATUS	mandatory
	DESCRIPTION	
		"The local directory number type. "
	::= { dialerIsdnNET3BChEntry 4 }

dialerIsdnNET3BChLocalSubType    OBJECT-TYPE
	SYNTAX	IsdnSubType
	ACCESS  read-only
	STATUS  mandatory
	DESCRIPTION
		"The local subaddress type. "
	::= { dialerIsdnNET3BChEntry 5 }

dialerIsdnNET3BChLocalSub	OBJECT-TYPE	
	SYNTAX  DisplayString (SIZE (0..21))
	ACCESS	read-only 
	STATUS	mandatory
	DESCRIPTION	
		"The local directory number type. "
	::= { dialerIsdnNET3BChEntry 6 }

dialerIsdnNET3BChRemoteDnType	OBJECT-TYPE	
	SYNTAX  IsdnDnType 	      
	ACCESS	read-write
	STATUS	mandatory
	DESCRIPTION	
		"The local directory number type. "
	::= { dialerIsdnNET3BChEntry 7 }

dialerIsdnNET3BChRemoteDnPlan 	OBJECT-TYPE	
	SYNTAX  IsdnDnPlan
	ACCESS	read-write
	STATUS	mandatory
	DESCRIPTION	
		"The local directory number plan. "
	::= { dialerIsdnNET3BChEntry 8 }

dialerIsdnNET3BChRemoteDn  	OBJECT-TYPE	
	SYNTAX  DisplayString (SIZE (0..21))
	ACCESS	read-write		   
	STATUS	mandatory
	DESCRIPTION	
		"The local directory number type. "
	::= { dialerIsdnNET3BChEntry 9 }

dialerIsdnNET3BChRemoteSubType     OBJECT-TYPE
	SYNTAX	IsdnSubType
	ACCESS  read-write
	STATUS  mandatory
	DESCRIPTION
		"The local subaddress type. "
	::= { dialerIsdnNET3BChEntry 10 }

dialerIsdnNET3BChRemoteSub	OBJECT-TYPE	
	SYNTAX  DisplayString (SIZE (0..21))
	ACCESS	read-write 
	STATUS	mandatory
	DESCRIPTION	
		"The local directory number type. "
	::= { dialerIsdnNET3BChEntry 11 }

dialerIsdnNET3BChCallType 	OBJECT-TYPE	
	SYNTAX  IsdnCallType
	ACCESS	read-only 
	STATUS	mandatory
	DESCRIPTION	
		"The current call type. "
	::= { dialerIsdnNET3BChEntry 12 }

dialerIsdnNET3BChCallSpeed 	OBJECT-TYPE	
	SYNTAX  IsdnCallSpeed
	ACCESS	read-write 
	STATUS	mandatory
	DESCRIPTION	
		"The current call speed. "
	::= { dialerIsdnNET3BChEntry 13 }

dialerIsdnNET3BChBChannel  	OBJECT-TYPE	
	SYNTAX  IsdnBChannels
	ACCESS	read-only 
	STATUS	mandatory
	DESCRIPTION	
		"The current B Channel connected to. "
	::= { dialerIsdnNET3BChEntry 14 }

dialerIsdnNET3BChAnsEnable 	OBJECT-TYPE	
	SYNTAX 	IsdnAnsEnable 
	ACCESS	read-only 
	STATUS	mandatory
	DESCRIPTION	
		"Answer enable status. "
	::= { dialerIsdnNET3BChEntry 15 }

dialerIsdnNET3BChTnsNetId      	 OBJECT-TYPE
	SYNTAX 	IsdnTnsNetId
	ACCESS  read-only
	STATUS  mandatory
	DESCRIPTION
		"The transit network id. "
	::= { dialerIsdnNET3BChEntry 16 }

dialerIsdnNET3BChTnsIdPlan  	OBJECT-TYPE
	SYNTAX 	IsdnTnsIdPlan
	ACCESS  read-only
	STATUS  mandatory
	DESCRIPTION
		"The transit network plan. "
	::= { dialerIsdnNET3BChEntry 17 }

dialerIsdnNET3BChTnsDigs 	OBJECT-TYPE
	SYNTAX	DisplayString (SIZE (0..16))
	ACCESS	read-write
	STATUS	mandatory
	DESCRIPTION	
		"The string identifying the selected long distance carrier. In ISDN 
		terms, it is called the Transit Network Selection. This string 
		is usually made of 3 digits and is assigned by Bellcore."
	::= { dialerIsdnNET3BChEntry 18 }

dialerIsdnNET3BChScrStatus	 OBJECT-TYPE	
	SYNTAX  IsdnScrStatus
	ACCESS	read-only 
	STATUS	mandatory
	DESCRIPTION	
		"The status of call screening. "
	::= { dialerIsdnNET3BChEntry 19 }

dialerIsdnNET3BChCallOpt  	OBJECT-TYPE
	SYNTAX 	IsdnCallOpt
	ACCESS  read-only
	STATUS  mandatory
	DESCRIPTION
		"The current call option. " 
	::= { dialerIsdnNET3BChEntry 20 }

dialerIsdnNET3BChCcState   OBJECT-TYPE
	SYNTAX  IsdnNET3BCcState	 
	ACCESS	read-only 
	STATUS	mandatory
	DESCRIPTION	
		"The state of call control subsystem."
	::= { dialerIsdnNET3BChEntry 21 }

dialerIsdnNET3BChCcNbCause	OBJECT-TYPE	
	SYNTAX  INTEGER
	ACCESS	read-only 
	STATUS	mandatory
	DESCRIPTION	
		"The number of causes saved."
	::= { dialerIsdnNET3BChEntry 22 }

dialerIsdnNET3BChCcCause     	OBJECT-TYPE	
	SYNTAX  OCTET STRING  (SIZE (0..10))
	ACCESS	read-only 
	STATUS	mandatory
	DESCRIPTION	
		"Last causes saved. "
	::= { dialerIsdnNET3BChEntry 23 }

dialerIsdnNET3BChL3State   	OBJECT-TYPE	
	SYNTAX  IsdnL3State
	ACCESS	read-only 
	STATUS	mandatory
	DESCRIPTION	
		"The state of layer 3 subsystem. "
	::= { dialerIsdnNET3BChEntry 24 }

dialerIsdnNET3BChL2State   	OBJECT-TYPE	
	SYNTAX  IsdnL2State 	
	ACCESS	read-only 
	STATUS	mandatory
	DESCRIPTION	
		"The state of layer 2 subsystem. "
	::= { dialerIsdnNET3BChEntry 25 }

dialerIsdnNET3BChTeiValue     	OBJECT-TYPE	
	SYNTAX  INTEGER	
	ACCESS	read-only 
	STATUS	mandatory
	DESCRIPTION	
		" The static TEI value on the D Channel for data communications."																	 
	::= { dialerIsdnNET3BChEntry 26 }

dialerIsdnNET3BChTeiStatus	OBJECT-TYPE	
	SYNTAX  IsdnTeiStatus	
	ACCESS	read-only 
	STATUS	mandatory
	DESCRIPTION	
		" The status of TEI - always ASSIGNED."
	::= { dialerIsdnNET3BChEntry 27 }

dialerIsdnNET3BChStoDefined	OBJECT-TYPE
	SYNTAX  IsdnStoDefined
	ACCESS  read-only
	STATUS  mandatory
	DESCRIPTION
		"The validity of  sto- elements. " 
	::= { dialerIsdnNET3BChEntry 28 }

dialerIsdnNET3BChStoDnType	OBJECT-TYPE
	SYNTAX 	INTEGER
	ACCESS  read-only
	STATUS  mandatory
	DESCRIPTION
		"The stored directory number type. " 
	::= { dialerIsdnNET3BChEntry 29 }

dialerIsdnNET3BChStoDnPlan	OBJECT-TYPE
	SYNTAX 	INTEGER
	ACCESS  read-only
	STATUS  mandatory
	DESCRIPTION
		"The stored directory number plan. " 
	::= { dialerIsdnNET3BChEntry 30 }

dialerIsdnNET3BChStoDn		OBJECT-TYPE
	SYNTAX 	DisplayString (SIZE (0..21))	
	ACCESS  read-only
	STATUS  mandatory
	DESCRIPTION
		"The stored directory number. " 
	::= { dialerIsdnNET3BChEntry 31 }

dialerIsdnNET3BChStoSubType	OBJECT-TYPE
	SYNTAX 	INTEGER
	ACCESS  read-only
	STATUS  mandatory
	DESCRIPTION
		"The stored subaddress type. " 
	::= { dialerIsdnNET3BChEntry 32 }

dialerIsdnNET3BChStoSub		OBJECT-TYPE
	SYNTAX 	DisplayString (SIZE (0..21))	
	ACCESS  read-only
	STATUS  mandatory
	DESCRIPTION
		"The stored subaddress. " 
	::= { dialerIsdnNET3BChEntry 33 }

dialerIsdnNET3BChStoTnsNetId	 OBJECT-TYPE
	SYNTAX 	INTEGER
	ACCESS  read-only
	STATUS  mandatory
	DESCRIPTION
		"The stored transit network id. " 
	::= { dialerIsdnNET3BChEntry 34 }

dialerIsdnNET3BChStoTnsPlan	 OBJECT-TYPE
	SYNTAX 	INTEGER
	ACCESS  read-only
	STATUS  mandatory
	DESCRIPTION
		"The stored transit network plan. " 
	::= { dialerIsdnNET3BChEntry 35 }

dialerIsdnNET3BChStoDigs		 OBJECT-TYPE
	SYNTAX 	DisplayString (SIZE (0..16))	
	ACCESS  read-only
	STATUS  mandatory
	DESCRIPTION
		"The stored transit network address. " 
	::= { dialerIsdnNET3BChEntry 36 }

dialerIsdnNET3BChStoBcType	OBJECT-TYPE
	SYNTAX 	INTEGER
	ACCESS  read-only
	STATUS  mandatory
	DESCRIPTION
		"The stored bearer cap. type. " 
	::= { dialerIsdnNET3BChEntry 37 }

dialerIsdnNET3BChStoBcOpt	OBJECT-TYPE
	SYNTAX 	INTEGER
	ACCESS  read-only
	STATUS  mandatory
	DESCRIPTION
		"The stored bearer cap. option. " 
	::= { dialerIsdnNET3BChEntry 38 }

-- ****************************************************************************
--		Dialer ISDN TPH BChannel Table
-- ****************************************************************************

dialerIsdnTPHBChTable		OBJECT-TYPE    
	SYNTAX	SEQUENCE OF  DialerIsdnTPHBChEntry
	ACCESS	not-accessible
	STATUS	mandatory
	DESCRIPTION	
		"The table for the ISDN TPH BChannel dialer."
	::= { dialer 18 }

dialerIsdnTPHBChEntry		OBJECT-TYPE
	SYNTAX	DialerIsdnTPHBChEntry
	ACCESS	not-accessible
	STATUS	mandatory
	DESCRIPTION	
		"The set of attributes for one port."
	INDEX		{ dialerIsdnTPHBChPortRef }
	::= { dialerIsdnTPHBChTable 1 }

DialerIsdnTPHBChEntry ::= SEQUENCE {
	dialerIsdnTPHBChPortRef
		PortRef,
	dialerIsdnTPHBChLocalDnType
		IsdnDnType,
	dialerIsdnTPHBChLocalDnPlan
		IsdnDnPlan,
	dialerIsdnTPHBChLocalDn
		DisplayString,
	dialerIsdnTPHBChLocalSubType
		IsdnSubType,
	dialerIsdnTPHBChLocalSub
		DisplayString, 
	dialerIsdnTPHBChRemoteDnType
		IsdnDnType,
	dialerIsdnTPHBChRemoteDnPlan
		IsdnDnPlan,
	dialerIsdnTPHBChRemoteDn
		DisplayString,
	dialerIsdnTPHBChRemoteSubType
		IsdnSubType,
	dialerIsdnTPHBChRemoteSub
		DisplayString, 
	dialerIsdnTPHBChCallType  
		IsdnCallType,
	dialerIsdnTPHBChCallSpeed  
		IsdnCallSpeed,
	dialerIsdnTPHBChBChannel
		IsdnBChannels,
	dialerIsdnTPHBChAnsEnable
		IsdnAnsEnable,	 
	dialerIsdnTPHBChScrStatus
	        IsdnScrStatus,
	dialerIsdnTPHBChCallOpt
 		IsdnCallOpt,
	dialerIsdnTPHBChCcState
		IsdnTPHBCcState,
	dialerIsdnTPHBChCcNbCause
		INTEGER, 
	dialerIsdnTPHBChCcCause
		OCTET STRING,
	dialerIsdnTPHBChL3State	
		IsdnL3State,
	dialerIsdnTPHBChL2State 
		IsdnL2State,
	dialerIsdnTPHBChTeiValue 
		INTEGER,
	dialerIsdnTPHBChTeiStatus	
       		IsdnTeiStatus,
	dialerIsdnTPHBChStoDefined
		IsdnStoDefined,
	dialerIsdnTPHBChStoDnType
		INTEGER,
	dialerIsdnTPHBChStoDnPlan
		INTEGER,
	dialerIsdnTPHBChStoDn
		DisplayString, 
	dialerIsdnTPHBChStoSubType
		INTEGER,
	dialerIsdnTPHBChStoSub
		DisplayString,
	dialerIsdnTPHBChStoBcType
		INTEGER,
	dialerIsdnTPHBChStoBcOpt
		INTEGER
       }

dialerIsdnTPHBChPortRef  	OBJECT-TYPE
	SYNTAX  PortRef
	ACCESS	read-only 
	STATUS	mandatory
	DESCRIPTION	
		"The port number for which the TPH BChannel info is displayed. "
	::= { dialerIsdnTPHBChEntry 1 }

dialerIsdnTPHBChLocalDnType 	OBJECT-TYPE	
	SYNTAX  IsdnDnType 	      
	ACCESS	read-only 
	STATUS	mandatory
	DESCRIPTION	
		"The local directory number type. "
	::= { dialerIsdnTPHBChEntry 2 }

dialerIsdnTPHBChLocalDnPlan 	OBJECT-TYPE	
	SYNTAX  IsdnDnPlan
	ACCESS	read-only 
	STATUS	mandatory
	DESCRIPTION	
		"The local directory number plan. "
	::= { dialerIsdnTPHBChEntry 3 }

dialerIsdnTPHBChLocalDn  	OBJECT-TYPE	
	SYNTAX  DisplayString (SIZE (0..21))
	ACCESS	read-only 
	STATUS	mandatory
	DESCRIPTION	
		"The local directory number type. "
	::= { dialerIsdnTPHBChEntry 4 }

dialerIsdnTPHBChLocalSubType    OBJECT-TYPE
	SYNTAX	IsdnSubType
	ACCESS  read-only
	STATUS  mandatory
	DESCRIPTION
		"The local subaddress type. "
	::= { dialerIsdnTPHBChEntry 5 }

dialerIsdnTPHBChLocalSub	OBJECT-TYPE	
	SYNTAX  DisplayString (SIZE (0..21))
	ACCESS	read-only 
	STATUS	mandatory
	DESCRIPTION	
		"The local directory number type. "
	::= { dialerIsdnTPHBChEntry 6 }

dialerIsdnTPHBChRemoteDnType	OBJECT-TYPE	
	SYNTAX  IsdnDnType 	      
	ACCESS	read-write
	STATUS	mandatory
	DESCRIPTION	
		"The local directory number type. "
	::= { dialerIsdnTPHBChEntry 7 }

dialerIsdnTPHBChRemoteDnPlan 	OBJECT-TYPE	
	SYNTAX  IsdnDnPlan
	ACCESS	read-write
	STATUS	mandatory
	DESCRIPTION	
		"The local directory number plan. "
	::= { dialerIsdnTPHBChEntry 8 }

dialerIsdnTPHBChRemoteDn  	OBJECT-TYPE	
	SYNTAX  DisplayString (SIZE (0..21))
	ACCESS	read-write		  
	STATUS	mandatory
	DESCRIPTION	
		"The local directory number type. "
	::= { dialerIsdnTPHBChEntry 9 }

dialerIsdnTPHBChRemoteSubType     OBJECT-TYPE
	SYNTAX	IsdnSubType
	ACCESS  read-write
	STATUS  mandatory
	DESCRIPTION
		"The local subaddress type. "
	::= { dialerIsdnTPHBChEntry 10 }

dialerIsdnTPHBChRemoteSub	OBJECT-TYPE	
	SYNTAX  DisplayString (SIZE (0..21))
	ACCESS	read-write
	STATUS	mandatory
	DESCRIPTION	
		"The local directory number type. "
	::= { dialerIsdnTPHBChEntry 11 }

dialerIsdnTPHBChCallType 	OBJECT-TYPE	
	SYNTAX  IsdnCallType
	ACCESS	read-only 
	STATUS	mandatory
	DESCRIPTION	
		"The current call type. "
	::= { dialerIsdnTPHBChEntry 12 }

dialerIsdnTPHBChCallSpeed 	OBJECT-TYPE	
	SYNTAX  IsdnCallSpeed
	ACCESS	read-write 
	STATUS	mandatory
	DESCRIPTION	
		"The current call speed. "
	::= { dialerIsdnTPHBChEntry 13 }

dialerIsdnTPHBChBChannel  	OBJECT-TYPE	
	SYNTAX  IsdnBChannels
	ACCESS	read-only 
	STATUS	mandatory
	DESCRIPTION	
		"The current B Channel connected to. "
	::= { dialerIsdnTPHBChEntry 14 }

dialerIsdnTPHBChAnsEnable  	OBJECT-TYPE	
	SYNTAX 	IsdnAnsEnable 
	ACCESS	read-only 
	STATUS	mandatory
	DESCRIPTION	
		"Answer enable status. "
	::= { dialerIsdnTPHBChEntry 15 }

dialerIsdnTPHBChScrStatus	 OBJECT-TYPE	
	SYNTAX  IsdnScrStatus
	ACCESS	read-only 
	STATUS	mandatory
	DESCRIPTION	
		"The status of call screening. "
	::= { dialerIsdnTPHBChEntry 16 }

dialerIsdnTPHBChCallOpt  	OBJECT-TYPE
	SYNTAX 	IsdnCallOpt
	ACCESS  read-only
	STATUS  mandatory
	DESCRIPTION
		"The current call option. " 
	::= { dialerIsdnTPHBChEntry 17 }

dialerIsdnTPHBChCcState   OBJECT-TYPE
	SYNTAX  IsdnTPHBCcState	 
	ACCESS	read-only 
	STATUS	mandatory
	DESCRIPTION	
		"The state of call control subsystem."
	::= { dialerIsdnTPHBChEntry 18 }

dialerIsdnTPHBChCcNbCause	OBJECT-TYPE	
	SYNTAX  INTEGER
	ACCESS	read-only 
	STATUS	mandatory
	DESCRIPTION	
		"The number of causes saved."
	::= { dialerIsdnTPHBChEntry 19 }

dialerIsdnTPHBChCcCause     	OBJECT-TYPE	
	SYNTAX  OCTET STRING  (SIZE (0..10))
	ACCESS	read-only 
	STATUS	mandatory
	DESCRIPTION	
		"Last causes saved. "
	::= { dialerIsdnTPHBChEntry 20 }

dialerIsdnTPHBChL3State   	OBJECT-TYPE	
	SYNTAX  IsdnL3State
	ACCESS	read-only 
	STATUS	mandatory
	DESCRIPTION	
		"The state of layer 3 subsystem. "
	::= { dialerIsdnTPHBChEntry 21 }

dialerIsdnTPHBChL2State   	OBJECT-TYPE	
	SYNTAX  IsdnL2State 	
	ACCESS	read-only 
	STATUS	mandatory
	DESCRIPTION	
		"The state of layer 2 subsystem. "
	::= { dialerIsdnTPHBChEntry 22 }

dialerIsdnTPHBChTeiValue     	OBJECT-TYPE	
	SYNTAX  INTEGER	
	ACCESS	read-only 
	STATUS	mandatory
	DESCRIPTION	
		" The static TEI value on the D Channel for data communications."																	 
	::= { dialerIsdnTPHBChEntry 23 }

dialerIsdnTPHBChTeiStatus	OBJECT-TYPE	
	SYNTAX  IsdnTeiStatus	
	ACCESS	read-only 
	STATUS	mandatory
	DESCRIPTION	
		" The status of TEI - always ASSIGNED."
	::= { dialerIsdnTPHBChEntry 24 }

dialerIsdnTPHBChStoDefined	OBJECT-TYPE
	SYNTAX  IsdnStoDefined
	ACCESS  read-only
	STATUS  mandatory
	DESCRIPTION
		"The validity of  sto- elements. " 
	::= { dialerIsdnTPHBChEntry 25 }

dialerIsdnTPHBChStoDnType	OBJECT-TYPE
	SYNTAX 	INTEGER
	ACCESS  read-only
	STATUS  mandatory
	DESCRIPTION
		"The stored directory number type. " 
	::= { dialerIsdnTPHBChEntry 26 }

dialerIsdnTPHBChStoDnPlan	OBJECT-TYPE
	SYNTAX 	INTEGER
	ACCESS  read-only
	STATUS  mandatory
	DESCRIPTION
		"The stored directory number plan. " 
	::= { dialerIsdnTPHBChEntry 27 }

dialerIsdnTPHBChStoDn		OBJECT-TYPE
	SYNTAX 	DisplayString (SIZE (0..21))	
	ACCESS  read-only
	STATUS  mandatory
	DESCRIPTION
		"The stored directory number. " 
	::= { dialerIsdnTPHBChEntry 28 }

dialerIsdnTPHBChStoSubType	OBJECT-TYPE
	SYNTAX 	INTEGER
	ACCESS  read-only
	STATUS  mandatory
	DESCRIPTION
		"The stored subaddress type. " 
	::= { dialerIsdnTPHBChEntry 29 }

dialerIsdnTPHBChStoSub		OBJECT-TYPE
	SYNTAX 	DisplayString (SIZE (0..21))	
	ACCESS  read-only
	STATUS  mandatory
	DESCRIPTION
		"The stored subaddress. " 
	::= { dialerIsdnTPHBChEntry 30 }

dialerIsdnTPHBChStoBcType	OBJECT-TYPE
	SYNTAX 	INTEGER
	ACCESS  read-only
	STATUS  mandatory
	DESCRIPTION
		"The stored bearer cap. type. " 
	::= { dialerIsdnTPHBChEntry 31 }

dialerIsdnTPHBChStoBcOpt	OBJECT-TYPE
	SYNTAX 	INTEGER
	ACCESS  read-only
	STATUS  mandatory
	DESCRIPTION
		"The stored bearer cap. option. " 
	::= { dialerIsdnTPHBChEntry 32 }

-- ****************************************************************************
--		Dialer ISDN TPHD DChannel Table
-- ****************************************************************************

dialerIsdnTPHDChTable		OBJECT-TYPE    
	SYNTAX	SEQUENCE OF  DialerIsdnTPHDChEntry
	ACCESS	not-accessible
	STATUS	mandatory
	DESCRIPTION	
		"The table for the ISDN TPH DChannel dialer."
	::= { dialer 19 }

dialerIsdnTPHDChEntry		OBJECT-TYPE
	SYNTAX	DialerIsdnTPHDChEntry
	ACCESS	not-accessible
	STATUS	mandatory
	DESCRIPTION	
		"The set of attributes for one port."
	INDEX		{ dialerIsdnTPHDChPortRef }
	::= { dialerIsdnTPHDChTable 1 }

DialerIsdnTPHDChEntry ::= SEQUENCE {
	dialerIsdnTPHDChPortRef
		PortRef,
	dialerIsdnTPHDChTeiValue 
		INTEGER,
	dialerIsdnTPHDChTeiStatus	
       		IsdnTeiStatus,
	dialerIsdnTPHDChL2State 
		IsdnL2State,
	dialerIsdnTPHDChP3State
		IsdnP3State
	}

dialerIsdnTPHDChPortRef  	OBJECT-TYPE
	SYNTAX  PortRef
	ACCESS	read-only 
	STATUS	mandatory
	DESCRIPTION	
		"The port number for which the TPH DChannel info is displayed. "
	::= { dialerIsdnTPHDChEntry 1 }

dialerIsdnTPHDChTeiValue     	OBJECT-TYPE	
	SYNTAX  INTEGER	
	ACCESS	read-only 
	STATUS	mandatory
	DESCRIPTION	
		" The static TEI value on the D Channel for data communications."																	 
	::= { dialerIsdnTPHDChEntry 2 }

dialerIsdnTPHDChTeiStatus	OBJECT-TYPE	
	SYNTAX  IsdnTeiStatus	
	ACCESS	read-only 
	STATUS	mandatory
	DESCRIPTION	
		" The status of TEI - always ASSIGNED."
	::= { dialerIsdnTPHDChEntry 3 }

dialerIsdnTPHDChL2State   	OBJECT-TYPE	
	SYNTAX  IsdnL2State 	
	ACCESS	read-only 
	STATUS	mandatory
	DESCRIPTION	
		"The state of layer 2 subsystem. "
	::= { dialerIsdnTPHDChEntry 4 }
	
dialerIsdnTPHDChP3State		OBJECT-TYPE	
	SYNTAX  IsdnP3State  	
	ACCESS	read-only 
	STATUS	mandatory
	DESCRIPTION	
		"The current Packet layer state. "
	::= { dialerIsdnTPHDChEntry 5 }

END
