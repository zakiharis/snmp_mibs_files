ENTERASYS-CN-MIB-EXT-MIB DEFINITIONS ::= BEGIN

--  enterasys-cn-mib-ext-mib.txt
--
--  Part Number:
--
--

--  This module provides authoritative definitions for Enterasys 
--  Networks' Congestion Notification (CN) extension MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in 
--  connection with the management of Enterasys Networks products.

--  Copyright July, 2012 Enterasys Networks, Inc.

IMPORTS
    MODULE-IDENTITY, OBJECT-TYPE, Integer32, Unsigned32
        FROM SNMPv2-SMI
    RowStatus
        FROM SNMPv2-TC
    MODULE-COMPLIANCE, OBJECT-GROUP
        FROM SNMPv2-CONF
    SnmpAdminString
        FROM SNMP-FRAMEWORK-MIB
    IEEE8021PbbComponentIdentifier
        FROM IEEE8021-TC-MIB
    ieee8021CnGlobalEntry, ieee8021CnCpEntry
        FROM IEEE8021-CN-MIB
    etsysModules
        FROM ENTERASYS-MIB-NAMES;

etsysCnMibExtMIB MODULE-IDENTITY
    LAST-UPDATED "201207201221Z"  -- Fri Jul 20 12:21 UTC 2012
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"
   
    DESCRIPTION
        "This MIB module defines a portion of the SNMP MIB under
         the Enterasys Networks enterprise OID pertaining to 
         proprietary extensions to the IEEE8021-CN-MIB.

         This MIB was designed to be used for configuration of
         CN queue profiles.  The standard
         IEEE8021-CN-MIB provides a congestion point object to 
         manage parameters that are specific to a congestion
         notification queue, however many platforms do not 
         support direct configuration of queues in the hardware.
         Some hardware support for CN provides the ability to 
         configure a set of profiles which are then mapped to 
         hardware queues.  The number of profiles supported is 
         hardware specific.  A queue profile provides the same set 
         of parameters that are provided in a congestion point 
         managed object.  Each congestion point is then provided 
         a queue profile index which maps the congestion point 
         object to a profile."

    REVISION     "201207201221Z"  -- Fri Jul 20 12:21 UTC 2012
    DESCRIPTION  "The initial version of this MIB module."

    ::= { etsysModules 95 } 

-- -------------------------------------------------------------
-- Textual Conventions
-- -------------------------------------------------------------

-- -------------------------------------------------------------
-- MIB Objects
-- -------------------------------------------------------------

etsysCnMibExtObjects    OBJECT IDENTIFIER ::= { etsysCnMibExtMIB 1 }

etsysCnMibExtSysBranch  OBJECT IDENTIFIER 
                        ::= { etsysCnMibExtObjects 1 }

etsysCnMibExtCompBranch OBJECT IDENTIFIER 
                        ::= { etsysCnMibExtObjects 2 }

-- -------------------------------------------------------------
-- System Objects
-- -------------------------------------------------------------

-- -------------------------------------------------------------
-- CN Queue Profile Type Table
-- -------------------------------------------------------------

etsysCnMibExtQpTypeTable OBJECT-TYPE
    SYNTAX      SEQUENCE OF EtsysCnMibExtQpTypeEntry
    MAX-ACCESS  not-accessible
    STATUS      current
    DESCRIPTION
        "A table of CN queue profile types."
    ::= { etsysCnMibExtSysBranch 1 }

etsysCnMibExtQpTypeEntry OBJECT-TYPE
    SYNTAX      EtsysCnMibExtQpTypeEntry
    MAX-ACCESS  not-accessible
    STATUS      current
    DESCRIPTION
        "An entry in the CN queue profile type table."
    INDEX { etsysCnMibExtQptIdentifier }
    ::= { etsysCnMibExtQpTypeTable 1 }

EtsysCnMibExtQpTypeEntry ::=
    SEQUENCE {
        etsysCnMibExtQptIdentifier      
            Unsigned32,
        etsysCnMibExtQptDesc            
            SnmpAdminString,
        etsysCnMibExtQptMaxQpEntries    
            Unsigned32,
        etsysCnMibExtQptSupport         
            BITS
    }

etsysCnMibExtQptIdentifier OBJECT-TYPE
    SYNTAX      Unsigned32
    MAX-ACCESS  not-accessible
    STATUS      current
    DESCRIPTION
        "The CN queue profile type within the system to which the 
         information in this entry applies."
    ::= { etsysCnMibExtQpTypeEntry 1 }

etsysCnMibExtQptDesc OBJECT-TYPE
    SYNTAX      SnmpAdminString (SIZE(1..256))
    MAX-ACCESS  read-only
    STATUS      current
    DESCRIPTION
        "A textual description of the CN queue profile type for this 
         entry."
    ::= { etsysCnMibExtQpTypeEntry 2 }

etsysCnMibExtQptMaxQpEntries OBJECT-TYPE
    SYNTAX      Unsigned32
    MAX-ACCESS  read-only
    STATUS      current
    DESCRIPTION
        "The maximum number of CN queue profile entries allowed for this
         profile type."
    ::= { etsysCnMibExtQpTypeEntry 3 }

etsysCnMibExtQptSupport OBJECT-TYPE
    SYNTAX      BITS {
        supportSizeSetPoint(0),
        supportFeedbackWeight(1),
        supportMinSampleBase(2),
        supportMinHeaderOctets(3)
    }
    MAX-ACCESS  read-only
    STATUS      current
    DESCRIPTION
        "This object represents the CN queue
         profile parameters that are supported by queue profile
         entries of the queue profile type defined by this entry."
    ::= { etsysCnMibExtQpTypeEntry 4 }

etsysCnMibExtMaxCompActivePriVals OBJECT-TYPE
    SYNTAX      Unsigned32
    MAX-ACCESS  read-only
    STATUS      current
    DESCRIPTION
        "The maximum number of active ieee8021CnCompntPriTable
         entries allowed per component in the system.  An entry 
         is active if the ieee8021CnComPriRowStatus is active."
    ::= { etsysCnMibExtSysBranch 2 }

-- ------------------------------------------------------------
-- Component Objects
-- ------------------------------------------------------------

-- -------------------------------------------------------------
-- The CN queue configuration profile table.
-- One table per bridge component.  One entry per profile type,
-- per profile index.  Controls the configuration of congestion
-- point queues that are assigned to a specific configuration
-- profile.
-- -------------------------------------------------------------

etsysCnMibExtQpTable OBJECT-TYPE
    SYNTAX      SEQUENCE OF EtsysCnMibExtQpEntry
    MAX-ACCESS  not-accessible
    STATUS      current
    DESCRIPTION
        "A table of CN queue configuration profiles."
    ::= { etsysCnMibExtCompBranch 1 }

etsysCnMibExtQpEntry OBJECT-TYPE
    SYNTAX      EtsysCnMibExtQpEntry
    MAX-ACCESS  not-accessible
    STATUS      current
    DESCRIPTION
        "An entry in the CN profile table."
    INDEX { etsysCnMibExtQpComponentId,
            etsysCnMibExtQpTypeId,
            etsysCnMibExtQpIndex }
    ::= { etsysCnMibExtQpTable 1 }

EtsysCnMibExtQpEntry ::=
    SEQUENCE {
        etsysCnMibExtQpComponentId      
            IEEE8021PbbComponentIdentifier,
        etsysCnMibExtQpTypeId           
            Unsigned32,
        etsysCnMibExtQpIndex            
            Unsigned32,
        etsysCnMibExtQpSizeSetPoint     
            Unsigned32,
        etsysCnMibExtQpFeedbackWeight   
            Integer32,
        etsysCnMibExtQpMinSampleBase    
            Unsigned32,
        etsysCnMibExtQpMinHeaderOctets  
            Unsigned32,
        etsysCnMibExtQpRowStatus        
            RowStatus
    }

etsysCnMibExtQpComponentId OBJECT-TYPE
    SYNTAX      IEEE8021PbbComponentIdentifier
    MAX-ACCESS  not-accessible   
    STATUS      current
    DESCRIPTION
        "The bridge component within the system to which the information
         in this etsysCnMibExtQpEntry applies.  If the system
         is not a Bridge, or if only one component is present in the
         Bridge, then this variable (index) MUST be equal to 1."
    REFERENCE
        "802.1Qau clause 17.2.13"
    ::= { etsysCnMibExtQpEntry 1 }

etsysCnMibExtQpTypeId OBJECT-TYPE
    SYNTAX      Unsigned32
    MAX-ACCESS  not-accessible
    STATUS      current
    DESCRIPTION
        "This object represents the CN queue profile type to which this
         entry applies."
    ::= { etsysCnMibExtQpEntry 2 }

etsysCnMibExtQpIndex OBJECT-TYPE
    SYNTAX      Unsigned32
    MAX-ACCESS  not-accessible
    STATUS      current
    DESCRIPTION
        "This object represents the CN queue profile to which this 
         entry applies."
    ::= { etsysCnMibExtQpEntry 3 }

etsysCnMibExtQpSizeSetPoint OBJECT-TYPE
    SYNTAX      Unsigned32  (100..4294967295)
    UNITS       "octets"
    MAX-ACCESS  read-create
    STATUS      current
    DESCRIPTION
        "This object is the set point for the queues managed by this
         profile entry.  Congestion Notification Messages are transmitted
         to the sources of frames queued in this CP's queue in order to
         keep the total number of octets stored in the queue at this set
         point."
    DEFVAL { 26000 }
    ::= { etsysCnMibExtQpEntry 4 }

etsysCnMibExtQpFeedbackWeight OBJECT-TYPE
    SYNTAX      Integer32   (-10..10)
    MAX-ACCESS  read-create
    STATUS      current
    DESCRIPTION
        "This object controls the weight (cpW) change in queue length
        in the calculation of cpFb when the Congestion Point is
        generating a Congestion Notification Message.

        The weight cpW is equal to two to the power of this object.
        Thus, if this object contains a -1, cpW = 1/2."
    DEFVAL { 1 }
    ::= { etsysCnMibExtQpEntry 5 }

etsysCnMibExtQpMinSampleBase OBJECT-TYPE
    SYNTAX      Unsigned32 (10000..4294967295)
    UNITS       "octets"
    MAX-ACCESS  read-create
    STATUS      current
    DESCRIPTION
       "This object determines the minimum number of octets to
        enqueue in the Congestion Point's queue between transmissions
        of Congestion Notification Messages."
    REFERENCE
       "802.1Qau clause 32.8.11"
    DEFVAL { 150000 }
    ::= { etsysCnMibExtQpEntry 6 }

etsysCnMibExtQpMinHeaderOctets OBJECT-TYPE
    SYNTAX      Unsigned32 (0..64)
    UNITS       "octets"
    MAX-ACCESS  read-create
    STATUS      current
    DESCRIPTION
       "Specifies the minimum number of octets to be returned in a
        Congestion Notification Message from the mac_service_data_unit
        of the data frame that triggered transmission of the CNM.  If
        the mac_service_data_unit has fewer octets than the value of
        this object, then all of the mac_service_data_unit is returned
        in the CNM."
    DEFVAL { 0 }
    ::= { etsysCnMibExtQpEntry 7 }

etsysCnMibExtQpRowStatus OBJECT-TYPE
    SYNTAX      RowStatus
    MAX-ACCESS  read-create
    STATUS      current
    DESCRIPTION
        "This object indicates the status of an entry, and is used to
         create/delete entries."
    ::= { etsysCnMibExtQpEntry 8 }

-- -------------------------------------------------------------
-- Congestion point extension table.  One per component, per 
-- interface, per congestion point index.
-- -------------------------------------------------------------

etsysCnMibExtCpTable OBJECT-TYPE
    SYNTAX      SEQUENCE OF EtsysCnMibExtCpEntry
    MAX-ACCESS  not-accessible
    STATUS      current
    DESCRIPTION
        "A table of CN congestion point objects."
    ::= { etsysCnMibExtCompBranch 2 }

etsysCnMibExtCpEntry OBJECT-TYPE
    SYNTAX      EtsysCnMibExtCpEntry
    MAX-ACCESS  not-accessible
    STATUS      current
    DESCRIPTION
        "An entry in the CN congestion point table."
    AUGMENTS { ieee8021CnCpEntry }
    ::= { etsysCnMibExtCpTable 1 }

EtsysCnMibExtCpEntry ::=
    SEQUENCE {
        etsysCnMibExtCpQpTypeId    
            Unsigned32,
        etsysCnMibExtCpQpIndex     
            Unsigned32
    }

etsysCnMibExtCpQpTypeId OBJECT-TYPE
    SYNTAX      Unsigned32
    MAX-ACCESS  read-only
    STATUS      current
    DESCRIPTION
        "This object represents the CN queue profile type to which this 
         entry applies."
    ::= { etsysCnMibExtCpEntry 1 }

etsysCnMibExtCpQpIndex OBJECT-TYPE
    SYNTAX      Unsigned32
    MAX-ACCESS  read-write
    STATUS      current
    DESCRIPTION
        "This object represents the CN queue profile to which this 
         entry applies." 
    ::= { etsysCnMibExtCpEntry 2 }
 
-- -------------------------------------------------------------
-- Global extension table. One per component.
-- -------------------------------------------------------------

etsysCnMibExtGlobalTable OBJECT-TYPE
    SYNTAX      SEQUENCE OF EtsysCnMibExtGlobalEntry
    MAX-ACCESS  not-accessible
    STATUS      current
    DESCRIPTION
        "A table of CN global configuration and status objects."
    ::= { etsysCnMibExtCompBranch 3 }

etsysCnMibExtGlobalEntry OBJECT-TYPE
    SYNTAX      EtsysCnMibExtGlobalEntry
    MAX-ACCESS  not-accessible
    STATUS      current
    DESCRIPTION
        "An entry in the CN global table."
    AUGMENTS { ieee8021CnGlobalEntry }
    ::= { etsysCnMibExtGlobalTable 1 }

EtsysCnMibExtGlobalEntry ::= 
    SEQUENCE {
        etsysCnMibExtGlobalActivePriVals  
            Unsigned32
    }

etsysCnMibExtGlobalActivePriVals OBJECT-TYPE
    SYNTAX      Unsigned32
    MAX-ACCESS  read-only
    STATUS      current
    DESCRIPTION
        "The number of active ieee8021CnCompntPriTable entries for this
         component in the system.  An entry is active if the 
         ieee8021CnComPriRowStatus is active."
    ::= { etsysCnMibExtGlobalEntry 1 }

-- -------------------------------------------------------------
-- Conformance Information
-- -------------------------------------------------------------

etsysCnMibExtConformance OBJECT IDENTIFIER ::= { etsysCnMibExtMIB 2 }

etsysCnMibExtGroups      OBJECT IDENTIFIER 
                         ::= { etsysCnMibExtConformance 1 }

etsysCnMibExtCompliances OBJECT IDENTIFIER 
                         ::= { etsysCnMibExtConformance 2 }

-- -------------------------------------------------------------
-- Units of conformance
-- -------------------------------------------------------------

etsysCnMibExtQpTypeGroup OBJECT-GROUP
    OBJECTS {
        etsysCnMibExtQptDesc,
        etsysCnMibExtQptMaxQpEntries,
        etsysCnMibExtQptSupport
    }
    STATUS      current
    DESCRIPTION
        "The collection of objects to provide information about
         congestion notification queue profile types that are  
         supported in a system."
    ::= { etsysCnMibExtGroups 1 }

etsysCnMibExtSysGroup OBJECT-GROUP
    OBJECTS {
        etsysCnMibExtMaxCompActivePriVals
    }
    STATUS      current
    DESCRIPTION
        "A collection of objects to provide information about
         extended capabilities of a system which supports congestion 
         notification."
    ::= { etsysCnMibExtGroups 2 }

etsysCnMibExtGlobalGroup OBJECT-GROUP
    OBJECTS {
        etsysCnMibExtGlobalActivePriVals
    }
    STATUS      current
    DESCRIPTION
        "A collection of objects to provide information about
         extended capabilities of a component in a system which 
         supports congestion notification."
    ::= { etsysCnMibExtGroups 3 }

etsysCnMibExtQpGroup OBJECT-GROUP
    OBJECTS {
        etsysCnMibExtQpSizeSetPoint,
        etsysCnMibExtQpFeedbackWeight,
        etsysCnMibExtQpMinSampleBase,
        etsysCnMibExtQpMinHeaderOctets,
        etsysCnMibExtQpRowStatus
    }
    STATUS      current
    DESCRIPTION
        "A collection of objects providing the ability to configure
         a CN queue profile which can be assigned to a CN profile."
    ::= { etsysCnMibExtGroups 4 }

etsysCnMibExtCpGroup OBJECT-GROUP
    OBJECTS {
        etsysCnMibExtCpQpTypeId,
        etsysCnMibExtCpQpIndex
    }
    STATUS      current
    DESCRIPTION
        "A collection of objects providing the ability to map a CN
         congestion point object to a CN queue profile object."
    ::= { etsysCnMibExtGroups 5 }


-- -------------------------------------------------------------
-- Compliance statements
-- -------------------------------------------------------------

etsysCnMibExtCompliance MODULE-COMPLIANCE
    STATUS      current
    DESCRIPTION
        "The compliance statement for devices that support etsysCnMibExtMIB."

    MODULE
        MANDATORY-GROUPS {
            etsysCnMibExtQpTypeGroup,
            etsysCnMibExtSysGroup,
            etsysCnMibExtGlobalGroup,
            etsysCnMibExtQpGroup,
            etsysCnMibExtCpGroup
        }

    ::= { etsysCnMibExtCompliances 1 }

END
