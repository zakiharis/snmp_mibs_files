-- Extreme Networks ExtremeXOS 15.3.2.11 Proprietary MIB


-- ################################################################################

EXTREME-BASE-MIB DEFINITIONS ::= BEGIN

    IMPORTS
    enterprises            FROM RFC1155-SMI
    TEXTUAL-CONVENTION     FROM SNMPv2-TC
    MODULE-IDENTITY	   FROM SNMPv2-SMI;



    --  Organization & Product branches
    extremenetworks MODULE-IDENTITY
                LAST-UPDATED "1212061000Z"
                ORGANIZATION "Extreme Networks, Inc."
                CONTACT-INFO "www.extremenetworks.com"
                DESCRIPTION "Extreme Wireless Access Tables"
        ::= { enterprises 1916 }

    
    extremeV1Traps         OBJECT IDENTIFIER ::= { extremenetworks 0 }
    extremeAgent           OBJECT IDENTIFIER ::= { extremenetworks 1 }
    extremeProduct         OBJECT IDENTIFIER ::= { extremenetworks 2 }
    extremeMisc            OBJECT IDENTIFIER ::= { extremenetworks 3 }
    extremeV2Traps         OBJECT IDENTIFIER ::= { extremenetworks 4 } 

    --
    -- Extreme Products
    --    
    summit1                OBJECT IDENTIFIER ::= { extremeProduct 1 }
                           -- 8 x 1Gbps

    summit2                OBJECT IDENTIFIER ::= { extremeProduct 2 }
                           -- 2 x 1Gbps, 16 x 10/100Mbps

    summit3                OBJECT IDENTIFIER ::= { extremeProduct 3 }
                           -- 1 x 1Gbps, 24 x 10/100Mbps

    summit4                OBJECT IDENTIFIER ::= { extremeProduct 4 }
                           -- 6 x 1Gbps, 16 x 10/100Mbps UTP

    summit4fx              OBJECT IDENTIFIER ::= { extremeProduct 5 }
                           -- 6 x 1Gbps, 16 x 10/100Mbps fiber FX

    summit48               OBJECT IDENTIFIER ::= { extremeProduct 6 }
                           -- 2 x 1Gbps, 48 x 10/100Mbps

    summit24               OBJECT IDENTIFIER ::= { extremeProduct 7 }
                           -- 1 x 1Gbps, 24 x 10/100Mbps

    blackDiamond6800       OBJECT IDENTIFIER ::= { extremeProduct 8 }
                           -- chassis based system with dual msm and 8 switching cards

    blackDiamond6808       OBJECT IDENTIFIER ::= { extremeProduct 11 }
                           -- black diamond with the inferno chipset aka MSM64

    summit7iSX             OBJECT IDENTIFIER ::= { extremeProduct 12 }
                           -- 4 x 1Gbps GBIC, 28 x 1Gbps MT-RJ

    summit7iTX             OBJECT IDENTIFIER ::= { extremeProduct 13 }
                           -- 4 x 1Gbps GBIC, 28 x 10/100/1000 Base-TX

    summit1iTX             OBJECT IDENTIFIER ::= { extremeProduct 14 }
                           -- 2 x 1Gbps MT-RJ, 6 x 10/100/1000 Base-TX inferno chipset

    summit5i               OBJECT IDENTIFIER ::= { extremeProduct 15 }
                           -- 4 x 1Gbps GBIC, 12 x 1Gbps MT-RJ inferno chipset

    summit48i              OBJECT IDENTIFIER ::= { extremeProduct 16 }
                           -- 2 x 1Gbps GBIC, 48 x 10/100Mbps inferno chipset

    alpine3808             OBJECT IDENTIFIER ::= { extremeProduct 17 }
                           -- mini chassis based on the inferno chipset with 8 switching cards

    summit1iSX             OBJECT IDENTIFIER ::= { extremeProduct 19 }
                           -- 2 x 1Gbps GBIC, 6 x 1Gbps MT-RJ inferno chipset

    alpine3804             OBJECT IDENTIFIER ::= { extremeProduct 20 }
                           -- mini chassis based on the inferno chipset with 4 switching cards

    summit5iLX             OBJECT IDENTIFIER ::= { extremeProduct 21 }
                           -- 4 x 1Gbps GBIC, 12 x 10/100/1000 Base-TX inferno chipset

    summit5iTX             OBJECT IDENTIFIER ::= { extremeProduct 22 }
                           -- 4 x 1Gbps GBIC, 12 x 10/100/1000 Base-TX inferno chipset

    enetSwitch24Port       OBJECT IDENTIFIER ::= { extremeProduct 23 }
                           --  24 x 10/100 Mbps  

    blackDiamond6816       OBJECT IDENTIFIER ::= { extremeProduct 24 }
                           -- black diamond with 4 msm's and 16 switching cards

    summit24e3             OBJECT IDENTIFIER ::= { extremeProduct 25 }
                           -- 2 x 1Gbps GBIC, 24 x 10/100 Base-TX

    alpine3802             OBJECT IDENTIFIER ::= { extremeProduct 26 }
                           -- mini chassis based on the inferno chipset with 2-3 switching cards

    blackDiamond6804       OBJECT IDENTIFIER ::= { extremeProduct 27 }
                           -- chassis based system with 2 msm's and 4 switching cards

    summit48si             OBJECT IDENTIFIER ::= { extremeProduct 28 }
                           -- 2 x 1Gbps GBIC, 48 x 10/100Mbps, 1u
            
    summitPx1              OBJECT IDENTIFIER ::= { extremeProduct 30 }
                           --    1 x 1Gbps GBIC

    summit24e2TX           OBJECT IDENTIFIER ::= { extremeProduct 40 }
                           --  2 x 1000Base-T, 24 x 10/100 Base-TX

    summit24e2SX           OBJECT IDENTIFIER ::= { extremeProduct 41 }
                           --  2 x 1Gbps GBIC, 24 x 10/100 Base-SX

    summit200-24           OBJECT IDENTIFIER ::= { extremeProduct 53 }
                           --  2 x 1Gbps GBIC, 24 x 10/100 Base-TX

    summit200-48           OBJECT IDENTIFIER ::= { extremeProduct 54 }
                           --  2 x 1Gbps GBIC, 48 x 10/100 Base-TX

    summit300-48           OBJECT IDENTIFIER ::= { extremeProduct 55 }
                           --  2 x 1Gbps GBIC, 48 x 10/100 Base-TX POE

    bd10808                OBJECT IDENTIFIER ::= { extremeProduct 56 }
                           -- BlackDiamond 10808 Chassis
 
    summit400-48t          OBJECT IDENTIFIER ::= { extremeProduct 58 }
                           --  4 x 1Gbps fiber/copper, 44 x 1000 Base-T
 
    summit300-24           OBJECT IDENTIFIER ::= { extremeProduct 61 }
                           --  2 x 1Gbps GBIC, 24 x 10/100 Base-TX POE

    bd8810	           OBJECT IDENTIFIER ::= { extremeProduct 62 }
                           --  BlackDiamond 8810 Chassis

    summit400-24t           OBJECT IDENTIFIER ::= { extremeProduct 63 }
                           --  4 x 1Gbps fiber/copper, 20 x 1Gbps fiber

    summit400-24p           OBJECT IDENTIFIER ::= { extremeProduct 64 }
                           --  4 x 1Gbps fiber/copper, 20 x 1Gbps fiber

    summitX450-24x   OBJECT IDENTIFIER ::= { extremeProduct 65 }
                           --  4 x 1Gbps fiber/copper, 20 x 1Gbps fiber, 2 x 10G uplink
                  
    summitX450-24t   OBJECT IDENTIFIER ::= { extremeProduct 66 }
                           --  4 x 1Gbps fiber/copper, 20 x 1000 Base-T, 2 x 10G uplink
                  
    summitStack		   OBJECT IDENTIFIER ::= { extremeProduct 67 }
			   -- A stacked version of the Summit 200/300/4000

    summitWM100		   OBJECT IDENTIFIER ::= { extremeProduct 68 }
			   -- The FlightPath wireless controller with 10/100 ports

    summitWM1000	   OBJECT IDENTIFIER ::= { extremeProduct 69 }
			   -- The FlightPath wireless controller with 1 gig ports

    summit200-24fx	   OBJECT IDENTIFIER ::= { extremeProduct 70 }
			   -- 24 100FX fiber ports + 2 combo Gig uplink ports

	
    summitX450a-24t 	   OBJECT IDENTIFIER ::= { extremeProduct 71 }
			   -- 24 combo ports + 2 optional 10 gig ports + 
			   -- 4 combo ports + 2 stacking ports

    summitX450e-24p 	   OBJECT IDENTIFIER ::= { extremeProduct 72 }
			   -- PoE version of summitX450e-24p 



    bd8806                 OBJECT IDENTIFIER ::= { extremeProduct 74 }
                           -- Black Diamond 8800 6 slot chassis

    altitude350		   OBJECT IDENTIFIER ::= {extremeProduct 75 }
			   -- The altitude 350 product

    summitX450a-48t        OBJECT IDENTIFIER ::= {extremeProduct 76 }


    bd12804                OBJECT IDENTIFIER ::= {extremeProduct 77 }
                           -- bd12804 Chassis 


    summitX450e-48p   OBJECT IDENTIFIER ::= { extremeProduct 79 }
                           -- PoE version of the summitX450a-48t 

    summitX450a-24tDC   OBJECT IDENTIFIER ::= { extremeProduct 80 }
                           -- summitX450a-24t with DC power supply

--  OID 81 is deprecarted.

    summitX450a-24xDC   OBJECT IDENTIFIER ::= { extremeProduct 82 }
                      -- summitX450a-24x with DC power supply

    sentriantCE150   OBJECT IDENTIFIER ::= { extremeProduct 83 }

                                    -- sentriantCE150, this is security appliance.  


    summitX450a-24x   OBJECT IDENTIFIER ::= { extremeProduct 84 }
                                    --  4 x 1Gbps fiber/copper, 20 x 1Gbps fiber, 2 x 10G uplink


    bd12802   OBJECT IDENTIFIER ::= { extremeProduct 85 }
                                    -- 3-slot chassis, 1 MSM 2 IO modules


     altitude300 OBJECT IDENTIFIER ::= { extremeProduct 86 }
				-- altitude300 is the access point box. 


     summitX450a-48tDC   OBJECT IDENTIFIER ::= { extremeProduct 87 }
                           -- summitX450a-48t with DC power supply


     summitX250-24t     OBJECT IDENTIFIER ::= { extremeProduct 88 }

                           -- summitX250e: 24 10/100 copper ports, 2 100M fiber combo ports, 2 x 1G uplink option module

 

     summitX250-24p     OBJECT IDENTIFIER ::= { extremeProduct 89 }

                           -- PoE version of the summitX250-24t

 

     summitX250-24x     OBJECT IDENTIFIER ::= { extremeProduct 90 }

                           -- summitX250e: 24 SFP 100M fiber ports, 2 10/100 copper combo ports, 2 x 1G uplink option module

   

     summitX250-48t     OBJECT IDENTIFIER ::= { extremeProduct 91 }

                           -- summitX250e: 48 10/100 copper ports, 2 100M fiber combo ports, 2 x 1G uplink option module

 

     summitX250-48p     OBJECT IDENTIFIER ::= { extremeProduct 92 }

                           -- PoE version of the summitX250-48t

    summitVer2Stack     OBJECT IDENTIFIER ::= { extremeProduct 93 }
                           -- A stacked version of the EXOS Summit X450's, X250's


    summitWM200 OBJECT IDENTIFIER ::= { extremeProduct 94 }

    summitWM2000 OBJECT IDENTIFIER ::= { extremeProduct 95 }

    summitWM100Lite OBJECT IDENTIFIER ::= { extremeProduct 96 }

    summitX250-24tDC   OBJECT IDENTIFIER ::= { extremeProduct 97 }
                           -- summitX250e: DC powered 24 10/100 copper ports, 2 x 1G fiber combo ports

    summitX250-24xDC   OBJECT IDENTIFIER ::= { extremeProduct 98 }
                           -- summitX250e: DC powered 24 SFP 100M fiber ports, 2 x 1G copper combo ports

    summitX250-48tDC   OBJECT IDENTIFIER ::= { extremeProduct 99 }
                           -- summitX250e: DC powered 48 10/100 copper ports, 2 x 1G fiber combo ports

    summitX150-24t     OBJECT IDENTIFIER ::= { extremeProduct 100 }
                           -- summitX150: Layer 2 24 10/100 copper ports, 2 x 1G fiber combo ports

    summitX150-24tDC   OBJECT IDENTIFIER ::= { extremeProduct 101 }
                           -- summitX150: Layer 2 DC powered 24 10/100 copper ports, 2 x 1G fiber combo ports

    summitX150-24p     OBJECT IDENTIFIER ::= { extremeProduct 102 }
                           -- Layer 2 PoE version of the summitX150-24t

    summitX150-24x     OBJECT IDENTIFIER ::= { extremeProduct 103 }
                           -- summitX150: Layer 2 24 SFP 100M fiber ports, 2 x 1G copper combo ports

    summitX150-24xDC   OBJECT IDENTIFIER ::= { extremeProduct 104 }
                           -- summitX150: Layer 2 DC powered 24 SFP 100M fiber ports, 2 x 1G copper combo ports

    summitX150-48t     OBJECT IDENTIFIER ::= { extremeProduct 105 }
                           -- summitX150: Layer 2 48 10/100 copper ports, 2 x 1G fiber combo ports

    summitX150-48tDC   OBJECT IDENTIFIER ::= { extremeProduct 106 }
                           -- summitX150: Layer 2 DC powered 48 10/100 copper ports, 2 x 1G fiber combo ports

    summitX150-48p     OBJECT IDENTIFIER ::= { extremeProduct 107 }
                           -- Layer 2 PoE version of the summitX150-48t

    sentriantAGSW      OBJECT IDENTIFIER ::= { extremeProduct 108 }
                          -- Sentriant AG Network Access Control Software

    sentriantAG200     OBJECT IDENTIFIER ::= { extremeProduct 109 }
                          -- Sentriant AG200 Network Access Control appliance

    summitWM20         OBJECT IDENTIFIER ::= { extremeProduct 110 }
                          -- Summit WM20 WLAN Controller

    summitX350-24t     OBJECT IDENTIFIER ::= { extremeProduct 111 }
                          -- Layer 2 24 10/100/1000 copper ports, 4 x 1G fiber combo ports

    summitX350-48t     OBJECT IDENTIFIER ::= { extremeProduct 112 }
                          -- Layer 2 48 10/100/1000 copper ports, 4 x 1G fiber combo ports

    summitX650-24t     OBJECT IDENTIFIER ::= { extremeProduct 113 }
                          -- 24-port SummitX650 -10GbaseT (no VIM installed)

    summitX650-24x     OBJECT IDENTIFIER ::= { extremeProduct 114 }
                          -- 24-port SummitX650 SFP+ (no VIM installed)

    sentriantNG300     OBJECT IDENTIFIER ::= { extremeProduct 115 }
                         -- Sentriant NG300 Network  Behavioral Security appliance

    altitude360        OBJECT IDENTIFIER ::= { extremeProduct 116 }
				 -- altitude360 is the Outdoor Access Point(OAP)

    altitude450        OBJECT IDENTIFIER ::= { extremeProduct 117 }
				 -- altitude450 is the Next Generation Access Point(NGAP - supports high speed 11n WLAN)

    summitX650-24x-SSns      OBJECT IDENTIFIER ::= { extremeProduct 118 }
                          -- 24-port SummitX650 SFP+ switch +  VIM1-SummitStack (10G stack ports not selected)

    summitX650-24t-SSns      OBJECT IDENTIFIER ::= { extremeProduct 119 }
                          -- 24-port SummitX650 10GBaseT switch + VIM1-SummitStack (10G stack ports not selected)

    summitX650-24x-SS        OBJECT IDENTIFIER ::= { extremeProduct 120 }
                          -- 24-port SummitX650 SFP+ switch +  VIM1-SummitStack (10G stack ports selected)

    summitX650-24t-SS        OBJECT IDENTIFIER ::= { extremeProduct 121 }
                          -- 24-port  SummitX650 10GBaseT switch +  VIM1-SummitStack (10G stack ports selected)

    summitX650-24x-10G8X     OBJECT IDENTIFIER ::= { extremeProduct 122 }
                          -- 24-port SummitX650 SFP+ switch +  VIM1-10G8X

    summitX650-24t-10G8X     OBJECT IDENTIFIER ::= { extremeProduct 123 }
                          -- 24-port SummitX650 10GBaseT switch +  VIM1-10G8X

    summitX650-24x-SS256     OBJECT IDENTIFIER ::= { extremeProduct 124 }
                          -- 24-port SummitX650 SFP+ switch +  VIM1-SummitStack256

    summitX650-24t-SS256     OBJECT IDENTIFIER ::= { extremeProduct 125 }
                          -- 24-port SummitX650 10GBaseT +  VIM1-SummitStack256

    summitX650-24x-SS512     OBJECT IDENTIFIER ::= { extremeProduct 126 }
                          -- 24-port SummitX650 SFP+ switch +  VIM1-SummitStack512

    summitX650-24t-SS512     OBJECT IDENTIFIER ::= { extremeProduct 127 }
                          -- 24-port SummitX650 10GBaseT switch +  VIM1-SummitStack512
 
    bd20808            OBJECT IDENTIFIER ::= { extremeProduct 128 }
                             -- BD20808 10 slot Chassis 2 MSMs and 8 IO blades
    
    nwi-e450a          OBJECT IDENTIFIER ::= { extremeProduct 129 }
                             -- derived from summitX450a-24t for Ericsson OEM chassis blade  
                             -- 13 copper ports
                             -- 2 fiber ports
                             -- no stacking
    
    sentriantPS200v1     OBJECT IDENTIFIER ::= { extremeProduct 130 }
                               -- Sentriant PS200 Network Security Violation Monitoring appliance

    wirelessProducts  OBJECT IDENTIFIER ::= { extremeProduct 131 }

    summitWM3700       OBJECT IDENTIFIER ::= { wirelessProducts 15 }
                             -- Summit WM3700 WLAN Controller. Manages up to 256 Access Points 

    summitWM3600       OBJECT IDENTIFIER ::= { wirelessProducts 16 }
                             -- Summit WM3600 WLAN Controller. Manages up to 48 Access Points

    summitWM3400       OBJECT IDENTIFIER ::= { wirelessProducts 18 }
                             -- 5x 10/100/1000 LAN ports, 1x 10/100/1000 WAN port
                                                    
    bd20804            OBJECT IDENTIFIER ::= {extremeProduct 132 }
                             -- BD20804 6 slot Chassis 2 MSMs and 4 IO blades

    summitX480-48t       OBJECT IDENTIFIER ::= { extremeProduct 133 }
                         -- SummitX480-48t 48-port 10/100/1000 BASE-T,4-port 100/1000 BASE-X SFP (shared)

    summitX480-48t-SS    OBJECT IDENTIFIER ::= { extremeProduct 134 }
                         -- SummitX480-48t 48-port 10/100/1000 BASE-T,4-port 100/1000 BASE-X SFP (shared)
                         -- with VIM2-SummitStack

    summitX480-48t-10G4X OBJECT IDENTIFIER ::= { extremeProduct 135 }
                         -- SummitX480-48t 48-port 10/100/1000 BASE-T,4-port 100/1000 BASE-X SFP (shared)
                         -- with VIM2-10G4X

    summitX480-48t-SS128 OBJECT IDENTIFIER ::= { extremeProduct 136 }
                         -- SummitX480-48t 48-port 10/100/1000 BASE-T,4-port 100/1000 BASE-X SFP (shared)
                         -- with VIM2-SummitStack128

    summitX480-24x       OBJECT IDENTIFIER ::= { extremeProduct 137}
                         -- SummitX480-24x 24-port 100/1000 BASE-X SFP, 12 10/100/1000 BASE-T (shared) and 2 10G XFP ports

    summitX480-24x-SS    OBJECT IDENTIFIER ::= { extremeProduct 138 }
                         -- SummitX480-24x 24-port 100/1000 BASE-X SFP, 12 10/100/1000 BASE-T (shared) and 2 10G XFP ports
                         -- with VIM2-SummitStack

    summitX480-24x-10G4X OBJECT IDENTIFIER ::= { extremeProduct 139 }
                         -- SummitX480-24x 24-port 100/1000 BASE-X SFP, 12 10/100/1000 BASE-T (shared) and 2 10G XFP ports
                         -- with VIM2-10G4X

    summitX480-24x-SS128 OBJECT IDENTIFIER ::= { extremeProduct 140 }
                         -- SummitX480-24x 24-port 100/1000 BASE-X SFP, 12 10/100/1000 BASE-T (shared) and 2 10G XFP ports
                         -- with VIM2-SummitStack128

    summitX480-48x       OBJECT IDENTIFIER ::= { extremeProduct 141 }
                         -- SummitX480-48x 48-port 100/1000 BASE-X SFP 

    summitX480-48x-SS    OBJECT IDENTIFIER ::= { extremeProduct 142 }
                         -- SummitX480-48x 48-port 100/1000 BASE-X SFP 
                         -- with VIM2-SummitStack

    summitX480-48x-10G4X OBJECT IDENTIFIER ::= { extremeProduct 143 }
                         -- SummitX480-48x 48-port 100/1000 BASE-X SFP 
                         -- with VIM2-10G4X

    summitX480-48x-SS128  OBJECT IDENTIFIER ::= { extremeProduct 144 }
                         -- SummitX480-48x 48-port 100/1000 BASE-X SFP 
                         -- with VIM2-SummitStack128

    altitude3510         OBJECT IDENTIFIER ::= { extremeProduct 145 }
                               -- Dual Radio, Indoor Access Point, IEEE 802.11a/b/g

    altitude3550         OBJECT IDENTIFIER ::= { extremeProduct 146 }
                               -- Dual Radio, Outdoor Access Point, IEEE 802.11a/b/g 

    altitude4610         OBJECT IDENTIFIER ::= { extremeProduct 148 }
                               -- Dual Radio, Indoor Access Point - Internal antennas, IEEE 802.11a/b/g/n

    altitude4620         OBJECT IDENTIFIER ::= { extremeProduct 149 }
                               -- Dual Radio, Indoor Access Point - External antennas, IEEE 802.11a/b/g/n

    summitX450e-24t      OBJECT IDENTIFIER ::= { extremeProduct 150 }
			 -- 20 10/100/1000 copper ports
			 -- 4 combo copper/fiber ports 
                         -- XGM2 2 optional 10 gig ports
                         -- 2 10G stacking ports

    summitX450e-48t      OBJECT IDENTIFIER ::= { extremeProduct 151 }
			 -- 44 10/100/1000 copper ports
			 -- 4 combo copper/fiber ports 
                         -- XGM2 2 optional 10 gig ports
                         -- 2 10G stacking ports

    summitX460-24t         OBJECT IDENTIFIER ::= { extremeProduct 152 }
                          -- Summit X460: 20-ports copper + 4-ports combo copper/fiber + 4-ports fiber

    summitX460-24p         OBJECT IDENTIFIER ::= { extremeProduct 153 }
                          -- Summit X460: 20-ports POE+ copper + 4-ports combo copper/fiber + 4-ports fiber

    summitX460-24x         OBJECT IDENTIFIER ::= { extremeProduct 154 }
                          -- Summit X460: 20-ports fiber + 4-ports combo fiber/copper + 4-ports copper

    summitX460-48t         OBJECT IDENTIFIER ::= { extremeProduct 155 }
                          -- Summit X460: 48-ports copper + 4-ports fiber

    summitX460-48p         OBJECT IDENTIFIER ::= { extremeProduct 156 }
                          -- Summit X460: 48-ports POE+ copper + 4-ports fiber

    summitX460-48x         OBJECT IDENTIFIER ::= { extremeProduct 157 }
                          -- Summit X460: 48-ports fiber

    altitude4700           OBJECT IDENTIFIER ::= {extremeProduct 158 }
                                 -- High performance dual radio or tri-radio 802.11abgn access points with 3x3 MIMO. 

    summitX480-24x-SSV80 OBJECT IDENTIFIER ::= { extremeProduct 159 }
                         -- SummitX480-24x 24-port 100/1000 BASE-X SFP, 12 10/100/1000 BASE-T (shared) and 2 10G XFP ports
                         -- with VIM2-SummitStack-V80
    
    summitX480-48x-SSV80  OBJECT IDENTIFIER ::= { extremeProduct 160 }
                         -- SummitX480-48x 48-port 100/1000 BASE-X SFP 
                         -- with VIM2-SummitStack-V80

    summitX480-48t-SSV80 OBJECT IDENTIFIER ::= { extremeProduct 161 }
                         -- SummitX480-48t 48-port 10/100/1000 BASE-T,4-port 100/1000 BASE-X SFP (shared)
                         -- with VIM2-SummitStack-V80

    summitX650-24x-40G4X OBJECT IDENTIFIER ::= { extremeProduct 162 }
                         -- SummitX650-24x 24-port 1000/10000 SFP+ switch
                         -- with VIM3-40G4X
    
    summitX650-24t-40G4X OBJECT IDENTIFIER ::= { extremeProduct 163 }
                         -- SummitX650-24t 24-port 1000/10000 BASE-T switch
                         -- with VIM3-40G4X
    
    summitX480-24x-40G4X OBJECT IDENTIFIER ::= { extremeProduct 164 }
                         -- SummitX480-24x 24-port 100/1000 BASE-X SFP, 12 10/100/1000 BASE-T (shared) and 2 10G XFP ports
                         -- with VIM3-40G4X

    summitX480-48x-40G4X OBJECT IDENTIFIER ::= { extremeProduct 165 }
                         -- SummitX480-48x 48-port 100/1000 BASE-X SFP
                         -- with VIM3-40G4X

    summitX480-48t-40G4X OBJECT IDENTIFIER ::= { extremeProduct 166 }
                         -- SummitX480-48t 48-port 10/100/1000 BASE-T,4-port 100/1000 BASE-X SFP (shared)
                         -- with VIM3-40G4X
    
    summitX670-48x       OBJECT IDENTIFIER ::= { extremeProduct 167 }
                         -- 48-port SFP+ switch 

    summitX670v-48x      OBJECT IDENTIFIER ::= { extremeProduct 168 }
                         --  48-port SFP+ switch
                         -- with VIM4-40G4X
    
    e4g-400               OBJECT IDENTIFIER ::= { extremeProduct 169 }
                          -- E4G-400 20-ports copper + 4-ports combo copper/fiber + 4-ports fiber with SyncE

    e4g-200               OBJECT IDENTIFIER ::= { extremeProduct 171 }
                          -- E4G-200 Mobile Backhaul Cell Site Router 8-port 10/100/1000, 4 port SFP

    summitX440-8t       OBJECT IDENTIFIER ::= { extremeProduct 172 }
                          -- Summit X440: 8 10/100/1000BASE-T, 4 1000BASE-X SFP ports, Summit Stack Stacking ports

    summitX440-8p       OBJECT IDENTIFIER ::= { extremeProduct 173 }
                          -- Summit X440: 8 10/100/1000BASE-T PoE+, 4 1000BASE-X SFP ports, Summit Stack Stacking ports

    summitX440-24t      OBJECT IDENTIFIER ::= { extremeProduct 174 }
                          -- Summit X440: 24 10/100/1000BASE-T, 4 1000BASE-X SFP combo ports, Summit Stack Stacking ports

    summitX440-24p      OBJECT IDENTIFIER ::= { extremeProduct 175 }
                          -- Summit X440: 24 10/100/1000BASE-T PoE+, 4 1000BASE-X SFP combo ports, Summit Stack Stacking ports

    summitX440-48t      OBJECT IDENTIFIER ::= { extremeProduct 176 }
                          -- Summit X440: 48 10/100/1000BASE-T, 4 1000BASE-X SFP combo ports, Summit Stack Stacking ports

    summitX440-48p      OBJECT IDENTIFIER ::= { extremeProduct 177 }
                          -- Summit X440: 48 10/100/1000BASE-T PoE+, 4 1000BASE-X SFP combo ports, Summit Stack Stacking ports

    summitX440-24t-10G  OBJECT IDENTIFIER ::= { extremeProduct 178 }
                          -- Summit X440: 24 10/100/1000BASE-T, 4 1000BASE-X SFP combo ports, 2 10GBASE-X SFP+

    summitX440-24p-10G  OBJECT IDENTIFIER ::= { extremeProduct 179 }
                          -- Summit X440: 24 10/100/1000BASE-T PoE+, 4 1000BASE-X SFP combo ports, 2 10GBASE-X SFP+

    summitX440-48t-10G  OBJECT IDENTIFIER ::= { extremeProduct 180 }
                          -- Summit X440: 48 10/100/1000BASE-T, 2 1000BASE-X SFP combo ports, 2 10GBASE-X SFP+

    summitX440-48p-10G  OBJECT IDENTIFIER ::= { extremeProduct 181 }
                          -- Summit X440: 48 10/100/1000BASE-T PoE+, 2 1000BASE-X SFP combo ports, 2 10GBASE-X SFP+

    ags100-24t OBJECT IDENTIFIER ::= { extremeProduct 182 }
                         --	AGS100-24t
                         --	AGS 24-port TX Gig switch with 4 combo SFP 1000 Mbps ports
 
    ags150-24p OBJECT IDENTIFIER ::= { extremeProduct 183 }
                         --	AGS150-24p
                         --	AGS 24-port TX PoE 10G stack switch with 4 combo SFP 1000 Mbps ports 
                         -- and 2 CX4 10G Stacking ports
                         
    bdx8                 OBJECT IDENTIFIER ::= { extremeProduct 170 }
                           --  BlackDiamond X 8 Slot Chassis

    summitX670v-48t      OBJECT IDENTIFIER ::= { extremeProduct 184 }
                         -- 48 port 10GBASE-T switch
                         -- with 4 SFP+ combo ports and VIM4-40G4X optional card

    summitX440-L2-24t  OBJECT IDENTIFIER ::= { extremeProduct 185 }
                          -- Summit X440 L2 only: 24 10/100/1000BASE-T, 4 1000BASE-X SFP combo ports, Summit Stack is not supported

    summitX440-L2-48t  OBJECT IDENTIFIER ::= { extremeProduct 186 }
                          -- Summit X440 L2 only: 48 10/100/1000BASE-T, 4 1000BASE-X SFP combo ports, Summit Stack is not supported

    summitX440-24x      OBJECT IDENTIFIER ::= { extremeProduct 188 }
                          -- Summit X440: 24 1000BASE-X SFP ports, Summit Stack Stacking ports

    summitX440-24x-10g  OBJECT IDENTIFIER ::= { extremeProduct 189 }
                          -- Summit X440: 24 1000BASE-X SFP ports, 4 10/100/1000 copper combo ports, 2 10GBASE-X SFP+

    summitX440-24tdc    OBJECT IDENTIFIER ::= { extremeProduct 192 }
                          -- Summit X440: DC powered 24 10/100/1000BASE-T, 4 1000BASE-X SFP combo ports, Summit Stack Stacking ports

    summitX440-48tdc    OBJECT IDENTIFIER ::= { extremeProduct 193 }
                          -- Summit X440: DC powered 48 10/100/1000BASE-T, 4 1000BASE-X SFP combo ports, Summit Stack Stacking ports

    summitX430-24t      OBJECT IDENTIFIER ::= { extremeProduct 190 }
                          -- Summit X430: L2 only, 24 10/100/1000BASE-T, 4 1000BASE-X SFP ports, Summit Stack is not supported

    summitX430-48t      OBJECT IDENTIFIER ::= { extremeProduct 191 }
                          -- Summit X430: L2 only, 48 10/100/1000BASE-T, 4 1000BASE-X SFP ports, Summit Stack is not supported

    --
    -- Assorted OIDs that are pointed to by other MIBs 
    --
    extremeOids
         OBJECT IDENTIFIER ::= { extremeMisc 1 }

   --
   -- OIDs for as-yet-unstandardised 802.3 MAU types
   --     (see MAU MIB for usage)
   --
    extremeMauType
         OBJECT IDENTIFIER ::= { extremeOids 1 }

     extremeMauType1000BaseSX OBJECT IDENTIFIER
     ::= { extremeMauType 1 }
         -- "X fiber over short-wavelength laser PMD as specified
         -- in clause 38, duplex mode unknown"

     extremeMauType1000BaseLX OBJECT IDENTIFIER
     ::= { extremeMauType 2 }
         -- "X fiber over long-wavelength laser PMD as specified
         -- in clause 38, duplex mode unknown"

     extremeMauType1000BaseCX OBJECT IDENTIFIER
     ::= { extremeMauType 3 }
         -- "X copper over 150-ohm balanced cable PMD as specified
         -- in clause 39, duplex mode unknown"

     extremeMauType1000BaseSXFD OBJECT IDENTIFIER
     ::= { extremeMauType 4 }
         -- "X fiber over short-wavelength laser PMD as specified
         -- in clause 38, full-duplex mode"

     extremeMauType1000BaseLXFD OBJECT IDENTIFIER
     ::= { extremeMauType 5 }
         -- "X fiber over long-wavelength laser PMD as specified
         -- in clause 38, full-duplex mode"

     extremeMauType1000BaseCXFD OBJECT IDENTIFIER
     ::= { extremeMauType 6 }
         -- "X copper over 150-ohm balanced cable PMD as specified
         -- in clause 39, full-duplex mode"

     extremeMauType1000BaseWDMHD OBJECT IDENTIFIER
     ::= { extremeMauType 7 }
         -- "Gigabit WDM, half duplex"

     extremeMauType1000BaseWDMFD OBJECT IDENTIFIER
     ::= { extremeMauType 8 }
         -- "Gigabit WDM, full duplex"

     extremeMauType1000BaseLX70HD OBJECT IDENTIFIER
     ::= { extremeMauType 9 }
         -- "Gigabit LX70, half duplex"

     extremeMauType1000BaseLX70FD OBJECT IDENTIFIER
     ::= { extremeMauType 10 }
         -- "Gigabit LX70, full duplex"

     extremeMauType1000BaseZXHD OBJECT IDENTIFIER
     ::= { extremeMauType 11 }
         -- "Gigabit ZX, half duplex"

     extremeMauType1000BaseZXFD OBJECT IDENTIFIER
     ::= { extremeMauType 12 }
         -- "Gigabit ZX, full duplex"

     extremeMauType1000BaseLX100HD OBJECT IDENTIFIER
     ::= { extremeMauType 13 }
         -- "Gigabit LX100, half duplex"

     extremeMauType1000BaseLX100FD OBJECT IDENTIFIER
     ::= { extremeMauType 14 }
         -- "Gigabit LX100, full duplex"

     extremeMauType10GBaseCX4 OBJECT IDENTIFIER
     ::= { extremeMauType 15 }
         -- "10 Gigabit CX4"

     extremeMauType10GBaseZR OBJECT IDENTIFIER
     ::= { extremeMauType 16 }
         -- "10 Gigabit ZR"

     extremeMauType10GBaseDWDM OBJECT IDENTIFIER
     ::= { extremeMauType 17 }
         -- "10 Gigabit DWDM"

     extremeMauType10GBaseCX OBJECT IDENTIFIER
     ::= { extremeMauType 18 }
         -- "10 Gigabit CX - SFP+ twin coax cable"

     extremeMauType10GBaseT OBJECT IDENTIFIER
          ::= { extremeMauType 19 }
         -- "10 Gigabit BaseT "

     extremeMauType40GBaseX OBJECT IDENTIFIER
          ::= { extremeMauType 20 }
         -- "40 Gigabit BaseX "

    -- ===============================================================================

    --
    -- Extreme MIB Objects
    --
    extremeSystem          OBJECT IDENTIFIER ::= { extremeAgent 1 }
    extremeVlan            OBJECT IDENTIFIER ::= { extremeAgent 2 }
    extremeQos             OBJECT IDENTIFIER ::= { extremeAgent 3 }
    extremePort            OBJECT IDENTIFIER ::= { extremeAgent 4 }
    extremeVC              OBJECT IDENTIFIER ::= { extremeAgent 5 }
    extremeTrapPoll        OBJECT IDENTIFIER ::= { extremeAgent 6 }
    extremeQosPolicy       OBJECT IDENTIFIER ::= { extremeAgent 7 }
    extremeDlcs            OBJECT IDENTIFIER ::= { extremeAgent 8 }
    extremeFileTransfer    OBJECT IDENTIFIER ::= { extremeAgent 10 }
    extremeRtStats         OBJECT IDENTIFIER ::= { extremeAgent 11 }
    extremeEsrp            OBJECT IDENTIFIER ::= { extremeAgent 12 }
    extremeEdp             OBJECT IDENTIFIER ::= { extremeAgent 13 }
    extremeSlb             OBJECT IDENTIFIER ::= { extremeAgent 14 }
    extremeOspf            OBJECT IDENTIFIER ::= { extremeAgent 15 }
    extremeFdb             OBJECT IDENTIFIER ::= { extremeAgent 16 }
    extremeStp             OBJECT IDENTIFIER ::= { extremeAgent 17 }
    extremeEaps            OBJECT IDENTIFIER ::= { extremeAgent 18 }
    extremeLacp            OBJECT IDENTIFIER ::= { extremeAgent 19 }
    extremePOSMib          OBJECT IDENTIFIER ::= { extremeAgent 20 }
    extremeNPMib           OBJECT IDENTIFIER ::= { extremeAgent 21 }
    extremeNetFlow         OBJECT IDENTIFIER ::= { extremeAgent 22 }
    extremeSnmpv3          OBJECT IDENTIFIER ::= { extremeAgent 23 }
    extremeCable           OBJECT IDENTIFIER ::= { extremeAgent 24 }
    extremeWireless 	   OBJECT IDENTIFIER ::= { extremeAgent 25 }
    extremeServices 	   OBJECT IDENTIFIER ::= { extremeAgent 26 }
    extremePoE             OBJECT IDENTIFIER ::= { extremeAgent 27 }
    extremeDosMib          OBJECT IDENTIFIER ::= { extremeAgent 28 }
    extremeEnhDosMib       OBJECT IDENTIFIER ::= { extremeAgent 29 }
    extremeClearflow       OBJECT IDENTIFIER ::= { extremeAgent 30 }
    extremeEntity          OBJECT IDENTIFIER ::= { extremeAgent 31 }
    extremeSwMonitor       OBJECT IDENTIFIER ::= { extremeAgent 32 }
    extremeStackable       OBJECT IDENTIFIER ::= { extremeAgent 33 }
    extremeIpSecurity      OBJECT IDENTIFIER ::= { extremeAgent 34 }
    extremeUpm             OBJECT IDENTIFIER ::= { extremeAgent 35 }
    extremeIdMgr           OBJECT IDENTIFIER ::= { extremeAgent 36 }
    extremeMplsMIB         OBJECT IDENTIFIER ::= { extremeAgent 37 }
    extremeHclag           OBJECT IDENTIFIER ::= { extremeAgent 38 }
    extremeVM              OBJECT IDENTIFIER ::= { extremeAgent 39 }
    extremeAutoProvision   OBJECT IDENTIFIER ::= { extremeAgent 40 }
    extremeMlag            OBJECT IDENTIFIER ::= { extremeAgent 41 }
    extremeCfgMgmt         OBJECT IDENTIFIER ::= { extremeAgent 42 }

    extremeAP 		   OBJECT IDENTIFIER ::= { extremeWireless 1 }
    extremeLAC 		   OBJECT IDENTIFIER ::= { extremeWireless 2 }

    PortList ::= TEXTUAL-CONVENTION
        STATUS current
        DESCRIPTION
            "Each octet within this value specifies a set of eight
            ports, with the first octet specifying ports 1 through
            8, the second octet specifying ports 9 through 16, etc.
            Within each octet, the most significant bit represents
            the lowest numbered port, and the least significant bit
            represents the highest numbered port.  Thus, each port
            of the bridge is represented by a single bit within the
            value of this object.  If that bit has a value of '1'
            then that port is included in the set of ports; the port
            is not included if its bit has a value of '0'. If the
            object has a length of 0 then it is taken to refer to all
            of the ports in a given device."
        SYNTAX      OCTET STRING

    L4Port ::= TEXTUAL-CONVENTION
        STATUS  current
        DESCRIPTION
            "The value of a transport layer (layer-4) port number, in network
            byte order. A value of 0 indicates all allowed values of this 
            field i.e. wildcard."
        SYNTAX  INTEGER (0|1..65535)

    ExtremeGenAddr ::= TEXTUAL-CONVENTION
         STATUS      current
         DESCRIPTION
             "The value of an address."
         SYNTAX      OCTET STRING (SIZE (0..20))

    ExtremeDeviceId ::= TEXTUAL-CONVENTION
         STATUS      current
         DESCRIPTION
             "The switch identifier used by Extreme EDP protocol."
         SYNTAX      OCTET STRING (SIZE (8))

WPACipherSet ::= TEXTUAL-CONVENTION
	STATUS current
	DESCRIPTION
		"A set of supported ciphers which can be advertised
	 	 by WPA stations.  Each set bit indicates support for
		 a given cipher suite.  The special value none is 
		 allowed for representing the absence of information.
		 The value other is used to indicate an unknown cipher."
	SYNTAX BITS {
	        none(0),
		wep64(1),
		tkip(2),
		wrap(3),
		ccmp(4),
		wep128(5),
		other(6) }

WPAKeyMgmtSet ::= TEXTUAL-CONVENTION
	STATUS current
	DESCRIPTION
		"A set of supported key management suites.  For more info
		 see IEEE 802.11i D3.0 section 7."
	SYNTAX BITS {
		none(0),
		dot1x(1),
		psk(2)
	}

ClientAuthType ::= TEXTUAL-CONVENTION
	STATUS current
	DESCRIPTION "Type of client specified in the netlogin traps as well as the client table. For
			wired clients, only none, netlogin and dot1x are valid"
	SYNTAX INTEGER {
                          none(0),	   
			  open(1),
			  wep(2),
			  mac-based(3),
			  dot1x(4),
			  wpa-psk(5),
			  web-based (6),
    			  wpa2(7),
    			  wpa(8),
    			  wpa2-psk(9)}

WirelessRemoteConnectBindingType ::= TEXTUAL-CONVENTION
STATUS current
DESCRIPTION "The type of binding to be used when mapping APs to virtual ports"
SYNTAX INTEGER { 
    none(0),
    mac-address(1),
    serial-number(2),
    ip-address(3)}

END
