ENTERASYS-TWCB-MIB-2 DEFINITIONS ::= BEGIN

--  enterasys-twcb-mib-2.txt
--
--  Part Number:
--
--
--  This module provides authoritative definitions for Enterasys
--  Networks Transparent Web Cache Balancing (TWCB) functionality.
--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright March, 2010 Enterasys Networks, Inc.

IMPORTS
    MODULE-IDENTITY, OBJECT-TYPE
        FROM SNMPv2-SMI
    Unsigned32, Gauge32, Counter32
        FROM SNMPv2-SMI
    MODULE-COMPLIANCE, OBJECT-GROUP
        FROM SNMPv2-CONF
    RowStatus, TruthValue, DateAndTime
        FROM SNMPv2-TC
    InetVersion, InetAddressType, InetAddress, InetPortNumber
        FROM INET-ADDRESS-MIB
    etsysModules
        FROM ENTERASYS-MIB-NAMES
    SnmpAdminString
        FROM SNMP-FRAMEWORK-MIB;

etsysTWCBMIB MODULE-IDENTITY
LAST-UPDATED     "201008171215Z"  -- August 17, 2010, 12:15PM GMT
ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "The Enterasys Networks Proprietary MIB module for entities
         implementing TWCB."

    REVISION    "201008171215Z"  -- August 17, 2010, 12:15PM GMT
    DESCRIPTION "Initial version"
    
    ::= { etsysModules 76 }

-- -------------------------------------------------------------
-- TWCB MIB Groups
-- -------------------------------------------------------------

etsysTwcbGlobal             OBJECT IDENTIFIER ::= { etsysTWCBMIB 1 }
etsysTwcbGlobalStats        OBJECT IDENTIFIER ::= { etsysTwcbGlobal 1 }

etsysTwcbTables             OBJECT IDENTIFIER ::= { etsysTWCBMIB 2 }
etsysTwcbConformance        OBJECT IDENTIFIER ::= { etsysTWCBMIB 3 }

-- -------------------------------------------------------------
-- TWCB Global Statistics Branch
-- -------------------------------------------------------------
etsysTwcbStatsCachesUsed OBJECT-TYPE
    SYNTAX       Gauge32
    MAX-ACCESS   read-only
    STATUS       current
    DESCRIPTION
        "This object contains the number of TWCB Cache servers 
         currently configured."
    ::= { etsysTwcbGlobalStats 1 }

etsysTwcbStatsWcServerfarmsUsed OBJECT-TYPE
    SYNTAX       Gauge32
    MAX-ACCESS   read-only
    STATUS       current
    DESCRIPTION
        "This object contains the number of TWCB Server farms 
         currently configured."
    ::= { etsysTwcbGlobalStats 2 }

etsysTwcbStatsWebcacheUsed OBJECT-TYPE
    SYNTAX       Gauge32
    MAX-ACCESS   read-only
    STATUS       current
    DESCRIPTION
        "This object contains the number of TWCB Webcache servers 
         currently configured."
    ::= { etsysTwcbGlobalStats 3 }

etsysTwcbStatsBindingsCurrent OBJECT-TYPE
    SYNTAX       Gauge32
    MAX-ACCESS   read-only
    STATUS       current
    DESCRIPTION
        "This object contains the current number of active TWCB 
         bindings."
    ::= { etsysTwcbGlobalStats 4 }

etsysTwcbStatsBindingsHigh OBJECT-TYPE
    SYNTAX       Gauge32
    MAX-ACCESS   read-only
    STATUS       current
    DESCRIPTION
        "This object contains the highest number of TWCB active
         bindings active at one time."
    ::= { etsysTwcbGlobalStats 5 }

etsysTwcbStatsBindingsDeleted OBJECT-TYPE
    SYNTAX       Counter32
    MAX-ACCESS   read-only
    STATUS       current
    DESCRIPTION
        "This object contains the total number of TWCB
         bindings that have been deleted."
    ::= { etsysTwcbGlobalStats 6 }

etsysTwcbStatsBindingsTotal OBJECT-TYPE
    SYNTAX       Counter32
    MAX-ACCESS   read-only
    STATUS       current
    DESCRIPTION
        "This object contains the total number of TWCB bindings
         created."
    ::= { etsysTwcbGlobalStats 7 }

etsysTwcbStatsBindingsExhausted OBJECT-TYPE
    SYNTAX       Counter32
    MAX-ACCESS   read-only
    STATUS       current
    DESCRIPTION
        "This object contains the number of times a request to create
         a TWCB binding failed because there were no available free
         entries."
    ::= { etsysTwcbGlobalStats 8 }

etsysTwcbStatsBindingsNoCaches OBJECT-TYPE
    SYNTAX       Counter32
    MAX-ACCESS   read-only
    STATUS       current
    DESCRIPTION
        "This object contains the number of times a request to create
         a TWCB binding failed because there were no available Caches
         to establish a binding."
    ::= { etsysTwcbGlobalStats 9 }

etsysTwcbStatsBindingsPerSecond OBJECT-TYPE
    SYNTAX       Gauge32
    MAX-ACCESS   read-only
    STATUS       current
    DESCRIPTION
        "This object contains the average number of TWCB bindings 
         created per second. Normalized for 5 seconds."
    ::= { etsysTwcbGlobalStats 10 }

etsysTwcbStatsWebcacheActive OBJECT-TYPE
    SYNTAX       Gauge32
    MAX-ACCESS   read-only
    STATUS       current
    DESCRIPTION
        "This object contains the current number of active Webcache
         server entries."
    ::= { etsysTwcbGlobalStats 11 }

etsysTwcbStatsWebcacheHigh OBJECT-TYPE
    SYNTAX       Gauge32
    MAX-ACCESS   read-only
    STATUS       current
    DESCRIPTION
        "This object contains the highest number of active Webcache 
         server entries at one time."
    ::= { etsysTwcbGlobalStats 12 }

etsysTwcbStatsWcServerfarmActive OBJECT-TYPE
    SYNTAX       Gauge32
    MAX-ACCESS   read-only
    STATUS       current
    DESCRIPTION
        "This object contains the current number of active Server farm
         entries."
    ::= { etsysTwcbGlobalStats 13 }

etsysTwcbStatsWcServerfarmHigh OBJECT-TYPE
    SYNTAX       Gauge32
    MAX-ACCESS   read-only
    STATUS       current
    DESCRIPTION
        "This object contains the highest number of active Server farm 
         entries at one time."
    ::= { etsysTwcbGlobalStats 14 }

etsysTwcbStatsCacheActive OBJECT-TYPE
    SYNTAX       Gauge32
    MAX-ACCESS   read-only
    STATUS       current
    DESCRIPTION
        "This object contains the current number of active Cache server
         entries."
    ::= { etsysTwcbGlobalStats 15 }

etsysTwcbStatsCacheHigh OBJECT-TYPE
    SYNTAX       Gauge32
    MAX-ACCESS   read-only
    STATUS       current
    DESCRIPTION
        "This object contains the highest number of active Cache server
         entries at one time."
    ::= { etsysTwcbGlobalStats 16 }

etsysTwcbStatsClear OBJECT-TYPE
    SYNTAX       TruthValue
    MAX-ACCESS   read-write
    STATUS       current
    DESCRIPTION
        "Setting this object to a value of true(1) will cause the
         following objects to be reset to zero and new values
         generated:
         etsysTwcbStatsBindingsDeleted,
         etsysTwcbStatsBindingsTotal,
         etsysTwcbStatsBindingsExhausted,
         etsysTwcbStatsBindingsNoCaches,
         etsysTwcbStatsBindingsPerSecond,
         etsysTwcbWcServerfarmHits,
         etsysTwcbWcServerfarmStateChanges,
         etsysTwcbCacheHits,
         etsysTwcbCacheStateChanges,
         etsysTwcbWebcacheHits,
         etsysTwcbWebcacheStateChanges.
         The following objects will be reset to the current active
         counts:
         etsysTwcbStatsBindingsHigh,
         etsysTwcbStatsWebcacheHigh,
         etsysTwcbStatsWcServerfarmHigh,
         etsysTwcbStatsCacheHigh

         Setting this object to a value of false(2) has no effect.
         This object will always return a value of false(2)."
    DEFVAL       { false }
    ::= { etsysTwcbGlobalStats 17 }
    
 etsysTwcbStatsClearDateAndTime OBJECT-TYPE
    SYNTAX       DateAndTime
    MAX-ACCESS   read-only
    STATUS       current
    DESCRIPTION
        "The date / time the TWCB statistics was cleared."
    ::= { etsysTwcbGlobalStats 18 }
    
etsysTwcbStatsMinTimeoutValue OBJECT-TYPE
    SYNTAX       Unsigned32
    UNITS        "seconds" 
    MAX-ACCESS   read-only
    STATUS       current
    DESCRIPTION
         "The minimum timeout value allowable for Twcb timeouts."
    ::= { etsysTwcbGlobalStats 19 }

etsysTwcbStatsMaxTimeoutValue OBJECT-TYPE
    SYNTAX       Unsigned32
    UNITS        "seconds" 
    MAX-ACCESS   read-only
    STATUS       current
    DESCRIPTION
         "The maximum timeout value allowable for Twcb timeouts."
    ::= { etsysTwcbGlobalStats 20 }

-- -------------------------------------------------------------
-- TWCB Server Farm Table
-- -------------------------------------------------------------

etsysTwcbWcServerfarmTable OBJECT-TYPE
    SYNTAX       SEQUENCE OF EtsysTwcbWcServerfarmEntry
    MAX-ACCESS   not-accessible
    STATUS       current
    DESCRIPTION
        "A table containing objects defining the configuration 
         parameters, operational state and runtime statistics of
         TWCB Server farms."
    ::={ etsysTwcbTables  1 }

etsysTwcbWcServerfarmEntry OBJECT-TYPE
    SYNTAX       EtsysTwcbWcServerfarmEntry
    MAX-ACCESS   not-accessible
    STATUS       current
    DESCRIPTION
        "An entry in the etsysTwcbWcServerfarmTable containing the 
         operational characteristics of a TWCB Server farm. A TWCB
         Server farm contains a grouping of Cache servers 
         (etsysTwcbCacheEntry) that HTTP requests will be redirected
         to via the associated TWCB Webcache 
         (etsysTwcbWebcacheServerEntry)."
    INDEX    { etsysTwcbWcServerfarmInetVersion,
               etsysTwcbWcServerfarmName }
    ::= { etsysTwcbWcServerfarmTable 1 }

EtsysTwcbWcServerfarmEntry ::=
    SEQUENCE {
    etsysTwcbWcServerfarmInetVersion
        InetVersion,
    etsysTwcbWcServerfarmName
        SnmpAdminString,
    etsysTwcbWcServerfarmPredictor
        INTEGER,
    etsysTwcbWcServerfarmAdminStatus
        INTEGER,
    etsysTwcbWcServerfarmOperStatus
        INTEGER,
    etsysTwcbWcServerfarmConns
        Gauge32,
    etsysTwcbWcServerfarmHits
        Counter32,
    etsysTwcbWcServerfarmStateChanges
        Counter32,
    etsysTwcbWcServerfarmLastStateChangeDateAndTime
        DateAndTime,
    etsysTwcbWcServerfarmCachesCfg
        Gauge32,
    etsysTwcbWcServerfarmCachesUp
        Gauge32,
    etsysTwcbWcServerfarmWebcacheCfg
        Gauge32,
    etsysTwcbWcServerfarmRoundRobinCount
        Counter32,
    etsysTwcbWcServerfarmRowStatus
         RowStatus,
    etsysTwcbWcServerfarmId
        Unsigned32
    }

etsysTwcbWcServerfarmInetVersion OBJECT-TYPE
    SYNTAX       InetVersion
    MAX-ACCESS   not-accessible
    STATUS       current
    DESCRIPTION
        "The Internet address version of the TWCB Server farm."
    ::= { etsysTwcbWcServerfarmEntry 1 }

etsysTwcbWcServerfarmName OBJECT-TYPE
    SYNTAX       SnmpAdminString (SIZE(1..63))
    MAX-ACCESS   not-accessible
    STATUS       current
    DESCRIPTION
        "This object contains the unique name of the TWCB Server farm."
    ::= { etsysTwcbWcServerfarmEntry  2}

etsysTwcbWcServerfarmPredictor OBJECT-TYPE
    SYNTAX       INTEGER {
                   destIpHash(1),
                   roundrobin(2)
                   }
    MAX-ACCESS   read-only
    STATUS       current
    DESCRIPTION
        "This object contains the Predictor value. The predictor value
         defines the method of selecting the appropriate TWCB Cache 
         server when a new TWCB binding request is generated.
         - `destIpHash', indicates the predictor type is
           destIpHash.
         - `roundrobin', indicates the predictor type is round
           robin. A creation of a etsysTwcbWcSfarmRoundRobinEntry
           assigned to this etsysTwcbWcServerfarmName will result in
           this object being set to 'roundrobin'."
    DEFVAL { destIpHash }
    ::= { etsysTwcbWcServerfarmEntry 3 }

etsysTwcbWcServerfarmAdminStatus OBJECT-TYPE
    SYNTAX       INTEGER {
                   disabled(1),
                   enabled(2)
                   }
    MAX-ACCESS   read-create
    STATUS       current
    DESCRIPTION
        "This object contains the Administrative state of the TWCB
         Server farm.
         - `disabled', indicates the Server farm is administratively
           disabled.
         - `enabled', indicates the Server farm is administratively
           enabled."
    DEFVAL { enabled }
    ::= { etsysTwcbWcServerfarmEntry 4 }

etsysTwcbWcServerfarmOperStatus OBJECT-TYPE
    SYNTAX       INTEGER {
                   up(1),
                   down(2)
                   }
    MAX-ACCESS   read-only
    STATUS       current
    DESCRIPTION
        "This object contains the Operational state of the TWCB Server
         farm. The state of the TWCB Server farm will be deemed 'up' 
         when the row is 'active', the 
         etsysTwcbWcServerfarmAdminStatus is 'enabled' and at least 
         one etsysTwcbCacheEntry has been associated with this entry
         and it's etsysTwcbCacheOperStatus is 'up'.
         - `up', indicates the TWCB Server farm is operationally ready.
         - `down', indicates the TWCB Server farm is operationally
            unavailable."
    ::= { etsysTwcbWcServerfarmEntry 5 }

etsysTwcbWcServerfarmConns OBJECT-TYPE
    SYNTAX       Gauge32
    MAX-ACCESS   read-only
    STATUS       current
    DESCRIPTION
        "The current number of active TWCB connections established on
         this TWCB Server farm."
    ::= { etsysTwcbWcServerfarmEntry 6 }

etsysTwcbWcServerfarmHits OBJECT-TYPE
    SYNTAX       Counter32
    MAX-ACCESS   read-only
    STATUS       current
    DESCRIPTION
        "The total number of hits (redirected TWCB requests) this
         TWCB Server farm has received."
     ::= { etsysTwcbWcServerfarmEntry 7 }

etsysTwcbWcServerfarmStateChanges OBJECT-TYPE
    SYNTAX       Counter32
    MAX-ACCESS   read-only
    STATUS       current
    DESCRIPTION
        "The total number of state changes (see
         etsysTwcbWcServerfarmOperStatus) for this TWCB Server farm."
    ::= { etsysTwcbWcServerfarmEntry 8 }

etsysTwcbWcServerfarmLastStateChangeDateAndTime OBJECT-TYPE
    SYNTAX       DateAndTime
    MAX-ACCESS   read-only
    STATUS       current
    DESCRIPTION
        "The date / time the of last TWCB Webcache Server farm state 
         change."
    ::= { etsysTwcbWcServerfarmEntry 9 }

etsysTwcbWcServerfarmCachesCfg OBJECT-TYPE
    SYNTAX       Gauge32
    MAX-ACCESS   read-only
    STATUS       current
    DESCRIPTION
        "The total number of TWCB Cache servers (etsysTwcbCacheEntry)
         currently configured on this TWCB Server farm."
    ::= { etsysTwcbWcServerfarmEntry 10 }

etsysTwcbWcServerfarmCachesUp OBJECT-TYPE
    SYNTAX       Gauge32
    MAX-ACCESS   read-only
    STATUS       current
    DESCRIPTION
        "The total number of TWCB Caches servers (etsysTwcbCacheEntry)
         currently configured on this TWCB Server farm with a
         etsysTwcbCacheOperStatus of 'up'."
    ::= { etsysTwcbWcServerfarmEntry 11 }

etsysTwcbWcServerfarmWebcacheCfg OBJECT-TYPE
    SYNTAX       Gauge32
    MAX-ACCESS   read-only
    STATUS       current
    DESCRIPTION
        "The total number of etsysTwcbWebcacheServerName's bound to this
         etsysTwcbWcServerfarmName established by the creation of a
         etsysTwcbWebcacheServerfarmEntry."
    ::= { etsysTwcbWcServerfarmEntry 12 }

etsysTwcbWcServerfarmRoundRobinCount OBJECT-TYPE
    SYNTAX       Counter32
    MAX-ACCESS   read-only
    STATUS       current
    DESCRIPTION
        "The number of Round robin configurations assigned to the
         webcahce serverfarm. See etsysTwcbWcSfarmRoundRobinTable"
    ::= { etsysTwcbWcServerfarmEntry 13 }

etsysTwcbWcServerfarmRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Server farm entry is available for use by TWCB
           operations. Other writable leaves in this table MAY be
           modified while the row is in the active state.
         createAndGo(4)
         - This is the preferred mechanism for creating conceptual rows
           in this table.  A valid createAndGo requires a unique
           etsysTwcbWcServerfarmName, errors resulting from existing
           etsysTwcbWcServerfarmNames will result in the row not being
           created. All writable leaves have default values so a valid
           createAndGo will always transition a new entry to the
           active(1) state.
         destroy(6)
         - This will remove the etsysTwcbWcServerfarmEntry from the
           etsysTwcbWcServerfarmTable and make it unavailable for TWCB
           operations.  This will result in all associated TWCB entries
           (defined below) to also be deleted.
           TWCB Server Farm Round Robin Table entries
            (etsysTwcbWcSfarmRoundRobinEntry),
           TWCB Cache Server Table entries
            (etsysTwcbCacheEntry),
           TWCB Webcache Server Farm Table
            (etsysTwcbWebcacheServerfarmEntry)."
    ::= { etsysTwcbWcServerfarmEntry 14 }
    
etsysTwcbWcServerfarmId OBJECT-TYPE
    SYNTAX       Unsigned32
    MAX-ACCESS   read-only
    STATUS       current
    DESCRIPTION
         "This value is a unique TWCB Server farm identifier
          assigned by TWCB during creation.  This identifier is used 
          when creating an entry in the 
          etsysTwcbWebcacheServerfarmTable."
    ::= { etsysTwcbWcServerfarmEntry 15 }

-- -------------------------------------------------------------
-- TWCB Server Farm Round Robin Table
-- -------------------------------------------------------------

etsysTwcbWcSfarmRoundRobinTable OBJECT-TYPE
    SYNTAX       SEQUENCE OF EtsysTwcbWcSfarmRoundRobinEntry
    MAX-ACCESS   not-accessible
    STATUS       current
    DESCRIPTION
         "A table of entries defining ranges of destination IP 
          address, associated with TWCB Server farms.  These objects
          are used when configuring the Round Robin predictor assigned
          to the TWCB Server farm identified by 
          etsysTwcbWcServerfarmName."
    ::={ etsysTwcbTables  2 }

etsysTwcbWcSfarmRoundRobinEntry OBJECT-TYPE
    SYNTAX       EtsysTwcbWcSfarmRoundRobinEntry
    MAX-ACCESS   not-accessible
    STATUS       current
    DESCRIPTION
         "The TWCB Server Farm Round Robin Table of entries defining a
          range of destination IP addresses for this TWCB Server Farm 
          Round Robin Table entry. When an HTTP request is received
          for an address contained within this range, Caches servers
          will be selected using a round robin algorithm. When this 
          entry is created the leaf etsysTwcbWcServerfarmPredictor of
          the associated Server farm, identified by 
          etsysTwcbWcServerfarmName, will be set to 'roundrobin'."

    INDEX    { etsysTwcbWcSfarmRoundRobinAddressType,
               etsysTwcbWcServerfarmName,
               etsysTwcbWcSfarmRoundRobinStartIp,
               etsysTwcbWcSfarmRoundRobinEndIp}
    ::= { etsysTwcbWcSfarmRoundRobinTable 1 }

EtsysTwcbWcSfarmRoundRobinEntry ::=
    SEQUENCE {
    etsysTwcbWcSfarmRoundRobinAddressType
        InetAddressType,
    etsysTwcbWcSfarmRoundRobinStartIp
        InetAddress,
    etsysTwcbWcSfarmRoundRobinEndIp
        InetAddress,
    etsysTwcbWcSfarmRoundRobinRowStatus
        RowStatus
    }

etsysTwcbWcSfarmRoundRobinAddressType OBJECT-TYPE 
    SYNTAX       InetAddressType
    MAX-ACCESS   not-accessible
    STATUS       current
    DESCRIPTION 
        "The value of this property affects the size and format of
        etsysTwcbWcSfarmRoundRobinStartIp and 
        etsysTwcbWcSfarmRoundRobinEndIp. This value must be 
        consistent with the etsysTwcbWcServerfarmInetVersion defined by
        etsysLsnatWcServerfarmName."
    ::= { etsysTwcbWcSfarmRoundRobinEntry 1 } 

etsysTwcbWcSfarmRoundRobinStartIp OBJECT-TYPE
    SYNTAX       InetAddress
    MAX-ACCESS   not-accessible
    STATUS       current
    DESCRIPTION
         "The starting IP address for this range of IP addresses
          defining this TWCB Server Farm Round Robin List entry."
    ::= { etsysTwcbWcSfarmRoundRobinEntry 2 }

etsysTwcbWcSfarmRoundRobinEndIp OBJECT-TYPE
    SYNTAX       InetAddress
    MAX-ACCESS   not-accessible
    STATUS       current
    DESCRIPTION
         "The ending IP address for this range of IP addresses
          defining this TWCB Server Farm Round Robin List entry."
    ::= { etsysTwcbWcSfarmRoundRobinEntry 3 }

etsysTwcbWcSfarmRoundRobinRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Server farm Round Robin entry is available for use in
           TWCB operations.
         createAndGo(4)
         - This is the preferred mechanism for creating conceptual rows
           in this table.  A valid etsysTwcbWcServerfarmName must be
           present, Also errors resulting from:
          - Invalid etsysTwcbWcSfarmRoundRobinStartIp and 
             etsysTwcbWcSfarmRoundRobinEndIp combinations.
          - etsysTwcbWcSfarmRoundRobinAddressType inconsistencies with 
             the etsysTwcbWcServerfarmInetVersion associated with the 
             etsysTwcbWcServerfarmName. 
           There are no other writable leaves so a successful 
           createAndGo will always transition a new entry to the 
           active(1) state. Creating this object will also result in
           the etsysTwcbWcServerfarmPredictor entry of the associated
           Server farm identified by etsysTwcbWcServerfarmName to be 
           set to roundrobin(2).
         destroy(6)
         - This will remove the etsysTwcbWcSfarmRoundRobinEntry from the
           etsysTwcbWcSfarmRoundRobinTable and make it unavailable for
           TWCB operations.
           Destroying this object will also result in the
           etsysTwcbWcServerfarmPredictor entry of the associated
           Server farm identified by etsysTwcbWcServerfarmName to be 
           set to destIpHash(1)."
    ::= { etsysTwcbWcSfarmRoundRobinEntry 4 }

-- -------------------------------------------------------------
-- TWCB Cache Server Table
-- -------------------------------------------------------------

etsysTwcbCacheServerTable OBJECT-TYPE
    SYNTAX       SEQUENCE OF EtsysTwcbCacheServerEntry
    MAX-ACCESS   not-accessible
    STATUS       current
    DESCRIPTION
        "A table containing objects defining the configuration
         parameters, operational states and runtime statistics of
         TWCB Cache servers."
    ::={ etsysTwcbTables  3 }

etsysTwcbCacheServerEntry OBJECT-TYPE
    SYNTAX       EtsysTwcbCacheServerEntry
    MAX-ACCESS   not-accessible
    STATUS       current
    DESCRIPTION
         "An entry in the etsysTwcbCacheServerTable containing the 
          operational characteristics of a Cache server and it's 
          association with a TWCB Server farm. A TWCB Cache server
          is a local server on which web objects are cached. The
          TWCB Cache servers should have a web based proxy cache
          running."
     INDEX    { etsysTwcbCacheServerAddressType,
                etsysTwcbWcServerfarmName,
                etsysTwcbCacheServerIp }
     ::= { etsysTwcbCacheServerTable 1 }

EtsysTwcbCacheServerEntry ::=
    SEQUENCE {
    etsysTwcbCacheServerAddressType
        InetAddressType,
    etsysTwcbCacheServerIp
        InetAddress,
    etsysTwcbCacheServerWeight
        Unsigned32,
    etsysTwcbCacheServerMaxConns
        Unsigned32,
    etsysTwcbCacheServerFailDetectType
        INTEGER,
    etsysTwcbCacheServerFailDetectProbeOne
        SnmpAdminString,
    etsysTwcbCacheServerFailDetectProbeTwo
        SnmpAdminString,
    etsysTwcbCacheServerFailDetectAppPort
        InetPortNumber,
    etsysTwcbCacheServerAdminStatus
        INTEGER,
    etsysTwcbCacheServerOperStatus
        INTEGER,
    etsysTwcbCacheServerConns
        Gauge32,
    etsysTwcbCacheServerHits
        Counter32,
    etsysTwcbCacheServerStateChanges
        Counter32,
    etsysTwcbCacheServerLastStateChangeDateAndTime
        DateAndTime,
    etsysTwcbCacheServerRowStatus
        RowStatus
        }

etsysTwcbCacheServerAddressType OBJECT-TYPE
    SYNTAX       InetAddressType
    MAX-ACCESS   not-accessible
    STATUS       current
    DESCRIPTION
        "The Internet Protocol version.  The value of this property
         affects the size and format of the etsysTwcbCacheServerIp."
    ::= { etsysTwcbCacheServerEntry 1 }

etsysTwcbCacheServerIp OBJECT-TYPE
    SYNTAX       InetAddress
    MAX-ACCESS   not-accessible
    STATUS       current
    DESCRIPTION
         "The assigned IP address identifying this TWCB Cache server."
    ::= { etsysTwcbCacheServerEntry 2 }

etsysTwcbCacheServerWeight OBJECT-TYPE
    SYNTAX       Unsigned32 (1..155)
    MAX-ACCESS   read-create
    STATUS       current
    DESCRIPTION
         "A weight assigned to this TWCB Cache server to be used in
          selecting this TWCB Cache server over other created TWCB 
          Cache servers, within the same TWCB Server farm, for TWCB 
          redirects.  This value is only significant when the 
          etsysTwcbWcServerfarmPredictor for the associated TWCB 
          Server farm is set to roundrobin(2)."
    DEFVAL { 1 }
    ::= { etsysTwcbCacheServerEntry 3 }

etsysTwcbCacheServerMaxConns OBJECT-TYPE
    SYNTAX       Unsigned32
    MAX-ACCESS   read-create
    STATUS       current
    DESCRIPTION
         "The maximum number of TWCB connections allowed for this TWCB 
          Cache server at any one time. While the current number of
          connections (etsysTwcbCacheConns) equals this value this TWCB
          Cache server will no longer be considered for TWCB redirects.
          A value of zero indicates that there is no limit."
    DEFVAL { 0 }
    ::= { etsysTwcbCacheServerEntry 4 }

etsysTwcbCacheServerFailDetectType OBJECT-TYPE
    SYNTAX       INTEGER {
                   none(1),
                   probe(2)
                   }
    MAX-ACCESS   read-create
    STATUS       current
    DESCRIPTION
        "This object contains the fail detect type assigned to this 
        Cache server.
        - `none', indicates there is no fail detection used to verify
          the operational state of the Cache Server.
        - `probe', indicates that probes are used to verify the 
          operational state or the Cache server."
    DEFVAL { probe }
    ::= { etsysTwcbCacheServerEntry 5 }

etsysTwcbCacheServerFailDetectProbeOne OBJECT-TYPE
    SYNTAX       SnmpAdminString (SIZE(0..31))
    MAX-ACCESS   read-create
    STATUS       current
    DESCRIPTION
        "The name of probe one assigned to the Cache Server. Probes are
        used to verify the operational state of the Cache Server. A 
        null string indicates that probe one is not assigned."
    DEFVAL { "" }
    ::= { etsysTwcbCacheServerEntry 6 }

etsysTwcbCacheServerFailDetectProbeTwo OBJECT-TYPE
    SYNTAX       SnmpAdminString (SIZE(0..31))
    MAX-ACCESS   read-create
    STATUS       current
    DESCRIPTION
        "The name of probe two assigned to the Cache Server. Probes are 
        used to verify the operational state of the Cache Server. A 
        null string indicates that probe two is not assigned."
    DEFVAL { "" }
    ::= { etsysTwcbCacheServerEntry 7 }

etsysTwcbCacheServerFailDetectAppPort OBJECT-TYPE
    SYNTAX       InetPortNumber (1..65535)
    MAX-ACCESS   read-create
    STATUS       current
    DESCRIPTION
        "The service port used when an application TCP probe session is 
        configured in etsysTwcbCacheServerFailDetectProbeOne or 
        etsysTwcbCacheServerFailDetectProbeTwo for this Cache server."
    DEFVAL { 80 }
    ::= { etsysTwcbCacheServerEntry 8 }
    
etsysTwcbCacheServerAdminStatus OBJECT-TYPE
    SYNTAX       INTEGER {
                   disabled(1),
                   enabled(2)
                   }
    MAX-ACCESS   read-create
    STATUS       current
    DESCRIPTION
        "This object contains the Administrative state of the TWCB 
         Cache server.
         - `disabled', indicates the TWCB Cache server is 
           administratively disabled.
         - `enabled', indicates the TWCB Cache server is 
           administratively enabled."
    DEFVAL { disabled }
    ::= { etsysTwcbCacheServerEntry 9 }

etsysTwcbCacheServerOperStatus OBJECT-TYPE
    SYNTAX       INTEGER {
                   up(1),
                   down(2)
                   }
    MAX-ACCESS   read-only
    STATUS       current
    DESCRIPTION
        "This object contains the Operational state of the TWCB Cache
         server. The state of the TWCB Cache server will be deemed 'up'
         when the row is 'active', the etsysTwcbCacheAdminStatus is
         'enabled' and the TWCB Cache server is accessible.
         - `up', indicates the TWCB Cache server is operationally 
           ready.
         - `down', indicates the TWCB Cache server is operationally
           unavailable."
    ::= { etsysTwcbCacheServerEntry 10 }

etsysTwcbCacheServerConns OBJECT-TYPE
    SYNTAX       Gauge32
    MAX-ACCESS   read-only
    STATUS       current
    DESCRIPTION
         "The current number of active TWCB connections established on
          this TWCB Cache server."
    ::= { etsysTwcbCacheServerEntry 11 }

etsysTwcbCacheServerHits OBJECT-TYPE
    SYNTAX       Counter32
    MAX-ACCESS   read-only
    STATUS       current
    DESCRIPTION
         "The total number of hits (redirected TWCB requests) this
          TWCB Cache server has received."
    ::= { etsysTwcbCacheServerEntry 12 }

etsysTwcbCacheServerStateChanges OBJECT-TYPE
    SYNTAX       Counter32
    MAX-ACCESS   read-only
    STATUS       current
    DESCRIPTION
         "The total number of state changes (see 
          etsysTwcbCacheOperStatus)for this TWCB Cache server."
    ::= { etsysTwcbCacheServerEntry 13 }

etsysTwcbCacheServerLastStateChangeDateAndTime OBJECT-TYPE
    SYNTAX       DateAndTime
    MAX-ACCESS   read-only
    STATUS       current
    DESCRIPTION
        "The date / time the of last TWCB Cache Server state change."
    ::= { etsysTwcbCacheServerEntry 14 }

etsysTwcbCacheServerRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Cache entry is available for use by TWCB operations.
           Other writable leaves in this table MAY be modified while
           the row is in the active state.
         createAndGo(4)
         - This is the preferred mechanism for creating conceptual rows
           in this table.  A valid etsysTwcbWcServerfarmName must be
           present. Also errors resulting from an invalid
           etsysTwcbCacheServerIp when creating the TWCB entry will 
           result in the row not being created.  All writable leaves 
           have default values so a valid createAndGo will always 
           transition a new entry to the active(1) state.
         destroy(6)
         - This will remove the etsysTwcbCacheServerEntry from the
           etsysTwcbCacheServerTable and make it unavailable for TWCB
           operations."
    ::= { etsysTwcbCacheServerEntry 15 }
    
-- -------------------------------------------------------------
-- TWCB Webcache Server Table
-- -------------------------------------------------------------

etsysTwcbWebcacheServerTable OBJECT-TYPE
    SYNTAX       SEQUENCE OF EtsysTwcbWebcacheServerEntry
    MAX-ACCESS   not-accessible
    STATUS       current
    DESCRIPTION
        "A table containing objects defining the configuration 
         parameters, operational states and runtime statistics of
         TWCB Webcache servers."
    ::={ etsysTwcbTables  4 }

etsysTwcbWebcacheServerEntry OBJECT-TYPE
    SYNTAX       EtsysTwcbWebcacheServerEntry
    MAX-ACCESS   not-accessible
    STATUS       current
    DESCRIPTION
         "An entry in the etsysTwcbWebcacheServerTable containing the 
          operational characteristics of a TWCB Webcache server. A
          TWCB Webcache server defines the operation of redirected 
          HTTP requests to defined TWCB Cache servers."
    INDEX    { etsysTwcbWebcacheServerInetVersion, 
               etsysTwcbWebcacheServerName }
    ::= { etsysTwcbWebcacheServerTable 1 }

EtsysTwcbWebcacheServerEntry ::=
    SEQUENCE {
    etsysTwcbWebcacheServerInetVersion
        InetVersion,
    etsysTwcbWebcacheServerName
        SnmpAdminString,
    etsysTwcbWebcacheServerIdleTimeout
        Unsigned32,
    etsysTwcbWebcacheServerHttpport
        InetPortNumber,
    etsysTwcbWebcacheServerAdminStatus
        INTEGER,
    etsysTwcbWebcacheServerOperStatus
        INTEGER,
    etsysTwcbWebcacheServerConns
        Gauge32,
    etsysTwcbWebcacheServerHits
        Counter32,
    etsysTwcbWebcacheServerStateChanges
        Counter32,
    etsysTwcbWebcacheServerLastStateChangeDateAndTime
        DateAndTime,
    etsysTwcbWebcacheServerHostPermitCount
        Counter32,
    etsysTwcbWebcacheServerHostDenyCount
        Counter32,
    etsysTwcbWebcacheServerBypassListCount
       Counter32,
    etsysTwcbWebcacheServerServerfarmCount
       Counter32,
    etsysTwcbWebcacheServerRowStatus
        RowStatus
        }

etsysTwcbWebcacheServerInetVersion OBJECT-TYPE
    SYNTAX       InetVersion
    MAX-ACCESS   not-accessible
    STATUS       current
    DESCRIPTION
        "The Internet address version of the TWCB Webcache server."
    ::= { etsysTwcbWebcacheServerEntry 1 }

etsysTwcbWebcacheServerName OBJECT-TYPE
    SYNTAX       SnmpAdminString (SIZE(1..63))
    MAX-ACCESS   not-accessible
    STATUS       current
    DESCRIPTION
        "This object contains the unique name of the TWCB Webcache
         server."
    ::= { etsysTwcbWebcacheServerEntry  2}

etsysTwcbWebcacheServerIdleTimeout OBJECT-TYPE
    SYNTAX       Unsigned32
    UNITS        "seconds"
    MAX-ACCESS   read-create
    STATUS       current
    DESCRIPTION
         "The idle timeout value for bindings created using this
          TWCB Webcache server."
    DEFVAL { 41 }
    ::= { etsysTwcbWebcacheServerEntry 3 }

etsysTwcbWebcacheServerHttpport OBJECT-TYPE
    SYNTAX       InetPortNumber (1..65535)
    MAX-ACCESS   read-create
    STATUS       current
    DESCRIPTION
         "The destination port for which HTTP requests destined to
          TWCB redirected interfaces will be redirected to TWCB Cache
          servers."
    DEFVAL { 80 }
    ::= { etsysTwcbWebcacheServerEntry 4 }

etsysTwcbWebcacheServerAdminStatus OBJECT-TYPE
    SYNTAX       INTEGER {
                   disabled(1),
                   enabled(2)
                   }
    MAX-ACCESS   read-create
    STATUS       current
    DESCRIPTION
        "This object contains the administrative state of the TWCB 
         Webcache server.
         - `disabled', indicates the TWCB Webcache server is
           administratively disabled.
         - `enabled', indicates the TWCB Webcache server is
           administratively enabled."
    DEFVAL { disabled }
    ::= { etsysTwcbWebcacheServerEntry 5 }

etsysTwcbWebcacheServerOperStatus OBJECT-TYPE
    SYNTAX       INTEGER {
                   up(1),
                   down(2)
                   }
    MAX-ACCESS   read-only
    STATUS       current
    DESCRIPTION
        "This object contains the Operational state of the TWCB 
         Webcache server. The state of the TWCB Webcache server will be
         deemed 'up' when the row is 'active', the 
         etsysTwcbWebcacheServerAdminStatus is 'enabled' and at least
         one etsysTwcbWcServerfarmEntry has been associated with this 
         entry and the etsysTwcbWcServerfarmOperStatus is 'up'.
         - `up', indicates the TWCB Webcache server is operationally 
           ready.
         - `down', indicates the TWCB Webcache server is operationally
           unavailable."
    ::= { etsysTwcbWebcacheServerEntry 6 }

etsysTwcbWebcacheServerConns OBJECT-TYPE
    SYNTAX       Gauge32
    MAX-ACCESS   read-only
    STATUS       current
    DESCRIPTION
         "The current number of active TWCB connections established on
          this TWCB Webcache server."
    ::= { etsysTwcbWebcacheServerEntry 7 }

etsysTwcbWebcacheServerHits OBJECT-TYPE
    SYNTAX       Counter32
    MAX-ACCESS   read-only
    STATUS       current
    DESCRIPTION
         "The total number of hits (redirected TWCB requests) this
          TWCB Webcache server has received."
    ::= { etsysTwcbWebcacheServerEntry 8 }

etsysTwcbWebcacheServerStateChanges OBJECT-TYPE
    SYNTAX       Counter32
    MAX-ACCESS   read-only
    STATUS       current
    DESCRIPTION
         "The total number of state changes (see
          etsysTwcbWebcacheServerOperStatus) for this TWCB Webcache
          server."
    ::= { etsysTwcbWebcacheServerEntry 9 }

etsysTwcbWebcacheServerLastStateChangeDateAndTime OBJECT-TYPE
    SYNTAX       DateAndTime
    MAX-ACCESS   read-only
    STATUS       current
    DESCRIPTION
        "The date / time of the last TWCB Webcache Server state 
         change."
    ::= { etsysTwcbWebcacheServerEntry 10 }

etsysTwcbWebcacheServerHostPermitCount OBJECT-TYPE
    SYNTAX       Counter32
    MAX-ACCESS   read-only
    STATUS       current
    DESCRIPTION
        "The number of Host permit configurations assigned to the
         webcahce server. See etsysWebcacheServerHostPermitTable"
    ::= { etsysTwcbWebcacheServerEntry 11 }

etsysTwcbWebcacheServerHostDenyCount OBJECT-TYPE
    SYNTAX       Counter32
    MAX-ACCESS   read-only
    STATUS       current
    DESCRIPTION
        "The number of Host deny configurations assigned to the 
         webcahce server.  See etsysWebcacheServerDenyPermitTable"
    ::= { etsysTwcbWebcacheServerEntry 12 }
    
etsysTwcbWebcacheServerBypassListCount OBJECT-TYPE
    SYNTAX       Counter32
    MAX-ACCESS   read-only
    STATUS       current
    DESCRIPTION
        "The number of Bypass list configurations assigned to the 
         webcahce server. See etsysWebcacheServerBypassListTable"
    ::= { etsysTwcbWebcacheServerEntry 13 }
    
etsysTwcbWebcacheServerServerfarmCount OBJECT-TYPE
    SYNTAX       Counter32
    MAX-ACCESS   read-only
    STATUS       current
    DESCRIPTION
        "The number of server farms configured to the webcahce server. 
         See etsysWebcacheServerServerfarmTable"
    ::= { etsysTwcbWebcacheServerEntry 14 }
    
etsysTwcbWebcacheServerRowStatus OBJECT-TYPE
    SYNTAX       RowStatus
    MAX-ACCESS   read-create
    STATUS       current
    DESCRIPTION
        "This object permits management of the table by facilitating
         actions such as row creation and deletion.

         The value of this object has no effect on whether other objects
         in the conceptual row can be modified.

         The only allowable row status of this conceptual row in the
         table are:
         active(1)
         - The Webcache entry is available for use by TWCB operations.
           Other writable leaves in this table MAY be modified while
           the row is in the active state.
         createAndGo(4)
         - This is the preferred mechanism for creating conceptual rows
           in this table.  A valid createAndGo requires a unique
           etsysTwcbWebcacheServerName, errors resulting from existing
           etsysTwcbWebcacheServerNames will result in the row not 
           being created. All writable leaves have default values so a 
           valid createAndGo will always transition a new entry to the
           active(1) state.
         destroy(6)
         - This will remove the etsysTwcbWebcacheServerEntry from the
           etsysTwcbWebcacheServerTable and make it unavailable for 
           TWCB operations.  This will result in all associated TWCB 
           entries (defined below) to also be deleted.
           TWCB Webcache Server Host Permit Table entries
            (etsysTwcbWebcacheServerHostPermitTable),
           TWCB Webcache Server Host Deny Table entries
            (etsysTwcbWebcacheServerHostDenyEntry),
           TWCB Webcache Server Bypass Table
            (etsysTwcbWebcacheServerBypassEntry),
           TWCB Webcache Server farm Table
            (etsysTwcbWebcacheServerfarmEntry)."
    ::= { etsysTwcbWebcacheServerEntry 15 }
    
-- -------------------------------------------------------------
-- TWCB Webcache Server Host Permit Redirect Table
-- -------------------------------------------------------------

etsysTwcbWebcacheServerHostPermitTable OBJECT-TYPE
    SYNTAX       SEQUENCE OF EtsysTwcbWebcacheServerHostPermitEntry
    MAX-ACCESS   not-accessible
    STATUS       current
    DESCRIPTION
        "The TWCB Webcache Host Permit Table of entries defining ranges 
         of source IP address, associated with TWCB Webcache Host 
         Permit configurations.  These objects are used when 
         configuring the Host Permit ranges assigned to the Webcache
         server identified by etsysTwcbWebcacheServerName."
    ::={ etsysTwcbTables  5 }

etsysTwcbWebcacheServerHostPermitEntry OBJECT-TYPE
    SYNTAX       EtsysTwcbWebcacheServerHostPermitEntry
    MAX-ACCESS   not-accessible
    STATUS       current
    DESCRIPTION
         "An entry in the etsysTwcbWebcacheServerHostPermitTable defining a 
          range of source IP addresses for this TWCB Webcache server 
          Host Permit Table entry. The Host Permit Table entry defines
          a range of source IP addresses for which HTTP requests will 
          be allowed to be redirected by TWCB. If no Webcache Host 
          Permit entry or Webcache Host Deny entry exists than all 
          source IP addresses will be allowed. Once one Webcache Host
          Permit entry has been created than all IP address falling 
          outside the defined range of IP addresses for all Webcache 
          Host Permit entries will be denied."
    INDEX    { etsysTwcbWebcacheServerHostPermitAddressType,
               etsysTwcbWebcacheServerName,
               etsysTwcbWebcacheServerHostPermitStartIp,
               etsysTwcbWebcacheServerHostPermitEndIp }
    ::= { etsysTwcbWebcacheServerHostPermitTable 1 }

EtsysTwcbWebcacheServerHostPermitEntry ::=
    SEQUENCE {
    etsysTwcbWebcacheServerHostPermitAddressType
        InetAddressType,
    etsysTwcbWebcacheServerHostPermitStartIp
        InetAddress,
    etsysTwcbWebcacheServerHostPermitEndIp
        InetAddress,
    etsysTwcbWebcacheServerHostPermitRowStatus
        RowStatus
    }

etsysTwcbWebcacheServerHostPermitAddressType OBJECT-TYPE
    SYNTAX       InetAddressType
    MAX-ACCESS   not-accessible
    STATUS       current
    DESCRIPTION
        "The Internet Protocol version.  The value of this property
         affects the size and format of the
         etsysTwcbWebcacheServerHostPermitStartIp and
         etsysTwcbWebcacheServerHostPermitEndIp objects both objects 
         must be of the same INET Address Type."

    ::= { etsysTwcbWebcacheServerHostPermitEntry 1 }

etsysTwcbWebcacheServerHostPermitStartIp OBJECT-TYPE
    SYNTAX       InetAddress
    MAX-ACCESS   not-accessible
    STATUS       current
    DESCRIPTION
         "The starting IP address for this range of IP addresses
          defining this TWCB Webcache Server Host Permit entry."
    ::= { etsysTwcbWebcacheServerHostPermitEntry 2 }

etsysTwcbWebcacheServerHostPermitEndIp OBJECT-TYPE
    SYNTAX       InetAddress
    MAX-ACCESS   not-accessible
    STATUS       current
    DESCRIPTION
         "The ending IP address for this range of IP addresses
          defining this TWCB Webcache Server Host Permit entry."
    ::= { etsysTwcbWebcacheServerHostPermitEntry 3 }

etsysTwcbWebcacheServerHostPermitRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Webcache Host Permit entry is available for use in TWCB
           operations.
         createAndGo(4)
         - This is the preferred mechanism for creating conceptual rows
           in this table.  A valid etsysTwcbWebcacheServerName must be 
           present. Also errors resulting from invalid
           etsysTwcbWebcacheServerHostPermitStartIp and
           etsysTwcbWebcacheServerHostPermitEndIp when creating the 
           TWCB entry will result in the row not being created. There 
           are no other writable leaves so a successful createAndGo 
           will always transition a new entry to the active(1) state.
         destroy(6)
         - This will remove the etsysTwcbWebcacheServerHostPermitEntry 
           from the etsysTwcbWebcacheServerHostPermitTable and make it 
           unavailable for TWCB operations."
    ::= { etsysTwcbWebcacheServerHostPermitEntry 4 }

-- -------------------------------------------------------------
-- TWCB Webcache Server Host Deny Redirect Table
-- -------------------------------------------------------------

etsysTwcbWebcacheServerHostDenyTable OBJECT-TYPE
    SYNTAX       SEQUENCE OF EtsysTwcbWebcacheServerHostDenyEntry
    MAX-ACCESS   not-accessible
    STATUS       current
    DESCRIPTION
        "The Webcache Server Host Deny Table of entries defining ranges
         of source IP address, associated with TWCB Webcache Server 
         Host Deny configurations.  These objects are used when 
         configuring the Host Deny ranges assigned to the Webcache 
         server identified by etsysTwcbWebcacheServerName."
    ::={ etsysTwcbTables  6 }

etsysTwcbWebcacheServerHostDenyEntry OBJECT-TYPE
    SYNTAX       EtsysTwcbWebcacheServerHostDenyEntry
    MAX-ACCESS   not-accessible
    STATUS       current
    DESCRIPTION
         "An entry in the etsysTwcbWebcacheServerHostDenyTable defining
          a range of source IP addresses for this TWCB Webcache server 
          Host Deny Table entry. The TWCB Webcache server Host Deny 
          Table entry defines a range of source IP addresses for which 
          HTTP requests will not be allowed to be redirected by TWCB. 
          If no TWCB Webcache Server Host Permit entry or TWCB Webcache
          Server Host Deny entry exists  than all source IP addresses 
          will be allowed. A TWCB Webcache Server Host Deny entry takes
          presidency over any created TWCB Host Permit entries.  If an 
          address falls within a defined TWCB Webcache Server Host Deny
          range of addresses than that address will be denied 
          regardless if it also falls within a TWCB Webcache Server
          Host Permit entry."
    INDEX    { etsysTwcbWebcacheServerHostDenyAddressType,
               etsysTwcbWebcacheServerName,
               etsysTwcbWebcacheServerHostDenyStartIp,
               etsysTwcbWebcacheServerHostDenyEndIp }
    ::= { etsysTwcbWebcacheServerHostDenyTable 1 }

EtsysTwcbWebcacheServerHostDenyEntry ::=
    SEQUENCE {
    etsysTwcbWebcacheServerHostDenyAddressType
        InetAddressType,
    etsysTwcbWebcacheServerHostDenyStartIp
        InetAddress,
    etsysTwcbWebcacheServerHostDenyEndIp
        InetAddress,
    etsysTwcbWebcacheServerHostDenyRowStatus
        RowStatus
    }

etsysTwcbWebcacheServerHostDenyAddressType OBJECT-TYPE
    SYNTAX       InetAddressType
    MAX-ACCESS   not-accessible
    STATUS       current
    DESCRIPTION
        "The Internet Protocol version.  The value of this property
         affects the size and format of the
         etsysTwcbWebcacheServerHostDenyStartIp and
         etsysTwcbWebcacheServerHostDenyEndIp objects both objects must
         be of the same INET Address Type."
    ::= { etsysTwcbWebcacheServerHostDenyEntry 1 }

etsysTwcbWebcacheServerHostDenyStartIp OBJECT-TYPE
    SYNTAX       InetAddress
    MAX-ACCESS   not-accessible
    STATUS       current
    DESCRIPTION
         "The starting IP address for this range of IP addresses
          defining this TWCB Webcache Server Host Deny entry."
    ::= { etsysTwcbWebcacheServerHostDenyEntry 2 }

etsysTwcbWebcacheServerHostDenyEndIp OBJECT-TYPE
    SYNTAX       InetAddress
    MAX-ACCESS   not-accessible
    STATUS       current
    DESCRIPTION
         "The ending IP address for this range of IP addresses
          defining this TWCB Webcache Server Host Deny entry."
    ::= { etsysTwcbWebcacheServerHostDenyEntry 3 }

etsysTwcbWebcacheServerHostDenyRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Webcache Server Host Deny entry is available for use in
           TWCB operations.
         createAndGo(4)
         - This is the preferred mechanism for creating conceptual rows
           in this table.  A valid etsysTwcbWebcacheServerName must be 
           present. Also errors resulting from invalid
           etsysTwcbWebcacheServerHostDenyStartIp and
           etsysTwcbWebcacheServerHostDenyEndIp when creating the TWCB 
           entry will result in the row not being created. There are no
           other writable leaves so a successful createAndGo will 
           always transition a new entry to the active(1) state.
         destroy(6)
         - This will remove the etsysTwcbWebcacheServerHostDenyEntry 
           from the etsysTwcbWebcacheServerHostDenyTable and make it
           unavailable for TWCB operations."
    ::= { etsysTwcbWebcacheServerHostDenyEntry 4 }

-- -------------------------------------------------------------
-- TWCB Webcache Server Bypass List Table
-- -------------------------------------------------------------

etsysTwcbWebcacheServerBypassTable OBJECT-TYPE
    SYNTAX       SEQUENCE OF EtsysTwcbWebcacheServerBypassEntry
    MAX-ACCESS   not-accessible
    STATUS       current
    DESCRIPTION
        "A table of entries defining ranges of destination IP address
         associated with TWCB Webcache Server Bypass List 
         configurations. These objects are used when configuring the 
         Bypass List ranges assigned to the Webcache server identified
         by  etsysTwcbWebcacheServerName."
    ::={ etsysTwcbTables  7 }

etsysTwcbWebcacheServerBypassEntry OBJECT-TYPE
    SYNTAX       EtsysTwcbWebcacheServerBypassEntry
    MAX-ACCESS   not-accessible
    STATUS       current
    DESCRIPTION
         "An entry in the etsysTwcbWebcacheServerBypassTable defining 
          a range of destination IP addresses for this TWCB Webcache 
          server Bypass List Table entry. The TWCB Bypass List Table 
          entry defines a range of destination IP addresses for which
          HTTP requests will not be redirected by TWCB."

    INDEX    { etsysTwcbWebcacheServerBypassAddressType,
               etsysTwcbWebcacheServerName,
               etsysTwcbWebcacheServerBypassStartIp,
               etsysTwcbWebcacheServerBypassEndIp }
    ::= { etsysTwcbWebcacheServerBypassTable 1 }

EtsysTwcbWebcacheServerBypassEntry ::=
    SEQUENCE {
    etsysTwcbWebcacheServerBypassAddressType
        InetAddressType,
    etsysTwcbWebcacheServerBypassStartIp
        InetAddress,
    etsysTwcbWebcacheServerBypassEndIp
        InetAddress,
    etsysTwcbWebcacheServerBypassRowStatus
        RowStatus
    }

etsysTwcbWebcacheServerBypassAddressType OBJECT-TYPE
    SYNTAX       InetAddressType
    MAX-ACCESS   not-accessible
    STATUS       current
    DESCRIPTION
        "The Internet Protocol version.  The value of this property
         affects the size and format of the
         etsysTwcbWebcacheServerBypassStartIp and
         etsysTwcbWebcacheServerBypassEndIp objects both objects must
         be of the same INET Address Type."
    ::= { etsysTwcbWebcacheServerBypassEntry 1 }

etsysTwcbWebcacheServerBypassStartIp OBJECT-TYPE
    SYNTAX       InetAddress
    MAX-ACCESS   not-accessible
    STATUS       current
    DESCRIPTION
         "The starting IP address for this range of IP addresses
          defining this TWCB Webcache Server Bypass List entry."
    ::= { etsysTwcbWebcacheServerBypassEntry 2 }

etsysTwcbWebcacheServerBypassEndIp OBJECT-TYPE
    SYNTAX       InetAddress
    MAX-ACCESS   not-accessible
    STATUS       current
    DESCRIPTION
         "The ending IP address for this range of IP addresses
          defining this TWCB Webcache Server Bypass List entry."
    ::= { etsysTwcbWebcacheServerBypassEntry 3 }

etsysTwcbWebcacheServerBypassRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Webcache Bypass List entry is available for use in TWCB
           operations.
         createAndGo(4)
         - This is the preferred mechanism for creating conceptual rows
           in this table.  A valid etsysTwcbWebcacheServerName must be 
           present. Also errors resulting from invalid
           etsysTwcbWebcacheServerBypassStartIp and
           etsysTwcbWebcacheServerBypassEndIp when creating the TWCB 
           entry will result in the row not being created. There are no
           other writable leaves so a successful createAndGo will 
           always transition a new entry to the active(1) state.
         destroy(6)
         - This will remove the etsysTwcbWebcacheServerBypassEntry from
           the etsysTwcbWebcacheServerBypassTable and make it unavailable
           for TWCB operations."
    ::= { etsysTwcbWebcacheServerBypassEntry 4 }

-- -------------------------------------------------------------
-- TWCB Webcache Server Farm Table
-- -------------------------------------------------------------

etsysTwcbWebcacheServerfarmTable OBJECT-TYPE
    SYNTAX       SEQUENCE OF EtsysTwcbWebcacheServerfarmEntry
    MAX-ACCESS   not-accessible
    STATUS       current
    DESCRIPTION
        "A table of entries mapping Server Farm Table entries 
         (etsysTwcbWcServerfarmName) to TWCB Webcache 
         Server Table entries (etsysTwcbWebcacheServerName). This 
         objects is used to map TWCB Server farms to the Webcache 
         servers  identified by etsysTwcbWebcacheServerName."
    ::={ etsysTwcbTables  8 }

etsysTwcbWebcacheServerfarmEntry OBJECT-TYPE
    SYNTAX       EtsysTwcbWebcacheServerfarmEntry
    MAX-ACCESS   not-accessible
    STATUS       current
    DESCRIPTION
         "An entry in the etsysTwcbWebcacheServerfarmTable defining 
          the association of TWCB Server farms to TWCB Webcache 
          servers. The Webcache Server Farm Table binds a Webcache 
          server entry (etsysTwcbWebcacheServerName) to a TWCB Server Farm 
          entry (etsysTwcbWcServerfarmId)."
    INDEX    { etsysTwcbWebcacheServerInetVersion, 
    		   etsysTwcbWebcacheServerName, 
    		   etsysTwcbWcServerfarmId }
    ::= { etsysTwcbWebcacheServerfarmTable 1 }

EtsysTwcbWebcacheServerfarmEntry ::=
    SEQUENCE {
    etsysTwcbWebcacheServerfarmRowStatus
        RowStatus
    }

etsysTwcbWebcacheServerfarmRowStatus OBJECT-TYPE
    SYNTAX       RowStatus
    MAX-ACCESS   read-create
    STATUS       current
    DESCRIPTION
        "This object permits management of the table by facilitating
         actions such as row creation and deletion.

         The value of this object has no effect on whether other
         objects in the conceptual row can be modified.

         The only allowable row status of this conceptual row in the
         table are:
         active(1)
         - The Webcache Server farm entry is available for use in TWCB
           operations.
         createAndGo(4)
         - This is the preferred mechanism for creating conceptual rows
           in this table.  A valid etsysTwcbWebcacheServerName and
           etsysTwcbWcServerfarmId must be present. There are no 
           other writable leaves so a successful createAndGo will always
           transition a new entry to the active(1) state.
         destroy(6)
         - This will remove the etsysTwcbWebcacheServerfarmEntry from
           the etsysTwcbWebcacheServerfarmTable and make it unavailable
           for TWCB operations."
    ::= { etsysTwcbWebcacheServerfarmEntry 1 }

-- -------------------------------------------------------------
-- TWCB Binding Table
-- -------------------------------------------------------------
etsysTwcbBindingTable OBJECT-TYPE
    SYNTAX       SEQUENCE OF EtsysTwcbBindingEntry
    MAX-ACCESS   not-accessible
    STATUS       current
    DESCRIPTION
        "The Binding List Table of entries defining active TWCB
         bindings."
    ::={ etsysTwcbTables  9 }

etsysTwcbBindingEntry OBJECT-TYPE
    SYNTAX       EtsysTwcbBindingEntry
    MAX-ACCESS   not-accessible
    STATUS       current
    DESCRIPTION
         "A table defining an active TWCB binding.  The 
          etsysTwcbBindingEntry defines the runtime characteristics
          of a TWCB binding."
    INDEX    { etsysTwcbBindingId }
    ::= { etsysTwcbBindingTable  1 }

EtsysTwcbBindingEntry ::=
        SEQUENCE {
        etsysTwcbBindingId
            Unsigned32,
        etsysTwcbBindingState
            INTEGER,
        etsysTwcbBindingAddressType
            InetAddressType,
        etsysTwcbBindingSrcIp
            InetAddress,
        etsysTwcbBindingSrcPort
            InetPortNumber,
        etsysTwcbBindingDstIp
            InetAddress,
        etsysTwcbBindingDstPort
            InetPortNumber,
        etsysTwcbBindingHWConns
            Gauge32,
        etsysTwcbBindingWebcacheName
            SnmpAdminString,
        etsysTwcbBindingWcServerfarmName
            SnmpAdminString,
        etsysTwcbBindingCacheIp
            InetAddress,
        etsysTwcbBindingCreationDate
            DateAndTime,
        etsysTwcbBindingExpirationDate
            DateAndTime,
        etsysTwcbBindingIdleTime
            Unsigned32,
        etsysTwcbBindingExpireTime
            Unsigned32,
        etsysTwcbBindingClear
            TruthValue
        }

etsysTwcbBindingId OBJECT-TYPE
    SYNTAX       Unsigned32 (1..65535)
    MAX-ACCESS   not-accessible
    STATUS       current
    DESCRIPTION
         "This value is a unique TWCB binding identifier
          assigned by TWCB during binding creation."
    ::= { etsysTwcbBindingEntry 1 }

etsysTwcbBindingState OBJECT-TYPE
    SYNTAX       INTEGER {
                   init(1),
                   syncing(2),
                   established(3)
                   }
    MAX-ACCESS   read-only
    STATUS       current
    DESCRIPTION
        "This object contains the current state of this binding.
        - `init', indicates this binding is initializing.
        - `syncing', indicates this binding is syncing.
        - `established', indicates this binding is established."
    ::= { etsysTwcbBindingEntry 2 }
    
etsysTwcbBindingAddressType OBJECT-TYPE
    SYNTAX       InetAddressType
    MAX-ACCESS   read-only
    STATUS       current
    DESCRIPTION
        "The value of this property affects the size and format of
         the etsysTwcbBindingSrcIp, etsysTwcbBindingDstIp and 
         etsysTwcbBindingCacheIp."
    ::= { etsysTwcbBindingEntry 3 }

etsysTwcbBindingSrcIp OBJECT-TYPE
    SYNTAX       InetAddress
    MAX-ACCESS   read-only
    STATUS       current
    DESCRIPTION
         "The source IP address for this current TWCB binding entry."
    ::= { etsysTwcbBindingEntry 4 }

etsysTwcbBindingSrcPort OBJECT-TYPE
    SYNTAX       InetPortNumber (1..65535)
    MAX-ACCESS   read-only
    STATUS       current
    DESCRIPTION
         "The source port for this current TWCB binding entry."
    ::= { etsysTwcbBindingEntry 5 }

etsysTwcbBindingDstIp OBJECT-TYPE
    SYNTAX       InetAddress
    MAX-ACCESS   read-only
    STATUS       current
    DESCRIPTION
         "The destination IP address for this current TWCB binding
          entry."
    ::= { etsysTwcbBindingEntry 6 }

etsysTwcbBindingDstPort OBJECT-TYPE
    SYNTAX       InetPortNumber (1..65535)
    MAX-ACCESS   read-only
    STATUS       current
    DESCRIPTION
         "The destination port for this current TWCB binding entry."
    ::= { etsysTwcbBindingEntry 7 }

etsysTwcbBindingHWConns OBJECT-TYPE
    SYNTAX       Gauge32
    MAX-ACCESS   read-only
    STATUS       current
    DESCRIPTION
        "This object contains the total number of hardware connections
         currently active using this TWCB binding."
    ::= { etsysTwcbBindingEntry 8 }

etsysTwcbBindingWebcacheName OBJECT-TYPE
    SYNTAX       SnmpAdminString (SIZE(1..63))
    MAX-ACCESS   read-only
    STATUS       current
    DESCRIPTION
        "This object contains the name of the TWCB Webcache
         associated with this TWCB binding."
    ::= { etsysTwcbBindingEntry 9 }

etsysTwcbBindingWcServerfarmName OBJECT-TYPE
    SYNTAX       SnmpAdminString (SIZE(1..63))
    MAX-ACCESS   read-only
    STATUS       current
    DESCRIPTION
        "This object contains the name of the TWCB Webcache
         Server farm associated with this TWCB binding."
    ::= { etsysTwcbBindingEntry 10 }

etsysTwcbBindingCacheIp OBJECT-TYPE
    SYNTAX       InetAddress
    MAX-ACCESS   read-only
    STATUS       current
    DESCRIPTION
         "The Cache server IP address of this current TWCB binding
          entry."
    ::= { etsysTwcbBindingEntry 11 }

etsysTwcbBindingCreationDate OBJECT-TYPE
    SYNTAX       DateAndTime
    MAX-ACCESS   read-only
    STATUS       current
    DESCRIPTION
         "The creation date / time of this current TWCB binding
          entry."
    ::= { etsysTwcbBindingEntry 12 }

etsysTwcbBindingExpirationDate OBJECT-TYPE
    SYNTAX       DateAndTime
    MAX-ACCESS   read-only
    STATUS       current
    DESCRIPTION
         "The expiration date / time of this current TWCB binding
          entry."
    ::= { etsysTwcbBindingEntry 13 }

etsysTwcbBindingIdleTime OBJECT-TYPE
    SYNTAX       Unsigned32
    UNITS        "seconds"
    MAX-ACCESS   read-only
    STATUS       current
    DESCRIPTION
         "The consecutive idle time (in seconds) of this current
          TWCB binding entry."
    ::= { etsysTwcbBindingEntry 14 }

etsysTwcbBindingExpireTime OBJECT-TYPE
    SYNTAX       Unsigned32
    UNITS        "seconds"
    MAX-ACCESS   read-only
    STATUS       current
    DESCRIPTION
         "The number of idle seconds left before this current TWCB
          binding entry will age out."
    ::= { etsysTwcbBindingEntry 15 }

etsysTwcbBindingClear OBJECT-TYPE
    SYNTAX       TruthValue
    MAX-ACCESS   read-write
    STATUS       current
    DESCRIPTION
        "Setting this object to a value of true(1) will cause the this
         etsysTwcbBindingEntry to be deleted from the
         etsysTwcbBindingTable.

         Setting this object to a value of false(2) has no effect.
         This object will always return a value of false(2)."
    DEFVAL { false }
    ::= { etsysTwcbBindingEntry 16 }
    
-- ------------------------------------
-- Conformance information
-- ------------------------------------

etsysTwcbMIBGroups
    OBJECT IDENTIFIER ::= { etsysTwcbConformance 1 }
etsysTwcbMIBCompliances
    OBJECT IDENTIFIER ::= { etsysTwcbConformance 2 }

-- -------------------------------------------------------------
-- Units of conformance
-- -------------------------------------------------------------

etsysTwcbMIBGlobalStatsGroup  OBJECT-GROUP
    OBJECTS {
        etsysTwcbStatsCachesUsed,
        etsysTwcbStatsWcServerfarmsUsed,
        etsysTwcbStatsWebcacheUsed,
        etsysTwcbStatsBindingsCurrent,
        etsysTwcbStatsBindingsHigh,
        etsysTwcbStatsBindingsDeleted,
        etsysTwcbStatsBindingsTotal,
        etsysTwcbStatsBindingsExhausted,
        etsysTwcbStatsBindingsNoCaches,
        etsysTwcbStatsBindingsPerSecond,
        etsysTwcbStatsWebcacheActive,
        etsysTwcbStatsWebcacheHigh,
        etsysTwcbStatsWcServerfarmActive,
        etsysTwcbStatsWcServerfarmHigh,
        etsysTwcbStatsCacheActive,
        etsysTwcbStatsCacheHigh,
        etsysTwcbStatsClear,
        etsysTwcbStatsClearDateAndTime,
        etsysTwcbStatsMinTimeoutValue,
        etsysTwcbStatsMaxTimeoutValue
        }
    STATUS       current
    DESCRIPTION
        "The statistics group for TWCB global statistical information."
    ::= { etsysTwcbMIBGroups 1 }

etsysTwcbMIBWcServerfarmTableGroup  OBJECT-GROUP
    OBJECTS {
        etsysTwcbWcServerfarmPredictor,
        etsysTwcbWcServerfarmAdminStatus,
        etsysTwcbWcServerfarmOperStatus,
        etsysTwcbWcServerfarmConns,
        etsysTwcbWcServerfarmHits,
        etsysTwcbWcServerfarmStateChanges,
        etsysTwcbWcServerfarmLastStateChangeDateAndTime,
        etsysTwcbWcServerfarmCachesCfg,
        etsysTwcbWcServerfarmCachesUp,
        etsysTwcbWcServerfarmWebcacheCfg,
        etsysTwcbWcServerfarmRoundRobinCount,
        etsysTwcbWcServerfarmRowStatus,
        etsysTwcbWcServerfarmId
        }
    STATUS       current
    DESCRIPTION
        "The TWCB Server Farm group for TWCB Webcache Server farm
         configuration and state operations."
    ::= { etsysTwcbMIBGroups 2 }

etsysTwcbMIBWcSfarmRoundRobinTableGroup  OBJECT-GROUP
    OBJECTS {
        etsysTwcbWcSfarmRoundRobinRowStatus
        }
    STATUS       current
    DESCRIPTION
        "The TWCB Server Farm Round Robin group for TWCB Server farm
         Round Robin configuration."
    ::= { etsysTwcbMIBGroups 3 }

etsysTwcbMIBCacheServerTableGroup  OBJECT-GROUP
    OBJECTS {
        etsysTwcbCacheServerWeight,
        etsysTwcbCacheServerMaxConns,
        etsysTwcbCacheServerFailDetectType,
        etsysTwcbCacheServerFailDetectProbeOne,
        etsysTwcbCacheServerFailDetectProbeTwo,
        etsysTwcbCacheServerFailDetectAppPort,
        etsysTwcbCacheServerAdminStatus,
        etsysTwcbCacheServerOperStatus,
        etsysTwcbCacheServerConns,
        etsysTwcbCacheServerHits,
        etsysTwcbCacheServerStateChanges,
        etsysTwcbCacheServerLastStateChangeDateAndTime,
        etsysTwcbCacheServerRowStatus
        }
    STATUS       current
    DESCRIPTION
        "The TWCB Cache server group for TWCB Cache server 
        configuration and state operations."
    ::= { etsysTwcbMIBGroups 4 }

etsysTwcbMIBWebcacheServerTableGroup  OBJECT-GROUP
    OBJECTS {
        etsysTwcbWebcacheServerIdleTimeout,
        etsysTwcbWebcacheServerHttpport,
        etsysTwcbWebcacheServerAdminStatus,
        etsysTwcbWebcacheServerOperStatus,
        etsysTwcbWebcacheServerConns,
        etsysTwcbWebcacheServerHits,
        etsysTwcbWebcacheServerStateChanges,
        etsysTwcbWebcacheServerLastStateChangeDateAndTime,
        etsysTwcbWebcacheServerHostPermitCount,
        etsysTwcbWebcacheServerHostDenyCount,
        etsysTwcbWebcacheServerBypassListCount,
        etsysTwcbWebcacheServerServerfarmCount,
        etsysTwcbWebcacheServerRowStatus
        }
    STATUS       current
    DESCRIPTION
        "The TWCB Webcache server group for TWCB Webcache server
        configuration and state operations."
    ::= { etsysTwcbMIBGroups 5 }

etsysTwcbMIBWebcacheServerHostPermitTableGroup  OBJECT-GROUP
    OBJECTS {
        etsysTwcbWebcacheServerHostPermitRowStatus
        }
    STATUS       current
    DESCRIPTION
        "The Webcache Server Host Permit group for TWCB Webcache Host
         Permit configuration."
    ::= { etsysTwcbMIBGroups 6 }

etsysTwcbMIBWebcacheServerHostDenyTableGroup  OBJECT-GROUP
    OBJECTS {
        etsysTwcbWebcacheServerHostDenyRowStatus
        }
    STATUS       current
    DESCRIPTION
        "The Webcache Server Host Deny group for TWCB Webcache Host
         Deny configuration."
    ::= { etsysTwcbMIBGroups 7 }

etsysTwcbMIBWebcacheServerBypassTableGroup  OBJECT-GROUP
    OBJECTS {
        etsysTwcbWebcacheServerBypassRowStatus
        }
    STATUS       current
    DESCRIPTION
        "The Webcache Server Bypass List group for TWCB Webcache Bypass
         List configuration."
    ::= { etsysTwcbMIBGroups 8 }

etsysTwcbMIBWebcacheServerfarmTableGroup  OBJECT-GROUP
    OBJECTS {
        etsysTwcbWebcacheServerfarmRowStatus
        }
    STATUS       current
    DESCRIPTION
        "The Webcache Server Farm group for TWCB Webcache Server farm
         assignment configuration."
    ::= { etsysTwcbMIBGroups 9 }

etsysTwcbMIBBindingTableGroup OBJECT-GROUP
    OBJECTS {
        etsysTwcbBindingAddressType,
        etsysTwcbBindingSrcIp,
        etsysTwcbBindingSrcPort,
        etsysTwcbBindingDstIp,
        etsysTwcbBindingDstPort,
        etsysTwcbBindingHWConns,
        etsysTwcbBindingWebcacheName,
        etsysTwcbBindingWcServerfarmName,
        etsysTwcbBindingCacheIp,
        etsysTwcbBindingCreationDate,
        etsysTwcbBindingExpirationDate,
        etsysTwcbBindingIdleTime,
        etsysTwcbBindingExpireTime,
        etsysTwcbBindingClear,
        etsysTwcbBindingState
        }
    STATUS       current
    DESCRIPTION
        "The Bindings group for TWCB Binding information."
    ::= { etsysTwcbMIBGroups 10 }

-- ------------------------------------
-- Compliance statements
-- ------------------------------------

etsysTwcbMIBCompliance MODULE-COMPLIANCE
    STATUS       current
    DESCRIPTION
        "The compliance statement for implementation of the Router
         Application Services TWCB functionality."
    MODULE
        MANDATORY-GROUPS  {
            etsysTwcbMIBGlobalStatsGroup,
            etsysTwcbMIBWcServerfarmTableGroup,
            etsysTwcbMIBWcSfarmRoundRobinTableGroup,
            etsysTwcbMIBCacheServerTableGroup,
            etsysTwcbMIBWebcacheServerTableGroup,
            etsysTwcbMIBWebcacheServerHostPermitTableGroup,
            etsysTwcbMIBWebcacheServerHostDenyTableGroup,
            etsysTwcbMIBWebcacheServerBypassTableGroup,
            etsysTwcbMIBWebcacheServerfarmTableGroup,
            etsysTwcbMIBBindingTableGroup
       }

        OBJECT      etsysTwcbStatsClear
        MIN-ACCESS  read-only
        DESCRIPTION
            "Write access is not required."

        OBJECT      etsysTwcbWcServerfarmRowStatus
--        SYNTAX      RowStatus {
        SYNTAX      INTEGER {
                        active(1),
                        createAndGo(4),
                        destroy(6)
                    }
        DESCRIPTION
            "Only active, createAndGo and destroy are allowed."

        OBJECT      etsysTwcbWcSfarmRoundRobinRowStatus
--        SYNTAX      RowStatus {
        SYNTAX      INTEGER {
                        active(1),
                        createAndGo(4),
                        destroy(6)
                    }
        DESCRIPTION
            "Only active, createAndGo and destroy are allowed."

        OBJECT      etsysTwcbCacheServerRowStatus
--        SYNTAX      RowStatus {
        SYNTAX      INTEGER {
                        active(1),
                        createAndGo(4),
                        destroy(6)
                    }
        DESCRIPTION
            "Only active, createAndGo and destroy are allowed."

        OBJECT      etsysTwcbWebcacheServerRowStatus
--        SYNTAX      RowStatus {
        SYNTAX      INTEGER {
                        active(1),
                        createAndGo(4),
                        destroy(6)
                    }
        DESCRIPTION
            "Only active, createAndGo and destroy are allowed."

        OBJECT      etsysTwcbWebcacheServerHostPermitRowStatus
--        SYNTAX      RowStatus {
        SYNTAX      INTEGER {
                        active(1),
                        createAndGo(4),
                        destroy(6)
                    }
        DESCRIPTION
            "Only active, createAndGo and destroy are allowed."

        OBJECT      etsysTwcbWebcacheServerHostDenyRowStatus
--        SYNTAX      RowStatus {
        SYNTAX      INTEGER {
                        active(1),
                        createAndGo(4),
                        destroy(6)
                    }
        DESCRIPTION
            "Only active, createAndGo and destroy are allowed."

        OBJECT      etsysTwcbWebcacheServerBypassRowStatus
--        SYNTAX      RowStatus {
        SYNTAX      INTEGER {
                        active(1),
                        createAndGo(4),
                        destroy(6)
                    }
        DESCRIPTION
            "Only active, createAndGo and destroy are allowed."

        OBJECT      etsysTwcbBindingAddressType
--        SYNTAX      InetAddressType {
        SYNTAX      INTEGER {
                        ipv4(1),
                        ipv6(2)
                    }
        DESCRIPTION
            "Only IPv4 and IPv6 addresses are allowed."

        OBJECT      etsysTwcbBindingClear
        MIN-ACCESS  read-only
        DESCRIPTION
            "Write access is not required."

     ::= { etsysTwcbMIBCompliances 1 }

END
