ENTERASYS-IEEE8021-Q-BRIDGE-MIB-EXT-MIB DEFINITIONS ::= BEGIN

--  enterasys-ieee8021-q-bridge-mib-ext-mib.txt 
--
--  Part Number:
--
--

--  This module provides authoritative definitions for Enterasys
--  Networks' IEEE8021-Q-BRIDGE-MIB extension mib

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in
--  connection with the management of Enterasys Networks products.

--  Copyright February, 2013 Enterasys Networks, Inc.

IMPORTS
    MODULE-IDENTITY, OBJECT-TYPE, Counter64
        FROM SNMPv2-SMI
    MODULE-COMPLIANCE, OBJECT-GROUP
        FROM SNMPv2-CONF
    TEXTUAL-CONVENTION
        FROM SNMPv2-TC
    IEEE8021PbbComponentIdentifier, IEEE8021VlanIndex
        FROM IEEE8021-TC-MIB
    EnabledStatus
        FROM P-BRIDGE-MIB
    ieee8021BridgeBasePortEntry
        FROM IEEE8021-BRIDGE-MIB
    etsysModules
        FROM ENTERASYS-MIB-NAMES;

etsysIeee8021QBridgeMibExtMIB MODULE-IDENTITY
    LAST-UPDATED "201302151853Z"  -- Fri Feb 15 18:53 UTC 2013
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "This MIB module defines a portion of the SNMP MIB under
         the Enterasys Networks enterprise OID pertaining to
         proprietary extensions to the IEEE8021-Q-BRIDGE-MIB."

    REVISION     "201302151853Z"  -- Fri Feb 15 18:53 UTC 2013
    DESCRIPTION  "Added the  etsysIeee8021QBridgeFdb branch to 
                  control and report the number of entries in 
                  the filter database."

    REVISION     "201202071359Z"  -- Tue Feb  7 13:59 UTC 2012
    DESCRIPTION  "Initial version of this MIB module."

    ::= { etsysModules 88 }

-- -------------------------------------------------------------
-- Textual Conventions
-- -------------------------------------------------------------
EtsysIeee8021QBridgeFdbEntries ::= TEXTUAL-CONVENTION 
    STATUS  current
    DESCRIPTION
        "Integer that especifies the maximum number of entries
         in the filter database."
    SYNTAX      INTEGER {
                  is4K   ( 4096   ),
                  is8K   ( 8192   ),
                  is16K  ( 16384  ),
                  is32K  ( 32768  ),
                  is64K  ( 65536  ),
                  is128K ( 131072 )
                }

-- -------------------------------------------------------------
-- Object and Conformance Definitions
-- -------------------------------------------------------------

etsysIeee8021QBridgeMibExtObjects 
    OBJECT IDENTIFIER ::= { etsysIeee8021QBridgeMibExtMIB 1 }

etsysIeee8021QBridgeMibExtConformance
    OBJECT IDENTIFIER ::= { etsysIeee8021QBridgeMibExtMIB 2 }

-- -------------------------------------------------------------
-- Object Branch Definitions
-- -------------------------------------------------------------

etsysIeee8021QBridgeMibExtMvrpBranch
    OBJECT IDENTIFIER ::= { etsysIeee8021QBridgeMibExtObjects 1 }

etsysIeee8021QBridgeMibExtPortVlanBranch
    OBJECT IDENTIFIER ::= { etsysIeee8021QBridgeMibExtObjects 2 }

etsysIeee8021QBridgeMibExtFdbBranch
    OBJECT IDENTIFIER ::= { etsysIeee8021QBridgeMibExtObjects 3 }

-- -------------------------------------------------------------
-- The Enterasys MVRP VLAN Restriction Configuration Table
-- -------------------------------------------------------------

etsysIeee8021QVlanMvrpRestrictedTable OBJECT-TYPE
    SYNTAX      SEQUENCE OF EtsysIeee8021QVlanMvrpRestrictedEntry
    MAX-ACCESS  not-accessible
    STATUS      current
    DESCRIPTION
        "A table containing per VLAN control and status
         information for MVRP VLAN configuration in the device."
    ::= { etsysIeee8021QBridgeMibExtMvrpBranch 1 }

etsysIeee8021QVlanMvrpRestrictedEntry OBJECT-TYPE
    SYNTAX      EtsysIeee8021QVlanMvrpRestrictedEntry
    MAX-ACCESS  not-accessible
    STATUS      current
    DESCRIPTION
        "Information controlling proprietary VLAN configuration 
         for MVRP on a device."
    INDEX { etsysIeee8021QVlanMvrpRestrictedComponentId,
            etsysIeee8021QVlanMvrpRestrictedIndex }
    ::= { etsysIeee8021QVlanMvrpRestrictedTable 1 }

EtsysIeee8021QVlanMvrpRestrictedEntry ::=
    SEQUENCE {
        etsysIeee8021QVlanMvrpRestrictedComponentId
            IEEE8021PbbComponentIdentifier,
        etsysIeee8021QVlanMvrpRestrictedIndex
            IEEE8021VlanIndex,
        etsysIeee8021QVlanMvrpRestrictedStatus
            EnabledStatus
    }

etsysIeee8021QVlanMvrpRestrictedComponentId OBJECT-TYPE
    SYNTAX      IEEE8021PbbComponentIdentifier
    MAX-ACCESS  not-accessible
    STATUS      current
    DESCRIPTION
        "The PBB component identifier to which this entry's 
         restricted MVRP VLAN attribute status applies."
    ::= { etsysIeee8021QVlanMvrpRestrictedEntry 1 }

etsysIeee8021QVlanMvrpRestrictedIndex OBJECT-TYPE
    SYNTAX      IEEE8021VlanIndex
    MAX-ACCESS  not-accessible
    STATUS      current
    DESCRIPTION
        "The VLAN to which this entry's restricted MVRP VLAN 
         attribute status applies."
    ::= { etsysIeee8021QVlanMvrpRestrictedEntry 2 }

etsysIeee8021QVlanMvrpRestrictedStatus OBJECT-TYPE
    SYNTAX      EnabledStatus
    MAX-ACCESS  read-write
    STATUS      current
    DESCRIPTION
        "The state of restricted MVRP operation for this VLAN.  The 
         value enabled(1) indicates that restricted MVRP operation is 
         enabled for this VLAN.  This object affects MVRP Applicant
         and Registrar state machines for this VLAN on all ports.  
         If restricted MVRP is enabled for a VLAN the following rules 
         are applied:

         1. If MVRP is globally enabled and 

         2. If MVRP is enabled at the port level, then

         3. Any ports that were members of the dot1qVlanCurrentEgressPorts
            table due to MVRP will signal to remove this registration and no
            further registration requests received in MVRP PDUs for this 
            VLAN will be processed and

         4. Any ports that were propagating registration information for 
            this VLAN will cease propagation and all further MVRP PDUs 
            transmitted after the initial withdrawal attempt will not
            include event notifications for this VLAN."
    DEFVAL      { disabled }
    ::= { etsysIeee8021QVlanMvrpRestrictedEntry 3 }

-- -------------------------------------------------------------
-- The Enterasys Port VLAN Extension Table
-- -------------------------------------------------------------

etsysIeee8021QBridgeMibExtPortVlanTable OBJECT-TYPE
    SYNTAX      SEQUENCE OF EtsysIeee8021QBridgeMibExtPortVlanEntry
    MAX-ACCESS  not-accessible
    STATUS      current
    DESCRIPTION
        "A table of bridge port MRP timer control information."
    ::= { etsysIeee8021QBridgeMibExtPortVlanBranch 1 }

etsysIeee8021QBridgeMibExtPortVlanEntry OBJECT-TYPE
    SYNTAX      EtsysIeee8021QBridgeMibExtPortVlanEntry
    MAX-ACCESS  not-accessible
    STATUS      current
    DESCRIPTION
        "A conceptual row in etsysIeee8021QBridgeMibExtPortVlanTable."
    AUGMENTS { ieee8021BridgeBasePortEntry }
    ::= { etsysIeee8021QBridgeMibExtPortVlanTable 1 }

EtsysIeee8021QBridgeMibExtPortVlanEntry ::=
    SEQUENCE {
        etsysIeee8021QBridgePortMvrpRxVidTranslationErrors
            Counter64,
        etsysIeee8021QBridgePortMvrpTxVidTranslationErrors
            Counter64
    }

etsysIeee8021QBridgePortMvrpRxVidTranslationErrors OBJECT-TYPE
    SYNTAX      Counter64
    UNITS       "MVRP receive VID translation errors"
    MAX-ACCESS  read-only
    STATUS      current
    DESCRIPTION
        "The total number of receive errors for MVRP due to an
         incompatible VID translation configuration on a port. 

         This error occurs when an MVRPDU is received on a
         port which has a VID translation table configured and
         the MVRPDU contains messages for multiple local VIDs 
         that map to the same relay VID.  The MVRPDU is 
         discarded when this error is detected."
    ::= { etsysIeee8021QBridgeMibExtPortVlanEntry 1 }

etsysIeee8021QBridgePortMvrpTxVidTranslationErrors OBJECT-TYPE
    SYNTAX      Counter64
    UNITS       "MVRP transmit VID translation errors"
    MAX-ACCESS  read-only
    STATUS      current
    DESCRIPTION
        "The total number of transmit errors for MVRP due to an
         incompatible VID translation configuration on a port.  

         This error occurs when an MVRPDU is being encoded for
         transmit on a port which has a VID translation table 
         configured and the MVRPDU has messages for multiple 
         local VIDs that map to the same relay VID.  The MVRPDU
         is discarded when this error occurs."
    ::= { etsysIeee8021QBridgeMibExtPortVlanEntry 2 }

-- -------------------------------------------------------------
-- The Enterasys FDB extension leaves
-- -------------------------------------------------------------
etsysIeee8021QBridgeFdb
    OBJECT IDENTIFIER ::= { etsysIeee8021QBridgeMibExtFdbBranch 1 }

etsysIeee8021QBridgeFdbMaxNumEntriesCapabilities OBJECT-TYPE
    SYNTAX      BITS {
                    fdbMaxNumEntries4K(0),
                    fdbMaxNumEntries8K(1),
                    fdbMaxNumEntries16K(2),
                    fdbMaxNumEntries32K(3),
                    fdbMaxNumEntries64K(4),
                    fdbMaxNumEntries128K(5)
                }
    MAX-ACCESS  read-only
    STATUS      current
    DESCRIPTION
        "Indicates the values of maximum number of entries supported
         by the hardware. The possible values are as follows:
             fdbMaxNumEntries4K(0) - The maximum number of entries in
                 the filter database is 4K (4096).

             fdbMaxNumEntries8K(1) - The maximum number of entries in
                 the filter database is 8K (8192).

             fdbMaxNumEntries16K(2) - The maximum number of entries in
                 the filter database is 16K (16384).

             fdbMaxNumEntries32K(3) - The maximum number of entries in
                 the filter database is 32K (32768).

             fdbMaxNumEntries64K(4) - The maximum number of entries in
                 the filter database is 64K (65536).

             fdbMaxNumEntries128K(5) - The maximum number of entries in
                 the filter database is 128K (131072)."

    ::= { etsysIeee8021QBridgeFdb 1 }

etsysIeee8021QBridgeFdbMaxNumEntries OBJECT-TYPE
    SYNTAX      EtsysIeee8021QBridgeFdbEntries 
    MAX-ACCESS  read-write
    STATUS      current
    DESCRIPTION
        "Indicates the configured maximum number of entries in the
         filter database."

    ::= { etsysIeee8021QBridgeFdb 2 }

etsysIeee8021QBridgeFdbOperMaxNumEntries OBJECT-TYPE
    SYNTAX      EtsysIeee8021QBridgeFdbEntries
    MAX-ACCESS  read-only
    STATUS      current
    DESCRIPTION
        "Indicates the operational maximum number of entries in the
         filter database."

    ::= { etsysIeee8021QBridgeFdb 3 }

-- -------------------------------------------------------------
-- Conformance Information
-- -------------------------------------------------------------

etsysIeee8021QBridgeMibExtGroups      
    OBJECT IDENTIFIER ::= { etsysIeee8021QBridgeMibExtConformance 1 }

etsysIeee8021QBridgeMibExtCompliances 
    OBJECT IDENTIFIER ::= { etsysIeee8021QBridgeMibExtConformance 2 }

-- -------------------------------------------------------------
-- Units of conformance
-- -------------------------------------------------------------

etsysIeee8021QBridgeMibExtMvrpGroup OBJECT-GROUP
    OBJECTS { etsysIeee8021QVlanMvrpRestrictedStatus }
    STATUS      current
    DESCRIPTION
        "A collection of objects providing device level control over
         the ability of MVRP to add and remove unconfigured ports to
         the egress list of particular VLANs."
    ::= { etsysIeee8021QBridgeMibExtGroups 1 }

etsysIeee8021QBridgeMibExtPortVlanGroup OBJECT-GROUP
    OBJECTS { etsysIeee8021QBridgePortMvrpRxVidTranslationErrors,
              etsysIeee8021QBridgePortMvrpTxVidTranslationErrors }
    STATUS      current
    DESCRIPTION
        "A collection of objects providing statistics on errors
         detected by MVRP that identify incompatible configuration
         of the VID translation table."
    ::= { etsysIeee8021QBridgeMibExtGroups 2 }

etsysIeee8021QBridgeMibExtFdbGroup OBJECT-GROUP
    OBJECTS { etsysIeee8021QBridgeFdbMaxNumEntriesCapabilities,
              etsysIeee8021QBridgeFdbMaxNumEntries,
              etsysIeee8021QBridgeFdbOperMaxNumEntries }
    STATUS      current
    DESCRIPTION
        "A collection of objects providing information about 
         the maximum number of entries in the filter database."
    ::= { etsysIeee8021QBridgeMibExtGroups 3 }
 
-- -------------------------------------------------------------
-- Compliance statements
-- -------------------------------------------------------------

etsysIeee8021QBridgeMibExtMvrp MODULE-COMPLIANCE
    STATUS      current
    DESCRIPTION
        "The compliance statement for devices that support
        Enterasys extensions to IEEE8021-Q-BRIDGE-MIB."

    MODULE
        GROUP       etsysIeee8021QBridgeMibExtMvrpGroup
        DESCRIPTION
            "This group is REQUIRED for devices that support the ability
             to include or exclude individual VLANs from participating in
             MVRP."
    ::= { etsysIeee8021QBridgeMibExtCompliances  1 }

etsysIeee8021QBridgeMibExtPortVlan MODULE-COMPLIANCE
    STATUS      current
    DESCRIPTION
        "The compliance statement for devices that support
         Enterasys extensions to IEEE8021-Q-BRIDGE-MIB."

    MODULE
        GROUP       etsysIeee8021QBridgeMibExtPortVlanGroup
        DESCRIPTION
            "This group is REQUIRED for devices that support the ability
             to configure MVRP and VID translation on a port."
    ::= { etsysIeee8021QBridgeMibExtCompliances  2 }

etsysIeee8021QBridgeMibExtFdb MODULE-COMPLIANCE
    STATUS      current
    DESCRIPTION
        "The compliance statement for devices that support
         Enterasys extensions to IEEE8021-Q-BRIDGE-MIB."

     MODULE
        GROUP       etsysIeee8021QBridgeMibExtFdbGroup
        DESCRIPTION
            "This group is REQUIRED for devices that support the ability
             to resize the maximum number of entries in the filter 
             database."
    ::= { etsysIeee8021QBridgeMibExtCompliances  3 }

END
