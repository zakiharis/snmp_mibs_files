-- Revision 1.0.1.
-- Copyright 2000 Marconi Corporation.
-- All rights reserved.

ES1200-MIB    DEFINITIONS ::= BEGIN
    IMPORTS
        OBJECT-TYPE    FROM RFC-1212
        enterprises     FROM RFC1155-SMI
        IpAddress    FROM RFC1155-SMI
        TRAP-TYPE    FROM RFC-1215
        Counter, TimeTicks          FROM RFC1155-SMI
        dot1dBasePort, MacAddress   FROM BRIDGE-MIB
        DisplayString    FROM RFC1213-MIB;


-- =================================
    PortList    ::= OCTET STRING(SIZE(12))
    VlanIndex    ::= INTEGER (1..4094)
-- =================================

    fore    OBJECT IDENTIFIER ::= { enterprises 326 }
    systems    OBJECT IDENTIFIER ::= { fore 2 }
    ethernet    OBJECT IDENTIFIER ::= { systems 20 }
	edge    OBJECT IDENTIFIER ::= { ethernet 1 }
	edgecommon    OBJECT IDENTIFIER ::= { edge 1 }

    golf    OBJECT IDENTIFIER ::= { edge 2 }
    golfproducts    OBJECT IDENTIFIER ::= { golf 1 }
    es1200    OBJECT IDENTIFIER ::= { golfproducts 2 }

-- id_rec.mib

	golfcommon    OBJECT IDENTIFIER ::= { golf 2 }
        fore-products    OBJECT IDENTIFIER ::= { golfcommon 1 }
            fore-es1200Prod    OBJECT IDENTIFIER ::= { fore-products 25 }
                swProperty    OBJECT IDENTIFIER ::= { fore-es1200Prod 1 }
                    swModule    OBJECT IDENTIFIER ::= { swProperty 1 }
                
                es1200DevRegistration    OBJECT IDENTIFIER ::= { fore-es1200Prod 2 }
                    es1200Device    OBJECT IDENTIFIER ::= { es1200DevRegistration 1 }
                
                es1200UnitRegistration    OBJECT IDENTIFIER ::= { fore-es1200Prod 3 }
                    es1200Master    OBJECT IDENTIFIER ::= { es1200UnitRegistration 1 }
                    es1210Slave1    OBJECT IDENTIFIER ::= { es1200UnitRegistration 2 }
                    es1210Slave2    OBJECT IDENTIFIER ::= { es1200UnitRegistration 3 }        
                    es1210Slave3    OBJECT IDENTIFIER ::= { es1200UnitRegistration 4 }
                               
                es1200ModuleRegistration    OBJECT IDENTIFIER ::= { fore-es1200Prod 4 }
                    es1200ModuleMainboardTx    OBJECT IDENTIFIER ::= { es1200ModuleRegistration 1 }
                    es1200ModuleTxTwoPort    OBJECT IDENTIFIER ::= { es1200ModuleRegistration 2 }
                    es1200ModuleFxSC    OBJECT IDENTIFIER ::= { es1200ModuleRegistration 3 }
                    es1200ModuleFxMTRJ    OBJECT IDENTIFIER ::= { es1200ModuleRegistration 4 }
                    es1200ModuleSIO    OBJECT IDENTIFIER ::= { es1200ModuleRegistration 5 }
                    es1200ModuleSXGIGAOnePort    OBJECT IDENTIFIER ::= { es1200ModuleRegistration 6 }
                    es1200ModuleSXGIGATwoPort    OBJECT IDENTIFIER ::= { es1200ModuleRegistration 7 }
                    es1200ModuleLXGIGAOnePort    OBJECT IDENTIFIER ::= { es1200ModuleRegistration 8 }
                    es1200ModuleLXGIGATwoPort    OBJECT IDENTIFIER ::= { es1200ModuleRegistration 9 }
                    es1200ModuleTXGIGAOnePort    OBJECT IDENTIFIER ::= { es1200ModuleRegistration 10 }
                    es1200ModuleTXGIGATwoPort    OBJECT IDENTIFIER ::= { es1200ModuleRegistration 11 }                                                
                    es1200ModuleNone    OBJECT IDENTIFIER ::= { es1200ModuleRegistration 12 }
                    
                es1210ModuleRegistration    OBJECT IDENTIFIER ::= { fore-es1200Prod 5 }
                    es1210ModuleMainboardTx    OBJECT IDENTIFIER ::= { es1210ModuleRegistration 1 }
                    es1210ModuleTxTwoPort    OBJECT IDENTIFIER ::= { es1210ModuleRegistration 2 }
                    es1210ModuleFxSC    OBJECT IDENTIFIER ::= { es1210ModuleRegistration 3 }
                    es1210ModuleFxMTRJ    OBJECT IDENTIFIER ::= { es1210ModuleRegistration 4 }
                    es1210ModuleSIO    OBJECT IDENTIFIER ::= { es1210ModuleRegistration 5 }                                    
                    es1210ModuleNone    OBJECT IDENTIFIER ::= { es1210ModuleRegistration 6 }
                    
                es1200PortRegistration    OBJECT IDENTIFIER ::= { fore-es1200Prod 6 }
                    es1200Port-10-100TX    OBJECT IDENTIFIER ::= { es1200PortRegistration 1 }
                    es1200Port-100-SC    OBJECT IDENTIFIER ::= { es1200PortRegistration 2 }
                    es1200Port-100-MTRJ    OBJECT IDENTIFIER ::= { es1200PortRegistration 3 }
                    es1200Port-1000-SX    OBJECT IDENTIFIER ::= { es1200PortRegistration 4 }
                    es1200Port-1000-LX    OBJECT IDENTIFIER ::= { es1200PortRegistration 5 }
                    es1200Port-1000-TX    OBJECT IDENTIFIER ::= { es1200PortRegistration 6 }
                    
                es1210PortRegistration    OBJECT IDENTIFIER ::= { fore-es1200Prod 7 }
                    es1210Port-10-100TX    OBJECT IDENTIFIER ::= { es1210PortRegistration 1 }
                    es1210Port-100-SC    OBJECT IDENTIFIER ::= { es1210PortRegistration 2 }
                    es1210Port-100-MTRJ    OBJECT IDENTIFIER ::= { es1210PortRegistration 3 }                                            

                es1200PowerSupplyRegistration    OBJECT IDENTIFIER ::= { fore-es1200Prod 8 }
                    es1200PowerSupply    	OBJECT IDENTIFIER ::= { es1200PowerSupplyRegistration 1 }
                    
                es1210PowerSupplyRegistration    OBJECT IDENTIFIER ::= { fore-es1200Prod 9 }
                    es1210PowerSupply    	OBJECT IDENTIFIER ::= { es1210PowerSupplyRegistration 1 }                                            

                es1200FanRegistration    OBJECT IDENTIFIER ::= { fore-es1200Prod 10 }
                    es1200Fan    OBJECT IDENTIFIER ::= { es1200FanRegistration 1 }
                    
                es1210FanRegistration    OBJECT IDENTIFIER ::= { fore-es1200Prod 11 }
                    es1210Fan    OBJECT IDENTIFIER ::= { es1210FanRegistration 1 }                                            

                es1200SlotRegistration    OBJECT IDENTIFIER ::= { fore-es1200Prod 12 }
                    es1200Slot1    OBJECT IDENTIFIER ::= { es1200SlotRegistration 1 }
                    es1200Slot2    OBJECT IDENTIFIER ::= { es1200SlotRegistration 2 }
                    es1200Slot3    OBJECT IDENTIFIER ::= { es1200SlotRegistration 3 }
                    
                es1210SlotRegistration    OBJECT IDENTIFIER ::= { fore-es1200Prod 13 }
                    es1210Slot1    OBJECT IDENTIFIER ::= { es1210SlotRegistration 1 }
                    es1210Slot2    OBJECT IDENTIFIER ::= { es1210SlotRegistration 2 }                                            

                es1200SensorRegistration    OBJECT IDENTIFIER ::= { fore-es1200Prod 14 }

                es1200BackplaneRegistration    OBJECT IDENTIFIER ::= { fore-es1200Prod 15 }

    fore-mgmt    OBJECT IDENTIFIER ::= { golfcommon 2 }
    es1200Mgmt    OBJECT IDENTIFIER ::= { fore-mgmt 25 }
    swL2Mgmt    OBJECT IDENTIFIER ::= { es1200Mgmt 2 }

-- struct.mib

    swStructure    OBJECT IDENTIFIER ::= { es1200Mgmt 1 }

-- ********************************************************************
--  swStructInfo describe the device level structure information        
-- ********************************************************************
    swStructInfo    OBJECT IDENTIFIER ::= { swStructure 1 }

    swStructDevType OBJECT-TYPE
        SYNTAX OBJECT IDENTIFIER
        ACCESS read-only
        STATUS mandatory
        DESCRIPTION
            "Specifies the device type"
        ::= { swStructInfo 1 }

    swStructDevDescr OBJECT-TYPE
        SYNTAX DisplayString (SIZE(0..64))
        ACCESS read-only
        STATUS mandatory
        DESCRIPTION
            "Describes the type of the device"
        ::= { swStructInfo 2 }

    swStructPortEncodingFactor OBJECT-TYPE
        SYNTAX INTEGER
        ACCESS read-only
        STATUS mandatory
        DESCRIPTION
            "The factor to encode the global port ID from unit ID and the local port ID.
              This global port ID is required to access the bridge MIB and spanning tree MIB 
              defined by the standard body. This global port ID will provide a unigue port ID for
              each port across the entire device.
              Example: supoposed that the encoding factor is 24, then port 2 located on unit 2 will 
              be encoded as port 26"
        ::= { swStructInfo 3 }

-- ********************************************************************
--  swStructUnitTable        
-- ********************************************************************

    swStructUnitTable OBJECT-TYPE
        SYNTAX  SEQUENCE OF SwStructUnitEntry
        ACCESS  not-accessible
        STATUS  mandatory
        DESCRIPTION
            "A table that contains information about a unit in the device."
        ::= { swStructure 2 }

    swStructUnitEntry OBJECT-TYPE
        SYNTAX  SwStructUnitEntry
        ACCESS  not-accessible
        STATUS  mandatory
        DESCRIPTION
            "A list of information for each unit in the device."
        INDEX   { swStructUnitIndex }
        ::= { swStructUnitTable 1 }

    SwStructUnitEntry ::= 
        SEQUENCE {
            swStructUnitIndex
                INTEGER,
            swStructUnitType
                OBJECT IDENTIFIER,
            swStructUnitDescr
                DisplayString (SIZE(0..64)),
            swStructUnitLedInfo
                OCTET STRING (SIZE(0..7)),
            swStructUnitMaxModuleNum
                INTEGER,
            swStructUnitMaxPortNum
                INTEGER,
            swStructUnitNumOfPortInUse
                INTEGER,
            swStructUnitOperStatus
                INTEGER,
            swStructUnitLastChange
                INTEGER
        }

    swStructUnitIndex OBJECT-TYPE
        SYNTAX INTEGER
        ACCESS read-only
        STATUS mandatory
        DESCRIPTION
            "ID of the unit in the device"
        ::= { swStructUnitEntry 1 }

    swStructUnitType OBJECT-TYPE
        SYNTAX OBJECT IDENTIFIER
        ACCESS read-only
        STATUS mandatory
        DESCRIPTION
            "Type of the unit"
        ::= { swStructUnitEntry 2 }

    swStructUnitDescr OBJECT-TYPE
        SYNTAX DisplayString (SIZE(0..64))
        ACCESS read-only
        STATUS mandatory
        DESCRIPTION
            "Type of the unit in displayed string format"
        ::= { swStructUnitEntry 3 }

    swStructUnitLedInfo OBJECT-TYPE
        SYNTAX OCTET STRING (SIZE(0..7))
        ACCESS read-only
        STATUS mandatory
        DESCRIPTION
            "Provides the LED information for the unit.
             Master:
                byte 0:
                    bit 0:Condole in Use (0:not used,1:used)
                    bit 1:Giga module status (0:not exist,1:exist)
                    bit 2:Giga module port1 status (0:link fail,1:link pass)
                    bit 3:Giga module port2 status (0:link fail,1:link pass)
                    
                    bit 4:Slot2 module status (0:not exist,1:exist)
                    bit 5:Unit slave1 status (0:not exist,1:exist)
                    bit 6:Unit slave2 status (0:not exist,1:exist)
                    bit 7:Unit slave3 status (0:not exist,1:exist)
                    
                byte 1:
                    bit 0:Slot1 module port1 nway status (0:10M,1:100M)
                    bit 1:Slot1 module port1 link status (0:link fail,1:link pass)
                    bit 2:Slot1 module port2 nway status (0:10M,1:100M)            
                    bit 3:Slot1 module port2 link status (0:link fail,1:link pass) 
                    
                    bit 4:Base module port1 nway status (0:10M,1:100M)           
                    bit 5:Base module port1 link status (0:link fail,1:link pass)
                    bit 6:Base module port2 nway status (0:10M,1:100M)             
                    bit 7:Base module port2 link status (0:link fail,1:link pass)  
                    
                byte 2:
                    bit 0:Base module port3 nway status (0:10M,1:100M)            
                    bit 1:Base module port3 link status (0:link fail,1:link pass) 
                    bit 2:Base module port4 nway status (0:10M,1:100M)             
                    bit 3:Base module port4 link status (0:link fail,1:link pass)  
                    
                    bit 4:Base module port5 nway status (0:10M,1:100M)           
                    bit 5:Base module port5 link status (0:link fail,1:link pass)
                    bit 6:Base module port6 nway status (0:10M,1:100M)             
                    bit 7:Base module port6 link status (0:link fail,1:link pass)
                    
                byte 3: ...
                  .
                  .
                byte 7: ...  
                        
             Slave:
                byte 0:
                    bit 0:Not used
                    bit 1:Not used
                    bit 2:Not used
                    bit 3:Not used
                    
                    bit 4:Slot2 module status (0:not exist,1:exist)
                    bit 5:Unit slave1 status (0:not exist,1:exist)
                    bit 6:Unit slave2 status (0:not exist,1:exist)
                    bit 7:Unit slave3 status (0:not exist,1:exist)
                    
                byte 1:
                    bit 0:Slot1 module port1 nway status (0:10M,1:100M)
                    bit 1:Slot1 module port1 link status (0:link fail,1:link pass)
                    bit 2:Slot1 module port2 nway status (0:10M,1:100M)            
                    bit 3:Slot1 module port2 link status (0:link fail,1:link pass) 
                    
                    bit 4:Base module port1 nway status (0:10M,1:100M)           
                    bit 5:Base module port1 link status (0:link fail,1:link pass)
                    bit 6:Base module port2 nway status (0:10M,1:100M)             
                    bit 7:Base module port2 link status (0:link fail,1:link pass)  
                    
                byte 2: ...
                  .
                  .
                byte 7: ...       
                         
            "
        ::= { swStructUnitEntry 4 }

    swStructUnitMaxModuleNum OBJECT-TYPE
        SYNTAX INTEGER
        ACCESS read-only
        STATUS mandatory
        DESCRIPTION
            "Maximum number of modules allowed on the unit"
        ::= { swStructUnitEntry 5 }
        
    swStructUnitMaxPortNum OBJECT-TYPE
        SYNTAX INTEGER
        ACCESS read-only
        STATUS mandatory
        DESCRIPTION
            "Maximum number of ports allowed on the unit"
        ::= { swStructUnitEntry 6 }

    swStructUnitNumOfPortInUse OBJECT-TYPE
        SYNTAX INTEGER
        ACCESS read-only
        STATUS mandatory
        DESCRIPTION
            "Number of ports which has link being connected to the port"
        ::= { swStructUnitEntry 7 }

    swStructUnitOperStatus OBJECT-TYPE
        SYNTAX INTEGER {
            other(1),
            notAvail(2),
            removed(3),
            disabled(4),
            normal(5),
            nonFatalErr(9),
            fatalErr(10)
        }
        ACCESS read-only
        STATUS mandatory
        DESCRIPTION
            "Describes the operation status for the unit"
        ::= { swStructUnitEntry 8 }

    swStructUnitLastChange OBJECT-TYPE
        SYNTAX INTEGER
        ACCESS read-only
        STATUS mandatory
        DESCRIPTION
            "Provides the time that the unit is up last time"
        ::= { swStructUnitEntry 9 }

-- ********************************************************************
--  swStructModuleTable        
-- ********************************************************************

    swStructModuleTable OBJECT-TYPE
        SYNTAX  SEQUENCE OF SwStructModuleEntry
        ACCESS  not-accessible
        STATUS  mandatory
        DESCRIPTION
            "A table that contains information about a module."
        ::= { swStructure 3 }

    swStructModuleEntry OBJECT-TYPE
        SYNTAX  SwStructModuleEntry
        ACCESS  not-accessible
        STATUS  mandatory
        DESCRIPTION
            "A list of information for a module."
        INDEX   { swStructModuleUnitIndex, swStructModuleIndex, swStructModuleSubMduIndex }
        ::= { swStructModuleTable 1 }

    SwStructModuleEntry ::= 
        SEQUENCE {
            swStructModuleUnitIndex
                INTEGER,
            swStructModuleIndex
                INTEGER,
            swStructModuleSubMduIndex
                INTEGER,
            swStructModuleType
                OBJECT IDENTIFIER,
            swStructModuleDescr
                DisplayString (SIZE(0..64)),
            swStructModuleVersion
                INTEGER,
            swStructModuleMaxPortNum
                INTEGER,            
            swStructModuleEncodingOffset
                INTEGER,
--            swStructModuleRAM 
--                INTEGER,
--            swStructModuleEPROM
--                INTEGER,
--            swStructModuleFLASH
--                INTEGER,
--            swStructModuleLEDInfo
--                OCTET STRING (SIZE (2..32)),
            swStructModuleOperStatus
                INTEGER,
            swStructModuleLastChange
                INTEGER
        }

    swStructModuleUnitIndex OBJECT-TYPE
        SYNTAX INTEGER
        ACCESS read-only
        STATUS mandatory
        DESCRIPTION
            "ID of the unit in the device"
        ::= { swStructModuleEntry 1 }

    swStructModuleIndex OBJECT-TYPE
        SYNTAX INTEGER
        ACCESS read-only
        STATUS mandatory
        DESCRIPTION
            "ID of the Module in the device"
        ::= { swStructModuleEntry 2 }

    swStructModuleSubMduIndex OBJECT-TYPE
        SYNTAX INTEGER
        ACCESS read-only
        STATUS mandatory
        DESCRIPTION
            "If the module doesnot contain sub module, sub module ID is 0. Otherwise, 
             it indicates the ID of the sub module relative to the module"
        ::= { swStructModuleEntry 3 }

    swStructModuleType OBJECT-TYPE
        SYNTAX OBJECT IDENTIFIER
        ACCESS read-only
        STATUS mandatory
        DESCRIPTION
            "Type of the module"
        ::= { swStructModuleEntry 4 }

    swStructModuleDescr OBJECT-TYPE
        SYNTAX DisplayString (SIZE(0..64))
        ACCESS read-only
        STATUS mandatory
        DESCRIPTION
            "Type of the module in displayed string format"
        ::= { swStructModuleEntry 5 }

    swStructModuleVersion OBJECT-TYPE
        SYNTAX INTEGER
        ACCESS read-only
        STATUS mandatory
        DESCRIPTION
            "Provides PCB version of the module"
        ::= { swStructModuleEntry 6 }

    swStructModuleMaxPortNum OBJECT-TYPE
        SYNTAX INTEGER
        ACCESS read-only
        STATUS mandatory
        DESCRIPTION
            "Maximum number of ports allowed on the module"
        ::= { swStructModuleEntry 7 }

    swStructModuleEncodingOffset OBJECT-TYPE
        SYNTAX INTEGER
        ACCESS read-only
        STATUS mandatory
        DESCRIPTION
            "Each module has a offset for encoding the port ID relative to a unit. This encoding
              will provide a unigue port ID for ports located on the device. 
              Example: supoposed that the offset for module 2 is 21, then port 2 located on 
              module 2 will be encoded as port 22"
        ::= { swStructModuleEntry 8 }

--    swStructModuleRAM OBJECT-TYPE
--        SYNTAX INTEGER
--        ACCESS read-only
--        STATUS mandatory
--        DESCRIPTION
--            "get ram size by K on specified module"
--        ::= { swStructModuleEntry 9 }

--    swStructModuleEPROM OBJECT-TYPE
--        SYNTAX INTEGER
--        ACCESS read-only
--        STATUS mandatory
--        DESCRIPTION
--            " get eprom size by K on specified module"
--        ::= { swStructModuleEntry 10 }

--        swStructModuleFLASH OBJECT-TYPE
--        SYNTAX INTEGER
--        ACCESS read-only
--        STATUS mandatory
--        DESCRIPTION
--            "get flash rom size by K on specified module"
--        ::= { swStructModuleEntry 11 }
     
--         swStructModuleLEDInfo OBJECT-TYPE
--        SYNTAX OCTET STRING (SIZE (2..32))
--        ACCESS read-only
--        STATUS mandatory
--        DESCRIPTION
--            "get LED information on specifiled module"
--        ::= { swStructModuleEntry 12 }
                   
    swStructModuleOperStatus OBJECT-TYPE
        SYNTAX INTEGER {
            other(1),
            notAvail(2),
            removed(3),
            disabled(4),
            normal(5),
            nonFatalErr(9),
            fatalErr(10)
        }
        ACCESS read-only
        STATUS mandatory
        DESCRIPTION
            "Provides operation status of the module"
        ::= { swStructModuleEntry 9 }

    swStructModuleLastChange OBJECT-TYPE
        SYNTAX INTEGER
        ACCESS read-only
        STATUS mandatory
        DESCRIPTION
            "Provides the time that the module is up last time"
        ::= { swStructModuleEntry 10 }


-- ********************************************************************
--  swStructPowerTable describes the power supply structure information        
-- ********************************************************************

    swStructPowerTable OBJECT-TYPE
        SYNTAX  SEQUENCE OF SwStructPowerEntry
        ACCESS  not-accessible
        STATUS  mandatory
        DESCRIPTION
            "A table that contains information about every board."
        ::= { swStructure 4 }

    swStructPowerEntry OBJECT-TYPE
        SYNTAX  SwStructPowerEntry
        ACCESS  not-accessible
        STATUS  mandatory
        DESCRIPTION
            "A list of information for each board of the chassis."
        INDEX   { swStructPowerUnitIndex, swStructPowerIndex}
        ::= { swStructPowerTable 1 }

    SwStructPowerEntry ::= 
        SEQUENCE {
            swStructPowerUnitIndex
                INTEGER,
            swStructPowerIndex
                INTEGER,
            swStructPowerOperStatus
                INTEGER
        }

    swStructPowerUnitIndex OBJECT-TYPE
        SYNTAX INTEGER
        ACCESS read-only
        STATUS mandatory
        DESCRIPTION
            "ID of the unit in the device"
        ::= { swStructPowerEntry 1 }

    swStructPowerIndex OBJECT-TYPE
        SYNTAX INTEGER
        ACCESS read-only
        STATUS mandatory
        DESCRIPTION
            "ID of the power supply in the unit"
        ::= { swStructPowerEntry 2 }

    swStructPowerOperStatus OBJECT-TYPE
        SYNTAX INTEGER {
            other(1),
            notAvail(2),
            removed(3),
            disabled(4),
            normal(5),
            nonFatalErr(9),
            fatalErr(10)
        }
        ACCESS read-only
        STATUS mandatory
        DESCRIPTION
            "Describes the operation status of the power supply"
        ::= { swStructPowerEntry 3 }

-- ********************************************************************
--  swStructFanTable describes the fan structure information        
-- ********************************************************************

    swStructFanTable OBJECT-TYPE
        SYNTAX  SEQUENCE OF SwStructFanEntry
        ACCESS  not-accessible
        STATUS  mandatory
        DESCRIPTION
            "A table that contains information about every board."
        ::= { swStructure 5 }

    swStructFanEntry OBJECT-TYPE
        SYNTAX  SwStructFanEntry
        ACCESS  not-accessible
        STATUS  mandatory
        DESCRIPTION
            "A list of information for each board of the chassis."
        INDEX   { swStructFanUnitIndex, swStructFanIndex }
        ::= { swStructFanTable 1 }

    SwStructFanEntry ::= 
        SEQUENCE {
            swStructFanUnitIndex
                INTEGER,
            swStructFanIndex
                INTEGER,
            swStructFanOperStatus
                INTEGER
        }

    swStructFanUnitIndex OBJECT-TYPE
        SYNTAX INTEGER
        ACCESS read-only
        STATUS mandatory
        DESCRIPTION
            "ID of the unit in the device"
        ::= { swStructFanEntry 1 }

    swStructFanIndex OBJECT-TYPE
        SYNTAX INTEGER
        ACCESS read-only
        STATUS mandatory
        DESCRIPTION
            "ID of the fan in the device"
        ::= { swStructFanEntry 2 }

    swStructFanOperStatus OBJECT-TYPE
        SYNTAX INTEGER {
            other(1),
            notAvail(2),
            removed(3),
            disabled(4),
            normal(5),
            nonFatalErr(9),
            fatalErr(10)
        }
        ACCESS read-only
        STATUS mandatory
        DESCRIPTION
            "Describes the operation status of the fan"
        ::= { swStructFanEntry 3 }

-- sfdb.mib

    swFDB    OBJECT IDENTIFIER ::= { swL2Mgmt 9 }

    endOfMIB    OBJECT-TYPE
        SYNTAX  INTEGER
        ACCESS  read-only
        STATUS  optional
DESCRIPTION ""
        ::= { es1200Mgmt 9999 }

-- ********************************************************************
--  swFdbStaticTable
-- ********************************************************************
    swFdbStaticTable OBJECT-TYPE
        SYNTAX SEQUENCE OF SwFdbStaticEntry
        ACCESS not-accessible
        STATUS mandatory
        DESCRIPTION
            "This table defines for frames with specific destincation MAC address,
             the set of ports that the frame will be forwarded to. Note that if a MAC
             address appears in this table also appears in the filter table, the filter
             table has higher priority over than this table. See swFdbFilterTable description."
        ::= { swFDB 1 }

    swFdbStaticEntry OBJECT-TYPE
        SYNTAX SwFdbStaticEntry
        ACCESS not-accessible
        STATUS mandatory
        DESCRIPTION
            "A list of information specifies which ports the frames with specific
             destination MAC address to go."
        INDEX  { swFdbStaticVid , swFdbStaticAddress }
        ::= { swFdbStaticTable 1 }

    SwFdbStaticEntry ::=
        SEQUENCE {
            swFdbStaticVid
                INTEGER,
            swFdbStaticAddress
                MacAddress,
            swFdbStaticPortMap
                PortList,
            swFdbStaticJoinIGMPSnooping
                INTEGER,
            swFdbStaticState
                INTEGER,
            swFdbStaticStatus
                INTEGER
        }

    swFdbStaticVid OBJECT-TYPE
        SYNTAX INTEGER
        ACCESS read-only
        STATUS mandatory
        DESCRIPTION
            "This object indicates the VLAN-ID. If the swVlanInfoStatus is
            port-base mode , the object ranges from 1 to 12. If VLAN is in
            mac-based mode or disabled, the object indicates the default
            VLAN-ID(0)."
        ::= { swFdbStaticEntry 1 }

    swFdbStaticAddress OBJECT-TYPE
        SYNTAX MacAddress
        ACCESS read-only
        STATUS mandatory
        DESCRIPTION
            "The MAC address which this forwarding entry applied. It can be an unicast address
             or a multicast address."
        ::= { swFdbStaticEntry 2 }

    swFdbStaticPortMap OBJECT-TYPE
        SYNTAX PortList
        ACCESS read-write
        STATUS mandatory
        DESCRIPTION
            "The set of ports to which frames received containing the value of swFdbStaticAddress
             as the DA, are allowed to be forwarded. Each octet within the value of
             this object specifies a set of eight ports, with the first octet specifying
             ports 1 through 8, the second octet specifying ports 9 through 16, etc.
             Within each octet, the most significant bit represents the lowest
             numbered port, and the least significant bit represents the highest
             numbered port.  Thus, each port of the bridge is represented by
             a single bit within the value of this object.  If that bit has a
             value of '1' then that port is included in the set of ports; the
             port is not included if its bit has a value of '0'.(Note that the
             setting of the bit corresponding to the port from which a frame
             is received is irrelevant.)"
        ::= { swFdbStaticEntry 3 }

    swFdbStaticJoinIGMPSnooping OBJECT-TYPE
        SYNTAX INTEGER {
               other(1),
               disabled(2),
               enabled(3)
               }
        ACCESS read-write
        STATUS mandatory
        DESCRIPTION
            "This object indicates whether to allow ports to join/leave IGMP group
             via IGMP Snooping.

             For a multicast address entry, port group could be classified into
             two catelogies : one is static and another is dynamic. In static port
             group, port members is defined statically by user, and dynamic port
             group allows a port member to join/leave the membership dynamically,
             according to IGMP report/leave messages. When this object is set to
             'enabled', it allows dynamic port group updated for the multicast
             address entry as well as static port group. When it is set to 'disabled'
             , dynamic port member join/leave is disabled, but static port group is
             not affected.

             This object is only vaild for multicast address indicated by
             swFdbStaticAddressIndex. It always is 'disabled' for unicast addresses.

            other(1) - this entry is currently in use but the conditions under
                which it will remain so are different from each of the following
                values.
            disabled(2) - this entry doesn't allow dynamic updates via IGMP Snooping.This
                          is a default setting.
            enabled(3) - this entry allow dynamic updates via IGMP Snooping."
        ::= { swFdbStaticEntry 4 }

    swFdbStaticState OBJECT-TYPE
        SYNTAX INTEGER {
               other(1),
               invalid(2),
               valid(3)
        }
        ACCESS read-write
        STATUS mandatory
        DESCRIPTION
            "This object indicates the status of this entry.
            other(1) - this entry is currently in use but the conditions under
                which it will remain so are different from each of the following
                values.
            invalid(2) - writing this value to the object, and then the corresponding
                entry will be removed from the table.
            valid(3) - this entry is reside in the table."
        ::= { swFdbStaticEntry 5 }

    swFdbStaticStatus OBJECT-TYPE
        SYNTAX INTEGER {
               other(1),
               apply(2),
               not-apply(3)
        }
        ACCESS read-only
        STATUS mandatory
        DESCRIPTION
            "This object indicates the status of this entry.
            other(1) - this entry is currently in use but the conditions under
                which it will remain so are different from each of the following
                values.
            apply(2) - this entry is currently in use and reside in the table.
            not-apply(3) - this entry is reside in the table but currently not
                           in use due to conflict with filter table."
        ::= { swFdbStaticEntry 6 }

    swFdbStaticMemberTable OBJECT-TYPE
        SYNTAX SEQUENCE OF SwFdbStaticMemberEntry
        ACCESS not-accessible
        STATUS mandatory
        DESCRIPTION
            "A list of information provide a different view for those ports where packets from
              the given Vlan need to be forwarded to."
        ::= { swFDB 2 }

    swFdbStaticMemberEntry OBJECT-TYPE
        SYNTAX SwFdbStaticMemberEntry
        ACCESS not-accessible
        STATUS mandatory
        DESCRIPTION
            "A list of MIB capability entries supported by this forwarding static table."
        INDEX  { swFdbStaticMemberVid, swFdbStaticMemberAddress ,
                         swFdbStaticMemberUnitIndex,
                         swFdbStaticMemberModuleIndex,
                         swFdbStaticMemberPortIndex }
        ::= { swFdbStaticMemberTable 1 }

    SwFdbStaticMemberEntry ::=
        SEQUENCE {
            swFdbStaticMemberVid
                INTEGER,
            swFdbStaticMemberAddress
                MacAddress,
            swFdbStaticMemberUnitIndex
                INTEGER,
            swFdbStaticMemberModuleIndex
                INTEGER,
            swFdbStaticMemberPortIndex
                INTEGER
        }

    swFdbStaticMemberVid OBJECT-TYPE
        SYNTAX INTEGER
        ACCESS read-only
        STATUS mandatory
        DESCRIPTION
            "This object indicates the VLAN-ID. If the swVlanInfoStatus is
            port-base mode , the object ranges from 1 to 12. If VLAN is in
            mac-based mode or disabled, the object indicates the default
            VLAN-ID(0)."
        ::= { swFdbStaticMemberEntry 1 }

    swFdbStaticMemberAddress OBJECT-TYPE
        SYNTAX MacAddress
        ACCESS read-only
        STATUS mandatory
        DESCRIPTION
            "The MAC address which this forwarding entry applied. It can be an unicast address
             or a multicast address."
        ::= { swFdbStaticMemberEntry 2 }

    swFdbStaticMemberUnitIndex OBJECT-TYPE
        SYNTAX INTEGER
        ACCESS read-only
        STATUS mandatory
        DESCRIPTION
            "Specifies the unit ID where the port is located"
        ::= { swFdbStaticMemberEntry 3 }

    swFdbStaticMemberModuleIndex OBJECT-TYPE
        SYNTAX INTEGER
        ACCESS read-only
        STATUS mandatory
        DESCRIPTION
            "Specifies the module ID where the port is located"
        ::= { swFdbStaticMemberEntry 4 }

    swFdbStaticMemberPortIndex OBJECT-TYPE
        SYNTAX INTEGER
        ACCESS read-only
        STATUS mandatory
        DESCRIPTION
            "Specifies the port index relative to the module"
        ::= { swFdbStaticMemberEntry 5 }

    swFdbFilterTable OBJECT-TYPE
        SYNTAX SEQUENCE OF SwFdbFilterEntry
        ACCESS not-accessible
        STATUS mandatory
        DESCRIPTION
            "This table defines information for the device to filter packets with
             specific MAC address (either as the DA or as the SA). The MAC address
             can be a unicast address or a multicast address.This table has higher
             priority than both static FDB table and IGMP table. It means that if a
             MAC address appears on this table also appears on the static FDB table,
             the device will use the information provide by this table to process
             the packet."
        ::= { swFDB 3 }

    swFdbFilterEntry OBJECT-TYPE
        SYNTAX SwFdbFilterEntry
        ACCESS not-accessible
        STATUS mandatory
        DESCRIPTION
            "A list of information about a specific unicast/multicast MAC address
             for which the switch has filtering information."
        INDEX  { swFdbFilterVid, swFdbFilterAddress }
        ::= { swFdbFilterTable 1 }

    SwFdbFilterEntry ::=
        SEQUENCE {
            swFdbFilterVid
                INTEGER,
            swFdbFilterAddress
                MacAddress,
            swFdbFilterState
                INTEGER
        }

    swFdbFilterVid OBJECT-TYPE
        SYNTAX INTEGER
        ACCESS read-only
        STATUS mandatory
        DESCRIPTION
            "This object indicates the VLAN-ID. If the swVlanInfoStatus is
            port-base mode , the object ranges from 1 to 12. If VLAN is in
            mac-based mode or disabled, the object indicates the default
            VLAN-ID(0)."
        ::= { swFdbFilterEntry 1 }

    swFdbFilterAddress OBJECT-TYPE
        SYNTAX MacAddress
        ACCESS read-only
        STATUS mandatory
        DESCRIPTION
            "This object indicates a unicast/multicast MAC address for which the bridge
            has filtering information."
        ::= { swFdbFilterEntry 2 }

    swFdbFilterState OBJECT-TYPE
        SYNTAX INTEGER {
               other(1),
               invalid(2),
               valid(3),
               dst-src-addr(4)
        }
        ACCESS read-write
        STATUS mandatory
        DESCRIPTION
            "This object indicates the status of this entry.
            other(1) - this entry is currently in use but the conditions under
                which it will remain so are different from each of the following
                values.
            invalid(2) - writing this value to the object, and then the corresponding
                entry will be removed from the table.
            valid(3) - writing this value to the object, and then the corresponding
                entry will be added into the table.
            dst-src-addr(4) - recieved frames's destination address or source
                address are currently used to be filtered as it meets with
                the MAC address entry of the table."
        ::= { swFdbFilterEntry 3 }


-- sl2port.mib

	swL2PortMgmt    OBJECT IDENTIFIER ::= { swL2Mgmt 4 }

    -- *******************************************************
    -- *******************************************************
    swL2PortInfoTable OBJECT-TYPE
        SYNTAX  SEQUENCE OF SwL2PortInfoEntry
        ACCESS  not-accessible
        STATUS  mandatory
        DESCRIPTION
            "A table that contains information about every port."
        ::= { swL2PortMgmt 1 }

    swL2PortInfoEntry OBJECT-TYPE
        SYNTAX  SwL2PortInfoEntry
        ACCESS not-accessible
        STATUS  mandatory
        DESCRIPTION
            "A list of information for each port of the device."
        INDEX    { swL2PortInfoUnitIndex, swL2PortInfoModuleIndex, swL2PortInfoIndex }
        ::= { swL2PortInfoTable 1 }

    SwL2PortInfoEntry ::=
        SEQUENCE {
            swL2PortInfoUnitIndex
                INTEGER,
            swL2PortInfoModuleIndex
                INTEGER,
            swL2PortInfoIndex
                INTEGER,
            swL2PortInfoType
                INTEGER,
            swL2PortInfoDescr
                DisplayString (SIZE(0..64)),
            swL2PortInfoLinkStatus
                INTEGER,
            swL2PortInfoNwayStatus
                INTEGER
        }

    swL2PortInfoUnitIndex OBJECT-TYPE
        SYNTAX INTEGER
        ACCESS read-only
        STATUS mandatory
        DESCRIPTION
            "Indicates ID of the unit in the device"
        ::= { swL2PortInfoEntry 1 }

    swL2PortInfoModuleIndex OBJECT-TYPE
        SYNTAX INTEGER
        ACCESS read-only
        STATUS mandatory
        DESCRIPTION
            "Indicates ID of the module on the unit"
        ::= { swL2PortInfoEntry 2 }

    swL2PortInfoIndex OBJECT-TYPE
        SYNTAX INTEGER
        ACCESS read-only
        STATUS mandatory
        DESCRIPTION
            "Indicates ID of the port on the module"
        ::= { swL2PortInfoEntry 3 }

    swL2PortInfoType OBJECT-TYPE
        SYNTAX INTEGER {
            portType-100TX(1),
            portType-100FXSC(2),
            portType-100FXMTRJ(3),
            portType-GIGASX(4),
            portType-GIGALX(5),
            portType-GIGATX(6),
            other(7)
        }
        ACCESS read-only
        STATUS mandatory
        DESCRIPTION
            "Indicates the connector type of this port."
        ::= { swL2PortInfoEntry 4 }

    swL2PortInfoDescr OBJECT-TYPE
        SYNTAX DisplayString (SIZE(0..64))
        ACCESS read-only
        STATUS mandatory
        DESCRIPTION
            "Provides port type information in displayed string format"
        ::= { swL2PortInfoEntry 5 }

    swL2PortInfoLinkStatus OBJECT-TYPE
        SYNTAX INTEGER {
            other(1),
            link-pass(2),
            link-fail(3)
        }
        ACCESS read-only
        STATUS mandatory
        DESCRIPTION
            "Indicates port link status "
        ::= { swL2PortInfoEntry 6 }

    swL2PortInfoNwayStatus OBJECT-TYPE
        SYNTAX INTEGER {
            other(1),
            half-10Mbps(2),
            full-10Mbps(3),
            half-100Mbps(4),
            full-100Mbps(5),
            half-1Gigabps(6),	--added by Claire, 2000/9/6 05:19PM
            full-1Gigabps(7)
        }
        ACCESS read-only
        STATUS mandatory
        DESCRIPTION
            "This object indicates the port speed and duplex mode."
        ::= { swL2PortInfoEntry 7 }

    -- *******************************************************


    swL2PortCtrlTable OBJECT-TYPE
        SYNTAX SEQUENCE OF SwL2PortCtrlEntry
        ACCESS not-accessible
        STATUS mandatory
        DESCRIPTION
            "A table that contains control information about every port."
        ::= { swL2PortMgmt 2 }

    swL2PortCtrlEntry OBJECT-TYPE
        SYNTAX SwL2PortCtrlEntry
        ACCESS not-accessible
        STATUS mandatory
        DESCRIPTION
            "A list of control information for each port of the device."
        INDEX   { swL2PortCtrlUnitIndex, swL2PortCtrlModuleIndex, swL2PortCtrlIndex }
        ::= { swL2PortCtrlTable 1 }

    SwL2PortCtrlEntry ::=
        SEQUENCE {
            swL2PortCtrlUnitIndex
                INTEGER,
            swL2PortCtrlModuleIndex
                INTEGER,
           swL2PortCtrlIndex
                INTEGER,
            swL2PortCtrlAdminState
                INTEGER,
            swL2PortCtrlLinkStatusAlarmState
                INTEGER,
            swL2PortCtrlNwayState
                INTEGER,
            swL2PortCtrlFlowCtrlState
                INTEGER,
            swL2PortCtrlBackPressState
                INTEGER,
            swL2PortCtrlLockState
                INTEGER,
            swL2PortCtrlPriority
                INTEGER,
            swL2PortCtrlStpState
                INTEGER,
            swL2PortCtrlHOLState
                INTEGER,
            swL2PortCtrlBcastRisingAct
                INTEGER,
            swL2PortCtrlBcastFallingAct
                INTEGER
        }

    swL2PortCtrlUnitIndex OBJECT-TYPE
        SYNTAX INTEGER
        ACCESS read-only
        STATUS mandatory
        DESCRIPTION
            "Indicates ID of the unit in the device"
        ::= { swL2PortCtrlEntry 1 }

    swL2PortCtrlModuleIndex OBJECT-TYPE
        SYNTAX INTEGER
        ACCESS read-only
        STATUS mandatory
        DESCRIPTION
            "Indicates ID of the module on the unit"
        ::= { swL2PortCtrlEntry 2 }

    swL2PortCtrlIndex OBJECT-TYPE
        SYNTAX INTEGER
        ACCESS read-only
        STATUS mandatory
        DESCRIPTION
            "This object indicates the device port number.(1..Max port number)"
        ::= { swL2PortCtrlEntry 3 }

    swL2PortCtrlAdminState OBJECT-TYPE
        SYNTAX INTEGER {
            other(1),
            disabled(2),
            enabled(3),
            notAvailable (4)
        }
        ACCESS read-write
        STATUS mandatory
        DESCRIPTION
            "This object decides the port to be enabled or disabled."
        ::= { swL2PortCtrlEntry 4 }

    swL2PortCtrlLinkStatusAlarmState OBJECT-TYPE
        SYNTAX INTEGER {
            other(1),
            disabled(2),
            enabled(3),
            notAvailable (4)
       }
        ACCESS read-write
        STATUS mandatory
        DESCRIPTION
            "Depends on this object to determine to send a trap or
             not when link status changes ."
        ::= { swL2PortCtrlEntry 5 }

    swL2PortCtrlNwayState OBJECT-TYPE
        SYNTAX INTEGER {
            other(1),
            nway-enabled(2),
            nway-disabled-10Mbps-Half(3),
            nway-disabled-10Mbps-Full(4),
            nway-disabled-100Mbps-Half(5),
            nway-disabled-100Mbps-Full(6),
            nway-disabled-1Gigabps-Half(7),
            nway-disabled-1Gigabps-Full(8),
            notAvailable (10)
        }
        ACCESS read-write
        STATUS mandatory
        DESCRIPTION
            "Chooses the port speed, duplex mode, and N-Way function mode."
        ::= { swL2PortCtrlEntry 6 }

    swL2PortCtrlFlowCtrlState OBJECT-TYPE
        SYNTAX INTEGER {
            other(1),
            disabled(2),
            enabled(3)
--               auto-negotiation(4),
--               notAvailable (5)
        }
        ACCESS read-write
        STATUS mandatory
        DESCRIPTION
            "Sets IEEE 802.3x compliant flow control function as enabled or disabled.
             And IEEE 802.3x compliant flow control function work only when the port
             is in full duplex mode.The setting is effective the next time you reset
             or power on the hub."
        ::= { swL2PortCtrlEntry 7 }

    swL2PortCtrlBackPressState OBJECT-TYPE
        SYNTAX INTEGER {
            other(1),
            disabled(2),
            enabled(3)
--               auto-negotiation(4),
--               notAvailable (5)
        }
        ACCESS read-write
        STATUS mandatory
        DESCRIPTION
            "Depends on this object to determine to enable or disable the
             backpressure function when the port is working in half duplex mode."
        ::= { swL2PortCtrlEntry 8 }

    swL2PortCtrlLockState OBJECT-TYPE
        SYNTAX INTEGER {
            other(1),
            disable(2),
            enable(3),
            notAvailable (4)
       }
        ACCESS read-write
        STATUS mandatory
        DESCRIPTION
            "The state of this entry.  The meanings of the values are:
            other(1)   - this entry is currently in use but the conditions under
                         which it will remain so are different from each of the
                         following values.
            disable(2) - Port lock funtion disable.
            enable(3) -  Locking a port provides the CPU with the ability to
                         decide which address are permitted to reside on such
                         port, who knows about these address, and unknown packet
                         forwarding to/from such ports. This is a way to prevent
                         undesired traffic from being received or transmmited on
                         the port."
        ::= { swL2PortCtrlEntry 9 }

    swL2PortCtrlPriority OBJECT-TYPE
        SYNTAX INTEGER {
            other(1),
            default(2),
            force-low-priority(3),
            force-high-priority(4),
            notAvailable (5)
        }
        ACCESS read-write
        STATUS mandatory
        DESCRIPTION
            "The priority queueing for packets received on this port, except for
            BPDU/IGMP packets and packets with unknown unicast destination address.
            IGMP and BPDU packets are always routed with high priority; packets with
            unknown unicast destination addresses are always routed with low priority.
            Other packets follow the rules below:
            other(1)   - this entry is currently in use but the conditions under
                         which it will remain so are different from each of the
                         following values.

            default(2) - A packet is normally classified as low priority
                         ,unless at least one of the following is true:
                         (a)The packet contained a TAG (per 802.1Q definition) with the
                              priority greater or equal to 4.
                         (b)The address-table entry for the destination address had Pd=HIGH.
            force-low_priority(3) - A packet is normally classified as low priority.
            force-high_priority(4) - A packet is normally classified as high priority."
        ::= { swL2PortCtrlEntry 10 }

    swL2PortCtrlStpState OBJECT-TYPE
        SYNTAX INTEGER {
            other(1),
            disabled(2),
            enabled(3),
            notAvailable (4)
        }
        ACCESS read-write
        STATUS mandatory
        DESCRIPTION
            "The state of STP(spanning tree algorithm) operation on this port. That's
            meaning the port whether add in the STP. The value enabled(3) indicates
            that STP is enabled on this port, as long as swDevCtrlStpState is also
            enabled for this device. When disabled(2) but swDevCtrlStpState is still
            enabled for the device, STP is disabled on this port : any BPDU packets
            received will be discarded and no BPDU packets will be propagated from
            the port."
        ::= { swL2PortCtrlEntry 11 }

    swL2PortCtrlHOLState OBJECT-TYPE
        SYNTAX INTEGER {
            other(1),
            disabled(2),
            enabled(3),
            notAvailable (4)
        }
        ACCESS read-write
        STATUS mandatory
        DESCRIPTION
            "The object provides a way to prevent HOL (Head Of Line) blocking
            between ports. HOL protection may prevent forwarding a packet to
            a blocking port.The idea relies on the assumption that it is better
            to discard packets destined to blocking ports, then to let them consume
            more and more buffers in the input-port's Rx-counters because eventually
            these input ports may become totally blocked. The meanings of the values
            are:
            other(1) - this entry is currently in use but the conditions under
                              which it will remain so are different from each of the following
                              values.
            disabled(2) - HOL function disable.
            enabled(3) - HOL function enable."
        ::= { swL2PortCtrlEntry 12 }

    swL2PortCtrlBcastRisingAct OBJECT-TYPE
        SYNTAX INTEGER {
            other(1),
            do-nothing(2),
            blocking(3),
            blocking-trap(4),
            notAvailable (5)
        }
        ACCESS read-write
        STATUS mandatory
        DESCRIPTION
            "This object indicates the system action when broadcast storm
             rising threshold is met.
            other(1) - this entry is currently in use but the conditions under
                which it will remain so are different from each of the following
                values.
            do-nothing(2) - no action.
            blocking(3) - the port can discard any coming broadcast frame.
            blocking-trap(4) - the port can discard any coming broadcast frame.
            And the device can send a broadcast rising trap."
        ::= { swL2PortCtrlEntry 13 }

    swL2PortCtrlBcastFallingAct OBJECT-TYPE
        SYNTAX INTEGER {
            other(1),
            do-nothing(2),
            forwarding(3),
            forwarding-trap(4),
            notAvailable (5)
        }
        ACCESS read-write
        STATUS mandatory
        DESCRIPTION
            "This object indicates the device action when broadcast storm
            falling threshold is met.
            other(1) - this entry is currently in use but the conditions under
                which it will remain so are different from each of the following
                values.
            do-nothing(2) - no action.
            forwarding(3) - the port has returned to normal operation mode.
            forwarding-trap(4) - the port has returned to normal operation mode. And
            the device can send a broadcast falling trap."
        ::= { swL2PortCtrlEntry 14 }


    -- *******************************************************

    swL2PortStTable OBJECT-TYPE
        SYNTAX SEQUENCE OF SwL2PortStEntry
        ACCESS not-accessible
        STATUS mandatory
        DESCRIPTION
            "A list of port statistic Counter entries."
        ::= { swL2PortMgmt 3 }

    swL2PortStEntry OBJECT-TYPE
        SYNTAX SwL2PortStEntry
        ACCESS not-accessible
        STATUS mandatory
        DESCRIPTION
            "This entry include all the port statistic Counter which support
            by the device, like Bytes received, Bytes Sent ..."
        INDEX   { swL2PortStUnitIndex, swL2PortStModuleIndex, swL2PortStIndex }
        ::= { swL2PortStTable 1 }

    SwL2PortStEntry ::=
        SEQUENCE {
            swL2PortStUnitIndex
                INTEGER,
            swL2PortStModuleIndex
                INTEGER,
            swL2PortStIndex
                INTEGER,
            swL2PortStByteRx
                Counter,
            swL2PortStByteTx
                Counter,
            swL2PortStFrameRx
                Counter,
            swL2PortStFrameTx
                Counter,
            swL2PortStTotalBytesRx
                Counter,
            swL2PortStTotalFramesRx
                Counter,
            swL2PortStBroadcastFramesRx
                Counter,
            swL2PortStMulticastFramesRx
                Counter,
            swL2PortStCRCError
                Counter,
            swL2PortStOversizeFrames
                Counter,
            swL2PortStFragments
                Counter,
            swL2PortStJabber
                Counter,
            swL2PortStCollision
                Counter,
            swL2PortStLateCollision
                Counter,
            swL2PortStFrames-64-bytes
                Counter,
            swL2PortStFrames-65-127-bytes
                Counter,
            swL2PortStFrames-128-255-bytes
                Counter,
            swL2PortStFrames-256-511-bytes
                Counter,
            swL2PortStFrames-512-1023-bytes
                Counter,
            swL2PortStFrames-1024-1536-bytes
                Counter,
            swL2PortStFramesDroppedFrames
                Counter,
            swL2PortStMulticastFramesTx
                Counter,
            swL2PortStBroadcastFramesTx
                Counter,
            swL2PortStUndersizeFrames
                Counter
        }

    swL2PortStUnitIndex OBJECT-TYPE
        SYNTAX INTEGER
        ACCESS read-only
        STATUS mandatory
        DESCRIPTION
            "indicates ID of the unit in the device"
        ::= { swL2PortStEntry 1 }

    swL2PortStModuleIndex OBJECT-TYPE
        SYNTAX INTEGER
        ACCESS read-only
        STATUS mandatory
        DESCRIPTION
            "indicates ID of the module on the unit"
        ::= { swL2PortStEntry 2 }

    swL2PortStIndex OBJECT-TYPE
        SYNTAX INTEGER
        ACCESS read-only
        STATUS mandatory
        DESCRIPTION
            "This object indicates the device port number.(1..Max port number)"
        ::= { swL2PortStEntry 3 }

    swL2PortStByteRx OBJECT-TYPE
        SYNTAX Counter
        ACCESS read-only
        STATUS mandatory
        DESCRIPTION
            "swDevCtrlCounterMode = 2(switched-frames):This counter is incre-
            mented once for every data octet of good packets(unicast + multi-
            cast + broadcast) received.

             swDevCtrlCounterMode = 3(all-frames):This counter is incremented
            once for every data octet of good packets(unicast + multicast +
            broadcast packets) and for local and dropped packets."
        ::= { swL2PortStEntry 4 }

    swL2PortStByteTx OBJECT-TYPE
        SYNTAX Counter
        ACCESS read-only
        STATUS mandatory
        DESCRIPTION
            "This counter is incremented once for every data octet of a trans-
            mitted good packet."
        ::= { swL2PortStEntry 5 }

    swL2PortStFrameRx OBJECT-TYPE
        SYNTAX Counter
        ACCESS read-only
        STATUS mandatory
        DESCRIPTION
            "swDevCtrlCounterMode = 2(switched-frames):This counter is incre-
            mented once for every good packet(unicast + multicast + broadcast
            ) received.

             swDevCtrlCounterMode = 3(all-frames):This counter is incremented
            once for every good packet(unicast + multicast + broadcast packets)
            and for local and dropped packets received."
        ::= { swL2PortStEntry 6 }

    swL2PortStFrameTx OBJECT-TYPE
        SYNTAX Counter
        ACCESS read-only
        STATUS mandatory
        DESCRIPTION
            "This counter is incremented once for every transmitted good packet."
        ::= { swL2PortStEntry 7 }

    swL2PortStTotalBytesRx OBJECT-TYPE
        SYNTAX Counter
        ACCESS read-only
        STATUS mandatory
        DESCRIPTION
            "This counter is incremented once for every data octet of all
            received packets. This include data octets of rejected and local
            packets which are not forwarded to the switching core for trans-
            mission. This counter should reflect all the data octets received
            on the line. Note: A nibble is not counted as a whole byte."
        ::= { swL2PortStEntry 8 }

    swL2PortStTotalFramesRx OBJECT-TYPE
        SYNTAX Counter
        ACCESS read-only
        STATUS mandatory
        DESCRIPTION
            "This counter is incremented once for every received packets. This
            include rejected and local packets which are not forwarded to the
            switching core for transmission. This counter should reflect all
            packets received on the line."
        ::= { swL2PortStEntry 9 }

    swL2PortStBroadcastFramesRx OBJECT-TYPE
        SYNTAX Counter
        ACCESS read-only
        STATUS mandatory
        DESCRIPTION
            "swDevCtrlCounterMode = 2(switched-frames):This counter is incre-
            mented once for every good broadcast packet received.

             swDevCtrlCounterMode = 3(all-frames):This counter is incremented
            once for every good broadcast packet received and for local and
            dropped broadcast packets."
        ::= { swL2PortStEntry 10 }


    swL2PortStMulticastFramesRx OBJECT-TYPE
        SYNTAX Counter
        ACCESS read-only
        STATUS mandatory
        DESCRIPTION
            "swDevCtrlCounterMode = 2(switched-frames):This counter is incre-
            mented once for every good multicast packet received.

             swDevCtrlCounterMode = 3(all-frames):This counter is incremented
            once for every good multicast packet received and for local and
            dropped multicast packets. This counter does not include broad-
            cast packets."
        ::= { swL2PortStEntry 11 }

    swL2PortStCRCError OBJECT-TYPE
        SYNTAX Counter
        ACCESS read-only
        STATUS mandatory
        DESCRIPTION
            "This counter is incremented once for every received packet which
            meets all the following conditions:
            1.Packet data length is between 64 and 1518 bytes inclusive.
            2.Packet has invalid CRC.
            3.Collision event , late collision event and receive error event
              have not been detected."
        ::= { swL2PortStEntry 12 }

    swL2PortStOversizeFrames OBJECT-TYPE
        SYNTAX Counter
        ACCESS read-only
        STATUS mandatory
        DESCRIPTION
            "The number of good frames with length more than 1518 bytes."
        ::= { swL2PortStEntry 13 }

    swL2PortStFragments OBJECT-TYPE
        SYNTAX Counter
        ACCESS read-only
        STATUS mandatory
        DESCRIPTION
            "This counter is incremented once for every received packet which
            meets all the following conditions:
            1.Packet data length is less than 64 bytes or packet withourt SFD
              and is less than 64 bytes in length.
            2.Packet has invalid CRC.
            3.Collision event , late collision event and receive error event
              have not been detected."
        ::= { swL2PortStEntry 14 }

    swL2PortStJabber OBJECT-TYPE
        SYNTAX Counter
        ACCESS read-only
        STATUS mandatory
        DESCRIPTION
            "The number of frames with length more than 1518 bytes and with
            CRC error or misaligned."
        ::= { swL2PortStEntry 15 }

    swL2PortStCollision OBJECT-TYPE
        SYNTAX Counter
        ACCESS read-only
        STATUS mandatory
        DESCRIPTION
            "The number of Collisions"
        ::= { swL2PortStEntry 16 }

    swL2PortStLateCollision OBJECT-TYPE
        SYNTAX Counter
        ACCESS read-only
        STATUS mandatory
        DESCRIPTION
            "The number of Late Collision(collision occurring later than
            576th transmitted bit)."
        ::= { swL2PortStEntry 17 }

    swL2PortStFrames-64-bytes OBJECT-TYPE
        SYNTAX Counter
        ACCESS read-only
        STATUS mandatory
        DESCRIPTION
            "This counter is incremented once for every received and trans-
            mitted packet with size of 64 bytes. This counter includes reject-
            ed received and transmitted packets."
        ::= { swL2PortStEntry 18 }

    swL2PortStFrames-65-127-bytes OBJECT-TYPE
        SYNTAX Counter
        ACCESS read-only
        STATUS mandatory
        DESCRIPTION
            "This counter is incremented once for every received and trans-
            mitted packet with size of 65 to 127 bytes. This counter includes
            rejected received and transmitted packets."
        ::= { swL2PortStEntry 19 }

    swL2PortStFrames-128-255-bytes OBJECT-TYPE
        SYNTAX Counter
        ACCESS read-only
        STATUS mandatory
        DESCRIPTION
            "This counter is incremented once for every received and trans-
            mitted packet with size of 128 to 255 bytes. This counter includes
            rejected received and transmitted packets."
        ::= { swL2PortStEntry 20 }

    swL2PortStFrames-256-511-bytes OBJECT-TYPE
        SYNTAX Counter
        ACCESS read-only
        STATUS mandatory
        DESCRIPTION
            "This counter is incremented once for every received and trans-
            mitted packet with size of 256 to 511 bytes. This counter includes
            rejected received and transmitted packets."
        ::= { swL2PortStEntry 21 }

    swL2PortStFrames-512-1023-bytes OBJECT-TYPE
        SYNTAX Counter
        ACCESS read-only
        STATUS mandatory
        DESCRIPTION
            "This counter is incremented once for every received and trans-
            mitted packet with size of 512 to 1023 bytes. This counter includ-
            es rejected received and transmitted packets."
        ::= { swL2PortStEntry 22 }

    swL2PortStFrames-1024-1536-bytes OBJECT-TYPE
        SYNTAX Counter
        ACCESS read-only
        STATUS mandatory
        DESCRIPTION
            "This counter is incremented once for every received and trans-
            mitted packet with size of 1024 to 1536 bytes. This counter includ-
            es rejected received and transmitted packets."
        ::= { swL2PortStEntry 23 }

    swL2PortStFramesDroppedFrames OBJECT-TYPE
        SYNTAX Counter
        ACCESS read-only
        STATUS mandatory
        DESCRIPTION
            "This counter is incremented once for every received dropped pack-
            et."
        ::= { swL2PortStEntry 24 }

    swL2PortStMulticastFramesTx OBJECT-TYPE
        SYNTAX Counter
        ACCESS read-only
        STATUS mandatory
        DESCRIPTION
            "The number of multicast frames sent. This counter does not include
            broadcast packets."
        ::= { swL2PortStEntry 25 }

    swL2PortStBroadcastFramesTx OBJECT-TYPE
        SYNTAX Counter
        ACCESS read-only
        STATUS mandatory
        DESCRIPTION
            "The number of broadcast frames sent."
        ::= { swL2PortStEntry 26 }

    swL2PortStUndersizeFrames OBJECT-TYPE
        SYNTAX Counter
        ACCESS read-only
        STATUS mandatory
        DESCRIPTION
            "This counter is incremented once for every received packet which
            meets all the following conditions:
            1.Packet data length is less than 64 bytes.
            2.Packet has valid CRC.
            3.Collision event , late collision event and receive error event
              have not been detected."
        ::= { swL2PortStEntry 27 }

-- =========================
-- Trap Group Definition
-- =========================
    swEventPortPartition TRAP-TYPE
              ENTERPRISE es1200
              VARIABLES {
	      	  	swL2PortInfoUnitIndex, swL2PortInfoModuleIndex, swL2PortInfoIndex
              }
              DESCRIPTION
                      "The trap is sent whenever the port state enter the
                      Partion mode when more than 61 collisions occur while
                      trasmitting."
		::= 1

    swEventlinkChangeEvent TRAP-TYPE
              ENTERPRISE es1200
              VARIABLES {
	      	  	swL2PortInfoUnitIndex, swL2PortInfoModuleIndex, swL2PortInfoIndex
              }
              DESCRIPTION
                      "The trap is sent whenever the link state of a port changes
                      from link up to link down or from link down to link up"
                ::= 2

    swEventBcastRisingStorm TRAP-TYPE
              ENTERPRISE es1200
              VARIABLES {
	      	  	swL2PortInfoUnitIndex, swL2PortInfoModuleIndex, swL2PortInfoIndex
              }
              DESCRIPTION
                      "The trap indicates that broadcast higher rising threshold
                      . This trap including the port ID"
                ::= 3

    swEventBcastFallingStorm TRAP-TYPE
              ENTERPRISE es1200
              VARIABLES {
	      	  	swL2PortInfoUnitIndex, swL2PortInfoModuleIndex, swL2PortInfoIndex
              }
              DESCRIPTION
                      "The trap indicates that broadcast higher falling threshold
                      . This trap including the port ID"
                ::= 4

-- sigmp.mib
	swIGMP    OBJECT IDENTIFIER ::= { swL2Mgmt 7 }


-- ****************************************************************************
-- swIGMPCtrl
-- ****************************************************************************
   swIGMPCtrl    OBJECT IDENTIFIER ::= { swIGMP 1 }

   swIGMPAdminState OBJECT-TYPE
        SYNTAX INTEGER {
            other(1),
            disabled(2),
            enabled(3)
        }
        ACCESS read-write
        STATUS mandatory
        DESCRIPTION
            "This object allows the user to enable/disable the IGMP snooping function.
              The IGMP function provided by the device includes both v1 and v2."
        ::= { swIGMPCtrl 1 }

    swIGMPTimeout OBJECT-TYPE
        SYNTAX INTEGER
        ACCESS read-write
        STATUS mandatory
        DESCRIPTION
            "The timeout value for sending IGMP query packet when no one
             was sent by the multicast router in the lan. The device will
             actively send the query message. "
        DEFVAL    { 300 }
        ::= { swIGMPCtrl 2 }

-- **************************************************************************
--  swIGMPInfoTable                  OBJECT IDENTIFIER ::= {  swIGMP 2 }
-- **************************************************************************

    swIGMPInfoTable OBJECT-TYPE
        SYNTAX SEQUENCE OF SwIGMPInfoEntry
        ACCESS not-accessible
        STATUS mandatory
        DESCRIPTION
            "The table contains the number current IGMP query packets which
             is captured by this device, as well as the IGMP query packets
             sent by the device."
        ::= { swIGMP 2 }

    swIGMPInfoEntry OBJECT-TYPE
        SYNTAX SwIGMPInfoEntry
        ACCESS not-accessible
        STATUS mandatory
        DESCRIPTION
            "Information about current IGMP query information, provided that
             swDevIGMPCaptureState and swIGMPCtrlState of associated VLAN
             entry are all enabled."
        INDEX  { swIGMPInfoIndex }
        ::= { swIGMPInfoTable 1 }

    SwIGMPInfoEntry ::=
        SEQUENCE {
            swIGMPInfoIndex
                INTEGER,
            swIGMPInfoVid
                INTEGER,
            swIGMPInfoQueryCount
                INTEGER,
            swIGMPInfoTxQueryCount
                INTEGER
        }

    swIGMPInfoIndex OBJECT-TYPE
        SYNTAX INTEGER (1..12)
        ACCESS read-only
        STATUS mandatory
        DESCRIPTION
            "This object indicates the IGMP query information entry number. It could
             be up to 12 entries, depending on current number of VLAN entries."
        ::= { swIGMPInfoEntry 1 }

    swIGMPInfoVid OBJECT-TYPE
        SYNTAX INTEGER
        ACCESS read-only
        STATUS mandatory
        DESCRIPTION
            "This object indicates the Vid of associated IGMP info table entry. It
             follows swIGMPCtrlVid in the associated entry of IGMP control table
             (swIGMPCtrlTable)."
        ::= { swIGMPInfoEntry 2 }

    swIGMPInfoQueryCount OBJECT-TYPE
        SYNTAX INTEGER
        ACCESS read-only
        STATUS mandatory
        DESCRIPTION
            "This object indicates the number of query packets received since the
             IGMP function enabled, in per-VLAN basis."
        ::= { swIGMPInfoEntry 3 }

    swIGMPInfoTxQueryCount OBJECT-TYPE
        SYNTAX INTEGER
        ACCESS read-only
        STATUS mandatory
        DESCRIPTION
            "This object indicates the send count of IGMP query messages, in
             per-VLAN basis. In case of IGMP timer expiration, the switch
             sends IGMP query packets to related VLAN member ports and increment
             this object by 1."
        ::= { swIGMPInfoEntry 4 }

-- **************************************************************************
--  swIGMPTable                  OBJECT IDENTIFIER ::= {  swIGMP 3 }
-- **************************************************************************

    swIGMPTable OBJECT-TYPE
        SYNTAX SEQUENCE OF SwIGMPEntry
        ACCESS not-accessible
        STATUS mandatory
        DESCRIPTION
            "This table contains information regarding to the IGMP group membership report
             received by each port. The system will use the information recorded in this
             table to forward the multicast packet to those ports which have group membership.
             Since packets will not be forwarded to necessary ports, the network bandwith can
             thus be saved."
        ::= { swIGMP 3 }

    swIGMPEntry OBJECT-TYPE
        SYNTAX SwIGMPEntry
        ACCESS not-accessible
        STATUS mandatory
        DESCRIPTION
            "Each entry describes the ports which are member of a specific group address.
              Note that when a specific multicast address existing in the table also exist in
              the filter table, the filter table has higher priority over this table."
        INDEX  { swIGMPVid, swIGMPGroupIpAddr }
        ::= { swIGMPTable 1 }

    SwIGMPEntry ::=
        SEQUENCE {
            swIGMPVid
                INTEGER,
            swIGMPGroupIpAddr
                IpAddress,
            swIGMPGroupMacAddr
                MacAddress,
            swIGMPPortMap
                PortList,
            swIGMPIpGroupReportCount
                INTEGER
        }

    swIGMPVid OBJECT-TYPE
        SYNTAX INTEGER
        ACCESS read-only
        STATUS mandatory
        DESCRIPTION
            "This object indicates the Vid of individual IGMP table entry. It
             shows the Vid of IGMP report information captured on network."
        ::= { swIGMPEntry 1 }

    swIGMPGroupIpAddr OBJECT-TYPE
        SYNTAX IpAddress
        ACCESS read-only
        STATUS mandatory
        DESCRIPTION
            "A IP multicast group address which has port membership in the underlying network."
        ::= { swIGMPEntry 2 }

    swIGMPGroupMacAddr OBJECT-TYPE
        SYNTAX MacAddress
        ACCESS read-only
        STATUS mandatory
        DESCRIPTION
            "The multicast MAC address corresponds to swIGMPGroupIpAddr."
        ::= { swIGMPEntry 3 }

    swIGMPPortMap OBJECT-TYPE
        SYNTAX PortList
        ACCESS read-only
        STATUS mandatory
        DESCRIPTION
            "Indicates the set of ports which are members of this multicast group.
             These ports are represented by a octet string.The most significant bit
             represents the lowest numbered port, and the least significant bit
             represents the highest numbered port."
        ::= { swIGMPEntry 4 }

    swIGMPIpGroupReportCount OBJECT-TYPE
        SYNTAX INTEGER
        ACCESS read-only
        STATUS mandatory
        DESCRIPTION
            "Indicates the number of group membership report packets received by the device
             corresponding to this multicast group."
        ::= { swIGMPEntry 5 }

-- +updated by Jemy 2000/2/10 02:37PM B14
-- *****************************************************************************
--  swIGMPCtrlTable
-- *****************************************************************************
    swIGMPCtrlTable OBJECT-TYPE
        SYNTAX  SEQUENCE OF SwIGMPCtrlEntry
        ACCESS  not-accessible
        STATUS  mandatory
        DESCRIPTION
            "The table controls the Vlan's IGMP function. Its scale depends on
             current VLAN state (swVlanInfoStatus). If VLAN is disabled or
             in Mac-Base mode, there is only one entry in the table, with
             index 1. If VLAN is in Port-Base or 802.1q mode, the number of
             entries can be up to 12, with index range from 1 to 12."
        ::= { swIGMP 4 }

    swIGMPCtrlEntry OBJECT-TYPE
        SYNTAX  SwIGMPCtrlEntry
        ACCESS  not-accessible
        STATUS  mandatory
        DESCRIPTION
            "The entry in IGMP control table (swIGMPCtrlTable).
             The entry is effective only when IGMP capture switch is enabled."
        INDEX   { swIGMPCtrlIndex }
        ::= { swIGMPCtrlTable 1 }

    SwIGMPCtrlEntry ::=
        SEQUENCE {
            swIGMPCtrlIndex
                INTEGER,
            swIGMPCtrlVid
                INTEGER (1..4094),
            swIGMPCtrlTimer
                INTEGER,
            swIGMPCtrlState
                INTEGER
        }

    swIGMPCtrlIndex OBJECT-TYPE
        SYNTAX  INTEGER (1..12)
        ACCESS  read-only
        STATUS  mandatory
        DESCRIPTION
            "This object indicates the IGMP control entry number.Its scale depends on
             current VLAN state (es400VlanInfoStatus). If VLAN is disabled or in
             Mac-Base mode, there is only one entry in the table, with index 1.
             If VLAN is in Port-Base or 802.1q mode, the number of entries is 12,
             with index range from 1 to 12."
        ::= { swIGMPCtrlEntry 1 }

    swIGMPCtrlVid OBJECT-TYPE
        SYNTAX  INTEGER (1..4094)
        ACCESS  read-write
        STATUS  mandatory
        DESCRIPTION
            "This object indicates the IGMP control entry's VLAN id. If VLAN is
             disabled or in Mac-Base mode, the Vid is always 0 and cannot be changed
             by management users. If VLAN is in Port-Base mode, the Vid is arranged
             from 1 to 12 , fixed form. If VLAN is in 802.1q mode, the Vid setting
             can vary from 1 to 4094 by management user, and the Vid in each entry
             must be unique in the IGMP Control Table."
        ::= { swIGMPCtrlEntry 2 }

    swIGMPCtrlTimer OBJECT-TYPE
        SYNTAX  INTEGER  (30..9999)
        ACCESS  read-write
        STATUS  mandatory
        DESCRIPTION
            "The timer value for sending IGMP query packet when none
             was sent by the multicast router in the LAN. The timer works
             in per-VLAN basis. Our device will be activated to send the query
             message if the timer is expired. Please reference RFC2236-1997.
             And it recommends a default of 125 seconds. The timeout value must
             be at least 30 seconds."
        DEFVAL  { 300 }
        ::= { swIGMPCtrlEntry 3 }

    swIGMPCtrlState OBJECT-TYPE
        SYNTAX  INTEGER {
            other(1),
            disabled(2),
            enabled(3),
            deleted(4)
        }
        ACCESS  read-write
        STATUS  mandatory
        DESCRIPTION
            "This object indicates the status of this entry.
             other(1) - This entry is currently in use but the conditions under
                        which it will remain so are different from each of the
                        following values.
             disable(2) - IGMP funtion is disabled for this entry.
             enable(3) - IGMP funtion is enabled for this entry.
             deleted(4) - IGMP entry is deleted."
        ::= { swIGMPCtrlEntry 4 }
-- -

--sl2dev.mib
	swL2DevMgmt    OBJECT IDENTIFIER ::= { swL2Mgmt 1 }
	swL2DevCtrl    OBJECT IDENTIFIER ::= { swL2DevMgmt 1 }


-- ****************************************************************************
-- ****************************************************************************
    swL2DevCtrlStpState OBJECT-TYPE
        SYNTAX INTEGER {
            other(1),
            disabled(2),
            enabled(3),
            notAvailable(4)
        }
        ACCESS read-write
        STATUS mandatory
        DESCRIPTION
            "This object can be enabled or disabled spanning tree algorithm
             during runtime of the system."
        ::= { swL2DevCtrl 1 }

    swL2DevCtrlPartitionModeState OBJECT-TYPE
        SYNTAX INTEGER {
            other(1),
            disabled(2),
            enabled(3),
            notAvailable(4)
        }
        ACCESS read-write
        STATUS mandatory
        DESCRIPTION
            "This object used to enable or disable port auto partition. When the
             object apply for all ports of the device"
        ::= { swL2DevCtrl 2 }


    swL2DevCtrlTableLockState OBJECT-TYPE
       SYNTAX  INTEGER {
            other(1),
            disabled(2),
            enabled(3),
            notAvailable(4)
       }
       ACCESS  read-write
       STATUS  mandatory
       DESCRIPTION
           "This object indicates whether the address table is locked.
            In other words, the address table doesn't learn any more new address.
            The aging timer is suspended when the address table is locked. As long
            as the table is locked, all of the frames are dropped if the destination
            can not be found in the address."
       ::= { swL2DevCtrl 3 }

    swL2DevCtrlHOLState OBJECT-TYPE
        SYNTAX INTEGER {
            other(1),
            disabled(2),
            enabled(3),
            notAvailable(4)
        }
        ACCESS read-write
        STATUS mandatory
        DESCRIPTION
            "The object provides a way to prevent HOL (Head Of Line) blocking
             between ports. HOL protection may prevent forwarding a packet to
             a blocking port.The idea relies on the assumption that it is better
             to discard packets destined to blocking ports, then to let them consume
             more and more buffers in the input-port's Rx-counters because eventually
             these input ports may become totally blocked. The meanings of the values
             are:

             other(1) - this entry is currently in use but the conditions under
                               which it will remain so are different from each of the following
                               values.
            disabled(2) - HOL function disable for device.
            enabled(3) - HOL function enable for device."
        ::= { swL2DevCtrl 4 }

-- + added by Jemy 10/12/99
    swL2DevCtrlAddrLookupModesAndHitRate OBJECT-TYPE
        SYNTAX INTEGER {
            level0(1),
            level1(2),
            level2(3),
            level3(4),
            level4(5),
            level5(6),
            level6(7),
            level7(8)
        }
        ACCESS read-write
        STATUS mandatory
        DESCRIPTION
            "According to the differnet address looke mode setting, to enlarge the
             address table size is possible in device. But there is side effect as
             the higher level you have, the lower thorughput device has. That means
             Level 0 get the smallest table size, but get better performace. We
             recommand the user use the Level 1 as defualt setting."
        ::= { swL2DevCtrl 5 }

      swL2DevCtrlUploadImageFileName OBJECT-TYPE
         SYNTAX  DisplayString  (SIZE (0..64))
          ACCESS  read-write
          STATUS  mandatory
          DESCRIPTION
              "The name of the image file to be uploaded from the device to TFTP server
               when enabling image upload function (by writing swDevCtrlUploadImage)."
          ::= { swL2DevCtrl 6 }

      swL2DevCtrlUploadImage OBJECT-TYPE
          SYNTAX  INTEGER
          ACCESS  write-only
          STATUS  mandatory
          DESCRIPTION
              "Image file upload control. Writing it by any value will
               immediately invoke image upload function."
          ::= { swL2DevCtrl 7 }
    
      swL2DevCtrlClearAddressTable OBJECT-TYPE
        SYNTAX  INTEGER {
                    other(1),
                    clear(2)
                }
        ACCESS  read-write
        STATUS  mandatory
        DESCRIPTION
            "This object indicates the agent clear address table.
             Setting this object to clear(2) will clear address
             table. The agent alwats return other(1) when this
             object is read."
        ::= { swL2DevCtrl 8 }

-- marked by Richard ,for not suppport in phase two,2000/6/15 01:08PM
--     swL2DevCtrlJumboframeRestartState OBJECT-TYPE
--         SYNTAX INTEGER {
--                other(1),
--                disabled(2),
--                enabled(3)
--                }
--         ACCESS read-write
--         STATUS mandatory
--         DESCRIPTION
--             "This object used to indicate the state of gigabit to gigabit jumbo
--             frame support while the device restart.The meanings of the values are :
--
--             other(1) - this entry is currently in use but the conditions under
--                 which it will remain so are different from each of the following
--                 values.
--             disabled(2) - Jumbo frame support disable for device.
--             enabled(3) - Jumbo frame support enable for device."
--         ::= { swL2DevCtrl 6 }

   -- ***************************************************
    swL2DevAlarm              OBJECT IDENTIFIER ::= { swL2DevMgmt 2 }

    swL2DevAlarmPartition OBJECT-TYPE
        SYNTAX INTEGER {
            other(1),
            disabled(2),
            enabled(3),
            notAvailable(4)
        }
        ACCESS read-write
        STATUS mandatory
        DESCRIPTION
            "Depending on this object, the device send a trap or not when
             any one of the device's ports was partitioned."
       ::= { swL2DevAlarm 1 }

    swL2DevAlarmNewRoot OBJECT-TYPE
        SYNTAX INTEGER {
            other(1),
            disabled(2),
            enabled(3),
            notAvailable(4)
        }
        ACCESS read-write
        STATUS mandatory
        DESCRIPTION
            "When the device has become the new root of the Spanning Tree, this
              object decide whether to send a new root trap."
        ::= { swL2DevAlarm 2 }

    swL2DevAlarmTopChange OBJECT-TYPE
        SYNTAX INTEGER {
            other(1),
            disabled(2),
            enabled(3),
            notAvailable(4)
        }
        ACCESS read-write
        STATUS mandatory
        DESCRIPTION
            "This object determines to send a trap or not when the switch topology
             was changed. If the object is enabled(3), the topologyChange trap is
             sent by the device when any of its configured ports transitions from
             the Learning state to the Forwarding state, or from the Forwarding state
             to the Blocking state. For the same port tranition, the device doesn't
             send the trap if this object value is disabled or other."
        ::= { swL2DevAlarm 3 }

    swL2DevAlarmLinkChange OBJECT-TYPE
        SYNTAX INTEGER {
            other(1),
            disabled(2),
            enabled(3),
            notAvailable(4)
        }
        ACCESS read-write
        STATUS mandatory
        DESCRIPTION
            "This object determines to send a trap or not when the link
              was changed. If the object is enabled(3), the Link Change trap is
              sent by the device when any of its ports link change. The device doesn't
              send the trap if this object value is disabled or other."
        ::= { swL2DevAlarm 4 }

-- ***************************************************
-- marked by Richard ,for not suppport in phase two,2000/6/15 01:08PM
-- ++
--     swL2DevInfo              OBJECT IDENTIFIER ::= { swL2DevMgmt 3 }
--
--     swL2DevInfoJumboframeStatus OBJECT-TYPE
--         SYNTAX INTEGER {
--                other(1),
--                disabled(2),
--                enabled(3)
--                }
--         ACCESS read-only
--         STATUS mandatory
--         DESCRIPTION
--             "The current status  of  gigabit to gigabit jumbo frame support.
--              The meanings of the values are :
--
--             other(1) - this entry is currently in use but the conditions under
--                 which it will remain so are different from each of the following
--                 values.
--             disabled(2) - Jumbo frame support disable for device.
--             enabled(3) - Jumbo frame support enable for device."
--         ::= { swL2DevInfo 1 }
-- --


-- spbrd.mib
	swVlan    OBJECT IDENTIFIER ::= { swL2Mgmt 8 }
	pBridgeMIBObjects   OBJECT IDENTIFIER ::= { swVlan 4 }

-- *****************************************************************************
-- Textual Conventions
-- *****************************************************************************
-- Declarations for SNMPv1
    EnabledStatus   ::= INTEGER { enabled(1), disabled(2) }
    TruthValue      ::= INTEGER { true(1), false(2) }
    TimeInterval    ::= INTEGER

-- *****************************************************************************
-- groups in the P-BRIDGE MIB
-- *****************************************************************************
    dot1dExtBase    OBJECT IDENTIFIER ::= { pBridgeMIBObjects 1 }
    dot1dPriority   OBJECT IDENTIFIER ::= { pBridgeMIBObjects 2 }
    dot1dGarp       OBJECT IDENTIFIER ::= { pBridgeMIBObjects 3 }
    dot1dGmrp       OBJECT IDENTIFIER ::= { pBridgeMIBObjects 4 }

-- *****************************************************************************
-- the dot1dExtBase group
-- *****************************************************************************
    dot1dDeviceCapabilities OBJECT-TYPE
        SYNTAX  INTEGER
        ACCESS  read-only
        STATUS  mandatory
        DESCRIPTION
            "Indicates the optional parts of IEEE 802.1D and 802.1Q that are
             implemented by this device and are managable through this MIB.
             Capabilities that are allowed on a per-port basis are indicated
             in dot1dPortCapabilities."
        REFERENCE
            "ISO/IEC 15802-3 Section 5.2,
             IEEE 802.1Q/D11 Section 5.2, 12.10.1.1.3/b/2"
        ::= { dot1dExtBase 1 }

    dot1dTrafficClassesEnabled OBJECT-TYPE
        SYNTAX  TruthValue
        ACCESS  read-only
        STATUS  mandatory
        DESCRIPTION
            "The value true(1) indicates that Traffic Classes are enabled on
             this bridge. When false(2), the bridge operates with a single
             priority level for all traffic."
        DEFVAL  { true }
        ::= { dot1dExtBase 2 }

    dot1dGmrpStatus OBJECT-TYPE
        SYNTAX  EnabledStatus
        ACCESS  read-write
        STATUS  mandatory
        DESCRIPTION
            "The administrative status requested by management for GMRP.
             The value enabled(1) indicates that GMRP should be enabled on
             this device, in all VLANs, on all ports for which it has not been
             specifically disabled. When disabled(2), GMRP is disabled, in all
             VLANs, on all ports and all GMRP packets will be forwarded
             transparently. This object affects both Applicant and Registrar
             state machines. A transition from disabled(2) to enabled(1) will
             cause a reset of all GMRP state machines on all ports."
-- +updated by Jemy 2000/2/10 08:38PM B14
        DEFVAL  { disabled }
-- -
        ::= { dot1dExtBase 3 }

    dot1dPortCapabilitiesTable OBJECT-TYPE
        SYNTAX  SEQUENCE OF Dot1dPortCapabilitiesEntry
        ACCESS  not-accessible
        STATUS  mandatory
        DESCRIPTION
            "A table that contains capabilities information about every port
             that is associated with this bridge."
        ::= { dot1dExtBase 4 }

    dot1dPortCapabilitiesEntry OBJECT-TYPE
        SYNTAX  Dot1dPortCapabilitiesEntry
        ACCESS  not-accessible
        STATUS  mandatory
        DESCRIPTION
            "A set of capabilities information about this port indexed
             by dot1dBasePort."
        INDEX   {dot1dBasePort}
        ::= { dot1dPortCapabilitiesTable 1 }

    Dot1dPortCapabilitiesEntry ::=
        SEQUENCE {
            dot1dPortCapabilities
                INTEGER
        }

    dot1dPortCapabilities OBJECT-TYPE
        SYNTAX  INTEGER
        ACCESS  read-only
        STATUS  mandatory
        DESCRIPTION
            "Indicates the parts of IEEE 802.1D and 802.1Q that are optional
             on a per-port basis that are implemented by this device and are
             managable through this MIB."
        REFERENCE
            "ISO/IEC 15802-3 Section 5.2,
             IEEE 802.1Q/D11 Section 5.2"
        ::= { dot1dPortCapabilitiesEntry 1 }

-- *****************************************************************************
-- the dot1dPriority group
-- *****************************************************************************
    dot1dPortPriorityTable OBJECT-TYPE
        SYNTAX  SEQUENCE OF Dot1dPortPriorityEntry
        ACCESS  not-accessible
        STATUS  mandatory
        DESCRIPTION
            "A table that contains information about every port that is
             associated with this transparent bridge."
        ::= { dot1dPriority 1 }

    dot1dPortPriorityEntry OBJECT-TYPE
        SYNTAX  Dot1dPortPriorityEntry
        ACCESS  not-accessible
        STATUS  mandatory
        DESCRIPTION
            "A list of the number of egress traffic classes supported for each
             port in a transparent bridge. This is indexed by dot1dBasePort."
        INDEX   { dot1dBasePort }
        ::= { dot1dPortPriorityTable 1 }

    Dot1dPortPriorityEntry ::=
        SEQUENCE {
            dot1dPortNumTrafficClasses
                INTEGER
        }

    dot1dPortNumTrafficClasses OBJECT-TYPE
        SYNTAX  INTEGER (1..8)
        ACCESS  read-only
        STATUS  mandatory
        DESCRIPTION
            "The number of egress traffic classes supported on this port.
             This object may optionally be read-only."
        ::= { dot1dPortPriorityEntry 1 }

-- *****************************************************************************
-- the dot1dGarp group
-- *****************************************************************************
    dot1dPortGarpTable OBJECT-TYPE
        SYNTAX  SEQUENCE OF Dot1dPortGarpEntry
        ACCESS  not-accessible
        STATUS  mandatory
        DESCRIPTION
            "A table of GARP control information about every bridge port.
             This is indexed by dot1dBasePort."
        ::= { dot1dGarp 1 }

    dot1dPortGarpEntry OBJECT-TYPE
        SYNTAX  Dot1dPortGarpEntry
        ACCESS  not-accessible
        STATUS  mandatory
        DESCRIPTION
            "GARP control information for a bridge port."
        INDEX   { dot1dBasePort }
        ::= { dot1dPortGarpTable 1 }

    Dot1dPortGarpEntry ::=
        SEQUENCE {
            dot1dPortGarpJoinTime
                TimeInterval,
            dot1dPortGarpLeaveTime
                TimeInterval,
            dot1dPortGarpLeaveAllTime
                TimeInterval
        }

    dot1dPortGarpJoinTime OBJECT-TYPE
        SYNTAX  TimeInterval (20..65535)
        ACCESS  read-write
        STATUS  mandatory
        DESCRIPTION
            "The GARP Join time, in centiseconds."
        DEFVAL  { 20 }
        ::= { dot1dPortGarpEntry 1 }

    dot1dPortGarpLeaveTime OBJECT-TYPE
        SYNTAX  TimeInterval (20..65535)
        ACCESS  read-write
        STATUS  mandatory
        DESCRIPTION
            "The GARP Leave time, in centiseconds."
        DEFVAL  { 60 }
        ::= { dot1dPortGarpEntry 2 }

    dot1dPortGarpLeaveAllTime OBJECT-TYPE
        SYNTAX  TimeInterval (20..65535)
        ACCESS  read-write
        STATUS  mandatory
        DESCRIPTION
            "The GARP LeaveAll time, in centiseconds."
        DEFVAL  { 1000 }
        ::= { dot1dPortGarpEntry 3 }

-- *****************************************************************************
-- The GMRP Port Configuration and Status Table
-- *****************************************************************************
    dot1dPortGmrpTable OBJECT-TYPE
        SYNTAX  SEQUENCE OF Dot1dPortGmrpEntry
        ACCESS  not-accessible
        STATUS  mandatory
        DESCRIPTION
            "A table of GMRP control and status information about every bridge port.
             Augments the dot1dBasePortTable."
        ::= { dot1dGmrp 1 }

    dot1dPortGmrpEntry OBJECT-TYPE
        SYNTAX  Dot1dPortGmrpEntry
        ACCESS  not-accessible
        STATUS  mandatory
        DESCRIPTION
            "GMRP control and status information for a bridge port."
        INDEX { dot1dBasePort}
        ::= { dot1dPortGmrpTable 1 }

    Dot1dPortGmrpEntry ::=
        SEQUENCE {
            dot1dPortGmrpStatus
                EnabledStatus,
            dot1dPortGmrpFailedRegistrations
                Counter,
            dot1dPortGmrpLastPduOrigin
                MacAddress
        }

    dot1dPortGmrpStatus OBJECT-TYPE
        SYNTAX  EnabledStatus
        ACCESS  read-write
        STATUS  mandatory
        DESCRIPTION
            "The state of GMRP operation on this port.
             The value enabled(1) indicates that GMRP is enabled on this port,
             in all VLANs, as long as dot1dGmrpStatus is also enabled for this
             device.
             When disabled(2) but dot1dGmrpStatus is still enabled for the
             device, GMRP is disabled on this port in all VLANs: any GMRP
             packets received will be silently discarded and no GMRP
             registrations will be propagated from other ports.
             This object affects all GMRP Applicant and Registrar state machines
             on this port.
             A transition from disabled(2) to enabled(1) will cause a reset of
             all GMRP state machines on this port."
        DEFVAL  { enabled }
        ::= { dot1dPortGmrpEntry 1 }

    dot1dPortGmrpFailedRegistrations OBJECT-TYPE
        SYNTAX  Counter
        ACCESS  read-only
        STATUS  mandatory
        DESCRIPTION
            "The total number of failed GMRP registrations, for any reason,
             in all VLANs, on this port."
        ::= { dot1dPortGmrpEntry 2 }

    dot1dPortGmrpLastPduOrigin OBJECT-TYPE
        SYNTAX  MacAddress
        ACCESS  read-only
        STATUS  mandatory
        DESCRIPTION
            "The Source MAC Address of the last GMRP message received on this port."
        ::= { dot1dPortGmrpEntry 3 }


-- sqbrd.mib
	qBridgeMIBObjects   OBJECT IDENTIFIER ::= { swVlan 5 }

-- *****************************************************************************
-- Textual Conventions
-- *****************************************************************************
-- Declarations for SNMPv1
    --EnabledStatus   ::= INTEGER { enabled(1), disabled(2) }
    Unsigned32      ::= INTEGER
    --PortList        ::= OCTET STRING
    --VlanIndex       ::= Unsigned32
    VlanId          ::= INTEGER (1..4094)
    --DisplayString   ::= OCTET STRING (SIZE (0..255))
    --TruthValue      ::= INTEGER { true(1), false(2) }
    TimeFilter      ::= INTEGER

-- *****************************************************************************
-- groups in the Q-BRIDGE MIB
-- *****************************************************************************
    dot1qBase       OBJECT IDENTIFIER ::= { qBridgeMIBObjects 1 }
    dot1qTp         OBJECT IDENTIFIER ::= { qBridgeMIBObjects 2 }
    dot1qStatic     OBJECT IDENTIFIER ::= { qBridgeMIBObjects 3 }
    dot1qVlan       OBJECT IDENTIFIER ::= { qBridgeMIBObjects 4 }

-- *****************************************************************************
-- the dot1qBase group
-- *****************************************************************************
    dot1qVlanVersionNumber OBJECT-TYPE
        SYNTAX  INTEGER {
            version1(1)
        }
        ACCESS  read-only
        STATUS  mandatory
        DESCRIPTION
            "The version number of IEEE 802.1Q that this device supports."
        REFERENCE
            "IEEE 802.1Q/D11 Section 12.10.1.1"
        ::= { dot1qBase 1 }

    dot1qMaxVlanId OBJECT-TYPE
        SYNTAX  VlanId
        ACCESS  read-only
        STATUS  mandatory
        DESCRIPTION
            "The maximum IEEE 802.1Q VLAN ID that this device supports."
        REFERENCE
            "IEEE 802.1Q/D11 Section 9.3.2.3"
        ::= { dot1qBase 2 }

    dot1qMaxSupportedVlans OBJECT-TYPE
        SYNTAX  Unsigned32
        ACCESS  read-only
        STATUS  mandatory
        DESCRIPTION
            "The maximum number of IEEE 802.1Q VLANs that this device supports."
        REFERENCE
            "IEEE 802.1Q/D11 Section 12.10.1.1"
        ::= { dot1qBase 3 }

    dot1qNumVlans OBJECT-TYPE
        SYNTAX  Unsigned32
        ACCESS  read-only
        STATUS  mandatory
        DESCRIPTION
            "The current number of IEEE 802.1Q VLANs that are configured in
             this device."
        REFERENCE
            "IEEE 802.1Q/D11 Section 12.7.1.1"
        ::= { dot1qBase 4 }

    dot1qGvrpStatus OBJECT-TYPE
        SYNTAX  EnabledStatus
        ACCESS  read-write
        STATUS  mandatory
        DESCRIPTION
            "The administrative status requested by management for GVRP.
             The value enabled(1) indicates that GVRP should be enabled on this
             device, on all ports for which it has not been specifically disabled.
             When disabled(2), GVRP is disabled on all ports and all GVRP packets
             will be forwarded transparently.
             This object affects all GVRP Applicant and Registrar state machines.
             A transition from disabled(2) to enabled(1) will cause a reset of
             all GVRP state machines on all ports."
        DEFVAL  { enabled }
        ::= { dot1qBase 5 }

-- *****************************************************************************
-- the dot1qTp group
-- *****************************************************************************
    dot1qFdbTable OBJECT-TYPE
        SYNTAX  SEQUENCE OF Dot1qFdbEntry
        ACCESS  not-accessible
        STATUS  mandatory
        DESCRIPTION
            "A table that contains configuration and control information for
             each Filtering Database currently operating on this device.
             Entries in this table appear automatically when VLANs are assigned
             FDB IDs in the dot1qVlanCurrentTable."
        ::= { dot1qTp 1 }

    dot1qFdbEntry OBJECT-TYPE
        SYNTAX  Dot1qFdbEntry
        ACCESS  not-accessible
        STATUS  mandatory
        DESCRIPTION
            "Information about a specific Filtering Database."
        INDEX   { dot1qFdbId }
        ::= { dot1qFdbTable 1 }

    Dot1qFdbEntry ::=
        SEQUENCE {
            dot1qFdbId
                Unsigned32,
            dot1qFdbDynamicCount
                Counter
        }

    dot1qFdbId OBJECT-TYPE
        SYNTAX  Unsigned32
        ACCESS  not-accessible
        STATUS  mandatory
        DESCRIPTION
            "The identity of this Filtering Database."
        ::= { dot1qFdbEntry 1 }

    dot1qFdbDynamicCount OBJECT-TYPE
        SYNTAX  Counter
        ACCESS  read-only
        STATUS  mandatory
        DESCRIPTION
            "The current number of dynamic entries in this Filtering Database."
        REFERENCE
            "IEEE 802.1Q/D11 Section 12.7.1.1.3"
        ::= { dot1qFdbEntry 2 }

-- *****************************************************************************
-- Multiple Forwarding Databases for 802.1Q Transparent devices.
-- This table is an alternative to the dot1dTpFdbTable, previously defined
-- for 802.1D devices which only support a single Forwarding Database.
-- *****************************************************************************
    dot1qTpFdbTable OBJECT-TYPE
        SYNTAX  SEQUENCE OF Dot1qTpFdbEntry
        ACCESS  not-accessible
        STATUS  mandatory
        DESCRIPTION
            "A table that contains information about unicast entries for which
             the device has forwarding and/or filtering information.
             This information is used by the transparent bridging function in
             determining how to propagate a received frame."
        REFERENCE
            "IEEE 802.1Q/D11 Section 12.7.7"
        ::= { dot1qTp 2 }

    dot1qTpFdbEntry OBJECT-TYPE
        SYNTAX  Dot1qTpFdbEntry
        ACCESS  not-accessible
        STATUS  mandatory
        DESCRIPTION
            "Information about a specific unicast MAC address for which the
             device has some forwarding and/or filtering information."
        INDEX   { dot1qFdbId, dot1qTpFdbAddress }
        ::= { dot1qTpFdbTable 1 }

    Dot1qTpFdbEntry ::=
        SEQUENCE {
            dot1qTpFdbAddress
                MacAddress,
            dot1qTpFdbPort
                INTEGER,
            dot1qTpFdbStatus
                INTEGER
        }

    dot1qTpFdbAddress OBJECT-TYPE
        SYNTAX  MacAddress
        ACCESS  not-accessible
        STATUS  mandatory
        DESCRIPTION
            "A unicast MAC address for which the device has forwarding and/or
             filtering information."
        ::= { dot1qTpFdbEntry 1 }

    dot1qTpFdbPort OBJECT-TYPE
        SYNTAX  INTEGER (0..65535)
        ACCESS  read-only
        STATUS  mandatory
        DESCRIPTION
            "Either the value '0', or the port number of the port on which
             a frame having a source address equal to the value of the
             corresponding instance of dot1qTpFdbAddress has been seen.
             A value of '0' indicates that the port number has not been learned
             but that the device does have some forwarding/filtering information
             about this address (e.g. in the dot1qStaticUnicastTable).
             Implementers are encouraged to assign the port value to this object
             whenever it is learned even for addresses for which the corresponding
             value of dot1qTpFdbStatus is not learned(3)."
        ::= { dot1qTpFdbEntry 2 }

    dot1qTpFdbStatus OBJECT-TYPE
        SYNTAX  INTEGER {
            other(1),
            invalid(2),
            learned(3),
            self(4),
            mgmt(5)
        }
        ACCESS  read-only
        STATUS  mandatory
        DESCRIPTION
            "The status of this entry. The meanings of the values are:
             other(1) - none of the following. This may include the case where
                        some other MIB object (not the corresponding instance
                        of dot1qTpFdbPort, nor an entry in the dot1qStaticUnicastTable)
                        is being used to determine if and how frames addressed to
                        the value of the corresponding instance of dot1qTpFdbAddress
                        are being forwarded.
             invalid(2) - this entry is no longer valid (e.g., it was learned
                          but has since aged out), but has not yet been flushed
                          from the table.
             learned(3) - the value of the corresponding instance of dot1qTpFdbPort
                          was learned and is being used.
             self(4) - the value of the corresponding instance of dot1qTpFdbAddress
                       represents one of the device's addresses.
                       The corresponding instance of dot1qTpFdbPort indicates
                       which of the device's ports has this address.
             mgmt(5) - the value of the corresponding instance of dot1qTpFdbAddress
                       is also the value of an existing instance of dot1qStaticAddress."
        ::= { dot1qTpFdbEntry 3 }

    dot1qTpGroupTable OBJECT-TYPE
        SYNTAX  SEQUENCE OF Dot1qTpGroupEntry
        ACCESS  not-accessible
        STATUS  mandatory
        DESCRIPTION
            "A table containing filtering information for VLANs configured into
             the bridge by (local or network) management, or learnt dynamically,
             specifying the set of ports to which frames received on a VLAN for
             this FDB and containing a specific Group destination address are
             allowed to be forwarded."
        ::= { dot1qTp 3 }

    dot1qTpGroupEntry OBJECT-TYPE
        SYNTAX  Dot1qTpGroupEntry
        ACCESS  not-accessible
        STATUS  mandatory
        DESCRIPTION
            "Filtering information configured into the bridge by management,
             or learnt dynamically, specifying the set of ports to which frames
             received on a VLAN and containing a specific Group destination
             address, are allowed to be forwarded.
             The subset of these ports learnt dynamically is also provided."
        INDEX   { dot1qVlanIndex, dot1qTpGroupAddress }
        ::= { dot1qTpGroupTable 1 }

    Dot1qTpGroupEntry ::=
        SEQUENCE {
            dot1qTpGroupAddress
                MacAddress,
            dot1qTpGroupEgressPorts
                PortList,
            dot1qTpGroupLearnt
                PortList
        }

    dot1qTpGroupAddress OBJECT-TYPE
        SYNTAX  MacAddress
        ACCESS  not-accessible
        STATUS  mandatory
        DESCRIPTION
            "The destination Group MAC address in a frame to which this entry's
             filtering information applies."
        ::= { dot1qTpGroupEntry 1 }

    dot1qTpGroupEgressPorts OBJECT-TYPE
        SYNTAX  PortList
        ACCESS  read-only
        STATUS  mandatory
        DESCRIPTION
            "The complete set of ports, in this Filtering Database, to which
             frames destined for this Group MAC address are currently being
             explicitly forwarded.
             This does not include ports for which this address is only
             implicitly forwarded, in the dot1qForwardAllPorts list."
        ::= { dot1qTpGroupEntry 2 }

    dot1qTpGroupLearnt OBJECT-TYPE
        SYNTAX  PortList
        ACCESS  read-only
        STATUS  mandatory
        DESCRIPTION
            "The subset of ports in dot1qTpGroupEgressPorts which were learnt by
             GMRP or some other dynamic mechanism, in this Filtering database."
        ::= { dot1qTpGroupEntry 3 }

-- *****************************************************************************
-- the dot1qStatic group
-- *****************************************************************************

-- -------------------------------------------------------------
-- The Static (Destination-Address Filtering) Database
-- -------------------------------------------------------------

dot1qStaticMulticastTable OBJECT-TYPE
    SYNTAX      SEQUENCE OF Dot1qStaticMulticastEntry
    ACCESS      not-accessible
    STATUS      mandatory
    DESCRIPTION
        "A table containing filtering information for Multicast
        and Broadcast MAC addresses for each VLAN, configured
        into the device by (local or network) management
        specifying the set of ports to which frames received
        from specific ports and containing specific Multicast
        and Broadcast destination addresses are allowed to be
        forwarded.  A value of zero in this table as the port
        number from which frames with a specific destination
        address are received, is used to specify all ports for
        which there is no specific entry in this table for that
        particular destination address.  Entries are valid for
        Multicast and Broadcast addresses only."
    REFERENCE
        "IEEE 802.1Q/D11 Section 12.7.7,
        ISO/IEC 15802-3 Section 7.9.1"
    ::= { dot1qStatic 2 }

dot1qStaticMulticastEntry OBJECT-TYPE
    SYNTAX      Dot1qStaticMulticastEntry
    ACCESS      not-accessible
    STATUS      mandatory
    DESCRIPTION
        "Filtering information configured into the device by
        (local or network) management specifying the set of
        ports to which frames received from this specific port
        for this VLAN and containing this Multicast or Broadcast
        destination address are allowed to be forwarded."
    INDEX   {
        dot1qVlanIndex,
        dot1qStaticMulticastAddress,
        dot1qStaticMulticastReceivePort
    }
    ::= { dot1qStaticMulticastTable 1 }

Dot1qStaticMulticastEntry ::=
    SEQUENCE {
        dot1qStaticMulticastAddress
            MacAddress,
        dot1qStaticMulticastReceivePort
            INTEGER,
        dot1qStaticMulticastStaticEgressPorts
            PortList,
        dot1qStaticMulticastForbiddenEgressPorts
            PortList,
        dot1qStaticMulticastStatus
            INTEGER
    }

dot1qStaticMulticastAddress OBJECT-TYPE
    SYNTAX      MacAddress
    ACCESS      not-accessible
    STATUS      mandatory
    DESCRIPTION
        "The destination MAC address in a frame to which this
        entry's filtering information applies.  This object must
        take the value of a Multicast or Broadcast address."
    ::= { dot1qStaticMulticastEntry 1 }

dot1qStaticMulticastReceivePort OBJECT-TYPE
    SYNTAX      INTEGER (0..65535)
    ACCESS      not-accessible
    STATUS      mandatory
    DESCRIPTION
        "Either the value '0', or the port number of the port
        from which a frame must be received in order for this
        entry's filtering information to apply.  A value of zero
        indicates that this entry applies on all ports of the
        device for which there is no other applicable entry."
    ::= { dot1qStaticMulticastEntry 2 }

dot1qStaticMulticastStaticEgressPorts OBJECT-TYPE
    SYNTAX      PortList
    ACCESS      read-write
    STATUS      mandatory
    DESCRIPTION
        "The set of ports to which frames received from a
        specific port and destined for a specific Multicast or
        Broadcast MAC address must be forwarded, regardless of
        any dynamic information e.g. from GMRP.  A port may not
        be added in this set if it is already a member of the
        set of ports in dot1qStaticMulticastForbiddenEgressPorts.
        The default value of this object is a string of ones of
        appropriate length."
    ::= { dot1qStaticMulticastEntry 3 }
dot1qStaticMulticastForbiddenEgressPorts OBJECT-TYPE
    SYNTAX      PortList
    ACCESS      read-write
    STATUS      mandatory
    DESCRIPTION
        "The set of ports to which frames received from a
        specific port and destined for a specific Multicast or
        Broadcast MAC address must not be forwarded, regardless
        of any dynamic information e.g. from GMRP.  A port may
        not be added in this set if it is already a member of the
        set of ports in dot1qStaticMulticastStaticEgressPorts.
        The default value of this object is a string of zeros of
        appropriate length."
    ::= { dot1qStaticMulticastEntry 4 }

dot1qStaticMulticastStatus OBJECT-TYPE
    SYNTAX      INTEGER {
                    other(1),
                    invalid(2),
                    permanent(3),
                    deleteOnReset(4),
                    deleteOnTimeout(5)
                }
    ACCESS      read-write
    STATUS      mandatory
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { dot1qStaticMulticastEntry 5 }



-- *****************************************************************************
-- the dot1qVlan group
-- *****************************************************************************
    dot1qVlanNumDeletes OBJECT-TYPE
        SYNTAX  Counter
        ACCESS  read-only
        STATUS  mandatory
        DESCRIPTION
            "The number of times a VLAN entry has been deleted from the
             dot1qVlanCurrentTable (for any reason).
             If an entry is deleted, then inserted, and then deleted, this
             counter will be incremented by 2."
        ::= { dot1qVlan 1 }

    dot1qVlanCurrentTable OBJECT-TYPE
        SYNTAX  SEQUENCE OF Dot1qVlanCurrentEntry
        ACCESS  not-accessible
        STATUS  mandatory
        DESCRIPTION
            "A table containing current configuration information for each VLAN
             currently configured into the device by (local or network) management,
             or dynamically created as a result of GVRP requests received."
        ::= { dot1qVlan 2 }

    dot1qVlanCurrentEntry OBJECT-TYPE
        SYNTAX  Dot1qVlanCurrentEntry
        ACCESS  not-accessible
        STATUS  mandatory
        DESCRIPTION
            "Information for a VLAN configured into the device by (local or
             network) management, or dynamically created as a result of GVRP
             requests received."
        INDEX   { dot1qVlanTimeMark, dot1qVlanIndex }
        ::= { dot1qVlanCurrentTable 1 }

    Dot1qVlanCurrentEntry ::=
        SEQUENCE {
            dot1qVlanTimeMark
                TimeFilter,
            dot1qVlanIndex
                VlanIndex,
            dot1qVlanFdbId
                Unsigned32,
            dot1qVlanCurrentEgressPorts
                PortList,
            dot1qVlanCurrentUntaggedPorts
                PortList,
            dot1qVlanStatus
                INTEGER,
            dot1qVlanCreationTime
                TimeTicks
        }

    dot1qVlanTimeMark OBJECT-TYPE
        SYNTAX  TimeFilter
        ACCESS  not-accessible
        STATUS  mandatory
        DESCRIPTION
            "A TimeFilter for this entry. See the TimeFilter textual convention
             to see how this works."
        ::= { dot1qVlanCurrentEntry 1 }

    dot1qVlanIndex OBJECT-TYPE
        SYNTAX  VlanIndex
        ACCESS  not-accessible
        STATUS  mandatory
        DESCRIPTION
            "The VLAN-ID or other identifier refering to this VLAN."
        ::= { dot1qVlanCurrentEntry 2 }

    dot1qVlanFdbId OBJECT-TYPE
        SYNTAX  Unsigned32
        ACCESS  read-only
        STATUS  mandatory
        DESCRIPTION
            "The Filtering Database used by this VLAN. This is one of the
             dot1qFdbId values in the dot1qFdbTable.
             This value is allocated automatically by the device whenever the
             VLAN is created: either dynamically by GVRP, or by management,
             in dot1qVlanStaticTable.
             Allocation of this value follows the learning constraints defined
             for this VLAN in dot1qLearningConstraintsTable."
        ::= { dot1qVlanCurrentEntry 3 }

    dot1qVlanCurrentEgressPorts OBJECT-TYPE
        SYNTAX  PortList
        ACCESS  read-only
        STATUS  mandatory
        DESCRIPTION
            "The set of ports which are transmitting traffic for this VLAN as
             either tagged or untagged frames."
        REFERENCE
            "IEEE 802.1Q/D11 Section 12.10.2.1"
        ::= { dot1qVlanCurrentEntry 4 }

    dot1qVlanCurrentUntaggedPorts OBJECT-TYPE
        SYNTAX  PortList
        ACCESS  read-only
        STATUS  mandatory
        DESCRIPTION
            "The set of ports which are transmitting traffic for this VLAN as
             untagged frames."
        REFERENCE
            "IEEE 802.1Q/D11 Section 12.10.2.1"
        ::= { dot1qVlanCurrentEntry 5 }

    dot1qVlanStatus OBJECT-TYPE
        SYNTAX  INTEGER {
            other(1),
            permanent(2),
            dynamicGvrp(3)
        }
        ACCESS  read-only
        STATUS  mandatory
        DESCRIPTION
            "This object indicates the status of this entry.
             other(1) - this entry is currently in use but the conditions under
                        which it will remain so differ from the following values.
             permanent(2) - this entry, corresponding to an entry in
                            dot1qVlanStaticTable, is currently in use and will
                            remain so after the next reset of the device.
                            The port lists for this entry include ports from
                            the equivalent dot1qVlanStaticTable entry and ports
                            learnt dynamically.
            dynamicGvrp(3) - this entry is currently in use and will remain so
                             until removed by GVRP.
                             There is no static entry for this VLAN and it will
                             be removed when the last port leaves the VLAN."
        ::= { dot1qVlanCurrentEntry 6 }

    dot1qVlanCreationTime OBJECT-TYPE
        SYNTAX  TimeTicks
        ACCESS  read-only
        STATUS  mandatory
        DESCRIPTION
            "The value of sysUpTime when this VLAN was created."
        ::= { dot1qVlanCurrentEntry 7 }

    dot1qVlanStaticTable OBJECT-TYPE
        SYNTAX  SEQUENCE OF Dot1qVlanStaticEntry
        ACCESS  not-accessible
        STATUS  mandatory
        DESCRIPTION
            "A table containing static configuration information for each VLAN
             configured into the device by (local or network) management.
             All entries are permanent and will be restored after the device
             is reset."
        ::= { dot1qVlan 3 }

    dot1qVlanStaticEntry OBJECT-TYPE
        SYNTAX  Dot1qVlanStaticEntry
        ACCESS  not-accessible
        STATUS  mandatory
        DESCRIPTION
            "Static information for a VLAN configured into the device by (local
             or network) management."
        INDEX   { dot1qVlanIndex }
        ::= { dot1qVlanStaticTable 1 }

    Dot1qVlanStaticEntry ::=
        SEQUENCE {
            dot1qVlanStaticName
                DisplayString,
            dot1qVlanStaticEgressPorts
                PortList,
            dot1qVlanForbiddenEgressPorts
                PortList,
            dot1qVlanStaticUntaggedPorts
                PortList,
            dot1qVlanStaticRowState
                INTEGER
        }

    dot1qVlanStaticName OBJECT-TYPE
        SYNTAX  DisplayString (SIZE (0..32))
        ACCESS  read-write
        STATUS  mandatory
        DESCRIPTION
            "An administratively assigned string, which may be used to identify
             the VLAN."
        REFERENCE
            "IEEE 802.1Q/D11 Section 12.10.2.1"
        ::= { dot1qVlanStaticEntry 1 }

    dot1qVlanStaticEgressPorts OBJECT-TYPE
        SYNTAX  PortList
        ACCESS  read-write
        STATUS  mandatory
        DESCRIPTION
            "The set of ports which are permanently assigned to the egress list
             for this VLAN by management. Changes to a bit in this object affect
             the per-port per-VLAN Registrar control for Registration Fixed for
             the relevant GVRP state machine on each port.
             A port may not be added in this set if it is already a member of
             the set of ports in dot1qVlanForbiddenEgressPorts. The default
             value of this object is a string of zeros of appropriate length,
             indicating not fixed."
        REFERENCE
            "IEEE 802.1Q/D11 Section 12.7.7.3, 11.2.3.2.3"
        ::= { dot1qVlanStaticEntry 2 }

    dot1qVlanForbiddenEgressPorts OBJECT-TYPE
        SYNTAX  PortList
        ACCESS  read-write
        STATUS  mandatory
        DESCRIPTION
            "The set of ports which are prohibited by management from being
             included in the egress list for this VLAN.
             Changes to this object that cause a port to be included or excluded
             affect the per-port per-VLAN Registrar control for Registration
             Forbidden for the relevant GVRP state machine on each port.
             A port may not be added in this set if it is already a member of
             the set of ports in dot1qVlanStaticEgressPorts.
             The default value of this object is a string of zeros of
             appropriate length, excluding all ports from the forbidden set."
        REFERENCE
            "IEEE 802.1Q/D11 Section 12.7.7.3, 11.2.3.2.3"
        ::= { dot1qVlanStaticEntry 3 }

    dot1qVlanStaticUntaggedPorts OBJECT-TYPE
        SYNTAX  PortList
        ACCESS  read-write
        STATUS  mandatory
        DESCRIPTION
            "The set of ports which should transmit egress packets for this VLAN
             as untagged. The default value of this object for the default VLAN
             (VlanId 001) is a string of appropriate length including all ports.
             There is no specified default for other VLANs.
             If a device cannot support a value being set then its agent will
             reject the set operation.
             Attempts to set more than one VLAN to be untagged on egress may be
             rejected by devices which do not support this option."
        REFERENCE
            "IEEE 802.1Q/D11 Section 12.10.2.1"
        ::= { dot1qVlanStaticEntry 4 }

    dot1qVlanStaticRowState OBJECT-TYPE
        SYNTAX  INTEGER {
            other(1),
            invalid(2),
            valid(3)
        }
        ACCESS  read-write
        STATUS  mandatory
        DESCRIPTION
            "This object indicates the status of this entry.
             other(1) - this entry is currently in use but the conditions under
                        which it will remain so are different from each of the
                        following values.
             invalid(2) - writing this value to the object, and then the
                          corresponding entry will be removed from the table.
             valid(3) - this entry is reside in the table."
        ::= { dot1qVlanStaticEntry 5 }

    dot1qPortVlanTable OBJECT-TYPE
        SYNTAX  SEQUENCE OF Dot1qPortVlanEntry
        ACCESS  not-accessible
        STATUS  mandatory
        DESCRIPTION
            "A table containing per port control and status information for VLAN
             configuration in the device."
        ::= { dot1qVlan 4 }

    dot1qPortVlanEntry OBJECT-TYPE
        SYNTAX  Dot1qPortVlanEntry
        ACCESS  not-accessible
        STATUS  mandatory
        DESCRIPTION
            "Information controlling VLAN configuration for a port on the device.
             This is indexed by dot1dBasePort."
        INDEX { dot1dBasePort }
        ::= { dot1qPortVlanTable 1 }

    Dot1qPortVlanEntry ::=
        SEQUENCE {
            dot1qPvid
                VlanIndex,
            dot1qPortIngressFiltering
                TruthValue,
            dot1qPortGvrpStatus
                EnabledStatus,
            dot1qPortGvrpFailedRegistrations
                Counter,
            dot1qPortGvrpLastPduOrigin
                MacAddress
        }

    dot1qPvid OBJECT-TYPE
        SYNTAX  VlanIndex
        ACCESS  read-write
        STATUS  mandatory
        DESCRIPTION
            "The PVID, the VLAN ID assigned to untagged frames or Prority-Tagged
             frames received on this port."
        REFERENCE
            "IEEE 802.1Q/D11 Section 12.10.1.1"
        DEFVAL  { 1 }
        ::= { dot1qPortVlanEntry 1 }

    dot1qPortIngressFiltering OBJECT-TYPE
        SYNTAX  TruthValue
        ACCESS  read-write
        STATUS  mandatory
        DESCRIPTION
            "When this is true(1) the device will discard incoming frames for
             VLANs which do not include this Port in its Member set.
             When false(2), the port will accept all incoming frames.
             This control does not affect VLAN independent BPDU frames, such
             as GVRP and STP.
             It does affect VLAN dependent BPDU frames, such as GMRP."
        REFERENCE
            "IEEE 802.1Q/D11 Section 12.10.1.4"
        DEFVAL  { false }
        ::= { dot1qPortVlanEntry 2 }

    dot1qPortGvrpStatus OBJECT-TYPE
        SYNTAX  EnabledStatus
        ACCESS  read-write
        STATUS  mandatory
        DESCRIPTION
            "The state of GVRP operation on this port.
             The value enabled(1) indicates that GVRP is enabled on this port,
             as long as dot1qGvrpStatus is also enabled for this device.
             When disabled(2) but dot1qGvrpStatus is still enabled for the
             device, GVRP is disabled on this port: any GVRP packets received
             will be silently discarded and no GVRP registrations will be
             propagated from other ports.
             This object affects all GVRP Applicant and Registrar state machines
             on this port.
             A transition from disabled(2) to enabled(1) will cause a reset of
             all GVRP state machines on this port."
        DEFVAL  { enabled }
        ::= { dot1qPortVlanEntry 3 }

    dot1qPortGvrpFailedRegistrations OBJECT-TYPE
        SYNTAX  Counter
        ACCESS  read-only
        STATUS  mandatory
        DESCRIPTION
            "The total number of failed GVRP registrations, for any reason,
             on this port."
        ::= { dot1qPortVlanEntry 4 }

    dot1qPortGvrpLastPduOrigin OBJECT-TYPE
        SYNTAX  MacAddress
        ACCESS  read-only
        STATUS  mandatory
        DESCRIPTION
            "The Source MAC Address of the last GVRP message received on this port."
        ::= { dot1qPortVlanEntry 5 }

-- sniff.mib
	swPortSniff    OBJECT IDENTIFIER ::= { swL2Mgmt 5 }

-- *********************************************************************************************
    swSniffCtrlTable OBJECT-TYPE
        SYNTAX SEQUENCE OF SwSniffCtrlEntry
        ACCESS not-accessible
        STATUS mandatory
        DESCRIPTION
            "A list of port sniffing entries.Port Sniffing function provides an easy
             way to monitor traffic on any port. In this way any good packets appears
             on the source mirror port also shows up on the target mirror port
             without need to reconstruct the LAN."
        ::= { swPortSniff 1 }

    swSniffCtrlEntry OBJECT-TYPE
        SYNTAX SwSniffCtrlEntry
        ACCESS not-accessible
        STATUS mandatory
        DESCRIPTION
            "Each entry contains a pair of sniff source port and target port."
        INDEX  { swSniffIndex }
        ::= { swSniffCtrlTable 1 }

    SwSniffCtrlEntry ::=
        SEQUENCE {
            swSniffIndex
                INTEGER,
            swSniffSourcePort
                INTEGER,
            swSniffTargetPort
                INTEGER,
            swSniffState
                INTEGER
        }

    swSniffIndex OBJECT-TYPE
        SYNTAX INTEGER
        ACCESS read-only
        STATUS mandatory
        DESCRIPTION
            "A unique number to identify the sniff entry."
        ::= { swSniffCtrlEntry 1 }

    swSniffSourcePort OBJECT-TYPE
        SYNTAX INTEGER (1..96)
        ACCESS read-write
        STATUS mandatory
        DESCRIPTION
            "Indicates the source port whose traffic will be sniffed."
        ::= { swSniffCtrlEntry 2 }

    swSniffTargetPort OBJECT-TYPE
        SYNTAX INTEGER (1..96)
        ACCESS read-write
        STATUS mandatory
        DESCRIPTION
            "Indicates the target port which the traffic appears on the source sniffed port
             will be copied to. A trunk port member cannot be configured as a target
             Sniffing port"
        ::= { swSniffCtrlEntry 3 }

    swSniffState OBJECT-TYPE
        SYNTAX INTEGER {
            other(1),
            disable(2),
            enable(3)
        }
        ACCESS read-write
        STATUS mandatory
        DESCRIPTION
            "This object indicates the status of this entry.
            other(1)   - this entry is currently in use but the conditions under
                                which it will remain so are different from each of the
                                following values.
            disable(2) - Sniff funtion disable.
            enable(3) -  Sniff funtion enable and Sniff received or transmit
                                  packet by Sniff source port."
        ::= { swSniffCtrlEntry 4 }



-- strunk.mib
	swPortTrunk    OBJECT IDENTIFIER ::= { swL2Mgmt 6 }

-- ************************************************************************
--  swPortTrunkTable       OBJECT IDENTIFIER ::= {  swPortTrunk 1 }
-- ************************************************************************
    swPortTrunkCtrlTable OBJECT-TYPE
        SYNTAX SEQUENCE OF SwPortTrunkCtrlEntry
        ACCESS not-accessible
        STATUS mandatory
        DESCRIPTION
            "This table specifies which port trunking configuration.
             Trunking ID is as following :
             trunk 1 - unit1, base, port5~12;
             trunk 2 - unit1, base, port13~20;
             trunk 3 - unit1, slot1, port21,22;
             trunk 4 - reserved;
             trunk 5,   9, 13 - unit2(3, 4), base, port7~14;
             trunk 6, 10, 14 - unit2(3, 4), base, port15~22;
             trunk 7, 11, 15 - unit2(3, 4), slot1, port23,24;
             trunk 8, 12, 16 - reserved"
        ::= { swPortTrunk 1 }

    swPortTrunkCtrlEntry OBJECT-TYPE
        SYNTAX SwPortTrunkCtrlEntry
        ACCESS not-accessible
        STATUS mandatory
        DESCRIPTION
            "Each entry specifies which ports are grouped as a single logical link."
        INDEX  { swPortTrunkCtrlIndex }
        ::= { swPortTrunkCtrlTable 1 }

    SwPortTrunkCtrlEntry ::=
        SEQUENCE {
            swPortTrunkCtrlIndex
                INTEGER,
            swPortTrunkCtrlAnchorPort
                INTEGER,
            swPortTrunkCtrlMasterPort
                INTEGER,
            swPortTrunkCtrlName
                DisplayString (SIZE (0..16)),
            swPortTrunkCtrlMember
                PortList,
            swPortTrunkCtrlState
                INTEGER
        }

    swPortTrunkCtrlIndex OBJECT-TYPE
        SYNTAX INTEGER
        ACCESS read-only
        STATUS mandatory
        DESCRIPTION
            "The index of logical trunk of ports."
        ::= { swPortTrunkCtrlEntry 1 }

    swPortTrunkCtrlAnchorPort OBJECT-TYPE
        SYNTAX INTEGER
        ACCESS read-write
        STATUS mandatory
        DESCRIPTION
            "get anchor port number between trunk ports"
        ::= { swPortTrunkCtrlEntry 2 }

    swPortTrunkCtrlMasterPort OBJECT-TYPE
        SYNTAX INTEGER
        ACCESS read-only
        STATUS mandatory
        DESCRIPTION
            "get master port number between trunk ports"
        ::= { swPortTrunkCtrlEntry 3 }

    swPortTrunkCtrlName OBJECT-TYPE
        SYNTAX DisplayString (SIZE (0..16))
        ACCESS read-write
        STATUS mandatory
        DESCRIPTION
            "The name of logical trunk of ports."
        ::= { swPortTrunkCtrlEntry 4 }

    swPortTrunkCtrlMember OBJECT-TYPE
        SYNTAX PortList
        ACCESS read-write
        STATUS mandatory
        DESCRIPTION
            "specifies the member ports which are grouped as a trunk."
        ::= { swPortTrunkCtrlEntry 5 }


    swPortTrunkCtrlState OBJECT-TYPE
        SYNTAX INTEGER {
               other(1),
               disabled(2),
               enabled(3)
               }
        ACCESS read-write
        STATUS mandatory
        DESCRIPTION
            "This object determines whether the trunk setting is in enable/disable state."
        ::= { swPortTrunkCtrlEntry 6 }

    swPortTrunkMemberTable OBJECT-TYPE
        SYNTAX SEQUENCE OF SwPortTrunkMemberEntry
        ACCESS not-accessible
        STATUS mandatory
        DESCRIPTION
            "A list of information provide a different view for member ports grouped as a trunk"
        ::= { swPortTrunk 2 }

    swPortTrunkMemberEntry OBJECT-TYPE
        SYNTAX SwPortTrunkMemberEntry
        ACCESS not-accessible
        STATUS mandatory
        DESCRIPTION
            "Each entry corresponds to a member port."
        INDEX  { swPortTrunkMemberIndex,
                         swPortTrunkMemberUnitIndex,
                         swPortTrunkMemberModuleIndex,
                         swPortTrunkMemberPortIndex}
        ::= { swPortTrunkMemberTable 1 }

    SwPortTrunkMemberEntry ::=
        SEQUENCE {
            swPortTrunkMemberIndex
                INTEGER,
            swPortTrunkMemberUnitIndex
                INTEGER,
            swPortTrunkMemberModuleIndex
                INTEGER,
            swPortTrunkMemberPortIndex
                INTEGER
        }

    swPortTrunkMemberIndex OBJECT-TYPE
        SYNTAX INTEGER
        ACCESS read-only
        STATUS mandatory
        DESCRIPTION
            "Indicates the trunk ID where the port is located."
        ::= { swPortTrunkMemberEntry 1 }

    swPortTrunkMemberUnitIndex OBJECT-TYPE
        SYNTAX INTEGER
        ACCESS read-only
        STATUS mandatory
        DESCRIPTION
            "Indicates the unit ID where the port is located."
        ::= { swPortTrunkMemberEntry 2 }

    swPortTrunkMemberModuleIndex OBJECT-TYPE
        SYNTAX INTEGER
        ACCESS read-only
        STATUS mandatory
        DESCRIPTION
            "Indicates the module ID where the port is located."
        ::= { swPortTrunkMemberEntry 3 }

    swPortTrunkMemberPortIndex OBJECT-TYPE
        SYNTAX INTEGER
        ACCESS read-only
        STATUS mandatory
        DESCRIPTION
            "Indicates the port index relative to the module."
        ::= { swPortTrunkMemberEntry 4 }


-- svlan.mib

    swVlanCtrl    OBJECT IDENTIFIER ::= { swVlan 1 }
    swMacBaseVlan    OBJECT IDENTIFIER ::= { swVlan 2 }
    swPortBaseVlan  OBJECT IDENTIFIER ::= { swVlan 3 }

-- ********************************************************************
--  swVlanCtrl
-- ********************************************************************
    swVlanCtrlMode OBJECT-TYPE
        SYNTAX  INTEGER {
            other(1),
            disabled(2),    -- Vlan function be disable
            mac-base(3),    -- proprietary mac base Vlan
            ieee8021q(4),   -- 802.1q gvrp base Vlan
            port-base(5)    -- proprietary port base Vlan
        }
        ACCESS  read-write
        STATUS  mandatory
        DESCRIPTION
            "This object controls which Vlan function will be enable (or disable)
              when the switch hub restart at the startup (power on) or warm
              start."
        ::= { swVlanCtrl 1 }

    swVlanInfoStatus OBJECT-TYPE
        SYNTAX  INTEGER {
            other(1),
            disabled(2),    -- Vlan function be disable
            mac-base(3),    -- proprietary mac base Vlan
            ieee8021q(4)    -- 802.1q gvrp base Vlan
        }
        ACCESS  read-only
        STATUS  mandatory
        DESCRIPTION
            "This object indicates which Vlan function be enable (or disable)
              in mandatoryly stage. There are no effect when change swVlanCtrlMode
              vlaue in the system running."
        ::= { swVlanCtrl 2 }

    swVlanSnmpPortVlan OBJECT-TYPE
        SYNTAX  VlanIndex
        ACCESS  read-write
        STATUS  mandatory
        DESCRIPTION
            "Indicates the Vlan which the SNMP port belongs to.
             The value range is 1 to 4094."
        ::= { swVlanCtrl 3 }

-- ********************************************************************
--  swMacBaseVlan
-- ********************************************************************

    swMacBaseVlanInfo    OBJECT IDENTIFIER ::= { swMacBaseVlan 1 }

    swMacBaseVlanMaxNum OBJECT-TYPE
        SYNTAX  INTEGER
        ACCESS  read-only
        STATUS  mandatory
        DESCRIPTION
            "The maximum number of Mac base Vlan allowed by the system."
        ::= { swMacBaseVlanInfo 1 }

    swMacBaseVlanAddrMaxNum OBJECT-TYPE
        SYNTAX  INTEGER
        ACCESS  read-only
        STATUS  mandatory
        DESCRIPTION
            "The maximum number of entries in Mac-based Vlan address table."
        ::= { swMacBaseVlanInfo 2 }

    swMacBaseVlanCtrlTable OBJECT-TYPE
        SYNTAX  SEQUENCE OF SwMacBaseVlanCtrlEntry
        ACCESS  not-accessible
        STATUS  mandatory
        DESCRIPTION
            "A table that contains information about MAC base Vlan
             entries for which the switch has forwarding and/or filtering
             information. This information is used by the transparent switching
             function in determining how to propagate a received frame."
        ::= { swMacBaseVlan 2 }

    swMacBaseVlanCtrlEntry OBJECT-TYPE
        SYNTAX  SwMacBaseVlanCtrlEntry
        ACCESS  not-accessible
        STATUS  mandatory
        DESCRIPTION
            "A list of information about a specific MAC base Vlan configuration
             portlist for which the switch has some forwarding and/or filtering
             information."
        INDEX   { swMacBaseVlanDesc }
        ::= { swMacBaseVlanCtrlTable 1 }

    SwMacBaseVlanCtrlEntry ::=
        SEQUENCE {
            swMacBaseVlanDesc
                DisplayString (SIZE (1..12)),
            swMacBaseVlanMacMember
                INTEGER,
            swMacBaseVlanCtrlState
                INTEGER
        }

    swMacBaseVlanDesc OBJECT-TYPE
        SYNTAX  DisplayString (SIZE (1..12))
        ACCESS  read-only
        STATUS  mandatory
        DESCRIPTION
            "A textual description of the Mac Base Vlan for memorization.
              The string cannot set to empty string. There is a default value for this string"
        ::= { swMacBaseVlanCtrlEntry 1 }

    swMacBaseVlanMacMember OBJECT-TYPE
        SYNTAX  INTEGER
        ACCESS  read-only
        STATUS  mandatory
        DESCRIPTION
            "This object indicates the total number of MAC addresses contained
              in the VLAN entry."
        ::= { swMacBaseVlanCtrlEntry 2 }

    swMacBaseVlanCtrlState OBJECT-TYPE
        SYNTAX  INTEGER {
            other(1),
            disabled(2),
            enabled(3)
        }
        ACCESS  read-write
        STATUS  mandatory
        DESCRIPTION
            "This object indicates the MacBase Vlan state."
        ::= { swMacBaseVlanCtrlEntry 3 }

--    swMacBaseVlanMemberTable OBJECT-TYPE
--        SYNTAX SEQUENCE OF SwMacBaseVlanMemberEntry
--        ACCESS not-accessible
--        STATUS mandatory
--        DESCRIPTION
--            "A list of information provide a different view for those ports where packets from
--			 the given Vlan need to be forwarded to."
--        ::= { swMacBaseVlan 3}

--    swMacBaseVlanMemberEntry OBJECT-TYPE
--        SYNTAX SwMacBaseVlanMemberEntry
--        ACCESS not-accessible
--        STATUS mandatory
--        DESCRIPTION
--            ""
--        INDEX  { swMacBaseVlanDesc, swMacBaseVlanMemberUnitIndex,
--                         swMacBaseVlanMemberModuleIndex, swMacBaseVlanMemberPortIndex }
--        ::= { swMacBaseVlanMemberTable 1 }

--    SwMacBaseVlanMemberEntry ::=
--        SEQUENCE {
--            swMacBaseVlanMemberUnitIndex
--                INTEGER,
--            swMacBaseVlanMemberModuleIndex
--                INTEGER,
--            swMacBaseVlanMemberPortIndex
--                INTEGER
--        }

--    swMacBaseVlanMemberUnitIndex OBJECT-TYPE
--        SYNTAX INTEGER
--        ACCESS read-only
--        STATUS mandatory
--        DESCRIPTION
--            "specifies the unit ID where the port is located"
--        ::= { swMacBaseVlanMemberEntry 1 }

--    swMacBaseVlanMemberModuleIndex OBJECT-TYPE
--        SYNTAX INTEGER
--        ACCESS read-only
--        STATUS mandatory
--        DESCRIPTION
--            "specifies the module ID where the port is located"
--        ::= { swMacBaseVlanMemberEntry 2 }

--    swMacBaseVlanMemberPortIndex OBJECT-TYPE
--        SYNTAX INTEGER
--        ACCESS read-only
--        STATUS mandatory
--        DESCRIPTION
--            "specifies the port index relative to the module"
--        ::= { swMacBaseVlanMemberEntry 3 }

    swMacBaseVlanAddrTable OBJECT-TYPE
        SYNTAX  SEQUENCE OF SwMacBaseVlanAddrEntry
        ACCESS  not-accessible
        STATUS  mandatory
        DESCRIPTION
            "A table that contains information about unicast or multicast
             entries for which the switch has forwarding and/or filtering
             information. This information is used by the transparent switching
             function in determining how to propagate a received frame. Note that
             the priority of MacBaseVlanAddr table entries is lowest than Filtering
             Table and FDB Table, i.e. if there is a table hash collision between
             the entries of MacBaseVlanAddr Table and Filtering Table inside the
             switch H/W address table, then Filtering Table entry overwrite the
             colliding entry of MacBaseVlanAddr Table. This state is same of FDB
             table. See swFdbFilterTable and swFdbStaticTable description also."
        ::= { swMacBaseVlan 3 }

    swMacBaseVlanAddrEntry OBJECT-TYPE
        SYNTAX  SwMacBaseVlanAddrEntry
        ACCESS  not-accessible
        STATUS  mandatory
        DESCRIPTION
            "A list of information about a specific unicast or multicast MAC
             address for which the switch has some forwarding and/or filtering
             information."
        INDEX { swMacBaseVlanAddr }
        ::= { swMacBaseVlanAddrTable 1 }

    SwMacBaseVlanAddrEntry ::=
        SEQUENCE {
            swMacBaseVlanAddr
                MacAddress,
            swMacBaseVlanAddrVlanDesc
                DisplayString (SIZE (1..64)),
            swMacBaseVlanAddrState
                INTEGER,
            swMacBaseVlanAddrStatus
                INTEGER
        }

    swMacBaseVlanAddr OBJECT-TYPE
        SYNTAX  MacAddress
        ACCESS  read-only
        STATUS  mandatory
        DESCRIPTION
            "This object indictaes a unicast or multicast MAC address for which
              the bridge has forwarding and/or filtering information."
        ::= { swMacBaseVlanAddrEntry 1 }

    swMacBaseVlanAddrVlanDesc OBJECT-TYPE
        SYNTAX  DisplayString (SIZE (1..64))
        ACCESS  read-write
        STATUS  mandatory
        DESCRIPTION
            "A textual description of the Mac Base Vlan for memorization ."
        ::= { swMacBaseVlanAddrEntry 2 }

    swMacBaseVlanAddrState OBJECT-TYPE
        SYNTAX  INTEGER {
            other(1),
            invalid(2),
            valid(3)
        }
        ACCESS  read-write
        STATUS  mandatory
        DESCRIPTION
            "This object indicates the MacBase Vlan Address entry state.
            other(1) - this entry is currently in use but the conditions under
                              which it will remain so are different from each of the following
                              values.
            invalid(2) - writing this value to the object, and then the corresponding
                                entry will be removed from the table.
            valid(3) - this entry is reside in the table."
        ::= { swMacBaseVlanAddrEntry 3 }

    swMacBaseVlanAddrStatus OBJECT-TYPE
        SYNTAX  INTEGER {
            other(1),
            apply(2),
            not-apply(3)
        }
        ACCESS  read-only
        STATUS  mandatory
        DESCRIPTION
            "This object indicates the MacBase Vlan Address entry state.
            other(1) - this entry is currently in use but the conditions under
                              which it will remain so are different from each of the following
                              values.
            apply(2) - this entry is currently in use and reside in the table.
            not-apply(3) - this entry is reside in the table but currently not
                                      in use due to conflict with filter table."
        ::= { swMacBaseVlanAddrEntry 4 }

-- *****************************************************************************
--  swPortBaseVlan
-- *****************************************************************************
    swPortBaseVlanTotalNum OBJECT-TYPE
        SYNTAX  INTEGER
        ACCESS  read-only
        STATUS  mandatory
        DESCRIPTION
            "The total number of Port-Base Vlan which is in enabled state
             within this switch hub."
        ::= { swPortBaseVlan 1 }

    swPortBaseVlanDefaultVlanTable OBJECT-TYPE
        SYNTAX  SEQUENCE OF SwPortBaseVlanDefaultVlanEntry
        ACCESS  not-accessible
        STATUS  mandatory
        DESCRIPTION
            "A table that contains default Port-Based VLAN list entries for the
             switch. The entry (Vid = 1,i.e. swPortBaseVlanDefaultPvid = 1) is
             defalut Port-Based VLAN , maintained by system."
        ::= { swPortBaseVlan 2 }

    swPortBaseVlanDefaultVlanEntry OBJECT-TYPE
        SYNTAX  SwPortBaseVlanDefaultVlanEntry
        ACCESS  not-accessible
        STATUS  mandatory
        DESCRIPTION
            "A list of default Port-Based VLAN information in
             swPortBaseVlanDefaultVlanTable."
        INDEX   { swPortBaseVlanDefaultPvid }
        ::= { swPortBaseVlanDefaultVlanTable 1 }

    SwPortBaseVlanDefaultVlanEntry ::=
        SEQUENCE {
            swPortBaseVlanDefaultPvid
                INTEGER,
            swPortBaseVlanDefaultDesc
                DisplayString,
            swPortBaseVlanDefaultPortList
                PortList,
            swPortBaseVlanDefaultPortNumber
                INTEGER
        }

    swPortBaseVlanDefaultPvid OBJECT-TYPE
        SYNTAX  INTEGER
        ACCESS  read-only
        STATUS  mandatory
        DESCRIPTION
            "This object indicates the default Port-Base Vlan ID. It occupies only
             1 entry in VLAN table, with VID=1."
        ::= { swPortBaseVlanDefaultVlanEntry 1 }

    swPortBaseVlanDefaultDesc OBJECT-TYPE
        SYNTAX  DisplayString (SIZE (1..12))
        ACCESS  read-only
        STATUS  mandatory
        DESCRIPTION
            "A textual description of the Port-Base Vlan."
        ::= { swPortBaseVlanDefaultVlanEntry 2 }

    swPortBaseVlanDefaultPortList OBJECT-TYPE
        SYNTAX  PortList
        ACCESS  read-only
        STATUS  mandatory
        DESCRIPTION
            "This object indicates the port member set of the specified Vlan.
             Each Vlan has a octect string to indicate the port map. The most
             significant bit represents the lowest numbered port, and the
             least significant bit represents the highest numbered port."
        ::= { swPortBaseVlanDefaultVlanEntry 3 }

    swPortBaseVlanDefaultPortNumber OBJECT-TYPE
        SYNTAX  INTEGER
        ACCESS  read-only
        STATUS  mandatory
        DESCRIPTION
            "This object indicates the number of ports of the entry."
        ::= { swPortBaseVlanDefaultVlanEntry 4 }

    swPortBaseVlanConfigTable OBJECT-TYPE
        SYNTAX  SEQUENCE OF SwPortBaseVlanConfigEntry
        ACCESS  not-accessible
        STATUS  mandatory
        DESCRIPTION
            "A table that contains Port-Based VLAN list entries for the switch.
             The device can't support port overlapping in Port-Based VLAN."
        ::= { swPortBaseVlan 3 }

    swPortBaseVlanConfigEntry OBJECT-TYPE
        SYNTAX  SwPortBaseVlanConfigEntry
        ACCESS  not-accessible
        STATUS  mandatory
        DESCRIPTION
            "A list of information about a specific Port-Based VLAN configuration
             in swPortBaseVlanConfigTable."
        INDEX   { swPortBaseVlanConfigPvid }
        ::= { swPortBaseVlanConfigTable 1 }

    SwPortBaseVlanConfigEntry ::=
        SEQUENCE {
            swPortBaseVlanConfigPvid
                INTEGER,
            swPortBaseVlanConfigDesc
                DisplayString,
            swPortBaseVlanConfigPortList
                PortList,
            swPortBaseVlanConfigPortNumber
                INTEGER
-- +deleted by Jemy 2000/2/10 06:37PM B14
--            swPortBaseVlanConfigState
--                INTEGER
-- -
        }

    swPortBaseVlanConfigPvid OBJECT-TYPE
        SYNTAX  INTEGER (2..12)
        ACCESS  read-only
        STATUS  mandatory
        DESCRIPTION
            "This object indicates the Port-Base Vlan ID. There are up to 11 entries
             for current product now. The object range varies from 2 to 12."
        ::= { swPortBaseVlanConfigEntry 1 }

    swPortBaseVlanConfigDesc OBJECT-TYPE
        SYNTAX  DisplayString (SIZE (1..12))
        ACCESS  read-write
        STATUS  mandatory
        DESCRIPTION
            "A textual description of the Port-Base Vlan. It cannot be a null string.
             And each description must be unique in the table."
        ::= { swPortBaseVlanConfigEntry 2 }

    swPortBaseVlanConfigPortList OBJECT-TYPE
        SYNTAX  PortList
        ACCESS  read-write
        STATUS  mandatory
        DESCRIPTION
            "This object indicates which ports are belong to the Vlan. Each Vlan
             has a octect string to indicate with port map. The most significant
             bit represents the lowest numbered port, and the least significant
             bit represents the highest numbered port."
        ::= { swPortBaseVlanConfigEntry 3 }

    swPortBaseVlanConfigPortNumber OBJECT-TYPE
        SYNTAX  INTEGER
        ACCESS  read-only
        STATUS  mandatory
        DESCRIPTION
            "This object indicates the number of ports of the entry."
        ::= { swPortBaseVlanConfigEntry 4 }

-- +deleted by Jemy 2000/2/10 06:08PM B14
--    swPortBaseVlanConfigState OBJECT-TYPE
--        SYNTAX  INTEGER {
--            other(1),
--            disabled(2),
--            enabled(3)
--        }
--        ACCESS  read-write
--        STATUS  mandatory
--        DESCRIPTION
--            "This object indicates the Port-Base Vlan state.
--             other(1) - this entry is currently in use but the conditions under
--                        which it will remain so are different from each of the
--                        following values.
--             disabled(2) - writing this value to the object, and then the
--                          corresponding entry will be removed from the table.
--             enabled(3) - this entry is reside in the table."
--       ::= { swPortBaseVlanConfigEntry 5 }
-- -

END
