-- extracted from draft-tesink-entity-supplmib-01.txt
-- at Fri Aug 20 06:22:54 2004

   ENTSUPPL-MIB DEFINITIONS ::= BEGIN

   IMPORTS
       MODULE-IDENTITY, OBJECT-TYPE,
       transmission
           FROM SNMPv2-SMI
       DateAndTime, DisplayString
           FROM SNMPv2-TC
       MODULE-COMPLIANCE, OBJECT-GROUP
           FROM SNMPv2-CONF
       entPhysicalIndex
           FROM ENTITY-MIB;

   entitySupplMIB MODULE-IDENTITY
       LAST-UPDATED "200408160000Z"  -- August 16, 2004
           ORGANIZATION "IETF Entity MIB Working Group"
           CONTACT-INFO
              "WG charter:
                 http://www.ietf.org/html.charters/entmib-charter.html

               Mailing Lists:
                 General Discussion: entmib@ietf.org
                 To Subscribe: http://www.ietf.org/mailman/listinfo/entmib

                Chair: Margaret Wasserman
               Postal:
                  Tel:
               E-mail: margaret@thingmagic.com

               Author: Kaj Tesink
               Postal: One Telcordia Drive
                       Piscataway, NJ 08854
                       USA
                  Tel: +1 732-699-6068
               E-mail: kaj@research.telcordia.com"

       DESCRIPTION
         "The objects in this MIB module are used in conjunction
         with objects in the ENTITY-MIB to manage entities

         Copyright (C) The Internet Society (2004).  This version
         of this MIB module is part of RFC yyyy;  see the RFC
         itself for full legal notices."
-- RFC Ed.: replace yyyy with actual RFC number & remove this notice

       REVISION    "200408160000Z "  -- August 16, 2004
       DESCRIPTION "Initial version, published as RFC yyyy."
-- RFC Ed.: replace yyyy with actual RFC number & remove this notice

       ::= { transmission 1 }
-- RFC Ed.: replace XXX with IANA-assigned number & remove this notice
   -- The main sections of the module

   entitySupplObjects     OBJECT IDENTIFIER ::= { entitySupplMIB 1 }

   entitySupplConformance OBJECT IDENTIFIER ::= { entitySupplMIB 2 }



   -- These objects provide extensions to the entPhysicalTable.

   entSupplPhysicalTable OBJECT-TYPE
       SYNTAX  SEQUENCE OF EntSupplPhysicalEntry
       MAX-ACCESS  not-accessible
       STATUS  current
       DESCRIPTION
          "The table for supplementary objects to the entPhysicalTable."
        ::= { entitySupplObjects 1 }

   entSupplPhysicalEntry OBJECT-TYPE
       SYNTAX  EntSupplPhysicalEntry
       MAX-ACCESS  not-accessible
       STATUS  current
       DESCRIPTION
          "An entry in the entSupplPhysicalTable.  For each
          instance of this object there MUST be a corresponding
          instance of entPhysicalEntry."
       INDEX  { entPhysicalIndex }
        ::= { entSupplPhysicalTable 1 }

   EntSupplPhysicalEntry ::=
       SEQUENCE {
           entSupplPhysicalManufacturingDate DateAndTime,
           entSupplPhysicalUris    OCTET STRING
           }


   entSupplPhysicalManufacturingDate  OBJECT-TYPE
       SYNTAX      DateAndTime
       MAX-ACCESS  read-only
       STATUS      current
       DESCRIPTION
          "The manufacturing date for the physical entity."
        ::= { entSupplPhysicalEntry 1 }

   entSupplPhysicalUris OBJECT-TYPE
       SYNTAX      DisplayString
       MAX-ACCESS  read-write
       STATUS      current
       DESCRIPTION
          "This object contains additional identification information
           about the physical entity. The object contains URIs and
           therefore the syntax of this object must conform to RFC
           2396 section 2. Multiple URIs may be separated by white
           space characters."
       ::= { entSupplPhysicalEntry 2 }



   --
   --     Conformance Statements
   --

   entitySupplGroups      OBJECT IDENTIFIER ::= { entitySupplConformance 1 }

   entitySupplCompliances OBJECT IDENTIFIER ::= { entitySupplConformance 2 }

   --     Object Groups

   entitySupplPhysicalGroup OBJECT-GROUP
       OBJECTS {
           entSupplPhysicalManufacturingDate,
           entSupplPhysicalUris
           }
       STATUS  current
       DESCRIPTION
          "A collection of supplemental objects
           for to support physical entity features."
        ::= { entitySupplGroups 1 }


   --     Compliance Statements

   entitySupplCompliance MODULE-COMPLIANCE
       STATUS  current
       DESCRIPTION
          "The compliance statement for entities that support
          this module.  Compliance with the entity3Compliance
          statement of the ENTITY-MIB is prerequisite."

       MODULE  -- this module
           MANDATORY-GROUPS {
               entitySupplPhysicalGroup
               }

           OBJECT       entSupplPhysicalUris
           MIN-ACCESS   read-only
           DESCRIPTION
               "Write access is not required."

        ::= { entitySupplCompliances 1 }

   END

-- 
--    Copyright (C) The Internet Society (2004).  All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
--       ************************************************************
--       * NOTES TO RFC Editor (to be removed prior to publication) *
--       *                                                          *
--       * 1.) The normative references [RFCwwww] and [RFCzzzz]     *
--       * must be updated to point to the appropriate              *
--       * RFC when the corresponding Internet Draft is published,  *
--       * and all occurrences of the reference tags must be        *
--       * changed.                                                 *
--       *                                                          *
--       * 2.) Please replace all occurrences of "yyyy" in the      *
--       * DESCRIPTION clause of the MODULE-IDENTITY invocation     *
--       * in Section 4 with the RFC number assigned to this        *
--       * specification and remove the accompanying notes.         *
--       *                                                          *
--       * 3.) Please replace "XXX" in the MODULE-IDENTITY value    *
--       * with an IANA-assigned value under the 'transmission'     *
--       * subtree and remove the accompanying note.                *
--       *                                                          *
--       ************************************************************
