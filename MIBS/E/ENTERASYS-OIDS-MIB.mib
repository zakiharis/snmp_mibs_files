ENTERASYS-OIDS-MIB DEFINITIONS ::= BEGIN

--  enterasys-oids-mib.txt
--
--  Part Number:
--
--

--  This module provides authoritative definitions for Enterasys
--  Networks' OIDs.
--
--  This module will be extended, as needed.

--  Enterasys Networks reserves the right to make changes in
--  specification and other information contained in this document
--  without prior notice.  The reader should consult Enterasys
--  Networks to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in connection
--  with the management of Enterasys products.

--  Copyright December, (2002-2011) Enterasys Networks, Inc.

IMPORTS
    MODULE-IDENTITY, OBJECT-IDENTITY
        FROM SNMPv2-SMI
    etsysOids, etsysModules
        FROM ENTERASYS-MIB-NAMES;


enterasysOidsMib MODULE-IDENTITY
    LAST-UPDATED "201101131927Z"  -- Thu Jan 13 19:27 UTC 2011
    ORGANIZATION "Enterasys Networks"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "This MIB module defines a portion of the SNMP enterprise
         MIBs under Enterasys Networks' enterprise OID pertaining to
         system OIDs.

         This module embodies all of the definitions of OIDs for
         Enterasys Networks' devices."

    REVISION    "201101131927Z"  -- Thu Jan 13 19:27 UTC 2011
    DESCRIPTION "Added the following OIDs:
                 etsysOidDevS6, etsysOidPhyS6xCHASSIS,
                 etsysOidPhyS6Backplane."

    REVISION    "201012201841Z"  -- Mon Dec 20 18:41 UTC 2010
    DESCRIPTION "Added the following OIDs:
                 etsysOidDevSSAxT5068x0652, etsysOidDevSSAxG5018x0652."

    REVISION    "201012141337Z"  -- Tue Dec 14 13:37 UTC 2010
    DESCRIPTION "Added the following OIDs:
                 etsysOidPhyMGBICxBX40xD, etsysOidPhyMGBICxBX40xU,
                 etsysOidPhyMGBICxBX120xD, etsysOidPhyMGBICxBX120xU."

    REVISION    "201012021833Z"  -- Thu Dec  2 18:33 UTC 2010
    DESCRIPTION "Added the etsysOidPhySxDCxPS OID."
   
    REVISION    "201011181818Z"  -- Thu Nov 18 18:18 UTC 2010
    DESCRIPTION "Added the following OIDs:
                 etsysOidDevK6, etsysOidDevK10,
                 etsysOidPhyK6xCHASSIS, etsysOidPhyK10xCHASSIS,
                 etsysOidPhyK6xFAN, etsysOidPhyK10xFAN,
                 etsysOidPhyKxACxPSx1440W, etsysOidPhyKxPOExExtConn,
                 etsysOidPhyK6FanTraySlot, etsysOidPhyK10FanTraySlot,
                 etsysOidPhyKLineCardSlot, etsysOidPhyKFabricModuleSlot,
                 etsysOidPhyKK2008x0204xF1, etsysOidPhyKK2008x0204xF2,
                 etsysOidPhyKK2000x0000xF1, etsysOidPhyKK2000x0000xF2,
                 etsysOidPhyKT2006x0224, etsysOidPhyKG2001x0224,
                 etsysOidPhyKK2008x0204, etsysOidPhyK6Backplane,
                 etsysOidPhyK10Backplane."
 
    REVISION    "201010041255Z"  -- Mon Oct  4 12:55 UTC 2010
    DESCRIPTION "Updated the DESCRIPTION and Name for the
                 etsysOidPhySSAxACxPSx600W OID."
    
    REVISION    "201009081439Z"  -- Wed Sep  8 14:39 UTC 2010
    DESCRIPTION "Added the etsysOidPhyIncompatiblePluggable OID."
    
    REVISION    "201006231758Z"  -- Wed Jun 23 17:58 UTC 2010
    DESCRIPTION "Added the etsysOidDevA4H254x8F8T OID."
    
    REVISION    "201006101427Z"  -- Thu Jun 10 14:27 UTC 2010
    DESCRIPTION "Added the following OIDs:
                 etsysOidPhyMGBICxBX10xD, etsysOidPhyMGBICxBX10xU."

    REVISION    "201006031512Z"  -- Thu Jun  3 15:12 UTC 2010
    DESCRIPTION "Added the following OIDs:
                 etsysOidDevA4H124x24TX, etsysOidDevA4H124x24FX,
                 etsysOidDevA4H124x8F8T, etsysOidDevA4H124x24,
                 etsysOidDevA4H124x24P, etsysOidDevA4H124x48,
                 etsysOidDevA4H124x48P."
 
    REVISION    "201005041953Z"  -- Tue May  4 19:53 UTC 2010
    DESCRIPTION "Added the following OIDs:
                 etsysOidPhy10GBxLWxSFPP, etsysOidPhy10GBxLWxXFP,
                 etsysOidPhy10GBxLWx20, etsysOidPhy10GBxLWx10,
                 etsysOidPhy10GBxLWx05, etsysOidPhy10GBxLWx03."
 
    REVISION    "201003051353Z"  -- Fri Mar  5 13:53 UTC 2010
    DESCRIPTION "Added the etsysOidDevNACxV OID."

    REVISION    "200910261715Z"  -- Mon Oct 26 17:15 UTC 2009
    DESCRIPTION "Added the following OIDs:
                 etsysOidPhyNSAxFAN, etsysOidPhyNSAxACxPS,
                 etsysOidPhyN1xFAN, etsysOidPhyN1xACxPS."

    REVISION    "200910261530Z"  -- Mon Oct 26 15:30 UTC 2009
    DESCRIPTION "Modified the Name for the following OIDs:
                 etsysOidDevB5K125x48P2, etsysOidDevC5K125x48P2, 
                 etsysOidDevC5K175x24."

    REVISION    "200909302004Z"  -- Wed Sep 30 20:04 UTC 2009
    DESCRIPTION "Added the etsysOidPhySSAxFAN OID."

    REVISION    "200908271307Z"  -- Thu Aug 27 13:07 UTC 2009
    DESCRIPTION "Added the following OIDs:
                 etsysOidDevNACxAx10 and etsysOidDevNACxAx20."
    
    REVISION    "200908250112Z"  -- Tue Aug 25  1:12 UTC 2009
    DESCRIPTION "Added the following OIDs:
                 etsysOidDevB5G124x24, etsysOidDevB5G124x24P2, 
                 etsysOidDevB5G124x48, etsysOidDevB5G124x48P2, 
                 etsysOidDevB5K125x24, etsysOidDevB5K125x24P2, 
                 etsysOidDevB5K125x48, etsysOidDevB5K125x48P2, 
                 etsysOidDevC5G124x24, etsysOidDevC5G124x24P2, 
                 etsysOidDevC5G124x48, etsysOidDevC5G124x48P2, 
                 etsysOidDevC5K125x24, etsysOidDevC5K125x24P2, 
                 etsysOidDevC5K125x48, etsysOidDevC5K125x48P2, 
                 etsysOidDevC5K175x24."
 
    REVISION    "200907081537Z"  -- Wed Jul  8 15:37 UTC 2009
    DESCRIPTION "Added the etsysOidPhyConsolePortUsbMicroAB OID."

    REVISION    "200907021738Z"  -- Thu Jul  2 17:38 UTC 2009
    DESCRIPTION "Added the etsysOidPhyNOT1206x0112 OID."

    REVISION    "200906221944Z"  -- Mon Jun 22 19:44 UTC 2009
    DESCRIPTION "Added the etsysOidPhySOT1206x0112 OID."
    
    REVISION    "200904071602Z"  -- Tue Apr  7 16:02 UTC 2009
    DESCRIPTION "Added the following OIDs:
                 etsysOidPhyS8Backplane, etsysOidPhyS4Backplane,
                 etsysOidPhyS3Backplane, etsysOidPhyN5Backplane,
                 etsysOidPhyN3Backplane, etsysOidPhyN1Backplane."
    
    REVISION    "200903311713Z"  -- Tue Mar 31 17:13 UTC 2009
    DESCRIPTION "Added the following OIDs:
                 etsysOidDevSSAxT4068x0252, etsysOidDevSSAxT1068x0652, 
                 etsysOidDevSSAxG1018x0652, etsysOidDevS3, 
                 etsysOidDevS4, etsysOidDevS8, 
                 etsysOidPhyS3xCHASSIS, etsysOidPhyS4xCHASSIS, 
                 etsysOidPhyS8xCHASSIS, etsysOidPhySxFAN, 
                 etsysOidPhySxACxPS, etsysOidPhySxPOExPS, 
                 etsysOidPhySxPOEx4BAY, etsysOidPhySxPOEx8BAY, 
                 etsysOidPhySPowerSupplySlot, etsysOidPhySFanTraySlot, 
                 etsysOidPhySIOModuleSlot, etsysOidPhySFabricModuleSlot, 
                 etsysOidPhySPoEPowerSupplySlot, etsysOidPhySK1208x0808xF6, 
                 etsysOidPhyST4106x0348xF6, etsysOidPhyST1206x0848xF6, 
                 etsysOidPhySG1201x0848xF6, etsysOidPhySK1008x0816, 
                 etsysOidPhyST4106x0248, etsysOidPhyST4006x0272, 
                 etsysOidPhyST1206x0848, etsysOidPhySG4101x0248, 
                 etsysOidPhySG1201x0848, etsysOidPhySOptModType1Slot, 
                 etsysOidPhySOptModType2Slot, etsysOidPhySOK1208x0104, 
                 etsysOidPhySOK1208x0102, etsysOidPhySOK1208x0204, 
                 etsysOidPhySOG1201x0112, etsysOidPhyNN0100x0100xF2, 
                 etsysOidPhyNT4106x0248, etsysOidPhyNT4006x0272, 
                 etsysOidPhyNT1006x0448, etsysOidPhyNK1008x0408, 
                 etsysOidPhyNG1001x0448, etsysOidPhyNG4101x0248, 
                 etsysOidPhyNGNOptModSlot, etsysOidPhyNOK1208x0102, 
                 etsysOidPhyNOK1208x0104, etsysOidPhyNOG1201x0112, 
                 etsysOidPhySSAxACxPSx600W, etsysOidPhySSAxACxPSx1000W, 
                 etsysOidPhySSAPowerSupplySlot, etsysOidPhy10GBxERxSFPP,
                 etsysOidPhyUSBAPort, etsysOidPhyUSBMicroABPort."

    REVISION    "200903051358Z"  -- Thu Mar  5 13:58 UTC 2009
    DESCRIPTION "Added the etsysOidPhy7SxDNSAx01 OID."
    
    REVISION    "200901051508Z"  -- Mon Jan  5 15:08 UTC 2009
    DESCRIPTION "Added the following OIDs:
                 etsysOidPhy10GbExSRxSFPP, etsysOidPhy10GbExLRxSFPP,
                 etsysOidPhy10GbExLRMxSFPP, etsysOidPhy10GbExC01xSFPP,
                 etsysOidPhy10GbExC03xSFPP, etsysOidPhy10GbExC10xSFPP,
                 etsysOidPhy10GbExC20xSFPP, etsysOidPhySFPPNoConnector,
                 and etsysOidPhy10GbExLRMxXFP."

    REVISION    "200811171604Z"  -- Mon Nov 17 16:04 UTC 2008
    DESCRIPTION "Added the etsysOidPhy7SxC20N OID."
    
    REVISION    "200808131904Z"  -- Wed Aug 13 19:04 UTC 2008
    DESCRIPTION "Added the following OIDs:
                 etsysOidDevNACxAx2K and etsysOidDevNACxAx3K."
    
    REVISION    "200806101259Z"  -- Tue Jun 10 12:59 UTC 2008
    DESCRIPTION "Added the etsysOidDevC3K122x24P OID."
    
    REVISION    "200804241400Z"  -- Thu Apr 24 14:00 UTC 2008
    DESCRIPTION "Added the etsysOidPhy7SxNACGx01 OID."
    
    REVISION    "200803132058Z"  -- Thu Mar 13 20:58 UTC 2008
    DESCRIPTION "Modified the DESCRIPTION clauses for the following:
                 etsysOidDevG3G124x24, etsysOidDevG3G170x24,
                 etsysOidDevD2G124x12, etsysOidDevD2G124x12P,
                 etsysOidDevG3G124x24P."

    REVISION    "200801242008Z"  -- Thu Jan 24 20:08 UTC 2008
    DESCRIPTION "Added the etsysOidDevG3G124x24P OID."
    
    REVISION    "200801102009Z"  -- Thu Jan 10 20:09 UTC 2008
    DESCRIPTION "Added the etsysOidDev7SxNSNACGx01NPS OID."
    
    REVISION    "200710301910Z"  -- Tue Oct 30 19:10 UTC 2007
    DESCRIPTION "Added the etsysOidPhyMGBICxLC07 OID."
    
    REVISION    "200710151310Z"  -- Mon Oct 15 13:10 UTC 2007
    DESCRIPTION "Changed MGBIC-N-LC04 to MGBIC-LC04.
                 Changed MGBIC-N-LC05 to MGBIC-LC05."
 
    REVISION    "200708301808Z"  -- Thu Aug 30 18:08 UTC 2007
    DESCRIPTION "Added the etsysOidPhy7SxNSNACGx01xNPS OID."
    
    REVISION    "200708291516Z"  -- Wed Aug 29 15:16 UTC 2007
    DESCRIPTION "Added the following OIDs:
                 etsysOidPhy7S4280x19, etsysOidPhy2S4082x25
                 and etsysOidDevMatrixN1NAC."
    
    REVISION    "200706251822Z"  -- Mon Jun 25 18:22 UTC 2007
    DESCRIPTION "Added the etsysOidDevRBTx8500 OID."
    
    REVISION    "200706141825Z"  -- Thu Jun 14 18:25 UTC 2007
    DESCRIPTION "Added the following OIDs:
                 etsysOidDevD2G124x12 and etsysOidDevD2G124x12P."
    
    REVISION    "200706041543Z"  -- Mon Jun  4 15:43 UTC 2007
    DESCRIPTION "Added the following OIDs:
                 etsysOidDevG3G124x24 and etsysOidDevG3G170x24."
    
    REVISION    "200705291312Z"  -- Tue May 29 13:12 UTC 2007
    DESCRIPTION "Corrected DESCRIPTION clause for etsysOidPhyMGBICxLC05."
 
    REVISION    "200704201158Z"  -- Fri Apr 20 11:58 UTC 2007
    DESCRIPTION "Added the etsysOidDevSNSxNSSxA OID."
    
    REVISION    "200704161443Z"  -- Mon Apr 16 14:43 UTC 2007
    DESCRIPTION "Added the following OIDs:
                 etsysOidDevA2H123x24, etsysOidDevB3H124x24FX,
                 etsysOidDevC3H124x24FX, etsysOidDevC3K122x24,
                 etsysOidDevC3K172x24, etsysOidDevC3Kx2XFP."

    REVISION    "200704051532Z"  -- Thu Apr  5 15:32 UTC 2007
    DESCRIPTION "Updated the DESCRIPTION clause for the following:
                 etsysOidPhyMGBICxLC04

                 Added the following OIDs:
                 etsysOidPhyMGBICxLC05, etsysOidPhy7K4297x02,
                 etsysOidPhy7K4297x04, etsysOidPhy7KR4297x02,
                 etsysOidPhy7KR4297x04."

    REVISION    "200702271749Z"  -- Tue Feb 27 17:49 UTC 2007
    DESCRIPTION "Added the following OIDs:
                 etsysOidPhy10GbExZRxXFP, etsysOidPhy10GbExZWxXFP,
                 etsysOidPhy10GbExZR, etsysOidPhy10GbExZW."

    REVISION    "200701251558Z"  -- Thu Jan 25 15:58 UTC 2007
    DESCRIPTION "Updated the DESCRIPTION clause for the following:
                 etsysOidPhy10GbExSR, etsysOidPhy10GbExLR, 
                 etsysOidPhy10GbExER, etsysOidPhy10GbExLX4,
                 etsysOidPhy10GbExSW, etsysOidPhy10GbExLW,
                 etsysOidPhy10GbExEW.

                 Added the following OIDs:
                 etsysOidPhy10GbExSRxXFP, etsysOidPhy10GbExLRxXFP,
                 etsysOidPhy10GbExERxXFP, etsysOidPhy10GbExCX4xXFP,
                 etsysOidPhy10GbExCX4, etsysOidPhy10GbExSWxXFP,
                 etsysOidPhy10GbExLWxXFP, etsysOidPhy10GbExEWxXFP,
                 etsysOidPhy10GbExLX4xXFP."
                      
    REVISION    "200701232101Z"  -- Tue Jan 23 21:01 UTC 2007
    DESCRIPTION "Changed MGBIC-LC04 to MGBIC-N-LC04."
 
    REVISION    "200610311954Z"  -- Tue Oct 31 19:54 UTC 2006
    DESCRIPTION "Added the following OIDs:
                 etsysOidPhyNoXfp, etsysOidPhyMGBICxLC04."

    REVISION    "200609291258Z"  -- Fri Sep 29 12:58 UTC 2006
    DESCRIPTION "Added the etsysOidDevSNSxPCCxWBA OID."

    REVISION    "200609201451Z"  -- Wed Sep 20 14:51 UTC 2006
    DESCRIPTION "Added the following OIDs:
                 etsysOidDevSNSxTAGxLPA, etsysOidDevSNSxTAGxHPA,
                 etsysOidDevSNSxTAGxBASE, etsysOidDev7SxNSTAGx01."

    REVISION    "200608251502Z"  -- Fri Aug 25 15:02 UTC 2006
    DESCRIPTION "Added the following OIDs:
                 etsysOidPhy7Gx6MGBICxB, etsysOidPhy7Kx2XFPx6MGBIC,
                 etsysOidPhy7GR4280x19, etsysOidPhy7GR4270x12,
                 etsysOidPhy7GR4202x30, etsysOidPhy7KR4290x02."

    REVISION    "200608161344Z"  -- Wed Aug 16 13:44 UTC 2006
    DESCRIPTION "Changed Name of etsysOidPhy7G4082x25 to 2G4082-25."

    REVISION    "200608071231Z"  -- Mon Aug  7 12:31 UTC 2006
    DESCRIPTION "Added the following OIDs:
                 etsysOidDevI3H252x02, etsysOidPhyI3Hx12TX,
                 etsysOidPhyI3Hx4FXxMM, etsysOidPhyI3Hx8FXxMM,
                 etsysOidPhyI3Hx8TXx2FX."
    
    REVISION    "200608031357Z"  -- Thu Aug  3 13:57 UTC 2006
    DESCRIPTION "Added the following OIDs:
                 etsysOidDevC3G124x24, etsysOidDevC3G124x24P,
                 etsysOidDevC3G124x48, etsysOidDevC3G124x48P,
                 etsysOidDevB3G124x24, etsysOidDevB3G124x24P,
                 etsysOidDevB3G124x48, etsysOidDevB3G124x48P."

    REVISION    "200606191832Z"  -- Mon Jun 19 18:32 UTC 2006
    DESCRIPTION "Added etsysOidPhy7G4082x25 OID."

    REVISION    "200603091914Z"  -- Thu Mar  9 19:14 UTC 2006
    DESCRIPTION "Added the etsysOidPhyC2G170x24 OID."
    
    REVISION    "200602161442Z"  -- Thu Feb 16 14:42 UTC 2006
    DESCRIPTION "Added the following OIDs:
                 etsysOidPhy7SxDSNSA7x01NPS, etsysOidPhy7SxNSTAGx01xNPS,
                 etsysOidPhy9603805, etsysOidPhy9603806"

    REVISION    "200602092006Z"  -- Thu Feb  9 20:06 UTC 2006
    DESCRIPTION "Added the etsysOidDevA2H254x16 OID."
    
    REVISION    "200602062031Z"  -- Mon Feb  6 20:31 UTC 2006
    DESCRIPTION "Added the etsysOidPhyXxM8x01 OID."
    
    REVISION    "200511101958Z"  -- Thu Nov 10 19:58 UTC 2005
    DESCRIPTION "Added the following OIDs:
                 etsysOidPhyGigEthIntNEMPort, etsysOidPhy7SxDSNSA7x01,
                 etsysOidPhy7SxNSTAGx01."
    
    REVISION    "200510111442Z"  -- Tue Oct 11 14:42 UTC 2005
    DESCRIPTION "Added the etsysOidPhyXxGT16x00 OID."

    REVISION    "200509211603Z"  -- Wed Sep 21 16:03 UTC 2005
    DESCRIPTION "Added the etsysOidDevNSTAGxGE250xTX and
                 etsysOidDevNSTAGxGE250xTX OIDs."

    REVISION    "200508311822Z"  -- Wed Aug 31 18:22 UTC 2005
    DESCRIPTION "Added the etsysOidDevRBT4102 OID."

    REVISION    "200506211245Z"  -- Tue Jun 21 12:45 GMT 2005
    DESCRIPTION "Added the following OIDs:
                 etsysOidDevA2H124x24, etsysOidDevA2H124x24P,
                 etsysOidDevA2H124x48, etsysOidDevA2H124x48P,
                 etsysOidDevA2H124x24FX." 

    REVISION    "200504191849Z"  -- Tue Apr 19 18:49 GMT 2005
    DESCRIPTION "Added the respective part numbers to the description
                 clauses for the following Mini-GBIC OIDs:
                 etsysOidPhyMGBICxMT01, etsysOidPhyMGBICxMT09,
                 etsysOidPhyMGBICxLC01, etsysOidPhyMGBICxLC09,
                 etsysOidPhyMGBICx02, etsysOidPhyMGBICx08, and
                 etsysOidPhyMGBICxLC03."

    REVISION    "200504121714Z"  -- Tue Apr 12 17:14 GMT 2005
    DESCRIPTION "Added the etsysOidDevRBTSAxAA and etsysOidDevRBTSAxAB
                 OIDs."

    REVISION    "200502202350Z"  -- Sun Feb 20 23:50 GMT 2005
    DESCRIPTION "Added the etsysOidPhyC2G134x24P OID."

    REVISION    "200502101939Z"  -- Thu Feb 10 19:39 GMT 2005
    DESCRIPTION "Added the etsysOidPhyX16xC, etsysOidPhyX8xC,
                 etsysOidPhyX8Backplane, etsysOidPhyX4Backplane,
                 etsysOidPhyXxFan, etsysOidPhyXxAC, etsysOidPhyXxCMx00,
                 etsysOidPhyX4xCMFx160x00, etsysOidPhyX16xF640,
                 etsysOidPhyX8xF320, etsysOidPhyXxM2x00,
                 etsysOidPhyXxG32x00, etsysOidPhyXxT48x01,
                 etsysOidPhyXxM2x01, etsysOidPhyXxM4x01,
                 etsysOidPhyXxG20x01, etsysOidPhyXxG40x01,
                 etsysOidPhyXIOModuleSlot, etsysOidPhyXFanTraySlot,
                 etsysOidPhyXFabricModuleSlot, etsysOidPhyX16Backplane,
                 etsysOidPhyXPowerSupplySlot, etsysOidPhyX4xC,
                 etsysOidPhyXControlModuleSlot, etsysOidPhyXxT32x00
                 etsysOidPhySFPxGBIC, and etsysOidPhyXFPxGBIC OIDs."

    REVISION    "200501121802Z"  -- Wed Jan 12 18:02 GMT 2005
    DESCRIPTION "Added the etsysOidPhyB2G124x24, etsysOidPhyB2G124x48,
                 etsysOidPhyB2G124x48P, etsysOidPhyB2H124x48,
                 etsysOidPhyB2H124x48P, etsysOidPhyB2G124x24P,
                 etsysOidPhyB2H124x24, etsysOidPhyB2H124x24P, and
                 etsysOidPhyB2H124x24FX OIDs."

    REVISION    "200501111956Z"  -- Tue Jan 11 19:56 GMT 2005
    DESCRIPTION "Added the etsysOidPhy7C117, etsysOidPhy7C115xP,
                 etsysOidPhy7C113, etsysOidPhy7C111,
                 etsysOidPhyN1ModuleSlot, etsysOidDevMatrixN1, and
                 etsysOidDevMatrixN1Gold OIDs."

    REVISION    "200408241329Z"  -- Tue Aug 24 13:29 GMT 2004
    DESCRIPTION "Added the etsysOidOtherLicenseKeyId OID."

    REVISION    "200408111924Z"  -- Wed Aug 11 19:24 GMT 2004
    DESCRIPTION "Added the etsysOidDevMatrixX4, etsysOidDevMatrixX8,
                 and etsysOidDevMatrixX16 OIDs."

    REVISION    "200408042118Z"  -- Wed Aug  4 21:18 GMT 2004
    DESCRIPTION "Added the etsysOidPhyN5PoEPoEPowerSupplySlot OID."

    REVISION    "200406011942Z"  -- Tue Jun  1 19:42 GMT 2004
    DESCRIPTION "Added the etsysOidPhy7Gx6MGBICxA OID."

    REVISION    "200405181553Z"  -- Tue May 18 15:53 GMT 2004
    DESCRIPTION "Added the etsysOidPhyV2H124x24FX OID."

    REVISION    "200404161915Z"  -- Fri Apr 16 19:15 GMT 2004
    DESCRIPTION "Added the etsysOidDevMatrixN5PoEGold,
                 etsysOidDevMatrixN5PoEPlatinum, etsysOidPhyNxPOE,
                 etsysOidPhyMGBICxLC03, etsysOidPhyNxPOEx1200W,
                 etsysOidPhyNxPOEPowerSupplySlot, etsysOidPhy7C105xP,
                 etsysOidPhy7C205x1, etsysOidPhyN5PoEPowerSupplySlot,
                 etsysOidPhy7C405, etsysOidPhyN5PoEFanTraySlot, and
                 etsysOidPhyN5PoEModuleSlot OIDs."

    REVISION    "200404021838Z"  -- Fri Apr  2 18:38 GMT 2004
    DESCRIPTION "Added the etsysOidPhy7G4202x72, etsysOidPhy7G4205x72,
                 etsysOidPhy7G4282x49, etsysOidPhy7G4285x49,
                 etsysOidPhy4G4202x72, etsysOidPhy4G4205x72,
                 etsysOidPhy4G4282x49, and etsysOidPhy4G4285x49 OIDs."

    REVISION    "200403191955Z"  -- Fri Mar 19 19:55 GMT 2004
    DESCRIPTION "Added the etsysOidDev2G4072x52 OID."

    REVISION    "200403151931Z"  -- Mon Mar 15 19:31 GMT 2004
    DESCRIPTION "Added the etsysOidDevXSRx1205, etsysOidDevXSRx1220,
                 etsysOidDevXSRx1225, etsysOidDevXSRx1230, and
                 etsysOidDevXSRx1235 OIDs, and deprecated the
                 etsysOidDevXSRx1100 OID."

    REVISION    "200403151711Z"  -- Mon Mar 15 17:11 GMT 2004
    DESCRIPTION "Added the etsysOidPhyC2G124x24, etsysOidPhyC2G124x48,
                 etsysOidPhyC2K122x24, etsysOidPhyC2H124x48P, and
                 etsysOidPhyC2G124x48P OIDs, updated the description
                 for the etsysOidPhyC2H124x48 OID, and deprecated a
                 number of OIDs for the Matrix C2 and C5 products."

    REVISION    "200402261455Z"  -- Thu Feb 26 14:55 GMT 2004
    DESCRIPTION "Added the etsysOidDevDragonIdsAppliance OID."

    REVISION    "200402191419Z"  -- Thu Feb 19 14:19 GMT 2004
    DESCRIPTION "Added the etsysOidPhy7G4280x19 OID."

    REVISION    "200402172131Z"  -- Tue Feb 17 21:31 GMT 2004
    DESCRIPTION "Added the etsysOidPhy4H4285x49 and
                 etsysOidPhy7H4385x49 OIDs."

    REVISION    "200401271643Z"  -- Tue Jan 27 16:43 GMT 2004
    DESCRIPTION "Added the etsysOidPhyNoXenpak OID.  Updated the
                 description clause for the etsysOidDevRBTR4xA OID,
                 it is being used as the OID for the AP3000."

    REVISION    "200312121713Z"  -- Fri Dec 12 17:13 GMT 2003
    DESCRIPTION "Added the etsysOidDevDFEPlatinumRouter and
                 etsysOidDevDFEGoldRouter OIDs."

    REVISION    "200310231527Z" -- Thu Oct 23 15:27 GMT 2003
    DESCRIPTION "Added the etsysOidDevMatrixE7Gold,
                 etsysOidDevMatrixN7Gold, and etsysOidDevMatrixN3Gold
                 OIDs.  Modified the description clauses for the
                 etsysOidDevMatrixE7, etsysOidDevMatrixN7, and 
                 etsysOidDevMatrixN3 OIDs."

    REVISION    "200310141504Z"  -- Tue Oct 14 15:04 GMT 2003
    DESCRIPTION "Added the etsysOidPhy7H4382x25 OID."

    REVISION    "200309192044Z"  -- Fri Sep 19 20:44 GMT 2003
    DESCRIPTION "Added the etsysOidDevRBTR4xA OID."

    REVISION    "200309171426Z"  -- Wed Sep 17 14:26 GMT 2003
    DESCRIPTION "Added etsysOidPhy4H4203x72, etsysOidPhy4H4283x49,
                 etsysOidPhy4G4282x41, etsysOidPhy4G4202x60,
                 etsysOidPhy4H4282x49, etsysOidPhy4H4202x72, and
                 etsysOidPhy4H4284x49 OIDs."

    REVISION    "200308292100Z"  -- Fri Aug 29 21:00 GMT 2003
    DESCRIPTION "Corrected descriptions for etsysOidPhyMGBICxMT01,
                 etsysOidPhyMGBICxLC01, and etsysOidPhyMGBICxLC09."

    REVISION    "200308191932Z"  -- Tue Aug 19 19:32 GMT 2003
    DESCRIPTION "Added etsysOidPhyMGBICx02 and etsysOidPhyMGBICx08
                 OIDs."

    REVISION    "200307301643Z"  -- Wed Jul 30 16:43 GMT 2003
    DESCRIPTION "Added the etsysOidPhyRj45ConsolePort OID."

    REVISION    "200307281636Z"  -- Mon Jul 28 16:36 GMT 2003
    DESCRIPTION "Added the etsysOidPhyMGBICNoConnector,
                 etsysOidPhyN7PowerSupplySlot, etsysOidPhyN7FanTraySlot,
                 etsysOidPhyN7ModuleSlot, etsysOidPhyN3PowerSupplySlot,
                 etsysOidPhyN3FanTraySlot, etsysOidPhyN3ModuleSlot,
                 etsysOidPhyE7PowerSupplySlot, etsysOidPhyE7FanTraySlot,
                 and etsysOidPhyE7ModuleSlot OIDs."

    REVISION    "200307171353Z"  -- Thu Jul 17 13:53 GMT 2003
    DESCRIPTION "Added the etsysOidDevRBTR3xA OID."

    REVISION    "200307092041Z"  -- Wed Jul  9 20:41 GMT 2003
    DESCRIPTION "Added the etsysOidPhy7G4202x60 and etsysOidPhy7G4282x41
                 OIDs."

    REVISION    "200307021725Z"  -- Wed Jul  2 17:25 GMT 2003
    DESCRIPTION "Changed the status of etsysOidPhyNIMxETHxTGRx01 to
                 deprecated and added the etsysOidPhyNIMxETHRx01,
                 etsysOidPhyNIMxFIBRx01, and etsysOidPhyNIMxDIRELAYx02
                 OIDs."

    REVISION    "200306051509Z"  -- Thu Jun  5 15:09 GMT 2003
    DESCRIPTION "Added the etsysOidPhyE1FxdAcPwrSup OID."

    REVISION    "200306031308Z"  -- Tue Jun  3 13:08 GMT 2003
    DESCRIPTION "Added the etsysOidPhy1Hx8FX OID."

    REVISION    "200305142108Z"  -- Wed May 14 21:08 GMT 2003
    DESCRIPTION "Added the etsysOidDevV2H124x24, etsysOidPhyV2G121x1,
                 etsysOidPhyV2G112x2, etsysOidPhyV2G151x1M, and
                 etsysOidPhyV2G151x1S OIDs."

    REVISION    "200305072048Z"  -- Wed May  7 20:48 GMT 2003
    DESCRIPTION "Added etsysOidDevC1G124x24 OID."

    REVISION    "200304252032Z"  -- Fri Apr 25 20:32 GMT 2003
    DESCRIPTION "Added etsysOidDev1H582x25 and etsysOidDev1G587x09
                 OIDs."

    REVISION    "200304171358Z"  -- Thu Apr 17 13:58 GMT 2003
    DESCRIPTION "Added etsysOidPhy7H4284x49 OID."

    REVISION    "200304171358Z"  -- Thu Apr 17 13:58 GMT 2003
    DESCRIPTION "Added etsysOidPhy7H4383x49 OID."

    REVISION    "200303051535Z"  -- Wed Mar  5 15:35 GMT 2003
    DESCRIPTION "Added the OIDs, etsysOidPhy 234-244, and etsysOidDevice
                 54-58, for a number of XSR branch and regional office
                 routers, and associated network interface modules."

    REVISION    "200302241506Z"  -- Mon Feb 24 15:06 GMT 2003
    DESCRIPTION "Added the OIDs etsysOidPhy7G4275x12 and
                 etsysOidPhy7G4270x09."

    REVISION    "200212312051Z"  -- Tue Dec 31 20:51 GMT 2002
    DESCRIPTION "Added the OIDs etsysOidDevMatrixN3 and
                 etsysOidDevMatrixN7.  Obsoleted chassis, fan
                 tray, and power supply OIDs related to the
                 Matrix E3 products."

    REVISION    "200212311920Z"  -- Tue Dec 31 19:20 GMT 2002
    DESCRIPTION "Added the OIDs etsysOidPhy7C107, etsysOidPhy7C103,
                 etsysOidPhy7C203x1, and etsysOidPhy7C403, for the
                 Matrix N3 and N7 products."

    REVISION    "200212131926Z"  -- Fri Dec 13 19:26 GMT 2002
    DESCRIPTION "Added the etsysOidDevMatrixE7 OID and updated the
                 CONTACT-INFO clause."

    REVISION    "200212031420Z"  -- Tue Dec  3 14:20 GMT 2002
    DESCRIPTION "Added the OIDs etsysOidPhy7G4270x10 and
                 etsysOidPhy7H4202x72 for the Matrix E7
                 products."

    REVISION    "200210291413Z"  -- Tue Oct 29 14:13 GMT 2002
    DESCRIPTION "Added a number of OIDs for the Matrix C1, C2, and
                 C5 series products.  etsysOidDevice 48-50 and
                 etsysOidPhy 211-225."

    REVISION    "200208302105Z"  -- Fri Aug 30 21:05 GMT 2002
    DESCRIPTION "Corrected the descriptions for a number of the
                 WAN NIMs.  etsysOidPhy 174, 178, 179, and 180."

    REVISION    "200208291923Z"  -- Thu Aug 29 19:23 GMT 2002
    DESCRIPTION "Added etsysOidPhyNIMxBRIxSTx01,
                 etsysOidPhyNIMxBRIxSTx02, etsysOidPhyNIMxBRIxUx01
                 and etsysOidPhyNIMxBRIxUx02."

    REVISION    "200208271503Z"  -- Tue Aug 27 15:03 GMT 2002
    DESCRIPTION "Added etsysOidDevVHx2202GT."

    REVISION    "200207121421Z"  -- Fri Jul 12 14:21 GMT 2002
    DESCRIPTION "Added etsysOidPhyGPIMx02."

    REVISION    "200206272109Z"  -- Thu Jun 27 21:09 GMT 2002
    DESCRIPTION "Deprecated etsysOidDevVHxSMGMTxL3.  Added
                 etsysOidDevVHx2402S2, etsysOidDevVHxSMGMT2,
                 etsysOidDevVHxRTM-L3, etsysOidPhy6C203x1,
                 etsysOidPhy6C403, and etsysOidPhy6C103."

    REVISION    "200206061841Z"  -- Thu Jun  6 18:41 GMT 2002
    DESCRIPTION "Added etsysOidIEEE8023adLagInterface."

    REVISION    "200205301711Z"  -- Thu May 30 17:11 GMT 2002
    DESCRIPTION "Added etsysOidPhy6C207x3."

    REVISION    "200204231943Z"  -- Tue Apr 23 19:43 GMT 2002
    DESCRIPTION "Added etsysOidDevXSRx1850.  Changed name comment
                 for etsysOidDevXPx1000 from XSG-1805 to XSR-1805.
                 Deprecated etsysOidPhy7H4303x48, etsysOidPhy7G4202x12,
                 and etsysOidPhy7G4370x08."

    REVISION    "200204082035Z"  -- Mon Apr  8 20:35 GMT 2002
    DESCRIPTION "Added etsysOidPhy7G4202x30, etsysOidPhy7Gx6MGBIC,
                 etsysOidPhy7H4382x49, etsysOidPhy7K4290x02,
                 etsysOidPhy7H4204x48, and etsysOidPhy2H412x49R
                 OIDs for Manhattan."

    REVISION    "200204021856Z"  -- Tue Apr  2 18:56 GMT 2002
    DESCRIPTION "Added etsysOidPhyMPC8240 and etsysOidPhyMPC8245
                 OIDs for the E1."

    REVISION    "200203142045Z"  -- Thu Mar 14 20:45 GMT 2002
    DESCRIPTION "Added etsysOidPhyER16xOS26x01 for ER16-OS26-01"

    REVISION    "200201141903Z"  -- Mon Jan 14 19:03 GMT 2002
    DESCRIPTION "Corrected my spelling mistakes in the following
                 description and modified the description of the
                 etsysOidPhyPortSlot object."

    REVISION    "200201091819Z"  -- Wed Jan  9 18:19 GMT 2002
    DESCRIPTION "Made a number of syntactic corrections to the
                 descriptions of various objects and deprecated
                 a number of duplicate objects.  etsysOidPhyPortSlot,
                 etsysOidPhy1000BASET, etsysOidPhy10100T, and 
                 etsysOidPhy6SSRLCGigEthBkplnPort were all deprecated."

    REVISION    "200112191633Z"  -- Wed Dec 19 16:33 GMT 2001
    DESCRIPTION "Added OIDs for the Frame Transfer Matrix
                 backplanes used in the E5, E6, and E7 chassis."

    REVISION    "200112132013Z"  -- Thu Dec 13 20:13 GMT 2001
    DESCRIPTION "Added OIDs for ER16-HFX31-24, ER16-HFX39-24,
                 ER16-GTX32-04, ER16-GTX32-08, SSR-GTX32-04,
                 SSR-GSX31-04, and SSR-GLX39-04, and made a
                 number of changes to prior Xp OIDs."

    REVISION    "200111091618Z"
    DESCRIPTION "Added OID for 6G302-06.
                 Removed duplicate Enterasys address information.
                 Stripped all of the CodeName, Requester, and
                 Comments comments from the MIB.  These will now
                 be entered as comments into the source code
                 repository."

    REVISION    "200111082001Z"
    DESCRIPTION "Added OID for VH-8G02S."

    REVISION    "200109261800Z"
    DESCRIPTION "Changed names of 1H152-51, 1G154-09, 1G276-13, 1H-2TX.
                 Added 136 Phy OIDs for the X-Pedition products,
                 needed for Entity MIB support.
                 Added Device OID for XP-2400 and Phy OIDs for XP NIMs."

    REVISION    "200108011230Z"
    DESCRIPTION "Added OIDs for ANG-3000, ANG-7000."

    REVISION    "200107261730Z"
    DESCRIPTION "Added OIDs for ANG-1102, ANG-1105."

    REVISION    "200107121930Z"
    DESCRIPTION "Added OID for VH-SMGMT-L3."

    REVISION    "200106261900Z"
    DESCRIPTION "Added OIDs for ANG-2000, also 1H152-50, 1G154-09,
                 1G276-13, and associated option modules."

    REVISION    "200105031300Z"
    DESCRIPTION "Added OIDs for 10 GbE port types."

    REVISION    "200104181500Z"
    DESCRIPTION "Added OID for XP-1000."

    REVISION    "200104021700Z"
    DESCRIPTION "Added OID for VH-8TX1MF."

    REVISION    "200103301500Z"
    DESCRIPTION "Added OID for RBTR2-A."

    REVISION    "200103011400Z"
    DESCRIPTION "Added IMPORT of OBJECT-IDENTITY from SNMPv2-SMI.
                 Fixes error reported by some compilers."

    REVISION    "200102221600Z"
    DESCRIPTION "Changed names of 5H162-50, 5H163-50."

    REVISION    "200012201900Z"
    DESCRIPTION "Added OIDs for 5H162-50, 5H163-50."

    REVISION    "200011092100Z"
    DESCRIPTION "Added OIDs for VH-2402-L3, VH-8G-L3.  Standardized comment
                 fields of OIDs for which a name change has been requested.
                 These are etsysOidDevice 9, 10, 11, 18, 19, 20 and 21."

    REVISION    "200010171616Z"
    DESCRIPTION "Addition of Matrix E5 frame, power supplies, fans,
                 and modules.  Addition of Matrix E7 frame, power supplies, 
                 fans, and modules.  Deprecated the etsysOidDevVG4x3DES."

    REVISION    "200009291900Z"
    DESCRIPTION "Many editorial changes. Made OBJECT IDENTIFIERS
                 into OBJECT-IDENTITY macro invocations."

    REVISION    "200005190000Z"
    DESCRIPTION "Add VG6 IP Tunnel/VPN box."

    REVISION    "200005170010Z"
    DESCRIPTION "Add support for more 6 series blades."

    REVISION    "200005170000Z"
    DESCRIPTION "VG4-3DES Ethernet+2 port SOHO router."

    REVISION    "200005110000Z"
    DESCRIPTION "Add OIDs for 9E521, deprecate duplicate for 6E308."

    REVISION    "200005010000Z"
    DESCRIPTION "Add OIDs for 6H202, 6E308."

    REVISION    "200004270000Z"
    DESCRIPTION "Add OIDs for E7 blades."

    REVISION    "200003310000Z"
    DESCRIPTION "Add OIDs for ELS products."

    REVISION    "200003220000Z"
    DESCRIPTION "Add OID for Matrix E7."

    REVISION    "200003161800Z"
    DESCRIPTION "Add requests received on March 15-16, 2000."

    REVISION    "200003160000Z"
    DESCRIPTION "The initial version of this MIB module."
    ::= { etsysModules 2 }

--  This part of the OID tree is used for OID assignments to 
--  Enterasys devices that are directly SNMP manageable.  All
--  devices under this branch should be directly accessible by
--  a unique IP address that is specific to that device.
--  Objects under this branch may include but are not limited to:
--
--     o repeaters
--     o switches
--     o routers
--     o "orphan" HSIMs (i.e. directly SNMP manageable HSIMs)
--
--  Values under this branch would be suitable for returning for MIB2
--  sysObjectID as defined in RFC2863.

etsysOidDevice OBJECT IDENTIFIER ::= { etsysOids 1 }

etsysOidDevEmpty OBJECT-IDENTITY
    STATUS      current
    DESCRIPTION
        "Reserved."
    ::= { etsysOidDevice 1 }

etsysOidDev6G306x06 OBJECT-IDENTITY
    STATUS      current
--  Name        "6G306-06"
--  Date        "200003160000Z"
    DESCRIPTION
        "Enterasys 6 port 100BASE-X Gigabit Ethernet module with GPIM 
         connectors."
    ::= { etsysOidDevice 2 }

etsysOidDev6H302x48 OBJECT-IDENTITY
    STATUS      current
--  Name        "6H302-48"
--  Date        "200003160000Z"
    DESCRIPTION
        "Enterasys 48 port RJ45 100BASE-TX Fast Ethernet module."
    ::= { etsysOidDevice 3 }

etsysOidDev6H303x48 OBJECT-IDENTITY
    STATUS      current
--  Name        "6H303-48"
--  Date        ""
    DESCRIPTION
        "Enterasys 48 port RJ21 100BASE-TX Fast Ethernet module."
    ::= { etsysOidDevice 4 }

etsysOidDev6H352x25 OBJECT-IDENTITY
    STATUS      current
--  Name        "6H352-25"
--  Date        "200003160000Z"
    DESCRIPTION
        "Enterasys 24 port RJ45 100BASE-TX Fast Ethernet module with 1 
         VHSIM uplink."
    ::= { etsysOidDevice 5 }

etsysOidDev6H308x24 OBJECT-IDENTITY
    STATUS      current
--  Name        "6H308-24"
--  Date        "200003160000Z"
    DESCRIPTION
        "Enterasys 24 port MT-RJ MMF 100BASE-FX Fast Ethernet module."
    ::= { etsysOidDevice 6 }

etsysOidDev6E308x24 OBJECT-IDENTITY
    STATUS      current
--  Name        "6E308-24"
--  Date        "200003160000Z"
    DESCRIPTION
        "Enterasys 24 port MT-RJ MMF 10BASE-FL Ethernet module."
    ::= { etsysOidDevice 7 }

etsysOidDev6C107 OBJECT-IDENTITY
    STATUS      current
--  Name        "6C107"
--  Date        "200003220000Z"
    DESCRIPTION
        "SNMP Agent for the Enterasys Matrix E7 Chassis."
    ::= { etsysOidDevice 8 }

etsysOidDevEls1000x8SX OBJECT-IDENTITY
    STATUS      current
--  Name        "VH-8G"
--  Date        "200003310000Z"
    DESCRIPTION
        "Enterasys 8 port SC 1000BASE-SX Gigabit Ethernet standalone."
    ::= { etsysOidDevice 9 }

etsysOidDevEls100x48TX2M OBJECT-IDENTITY
    STATUS      current
--  Name        "VH-4802"
--  Date        "200003310000Z"
    DESCRIPTION
        "Enterasys 48 port RJ45 100BASE-TX Fast Ethernet standalone with 
         2 Gigabit Ethernet uplinks."
    ::= { etsysOidDevice 10 }

etsysOidDevEls100x24TX2M OBJECT-IDENTITY
    STATUS      current
--  Name        "VH-SMGMT"
--  Date        "200003310000Z"
    DESCRIPTION
        "Enterasys 24 port RJ45 100BASE-TX Fast Ethernet standalone with
         2 expansion slots."
    ::= { etsysOidDevice 11 }

etsysOidDevDepricated001 OBJECT-IDENTITY
    STATUS      deprecated
--  Name        ""
--  Date        "200005110000Z"
    DESCRIPTION
        "Duplicate request."
    ::= { etsysOidDevice 12 }

etsysOidDev6H308x48 OBJECT-IDENTITY
    STATUS      current
--  Name        "6H308-48"
--  Date        "200004270000Z"
    DESCRIPTION
        "Enterasys 48 port MMF MT-RJ 100BASE-FX Fast Ethernet module."
    ::= { etsysOidDevice 13 }

etsysOidDev6E308x48 OBJECT-IDENTITY
    STATUS      current
--  Name        "6E308-48"
--  Date        "200005010000Z"
    DESCRIPTION
        "Enterasys 48 port MT-RJ 10BASE-FX Ethernet module."
    ::= { etsysOidDevice 14 }

etsysOidDev6H202x48 OBJECT-IDENTITY
    STATUS      current
--  Name        "6H202-48"
--  Date        "200005010000Z"
    DESCRIPTION
        "Enterasys 48 port RJ45 100BASE-TX Fast Ethernet module."
    ::= { etsysOidDevice 15 }

etsysOidDev9E531x24 OBJECT-IDENTITY
    STATUS      current
--  Name        "9E531-24"
--  Date        "200005110000Z"
    DESCRIPTION
        "Enterasys 24 port MT-RJ 10BASE-FL Ethernet module."
    ::= { etsysOidDevice 16 }

etsysOidDevVG4x3DES OBJECT-IDENTITY
    STATUS      deprecated
--  Name        "VG4-3DES"
--  Date        "200005170000Z"
    DESCRIPTION
        "Enterasys 1 port RJ45 100BASE-TX router with 2 WAN SPIM 
         connectors.  Small Office Home Office (SOHO) Ethernet/WAN 
         router with VPN. "
    ::= { etsysOidDevice 17 }

etsysOidDev6H002x48 OBJECT-IDENTITY
    STATUS      current
--  Name        "5H102-48"
--  Date        "200005170000Z"
    DESCRIPTION
        "Enterasys 48 port RJ45 100BASE-TX Fast Ethernet module."
    ::= { etsysOidDevice 18 }

etsysOidDev6H003x48 OBJECT-IDENTITY
    STATUS      current
--  Name        "5H103-48"
--  Date        "200005170000Z"
    DESCRIPTION
        "Enterasys 48 port RJ21 100BASE-TX Fast Ethernet module."
    ::= { etsysOidDevice 19 }

etsysOidDev6G066x06 OBJECT-IDENTITY
    STATUS      current
--  Name        "5G106-06"
--  Date        "200005170000Z"
    DESCRIPTION
        "Enterasys 4 port 1000BASE-SX Gigabit Ethernet module with 2 
         GBIC Gigabit Ethernet uplinks."
    ::= { etsysOidDevice 20 }

etsysOidDev6G063x06 OBJECT-IDENTITY
    STATUS      current
--  Name        "5G102-06"
--  Date        "200005170000Z"
    DESCRIPTION
        "Enterasys 6 port RJ45 1000BASE-T Gigabit Ethernet Module."
    ::= { etsysOidDevice 21 }

etsysOidDevVG6 OBJECT-IDENTITY
    STATUS      current
--  Name        "VG6"
--  Date        "200005190000Z"
    DESCRIPTION
        "Enterasys mid-range VPN gateway with IP Security, L2TP, AAA, 
         IP routing, IP-in-IP tunnels."
    ::= { etsysOidDevice 22 }

etsysOidDevER16 OBJECT-IDENTITY
    STATUS      current
--  Name        "ER16"
--  Date        "200008020000Z"
    DESCRIPTION
        "Enterasys 32 port SmartSwitch Router."
    ::= { etsysOidDevice 23 }

etsysOidDev5SSRMx02 OBJECT-IDENTITY
    STATUS      current
--  Name        "5SSRM-02"
--  Date        "200010020000Z"
    DESCRIPTION
        "Enterasys Advanced Router Module for the Matrix E5 chassis."
    ::= { etsysOidDevice 24 }

etsysOidDevVHx8TX1UM OBJECT-IDENTITY
    STATUS      current
--  Name        "VH-8TX1UM"
--  Date        "200010050000Z"
    DESCRIPTION
        "Enterasys 8 port RJ45 100BASE-TX standalone with 1 SMF 
         100BASE-FX port uplink."
    ::= { etsysOidDevice 25 }

etsysOidDevVHx2402xL3 OBJECT-IDENTITY
    STATUS      current
--  Name        "VH-2402-L3"
--  Date        "200011092100Z"
    DESCRIPTION
        "Enterasys 24 port RJ45 10/100 Fast Ethernet standalone
         L2/L3 switch with one uplink slot."
    ::= { etsysOidDevice 26 }

etsysOidDevVHx8GxL3 OBJECT-IDENTITY
    STATUS      current
--  Name        "VH-8G-L3"
--  Date        "200011092100Z"
    DESCRIPTION
        "Enterasys 8 port Gigabit Ethernet standalone L2/L3 switch,
         with 6 1000BASE-SX ports and 2 GBIC-style uplinks."
    ::= { etsysOidDevice 27 }

etsysOidDev5H162x50 OBJECT-IDENTITY
    STATUS      current
--  Name        "5H152-50"
--  Date        "200012201900Z"
    DESCRIPTION
        "Enterasys 48 port 100BASE-TX Fast Ethernet module with RJ45
         connectors and one slot for an optional two port Gigabit
         Ethernet uplink module."
    ::= { etsysOidDevice 28 }

etsysOidDev5H163x50 OBJECT-IDENTITY
    STATUS      current
--  Name        "5H153-50"
--  Date        "200012201900Z"
    DESCRIPTION
        "Enterasys 48 port 100BASE-TX Fast Ethernet module with RJ21
         connectors and one slot for an optional two port Gigabit
         Ethernet uplink module."
    ::= { etsysOidDevice 29 }

etsysOidDevRBTR2xA OBJECT-IDENTITY
    STATUS      current
--  Name        "RBTR2-A"
--  Date        "200103301500Z"
    DESCRIPTION
        "Enterasys wireless Access Point platform, provides Layer 2
         switched connection between 100BASE-TX wired Ethernet
         and 802.11 wireless LANs.  Supports two 802.11a or 802.11b
         radio links."
    ::= { etsysOidDevice 30 }

etsysOidDevVHx8TX1MF OBJECT-IDENTITY
    STATUS      current
--  Name        "VH-8TX1MF"
--  Date        "200104021700Z"
    DESCRIPTION
        "Enterasys 8 port RJ45 100BASE-TX standalone with
         1 MMF SC port uplink."
    ::= { etsysOidDevice 31 }

etsysOidDevXPx1000 OBJECT-IDENTITY
    STATUS      current
--  Name        "XSR-1805"
--  Date        "200104181500Z"
    DESCRIPTION
        "Enterasys Branch Router with 2 100BASE-TX Ethernet ports and
         two slots for optional WAN modules (T1/E1, ISDN, etc.)."
    ::= { etsysOidDevice 32 }

etsysOidDevANGx2000 OBJECT-IDENTITY
    STATUS      current
--  Name        "ANG-2000"
--  Date        "200106261900Z"
    DESCRIPTION
        "Enterasys integrated Router/Firewall/VPN Gateway."
    ::= { etsysOidDevice 33 }

etsysOidDev1H152x50 OBJECT-IDENTITY
    STATUS      current
--  Name        "1H582-51"
--  Date        "200106261900Z"
    DESCRIPTION
        "Enterasys 48 port 100BASE-TX Fast Ethernet standalone switch
         with 1 slot for optional interface modules."
    ::= { etsysOidDevice 34 }

etsysOidDev1G154x09 OBJECT-IDENTITY
    STATUS      current
--  Name        "1G582-09"
--  Date        "200106261900Z"
    DESCRIPTION
        "Enterasys 6 port 1000BASE-X Gigabit Ethernet standalone switch
         with 3 slots for optional interface modules."
    ::= { etsysOidDevice 35 }

etsysOidDev1G276x13 OBJECT-IDENTITY
    STATUS      current
--  Name        "1G694-13"
--  Date        "200106261900Z"
    DESCRIPTION
        "Enterasys 12 port 1000BASE-X Gigabit Ethernet standalone switch
         with a 10 Gigabit Ethernet uplink."
    ::= { etsysOidDevice 36 }

etsysOidDevVHxSMGMTxL3 OBJECT-IDENTITY
    STATUS      deprecated
--  Name        "VH-SMGMT-L3"
--  Date        "200107121930Z"
    DESCRIPTION
        "Enterasys L2/L3 management card for Vertical Horizon products."
    ::= { etsysOidDevice 37 }

etsysOidDevANGx1102 OBJECT-IDENTITY
    STATUS      current
--  Name        "ANG-1102"
--  Date        "200107261730Z"
    DESCRIPTION
        "Enterasys 2 port SOHO VPN Gateway."
    ::= { etsysOidDevice 38 }

etsysOidDevANGx1105 OBJECT-IDENTITY
    STATUS      current
--  Name        "ANG-1105"
--  Date        "200107261730Z"
    DESCRIPTION
        "Enterasys 5 port SOHO VPN Gateway."
    ::= { etsysOidDevice 39 }

etsysOidDevANGx3000 OBJECT-IDENTITY
    STATUS      current
--  Name        "ANG-3000"
--  Date        "200108011230Z"
    DESCRIPTION
        "Enterasys VPN Server for up to 500 concurrent connections."
    ::= { etsysOidDevice 40 }

etsysOidDevANGx7000 OBJECT-IDENTITY
    STATUS      current
--  Name        "ANG-7000"
--  Date        "200108011230Z"
    DESCRIPTION
        "Enterasys VPN Server for up to 5000 concurrent connections."
    ::= { etsysOidDevice 41 }

etsysOidDevXPx2400 OBJECT-IDENTITY
    STATUS      current
--  Name        "XP-2400"
--  Date        "200109261800Z"
    DESCRIPTION
        "Enterasys router with 16 100BASE-TX ports and 2 expansion slots."
    ::= { etsysOidDevice 42 }

etsysOidDevVHx8G02S OBJECT-IDENTITY
    STATUS      current
--  Name        "VH-8G02S"
--  Date        "200111012001Z"
    DESCRIPTION
        "Enterasys 8 port MMF 1000BASE-SX layer 2 switch with SC connectors."
    ::= { etsysOidDevice 43 }

etsysOidDev6G302x06 OBJECT-IDENTITY
    STATUS      current
--  Name        "6G302-06"
--  Date        "200111091618Z"
    DESCRIPTION
        "Enterasys 6 port RJ45 1000BASE-T Ethernet module."
    ::= { etsysOidDevice 44 }

etsysOidDevXSRx1850 OBJECT-IDENTITY
    STATUS      current
--  Name        "XSR-1850"
--  Date        "200204231932Z"  - Tue Apr 23 19:32 GMT 2002
    DESCRIPTION
        "Enterasys high performance security hardened branch office
         router / VPN device with 2 100BASE-TX Ethernet interfaces
         and two slots for optional WAN modules."
    ::= { etsysOidDevice 45 }

etsysOidDevVHx2402S2 OBJECT-IDENTITY
    STATUS      current
--  Name        "VH-2402S2"
--  Date        "200206271810Z"  - Thu Jun 27 18:10 GMT 2002
    DESCRIPTION
        "Enterasys 24 port RJ45 100BASE-TX stackable Fast Ethernet
         layer 2 switch with 2 uplink slots."
    ::= { etsysOidDevice 46 }

etsysOidDevVHx2202GT OBJECT-IDENTITY
    STATUS      current
--  Name        "VH-2202GT"
--  Date        "200208271503Z"  - Tue Aug 27 15:03 GMT 2002
    DESCRIPTION
        "Enterasys 22 port RJ45 1000BASE-T standalone Gigabit
         Ethernet layer 2 switch with 2 modular Mini-GBIC ports."
    ::= { etsysOidDevice 47 }

etsysOidDevC5M200 OBJECT-IDENTITY
    STATUS      deprecated
--  Name        "C5M200"
--  Date        "200210291413Z"   - Tue Oct 29 14:13 GMT 2002
    DESCRIPTION
        "Enterasys Matrix C5 System Management Module."
    ::= { etsysOidDevice 48 }

etsysOidDevC1H124x48 OBJECT-IDENTITY
    STATUS      current
--  Name        "C1H124-48"
--  Date        "200210291413Z"   - Tue Oct 29 14:13 GMT 2002
    DESCRIPTION
        "Enterasys Matrix C1 48 port RJ45 100BASE-TX Fast Ethernet
         standalone switch, with two RJ45 and two Mini-GBIC ports."
    ::= { etsysOidDevice 49 }

etsysOidDevC2M200 OBJECT-IDENTITY
    STATUS      deprecated
--  Name        "C2M200"
--  Date        "200210291413Z"   - Tue Oct 29 14:13 GMT 2002
    DESCRIPTION
        "Enterasys Matrix C2 System Management Module."
    ::= { etsysOidDevice 50 }

etsysOidDevMatrixE7 OBJECT-IDENTITY
    STATUS      current
--  Name        "Matrix E7 Management Entity"
--  Date        "200212131926Z"  - Fri Dec 13 19:26 GMT 2002
    DESCRIPTION
        "Enterasys Matrix E7 single IP address management entity
         for the DFE Platinum switch."
    ::= { etsysOidDevice 51 }

etsysOidDevMatrixN7 OBJECT-IDENTITY
    STATUS      current
--  Name        "Matrix N7 Management Entity"
--  Date        "200212312051Z"  - Tue Dec 31 20:51 GMT 2002
    DESCRIPTION
        "Enterasys Matrix N7 single IP address management entity
         for the DFE Platinum switch."
    ::= { etsysOidDevice 52 }

etsysOidDevMatrixN3 OBJECT-IDENTITY
    STATUS      current
--  Name        "Matrix N3 Management Entity"
--  Date        "200212312051Z"  - Tue Dec 31 20:51 GMT 2002
    DESCRIPTION
        "Enterasys Matrix N3 single IP address management entity
         for the DFE Platinum switch."
    ::= { etsysOidDevice 53 }

etsysOidDevXSRx1100 OBJECT-IDENTITY
    STATUS      deprecated
--  Name        "XSR-1100"
--  Date        "200303121917Z"  - Wed Mar 12 19:17 GMT 2003
    DESCRIPTION
        "Enterasys fixed configuration branch office router / VPN
         device with 4 100BASE-T Ethernet ports and a single WAN
         interface."
    ::= { etsysOidDevice 54 }

etsysOidDevXSRx3020 OBJECT-IDENTITY
    STATUS      current
--  Name        "XSR-3020"
--  Date        "200303051535Z"  - Wed Mar  5 15:35 GMT 2003
    DESCRIPTION
        "Enterasys, high end, high performance, security hardened,
         branch office router / VPN / Firewall device with 3
         1000BASE-T Ethernet ports, and two slots for optional
         WAN interface modules."
    ::= { etsysOidDevice 55 }

etsysOidDevXSRx3150 OBJECT-IDENTITY
    STATUS      current
--  Name        "XSR-3150"
--  Date        "200303051535Z"  - Wed Mar  5 15:35 GMT 2003
    DESCRIPTION
        "Enterasys, high performance, security hardened, 1U,
         regional office router / VPN / Firewall device with 3
         1000BASE-T Ethernet ports, and two slots for optional
         WAN interface modules."
    ::= { etsysOidDevice 56 }

etsysOidDevXSRx3250 OBJECT-IDENTITY
    STATUS      current
--  Name        "XSR-3250"
--  Date        "200303051535Z"  - Wed Mar  5 15:35 GMT 2003
    DESCRIPTION
        "Enterasys, high performance, security hardened, 1.5U,
         regional office router / VPN / Firewall device with 3
         1000BASE-T Ethernet ports, and six slots for optional
         WAN interface modules."
    ::= { etsysOidDevice 57 }

etsysOidDevXSRx4100 OBJECT-IDENTITY
    STATUS      current
--  Name        "XSR-4100"
--  Date        "200303051535Z"  - Wed Mar  5 15:35 GMT 2003
    DESCRIPTION
        "Enterasys, high performance, security hardened, high
         port density, 3U, regional office router / VPN / Firewall
         device with 3 1000BASE-T Ethernet ports, and fourteen
         slots for optional WAN interface modules."
    ::= { etsysOidDevice 58 }

etsysOidDev1H582x25 OBJECT-IDENTITY
    STATUS      current
--  Name        "1H582-25"
--  Date        "200304251442Z"  - Fri Apr 25 14:42 GMT 2003
    DESCRIPTION
        "Enterasys 24 port 100BASE-TX Fast Ethernet standalone switch
         with RJ45 connectors and one slot for an optional interface
         module."
    ::= { etsysOidDevice 59 }

etsysOidDev1G587x09 OBJECT-IDENTITY
    STATUS      current
--  Name        "1G587-09"
--  Date        "200304251442Z"  - Fri Apr 25 14:42 GMT 2003
    DESCRIPTION
        "Enterasys 6 port 1000BASE-X Gigabit Ethernet standalone switch
         with 6 modular Mini-GBIC ports and three slots for optional
         interface modules."
    ::= { etsysOidDevice 60 }

etsysOidDevC1G124x24 OBJECT-IDENTITY
    STATUS      current
--  Name        "C1G124-24"
--  Date        "200305072048Z"  - Wed May  7 20:48 GMT 2003
    DESCRIPTION
        "Enterasys Matrix C1 24 port RJ45 1000BASE-T Gigabit Ethernet
         standalone switch, with four Mini-GBIC ports."
    ::= { etsysOidDevice 61 }

etsysOidDevV2H124x24 OBJECT-IDENTITY
    STATUS      current
--  Name        "V2H124-24"
--  Date        "200305142108Z"  - Wed May 14 21:08 GMT 2003
    DESCRIPTION
        "Enterasys 24 port 100BASE-TX Fast Ethernet standalone L2
         switch with RJ45 connectors and two uplink slots."
    ::= { etsysOidDevice 62 }

etsysOidDevRBTR3xA OBJECT-IDENTITY
    STATUS      current
--  Name        "RBTR3-A"
--  Date        "200307171353Z"  - Thu Jul 17 13:53 GMT 2003
    DESCRIPTION
        "Enterasys RoamAbout R3 wireless access platform, provides
         an L2 switched connection between 100BASE-TX wired Ethernet
         and 802.11 wireless LANs supporting the 802.11a, 802.11b,
         or 802.11g standards."
    ::= { etsysOidDevice 63 }

etsysOidDevRBTR4xA OBJECT-IDENTITY
    STATUS      current
--  Name        "RBT3K"
--  Date        "200401271643Z"  - Tue Jan 27 16:43 GMT 2004
    DESCRIPTION
        "Enterasys AP3000 wireless access platform, provides an L2
         switched connection between 100BASE-TX wired Ethernet and
         802.11 wireless LANs supporting the 802.11b/g and 802.11a
         standards."
    ::= { etsysOidDevice 64 }

etsysOidDevMatrixE7Gold OBJECT-IDENTITY
    STATUS      current
--  Name        "Matrix E7-Gold Management Entity"
--  Date        "200310231527Z" - Thu Oct 23 15:27 GMT 2003
    DESCRIPTION
        "Enterasys Matrix E7 single IP address management entity
         for the DFE Gold switch."
    ::= { etsysOidDevice 65 }

etsysOidDevMatrixN7Gold OBJECT-IDENTITY
    STATUS      current
--  Name        "Matrix N7-Gold Management Entity"
--  Date        "200310231527Z" - Thu Oct 23 15:27 GMT 2003
    DESCRIPTION
        "Enterasys Matrix N7 single IP address management entity
         for the DFE Gold switch."
    ::= { etsysOidDevice 66 }

etsysOidDevMatrixN3Gold OBJECT-IDENTITY
    STATUS      current
--  Name        "Matrix N3-Gold Management Entity"
--  Date        "200310231527Z" - Thu Oct 23 15:27 GMT 2003
    DESCRIPTION
        "Enterasys Matrix N3 single IP address management entity
         for the DFE Gold switch."
    ::= { etsysOidDevice 67 }

etsysOidDevV2H124xPOE OBJECT-IDENTITY
    STATUS      current
--  Name        "V2H124-POE"
--  Date        "200312011638Z"  - Mon Dec  1 16:38 GMT 2003
    DESCRIPTION
        "Enterasys 24 port 100BASE-TX Fast Ethernet standalone L2
         switch with RJ45 connectors and two uplink slots.  Power
         over Ethernet is supported on the 24 100BASE-TX ports."
    ::= { etsysOidDevice 68 }

etsysOidDevDFEGoldRouter OBJECT-IDENTITY
    STATUS      current
--  Name        "DFE Gold Router Management Entity"
--  Date        "200312121713Z"  - Fri Dec 12 17:13 GMT 2003
    DESCRIPTION
        "Enterasys Matrix DFE Gold router management entity."
    ::= { etsysOidDevice 69 }

etsysOidDevDFEPlatinumRouter OBJECT-IDENTITY
    STATUS      current
--  Name        "DFE Platinum Management Entity"
--  Date        "200312121713Z"  - Fri Dec 12 17:13 GMT 2003
    DESCRIPTION
        "Enterasys Matrix DFE Platinum router management entity."
    ::= { etsysOidDevice 70 }

etsysOidDevDragonIdsAppliance OBJECT-IDENTITY
    STATUS      current
--  Name        "Dragon IDS Appliance"
--  Date        "200402261455Z"  - Thu Feb 26 14:55 GMT 2004
    DESCRIPTION
        "Enterasys Dragon Intrusion Detection System Appliance."
    ::= { etsysOidDevice 71 }

etsysOidDevXSRx1205 OBJECT-IDENTITY
    STATUS      current
--  Name        "XSR-1205"
--  Date        "200403151931Z"  - Mon Mar 15 19:31 GMT 2004
    DESCRIPTION
        "Enterasys fixed configuration branch office router / security
         gateway device with 1 100BASE-T Ethernet port for WAN
         connectivity, and a 4 port 100BASE-T Ethernet switch for LAN
         connections."
    ::= { etsysOidDevice 72 }

etsysOidDevXSRx1220 OBJECT-IDENTITY
    STATUS      current
--  Name        "XSR-1220"
--  Date        "200403151931Z"  - Mon Mar 15 19:31 GMT 2004
    DESCRIPTION
        "Enterasys fixed configuration branch office router / security
         gateway device with 1 ADSL Annex A,C port for WAN connectivity,
         and a 4 port 100BASE-T Ethernet switch for LAN connections."
    ::= { etsysOidDevice 73 }

etsysOidDevXSRx1225 OBJECT-IDENTITY
    STATUS      current
--  Name        "XSR-1225"
--  Date        "200403151931Z"  - Mon Mar 15 19:31 GMT 2004
    DESCRIPTION
        "Enterasys fixed configuration branch office router / security
         gateway device with 1 ADSL Annex A,C and 1 ISDN S/T port for
         WAN connectivity, and a 4 port 100BASE-T Ethernet switch for
         LAN connections."
    ::= { etsysOidDevice 74 }

etsysOidDevXSRx1230 OBJECT-IDENTITY
    STATUS      current
--  Name        "XSR-1230"
--  Date        "200403151931Z"  - Mon Mar 15 19:31 GMT 2004
    DESCRIPTION
        "Enterasys fixed configuration branch office router / security
         gateway device with 1 ADSL Annex B port for WAN connectivity,
         and a 4 port 100BASE-T Ethernet switch for LAN connections."
    ::= { etsysOidDevice 75 }

etsysOidDevXSRx1235 OBJECT-IDENTITY
    STATUS      current
--  Name        "XSR-1235"
--  Date        "200403151931Z"  - Mon Mar 15 19:31 GMT 2004
    DESCRIPTION
        "Enterasys fixed configuration branch office router / security
         gateway device with 1 ADSL Annex B and 1 ISDN S/T port for
         WAN connectivity, and a 4 port 100BASE-T Ethernet switch for
         LAN connections."
    ::= { etsysOidDevice 76 }

etsysOidDev2G4072x52 OBJECT-IDENTITY
    STATUS      current
--  Name        "2G4072-52"
--  Date        "200403191955Z"  - Fri Mar 19 19:55 GMT 2004
    DESCRIPTION
        "Enterasys Matrix DFE 52 port Gigabit Ethernet standalone
         switch with 48 1000BASE-T ports with RJ45 connectors and
         four 1000BASE-X ports with Mini-GBIC connectors."
    ::= { etsysOidDevice 77 }

etsysOidDevMatrixN5PoEGold OBJECT-IDENTITY
    STATUS      current
--  Name        "Matrix N5 PoE-Gold Management Entity"
--  Date        "200404161915Z"  - Fri Apr 16 19:15 GMT 2004
    DESCRIPTION
        "Enterasys Matrix N5 PoE single IP address management entity
         for the DFE Gold switch."
    ::= { etsysOidDevice 78 }

etsysOidDevMatrixN5PoEPlatinum OBJECT-IDENTITY
    STATUS      current
--  Name        "Matrix N5 PoE-Platinum Management Entity"
--  Date        "200404161915Z"  - Fri Apr 16 19:15 GMT 2004
    DESCRIPTION
        "Enterasys Matrix N5 PoE single IP address management entity
         for the DFE Platinum switch."
    ::= { etsysOidDevice 79 }

etsysOidDevMatrixX4 OBJECT-IDENTITY
    STATUS      current
--  Name        "Matrix X4 Management Entity"
--  Date        "200408111924Z"  - Wed Aug 11 19:24 GMT 2004
    DESCRIPTION
        "Enterasys Matrix X4 management entity."
    ::= { etsysOidDevice 80 }

etsysOidDevMatrixX8 OBJECT-IDENTITY
    STATUS      current
--  Name        "Matrix X8 Management Entity"
--  Date        "200408111924Z"  - Wed Aug 11 19:24 GMT 2004
    DESCRIPTION
        "Enterasys Matrix X8 management entity."
    ::= { etsysOidDevice 81 }

etsysOidDevMatrixX16 OBJECT-IDENTITY
    STATUS      current
--  Name        "Matrix X16 Management Entity"
--  Date        "200408111924Z"  - Wed Aug 11 19:24 GMT 2004
    DESCRIPTION
        "Enterasys Matrix X16 management entity."
    ::= { etsysOidDevice 82 }

etsysOidDevMatrixN1 OBJECT-IDENTITY
    STATUS      current
--  Name        "Matrix N1 Management Entity"
--  Date        "200501111956Z"  - Tue Jan 11 19:56 GMT 2005
    DESCRIPTION
        "Enterasys Matrix N1 single IP address management entity
         for the DFE Platinum switch."
    ::= { etsysOidDevice 83 }

etsysOidDevMatrixN1Gold OBJECT-IDENTITY
    STATUS      current
--  Name        "Matrix N1-Gold Management Entity"
--  Date        "200501111956Z"  - Tue Jan 11 19:56 GMT 2005
    DESCRIPTION
        "Enterasys Matrix N1 single IP address management entity
         for the DFE Gold switch."
    ::= { etsysOidDevice 84 }

etsysOidDevRBTSAxAA OBJECT-IDENTITY
    STATUS      current
--  Name        "RBTSA"
--  Date        "200504121714Z"  - Tue Apr 12 17:14 GMT 2005
    DESCRIPTION
        "Enterasys wireless Ethernet adapter, US (802.11a/b/g)."
    ::= { etsysOidDevice 85 }

etsysOidDevRBTSAxAB OBJECT-IDENTITY
    STATUS      current
--  Name        "RBTSA"
--  Date        "200504121714Z"  - Tue Apr 12 17:14 GMT 2005
    DESCRIPTION
        "Enterasys wireless Ethernet adapter, International (non US)
         (802.11a/b/g)."
    ::= { etsysOidDevice 86 }

etsysOidDevA2H124x24 OBJECT-IDENTITY
    STATUS    current
--  Name      "A2H124-24"
--  Date      "200506211303Z"  - Tue Jun 21 13:03 GMT 2005
    DESCRIPTION
        "Enterasys SecureStack A2 24 port RJ45 100BASE-TX Fast Ethernet
         stackable switch, with 2 1000BASE-T ports and 2 Mini-GBIC ports."
    ::= { etsysOidDevice 87 }

etsysOidDevA2H124x24P OBJECT-IDENTITY
    STATUS    current
--  Name      "A2H124-24P"
--  Date      "200506211303Z"  - Tue Jun 21 13:03 GMT 2005
    DESCRIPTION
        "Enterasys SecureStack A2 24 port RJ45 100BASE-TX Fast Ethernet
         stackable switch, with 2 1000BASE-T ports and 2 Mini-GBIC ports,
         and Power Over Ethernet (POE)."
    ::= { etsysOidDevice 88 }

etsysOidDevA2H124x48 OBJECT-IDENTITY
    STATUS    current
--  Name      "A2H124-48"
--  Date      "200506211303Z"  - Tue Jun 21 13:03 GMT 2005
    DESCRIPTION
        "Enterasys SecureStack A2 48 port RJ45 100BASE-TX Fast Ethernet
         stackable switch, with 2 1000BASE-T ports and 2 Mini-GBIC ports."
    ::= { etsysOidDevice 89 }

etsysOidDevA2H124x48P OBJECT-IDENTITY
    STATUS    current
--  Name      "A2H124-48P"
--  Date      "200506211303Z"  - Tue Jun 21 13:03 GMT 2005
    DESCRIPTION
        "Enterasys SecureStack A2 48 port RJ45 100BASE-TX Fast Ethernet
         stackable switch, with 2 1000BASE-T ports and 2 Mini-GBIC ports,
         and Power Over Ethernet (POE)."
    ::= { etsysOidDevice 90 }

etsysOidDevA2H124x24FX OBJECT-IDENTITY
    STATUS    current
--  Name      "A2H124-24FX"
--  Date      "200506211303Z"  - Tue Jun 21 13:03 GMT 2005
    DESCRIPTION
        "Enterasys SecureStack A2 24 port MT-RJ 100BASE-FX Fast Ethernet
         stackable switch, with 2 1000BASE-T ports and 2 Mini-GBIC ports."
    ::= { etsysOidDevice 91 }

etsysOidDevRBT4102 OBJECT-IDENTITY
    STATUS    current
--  Name      "RBT-4102"
--  Date      "200508311822Z"  - Wed Aug 31 18:22 UTC 2005
    DESCRIPTION
        "Enterasys RoamAbout AP 4102 (RBT-4102), provides
         an L2 switched connection between a 100BASE-TX wired Ethernet
         and two 802.11 embedded wireless LANs radios, one supporting 
         802.11a and the second supporting 802.11b/g technology."
    ::= { etsysOidDevice 92 }

etsysOidDevNSTAGxGE250xTX  OBJECT-IDENTITY
    STATUS    current
--  Name      "NSTAG-GE250-TX 
--  Date      "200509211603Z"  - Wed Sep 21 16:03 UTC 2005
    DESCRIPTION
        "Enterasys medium performance security appliance for controlling
         end system access to the network.  It can apply policies to an
         end system based on location or system health as well as 
         performing a RADIUS proxy to obtain the end systems access 
         rights.  Based on a configured policy, the TAG can determine the 
         health of a system by scanning it remotely and if needed 
         quarantine the system.  It is a 1U rack mountable system."
    ::= { etsysOidDevice 93 }

etsysOidDevNSTAGxGE500xTX  OBJECT-IDENTITY
    STATUS    current
--  Name      "NSTAG-GE500-TX
--  Date      "200509211603Z"  - Wed Sep 21 16:03 UTC 2005
    DESCRIPTION
        "Enterasys high performance security appliance for controlling
         end system access to the network.  It can apply policies to an 
         end system based on location or system health as well as 
         performing a RADIUS proxy to obtain the end systems access 
         rights.  Based on a configured policy, the TAG can determine the
         health of a system by scanning it remotely and if needed 
         quarantine the system.  It is a 1U rack mountable system."
    ::= { etsysOidDevice 94 }

etsysOidDevA2H254x16 OBJECT-IDENTITY
    STATUS    current
--  Name      "A2H254-16"
--  Date      "200602092006Z"  - Thu Feb  9 20:06 UTC 2006
    DESCRIPTION
        "Enterasys SecureStack A2 16 port Fast Ethernet stackable switch, 
         with 8 100BASE-TX ports, 8 100BASE-FX ports, 2 1000BASE-T ports 
         and 2 Mini-GBIC ports."
    ::= { etsysOidDevice 95 }

etsysOidDevC3G124x24 OBJECT-IDENTITY
    STATUS    current
--  Name      "C3G124-24"
--  Date      "200608031357Z"  - Thu Aug  3 13:57 UTC 2006
    DESCRIPTION
        "Enterasys SecureStack C3 24 port Gigabit Ethernet stackable 
         switch, with 24 RJ45 1000BASE-T ports and 4 SFP ports."
    ::= { etsysOidDevice 96 }

etsysOidDevC3G124x24P OBJECT-IDENTITY
    STATUS    current
--  Name      "C3G124-24P"
--  Date      "200608031357Z"  - Thu Aug  3 13:57 UTC 2006
    DESCRIPTION
        "Enterasys SecureStack C3 24 port Gigabit Ethernet stackable POE 
         switch, with 24 RJ45 1000BASE-T ports and 4 SFP ports."
    ::= { etsysOidDevice 97 }

etsysOidDevC3G124x48 OBJECT-IDENTITY
    STATUS    current
--  Name      "C3G124-48"
--  Date      "200608031357Z"  - Thu Aug  3 13:57 UTC 2006
    DESCRIPTION
        "Enterasys SecureStack C3 48 port Gigabit Ethernet stackable 
         switch, with 48 RJ45 1000BASE-T ports and 4 SFP ports."
    ::= { etsysOidDevice 98 }

etsysOidDevC3G124x48P OBJECT-IDENTITY
    STATUS    current
--  Name      "C3G124-48P"
--  Date      "200608031357Z"  - Thu Aug  3 13:57 UTC 2006
    DESCRIPTION
        "Enterasys SecureStack C3 48 port Gigabit Ethernet stackable POE 
         switch, with 48 RJ45 1000BASE-T ports and 4 SFP ports."
    ::= { etsysOidDevice 99 }

etsysOidDevB3G124x24 OBJECT-IDENTITY
    STATUS    current
--  Name      "B3G124-24"
--  Date      "200608031357Z"  - Thu Aug  3 13:57 UTC 2006
    DESCRIPTION
        "Enterasys SecureStack B3 24 port Gigabit Ethernet stackable 
         switch, with 24 RJ45 1000BASE-T ports and 4 SFP ports."
    ::= { etsysOidDevice 100 }

etsysOidDevB3G124x24P OBJECT-IDENTITY
    STATUS    current
--  Name      "B3G124-24P"
--  Date      "200608031357Z"  - Thu Aug  3 13:57 UTC 2006
    DESCRIPTION
        "Enterasys SecureStack B3 24 port Gigabit Ethernet stackable POE
         switch, with 24 RJ45 1000BASE-T ports and 4 SFP ports."
    ::= { etsysOidDevice 101 }

etsysOidDevB3G124x48 OBJECT-IDENTITY
    STATUS    current
--  Name      "B3G124-48"
--  Date      "200608031357Z"  - Thu Aug  3 13:57 UTC 2006
    DESCRIPTION
        "Enterasys SecureStack B3 48 port Gigabit Ethernet stackable 
         switch, with 48 RJ45 1000BASE-T ports and 4 SFP ports."
    ::= { etsysOidDevice 102 }

etsysOidDevB3G124x48P OBJECT-IDENTITY
    STATUS    current
--  Name      "B3G124-48P"
--  Date      "200608031357Z"  - Thu Aug  3 13:57 UTC 2006
    DESCRIPTION
        "Enterasys SecureStack B3 48 port Gigabit Ethernet stackable POE 
         switch, with 48 RJ45 1000BASE-T ports and 4 SFP ports."
    ::= { etsysOidDevice 103 }

etsysOidDevI3H252x02 OBJECT-IDENTITY
    STATUS    current
--  Name      "I3H252-02"
--  Date      "200608071231Z"  - Mon Aug  7 12:31 UTC 2006
    DESCRIPTION
        "Enterasys Industrial switch with two I/O Card Slots and two 
         fixed SFPs."
    ::= { etsysOidDevice 104 }

etsysOidDevSNSxTAGxLPA OBJECT-IDENTITY
    STATUS    current
--  Name      "SNS-TAG-LPA"
--  Date      "200609201451Z"  - Wed Sep 20 14:51 UTC 2006
    DESCRIPTION
        "Enterasys medium performance Network Access Control security
         appliance for controlling end system access to the network.  
         Based on an assessment of end systems health, vulnerabilities, 
         and compliance, it can modify the access of an end system on the 
         network.  This device is a 1U rack mountable system."
    ::= { etsysOidDevice 105 }

etsysOidDevSNSxTAGxHPA OBJECT-IDENTITY
    STATUS    current
--  Name      "SNS-TAG-HPA"
--  Date      "200609201451Z"  - Wed Sep 20 14:51 UTC 2006
    DESCRIPTION
        "Enterasys high performance Network Access Control security
         appliance for controlling end system access to the network.  
         Based on an assessment of end systems health, vulnerabilities, 
         and compliance, it can modify the access of an end system on the 
         network.  This device is a 1U rack mountable system."
    ::= { etsysOidDevice 106 }

etsysOidDevSNSxTAGxBASE OBJECT-IDENTITY
    STATUS    current
--  Name      "SNS-TAG-BASE"
--  Date      "200609201451Z"  - Wed Sep 20 14:51 UTC 2006
    DESCRIPTION
        "Enterasys integrated Network Access Control security appliance 
         for controlling end system access to the network.  Based on an 
         assessment of end systems health, vulnerabilities, and compliance,
         it can modify the access of an end system on the network.  This
         device is a 1U rack mountable system."
    ::= { etsysOidDevice 107 }

etsysOidDev7SxNSTAGx01 OBJECT-IDENTITY
    STATUS    current
--  Name      "7S-NSTAG-01"
--  Date      "200609201451Z"  - Wed Sep 20 14:51 UTC 2006
    DESCRIPTION
        "Enterasys Network Access Control security module for controlling
         end system access to the network.  Based on an assessment of end
         systems health, vulnerabilities, and compliance, it can modify 
         the access of an end system on the network.  This device is an 
         add-in card for the Matrix N series chassis."
    ::= { etsysOidDevice 108 }

etsysOidDevSNSxPCCxWBA OBJECT-IDENTITY
    STATUS    current
--  Name      "SNS-PCC-WBA
--  Date      "200609291258Z"  - Fri Sep 29 12:58 UTC 2006
    DESCRIPTION
        "Enterasys Policy Control Console Web Based security appliance
         for controlling end user policy configuration.  It is a 1U 
         rack mountable system."
    ::= { etsysOidDevice 109 }

etsysOidDevA2H123x24 OBJECT-IDENTITY
    STATUS    current
--  Name      "A2H123-24"
--  Date      "200704161443Z"  - Mon Apr 16 14:43 UTC 2007
    DESCRIPTION
        "Enterasys SecureStack A2 with 24 10/100 RJ-45 ports, 2 
         100Base-FX ports, and 2 Stack ports."
    ::= { etsysOidDevice 110 }

etsysOidDevB3H124x24FX OBJECT-IDENTITY
    STATUS    current
--  Name      "B3H124-24FX"
--  Date      "200704161443Z"  - Mon Apr 16 14:43 UTC 2007
    DESCRIPTION
        "Enterasys SecureStack B3 with 24 100Base-FX ports and 4 Mini-GBIC
         combination ports."
    ::= { etsysOidDevice 111 }

etsysOidDevC3H124x24FX OBJECT-IDENTITY
    STATUS    current
--  Name      "C3H124-24FX"
--  Date      "200704161443Z"  - Mon Apr 16 14:43 UTC 2007
    DESCRIPTION
        "Enterasys SecureStack C3 with 24 100Base-FX ports and 4 Mini-GBIC
         combination ports."
    ::= { etsysOidDevice 112 }

etsysOidDevC3K122x24 OBJECT-IDENTITY
    STATUS    current
--  Name      "C3K122-24"
--  Date      "200704161443Z"  - Mon Apr 16 14:43 UTC 2007
    DESCRIPTION
        "Enterasys SecureStack C3 with 24 10/100/1000 RJ-45 ports and 
         a slot for a dual 10 Gigabit Ethernet module which supports XFPs."
    ::= { etsysOidDevice 113 }

etsysOidDevC3K172x24 OBJECT-IDENTITY
    STATUS    current
--  Name      "C3K172-24"
--  Date      "200704161443Z"  - Mon Apr 16 14:43 UTC 2007
    DESCRIPTION
        "Enterasys SecureStack C3 with 24 SFP ports and a slot for a 
         dual 10 Gigabit Ethernet module which supports XFPs."
    ::= { etsysOidDevice 114 }

etsysOidDevC3Kx2XFP OBJECT-IDENTITY
    STATUS    current
--  Name      "C3K-2XFP"
--  Date      "200704161443Z"  - Mon Apr 16 14:43 UTC 2007
    DESCRIPTION
        "Enterasys SecureStack C3 Dual 10 Gigabit Ethernet module with 
         2 XFP slots for use in the SecureStack C3K product line."
    ::= { etsysOidDevice 115 }

etsysOidDevSNSxNSSxA OBJECT-IDENTITY
    STATUS    current
--  Name      "SNS-NSS-A"
--  Date      "200704201158Z"  - Fri Apr 20 11:58 UTC 2007
    DESCRIPTION
        "Enterasys NetSight Suite appliance.  The NetSight Suite is a
         business solution enabling the user to take full advantage of 
         the enhanced features and functionality of the Enterasys Secure
         Networks architecture."
    ::= { etsysOidDevice 116 }

etsysOidDevG3G124x24 OBJECT-IDENTITY
    STATUS    current
--  Name      "G3G124-24"
--  Date      "200706041543Z"  - Mon Jun  4 15:43 UTC 2007
    DESCRIPTION
        "Enterasys G3 with 24 1000BASE-TX ports and  
         3 expansion slots."
    ::= { etsysOidDevice 117 }

etsysOidDevG3G170x24 OBJECT-IDENTITY
    STATUS    current
--  Name      "G3G170-24"
--  Date      "200706041543Z"  - Mon Jun  4 15:43 UTC 2007
    DESCRIPTION
        "Enterasys G3 with 24 SFP ports and   
         3 expansion slots."
    ::= { etsysOidDevice 118 }

etsysOidDevD2G124x12 OBJECT-IDENTITY
    STATUS    current
--  Name      "D2G124x12"
--  Date      "200706141825Z"  - Thu Jun 14 18:25 UTC 2007
    DESCRIPTION
        "Enterasys D2 with 12 1000BASE-TX ports."
    ::= { etsysOidDevice 119 }

etsysOidDevD2G124x12P OBJECT-IDENTITY
    STATUS    current
--  Name      "D2G124x12P"
--  Date      "200706141825Z"  - Thu Jun 14 18:25 UTC 2007
    DESCRIPTION
        "Enterasys D2 with 12 1000BASE-TX POE ports."
    ::= { etsysOidDevice 120 }

etsysOidDevRBTx8500 OBJECT-IDENTITY
    STATUS    current
--  Name      "RBT-8500"
--  Date      "200706251822Z"  - Mon Jun 25 18:22 UTC 2007
    DESCRIPTION
        "Enterasys RoamAbout switch controller which provides
         support for up to 128 thin access points. Interfaces include 
         two 1 Gigabit SFP Ethernet ports."
    ::= { etsysOidDevice 121 }

etsysOidDevMatrixN1NAC OBJECT-IDENTITY
    STATUS    current
--  Name      "Matrix N1-NAC Management Entity"
--  Date      "200708291516Z"  - Wed Aug 29 15:16 UTC 2007
    DESCRIPTION
        "Enterasys Matrix N1 single IP address management entity
         for the DFE NAC switch."
    ::= { etsysOidDevice 122 }

etsysOidDev7SxNSNACGx01NPS OBJECT-IDENTITY
    STATUS    current
--  Name      "7S-NSNACG-01NPS"
--  Date      200801102009Z"  - Thu Jan 10 20:09 UTC 2008
    DESCRIPTION
        "Enterasys Networks NAC Controller Engine.  This is the NAC
         engine for the Enterasys NAC that controls access of an end 
         system on the network based on health assessment, 
         vulnerabilities, compliance, and more."
    ::= { etsysOidDevice 123 }

etsysOidDevG3G124x24P OBJECT-IDENTITY
    STATUS    current
--  Name      "G3G124-24P"
--  Date      "200801242008Z"  - Thu Jan 24 20:08 UTC 2008
    DESCRIPTION
        "Enterasys G3 with 24 1000BASE-TX ports,
         3 expansion slots, and Power over Ethernet (PoE)."
    ::= { etsysOidDevice 124 }

etsysOidDevC3K122x24P OBJECT-IDENTITY
    STATUS    current
--  Name      "C3K122-24P"
--  Date      "200704161443Z"  - Mon Apr 16 14:43 UTC 2007
    DESCRIPTION
        "Enterasys SecureStack C3 with 24 10/100/1000 RJ-45 ports and 
         a slot for a dual 10 Gigabit Ethernet module which supports 
         XFPs, and Power over Ethernet (PoE)."
    ::= { etsysOidDevice 125 }

etsysOidDevNACxAx2K OBJECT-IDENTITY
    STATUS    deprecated
--  Name      "NAC-A-2K"
--  Date      "200808131904Z"  - Wed Aug 13 19:04 UTC 2008
    DESCRIPTION
        "Enterasys NAC appliance for controlling end system access to the
         network.  It controls network access through Enterasys Policy or
         VLANs based on user, device, location, time, and configuration 
         (health).  It is a 1U rack mountable system."
    ::= { etsysOidDevice 126 }

etsysOidDevNACxAx3K OBJECT-IDENTITY
    STATUS    deprecated
--  Name      "NAC-A-3K"
--  Date      "200808131904Z"  - Wed Aug 13 19:04 UTC 2008
    DESCRIPTION
        "Enterasys NAC appliance for controlling end system access to the
         network.  It controls network access through Enterasys Policy or
         VLANs based on user, device, location, time, and configuration 
         (health).  It is a 1U rack mountable system."
    ::= { etsysOidDevice 127 }

etsysOidDevSSAxT4068x0252 OBJECT-IDENTITY
    STATUS    current
--  Name      "SSA-T4068-0252"
--  Date      "200903311713Z"  - Tue Mar 31 17:13 UTC 2009
    DESCRIPTION
        "Enterasys S-Series Standalone (SSA) Access device with 48 ports
         of 1000BASE-T Ethernet via RJ45 with PoE (802.3at) and 4 
         10GBASE-X Ethernet ports via SFP+."
    ::= { etsysOidDevice 128 }

etsysOidDevSSAxT1068x0652 OBJECT-IDENTITY
    STATUS    current
--  Name      "SSA-T1068-0652"
--  Date      "200903311713Z"  - Tue Mar 31 17:13 UTC 2009
    DESCRIPTION
        "Enterasys S-Series S150 Class Standalone (SSA) device
         with 48 ports of 1000BASE-T Ethernet via RJ45 with PoE (802.3at)
         and 4 10GBASE-X Ethernet ports via SFP+."
    ::= { etsysOidDevice 129 }

etsysOidDevSSAxG1018x0652 OBJECT-IDENTITY
    STATUS    current
--  Name      "SSA-G1018-0652"
--  Date      "200903311713Z"  - Tue Mar 31 17:13 UTC 2009
    DESCRIPTION
        "Enterasys S-Series S150 Class Standalone (SSA) device
         with 48 ports of 1000BASE-X Ethernet via SFP and 4 10GBASE-X 
         Ethernet ports via SFP+."
    ::= { etsysOidDevice 130 }

etsysOidDevS3 OBJECT-IDENTITY
    STATUS      current
--  Name        "S-Series S3 Management Entity"
--  Date        "200903311713Z"  - Tue Mar 31 17:13 UTC 2009
    DESCRIPTION
        "Enterasys S-Series S3 management entity."
    ::= { etsysOidDevice 131 }

etsysOidDevS4 OBJECT-IDENTITY
    STATUS      current
--  Name        "S-Series S4 Management Entity"
--  Date        "200903311713Z"  - Tue Mar 31 17:13 UTC 2009
    DESCRIPTION
        "Enterasys S-Series S4 management entity."
    ::= { etsysOidDevice 132 }

etsysOidDevS8 OBJECT-IDENTITY
    STATUS      current
--  Name        "S-Series S8 Management Entity"
--  Date        "200903311713Z"  - Tue Mar 31 17:13 UTC 2009
    DESCRIPTION
        "Enterasys S-Series S8 management entity."
    ::= { etsysOidDevice 133 }

etsysOidDevB5G124x24 OBJECT-IDENTITY
    STATUS    current
--  Name      "B5G124-24"
--  Date      "200908250112Z"  - Tue Aug 25  1:12 UTC 2009
    DESCRIPTION
        "Enterasys B-Series B5 with 24 1000BASE-T ports via RJ45, 
         4 combination ports via SFP, and  2 x 13G stack ports."
    ::= { etsysOidDevice 134 }

etsysOidDevB5G124x24P2 OBJECT-IDENTITY
    STATUS    current
--  Name      "B5G124-24P2"
--  Date      "200908250112Z"  - Tue Aug 25  1:12 UTC 2009
    DESCRIPTION
        "Enterasys B-Series B5 with 24 1000BASE-T ports via RJ45 with 
         PoE+, 4 combination ports via SFP, and  2 x 13G stack ports."
    ::= { etsysOidDevice 135 }

etsysOidDevB5G124x48 OBJECT-IDENTITY
    STATUS    current
--  Name      "B5G124-48"
--  Date      "200908250112Z"  - Tue Aug 25  1:12 UTC 2009
    DESCRIPTION
        "Enterasys B-Series B5 with 48 1000BASE-T ports via RJ45, 
         4 combination ports via SFP, and  2 x 13G stack ports."
    ::= { etsysOidDevice 136 }

etsysOidDevB5G124x48P2 OBJECT-IDENTITY
    STATUS    current
--  Name      "B5G124-48P2"
--  Date      "200908250112Z"  - Tue Aug 25  1:12 UTC 2009
    DESCRIPTION
        "Enterasys B-Series B5 with 48 1000BASE-T ports via RJ45 with 
         PoE+, 4 combination ports via SFP, and  2 x 13G stack ports."
    ::= { etsysOidDevice 137 }

etsysOidDevB5K125x24 OBJECT-IDENTITY
    STATUS    current
--  Name      "B5K125-24"
--  Date      "200908250112Z"  - Tue Aug 25  1:12 UTC 2009
    DESCRIPTION
        "Enterasys B-Series B5 with 24 1000BASE-T ports via RJ45, 
         2 ports of 10GBASE-X Ethernet via SFP+, and  2 x 13G stack 
         ports."
    ::= { etsysOidDevice 138 }

etsysOidDevB5K125x24P2 OBJECT-IDENTITY
    STATUS    current
--  Name      "B5K125-24P2"
--  Date      "200908250112Z"  - Tue Aug 25  1:12 UTC 2009
    DESCRIPTION
        "Enterasys B-Series B5 with 24 1000BASE-T ports via RJ45 with 
         PoE+, 2 ports of 10GBASE-X Ethernet via SFP+, and  2 x 13G stack
ports."
    ::= { etsysOidDevice 139 }

etsysOidDevB5K125x48 OBJECT-IDENTITY
    STATUS    current
--  Name      "B5K125-48"
--  Date      "200908250112Z"  - Tue Aug 25  1:12 UTC 2009
    DESCRIPTION
        "Enterasys B-Series B5 with 48 1000BASE-T ports via RJ45 and 
         2 ports of 10GBASE-X Ethernet via SFP+, and  2 x 13G stack 
         ports."
    ::= { etsysOidDevice 140 }

etsysOidDevB5K125x48P2 OBJECT-IDENTITY
    STATUS    current
--  Name      "B5K125-48P2"
--  Date      "200910261530Z"  - Mon Oct 26 15:30 UTC 2009
    DESCRIPTION
        "Enterasys B-Series B5 with 48 1000BASE-T ports via RJ45 with 
         PoE+ and 2 ports of 10GBASE-X Ethernet via SFP+, and  2 x 13G 
         stack ports."
    ::= { etsysOidDevice 141 }

etsysOidDevC5G124x24 OBJECT-IDENTITY
    STATUS    current
--  Name      "C5G124-24"
--  Date      "200908250112Z"  - Tue Aug 25  1:12 UTC 2009
    DESCRIPTION
        "Enterasys C-Series C5 with 24 1000BASE-T ports via RJ45, 
         4 combination ports via SFP, and  2 x 32G stack ports."
    ::= { etsysOidDevice 142 }

etsysOidDevC5G124x24P2 OBJECT-IDENTITY
    STATUS    current
--  Name      "C5G124-24P2"
--  Date      "200908250112Z"  - Tue Aug 25  1:12 UTC 2009
    DESCRIPTION
        "Enterasys C-Series C5 with 24 1000BASE-T ports via RJ45 with 
         PoE+, 4 combination ports via SFP, and  2 x 32G stack ports."
    ::= { etsysOidDevice 143 }

etsysOidDevC5G124x48 OBJECT-IDENTITY
    STATUS    current
--  Name      "C5G124-48"
--  Date      "200908250112Z"  - Tue Aug 25  1:12 UTC 2009
    DESCRIPTION
        "Enterasys C-Series C5 with 48 1000BASE-T ports via RJ45 and 
         4 combination ports via SFP, and  2 x 32G stack ports."
    ::= { etsysOidDevice 144 }

etsysOidDevC5G124x48P2 OBJECT-IDENTITY
    STATUS    current
--  Name      "C5G124-48P2"
--  Date      "200908250112Z"  - Tue Aug 25  1:12 UTC 2009
    DESCRIPTION
        "Enterasys C-Series C5 with 48 1000BASE-T ports via RJ45 with 
         PoE+ and 4 combination ports via SFP, and  2 x 32G stack ports."
    ::= { etsysOidDevice 145 }

etsysOidDevC5K125x24 OBJECT-IDENTITY
    STATUS    current
--  Name      "C5K125-24"
--  Date      "200908250112Z"  - Tue Aug 25  1:12 UTC 2009
    DESCRIPTION
        "Enterasys C-Series C5 with 24 1000BASE-T ports via RJ45, 
         2 ports of 10GBASE-X Ethernet via SFP+, and  2 x 32G stack 
         ports."
    ::= { etsysOidDevice 146 }

etsysOidDevC5K125x24P2 OBJECT-IDENTITY
    STATUS    current
--  Name      "C5K125-24P2"
--  Date      "200908250112Z"  - Tue Aug 25  1:12 UTC 2009
    DESCRIPTION
        "Enterasys C-Series C5 with 24 1000BASE-T ports via RJ45 with 
         PoE+, 2 ports of 10GBASE-X Ethernet via SFP+, and  2 x 32G stack
         ports."
    ::= { etsysOidDevice 147 }

etsysOidDevC5K125x48 OBJECT-IDENTITY
    STATUS    current
--  Name      "C5K125-48"
--  Date      "200908250112Z"  - Tue Aug 25  1:12 UTC 2009
    DESCRIPTION
        "Enterasys C-Series C5 with 48 1000BASE-T ports via RJ45, 
         2 ports of 10GBASE-X Ethernet via SFP+, and  2 x 32G stack 
         ports."
    ::= { etsysOidDevice 148 }

etsysOidDevC5K125x48P2 OBJECT-IDENTITY
    STATUS    current
--  Name      "C5K125-48P2"
--  Date      "200910261530Z"  - Mon Oct 26 15:30 UTC 2009
    DESCRIPTION
        "Enterasys C-Series C5 with 48 1000BASE-T ports via RJ45 with 
         PoE+, 2 ports of 10GBASE-X Ethernet via SFP+, and  2 x 32G stack
         ports."
    ::= { etsysOidDevice 149 }

etsysOidDevC5K175x24 OBJECT-IDENTITY
    STATUS    current
--  Name      "C5K175-24"
--  Date      "200910261530Z"  - Mon Oct 26 15:30 UTC 2009
    DESCRIPTION
        "Enterasys C-Series C5 with 24 1000BASE-X ports via SFP, 
         2 ports of 10GBASE-X Ethernet via SFP+."
    ::= { etsysOidDevice 150 }

etsysOidDevNACxAx10 OBJECT-IDENTITY
    STATUS    current
--  Name      "NAC-A-10"
--  Date      "200908271250Z"  - Thu Aug 27 12:50 UTC 2009
    DESCRIPTION
        "Enterasys NAC appliance for controlling end system access to the
         network.  It controls network access through Enterasys Policy or
         VLANs based on user, device, location, time, and configuration 
         (health).  It is a 1U rack mountable system."
    ::= { etsysOidDevice 151 }

etsysOidDevNACxAx20 OBJECT-IDENTITY
    STATUS    current
--  Name      "NAC-A-20"
--  Date      "200908271250Z"  - Thu Aug 27 12:50 UTC 2009
    DESCRIPTION
        "Enterasys NAC appliance for controlling end system access to the
         network.  It controls network access through Enterasys Policy or
         VLANs based on user, device, location, time, and configuration 
         (health).  Supports optional on-board assessment.  It is a 1U rack
         mountable system."
    ::= { etsysOidDevice 152 }

etsysOidDevNACxV OBJECT-IDENTITY
    STATUS    current
--  Name      "NAC-V"
--  Date      "201003051353Z"  - Fri Mar  5 13:53 UTC 2010
    DESCRIPTION
        "Enterasys Virtual NAC appliance for controlling end system access
         to the network.  It controls network access through Enterasys 
         Policy or VLANs based on user, device, location, time, and 
         configuration (health).  Supports optional on-board assessment."
    ::= { etsysOidDevice 153 }

etsysOidDevA4H124x24TX OBJECT-IDENTITY
    STATUS    current
--  Name      "A4H124-24TX"
--  Date      "201006031512Z"  - Thu Jun  3 15:12 UTC 2010
    DESCRIPTION
        "Enterasys SecureStack A4 24 port RJ45 100BASE-TX Fast Ethernet
         stackable switch, with 2 1000BASE-T ports and 2 Mini-GBIC ports."
    ::= { etsysOidDevice 154 }

etsysOidDevA4H124x24FX OBJECT-IDENTITY
    STATUS    current
--  Name      "A4H124-24FX"
--  Date      "201006031512Z"  - Thu Jun  3 15:12 UTC 2010
    DESCRIPTION
        "Enterasys SecureStack A4 24 port MT-RJ 100BASE-FX Fast Ethernet
         stackable switch, with 2 1000BASE-T ports and 2 Mini-GBIC ports."
    ::= { etsysOidDevice 155 }

etsysOidDevA4H124x8F8T OBJECT-IDENTITY
    STATUS    obsolete
--  Name      "A4H124-8F8T"
--  Date      "201006031512Z"  - Thu Jun  3 15:12 UTC 2010
    DESCRIPTION ""
    ::= { etsysOidDevice 156 }

etsysOidDevA4H124x24 OBJECT-IDENTITY
    STATUS    current
--  Name      "A4H124-24"
--  Date      "201006031512Z"  - Thu Jun  3 15:12 UTC 2010
    DESCRIPTION
        "Enterasys SecureStack A4 24 port RJ45 100BASE-TX Fast Ethernet
         stackable switch, with 2 1000BASE-T ports and 2 Mini-GBIC ports."
    ::= { etsysOidDevice 157 }

etsysOidDevA4H124x24P OBJECT-IDENTITY
    STATUS    current
--  Name      "A4H124-24P"
--  Date      "201006031512Z"  - Thu Jun  3 15:12 UTC 2010
    DESCRIPTION
        "Enterasys SecureStack A4 24 port RJ45 100BASE-TX Fast Ethernet
         stackable switch, with 2 1000BASE-T ports and 2 Mini-GBIC ports,
         and Power Over Ethernet (POE)."
    ::= { etsysOidDevice 158 }

etsysOidDevA4H124x48 OBJECT-IDENTITY
    STATUS    current
--  Name      "A4H124-48"
--  Date      "201006031512Z"  - Thu Jun  3 15:12 UTC 2010
    DESCRIPTION
        "Enterasys SecureStack A4 48 port RJ45 100BASE-TX Fast Ethernet
         stackable switch, with 2 1000BASE-T ports and 2 Mini-GBIC ports."
    ::= { etsysOidDevice 159 }

etsysOidDevA4H124x48P OBJECT-IDENTITY
    STATUS    current
--  Name      "A4H124-48P"
--  Date      "201006031512Z"  - Thu Jun  3 15:12 UTC 2010
    DESCRIPTION
        "Enterasys SecureStack A4 48 port RJ45 100BASE-TX Fast Ethernet
         stackable switch, with 2 1000BASE-T ports and 2 Mini-GBIC ports,
         and Power Over Ethernet (POE)."
    ::= { etsysOidDevice 160 }

etsysOidDevA4H254x8F8T OBJECT-IDENTITY
    STATUS    obsolete
--  Name      "A4H254-8F8T"
--  Date      "201006231758Z"  - Wed Jun 23 17:58 UTC 2010
    DESCRIPTION
        "Enterasys SecureStack A4 8 FE copper ports, 8 FE MT-RJ ports,
         with 2 1000BASE-T ports and 2 Mini-GBIC ports."
    ::= { etsysOidDevice 161 }

etsysOidDevK6 OBJECT-IDENTITY
    STATUS      current
--  Name        "K-Series K6 Management Entity"
--  Date        "201011181818Z"  - Thu Nov 18 18:18 UTC 2010
    DESCRIPTION
        "Enterasys K-Series K6 management entity."
    ::= { etsysOidDevice 162 }

etsysOidDevK10 OBJECT-IDENTITY
    STATUS      current
--  Name        "K-Series K10 Management Entity"
--  Date        "201011181818Z"  - Thu Nov 18 18:18 UTC 2010
    DESCRIPTION
        "Enterasys K-Series K10 management entity."
    ::= { etsysOidDevice 163 }

etsysOidDevS6 OBJECT-IDENTITY
    STATUS      current
--  Name        "S-Series S6 Management Entity"
--  Date        "201101131927Z"  - Thu Jan 13 19:27 UTC 2011
    DESCRIPTION
        "Enterasys S-Series S6 management entity."
    ::= { etsysOidDevice 164 }

--  This part of the OID tree is used for OID assignments to various
--  physical entities.  Generally, such entities may be fixed mount 
--  ports, removable ports, sub-assemblies, non-manageable modules,
--  power supplies, fan trays, and chassis frames. All objects under 
--  this branch are NOT directly SNMP manageable.  Specific examples 
--  of objects under this branch may include but are not limited to: 
--
--     o fixed mount front panel physical ports such as RJ45 100BASE-TX
--     o hot swappable ports such as GBICs
--     o removable but non-hot swappable ports such as PIMs 
--     o "integrated" HSIMs (i.e. not directly SNMP manageable)
--     o chassis line cards
--     o chassis backplanes
--     o chassis frames (i.e. sheet metal) 
--     o power supplies
--     o fan assemblies
-- 
--  Values under this branch would be suitable for returning for the
--  entPhysicalVendorType leaf in the ENTITY-MIB(RFC2737), and hrDeviceID 
--  leaf in HOST-RESOURCES-MIB(RFC2790).

etsysOidPhy OBJECT IDENTIFIER ::= { etsysOids 2 }

etsysOidPhyEmpty OBJECT-IDENTITY
    STATUS      current
    DESCRIPTION
        "Reserved."
    ::= { etsysOidPhy 1 }

etsysOidPhyMGBICxMT01 OBJECT-IDENTITY
    STATUS      current
--  Name        "MGBIC-MT01"
--  Date        "200010030000Z"
    DESCRIPTION
        "Enterasys MGBIC-MT01, a 1000BASE-SX Mini-GBIC with an MT-RJ
         connector."
    ::= { etsysOidPhy 2 }

etsysOidPhyMGBICxMT09 OBJECT-IDENTITY
    STATUS      current
--  Name        "MGBIC-MT09"
--  Date        "200010030000Z"
    DESCRIPTION
        "Enterasys MGBIC-MT09, a 1000BASE-LX Mini-GBIC with an MT-RJ
         connector."
    ::= { etsysOidPhy 3 }

etsysOidPhyMGBICxLC01 OBJECT-IDENTITY
    STATUS      current
--  Name        "MGBIC-LC01"
--  Date        "200010030000Z"
    DESCRIPTION
        "Enterasys MGBIC-LC01, a 1000BASE-SX Mini-GBIC with an LC
         connector."
    ::= { etsysOidPhy 4 }

etsysOidPhyMGBICxLC09 OBJECT-IDENTITY
    STATUS      current
--  Name        "MGBIC-LC09"
--  Date        "200010030000Z"
    DESCRIPTION
        "Enterasys MGBIC-LC09, a 1000BASE-LX Mini-GBIC with an LC
         connector."
    ::= { etsysOidPhy 5 }

etsysOidPhyFrtPnlFastEthRJ45 OBJECT-IDENTITY
    STATUS      current
--  Name        ""
--  Date        "200010100000Z"
    DESCRIPTION
        "Enterasys 100BASE-TX Fast Ethernet Front-panel fixed port 
         with RJ45 connector."
    ::= { etsysOidPhy 6 }

etsysOidPhyFrtPnlFastEthRJ21 OBJECT-IDENTITY
    STATUS      current
--  Name        ""
--  Date        "200010100000Z"
    DESCRIPTION
        "Enterasys 100BASE-TX Fast Ethernet Front-panel fixed port
         with RJ21 connector."
    ::= { etsysOidPhy 7 }

etsysOidPhyFrtPnlGigEthRJ45 OBJECT-IDENTITY
    STATUS      current
--  Name        ""
--  Date        "200010100000Z"
    DESCRIPTION
        "Enterasys 1000BASE-T Gigabit Ethernet Front-panel fixed port
         with RJ45 connector."
    ::= { etsysOidPhy 8 }

etsysOidPhyBackplaneFTM1 OBJECT-IDENTITY
    STATUS      current
--  Name        ""
--  Date        "200010100000Z"
    DESCRIPTION
        "Enterasys Frame Transfer Matrix 1 Backplane port."
    ::= { etsysOidPhy 9 }

etsysOidPhy7H4203x72 OBJECT-IDENTITY
    STATUS      current
--  Name        "7H4203-72"
--  Date        "200010050000Z"
    DESCRIPTION
        "Enterasys 72 port 100BASE-TX Fast Ethernet module with
         RJ21 connectors."
    ::= { etsysOidPhy 10 }

etsysOidPhy7H4273x52 OBJECT-IDENTITY
    STATUS      current
--  Name        "7H4273-52"
--  Date        "200010050000Z"
    DESCRIPTION
        "Enterasys 48 port 100BASE-TX RJ21 Fast Ethernet module, with
         4 port 1000BASE-X Gigabit Ethernet via Mini-GBIC connectors."
    ::= { etsysOidPhy 11 }

etsysOidPhy7H4303x48 OBJECT-IDENTITY
    STATUS      deprecated
--  Name        "7H4303-48"
--  Date        "200010050000Z"
    DESCRIPTION
        "Enterasys 48 port 100BASE-TX RJ21 Fast Ethernet module with
         Frame Transfer Matrix relay capability."
    ::= { etsysOidPhy 12 }

etsysOidPhy7G4270x12 OBJECT-IDENTITY
    STATUS      current
--  Name        "7G4270-12"
--  Date        "200010050000Z"
    DESCRIPTION
        "Enterasys 12 port 1000BASE-X Gigabit Ethernet module with 
         Mini-GBIC connectors."
    ::= { etsysOidPhy 13 }

etsysOidPhy7G4202x12 OBJECT-IDENTITY
    STATUS      deprecated
--  Name        "7G4202-12"
--  Date        "200010050000Z"
    DESCRIPTION
        "Enterasys 12 port 1000BASE-T RJ45 Gigabit Ethernet module."
    ::= { etsysOidPhy 14 }

etsysOidPhy7G4370x08 OBJECT-IDENTITY
    STATUS      deprecated
--  Name        "7G4370-08"
--  Date        "200010050000Z"
    DESCRIPTION
        "Enterasys 8 port 1000BASE-X Gigabit Ethernet module with
         Mini-GBIC connectors, and Frame Transfer Matrix relay 
         capability."
    ::= { etsysOidPhy 15 }

etsysOidPhy7K420Xx01 OBJECT-IDENTITY
    STATUS      current
--  Name        "7K420X-01"
--  Date        "200010050000Z"
    DESCRIPTION
        "Enterasys 1 port 10 Gigabit Ethernet module."
    ::= { etsysOidPhy 16 }

etsysOidPhy6C207x1 OBJECT-IDENTITY
    STATUS      current
--  Name        "6C207-1"
--  Date        "200010050000Z"
    DESCRIPTION
        "Enterasys AC power supply for the Matrix E7 chassis."
    ::= { etsysOidPhy 17 }

etsysOidPhy6C207x2 OBJECT-IDENTITY
    STATUS      current
--  Name        "6C207-2"
--  Date        "200010050000Z"
    DESCRIPTION
        "Enterasys DC power supply for the Matrix E7 chassis."
    ::= { etsysOidPhy 18 }

etsysOidPhy6C407 OBJECT-IDENTITY
    STATUS      current
--  Name        "6C407"
--  Date        "200010050000Z"
    DESCRIPTION
        "Enterasys fan tray for the Matrix E7 chassis."
    ::= { etsysOidPhy 19 }

etsysOidPhy5C205x3 OBJECT-IDENTITY
    STATUS      current
--  Name        "5C205-3"
--  Date        "200010100000Z"
    DESCRIPTION
        "Enterasys AC power supply for the Matrix E5 chassis."
    ::= { etsysOidPhy 20 }

etsysOidPhy5C205x2 OBJECT-IDENTITY
    STATUS      current
--  Name        "5C205-2"
--  Date        "200010100000Z"
    DESCRIPTION
        "Enterasys DC power supply for the Matrix E5 chassis."
    ::= { etsysOidPhy 21 }

etsysOidPhy5C405 OBJECT-IDENTITY
    STATUS      current
--  Name        "5C405"
--  Date        "200010100000Z"
    DESCRIPTION
        "Enterasys fan tray for the Matrix E5 chassis."
    ::= { etsysOidPhy 22 }

etsysOidPhy6C107 OBJECT-IDENTITY
    STATUS      current
--  Name        "6C107"
--  Date        "200010100000Z"
    DESCRIPTION
        "Enterasys 7 slot modular chassis frame for the Matrix E7."
    ::= { etsysOidPhy 23 }

etsysOidPhy5C105 OBJECT-IDENTITY
    STATUS      current
--  Name        "5C105"
--  Date        "200010100000Z"
    DESCRIPTION
        "Enterasys 5 slot modular chassis frame for the Matrix E5."
    ::= { etsysOidPhy 24 }

etsysOidPhy10GbExSR OBJECT-IDENTITY
    STATUS      current
--  Name        "10GBASE-SR"
--  Date        "200701251558Z"  - Thu Jan 25 15:58 UTC 2007
    DESCRIPTION
        "Enterasys 10GBASE-SR, XENPAK 10-Gigabit Ethernet LAN Interface
         with 850 nanometer serial port for 10-Gigabit Ethernet over
         multimode fiber (MMF) via an SC connector."
    ::= { etsysOidPhy 25 }

etsysOidPhy10GbExLR OBJECT-IDENTITY
    STATUS      current
--  Name        "10GBASE-LR"
--  Date        "200701251558Z"  - Thu Jan 25 15:58 UTC 2007
    DESCRIPTION
        "Enterasys 10GBASE-LR, XENPAK 10-Gigabit Ethernet LAN Interface
         with 1310 nanometer serial port for 10-Gigabit Ethernet over
         single-mode fiber (SMF) via an SC connector."
    ::= { etsysOidPhy 26 }

etsysOidPhy10GbExER OBJECT-IDENTITY
    STATUS      current
--  Name        "10GBASE-ER
--  Date        "200701251558Z"  - Thu Jan 25 15:58 UTC 2007
    DESCRIPTION
        "Enterasys 10GBASE-ER, XENPAK 10-Gigabit Ethernet LAN Interface
         with 1550 nanometer serial port for 10-Gigabit Ethernet over
         single-mode fiber (SMF) via an SC connector."
    ::= { etsysOidPhy 27 }

etsysOidPhy10GbExSW OBJECT-IDENTITY
    STATUS      current
--  Name        "10GBASE-SW"
--  Date        "200701251558Z"  - Thu Jan 25 15:58 UTC 2007
    DESCRIPTION
        "Enterasys 10GBASE-SW, XENPAK 10-Gigabit Ethernet WAN Interface
         with 850 nanometer serial port for 10-Gigabit Ethernet over
         multimode fiber (MMF) via an SC connector."
    ::= { etsysOidPhy 28 }

etsysOidPhy10GbExLW OBJECT-IDENTITY
    STATUS      current
--  Name        "10GBASE-LW"
--  Date        "200701251558Z"  - Thu Jan 25 15:58 UTC 2007
    DESCRIPTION
        "Enterasys 10GBASE-LW, XENPAK 10-Gigabit Ethernet WAN Interface
         with 1310 nanometer serial port for 10-Gigabit Ethernet over
         single-mode fiber (SMF) via an SC connector."
    ::= { etsysOidPhy 29 }

etsysOidPhy10GbExEW OBJECT-IDENTITY
    STATUS      current
--  Name        "10GBASE-EW"
--  Date        "200701251558Z"  - Thu Jan 25 15:58 UTC 2007
    DESCRIPTION
        "Enterasys 10GBASE-EW, XENPAK 10-Gigabit Ethernet WAN Interface
         with 1550 nanometer serial port for 10-Gigabit Ethernet over
         single-mode fiber (SMF) via an SC connector."
    ::= { etsysOidPhy 30 }

etsysOidPhy10GbExLX4 OBJECT-IDENTITY
    STATUS      current
--  Name        "10GBASE-LX4"
--  Date        "200701251558Z"  - Thu Jan 25 15:58 UTC 2007
    DESCRIPTION
        "Enterasys 10GBASE-LX4, XENPAK 10-Gigabit Ethernet LAN Interface
         with 4 channel WWDM 1310 nanometer serial port for 10-Gigabit
         Ethernet over multimode fiber (MMF) and single-mode fiber (SMF)
         via an SC connector."
    ::= { etsysOidPhy 31 }

etsysOidPhy1Hx16TX OBJECT-IDENTITY
    STATUS      current
--  Name        "1H-16TX"
--  Date        "200106261900Z"
    DESCRIPTION
        "Enterasys 16 port 100BASE-TX option module."
    ::= { etsysOidPhy 32 }

etsysOidPhy1Gx2GBIC OBJECT-IDENTITY
    STATUS      current
--  Name        "1G-2GBIC"
--  Date        "200106261900Z"
    DESCRIPTION
        "Enterasys 2 port GBIC option module."
    ::= { etsysOidPhy 33 }

etsysOidPhy1Gx2MGBIC OBJECT-IDENTITY
    STATUS      current
--  Name        "1G-2MGBIC"
--  Date        "200106261900Z"
    DESCRIPTION
        "Enterasys 2 port Mini-GBIC option module."
    ::= { etsysOidPhy 34 }

etsysOidPhy1Hx2TX OBJECT-IDENTITY
    STATUS      current
--  Name        "1G-2TX"
--  Date        "200106261900Z"
    DESCRIPTION
        "Enterasys 2 port 1000BASE-T option module."
    ::= { etsysOidPhy 35 }

etsysOidPhyZPIMxZ1 OBJECT-IDENTITY
    STATUS      current
--  Name        "ZPIM-Z1"
--  Date        "200106261900Z"
    DESCRIPTION
        "Enterasys single port 850nm CWDM 10GbE uplink module."
    ::= { etsysOidPhy 36 }

etsysOidPhyER16xCS OBJECT-IDENTITY
    STATUS      current
--  Name        "ER16-CS"
--  Date        "200109261800Z"
    DESCRIPTION
        "Enterasys 16 slot modular chassis for the X-Pedition ER16."
    ::= { etsysOidPhy 37 }

etsysOidPhyXPx16 OBJECT-IDENTITY
    STATUS      current
--  Name        "XP-16"
--  Date        "200109261800Z"
    DESCRIPTION
        "Enterasys 16 slot modular chassis for the X-Pedition 8600."
    ::= { etsysOidPhy 38 }

etsysOidPhyXPx8 OBJECT-IDENTITY
    STATUS      current
--  Name        "XP-8"
--  Date        "200109261800Z"
    DESCRIPTION
        "Enterasys 8 slot modular chassis for the X-Pedition 8000."
    ::= { etsysOidPhy 39 } 

etsysOidPhyXPx2xB128 OBJECT-IDENTITY
    STATUS      current
--  Name        "SSR-2-B128"
--  Date        "200109261800Z"
    DESCRIPTION
        "Enterasys 5 slot chassis (3 fixed with 2 expansion) for 
         X-Pedition 2000 series."
    ::= { etsysOidPhy 40 }

etsysOidPhyXPx2xGSX OBJECT-IDENTITY
    STATUS      current
--  Name        "XP-2-GSX"
--  Date        "200109261800Z"
    DESCRIPTION
        "Enterasys 5 slot fixed chassis for the X-Pedition 2000 series."
    ::= { etsysOidPhy 41 }

etsysOidPhyER16x04 OBJECT-IDENTITY
    STATUS      current
--  Name        "ER16-04"
--  Date        "200109261800Z"
    DESCRIPTION
        "Enterasys 4 port 1000BASE GBIC (T-Series) routing module
         for the X-Pedition ER16."
    ::= { etsysOidPhy 42 }

etsysOidPhyER16x08 OBJECT-IDENTITY
    STATUS      current
--  Name        "ER16-08"
--  Date        "200109261800Z"
    DESCRIPTION
        "Enterasys 8 port 1000BASE GBIC (T-Series) routing module
         for the X-Pedition ER16."
    ::= { etsysOidPhy 43 }

etsysOidPhyER16xSXx08 OBJECT-IDENTITY
    STATUS      current
--  Name        "ER16-SX-08"
--  Date        "200109261800Z"
    DESCRIPTION
        "Enterasys 8-port 1000BASE-SX (T-Series) routing module
         for the X-Pedition ER16."
    ::= { etsysOidPhy 44 }

etsysOidPhyER16xTXx24 OBJECT-IDENTITY
    STATUS      current
--  Name        "ER16-TX-24"
--  Date        "200109261800Z"
    DESCRIPTION
        "Enterasys 24 port 10/100BASE-TX (T-Series) routing module
         for the X-Pedition ER16."
    ::= { etsysOidPhy 45 }

etsysOidPhyER16xTXx32 OBJECT-IDENTITY
    STATUS      current
--  Name        "ER16-TX-32"
--  Date        "200109261800Z"
    DESCRIPTION
        "Enterasys 32 port 10/100BASE-TX module (T-Series)
         for the X-Pedition ER16."
    ::= { etsysOidPhy 46 }

etsysOidPhyER16xAC OBJECT-IDENTITY
    STATUS      current
--  Name        "ER16-AC"
--  Date        "200109261800Z"
    DESCRIPTION
        "Enterasys AC power supply for the X-Pedition ER16."
    ::= { etsysOidPhy 47 }

etsysOidPhyER16xFN OBJECT-IDENTITY
    STATUS      current
--  Name        "ER16-FN"
--  Date        "200109261800Z"
    DESCRIPTION
        "Enterasys Fan Tray for the X-Pedition ER16."
    ::= { etsysOidPhy 48 }

etsysOidPhyER16xCK OBJECT-IDENTITY
    STATUS      current
--  Name        "ER16-CK"
--  Date        "200109261800Z"
    DESCRIPTION
        "Enterasys Clock card module for the X-Pedition ER16."
    ::= { etsysOidPhy 49 }

etsysOidPhyER16xSF OBJECT-IDENTITY
    STATUS      current
--  Name        "ER16-SF"
--  Date        "200109261800Z"
    DESCRIPTION
        "Enterasys switching fabric module for the X-Pedition ER16."
    ::= { etsysOidPhy 50 }

etsysOidPhyER16xCM3 OBJECT-IDENTITY
    STATUS      current
--  Name        "ER16-CM3"
--  Date        "200109261800Z"
    DESCRIPTION
        "Enterasys CM3 control module (291 MHz) for the X-Pedition ER16."
    ::= { etsysOidPhy 51 }

etsysOidPhyER16xCM4 OBJECT-IDENTITY
    STATUS      current
--  Name        "ER16-CM4"
--  Date        "200109261800Z"
    DESCRIPTION
        "Enterasys CM4 control module (380 MHz) for the X-Pedition ER16."
    ::= { etsysOidPhy 52 }

etsysOidPhySSRxPSx16 OBJECT-IDENTITY
    STATUS      current
--  Name        "SSR-PS-16"
--  Date        "200109261800Z"
    DESCRIPTION
        "Enterasys AC power supply for the X-Pedition 8600."
    ::= { etsysOidPhy 53 }

etsysOidPhySSRxPSx16xDC OBJECT-IDENTITY
    STATUS      current
--  Name        "SSR-PS-16-DC"
--  Date        "200109261800Z"
    DESCRIPTION
        "Enterasys DC power supply for the X-Pedition 8600."
    ::= { etsysOidPhy 54 }

etsysOidPhySSRxSFx16 OBJECT-IDENTITY
    STATUS      current
--  Name        "SSR-SF-16"
--  Date        "200109261800Z"
    DESCRIPTION
        "Enterasys switch fabric module for the X-Pedition 8600."
    ::= { etsysOidPhy 55 }

etsysOidPhySSRxFANx16 OBJECT-IDENTITY
    STATUS      current
--  Name        "SSR-FAN-16"
--  Date        "200109261800Z"
    DESCRIPTION
        "Enterasys fan tray module for the X-Pedition 8600."
    ::= { etsysOidPhy 56 }

etsysOidPhySSRxPSx8 OBJECT-IDENTITY
    STATUS      current
--  Name        "SSR-PS-8"
--  Date        "200109261800Z"
    DESCRIPTION
        "Enterasys AC power supply for the X-Pedition 8000."
    ::= { etsysOidPhy 57 }

etsysOidPhySSRxPSx8xDC OBJECT-IDENTITY
    STATUS      current
--  Name        "SSR-PS-8-DC"
--  Date        "200109261800Z"
    DESCRIPTION
        "Enterasys DC power supply for the X-Pedition 8000."
    ::= { etsysOidPhy 58 }

etsysOidPhySSRxFANx8 OBJECT-IDENTITY
    STATUS      current
--  Name        "SSR-FAN-8"
--  Date        "200109261800Z"
    DESCRIPTION
        "Enterasys fan tray module for the X-Pedition 8000."
    ::= { etsysOidPhy 59 }

etsysOidPhyXPxPCMCIA OBJECT-IDENTITY
    STATUS      current
--  Name        "XP-PCMCIA"
--  Date        "200109261800Z"
    DESCRIPTION
        "Enterasys 8 MB PCMCIA Flash memory card for the X-Pedition
         8000 series and ER16 control modules."
    ::= { etsysOidPhy 60 }

etsysOidPhyXPxPCMCIAx16LN OBJECT-IDENTITY
    STATUS      current
--  Name        "XP-PCMCIA-16LN"
--  Date        "200109261800Z"
    DESCRIPTION
        "Enterasys 16 MB PCMCIA Flash memory card for the X-Pedition
         8000 series and ER16 control modules."
    ::= { etsysOidPhy 61 }

etsysOidPhyXPxPCMCIAx16AT OBJECT-IDENTITY
    STATUS      current
--  Name        "XP-PCMCIA-16AT"
--  Date        "200109261800Z"
    DESCRIPTION
        "Enterasys 16 MB ATA PCMCIA Flash memory card for the X-Pedition
         8000 series and ER16 control modules."
    ::= { etsysOidPhy 62 }

etsysOidPhyXPxPCMCIAx32AT OBJECT-IDENTITY
    STATUS      current
--  Name        "XP-PCMCIA-32AT"
--  Date        "200109261800Z"
    DESCRIPTION
        "Enterasys 32 MB ATA PCMCIA Flash memory card for the X-Pedition
         8000 series and ER16 control modules."
    ::= { etsysOidPhy 63 }

etsysOidPhySSRxCM2 OBJECT-IDENTITY
    STATUS      current
--  Name        "SSR-CM2"
--  Date        "200109261800Z"
    DESCRIPTION
        "Enterasys CM2 control module (198 MHz CPU)
         for the X-Pedition 8000 series."
    ::= { etsysOidPhy 64 }

etsysOidPhySSRxCM3 OBJECT-IDENTITY
    STATUS      current
--  Name        "SSR-CM3"
--  Date        "200109261800Z"
    DESCRIPTION
        "Enterasys CM3 control module (291 MHz CPU)
         for the X-Pedition 8000 series."
    ::= { etsysOidPhy 65 }

etsysOidPhySSRxCM4 OBJECT-IDENTITY
    STATUS      current
--  Name        "SSR-CM4"
--  Date        "200109261800Z"
    DESCRIPTION
        "Enterasys CM4 control module (375/380 MHz CPU)
         for the X-Pedition 8000 series."
    ::= { etsysOidPhy 66 }

etsysOidPhy10100T  OBJECT-IDENTITY
    STATUS      deprecated
--  Name        ""
--  Date        "200109261800Z"
    DESCRIPTION 
        "Enterasys 10/100BASE copper port with RJ45 connector.
         Use etsysOidPhyFrtPnlFastEthRJ45 instead."
    ::= { etsysOidPhy 67 }

etsysOidPhySSRxARE OBJECT-IDENTITY
    STATUS      current
--  Name        "SSR-ARE"
--  Date        "200109261800Z"
    DESCRIPTION
        "Enterasys Advanced Routing Engine (supports AppleTalk)
         for the X-Pedition 8000 series."
    ::= { etsysOidPhy 68 }

etsysOidPhySSRxATM29x02 OBJECT-IDENTITY
    STATUS      current
--  Name        "SSR-ATM29-02"
--  Date        "200109261800Z"
    DESCRIPTION
        "Enterasys 2 port ATM OC-3c (T-Series) routing module
         for the X-Pedition 8000 series."
    ::= { etsysOidPhy 69 }

etsysOidPhySSRxGTX32x02 OBJECT-IDENTITY
    STATUS      current
--  Name        "SSR-GTX32-02"
--  Date        "200109261800Z"
    DESCRIPTION
        "Enterasys 2 port 1000BASE-T (T-Series) routing module 
         (Cat 5 RJ45) for the X-Pedition 8000 series."
    ::= { etsysOidPhy 70 }

etsysOidPhySSRxGSX11x02 OBJECT-IDENTITY
    STATUS      current
--  Name        "SSR-GSX11-02"
--  Date        "200109261800Z"
    DESCRIPTION
        "Enterasys 2 port 1000BASE-SX routing module with SC connectors
         (for MMF only) with 4 MB of RAM for the X-Pedition 8000 series."
    ::= { etsysOidPhy 71 }

etsysOidPhySSRxGSX21x02 OBJECT-IDENTITY
    STATUS      current
--  Name        "SSR-GSX21-02"
--  Date        "200109261800Z"
    DESCRIPTION
        "Enterasys 2 port 1000BASE-SX routing module with SC connectors
         (for MMF only) with 16 MB of RAM for the X-Pedition 8000 series."
    ::= { etsysOidPhy 72 }

etsysOidPhySSRxGSX21x02xAA OBJECT-IDENTITY
    STATUS      current
--  Name        "SSR-GSX21-02-AA"
--  Date        "200109261800Z"
    DESCRIPTION
        "Enterasys 2 port 1000BASE-SX  (AA Series) routing module with
         SC connectors (for MMF only) for the X-Pedition 8000 series."
    ::= { etsysOidPhy 73 }

etsysOidPhySSRxGSX31x02 OBJECT-IDENTITY
    STATUS      current
--  Name        "SSR-GSX31-02"
--  Date        "200109261800Z"
    DESCRIPTION
        "Enterasys 2 port 1000BASE-SX (T-Series) routing module 
         with SC connectors (for MMF only) for the X-Pedition 8000 series."
    ::= { etsysOidPhy 74 }

etsysOidPhySSRxGLX19x02 OBJECT-IDENTITY
    STATUS      current
--  Name        "SSR-GLX19-02"
--  Date        "200109261800Z"
    DESCRIPTION
        "Enterasys 2 port 1000BASE-LX routing module with SC connectors
         (for MMF or SMF) with 4 MB of RAM for the X-Pedition 8000 series."
    ::= { etsysOidPhy 75 }

etsysOidPhySSRxGLX29x02 OBJECT-IDENTITY
    STATUS      current
--  Name        "SSR-GLX29-02"
--  Date        "200109261800Z"
    DESCRIPTION
        "Enterasys 2 port 1000BASE-LX routing module with SC connectors
         (for MMF or SMF) with 16 MB of RAM for the X-Pedition 8000 series."
    ::= { etsysOidPhy 76 }

etsysOidPhySSRxGLX29x02xAA OBJECT-IDENTITY
    STATUS      current
--  Name        "SSR-GLX29-02-AA"
--  Date        "200109261800Z"
    DESCRIPTION
        "Enterasys 2 port 1000BASE-LX (AA-Series) routing module 
         with SC connectors (for MMF or SMF) with 16 MB of RAM for
         X-Pedition 8000 series."
    ::= { etsysOidPhy 77 }

etsysOidPhySSRxGLX39x02 OBJECT-IDENTITY
    STATUS      current
--  Name        "SSR-GLX39-02"
--  Date        "200109261800Z"
    DESCRIPTION
        "Enterasys 2 port 1000BASE-LX (T-Series) routing module 
         with SC connectors (for MMF or SMF) for the X-Pedition 8000 series."
    ::= { etsysOidPhy 78 }

etsysOidPhySSRxGLH39x02 OBJECT-IDENTITY
    STATUS      current
--  Name        "SSR-GLH39-02"
--  Date        "200109261800Z"
    DESCRIPTION
        "Enterasys 2 port 1000BASE-LX (T-Series) long haul routing module
         with SC connectors (for MMF/SMF) for the X-Pedition 8000 series.
         These ports have a 70 km range."
    ::= { etsysOidPhy 79 }

etsysOidPhySSRxGLX70x01 OBJECT-IDENTITY
    STATUS      current
--  Name        "SSR-GLX70-01"
--  Date        "200109261800Z"
    DESCRIPTION
        "Enterasys 1 port 1000BASE-LX long haul routing module with
         SC connector (for SMF) with 16 MB of RAM for the X-Pedition
         8000 series.  This port has a 70 km range."
    ::= { etsysOidPhy 80 }

etsysOidPhySSRxGLX70x01xAA OBJECT-IDENTITY
    STATUS      current
--  Name        "SSR-GLX70-01-AA"
--  Date        "200109261800Z"
    DESCRIPTION
        "Enterasys 1 port 1000BASE-LX (AA-Series) routing module with
         SC connector (for SMF) with 16 MB of RAM for the X-Pedition
         8000 series.  This port has a 70 km range."
    ::= { etsysOidPhy 81 }

etsysOidPhySSRxHTX12x08 OBJECT-IDENTITY
    STATUS      current
--  Name        "SSR-HTX12-08"
--  Date        "200109261800Z"
    DESCRIPTION
        "Enterasys 8 port 10/100BASE-TX routing module with RJ45
         connectors (for Cat 5) with 4 MB of RAM for the X-Pedition
         8000 series."
    ::= { etsysOidPhy 82 }

etsysOidPhySSRxHTX12x08xAA OBJECT-IDENTITY
    STATUS      current
--  Name        "SSR-HTX12-08-AA"
--  Date        "200109261800Z"
    DESCRIPTION
        "Enterasys 8 port 10/100BASE-TX (AA-Series) routing module
         with RJ45 connectors (for Cat 5) with 4 MB of RAM for the
         X-Pedition 8000 series."
    ::= { etsysOidPhy 83 }

etsysOidPhySSRxHTX22x08 OBJECT-IDENTITY
    STATUS      current
--  Name        "SSR-HTX22-08"
--  Date        "200109261800Z"
    DESCRIPTION
        "Enterasys 8 port 10/100BASE-TX routing module with
         RJ45 connectors (for Cat 5) and 16 MB of RAM for the
         X-Pedition 8000 series."
    ::= { etsysOidPhy 84 }

etsysOidPhySSRxHTX22x08xAA OBJECT-IDENTITY
    STATUS      current
--  Name        "SSR-HTX22-08-AA"
--  Date        "200109261800Z"
    DESCRIPTION
        "Enterasys 8 port 10/100BASE-TX (AA-Series) routing module with
         RJ45 connectors (for Cat 5) for the X-Pedition 8000 series."
    ::= { etsysOidPhy 85 }

etsysOidPhySSRxHTX32x16 OBJECT-IDENTITY
    STATUS      current
--  Name        "SSR-HTX32-16"
--  Date        "200109261800Z"
    DESCRIPTION
        "Enterasys 16 port 10/100BASE-TX (T Series) with RJ45 connectors
         (for Cat 5) routing module for the X-Pedition 8000 series."
    ::= { etsysOidPhy 86 }

etsysOidPhySSRxHFX11x08 OBJECT-IDENTITY
    STATUS      current
--  Name        "SSR-HFX11-08"
--  Date        "200109261800Z"
    DESCRIPTION
        "Enterasys 8 port 100BASE-FX routing module with SC connectors
         (for MMF) and 4 MB of RAM for the X-Pedition 8000 series."
    ::= { etsysOidPhy 87 }

etsysOidPhySSRxHFX21x08 OBJECT-IDENTITY
    STATUS      current
--  Name        "SSR-HFX21-08"
--  Date        "200109261800Z"
    DESCRIPTION
        "Enterasys 8 port 100BASE-FX routing module with SC connectors
         (for MMF) and 16 MB of RAM for the X-Pedition 8000 series."
    ::= { etsysOidPhy 88 }

etsysOidPhySSRxHFX21x08xAA OBJECT-IDENTITY
    STATUS      current
--  Name        "SSR-HFX21-08-AA"
--  Date        "200109261800Z"
    DESCRIPTION
        "Enterasys 8 port 100BASE-FX (AA-Series) routing module
         with SC connectors (for MMF) and 16 MB of RAM for the
         X-Pedition 8000 series."
    ::= { etsysOidPhy 89 }

etsysOidPhySSRxHFX29x08 OBJECT-IDENTITY
    STATUS      current
--  Name        "SSR-HFX29-08"
--  Date        "200109261800Z"
    DESCRIPTION
        "Enterasys 8 port 100BASE-FX routing module with SC connectors
         (for SMF) and 16 MB of RAM for the X-Pedition 8000 series."
    ::= { etsysOidPhy 90 }

etsysOidPhySSRxHFX29x08xAA OBJECT-IDENTITY
    STATUS      current
--  Name        "SSR-HFX29-08-AA"
--  Date        "200109261800Z"
    DESCRIPTION
        "Enterasys 8 port 100BASE-FX (AA-Series) routing module
         with SC connectors (for SMF) and 16 MB of RAM for the
         X-Pedition 8000 series."
    ::= { etsysOidPhy 91 }

etsysOidPhySSRxFDDIx02 OBJECT-IDENTITY
    STATUS      current
--  Name        "SSR-FDDI-02"
--  Date        "200109261800Z"
    DESCRIPTION
        "Enterasys 2 port FDDI routing module for the X-Pedition 8000 series."
    ::= { etsysOidPhy 92 }

etsysOidPhySSRxHSSIx02 OBJECT-IDENTITY
    STATUS      current
--  Name        "SSR-HSSI-02"
--  Date        "200109261800Z"
    DESCRIPTION
        "Enterasys 2 port HSSI routing module for the X-Pedition 8000 series."
    ::= { etsysOidPhy 93 }

etsysOidPhySSRxHSSIx02xAA OBJECT-IDENTITY
    STATUS      current
--  Name        "SSR-HSSI-02-AA"
--  Date        "200109261800Z"
    DESCRIPTION
        "Enterasys 2 port HSSI (AA-Series) routing module 
         for the X-Pedition 8000 series."
    ::= { etsysOidPhy 94 }

etsysOidPhySSRxSERCx04 OBJECT-IDENTITY
    STATUS      current
--  Name        "SSR-SERC-04"
--  Date        "200109261800Z"
    DESCRIPTION
        "Enterasys 4 port Serial routing module with compression
         for the X-Pedition 8000 series."
    ::= { etsysOidPhy 95 }

etsysOidPhySSRxSERCx04xAA OBJECT-IDENTITY
    STATUS      current
--  Name        "SSR-SERC-04-AA"
--  Date        "200109261800Z"
    DESCRIPTION
        "Enterasys 4 port Serial (AA-Series) routing module
         for the X-Pedition 8000 series.  This module supports compression."
    ::= { etsysOidPhy 96 }

etsysOidPhySSRxSERCEx04 OBJECT-IDENTITY
    STATUS      current
--  Name        "SSR-SERCE-04"
--  Date        "200109261800Z"
    DESCRIPTION
        "Enterasys 4 port Serial routing module for the X-Pedition 8000 series.
         This module supports compression and encryption."
    ::= { etsysOidPhy 97 }

etsysOidPhySSRxSERCEx04xAA OBJECT-IDENTITY
    STATUS      current
--  Name        "SSR-SERCE-04-AA"
--  Date        "200109261800Z"
    DESCRIPTION
        "Enterasys 4 port Serial (AA-Series) routing module for the X-Pedition
         8000 series. This module supports compression and encryption."
    ::= { etsysOidPhy 98 }

etsysOidPhySSRxPOS21x04 OBJECT-IDENTITY
    STATUS      current
--  Name        "SSR-POS21-04"
--  Date        "200109261800Z"
    DESCRIPTION
        "Enterasys 4 port OC-3c/STM-1 Packet over SONET/SDH (T-Series)
         routing module with MT-RJ connectors (for MMF) for the X-Pedition
         8000 series."
    ::= { etsysOidPhy 99 }

etsysOidPhySSRxPOS29x04 OBJECT-IDENTITY
    STATUS      current
--  Name        "SSR-POS29-04"
--  Date        "200109261800Z"
    DESCRIPTION
        "Enterasys 4 port OC-3c/STM-1 Packet over SONET/SDH (T-Series)
         routing module with MT-RJ connectors (for SMF) for the X-Pedition
         8000 series."
    ::= { etsysOidPhy 100 }

etsysOidPhySSRxPOS31x02 OBJECT-IDENTITY
    STATUS      current
--  Name        "SSR-POS31-02"
--  Date        "200109261800Z"
    DESCRIPTION
        "Enterasys 2 port OC-12c/STM-4 Packet over SONET/SDH (T-Series)
         routing module with SC connectors (for MMF) for the X-Pedition 8000
         series."
    ::= { etsysOidPhy 101 }

etsysOidPhySSRxPOS39x02 OBJECT-IDENTITY
    STATUS      current
--  Name        "SSR-POS39-02"
--  Date        "200109261800Z"
    DESCRIPTION
        "Enterasys 2 port OC-12c/STM-4 Packet over SONET/SDH (T-Series)
         routing module with SC connectors (form SMF) for the X-Pedition 8000
         series."
    ::= { etsysOidPhy 102 }

etsysOidPhyXP2IntCM OBJECT-IDENTITY
    STATUS      current
--  Name        ""
--  Date        "200109261800Z"
    DESCRIPTION
        "Enterasys integrated control module in X-Pedition 2000 series."
    ::= { etsysOidPhy 103 }

etsysOidPhyXP2IntPs OBJECT-IDENTITY
    STATUS      current
--  Name        ""
--  Date        "200109261800Z"
    DESCRIPTION
        "Enterasys integrated power supply in X-Pedition 2000 series."
    ::= { etsysOidPhy 104 }

etsysOidPhyXP2IntTX08 OBJECT-IDENTITY
    STATUS      current
--  Name        ""
--  Date        "200109261800Z"
    DESCRIPTION
        "Enterasys integrated 8 port 10/100BASE-TX routing module
         with RJ45 connectors (for Cat 5) in X-Pedition 2000 series."
    ::= { etsysOidPhy 105 }

etsysOidPhyXPx2xTX OBJECT-IDENTITY
    STATUS      current
--  Name        "XP-2-TX"
--  Date        "200109261800Z"
    DESCRIPTION
        "Enterasys 8 port 10/100BASE-TX routing module
         with RJ45 connectors (for Cat 5) for the X-Pedition 2000 series."
    ::= { etsysOidPhy 106 }

etsysOidPhyXPx2xTXxAA OBJECT-IDENTITY
    STATUS      current
--  Name        "XP-2-TX-AA"
--  Date        "200109261800Z"
    DESCRIPTION
        "Enterasys 8 port 10/100BASE-TX (AA-Series) routing module
         with RJ45 connectors (for Cat 5) for the X-Pedition 2000 series."
    ::= { etsysOidPhy 107 }

etsysOidPhyXPx2xLX OBJECT-IDENTITY
    STATUS      current
--  Name        "XP-2-LX"
--  Date        "200109261800Z"
    DESCRIPTION
        "Enterasys 2 port 1000BASE-LX routing module
         with SC connectors (for SMF) for the X-Pedition 2000 series."
    ::= { etsysOidPhy 108 }

etsysOidPhyXPx2xLXxAA OBJECT-IDENTITY
    STATUS      current
--  Name        "XP-2-LX-AA"
--  Date        "200109261800Z"
    DESCRIPTION
        "Enterasys 2 port 1000BASE-LX  (AA-Series) routing module
         with SC connectors (for SMF) for the X-Pedition 2000 series."
    ::= { etsysOidPhy 109 }

etsysOidPhyXPx2xLX70 OBJECT-IDENTITY
    STATUS      current
--  Name        "XP-2-LX70"
--  Date        "200109261800Z"
    DESCRIPTION
        "Enterasys 1 port 1000BASE-LX long haul routing module
         with SC connector (for SMF) for the X-Pedition 2000 series.
         This module has a 70 km range."
    ::= { etsysOidPhy 110 }

etsysOidPhyXPx2xLX70xAA OBJECT-IDENTITY
    STATUS      current
--  Name        "XP-2-LX70-AA"
--  Date        "200109261800Z"
    DESCRIPTION
        "Enterasys 1 port 1000BASE-LX long haul (AA-Series) routing
         module with SC connectors (for SMF) for the X-Pedition 2000 series.
         This module has a 70 km range."
    ::= { etsysOidPhy 111 }

etsysOidPhyXPx2xSX OBJECT-IDENTITY
    STATUS      current
--  Name        "XP-2-SX"
--  Date        "200109261800Z"
    DESCRIPTION
        "Enterasys 2 port 1000BASE-SX routing module with SC connectors
         (for MMF) for the X-Pedition 2000 series."
    ::= { etsysOidPhy 112 }

etsysOidPhyXPx2xSXxAA OBJECT-IDENTITY
    STATUS      current
--  Name        "XP-2-SX-AA"
--  Date        "200109261800Z"
    DESCRIPTION
        "Enterasys 2 port 1000BASE-SX (AA-Series) routing module
         with SC connectors (for MMF) for the X-Pedition 2000 series."
    ::= { etsysOidPhy 113 }

etsysOidPhyXPx2xFX OBJECT-IDENTITY
    STATUS      current
--  Name        "XP-2-FX"
--  Date        "200109261800Z"
    DESCRIPTION
        "Enterasys 8 port 100BASE-FX routing module with MT-RJ connectors
         for the X-Pedition 2000 series."
    ::= { etsysOidPhy 114 }

etsysOidPhyXPx2xFXxAA OBJECT-IDENTITY
    STATUS      current
--  Name        "XP-2-FX-AA"
--  Date        "200109261800Z"
    DESCRIPTION
        "Enterasys 8 port 100BASE-FX (AA-Series) routing module with MT-RJ
         connectors for the X-Pedition 2000 series."
    ::= { etsysOidPhy 115 }

etsysOidPhyXPx2xHSSIxAA OBJECT-IDENTITY
    STATUS      current
--  Name        "XP-2-HSSI-AA"
--  Date        "200109261800Z"
    DESCRIPTION
        "Enterasys 2 port HSSI routing module for the X-Pedition 2000 series."
    ::= { etsysOidPhy 116 }

etsysOidPhyXPx2xSER OBJECT-IDENTITY
    STATUS      current
--  Name        "XP-2-SER"
--  Date        "200109261800Z"
    DESCRIPTION
        "Enterasys 2 port Serial routing module for the
         X-Pedition 2000 series."
    ::= { etsysOidPhy 117 }

etsysOidPhyXPx2xSERxAA OBJECT-IDENTITY
    STATUS      current
--  Name        "XP-2-SER-AA"
--  Date        "200109261800Z"
    DESCRIPTION
        "Enterasys 2 port Serial (AA-Series) routing module for
         X-Pedition 2000 series."
    ::= { etsysOidPhy 118 }

etsysOidPhyXPx2xSERC OBJECT-IDENTITY
    STATUS      current
--  Name        "XP-2-SERC"
--  Date        "200109261800Z"
    DESCRIPTION
        "Enterasys 4 port Serial routing module for the X-Pedition
         2000 series.  This module support compression."
    ::= { etsysOidPhy 119 }

etsysOidPhyXPx2xSERCxAA OBJECT-IDENTITY
    STATUS      current
--  Name        "XP-2-SERC-AA"
--  Date        "200109261800Z"
    DESCRIPTION
        "Enterasys 4 port Serial (AA-Series) routing module for
         X-Pedition 2000 series.  This module supports compression."
    ::= { etsysOidPhy 120 }

etsysOidPhyXPx2xSERCE OBJECT-IDENTITY
    STATUS      current
--  Name        "XP-2-SERCE"
--  Date        "200109261800Z"
    DESCRIPTION
        "Enterasys 4 port Serial routing module for the X-Pedition
         2000 series.  This module supports compression and encryption."
    ::= { etsysOidPhy 121 }

etsysOidPhyXPx2xSERCExAA OBJECT-IDENTITY
    STATUS      current
--  Name        "XP-2-SERCE-AA"
--  Date        "200109261800Z"
    DESCRIPTION
        "Enterasys 4 port Serial (AA-Series) routing module for
         X-Pedition 2000 series.  This module supports compression
         and encryption."
    ::= { etsysOidPhy 122 }

etsysOidPhyXPxAPHYx21 OBJECT-IDENTITY
    STATUS      current
--  Name        "XP-APHY-21"
--  Date        "200109261800Z"
    DESCRIPTION
        "Enterasys field replaceable OC-3c Multimode Fiber physical
         module for the X-Pedition ATM routing module."
    ::= { etsysOidPhy 123 }

etsysOidPhyXPxAPHYx22 OBJECT-IDENTITY
    STATUS      current
--  Name        "XP-APHY-22"
--  Date        "200109261800Z"
    DESCRIPTION
        "Enterasys field replaceable OC-3c UTP physical module for
         X-Pedition ATM routing module."
    ::= { etsysOidPhy 124 }

etsysOidPhyXPxAPHYx29IR OBJECT-IDENTITY
    STATUS      current
--  Name        "XP-APHY-29IR"
--  Date        "200109261800Z"
    DESCRIPTION
        "Enterasys field replaceable OC-3c SMF-IR physical module for
         X-Pedition ATM routing module."
    ::= { etsysOidPhy 125 }

etsysOidPhyXPxAPHYx67 OBJECT-IDENTITY
    STATUS      current
--  Name        "XP-APHY-67"
--  Date        "200109261800Z"
    DESCRIPTION
        "Enterasys field replaceable DS-3/T3 coax physical module for
         X-Pedition ATM routing module."
    ::= { etsysOidPhy 126 } 

etsysOidPhyXPxAPHYx77 OBJECT-IDENTITY
    STATUS      current
--  Name        "XP-APHY-77"
--  Date        "200109261800Z"
    DESCRIPTION
        "Enterasys field replaceable E-3 coax physical module for the
         X-Pedition ATM routing module."
    ::= { etsysOidPhy 127 }

etsysOidPhyXPxAPHYx82 OBJECT-IDENTITY
    STATUS      current
--  Name        "XP-APHY-82"
--  Date        "200109261800Z"
    DESCRIPTION
        "Enterasys field replaceable T-1 UTP Multimode Fiber physical module
         for the X-Pedition ATM routing module."
    ::= { etsysOidPhy 128 }

etsysOidPhyXPxAPHYx92 OBJECT-IDENTITY
    STATUS      current
--  Name        "XP-APHY-92"
--  Date        "200109261800Z"
    DESCRIPTION
        "Enterasys field replaceable E-1 UTP Multimode Fiber physical module
         for the X-Pedition ATM routing module."
    ::= { etsysOidPhy 129 }

etsysOidPhyXPxFPHYx01 OBJECT-IDENTITY
    STATUS      current
--  Name        "XP-FPHY-01"
--  Date        "200109261800Z"
    DESCRIPTION
        "Enterasys field replaceable FDDI MMF DAS/SAS port with SC connector
         for the X-Pedition FDDI routing module."
    ::= { etsysOidPhy 130 }

etsysOidPhyXPxFPHYx02 OBJECT-IDENTITY
    STATUS      current
--  Name        "XP-FPHY-02"
--  Date        "200109261800Z"
    DESCRIPTION
        "Enterasys field replaceable FDDI UTP SAS port with RJ45 connector
         for the X-Pedition FDDI routing module."
    ::= { etsysOidPhy 131 }

etsysOidPhyXPxFPHYx09 OBJECT-IDENTITY
    STATUS      current
--  Name        "XP-FPHY-09"
--  Date        "200109261800Z"
    DESCRIPTION
        "Enterasys field replaceable FDDI SMF DAS/SAS port with SC connector
         for the X-Pedition FDDI routing module."
    ::= { etsysOidPhy 132 }

etsysOidPhyHssiPort OBJECT-IDENTITY
    STATUS      current
--  Name        ""
--  Date        "200109261800Z"
    DESCRIPTION
        "Enterasys serial HSSI port."
    ::= { etsysOidPhy 133 }

etsysOidPhySerialConnection OBJECT-IDENTITY
    STATUS      current
--  Name        ""
--  Date        "200109261800Z"
    DESCRIPTION
        "Enterasys serial port with no connection."
    ::= { etsysOidPhy 134 }

etsysOidPhySerialEia530AConnection OBJECT-IDENTITY
    STATUS      current
--  Name        ""
--  Date        "200109261800Z"
    DESCRIPTION
        "Enterasys serial port with EIA 530A connection."
    ::= { etsysOidPhy 135 }

etsysOidPhySerialEia530Connection OBJECT-IDENTITY
    STATUS      current
--  Name        ""
--  Date        "200109261800Z"
    DESCRIPTION
        "Enterasys serial port with EIA 530 connection."
    ::= { etsysOidPhy 136 }

etsysOidPhySerialV35Connection OBJECT-IDENTITY
    STATUS      current
--  Name        ""
--  Date        "200109261800Z"
    DESCRIPTION
        "Enterasys serial port with V.35 connection."
    ::= { etsysOidPhy 137 }

etsysOidPhySerialX21Connection OBJECT-IDENTITY
    STATUS      current
--  Name        ""
--  Date        "200109261800Z"
    DESCRIPTION
        "Enterasys serial port with X.21 connection."
    ::= { etsysOidPhy 138 }

etsysOidPhyGigEthSXPort OBJECT-IDENTITY
    STATUS      current
--  Name        ""
--  Date        "200109261800Z"
    DESCRIPTION
        "Enterasys fixed 1000BASE-SX Short Wave port with SC connector."
    ::= { etsysOidPhy 139 }

etsysOidPhyGigEthLXPort OBJECT-IDENTITY
    STATUS      current
--  Name        ""
--  Date        "200109261800Z"
    DESCRIPTION
        "Enterasys fixed 1000BASE-LX Long Wave port with SC connector."
    ::= { etsysOidPhy 140 }

etsysOidPhyGigEthLLXPort OBJECT-IDENTITY
    STATUS      current
--  Name        ""
--  Date        "200109261800Z"
    DESCRIPTION
        "Enterasys fixed 1000BASE-LX Long Haul (70 km range) port with
         SC connector."
    ::= { etsysOidPhy 141 }

etsysOidPhy6SSRLCGigEthBkplnPort OBJECT-IDENTITY
    STATUS      deprecated
--  Name        ""
--  Date        "200109261800Z"
    DESCRIPTION
        "Enterasys fixed 1000BASE port with Matrix Backplane connection
         for Matrix E5, E6, and E7.
         While, from a hardware point of view, this is a gig port interface
         to the Matrix backplane, from a user point of view this is just
         a FTM backplane port.  Use etsysOidPhyBackplaneFTM1 instead."
    ::= { etsysOidPhy 142 }

etsysOidPhyGPIMx01 OBJECT-IDENTITY
    STATUS      current
--  Name        "GPIM-01"
--  Date        "200109261800Z"
    DESCRIPTION
        "Enterasys removable 1000BASE-SX short wave physical interface module
         with SC connector."
    ::= { etsysOidPhy 143 }

etsysOidPhyGPIMx08 OBJECT-IDENTITY
    STATUS      current
--  Name        "GPIM-08"
--  Date        "200109261800Z"
    DESCRIPTION
        "Enterasys removable 1000BASE-LX long haul (70 km range) physical
         interface module with SC connector."
    ::= { etsysOidPhy 144 }

etsysOidPhyGPIMx09 OBJECT-IDENTITY
    STATUS      current
--  Name        "GPIM-09"
--  Date        "200109261800Z"
    DESCRIPTION
        "Enterasys removable 1000BASE-LX long wave physical interface module
         with SC connector."
    ::= { etsysOidPhy 145 }

etsysOidPhyFastEthMMFPort OBJECT-IDENTITY
    STATUS      current
--  Name        ""
--  Date        "200109261800Z"
    DESCRIPTION
        "Enterasys 100BASE-FX multi-mode fiber port."
    ::= { etsysOidPhy 146 }

etsysOidPhyFastEthSMFPort OBJECT-IDENTITY
    STATUS      current
--  Name        ""
--  Date        "200109261800Z"
    DESCRIPTION
        "Enterasys 100BASE-FX single-mode fiber port."
    ::= { etsysOidPhy 147 }

etsysOidPhyER16Slot OBJECT-IDENTITY
    STATUS      current
--  Name        ""
--  Date        "200109261800Z"
    DESCRIPTION
        "Enterasys module slot for the X-Pedition ER16 router."
    ::= { etsysOidPhy 148 }

etsysOidPhyXP8Slot OBJECT-IDENTITY
    STATUS      current
--  Name        ""
--  Date        "200109261800Z"
    DESCRIPTION
        "Enterasys module slot for the X-Pedition 8000 series routers."
    ::= { etsysOidPhy 149 }

etsysOidPhyXP2Slot OBJECT-IDENTITY
    STATUS      current
--  Name        ""
--  Date        "200109261800Z"
    DESCRIPTION
        "Enterasys module slot for the X-Pedition 2000 series, 5SSRM-02,
         and 6SSRM-02 routers."
    ::= { etsysOidPhy 150 }

etsysOidPhyXP8IntFlash OBJECT-IDENTITY
    STATUS      current
--  Name        ""
--  Date        "200109261800Z"
    DESCRIPTION
        "Enterasys integrated Flash memory in X-Pedition 8000 series and ER16."
    ::= { etsysOidPhy 151 }

etsysOidPhyPOSOC3MMF OBJECT-IDENTITY
    STATUS      current
--  Name        ""
--  Date        "200109261800Z"
    DESCRIPTION 
        "Enterasys fixed POS OC-3 multi-mode fiber port with MT-RJ connector."
    ::= { etsysOidPhy 152 }

etsysOidPhyPOSOC3SMF OBJECT-IDENTITY
    STATUS      current
--  Name        ""
--  Date        "200109261800Z"
    DESCRIPTION 
        "Enterasys fixed POS OC-3 single-mode fiber port with MT-RJ connector."
    ::= { etsysOidPhy 153 }

etsysOidPhyPOSOC12MMF OBJECT-IDENTITY
    STATUS      current
--  Name        ""
--  Date        "200109261800Z"
    DESCRIPTION 
        "Enterasys fixed POS OC-12 multi-mode fiber port with SC connector."
    ::= { etsysOidPhy 154 }

etsysOidPhyPOSOC12SMF OBJECT-IDENTITY
    STATUS      current
--  Name        ""
--  Date        "200109261800Z"
    DESCRIPTION 
        "Enterasys fixed POS OC-12 single-mode fiber port with SC connector."
    ::= { etsysOidPhy 155 }

etsysOidPhy100BASEMTRJMMF OBJECT-IDENTITY
    STATUS      current
--  Name        ""
--  Date        "200109261800Z"
    DESCRIPTION 
        "Enterasys fixed 100BASE multi-mode fiber port with MT-RJ connector."
    ::= { etsysOidPhy 156 }

etsysOidPhy1000BASET OBJECT-IDENTITY
    STATUS      deprecated
--  Name        ""
--  Date        "200109261800Z"
    DESCRIPTION 
        "Enterasys fixed 1000BASE-T copper port with RJ45 connector.
         Use etsysOidPhyFrtPnlGigEthRJ45 instead."
    ::= { etsysOidPhy 157 }

etsysOidPhyXPx2xAtm OBJECT-IDENTITY
    STATUS      current
--  Name        "XP-2-ATM"
--  Date        "200109261800Z"
    DESCRIPTION 
        "Enterasys 2 port ATM routing module for the X-Pedition 2400."
    ::= { etsysOidPhy 158 }

etsysOidPhyPortSlot OBJECT-IDENTITY
    STATUS      deprecated
--  Name        ""
--  Date        "200109261800Z"
    DESCRIPTION 
        "Enterasys physical interface connector for all Enterasys routers.
         The value 0.0 should be returned in the ENTITY-MIB instead of
         this object."
    ::= { etsysOidPhy 159 }

etsysOidPhyER16xFDDIx02 OBJECT-IDENTITY
    STATUS      current
--  Name        "ER16-FDDI-02"
--  Date        "200109261800Z"
    DESCRIPTION 
        "Enterasys 2 port FDDI routing module for the X-Pedition ER-16."
    ::= { etsysOidPhy 160 }

etsysOidPhyER16xATM29x02 OBJECT-IDENTITY
    STATUS      current
--  Name        "ER16-ATM29-02"
--  Date        "200109261800Z"
    DESCRIPTION 
        "Enterasys 2 port ATM OC-3c (T-Series) routing module for the
         X-Pedition ER-16."
    ::= { etsysOidPhy 161 }

etsysOidPhyER16xSERCx04xAA OBJECT-IDENTITY
    STATUS      current
--  Name        "ER16-SERC-04-AA"
--  Date        "200109261800Z"
    DESCRIPTION 
        "Enterasys 4 port Serial  (AA Series) routing module for the
         X-Pedition ER-16.  This module supports compression."
    ::= { etsysOidPhy 162 }

etsysOidPhyER16xSERCEx04xA OBJECT-IDENTITY
    STATUS      current
--  Name        "ER16-SERCE-04-A"
--  Date        "200109261800Z"
    DESCRIPTION 
        "Enterasys 4 port Serial (AA Series) routing module for the
         X-Pedition ER-16.  This module supports compression and encryption."
    ::= { etsysOidPhy 163 }

etsysOidPhyER16xHSSIx02xAA OBJECT-IDENTITY
    STATUS      current
--  Name        "ER16-HSSI-02-AA"
--  Date        "200109261800Z"
    DESCRIPTION 
        "Enterasys 2 port HSSI (AA Series) routing module for the
         X-Pedition ER-16."
    ::= { etsysOidPhy 164 }

etsysOidPhyXPMemory64 OBJECT-IDENTITY
    STATUS      current
--  Name        ""
--  Date        "200109261800Z"
    DESCRIPTION 
        "Enterasys 64 MB control module memory for the X-Pedition routers."
    ::= { etsysOidPhy 165 }

etsysOidPhyXPMemory128 OBJECT-IDENTITY
    STATUS      current
--  Name        ""
--  Date        "200109261800Z"
    DESCRIPTION 
        "Enterasys 128 MB control module memory for the X-Pedition routers."
    ::= { etsysOidPhy 166 }

etsysOidPhyXPMemory256 OBJECT-IDENTITY
    STATUS      current
--  Name        ""
--  Date        "200109261800Z"
    DESCRIPTION 
        "Enterasys 256 MB control module memory for the X-Pedition routers."
    ::= { etsysOidPhy 167 }

etsysOidPhyXP8PowerSupplySlot OBJECT-IDENTITY
    STATUS      current
--  Name        ""
--  Date        "200109261800Z"
    DESCRIPTION 
        "Enterasys power supply slot for the X-Pedition 8000."
    ::= { etsysOidPhy 168 }

etsysOidPhyXP16PowerSupplySlot OBJECT-IDENTITY
    STATUS      current
--  Name        ""
--  Date        "200109261800Z"
    DESCRIPTION 
        "Enterasys power supply slot for the X-Pedition 8600."
    ::= { etsysOidPhy 169 }

etsysOidPhyER16PowerSupplySlot OBJECT-IDENTITY
    STATUS      current
--  Name        ""
--  Date        "200109261800Z"
    DESCRIPTION 
        "Enterasys power supply slot for the X-Pedition ER-16."
    ::= { etsysOidPhy 170 }

etsysOidPhyXP16SwitchingFabricSlot OBJECT-IDENTITY
    STATUS      current
--  Name        ""
--  Date        "200109261800Z"
    DESCRIPTION 
        "Enterasys switching fabric slot for the X-Pedition 8600."
    ::= { etsysOidPhy 171 }

etsysOidPhyER16SwitchingFabricSlot OBJECT-IDENTITY
    STATUS      current
--  Name        ""
--  Date        "200109261800Z"
    DESCRIPTION 
        "Enterasys switching fabric slot for the X-Pedition ER-16."
    ::= { etsysOidPhy 172 }

etsysOidPhyNIMxSERx02 OBJECT-IDENTITY
    STATUS      current
--  Name        "NIM-SER-02"
--  Date        "200109261800Z"
    DESCRIPTION 
        "Enterasys dual port serial network interface module (NIM)."
    ::= { etsysOidPhy 173 }

etsysOidPhyNIMxSERx04 OBJECT-IDENTITY
    STATUS      current
--  Name        "NIM-SER-04"
--  Date        "200109261800Z"
    DESCRIPTION 
        "Enterasys quad port serial network interface module (NIM)."
    ::= { etsysOidPhy 174 }

etsysOidPhyNIMxT1E1x01 OBJECT-IDENTITY
    STATUS      current
--  Name        "NIM-T1/E1-01"
--  Date        "200109261800Z"
    DESCRIPTION 
        "Enterasys single port Clear/Fractional T1/E1 NIM with DSU."
    ::= { etsysOidPhy 175 }

etsysOidPhyNIMxT1E1x02 OBJECT-IDENTITY
    STATUS      current
--  Name        "NIM-T1/E1-02"
--  Date        "200109261800Z"
    DESCRIPTION 
        "Enterasys dual port Clear/Fractional T1/E1 NIM with DSU."
    ::= { etsysOidPhy 176 }

etsysOidPhyNIMxT1E1x04 OBJECT-IDENTITY
    STATUS      current
--  Name        "NIM-T1/E1-04"
--  Date        "200109261800Z"
    DESCRIPTION 
        "Enterasys quad port Clear/Fractional T1/E1 NIM with DSU."
    ::= { etsysOidPhy 177 }

etsysOidPhyNIMxCT1E1x01 OBJECT-IDENTITY
    STATUS      current
--  Name        "NIM-CT1/E1-01"
--  Date        "200109261800Z"
    DESCRIPTION 
        "Enterasys single port Channelized T1/E1 NIM with DSU."
    ::= { etsysOidPhy 178 }

etsysOidPhyNIMxCT1E1x02 OBJECT-IDENTITY
    STATUS      current
--  Name        "NIM-CT1/E1-02"
--  Date        "200109261800Z"
    DESCRIPTION 
        "Enterasys dual port Channelized T1/E1 NIM with DSU."
    ::= { etsysOidPhy 179 }

etsysOidPhyNIMxCT1E1x04 OBJECT-IDENTITY
    STATUS      current
--  Name        "NIM-CT1/E1-04"
--  Date        "200109261800Z"
    DESCRIPTION 
        "Enterasys quad port Channelized T1/E1 NIM with DSU."
    ::= { etsysOidPhy 180 }

etsysOidPhyER16xHFX31x24 OBJECT-IDENTITY
    STATUS      current
--  Name        "ER16-HFX31-24" 
--  Date        "200112132013Z"  - Thu Dec 13 20:13 GMT 2001
    DESCRIPTION 
        "Enterasys 24 port 100BASE-FX (T-Series) routing module 
         with MT-RJ connectors (for MMF) for the X-Pedition ER16."
    ::= { etsysOidPhy 181 }

etsysOidPhyER16xHFX39x24 OBJECT-IDENTITY
    STATUS      current
--  Name        "ER16-HFX39-24" 
--  Date        "200112132013Z"  - Thu Dec 13 20:13 GMT 2001
    DESCRIPTION 
        "Enterasys 24 port 100BASE-FX (T-Series) routing module 
         with MT-RJ connectors (for SMF) for the X-Pedition ER16."
    ::= { etsysOidPhy 182 }

etsysOidPhyER16xGTX32x04 OBJECT-IDENTITY
    STATUS      current
--  Name        "ER16-GTX32-04" 
--  Date        "200112132013Z"  - Thu Dec 13 20:13 GMT 2001
    DESCRIPTION 
        "Enterasys 4 port 1000BASE-T (T-Series) routing module 
         with RJ45 connectors (for Cat 5) for the X-Pedition ER16."
    ::= { etsysOidPhy 183 }

etsysOidPhyER16xGTX32x08 OBJECT-IDENTITY
    STATUS      current
--  Name        "ER16-GTX32-08" 
--  Date        "200112132013Z"  - Thu Dec 13 20:13 GMT 2001
    DESCRIPTION 
        "Enterasys 8 port 1000BASE-T (T-Series) routing module 
         with RJ45 connectors (for Cat 5) for the X-Pedition ER16."
    ::= { etsysOidPhy 184 }

etsysOidPhySSRxGTX32x04 OBJECT-IDENTITY
    STATUS      current
--  Name        "SSR-GTX32-04" 
--  Date        "200112132013Z"  - Thu Dec 13 20:13 GMT 2001
    DESCRIPTION 
        "Enterasys 4 port 1000BASE-T (T-Series) routing module 
         with RJ45 connectors (for Cat 5) for the X-Pedition 8000 series."
    ::= { etsysOidPhy 185 }

etsysOidPhySSRxGSX31x04 OBJECT-IDENTITY
    STATUS      current
--  Name        "SSR-GSX31-04" 
--  Date        "200112132013Z"  - Thu Dec 13 20:13 GMT 2001
    DESCRIPTION 
        "Enterasys 4 port 1000BASE-SX  (T-Series) routing module 
         with SC connectors (for MMF) for the X-Pedition 8000 series."
    ::= { etsysOidPhy 186 }

etsysOidPhySSRxGLX39x04 OBJECT-IDENTITY
    STATUS      current
--  Name        "SSR-GLX39-04" 
--  Date        "200112132013Z"  - Thu Dec 13 20:13 GMT 2001
    DESCRIPTION 
        "Enterasys 4 port 1000BASE-LX  (T-Series) routing module 
         with SC connectors (for MMF or SMF) for the X-Pedition 8000 series."
    ::= { etsysOidPhy 187 }

etsysOidPhy5SlotFTM1Backplane OBJECT-IDENTITY 
    STATUS      current 
--  Name        "" 
--  Date        "200112191637Z" - Wed Dec 19 16:37 GMT 2001
    DESCRIPTION 
        "Enterasys Frame Transfer Matrix 1 Backplane for the 5 slot
         E5 or E6 chassis."
    ::= { etsysOidPhy 188 } 

etsysOidPhy7SlotFTM1Backplane OBJECT-IDENTITY 
    STATUS      current 
--  Name        "" 
--  Date        "200112191637Z" - Wed Dec 19 16:37 GMT 2001
    DESCRIPTION 
        "Enterasys Frame Transfer Matrix 1 Backplane for the 7 slot
         E7 chassis."
    ::= { etsysOidPhy 189 } 

etsysOidPhy7SlotFTM2Backplane OBJECT-IDENTITY 
    STATUS      current 
--  Name        "" 
--  Date        "200112191637Z" - Wed Dec 19 16:37 GMT 2001
    DESCRIPTION 
        "Enterasys Frame Transfer Matrix 2 Backplane for the 7 slot
         E7 chassis."
    ::= { etsysOidPhy 190 } 

etsysOidPhyER16xOS26x01 OBJECT-IDENTITY
    STATUS      current
--  Name        "ER16-OS26-01" 
--  Date        "200203141907Z"  - Thu Mar 14 19:07 GMT 2002
    DESCRIPTION 
        "Enterasys 1 port 10GbE routing module for the X-Pedition ER-16.
         Uses ZPIM uplink module."
    ::= { etsysOidPhy 191 }

etsysOidPhyMPC8240 OBJECT-IDENTITY 
    STATUS      current
--  Name        "MPC 8240" 
--  Date        "200204021856Z"  - Tue Apr  2 18:56 GMT 2002
    DESCRIPTION
         "Motorola PowerPC 8240 processor." 
    ::=  { etsysOidPhy 192 }  

etsysOidPhyMPC8245 OBJECT-IDENTITY 
    STATUS      current
--  Name        "MPC 8245" 
--  Date        "200204021856Z"  - Tue Apr  2 18:56 GMT 2002
    DESCRIPTION
         "Motorola PowerPC 8245 processor." 
    ::=  { etsysOidPhy 193 } 

etsysOidPhy7G4202x30 OBJECT-IDENTITY
    STATUS      current
--  Name        "7G4202-30"
--  Date        "200204082035Z"  - Mon Apr  8 20:35 GMT 2002
    DESCRIPTION
        "Enterasys 30 port 1000BASE-T Gigabit Ethernet module
         with RJ45 connectors."
    ::= { etsysOidPhy 194 }

etsysOidPhy7Gx6MGBIC OBJECT-IDENTITY
    STATUS      current
--  Name        "7G-6MGBIC"
--  Date        "200204082035Z"  - Mon Apr  8 20:35 GMT 2002
    DESCRIPTION
        "Enterasys 6 port 1000BASE-X Gigabit Ethernet uplink
         module with Mini-GBIC connectors."
    ::= { etsysOidPhy 195 }

etsysOidPhy7H4382x49 OBJECT-IDENTITY
    STATUS      current
--  Name        "7H4382-49"
--  Date        "200204082035Z"  - Mon Apr  8 20:35 GMT 2002
    DESCRIPTION
        "Enterasys 48 port 100BASE-TX Fast Ethernet module with
         RJ45 connectors and one uplink slot."
    ::= { etsysOidPhy 196 }

etsysOidPhy7K4290x02 OBJECT-IDENTITY
    STATUS      current
--  Name        "7K4290-02"
--  Date        "200204082035Z"  - Mon Apr  8 20:35 GMT 2002
    DESCRIPTION
        "Enterasys 2 port 10 Gigabit Ethernet module."
    ::= { etsysOidPhy 197 }

etsysOidPhy7H4204x48 OBJECT-IDENTITY
    STATUS      current
--  Name        "7H4204-48"
--  Date        "200204082035Z"  - Mon Apr  8 20:35 GMT 2002
    DESCRIPTION
        "Enterasys 48 port 100BASE-FX Fast Ethernet module with
         MMF MT-RJ connectors."
    ::= { etsysOidPhy 198 }

etsysOidPhy2H412x49R OBJECT-IDENTITY
    STATUS      current
--  Name        "2H412-49R"
--  Date        "200204082035Z"  - Mon Apr  8 20:35 GMT 2002
    DESCRIPTION
        "Enterasys 48 port 100BASE-TX Fast Ethernet standalone
         with RJ45 connectors and one uplink slot."
    ::= { etsysOidPhy 199 }

etsysOidPhy6C207x3 OBJECT-IDENTITY
    STATUS      current
--  Name        "6C207-3"
--  Date        "200205301711Z"  - Thu May 30 17:11 GMT 2002
    DESCRIPTION
        "Enterasys AC power supply (+5.25 Volts/280 Amps/1470 Watts,
         +12 Volts/8 Amps/96 Watts) for the Matrix E7/N7 chassis."
    ::= { etsysOidPhy 200 }

etsysOidPhy6C203x1 OBJECT-IDENTITY
    STATUS      obsolete
--  Name        "6C203-1"
--  Date        "200206271656Z"  - Thu Jun 27 16:56 GMT 2002
    DESCRIPTION
        "Enterasys AC power supply for the Matrix E3 chassis."
    ::= { etsysOidPhy 201 }

etsysOidPhy6C403 OBJECT-IDENTITY
    STATUS      obsolete
--  Name        "6C403"
--  Date        "200206271656Z"  - Thu Jun 27 16:56 GMT 2002
    DESCRIPTION
        "Enterasys fan tray for the Matrix E3 chassis."
    ::= { etsysOidPhy 202 }

etsysOidPhy6C103 OBJECT-IDENTITY
    STATUS      obsolete
--  Name        "6C103"
--  Date        "200206271656Z"  - Thu Jun 27 16:56 GMT 2002
    DESCRIPTION
        "Enterasys 3 slot modular chassis frame for the Matrix E3."
    ::= { etsysOidPhy 203 }

etsysOidPhyVHxSMGMT2 OBJECT-IDENTITY
    STATUS      current
--  Name        "VH-SMGMT2"
--  Date        "200206271656Z"  - Thu Jun 27 16:56 GMT 2002
    DESCRIPTION
        "Enterasys L2/L3 management card for Vertical Horizon products."
    ::= { etsysOidPhy 204 }

etsysOidPhyVHxRTMxL3 OBJECT-IDENTITY
    STATUS      current
--  Name        "VH-RTM-L3"
--  Date        "200206271656Z"  - Thu Jun 27 16:56 GMT 2002
    DESCRIPTION
        "Enterasys layer 3 routing module for the VH-2402S and VH-2402S2
         products."
    ::= { etsysOidPhy 205 }

etsysOidPhyGPIMx02 OBJECT-IDENTITY
    STATUS      current
--  Name        "GPIM-02"
--  Date        "200207121421Z"  - Fri Jul 12 14:21 GMT 2002
    DESCRIPTION
        "Enterasys removable 1000BASE-T GBIC with a single RJ45
         connector."
    ::= { etsysOidPhy 206 }

etsysOidPhyNIMxBRIxSTx01 OBJECT-IDENTITY
    STATUS      current
--  Name        "NIM-BRI-ST-01"
--  Date        "200208291923Z"  - Thu Aug 29 19:23 GMT 2002
    DESCRIPTION
        "Enterasys single port ISDN ST NIM offering 2 B channels
         (64 Kbit/sec each) and one D channel (16 Kbit/sec) with
         an RJ45 connector for the XSR products."
    ::= { etsysOidPhy 207 }

etsysOidPhyNIMxBRIxSTx02 OBJECT-IDENTITY
    STATUS      current
--  Name        "NIM-BRI-ST-02"
--  Date        "200208291923Z"  - Thu Aug 29 19:23 GMT 2002
    DESCRIPTION
        "Enterasys dual port ISDN ST NIM offering 2 B channels
         (64 Kbit/sec each) and one D channel (16 Kbit/sec) with
         two RJ45 connectors for the XSR products."
    ::= { etsysOidPhy 208 }

etsysOidPhyNIMxBRIxUx01 OBJECT-IDENTITY
    STATUS      current
--  Name        "NIM-BRI-U-01"
--  Date        "200208291923Z"  - Thu Aug 29 19:23 GMT 2002
    DESCRIPTION
        "Enterasys single port ISDN U NIM offering 2 B channels
         (64 Kbit/sec each) and one D channel (16 Kbit/sec) with
         an RJ45 connector for the XSR products."
    ::= { etsysOidPhy 209 }

etsysOidPhyNIMxBRIxUx02 OBJECT-IDENTITY
    STATUS      current
--  Name        "NIM-BRI-U-02"
--  Date        "200208291923Z"  - Thu Aug 29 19:23 GMT 2002
    DESCRIPTION
        "Enterasys dual port ISDN U NIM offering 2 B channels
         (64 Kbit/sec each) and one D channel (16 Kbit/sec) with
         two RJ45 connectors for the XSR products."
    ::= { etsysOidPhy 210 }

etsysOidPhyC5C105 OBJECT-IDENTITY
    STATUS    deprecated
--  Name      "C5C105"
--  Date      "200210291413Z"   - Tue Oct 29 14:13 GMT 2002
    DESCRIPTION
        "Enterasys Matrix C5 five slot modular chassis frame."
    ::= { etsysOidPhy 211 }

etsysOidPhyC5C305 OBJECT-IDENTITY
    STATUS    deprecated
--  Name      "C5C305"
--  Date      "200210291413Z"   - Tue Oct 29 14:13 GMT 2002
    DESCRIPTION
        "Enterasys Matrix C5 fan tray."
    ::= { etsysOidPhy 212 }

etsysOidPhyC5C205x1 OBJECT-IDENTITY
    STATUS    deprecated
--  Name      "C5C205-1"
--  Date      "200210291413Z"   - Tue Oct 29 14:13 GMT 2002
    DESCRIPTION
        "Enterasys Matrix C5 AC power supply."
    ::= { etsysOidPhy 213 }

etsysOidPhyC5H124x48 OBJECT-IDENTITY
    STATUS    deprecated
--  Name      "C5H124-48"
--  Date      "200210291413Z"   - Tue Oct 29 14:13 GMT 2002
    DESCRIPTION
        "Enterasys Matrix C5 48 port RJ45 100BASE-TX Fast Ethernet
         switching module, with one uplink slot."
    ::= { etsysOidPhy 214 }

etsysOidPhyC5G124x36 OBJECT-IDENTITY
    STATUS    deprecated
--  Name      "C5G124-36"
--  Date      "200210291413Z"   - Tue Oct 29 14:13 GMT 2002
    DESCRIPTION
        "Enterasys Matrix C5 36 port RJ45 1000BASE-T Gigabit Ethernet
         switching module with 4 Mini-GBIC uplink ports."
    ::= { etsysOidPhy 215 }

etsysOidPhyC5G122x24 OBJECT-IDENTITY
    STATUS    deprecated
--  Name      "C5G122-24"
--  Date      "200210291413Z"   - Tue Oct 29 14:13 GMT 2002
    DESCRIPTION
        "Enterasys Matrix C5 24 port RJ45 1000BASE-T Gigabit Ethernet
         switching module, with 2 Xenpak uplink ports."
    ::= { etsysOidPhy 216 }

etsysOidPhyC5G114x4 OBJECT-IDENTITY
    STATUS    deprecated
--  Name      "C5G114-4"
--  Date      "200210291413Z"   - Tue Oct 29 14:13 GMT 2002
    DESCRIPTION
        "Enterasys Matrix C5 uplink module with four Mini-GBIC Gigabit
         Ethernet ports."
    ::= { etsysOidPhy 217 }

etsysOidPhyC5G124x4 OBJECT-IDENTITY
    STATUS    deprecated
--  Name      "C5G124-4"
--  Date      "200210291413Z"   - Tue Oct 29 14:13 GMT 2002
    DESCRIPTION
        "Enterasys Matrix C5 uplink module with four 1000BASE-T
         RJ45 Gigabit Ethernet ports."
    ::= { etsysOidPhy 218 }

etsysOidPhyC5M100 OBJECT-IDENTITY
    STATUS    deprecated
--  Name      "C5M100"
--  Date      "200210291413Z"   - Tue Oct 29 14:13 GMT 2002
    DESCRIPTION
        "Enterasys Matrix C5 Connectivity Module."
    ::= { etsysOidPhy 219 }

etsysOidPhyC2H124x48 OBJECT-IDENTITY
    STATUS    current
--  Name      "C2H124-48"
--  Date      "200210291413Z"   - Tue Oct 29 14:13 GMT 2002
--  Updated   "200403151711Z"   - Mon Mar 15 17:11 GMT 2004
    DESCRIPTION
        "Enterasys Matrix C2 48 port RJ45 100BASE-TX Fast Ethernet
         stackable switch, with four Mini-GBIC ports."
    ::= { etsysOidPhy 220 }

etsysOidPhyC2G124x36 OBJECT-IDENTITY
    STATUS    deprecated
--  Name      "C2G124-36"
--  Date      "200210291413Z"   - Tue Oct 29 14:13 GMT 2002
    DESCRIPTION
        "Enterasys Matrix C2 36 port RJ45 1000BASE-T Gigabit Ethernet
         stackable switch, with four Mini-GBIC uplink ports."
    ::= { etsysOidPhy 221 }

etsysOidPhyC2G122x24 OBJECT-IDENTITY
    STATUS    deprecated
--  Name      "C2G122-24"
--  Date      "200210291413Z"   - Tue Oct 29 14:13 GMT 2002
    DESCRIPTION
        "Enterasys Matrix C2 24 port RJ45 1000BASE-T Gigabit Ethernet
         stackable switch, with two Xenpak uplink ports."
    ::= { etsysOidPhy 222 }

etsysOidPhyC2M100 OBJECT-IDENTITY
    STATUS    deprecated
--  Name      "C2M100"
--  Date      "200210291413Z"   - Tue Oct 29 14:13 GMT 2002
    DESCRIPTION
        "Enterasys Matrix C2 Connectivity Module."
    ::= { etsysOidPhy 223 }

etsysOidPhyC2C105 OBJECT-IDENTITY
    STATUS    deprecated
--  Name      "C2C105"
--  Date      "200210291413Z"   - Tue Oct 29 14:13 GMT 2002
    DESCRIPTION
        "Enterasys Matrix C2 redundant power supply chassis."
    ::= { etsysOidPhy 224 }

etsysOidPhyC2C100 OBJECT-IDENTITY
    STATUS    deprecated
--  Name      "C2C100"
--  Date      "200210291413Z"   - Tue Oct 29 14:13 GMT 2002
    DESCRIPTION
        "Enterasys Matrix C2 redundant power supply."
    ::= { etsysOidPhy 225 }

etsysOidPhy7G4270x10 OBJECT-IDENTITY
    STATUS      current
--  Name        "7G4270-10"
--  Date        "200212031420Z"  - Tue Dec  3 14:20 GMT 2002
    DESCRIPTION
        "Enterasys 10 port 1000BASE-X Gigabit Ethernet module with 
         Mini-GBIC connectors."
    ::= { etsysOidPhy 226 }

etsysOidPhy7H4202x72 OBJECT-IDENTITY
    STATUS      current
--  Name        "7H4202-72"
--  Date        "200212031420Z"  - Tue Dec  3 14:20 GMT 2002
    DESCRIPTION
        "Enterasys 72 port 100BASE-X Fast Ethernet module with 
         RJ45 connectors."
    ::= { etsysOidPhy 227 }

etsysOidPhy7C107 OBJECT-IDENTITY
    STATUS      current
--  Name        "7C107"
--  Date        "200212311920Z"  - Tue Dec 31 19:20 GMT 2002
    DESCRIPTION
        "Enterasys 7 slot modular chassis frame for the Matrix N7."
    ::= { etsysOidPhy 228 }

etsysOidPhy7C103 OBJECT-IDENTITY
    STATUS      current
--  Name        "7C103"
--  Date        "200212311920Z"  - Tue Dec 31 19:20 GMT 2002
    DESCRIPTION
        "Enterasys 3 slot modular chassis frame for the Matrix N3."
    ::= { etsysOidPhy 229 }

etsysOidPhy7C203x1 OBJECT-IDENTITY
    STATUS      current
--  Name        "7C203-1"
--  Date        "200212311920Z"  - Tue Dec 31 19:20 GMT 2002
    DESCRIPTION
        "Enterasys AC power supply for the Matrix N3 chassis."
    ::= { etsysOidPhy 230 }

etsysOidPhy7C403 OBJECT-IDENTITY
    STATUS      current
--  Name        "7C403"
--  Date        "200212311920Z"  - Tue Dec 31 19:20 GMT 2002
    DESCRIPTION
        "Enterasys fan tray for the Matrix N3 chassis."
    ::= { etsysOidPhy 231 }

etsysOidPhy7G4275x12 OBJECT-IDENTITY
    STATUS      current
--  Name        "7G4275-12"
--  Date        "200302241506Z"  - Wed Mar  5 19:18 GMT 2003
    DESCRIPTION
        "Enterasys 12 port Gigabit Ethernet module with 10 1000BASE-X
         ports with Mini-GBIC connectors and two 1000BASE-T ports with
         RJ45 connectors."
    ::= { etsysOidPhy 232 }

etsysOidPhy7G4270x09 OBJECT-IDENTITY
    STATUS      current
--  Name        "7G4270-09"
--  Date        "200302241506Z"  - Wed Mar  5 19:18 GMT 2003
    DESCRIPTION
        "Enterasys 9 port 1000BASE-X Gigabit Ethernet module with 
         Mini-GBIC connectors."
    ::= { etsysOidPhy 233 }

etsysOidPhyNIMxC16T3x01 OBJECT-IDENTITY
    STATUS      current
--  Name        "NIM-C16T3-01"
--  Date        "200303051535Z"  - Wed Mar  5 15:35 GMT 2003
    DESCRIPTION
        "Enterasys single port channelized T3 NIM, supporting up to 16
         T1 tributaries, for the XSR products."
    ::= { etsysOidPhy 234 }

etsysOidPhyNIMxC16E3x01 OBJECT-IDENTITY
    STATUS      current
--  Name        "NIM-C16E3-01"
--  Date        "200303051535Z"  - Wed Mar  5 15:35 GMT 2003
    DESCRIPTION
        "Enterasys single port channelized E3 NIM for the XSR products."
    ::= { etsysOidPhy 235 }

etsysOidPhyNIMxT3E3x01 OBJECT-IDENTITY
    STATUS      current
--  Name        "NIM-T3E3-01"
--  Date        "200303051535Z"  - Wed Mar  5 15:35 GMT 2003
    DESCRIPTION
        "Enterasys single port unchannelized T3/E3 NIM for the XSR
         products."
    ::= { etsysOidPhy 236 }

etsysOidPhyNIMxC16T3Sx01 OBJECT-IDENTITY
    STATUS      current
--  Name        "NIM-C16T3S-01"
--  Date        "200303051535Z"  - Wed Mar  5 15:35 GMT 2003
    DESCRIPTION
        "Enterasys single port channelized T3 NIM with system
         synchronization capabilities, supporting up to 16 T1
         tributaries, for the XSR products."
    ::= { etsysOidPhy 237 }

etsysOidPhyNIMxC16E3Sx01 OBJECT-IDENTITY
    STATUS      current
--  Name        "NIM-C16E3S-01"
--  Date        "200303051535Z"  - Wed Mar  5 15:35 GMT 2003
    DESCRIPTION
        "Enterasys single port channelized E3 NIM with system
         synchronization capabilities, for the XSR products."
    ::= { etsysOidPhy 238 }

etsysOidPhyNIMxC16T3GSx01 OBJECT-IDENTITY
    STATUS      current
--  Name        "NIM-C16T3GS-01"
--  Date        "200303051535Z"  - Wed Mar  5 15:35 GMT 2003
    DESCRIPTION
        "Enterasys single port channelized T3 NIM with a G.747
         multiplexer, supporting up to 16 E1 tributaries, and
         with system synchronization capabilities.  For the XSR
         products."
    ::= { etsysOidPhy 239 }

etsysOidPhyNIMxT3Sx01 OBJECT-IDENTITY
    STATUS      current
--  Name        "NIM-T3S-01"
--  Date        "200303051535Z"  - Wed Mar  5 15:35 GMT 2003
    DESCRIPTION
        "Enterasys single port unchannelized T3 NIM with system
         synchronization capabilities, for the XSR products."
    ::= { etsysOidPhy 240 }

etsysOidPhyNIMxE3Sx01 OBJECT-IDENTITY
    STATUS      current
--  Name        "NIM-E3S-01"
--  Date        "200303051535Z"  - Wed Mar  5 15:35 GMT 2003
    DESCRIPTION
        "Enterasys single port unchannelized E3 NIM with system
         synchronization capabilities, for the XSR products."
    ::= { etsysOidPhy 241 }

etsysOidPhyNIMxETHxTGRx01 OBJECT-IDENTITY
    STATUS      deprecated
--  Name        "NIM-ETH-TGR-01"
--  Date        "200303121917Z"  - Wed Mar 12 19:17 GMT 2003
--  Date        "200307021725Z"  - Wed Jul  2 17:25 GMT 2003
    DESCRIPTION
        "Enterasys single port 100BASE-TX Ethernet NIM with a
         single RJ45 connector for the XSR products."
    ::= { etsysOidPhy 242 }

etsysOidPhyNIMxADSLxACx01 OBJECT-IDENTITY
    STATUS      current
--  Name        "NIM-ADSL-AC-01"
--  Date        "200303051535Z"  - Wed Mar  5 15:35 GMT 2003
    DESCRIPTION
        "Enterasys single port ADSL over POTS NIM per ITU-T
         G.992.1 Annex A, C, for the XSR products."
    ::= { etsysOidPhy 243 }

etsysOidPhyNIMxADSLxBx01 OBJECT-IDENTITY
    STATUS      current
--  Name        "NIM-ADSL-B-01"
--  Date        "200303051535Z"  - Wed Mar  5 15:35 GMT 2003
    DESCRIPTION
        "Enterasys single port ADSL over ISDN NIM per ITU-T
         G.992.1 Annex B, for the XSR products."
    ::= { etsysOidPhy 244 }

etsysOidPhy7H4383x49 OBJECT-IDENTITY
    STATUS      current
--  Name        "7H4383-49"
--  Date        "200304171358Z"  - Thu Apr 17 13:58 GMT 2003
    DESCRIPTION
        "Enterasys 48 port 100BASE-TX Fast Ethernet module with
         RJ21 connectors and one uplink slot."
    ::= { etsysOidPhy 245 }

etsysOidPhy7H4284x49 OBJECT-IDENTITY
    STATUS      current
--  Name        "7H4284-49"
--  Date        "200304181851Z"  - Fri Apr 18 18:51 GMT 2003
    DESCRIPTION
        "Enterasys 48 port 100BASE-FX Fast Ethernet module with
         MMF MT-RJ connectors and one uplink slot."
    ::= { etsysOidPhy 246 }

etsysOidPhyV2G121x1 OBJECT-IDENTITY
    STATUS      current
--  Name        "V2G121-1"
--  Date        "200305142108Z"  - Wed May 14 21:08 GMT 2003
    DESCRIPTION
        "Enterasys single port 1000BASE-T uplink module with
         an RJ45 connector for the V2H products."
    ::= { etsysOidPhy 247 }

etsysOidPhyV2G112x2 OBJECT-IDENTITY
    STATUS      current
--  Name        "V2G112-2"
--  Date        "200305142108Z"  - Wed May 14 21:08 GMT 2003
    DESCRIPTION
        "Enterasys two port Gigabit uplink module with one
         1000BASE-T port, with an RJ45 connector, and one
         Mini-GBIC port, for the V2H products."
    ::= { etsysOidPhy 248 }

etsysOidPhyV2G151x1M OBJECT-IDENTITY
    STATUS      current
--  Name        "V2G151-1M"
--  Date        "200305142108Z"  - Wed May 14 21:08 GMT 2003
    DESCRIPTION
        "Enterasys single port 100BASE-FX MMF uplink module with
         one SC connector, for the V2H products."
    ::= { etsysOidPhy 249 }

etsysOidPhyV2G151x1S OBJECT-IDENTITY
    STATUS      current
--  Name        "V2G151-1S"
--  Date        "200305142108Z"  - Wed May 14 21:08 GMT 2003
    DESCRIPTION
        "Enterasys single port 100BASE-FX SMF uplink module with
         one SC connector, for the V2H products."
    ::= { etsysOidPhy 250 }

etsysOidPhy1Hx8FX OBJECT-IDENTITY
    STATUS      current
--  Name        "1H-8FX"
--  Date        "200306031308Z"  - Tue Jun  3 13:08 GMT 2003
    DESCRIPTION
        "Enterasys eight port 100BASE-FX MMF expansion module with
         MRTJ connectors, for the E1 product family."
    ::= { etsysOidPhy 251 }

etsysOidPhyE1FxdAcPwrSup OBJECT-IDENTITY
    STATUS      current
--  Date        "200306051509Z"  - Thu Jun  5 15:09 GMT 2003
    DESCRIPTION
        "Enterasys fixed AC power supply for the Matrix E1 product
         family."
    ::= { etsysOidPhy 252 }

etsysOidPhyNIMxETHRx01 OBJECT-IDENTITY
    STATUS      current
--  Name        "NIM-ETHR-01"
--  Date        "200307021725Z"  - Wed Jul  2 17:25 GMT 2003
    DESCRIPTION
        "Enterasys single port 100BASE-TX Ethernet NIM with a
         single RJ45 connector for the XSR products."
    ::= { etsysOidPhy 253 }

etsysOidPhyNIMxFIBRx01 OBJECT-IDENTITY
    STATUS      current
--  Name        "NIM-FIBR-01"
--  Date        "200307021725Z"  - Wed Jul  2 17:25 GMT 2003
    DESCRIPTION
        "Enterasys single port 100BASE-TX Ethernet NIM with a
         single MT-RJ connector for the XSR products."
    ::= { etsysOidPhy 254 }

etsysOidPhyNIMxDIRELAYx02 OBJECT-IDENTITY
    STATUS      current
--  Name        "NIM-DIRELAY-02"
--  Date        "200307021725Z"  - Wed Jul  2 17:25 GMT 2003
    DESCRIPTION
        "Enterasys two port Drop and Insert Fractional T1/E1 NIM with
         CSU/DSU for the XSR products."
    ::= { etsysOidPhy 255 }

etsysOidPhy7G4202x60 OBJECT-IDENTITY
    STATUS      current
--  Name        "7G4202-60"
--  Date        "200307092041Z"  - Wed Jul  9 20:41 GMT 2003
    DESCRIPTION
        "Enterasys 60 port 1000BASE-T Gigabit Ethernet module with 
         RJ45 connectors."
    ::= { etsysOidPhy 256 }

etsysOidPhy7G4282x41 OBJECT-IDENTITY
    STATUS      current
--  Name        "7G4282-41"
--  Date        "200307092041Z"  - Wed Jul  9 20:41 GMT 2003
    DESCRIPTION
        "Enterasys 40 port 1000BASE-T Gigabit Ethernet module with 
         RJ45 connectors and one uplink slot."
    ::= { etsysOidPhy 257 }

etsysOidPhyMGBICNoConnector OBJECT-IDENTITY
    STATUS      current
--  Name        ""
--  Date        "200307281636Z"  - Mon Jul 28 16:36 GMT 2003
    DESCRIPTION
        "Enterasys 1000BASE-X or 1000BASE-T Mini-GBIC slot with
         no Mini-GBIC present."
    ::= { etsysOidPhy 258 }

etsysOidPhyN7PowerSupplySlot OBJECT-IDENTITY
    STATUS      current
--  Name        ""
--  Date        "200307281636Z"  - Mon Jul 28 16:36 GMT 2003
    DESCRIPTION 
        "Enterasys power supply slot for the N7 chassis."
    ::= { etsysOidPhy 259 }

etsysOidPhyN7FanTraySlot OBJECT-IDENTITY
    STATUS      current
--  Name        ""
--  Date        "200307281636Z"  - Mon Jul 28 16:36 GMT 2003
    DESCRIPTION 
        "Enterasys fan tray slot for the N7 chassis."
    ::= { etsysOidPhy 260 }

etsysOidPhyN7ModuleSlot OBJECT-IDENTITY
    STATUS      current
--  Name        ""
--  Date        "200307281636Z"  - Mon Jul 28 16:36 GMT 2003
    DESCRIPTION 
        "Enterasys module slot for the N7 chassis."
    ::= { etsysOidPhy 261 }

etsysOidPhyN3PowerSupplySlot OBJECT-IDENTITY
    STATUS      current
--  Name        ""
--  Date        "200307281636Z"  - Mon Jul 28 16:36 GMT 2003
    DESCRIPTION 
        "Enterasys power supply slot for the N3 chassis."
    ::= { etsysOidPhy 262 }

etsysOidPhyN3FanTraySlot OBJECT-IDENTITY
    STATUS      current
--  Name        ""
--  Date        "200307281636Z"  - Mon Jul 28 16:36 GMT 2003
    DESCRIPTION 
        "Enterasys fan tray slot for the N3 chassis."
    ::= { etsysOidPhy 263 }

etsysOidPhyN3ModuleSlot OBJECT-IDENTITY
    STATUS      current
--  Name        ""
--  Date        "200307281636Z"  - Mon Jul 28 16:36 GMT 2003
    DESCRIPTION 
        "Enterasys module slot for the N3 chassis."
    ::= { etsysOidPhy 264 }

etsysOidPhyE7PowerSupplySlot OBJECT-IDENTITY
    STATUS      current
--  Name        ""
--  Date        "200307281636Z"  - Mon Jul 28 16:36 GMT 2003
    DESCRIPTION 
        "Enterasys power supply slot for the E7 chassis."
    ::= { etsysOidPhy 265 }

etsysOidPhyE7FanTraySlot OBJECT-IDENTITY
    STATUS      current
--  Name        ""
--  Date        "200307281636Z"  - Mon Jul 28 16:36 GMT 2003
    DESCRIPTION 
        "Enterasys fan tray slot for the E7 chassis."
    ::= { etsysOidPhy 266 }

etsysOidPhyE7ModuleSlot OBJECT-IDENTITY
    STATUS      current
--  Name        ""
--  Date        "200307281636Z"  - Mon Jul 28 16:36 GMT 2003
    DESCRIPTION 
        "Enterasys module slot for the E7 chassis."
    ::= { etsysOidPhy 267 }

etsysOidPhyRj45ConsolePort OBJECT-IDENTITY
    STATUS      current
--  Name        ""
--  Date        "200307301643Z"  - Wed Jul 30 16:43 GMT 2003
    DESCRIPTION 
        "Enterasys local management console port with an RJ45
         connector."
    ::= { etsysOidPhy 268 }

etsysOidPhyMGBICx02 OBJECT-IDENTITY
    STATUS      current
--  Name        "MGBIC-02"
--  Date        "200308191932Z"  - Tue Aug 19 19:32 GMT 2003
    DESCRIPTION
        "Enterasys MGBIC-02, a 1000BASE-T Mini-GBIC with an RJ45
         connector."
    ::= { etsysOidPhy 269 }

etsysOidPhyMGBICx08 OBJECT-IDENTITY
    STATUS      current
--  Name        "MGBIC-08"
--  Date        "200308191932Z"  - Tue Aug 19 19:32 GMT 2003
    DESCRIPTION
        "Enterasys MGBIC-08, a 1000BASE-LX/LH (70Km Long Haul) SMF
         Mini-GBIC with an LC connector."
    ::= { etsysOidPhy 270 }

etsysOidPhy4H4203x72 OBJECT-IDENTITY
    STATUS      current
--  Name        "4H4203-72"
--  Date        "200309171426Z"  - Wed Sep 17 14:26 GMT 2003
    DESCRIPTION
        "Enterasys 72 port 100BASE-TX Fast Ethernet module with
         RJ21 connectors."
    ::= { etsysOidPhy 271 }

etsysOidPhy4H4283x49 OBJECT-IDENTITY
    STATUS      current
--  Name        "4H4283-49"
--  Date        "200309171426Z"  - Wed Sep 17 14:26 GMT 2003
    DESCRIPTION
        "Enterasys 48 port 100BASE-TX Fast Ethernet module with
         RJ21 connectors and one uplink slot."
    ::= { etsysOidPhy 272 }

etsysOidPhy4G4282x41 OBJECT-IDENTITY
    STATUS      current
--  Name        "4G4282-41"
--  Date        "200309171426Z"  - Wed Sep 17 14:26 GMT 2003
    DESCRIPTION
        "Enterasys 40 port 1000BASE-T Gigabit Ethernet module with 
         RJ45 connectors and one uplink slot."
    ::= { etsysOidPhy 273 }

etsysOidPhy4G4202x60 OBJECT-IDENTITY
    STATUS      current
--  Name        "4G4202-60"
--  Date        "200309171426Z"  - Wed Sep 17 14:26 GMT 2003
    DESCRIPTION
        "Enterasys 60 port 1000BASE-T Gigabit Ethernet module with 
         RJ45 connectors."
    ::= { etsysOidPhy 274 }

etsysOidPhy4H4282x49 OBJECT-IDENTITY
    STATUS      current
--  Name        "4H4282-49"
--  Date        "200309171426Z"  - Wed Sep 17 14:26 GMT 2003
    DESCRIPTION
        "Enterasys 48 port 100BASE-TX Fast Ethernet module with
         RJ45 connectors and one uplink slot."
    ::= { etsysOidPhy 275 }

etsysOidPhy4H4202x72 OBJECT-IDENTITY
    STATUS      current
--  Name        "4H4202-72"
--  Date        "200309171426Z"  - Wed Sep 17 14:26 GMT 2003
    DESCRIPTION
        "Enterasys 72 port 100BASE-TX Fast Ethernet module with
         RJ45 connectors."
    ::= { etsysOidPhy 276 }

etsysOidPhy4H4284x49 OBJECT-IDENTITY
    STATUS      current
--  Name        "4H4284-49"
--  Date        "200309171426Z"  - Wed Sep 17 14:26 GMT 2003
    DESCRIPTION
        "Enterasys 48 port 100BASE-FX Fast Ethernet module with
         MMF MT-RJ connectors and one uplink slot."
    ::= { etsysOidPhy 277 }

etsysOidPhy7H4382x25 OBJECT-IDENTITY
    STATUS      current
--  Name        "7H4382-25"
--  Date        "200310141504Z"  - Tue Oct 14 15:04 GMT 2003
    DESCRIPTION
        "Enterasys 24 port 100BASE-TX Fast Ethernet module with
         RJ45 connectors and one uplink slot."
    ::= { etsysOidPhy 278 }

etsysOidPhyNoXenpak OBJECT-IDENTITY
    STATUS      current
--  Name        ""
--  Date        "200401271643Z"  - Tue Jan 27 16:43 GMT 2004
    DESCRIPTION
        "Enterasys 10GBASE slot with no XENPAK present."
    ::= { etsysOidPhy 279 }

etsysOidPhy4H4285x49 OBJECT-IDENTITY
    STATUS      current
--  Name        "4H4285-49"
--  Date        "200402172131Z"  - Tue Feb 17 21:31 GMT 2004
    DESCRIPTION
        "Enterasys 48 port 100BASE-TX Fast Ethernet module with
         RJ45 connectors and one uplink slot.  Power over Ethernet
         is supported on the 48 100BASE-TX ports."
    ::= { etsysOidPhy 280 }

etsysOidPhy7H4385x49 OBJECT-IDENTITY
    STATUS      current
--  Name        "7H4385-49"
--  Date        "200402172131Z"  - Tue Feb 17 21:31 GMT 2004
    DESCRIPTION
        "Enterasys 48 port 100BASE-TX Fast Ethernet module with
         RJ45 connectors and one uplink slot.  Power over Ethernet
         is supported on the 48 100BASE-TX ports."
    ::= { etsysOidPhy 281 }

etsysOidPhy7G4280x19 OBJECT-IDENTITY
    STATUS      current
--  Name        "7G4280-19"
--  Date        "200402191419Z"  - Thu Feb 19 14:19 GMT 2004
    DESCRIPTION
        "Enterasys 18 port 1000BASE-X Gigabit Ethernet module with
         Mini-GBIC connectors and one uplink slot."
    ::= { etsysOidPhy 282 }

etsysOidPhyC2G124x24 OBJECT-IDENTITY
    STATUS      current
--  Name        "C2G124-24"
--  Date        "200403151711Z"  - Mon Mar 15 17:11 GMT 2004
    DESCRIPTION
        "Enterasys Matrix C2 24 port RJ45 1000BASE-T Gigabit Ethernet
         stackable switch, with four Mini-GBIC ports."
    ::= { etsysOidPhy 283 }

etsysOidPhyC2G124x48 OBJECT-IDENTITY
    STATUS      current
--  Name        "C2G124-48"
--  Date        "200403151711Z"  - Mon Mar 15 17:11 GMT 2004
    DESCRIPTION
        "Enterasys Matrix C2 48 port RJ45 1000BASE-T Gigabit Ethernet
         stackable switch, with four Mini-GBIC ports."
    ::= { etsysOidPhy 284 }

etsysOidPhyC2K122x24 OBJECT-IDENTITY
    STATUS      current
--  Name        "C2K122-24"
--  Date        "200403151711Z"  - Mon Mar 15 17:11 GMT 2004
    DESCRIPTION
        "Enterasys Matrix C2 24 port RJ45 1000BASE-T Gigabit Ethernet
         stackable switch, with two 10 Gigabit XFP ports."
    ::= { etsysOidPhy 285 }

etsysOidPhyC2H124x48P OBJECT-IDENTITY
    STATUS      current
--  Name        "C2H124-48P"
--  Date        "200403151711Z"  - Mon Mar 15 17:11 GMT 2004
    DESCRIPTION
        "Enterasys Matrix C2 48 port RJ45 100BASE-TX Fast Ethernet
         stackable switch, with four Mini-GBIC ports.  Power over
         Ethernet is supported on the 48 100BASE-TX ports."
    ::= { etsysOidPhy 286 }

etsysOidPhyC2G124x48P OBJECT-IDENTITY
    STATUS      current
--  Name        "C2G124-48P"
--  Date        "200403151711Z"  - Mon Mar 15 17:11 GMT 2004
    DESCRIPTION
        "Enterasys Matrix C2 48 port RJ45 1000BASE-T Gigabit Ethernet
         stackable switch, with four Mini-GBIC ports.  Power over
         Ethernet is supported on the 48 1000BASE-T ports."
    ::= { etsysOidPhy 287 }

etsysOidPhy7G4202x72 OBJECT-IDENTITY
    STATUS      current
--  Name        "7G4202-72"
--  Date        "200404021838Z"  - Fri Apr  2 18:38 GMT 2004
    DESCRIPTION
        "Enterasys 72 port 1000BASE-T Gigabit Ethernet module with
         RJ45 connectors."
    ::= { etsysOidPhy 288 }

etsysOidPhy7G4205x72 OBJECT-IDENTITY
    STATUS      current
--  Name        "7G4205-72"
--  Date        "200404021838Z"  - Fri Apr  2 18:38 GMT 2004
    DESCRIPTION
        "Enterasys 72 port 1000BASE-T Gigabit Ethernet module with
         RJ45 connectors. Power over Ethernet is supported on the
         72 1000BASE-T ports."
    ::= { etsysOidPhy 289 }

etsysOidPhy7G4282x49 OBJECT-IDENTITY
    STATUS      current
--  Name        "7G4282-49"
--  Date        "200404021838Z"  - Fri Apr  2 18:38 GMT 2004
    DESCRIPTION
        "Enterasys 48 port 1000BASE-T Gigabit Ethernet module with
         RJ45 connectors and one uplink slot."
    ::= { etsysOidPhy 290 }

etsysOidPhy7G4285x49 OBJECT-IDENTITY
    STATUS      current
--  Name        "7G4285-49"
--  Date        "200404021838Z"  - Fri Apr  2 18:38 GMT 2004
    DESCRIPTION
        "Enterasys 48 port 1000BASE-T Gigabit Ethernet module with
         RJ45 connectors and one uplink slot. Power over Ethernet
         is supported on the 48 1000BASE-T ports."
    ::= { etsysOidPhy 291 }

etsysOidPhy4G4202x72 OBJECT-IDENTITY
    STATUS      current
--  Name        "4G4202-72"
--  Date        "200404021838Z"  - Fri Apr  2 18:38 GMT 2004
    DESCRIPTION
        "Enterasys 72 port 1000BASE-T Gigabit Ethernet module with
         RJ45 connectors."
    ::= { etsysOidPhy 292 }

etsysOidPhy4G4205x72 OBJECT-IDENTITY
    STATUS      current
--  Name        "4G4205-72"
--  Date        "200404021838Z"  - Fri Apr  2 18:38 GMT 2004
    DESCRIPTION
        "Enterasys 72 port 1000BASE-T Gigabit Ethernet module with
         RJ45 connectors. Power over Ethernet is supported on the
         72 1000BASE-T ports."
    ::= { etsysOidPhy 293 }

etsysOidPhy4G4282x49 OBJECT-IDENTITY
    STATUS      current
--  Name        "4G4282-49"
--  Date        "200404021838Z"  - Fri Apr  2 18:38 GMT 2004
    DESCRIPTION
        "Enterasys 48 port 1000BASE-T Gigabit Ethernet module with
         RJ45 connectors and one uplink slot."
    ::= { etsysOidPhy 294 }

etsysOidPhy4G4285x49 OBJECT-IDENTITY
    STATUS      current
--  Name        "4G4285-49"
--  Date        "200404021838Z"  - Fri Apr  2 18:38 GMT 2004
    DESCRIPTION
        "Enterasys 72 port 1000BASE-T Gigabit Ethernet module with
         RJ45 connectors and one uplink slot. Power over Ethernet
         is supported on the 48 1000BASE-T ports."
    ::= { etsysOidPhy 295 }

etsysOidPhyMGBICxLC03 OBJECT-IDENTITY
    STATUS      current
--  Name        "MGBIC-LC03"
--  Date        "200404161915Z"  - Fri Apr 16 19:15 GMT 2004
    DESCRIPTION
        "Enterasys MGBIC-LC03, 1000BASE-LX/LH (2Km Long Haul) MMF
         Mini-GBIC with an LC connector."
    ::= { etsysOidPhy 296 }

etsysOidPhyNxPOE OBJECT-IDENTITY
    STATUS      current
--  Name        "N-POE"
--  Date        "200404161915Z"  - Fri Apr 16 19:15 GMT 2004
    DESCRIPTION 
        "Enterasys Power over Ethernet power system."
    ::= { etsysOidPhy 297 }

etsysOidPhyNxPOEx1200W OBJECT-IDENTITY
    STATUS      current
--  Name        ""
--  Date        "200404161915Z"  - Fri Apr 16 19:15 GMT 2004
    DESCRIPTION 
        "Enterasys DC power supply for PoE power."
    ::= { etsysOidPhy 298 }

etsysOidPhyNxPOEPowerSupplySlot OBJECT-IDENTITY
    STATUS      current
--  Name        ""
--  Date        "200404161915Z"  - Fri Apr 16 19:15 GMT 2004
    DESCRIPTION 
        "Enterasys PoE power supply slot for the N-POE power system."
    ::= { etsysOidPhy 299 }

etsysOidPhy7C105xP OBJECT-IDENTITY
    STATUS      current
--  Name        "7C105-P"
--  Date        "200404161915Z"  - Fri Apr 16 19:15 GMT 2004
    DESCRIPTION
        "Enterasys 5 slot modular Power over Ethernet chassis frame
         for the Matrix N5 PoE."
    ::= { etsysOidPhy 300 }

etsysOidPhy7C205x1 OBJECT-IDENTITY
    STATUS      current
--  Name        "7C205-1"
--  Date        "200404161915Z"  - Fri Apr 16 19:15 GMT 2004
    DESCRIPTION
        "Enterasys AC power supply for the Matrix N5 PoE chassis."
    ::= { etsysOidPhy 301 }

etsysOidPhy7C405 OBJECT-IDENTITY
    STATUS      current
--  Name        "7C405"
--  Date        "200404161915Z"  - Fri Apr 16 19:15 GMT 2004
    DESCRIPTION
        "Enterasys fan tray for the Matrix N5 PoE chassis."
    ::= { etsysOidPhy 302 }

etsysOidPhyN5PoEPowerSupplySlot OBJECT-IDENTITY
    STATUS      current
--  Name        ""
--  Date        "200404161915Z"  - Fri Apr 16 19:15 GMT 2004
    DESCRIPTION
        "Enterasys power supply slot for the N5 PoE chassis."
    ::= { etsysOidPhy 303 }

etsysOidPhyN5PoEFanTraySlot OBJECT-IDENTITY
    STATUS      current
--  Name        ""
--  Date        "200404161915Z"  - Fri Apr 16 19:15 GMT 2004
    DESCRIPTION
        "Enterasys fan tray slot for the N5 PoE chassis."
    ::= { etsysOidPhy 304 }

etsysOidPhyN5PoEModuleSlot OBJECT-IDENTITY
    STATUS      current
--  Name        ""
--  Date        "200404161915Z"  - Fri Apr 16 19:15 GMT 2004
    DESCRIPTION
        "Enterasys module slot for the N5 PoE chassis."
    ::= { etsysOidPhy 305 }

etsysOidPhyV2H124x24FX OBJECT-IDENTITY
    STATUS      current
--  Name        "V2H124-24FX"
--  Date        "200405181553Z"  - Tue May 18 15:53 GMT 2004
    DESCRIPTION
        "Enterasys V2 24 port 100BASE-FX Fast Ethernet stackable
         switch, with MTRJ multi-mode connectors and two uplink
         slots."
    ::= { etsysOidPhy 306 }

etsysOidPhy7Gx6MGBICxA OBJECT-IDENTITY
    STATUS      current
--  Name        "7G-6MGBIC-A"
--  Date        "200406011942Z"  - Tue Jun  1 19:42 GMT 2004
    DESCRIPTION
        "Enterasys 6 port 1000BASE-X Gigabit Ethernet uplink
         module with Mini-GBIC connectors."
    ::= { etsysOidPhy 307 }

etsysOidPhyN5PoEPoEPowerSupplySlot OBJECT-IDENTITY
    STATUS      current
--  Name        ""
--  Date        "200408042118Z"  - Wed Aug  4 21:18 GMT 2004
    DESCRIPTION
        "Enterasys PoE power supply slot for the N5 PoE chassis."
    ::= { etsysOidPhy 308 }

etsysOidPhy7C117 OBJECT-IDENTITY
    STATUS      current
--  Name        "7C117"
--  Date        "200501111956Z"  - Tue Jan 11 19:56 GMT 2005
    DESCRIPTION
        "Enterasys 7 slot modular chassis frame for the Matrix N7."
    ::= { etsysOidPhy 309 }

etsysOidPhy7C115xP OBJECT-IDENTITY
    STATUS      current
--  Name        "7C115-P"
--  Date        "200501111956Z"  - Tue Jan 11 19:56 GMT 2005
    DESCRIPTION
        "Enterasys 5 slot modular Power over Ethernet chassis frame
         for the Matrix N5 PoE."
    ::= { etsysOidPhy 310 }

etsysOidPhy7C113 OBJECT-IDENTITY
    STATUS      current
--  Name        "7C113"
--  Date        "200501111956Z"  - Tue Jan 11 19:56 GMT 2005
    DESCRIPTION
        "Enterasys 3 slot modular chassis frame for the Matrix N3."
    ::= { etsysOidPhy 311 }

etsysOidPhy7C111 OBJECT-IDENTITY
    STATUS      current
--  Name        "7C111"
--  Date        "200501111956Z"  - Tue Jan 11 19:56 GMT 2005
    DESCRIPTION
        "Enterasys 1 slot modular chassis frame with power supplies
         and fans for the Matrix N1."
    ::= { etsysOidPhy 312 }

etsysOidPhyN1ModuleSlot OBJECT-IDENTITY
    STATUS      current
--  Name        ""
--  Date        "200501111956Z"  - Tue Jan 11 19:56 GMT 2005
    DESCRIPTION 
        "Enterasys module slot for the N1 chassis."
    ::= { etsysOidPhy 313 }

etsysOidPhyB2G124x24 OBJECT-IDENTITY
    STATUS      current
--  Name        "B2G124-24"
--  Date        "200501121802Z"  - Wed Jan 12 18:02 GMT 2005
    DESCRIPTION
        "Enterasys Matrix B2 24 port RJ45 1000BASE-T Gigabit Ethernet
         stackable switch, with four Mini-GBIC ports."
    ::= { etsysOidPhy 314 }

etsysOidPhyB2G124x48 OBJECT-IDENTITY
    STATUS      current
--  Name        "B2G124-48"
--  Date        "200501121802Z"  - Wed Jan 12 18:02 GMT 2005
    DESCRIPTION
        "Enterasys Matrix B2 48 port RJ45 1000BASE-T Gigabit Ethernet
         stackable switch, with four Mini-GBIC ports."
    ::= { etsysOidPhy 315 }

etsysOidPhyB2G124x48P OBJECT-IDENTITY
    STATUS      current
--  Name        "B2G124-48P"
--  Date        "200501121802Z"  - Wed Jan 12 18:02 GMT 2005
    DESCRIPTION
        "Enterasys Matrix B2 48 port RJ45 1000BASE-T Gigabit Ethernet
         stackable switch, with four Mini-GBIC ports.  Power over
         Ethernet is supported on the 48 1000BASE-T ports."
    ::= { etsysOidPhy 316 }

etsysOidPhyB2H124x48 OBJECT-IDENTITY
    STATUS    current
--  Name      "B2H124-48"
--  Date        "200501121802Z"  - Wed Jan 12 18:02 GMT 2005
    DESCRIPTION
        "Enterasys Matrix B2 48 port RJ45 100BASE-TX Fast Ethernet
         stackable switch, with four Mini-GBIC ports."
    ::= { etsysOidPhy 317 }

etsysOidPhyB2H124x48P OBJECT-IDENTITY
    STATUS      current
--  Name        "B2H124-48P"
--  Date        "200501121802Z"  - Wed Jan 12 18:02 GMT 2005
    DESCRIPTION
        "Enterasys Matrix B2 48 port RJ45 100BASE-TX Fast Ethernet
         stackable switch, with four Mini-GBIC ports.  Power over
         Ethernet is supported on the 48 100BASE-TX ports."
    ::= { etsysOidPhy 318 }

etsysOidPhyB2G124x24P OBJECT-IDENTITY
    STATUS      current
--  Name        "B2G124-24P"
--  Date        "200501121802Z"  - Wed Jan 12 18:02 GMT 2005
    DESCRIPTION
        "Enterasys Matrix B2 24 port RJ45 1000BASE-T Gigabit Ethernet
         stackable switch, with four Mini-GBIC ports.  Power over
         Ethernet is supported on the 24 1000BASE-T ports."
    ::= { etsysOidPhy 319 }

etsysOidPhyB2H124x24 OBJECT-IDENTITY
    STATUS      current
--  Name        "B2H124-24"
--  Date        "200501121802Z"  - Wed Jan 12 18:02 GMT 2005
    DESCRIPTION
        "Enterasys Matrix B2 24 port RJ45 100BASE-TX Fast Ethernet
         stackable switch, with four Mini-GBIC ports."
    ::= { etsysOidPhy 320 }

etsysOidPhyB2H124x24P OBJECT-IDENTITY
    STATUS      current
--  Name        "B2H124-24P"
--  Date        "200501121802Z"  - Wed Jan 12 18:02 GMT 2005
    DESCRIPTION
        "Enterasys Matrix B2 24 port RJ45 100BASE-TX Fast Ethernet
         stackable switch, with four Mini-GBIC ports.  Power over
         Ethernet is supported on the 24 100BASE-TX ports."
    ::= { etsysOidPhy 321 }

etsysOidPhyB2H124x24FX OBJECT-IDENTITY
    STATUS      current
--  Name        "B2H124-24FX"
--  Date        "200501121802Z"  - Wed Jan 12 18:02 GMT 2005
    DESCRIPTION
        "Enterasys B2 24 port 100BASE-FX Fast Ethernet stackable
         switch, with MTRJ multi-mode connectors and two uplink
         slots."
    ::= { etsysOidPhy 322 }

etsysOidPhyX16xC OBJECT-IDENTITY
    STATUS      current
--  Name        "X16-C"
--  Date        "200502092214Z"  - Wed Feb  9 22:14 GMT 2005
    DESCRIPTION
        "Enterasys 16 slot modular chassis frame for the Matrix X."
    ::= { etsysOidPhy 323 }

etsysOidPhyX8xC OBJECT-IDENTITY
    STATUS      current
--  Name        "X8-C"
--  Date        "200502092214Z"  - Wed Feb  9 22:14 GMT 2005
    DESCRIPTION
        "Enterasys 8 slot modular chassis frame for the Matrix X."
    ::= { etsysOidPhy 324 }

etsysOidPhyX4xC OBJECT-IDENTITY
    STATUS      current
--  Name        "X4-C"
--  Date        "200502092214Z"  - Wed Feb  9 22:14 GMT 2005
    DESCRIPTION
        "Enterasys 4 slot modular chassis frame for the Matrix X."
    ::= { etsysOidPhy 325 }

etsysOidPhyX16Backplane OBJECT-IDENTITY
    STATUS      current
--  Name        "Matrix X-16 Backplane"
--  Date        "200502092214Z"  - Wed Feb  9 22:14 GMT 2005
    DESCRIPTION
        "Enterasys backplane for the 16 Slot Matrix X chassis."
    ::= { etsysOidPhy 326 }

etsysOidPhyX8Backplane OBJECT-IDENTITY
    STATUS      current
--  Name        "Matrix X-8 Backplane"
--  Date        "200502092214Z"  - Wed Feb  9 22:14 GMT 2005
    DESCRIPTION
        "Enterasys backplane for the 8 Slot Matrix X chassis."
    ::= { etsysOidPhy 327 }

etsysOidPhyX4Backplane OBJECT-IDENTITY
    STATUS      current
--  Name        "Matrix X-4 Backplane"
--  Date        "200502092214Z"  - Wed Feb  9 22:14 GMT 2005
    DESCRIPTION
        "Enterasys backplane for the 4 Slot Matrix X chassis."
    ::= { etsysOidPhy 328 }

etsysOidPhyXxFan OBJECT-IDENTITY
    STATUS      current
--  Name        "X-Fan"
--  Date        "200502092214Z"  - Wed Feb  9 22:14 GMT 2005
    DESCRIPTION
        "Enterasys fan assembly for the Matrix X chassis."
    ::= { etsysOidPhy  329 }

etsysOidPhyXxAC OBJECT-IDENTITY
    STATUS      current
--  Name        "X-AC"
--  Date        "200502092214Z"  - Wed Feb  9 22:14 GMT 2005
    DESCRIPTION
        "Enterasys 1200 Watt AC power supply for the Matrix X chassis."
    ::= { etsysOidPhy  330 }

etsysOidPhyXxCMx00 OBJECT-IDENTITY
    STATUS      current
--  Name        "X-CM-00"
--  Date        "200502092214Z"  - Wed Feb  9 22:14 GMT 2005
    DESCRIPTION
        "Enterasys control module for the Matrix X16 and X8."
    ::= { etsysOidPhy  331 }

etsysOidPhyX4xCMFx160x00 OBJECT-IDENTITY
    STATUS      current
--  Name        "X4-CMF160-00"
--  Date        "200502092214Z"  - Wed Feb  9 22:14 GMT 2005
    DESCRIPTION
        "Enterasys control fabric module for the Matrix X4 with 10
         1000BASE-X SFP ports."
    ::= { etsysOidPhy  332 }

etsysOidPhyX16xF640 OBJECT-IDENTITY
    STATUS      current
--  Name        "X16-F640"
--  Date        "200502092214Z"  - Wed Feb  9 22:14 GMT 2005
    DESCRIPTION
        "Enterasys 640 Gbps fabric module for the Matrix X16."
    ::= { etsysOidPhy  333 }

etsysOidPhyX8xF320 OBJECT-IDENTITY
    STATUS      current
--  Name        "X8-F320"
--  Date        "200502092214Z"  - Wed Feb  9 22:14 GMT 2005
    DESCRIPTION
        "Enterasys 320 Gbps fabric module for the Matrix X8."
    ::= { etsysOidPhy  334 }

etsysOidPhyXxM2x00 OBJECT-IDENTITY
    STATUS      current
--  Name        "X-M2-00"
--  Date        "200502092214Z"  - Wed Feb  9 22:14 GMT 2005
    DESCRIPTION
        "Enterasys Matrix X I/O module with 2 10GBASE-X XFP ports."
    ::= { etsysOidPhy  335 }

etsysOidPhyXxG32x00 OBJECT-IDENTITY
    STATUS      current
--  Name        "X-G32-00"
--  Date        "200502092214Z"  - Wed Feb  9 22:14 GMT 2005
    DESCRIPTION
        "Enterasys Matrix X I/O module with 32 1000BASE-X SFP ports."
    ::= { etsysOidPhy  336 }

etsysOidPhyXxT48x01 OBJECT-IDENTITY
    STATUS      current
--  Name        "X-T48-01"
--  Date        "200502092214Z"  - Wed Feb  9 22:14 GMT 2005
    DESCRIPTION
        "Enterasys Matrix X I/O module with 48 1000BASE-T RJ45 ports."
    ::= { etsysOidPhy  337 }

etsysOidPhyXxM2x01 OBJECT-IDENTITY
    STATUS      current
--  Name        "X-M2-01"
--  Date        "200502092214Z"  - Wed Feb  9 22:14 GMT 2005
    DESCRIPTION
        "Enterasys Matrix X I/O module with 2 10GBASE-X XFP ports."
    ::= { etsysOidPhy  338 }

etsysOidPhyXxM4x01 OBJECT-IDENTITY
    STATUS      current
--  Name        "X-M4-01"
--  Date        "200502092214Z"  - Wed Feb  9 22:14 GMT 2005
    DESCRIPTION
        "Enterasys Matrix X I/O module with 4 10GBASE-X XFP ports."
    ::= { etsysOidPhy  339 }

etsysOidPhyXxG20x01 OBJECT-IDENTITY
    STATUS      current
--  Name        "X-G20-01"
--  Date        "200502092214Z"  - Wed Feb  9 22:14 GMT 2005
    DESCRIPTION
        "Enterasys Matrix X I/O module with 20 1000BASE-X SFP ports."
    ::= { etsysOidPhy  340 }

etsysOidPhyXxG40x01 OBJECT-IDENTITY
    STATUS      current
--  Name        "X-G20-01"
--  Date        "200502092214Z"  - Wed Feb  9 22:14 GMT 2005
    DESCRIPTION
        "Enterasys Matrix X I/O module with 40 1000BASE-X SFP ports."
    ::= { etsysOidPhy  341 }

etsysOidPhyXIOModuleSlot OBJECT-IDENTITY
    STATUS      current
--  Name        ""
--  Date        "200502092214Z"  - Wed Feb  9 22:14 GMT 2005
    DESCRIPTION
        "Enterasys I/O module slot for the Matrix X."
    ::= { etsysOidPhy  342 }

etsysOidPhyXControlModuleSlot OBJECT-IDENTITY
    STATUS      current
--  Name        ""
--  Date        "200502092214Z"  - Wed Feb  9 22:14 GMT 2005
    DESCRIPTION
        "Enterasys control module slot for the Matrix X."
    ::= { etsysOidPhy  343 }

etsysOidPhyXFabricModuleSlot OBJECT-IDENTITY
    STATUS      current
--  Name        ""
--  Date        "200502092214Z"  - Wed Feb  9 22:14 GMT 2005
    DESCRIPTION
        "Enterasys fabric module slot for the Matrix X."
    ::= { etsysOidPhy  344 }

etsysOidPhyXPowerSupplySlot OBJECT-IDENTITY
    STATUS      current
--  Name        ""
--  Date        "200502092214Z"  - Wed Feb  9 22:14 GMT 2005
    DESCRIPTION
        "Enterasys power supply slot for the Matrix X."
    ::= { etsysOidPhy  345 }

etsysOidPhyXFanTraySlot OBJECT-IDENTITY
    STATUS      current
--  Name        ""
--  Date        "200502092214Z"  - Wed Feb  9 22:14 GMT 2005
    DESCRIPTION
        "Enterasys fan tray slot for the Matrix X."
    ::= { etsysOidPhy  346 }

etsysOidPhySFPxGBIC OBJECT-IDENTITY
    STATUS      current
--  Name        ""
--  Date        "200502092214Z"  - Wed Feb  9 22:14 GMT 2005
    DESCRIPTION
        "Enterasys Gigabit Ethernet SFP GBIC port."
    ::= { etsysOidPhy  347 }

etsysOidPhyXFPxGBIC OBJECT-IDENTITY
    STATUS      current
--  Name        ""
--  Date        "200502092214Z"  - Wed Feb  9 22:14 GMT 2005
    DESCRIPTION
        "Enterasys 10 Gigabit Ethernet XFP GBIC port."
    ::= { etsysOidPhy  348 }

etsysOidPhyXxT32x00 OBJECT-IDENTITY
    STATUS      current
--  Name        "X-T32-00"
--  Date        "200502092214Z"  - Wed Feb  9 22:14 GMT 2005
    DESCRIPTION
        "Enterasys Matrix X I/O module with 32 1000BASE-T RJ45 ports."
    ::= { etsysOidPhy  349 }

etsysOidPhyC2G134x24P OBJECT-IDENTITY
    STATUS      current
--  Name        "C2G134-24P"
--  Date        "200502202350Z"  - Sun Feb 20 23:50 GMT 2005
    DESCRIPTION
        "Enterasys Matrix C2 24 port RJ21 1000BASE-T Gigabit Ethernet
         stackable switch, with four Mini-GBIC ports.  Power over
         Ethernet is supported on the 24 1000BASE-T ports."
    ::= { etsysOidPhy 350 }

etsysOidPhyXxGT16x00 OBJECT-IDENTITY
    STATUS      current
--  Name        "X-GT16-00"
--  Date        "200510111442Z"  - Tue Oct 11 14:42 UTC 2005
    DESCRIPTION
        "Enterasys Matrix X 16 port I/O module with 8 1000BASE-X SFP ports
         and either an additional 8 1000BASE-X SFP or 8 1000BASE-T RJ45 ports."
    ::= { etsysOidPhy  351 }

etsysOidPhyGigEthIntNEMPort OBJECT-IDENTITY
    STATUS      current
--  Name        ""
--  Date        "200511101958Z"  - Thu Nov 10 19:58 UTC 2005
    DESCRIPTION
        "Enterasys 1000BASE-X Gigabit Ethernet Port on an Integrated 
         Processor NEM."
    ::= { etsysOidPhy 352 }

etsysOidPhy7SxDSNSA7x01 OBJECT-IDENTITY
    STATUS      current
--  Name        "7S-DSNSA7-01" 
--  Date        "200511101958Z"  - Thu Nov 10 19:58 UTC 2005
    DESCRIPTION
        "Enterasys 2 Port Mini-GBIC Gigabit Ethernet Uplink Module with
         Integrated Security Processor and Dragon Security Software
         using an external power supply."
    ::= { etsysOidPhy 353 }

etsysOidPhy7SxNSTAGx01 OBJECT-IDENTITY
    STATUS      current
--  Name        "7S-NSTAG-01" 
--  Date        "200511101958Z"  - Thu Nov 10 19:58 UTC 2005
    DESCRIPTION
        "Enterasys 2 Port Mini-GBIC Gigabit Ethernet Uplink Module with
         Integrated Security Processor and TAG Security Software
         using an external power supply."
    ::= { etsysOidPhy 354 }

etsysOidPhyXxM8x01 OBJECT-IDENTITY
    STATUS      current
--  Name        "X-M8-01"
--  Date        "200602062031Z"  - Mon Feb  6 20:31 GMT 2006
    DESCRIPTION
        "Enterasys Matrix X I/O module with 8 10GBASE-X XFP ports."
    ::= { etsysOidPhy 355 }
 
etsysOidPhy7SxDSNSA7x01NPS OBJECT-IDENTITY
    STATUS      current
--  Name        "7S-DSNSA7-01NPS"
--  Date        "200602161442Z"  - Thu Feb 16 14:42 UTC 2006
    DESCRIPTION
        "Enterasys 2 Port Mini-GBIC Gigabit Ethernet Uplink Module with
         Integrated Security Processor and Dragon Security Software."
    ::= { etsysOidPhy 356 }

etsysOidPhy7SxNSTAGx01xNPS OBJECT-IDENTITY
    STATUS      current
--  Name        "7S-NSTAG-01-NPS"
--  Date        "200602161442Z"  - Thu Feb 16 14:42 UTC 2006
    DESCRIPTION
        "Enterasys 2 Port Mini-GBIC Gigabit Ethernet Uplink Module with
         Integrated Security Processor and TAG Security Software."
    ::= { etsysOidPhy 357 }

etsysOidPhy9603805 OBJECT-IDENTITY
    STATUS      current
--  Name        "9603805"
--  Date        "200602161442Z"  - Thu Feb 16 14:42 UTC 2006
    DESCRIPTION
        "Enterasys 2 Port Mini-GBIC Gigabit Ethernet Uplink Module with
         Integrated Security Processor using an external power supply."
    ::= { etsysOidPhy 358 }

etsysOidPhy9603806 OBJECT-IDENTITY
    STATUS      current
--  Name        "9603806"
--  Date        "200602161442Z"  - Thu Feb 16 14:42 UTC 2006
    DESCRIPTION
        "Enterasys 2 Port Mini-GBIC Gigabit Ethernet Uplink Module with
         Integrated Security Processor."
    ::= { etsysOidPhy 359 }

etsysOidPhyC2G170x24 OBJECT-IDENTITY
    STATUS      current
--  Name        "C2G170-24"
--  Date        "200603091914Z"  - Thu Mar  9 19:14 UTC 2006
    DESCRIPTION
        "Enterasys SecureStack C2 24 port 1000BASE-X SFP ports."
    ::= { etsysOidPhy 360 }

etsysOidPhy7G4082x25 OBJECT-IDENTITY
    STATUS      current
--  Name        "2G4082-25"
--  Date        "200608161344Z"  - Wed Aug 16 13:44 UTC 2006
    DESCRIPTION
        "Enterasys 24 port 1000BASE-T Gigabit Ethernet module with
         RJ45 connectors, one uplink slot and no FTM backplane."
    ::= { etsysOidPhy 361 }

etsysOidPhyI3Hx12TX OBJECT-IDENTITY
    STATUS      current
--  Name        "I3H-12TX"
--  Date        "200608071231Z"  - Mon Aug  7 12:31 UTC 2006
    DESCRIPTION
        "Enterasys Industrial 12 port 100BASE-TX I/O module with
         RJ45 connectors."
    ::= { etsysOidPhy 362 }

etsysOidPhyI3Hx4FXxMM OBJECT-IDENTITY
    STATUS      current
--  Name        "I3H-4FX-MM"
--  Date        "200608071231Z"  - Mon Aug  7 12:31 UTC 2006
    DESCRIPTION
        "Enterasys Industrial 4 port 100BASE-FX I/O module for
         multi-mode fiber."
    ::= { etsysOidPhy 363 }

etsysOidPhyI3Hx8FXxMM OBJECT-IDENTITY
    STATUS      current
--  Name        "I3H-8FX-MM"
--  Date        "200608071231Z"  - Mon Aug  7 12:31 UTC 2006
    DESCRIPTION
        "Enterasys Industrial 8 port 100BASE-FX I/O module for
         multi-mode fiber."
    ::= { etsysOidPhy 364 }

etsysOidPhyI3Hx8TXx2FX OBJECT-IDENTITY
    STATUS      current
--  Name        "I3H-8TX-2FX"
--  Date        "200608071231Z"  - Mon Aug  7 12:31 UTC 2006
    DESCRIPTION
        "Enterasys Industrial 10 port Fast Ethernet I/O module with
         8 100BASE-TX RJ45 connectors and 2 100BASE-FX fiber ports."
    ::= { etsysOidPhy 365 }

etsysOidPhy7Gx6MGBICxB OBJECT-IDENTITY
    STATUS      current
--  Name        "7G-6MGBIC-B"
--  Date        "200608251502Z"  - Fri Aug 25 15:02 UTC 2006
    DESCRIPTION
        "Enterasys 6 port 1000BASE-X Gigabit Ethernet and 100BASE-FX
         Fast Ethernet uplink module with Mini-GBIC connectors."
    ::= { etsysOidPhy 366 }
 
etsysOidPhy7Kx2XFPx6MGBIC OBJECT-IDENTITY
    STATUS      current
--  Name        "7K-2XFP-6MGBIC"
--  Date        "200608251502Z"  - Fri Aug 25 15:02 UTC 2006
    DESCRIPTION
        "Enterasys 2 port 10 Gigabit Ethernet with XFP connectors,
         6 port 1000BASE-X Gigabit Ethernet and 100BASE-FX Fast
         Ethernet with Mini-GBIC connectors uplink module."
    ::= { etsysOidPhy 367 }
 
etsysOidPhy7GR4280x19 OBJECT-IDENTITY
    STATUS      current
--  Name        "7GR4280-19"
    DESCRIPTION
        "Enterasys 18 port 1000BASE-X Gigabit Ethernet module with
         Mini-GBIC connectors and one uplink slot."
    ::= { etsysOidPhy 368 }
 
etsysOidPhy7GR4270x12 OBJECT-IDENTITY
    STATUS      current
--  Name        "7GR4270-12"
--  Date        "200608251502Z"  - Fri Aug 25 15:02 UTC 2006
    DESCRIPTION
        "Enterasys 12 port 1000BASE-X Gigabit Ethernet module with 
         Mini-GBIC connectors."
    ::= { etsysOidPhy 369 }
 
etsysOidPhy7GR4202x30 OBJECT-IDENTITY
    STATUS      current
--  Name        "7GR4202-30"
--  Date        "200608251502Z"  - Fri Aug 25 15:02 UTC 2006
    DESCRIPTION
        "Enterasys 30 port 1000BASE-T Gigabit Ethernet module
         with RJ45 connectors."
    ::= { etsysOidPhy 370 }
 
etsysOidPhy7KR4290x02 OBJECT-IDENTITY
    STATUS      current
--  Name        "7KR4290-02"
--  Date        "200608251502Z"  - Fri Aug 25 15:02 UTC 2006
    DESCRIPTION
        "Enterasys 2 port 10 Gigabit Ethernet module with XENPAK 
         connectors."
    ::= { etsysOidPhy 371 }

etsysOidPhyNoXfp OBJECT-IDENTITY
    STATUS      current
    DESCRIPTION
--  Date        "200610311954Z"  - Tue Oct 31 19:54 UTC 2006
        "Enterasys 10GBASE slot with no XFP present."
    ::= { etsysOidPhy 372 }
 
etsysOidPhyMGBICxLC04 OBJECT-IDENTITY
    STATUS      current
--  Name        "MGBIC-LC04"
--  Date        "200610311954Z"  - Tue Oct 31 19:54 UTC 2006
    DESCRIPTION
        "Enterasys MGBIC-LC04, a 100BASE-FX MMF Mini-GBIC with an LC
         connector."
    ::= { etsysOidPhy 373 }
 
etsysOidPhy10GbExSRxXFP OBJECT-IDENTITY
    STATUS      current
--  Name        "10GBASE-SR-XFP"
--  Date        "200701251558Z"  - Thu Jan 25 15:58 UTC 2007
    DESCRIPTION
       "Enterasys 10GBASE-SR-XFP, XFP 10-Gigabit Ethernet LAN Interface
        with 850 nanometer serial port for 10-Gigabit Ethernet over
        multimode fiber (MMF) via an LC connector."
    ::= { etsysOidPhy 374 }
 
etsysOidPhy10GbExLRxXFP OBJECT-IDENTITY
    STATUS      current
--  Name        "10GBASE-LR-XFP"
--  Date        "200701251558Z"  - Thu Jan 25 15:58 UTC 2007
    DESCRIPTION
        "Enterasys 10GBASE-LR-XFP, XFP 10-Gigabit Ethernet LAN Interface
         with 1310 nanometer serial port for 10-Gigabit Ethernet over
         single-mode fiber (SMF) via an LC connector."
    ::= { etsysOidPhy 375 }
 
etsysOidPhy10GbExERxXFP OBJECT-IDENTITY
    STATUS      current
--  Name        "10GBASE-ER-XFP"
--  Date        "200701251558Z"  - Thu Jan 25 15:58 UTC 2007
    DESCRIPTION
        "Enterasys 10GBASE-ER-XFP, XFP 10-Gigabit Ethernet LAN Interface
         with 1550 nanometer serial port for 10-Gigabit Ethernet over
         single-mode fiber (SMF) via an LC connector."
    ::= { etsysOidPhy 376 }
 
etsysOidPhy10GbExCX4xXFP OBJECT-IDENTITY
    STATUS      current
--  Name        "10GBASE-CX4-XFP"
--  Date        "200701251558Z"  - Thu Jan 25 15:58 UTC 2007
    DESCRIPTION
        "Enterasys 10GBASE-CX4-XFP, XFP 10-Gigabit Ethernet LAN Interface
         with serial port for 10-Gigabit Ethernet over CX4 rated copper
         cable."
    ::= { etsysOidPhy 377 }

etsysOidPhy10GbExCX4 OBJECT-IDENTITY
    STATUS      current
--  Name        "10GBASE-CX4"
--  Date        "200701251558Z"  - Thu Jan 25 15:58 UTC 2007
    DESCRIPTION
        "Enterasys 10GBASE-CX4, XENPAK 10-Gigabit Ethernet LAN Interface
         with serial port for 10-Gigabit Ethernet over CX4 rated copper
         cable."
    ::= { etsysOidPhy 378 }

etsysOidPhy10GbExSWxXFP OBJECT-IDENTITY
    STATUS      current
--  Name        "10GBASE-SW-XFP"
--  Date        "200701251558Z"  - Thu Jan 25 15:58 UTC 2007
    DESCRIPTION
        "Enterasys 10GBASE-SW-XFP, XFP 10-Gigabit Ethernet WAN Interface
         with 850 nanometer serial port for 10-Gigabit Ethernet over
         multimode fiber (MMF) via an LC connector."
    ::= { etsysOidPhy 379 }
 
etsysOidPhy10GbExLWxXFP OBJECT-IDENTITY
    STATUS      current
--  Name        "10GBASE-LW-XFP"
--  Date        "200701251558Z"  - Thu Jan 25 15:58 UTC 2007
    DESCRIPTION
         "Enterasys 10GBASE-LW-XFP, XFP 10-Gigabit Ethernet WAN Interface
          with 1310 nanometer serial port for 10-Gigabit Ethernet over
          single-mode fiber (SMF) via an LC connector."
    ::= { etsysOidPhy 380 }
 
 
etsysOidPhy10GbExEWxXFP OBJECT-IDENTITY
    STATUS      current
--  Name        "10GBASE-EW-XFP"
--  Date        "200701251558Z"  - Thu Jan 25 15:58 UTC 2007
    DESCRIPTION
        "Enterasys 10GBASE-EW-XFP, XFP 10-Gigabit Ethernet WAN Interface
         with 1550 nanometer serial port for 10-Gigabit Ethernet over
         single-mode fiber (SMF) via an LC connector."
    ::= { etsysOidPhy 381 }

etsysOidPhy10GbExLX4xXFP OBJECT-IDENTITY
    STATUS      current
--  Name        "10GBASE-LX4-XFP"
--  Date        "200701251558Z"  - Thu Jan 25 15:58 UTC 2007
    DESCRIPTION
        "Enterasys 10GBASE-LX4-XFP, XFP 10-Gigabit Ethernet LAN Interface
         with 4 channel WWDM 1310 nanometer serial port for 10-Gigabit
         Ethernet over multimode fiber (MMF) and single-mode fiber (SMF)
         via an SC connector."
    ::= { etsysOidPhy 382 }

etsysOidPhy10GbExZRxXFP OBJECT-IDENTITY
    STATUS      current
--  Name        "10GBASE-ZR-XFP"
--  Date        "200702271749Z"  - Tue Feb 27 17:49 UTC 2007
    DESCRIPTION
        "Enterasys 10GBASE-ZR-XFP, XFP 10-Gigabit Ethernet LAN Interface
         with 1550 nanometer serial port for long haul 10-Gigabit Ethernet
         over single-mode fiber (SMF) via an LC connector."
    ::= { etsysOidPhy 383 }

etsysOidPhy10GbExZWxXFP OBJECT-IDENTITY
    STATUS      current
--  Name        "10GBASE-ZW-XFP"
--  Date        "200702271749Z"  - Tue Feb 27 17:49 UTC 2007
    DESCRIPTION
        "Enterasys 10GBASE-ZW-XFP, XFP 10-Gigabit Ethernet WAN Interface
         with 1550 nanometer serial port for long haul 10-Gigabit Ethernet
         over single-mode fiber (SMF) via an LC connector."
    ::= { etsysOidPhy 384 }
 
etsysOidPhy10GbExZR OBJECT-IDENTITY
    STATUS      current
--  Name        "10GBASE-ZR
--  Date        "200702271749Z"  - Tue Feb 27 17:49 UTC 2007
    DESCRIPTION
        "Enterasys 10GBASE-ZR, XENPAK 10-Gigabit Ethernet LAN Interface
         with 1550 nanometer serial port for long haul 10-Gigabit Ethernet
         over single-mode fiber (SMF) via an SC connector."
    ::= { etsysOidPhy 385 }

etsysOidPhy10GbExZW OBJECT-IDENTITY
    STATUS      current
--  Name        "10GBASE-ZW"
--  Date        "200702271749Z"  - Tue Feb 27 17:49 UTC 2007
    DESCRIPTION
        "Enterasys 10GBASE-ZW, XENPAK 10-Gigabit Ethernet WAN Interface
         with 1550 nanometer serial port for long haul 10-Gigabit Ethernet
         over single-mode fiber (SMF) via an SC connector."
    ::= { etsysOidPhy 386 }

etsysOidPhyMGBICxLC05 OBJECT-IDENTITY
    STATUS      current
--  Name        "MGBIC-LC05"
--  Date        "200704051532Z"  - Thu Apr  5 15:32 UTC 2007
    DESCRIPTION
        "Enterasys MGBIC-LC05, a 100BASE-LX10 SMF Mini-GBIC with an LC
         connector."
    ::= { etsysOidPhy 387 }

etsysOidPhy7K4297x02 OBJECT-IDENTITY
    STATUS      current
--  Name        "7K4297-02"
--  Date        "200704051532Z"  - Thu Apr  5 15:32 UTC 2007
    DESCRIPTION
        "Enterasys 2 port 10 Gigabit Ethernet module with XFP 
         connectors."
    ::= { etsysOidPhy 388 }
 
etsysOidPhy7K4297x04 OBJECT-IDENTITY
    STATUS      current
--  Name        "7K4297-04"
--  Date        "200704051532Z"  - Thu Apr  5 15:32 UTC 2007
    DESCRIPTION
        "Enterasys 4 port 10 Gigabit Ethernet module with XFP 
         connectors."
    ::= { etsysOidPhy 389 }
 
etsysOidPhy7KR4297x02 OBJECT-IDENTITY
    STATUS      current
--  Name        "7KR4297-02"
--  Date        "200704051532Z"  - Thu Apr  5 15:32 UTC 2007
    DESCRIPTION
        "Enterasys 2 port 10 Gigabit Ethernet module with XFP 
         connectors."
    ::= { etsysOidPhy 390 }
 
etsysOidPhy7KR4297x04 OBJECT-IDENTITY
    STATUS      current
--  Name        "7KR4297-04"
--  Date        "200704051532Z"  - Thu Apr  5 15:32 UTC 2007
    DESCRIPTION
        "Enterasys 4 port 10 Gigabit Ethernet module with XFP 
         connectors."
    ::= { etsysOidPhy 391 }

etsysOidPhy7S4280x19 OBJECT-IDENTITY
    STATUS      current
--  Name        "7S4280-19"
--  Date        "200708291516Z"  - Wed Aug 29 15:16 UTC 2007
    DESCRIPTION
        "Enterasys 18 port 1000BASE-X Gigabit Ethernet NAC module with
         Mini-GBIC connectors and one uplink slot."
    ::= { etsysOidPhy 392 }

etsysOidPhy2S4082x25 OBJECT-IDENTITY
    STATUS      current
--  Name        "2S4082-25"
--  Date        "200708291516Z"  - Wed Aug 29 15:16 UTC 2007
    DESCRIPTION
        "Enterasys 24 port 1000BASE-T Gigabit Ethernet NAC module with
         RJ45 connectors, one uplink slot and no FTM backplane 
         connectivity."
    ::= { etsysOidPhy 393 }

etsysOidPhy7SxNSNACGx01xNPS OBJECT-IDENTITY
    STATUS      current
--  Name        "7S-NSNACG-01-NPS"
--  Date        "200708301808Z"  - Thu Aug 30 18:08 UTC 2007
    DESCRIPTION
        "Enterasys 2 Port Mini-GBIC Gigabit Ethernet Uplink Module with
         Integrated Security Processor and NAC Security Software."
    ::= { etsysOidPhy 394 }

etsysOidPhyMGBICxLC07 OBJECT-IDENTITY
    STATUS      current
--  Name        "MGBIC-LC07"
--  Date        "200710301910Z"  - Tue Oct 30 19:10 UTC 2007
    DESCRIPTION
        "Enterasys MGBIC-LC07, a 1000BASE-EZX (110Km Extended Long Reach)
         SMF Mini-GBIC via LC connector."
    ::= { etsysOidPhy 395 }
 
etsysOidPhy7SxNACGx01 OBJECT-IDENTITY
    STATUS      current
--  Name        "7S-NACG-01"
--  Date        "200804241400Z"  - Thu Apr 24 14:00 UTC 2008
    DESCRIPTION
        "Enterasys 2 Port Mini-GBIC Gigabit Ethernet Uplink Module with 
         Dual Core Integrated Security Processor and NAC Security 
         Software."
    ::= { etsysOidPhy 396 }

etsysOidPhy7SxC20N OBJECT-IDENTITY
    STATUS      current
--  Name        "7S-C20N"
--  Date        "200811171604Z"  - Mon Nov 17 16:04 UTC 2008
    DESCRIPTION
        "Enterasys 2 Port Mini-GBIC Gigabit Ethernet Uplink Module with
         Integrated HiPath Wireless C20N Controller with support for up 
         to 32 Access Points in normal mode or 64 Access Points in 
         failover mode."
    ::= { etsysOidPhy 397 }

etsysOidPhy10GbExSRxSFPP OBJECT-IDENTITY
    STATUS      current
--  Name        "10GB-SR-SFPP"
--  Date        "200901051508Z"  - Mon Jan  5 15:08 UTC 2009
    DESCRIPTION
        "Enterasys SFP+ 10GBASE-SR Ethernet interface with 
         850nm Short Wave Length optics for IEEE 802.3 MM fiber (MMF)
         via a LC connector. 33/82M fiber length."
    ::= { etsysOidPhy 398 }

etsysOidPhy10GbExLRxSFPP OBJECT-IDENTITY
    STATUS      current
--  Name        "10GB-LR-SFPP"
--  Date        "200901051508Z"  - Mon Jan  5 15:08 UTC 2009
    DESCRIPTION
        "Enterasys SFP+ 10GBASE-LR Ethernet interface with
         1310nm Long Wave Length optics for IEEE 802.3 SM fiber (SMF)
         via a LC connector. 10Km fiber length."
    ::= { etsysOidPhy 399 }

etsysOidPhy10GbExLRMxSFPP OBJECT-IDENTITY
    STATUS      current
--  Name        "10GB-LRM-SFPP"
--  Date        "200901051508Z"  - Mon Jan  5 15:08 UTC 2009
    DESCRIPTION
        "Enterasys SFP+ 10GBASE-LRM Ethernet interface with
         1310nm Long Wave Length optics for IEEE 802.3 MM fiber (MMF)
         via a LC connector. 220M fiber length."
    ::= { etsysOidPhy 400 }

etsysOidPhy10GbExC01xSFPP OBJECT-IDENTITY
    STATUS      current
--  Name        "10GB-C01-SFPP"
--  Date        "200901051508Z"  - Mon Jan  5 15:08 UTC 2009
    DESCRIPTION
        "Enterasys SFP+ 10 Gigabit Ethernet interface with
         pluggable copper cable assembly and integrated SFP+ transceiver.         
         1M cable length."
    ::= { etsysOidPhy 401 }

etsysOidPhy10GbExC03xSFPP OBJECT-IDENTITY
    STATUS      current
--  Name        "10GB-C03-SFPP"
--  Date        "200901051508Z"  - Mon Jan  5 15:08 UTC 2009
    DESCRIPTION
        "Enterasys SFP+ 10 Gigabit Ethernet interface with
         pluggable copper cable assembly and integrated SFP+ transceiver.         
         3M cable length."
    ::= { etsysOidPhy 402 }

etsysOidPhy10GbExC10xSFPP OBJECT-IDENTITY
    STATUS      current
--  Name        "10GB-C10-SFPP"
--  Date        "200901051508Z"  - Mon Jan  5 15:08 UTC 2009
    DESCRIPTION
        "Enterasys SFP+ 10 Gigabit Ethernet interface with
         pluggable copper cable assembly and integrated SFP+ transceiver.         
         10M cable length."
    ::= { etsysOidPhy 403 }

etsysOidPhy10GbExC20xSFPP OBJECT-IDENTITY
    STATUS      current
--  Name        "10GB-C20-SFPP"
--  Date        "200901051508Z"  - Mon Jan  5 15:08 UTC 2009
    DESCRIPTION
        "Enterasys SFP+ 10 Gigabit Ethernet interface with
         pluggable copper cable assembly and integrated SFP+ transceiver.         
         20M cable length."
    ::= { etsysOidPhy 404 }

etsysOidPhySFPPNoConnector OBJECT-IDENTITY
    STATUS      current
    DESCRIPTION
--  Date        "200901051508Z"  - Mon Jan  5 15:08 UTC 2009
        "Enterasys SFP+ interface with no physical SFP+ connector
         present."
    ::= { etsysOidPhy 405 }
 
etsysOidPhy10GbExLRMxXFP OBJECT-IDENTITY
    STATUS      current
--  Name        "10GB-LRM-XFP"
--  Date        "200901051508Z"  - Mon Jan  5 15:08 UTC 2009
    DESCRIPTION
        "Enterasys XFP 10GBASE-LRM Ethernet interface with
         1310nm Long Wave Length optics for IEEE 802.3 MM fiber (MMF)
         via a LC connector. 220M fiber length."
    ::= { etsysOidPhy 406 }

etsysOidPhy7SxDNSAx01 OBJECT-IDENTITY
    STATUS      current
--  Name        "7S-DNSA-01"
--  Date        "200903051358Z"  - Thu Mar  5 13:58 UTC 2009
    DESCRIPTION
        "Enterasys 2 Port Mini-GBIC Gigabit Ethernet Uplink Module with 
         Dual Core Integrated Security Processor and Dragon Security 
         Software."
    ::= { etsysOidPhy 407 }

etsysOidPhyS3xCHASSIS OBJECT-IDENTITY
    STATUS      current
--  Name        "S3-CHASSIS"
--  Date        "200903311713Z"  - Tue Mar 31 17:13 UTC 2009
    DESCRIPTION
        "Enterasys 3 slot modular chassis frame for the S-Series family."
    ::= { etsysOidPhy 408 }

etsysOidPhyS4xCHASSIS OBJECT-IDENTITY
    STATUS      current
--  Name        "S4-CHASSIS"
--  Date        "200903311713Z"  - Tue Mar 31 17:13 UTC 2009
    DESCRIPTION
        "Enterasys 4 slot modular chassis frame for the S-Series family."
    ::= { etsysOidPhy 409 }

etsysOidPhyS8xCHASSIS OBJECT-IDENTITY
    STATUS      current
--  Name        "S8-CHASSIS"
--  Date        "200903311713Z"  - Tue Mar 31 17:13 UTC 2009
    DESCRIPTION
        "Enterasys 8 slot modular chassis frame for the S-Series family."
    ::= { etsysOidPhy 410 }

etsysOidPhySxFAN OBJECT-IDENTITY
    STATUS      current
--  Name        "S-FAN"
--  Date        "200903311713Z"  - Tue Mar 31 17:13 UTC 2009
    DESCRIPTION
        "Enterasys S-Series fan tray for the S3, S4 and S8 chassis."
    ::= { etsysOidPhy 411 }

etsysOidPhySxACxPS OBJECT-IDENTITY
    STATUS      current
--  Name        "S-AC-PS"
--  Date        "200903311713Z"  - Tue Mar 31 17:13 UTC 2009
    DESCRIPTION
        "Enterasys S-Series 1200/1600W AC power supplies for the S3, S4 
         and S8 chassis."
    ::= { etsysOidPhy 412 }

etsysOidPhySxPOExPS OBJECT-IDENTITY
    STATUS      current
--  Name        "S-POE-PS"
--  Date        "200903311713Z"  - Tue Mar 31 17:13 UTC 2009
    DESCRIPTION
        "Enterasys S-Series 1200/2000W POE power supplies for the 
         S-POE-4BAY and S-POE-8BAY power subsystems."
    ::= { etsysOidPhy 413 }

etsysOidPhySxPOEx4BAY OBJECT-IDENTITY
    STATUS      current
--  Name        "S-POE-4BAY"
--  Date        "200903311713Z"  - Tue Mar 31 17:13 UTC 2009
    DESCRIPTION
        "Enterasys S-Series 4 slot POE power subsystem for the S3, S4
         and S8 chassis."
    ::= { etsysOidPhy 414 }

etsysOidPhySxPOEx8BAY OBJECT-IDENTITY
    STATUS      current
--  Name        "S-POE-8BAY"
--  Date        "200903311713Z"  - Tue Mar 31 17:13 UTC 2009
    DESCRIPTION
        "Enterasys S-Series 8 slot POE power subsystem for the S8 
         chassis."
    ::= { etsysOidPhy 415 }

etsysOidPhySPowerSupplySlot OBJECT-IDENTITY
    STATUS      current
--  Name        "S-Series Chassis Power Supply Slot"
--  Date        "200903311713Z"  - Tue Mar 31 17:13 UTC 2009
    DESCRIPTION
        "Enterasys S-Series chassis power supply slot for the 
         S3, S4 and S8 chassis."
    ::= { etsysOidPhy 416 }

etsysOidPhySFanTraySlot OBJECT-IDENTITY
    STATUS      current
--  Name        "S-Series Chassis Fan Tray Slot"
--  Date        "200903311713Z"  - Tue Mar 31 17:13 UTC 2009
    DESCRIPTION
        "Enterasys S-Series fan tray slot for the S3, S4 and S8 chassis."
    ::= { etsysOidPhy 417 }

etsysOidPhySIOModuleSlot OBJECT-IDENTITY
    STATUS      current
--  Name        "S-Series Chassis I/O Module Slot"
--  Date        "200903311713Z"  - Tue Mar 31 17:13 UTC 2009
    DESCRIPTION
        "Enterasys S-Series I/O module slot for the S3, S4 and 
         S8 chassis."
    ::= { etsysOidPhy 418 }

etsysOidPhySFabricModuleSlot OBJECT-IDENTITY
    STATUS      current
--  Name        "S-Series Chassis Fabric Module Slot"
--  Date        "200903311713Z"  - Tue Mar 31 17:13 UTC 2009
    DESCRIPTION
        "Enterasys S-Series Fabric module slot for the S4 and 
         S8 chassis."
    ::= { etsysOidPhy 419 }

etsysOidPhySPoEPowerSupplySlot OBJECT-IDENTITY
    STATUS      current
--  Name        "S-Series PoE Power Supply Slot"
--  Date        "200903311713Z"  - Tue Mar 31 17:13 UTC 2009
    DESCRIPTION
        "Enterasys S-Series PoE power supply slot for the 
         S-POE-4BAY and S-POE-8BAY PoE power subsystems."
    ::= { etsysOidPhy 420 }

etsysOidPhySK1208x0808xF6 OBJECT-IDENTITY
    STATUS      current
--  Name        "SK1208-0808-F6"
--  Date        "200903311713Z"  - Tue Mar 31 17:13 UTC 2009
    DESCRIPTION
        "Enterasys S-Series S150 Class I/O-Fabric Module with
         8 ports of 10GBASE-X Ethernet via SFP+ and two Type 2 options 
         slots."
    ::= { etsysOidPhy 421 }

etsysOidPhyST4106x0348xF6 OBJECT-IDENTITY
    STATUS      current
--  Name        "ST4106-0348-F6"
--  Date        "200903311713Z"  - Tue Mar 31 17:13 UTC 2009
    DESCRIPTION
        "Enterasys S-Series S130 Class I/O-Fabric Module with 48 ports of 
         1000BASE-T Ethernet via RJ45 with PoE (802.3at) and one Type 2 
         option slot."
    ::= { etsysOidPhy 422 }

etsysOidPhyST1206x0848xF6 OBJECT-IDENTITY
    STATUS      current
--  Name        "ST1206-0848-F6"
--  Date        "200903311713Z"  - Tue Mar 31 17:13 UTC 2009
    DESCRIPTION
        "Enterasys S-Series S150 Class I/O-Fabric Module with
         48 ports of 1000BASE-T Ethernet via RJ45 with PoE (802.3at) and
         two Type 2 option slots."
    ::= { etsysOidPhy 423 }

etsysOidPhySG1201x0848xF6 OBJECT-IDENTITY
    STATUS      current
--  Name        "SG1201-0848-F6"
--  Date        "200903311713Z"  - Tue Mar 31 17:13 UTC 2009
    DESCRIPTION
        "Enterasys S-Series S150 Class I/O-Fabric Module with
         48 ports of 1000BASE-X Ethernet via SFP and two Type 2 option 
         slots."
    ::= { etsysOidPhy 424 }

etsysOidPhySK1008x0816 OBJECT-IDENTITY
    STATUS      current
--  Name        "SK1008-0816"
--  Date        "200903311713Z"  - Tue Mar 31 17:13 UTC 2009
    DESCRIPTION
        "Enterasys S-Series S150 Class I/O Module with
         16 ports of 10GBASE-X Ethernet via SFP+ connectors."
    ::= { etsysOidPhy 425 }

etsysOidPhyST4106x0248 OBJECT-IDENTITY
    STATUS      current
--  Name        "ST4106-0248"
--  Date        "200903311713Z"  - Tue Mar 31 17:13 UTC 2009
    DESCRIPTION
        "Enterasys S-Series S130 Class I/O Module with 48 ports of 
         1000BASE-T Ethernet via RJ45 with PoE (802.3at) and one 
         Type 1 option slots."
    ::= { etsysOidPhy 426 }

etsysOidPhyST4006x0272 OBJECT-IDENTITY
    STATUS      current
--  Name        "ST4006-0272"
--  Date        "200903311713Z"  - Tue Mar 31 17:13 UTC 2009
    DESCRIPTION
        "Enterasys S-Series S130 Class I/O Module with 72 ports of 
         1000BASE-T Ethernet via RJ45 with PoE (802.3at)."
    ::= { etsysOidPhy 427 }

etsysOidPhyST1206x0848 OBJECT-IDENTITY
    STATUS      current
--  Name        "ST1206-0848"
--  Date        "200903311713Z"  - Tue Mar 31 17:13 UTC 2009
    DESCRIPTION
        "Enterasys S-Series S150 Class I/O Module with
         48 ports of 1000BASE-T Ethernet via RJ45 with PoE (802.3at) and
         two Type 2 option slots."
    ::= { etsysOidPhy 428 }

etsysOidPhySG4101x0248 OBJECT-IDENTITY
    STATUS      current
--  Name        "SG4101-0248"
--  Date        "200903311713Z"  - Tue Mar 31 17:13 UTC 2009
    DESCRIPTION
        "Enterasys S-Series S130 Class I/O Module with 48 ports of 
         1000BASE-X Ethernet via SFP and one Type 1 option slot."
    ::= { etsysOidPhy 429 }

etsysOidPhySG1201x0848 OBJECT-IDENTITY
    STATUS      current
--  Name        "SG1201-0848"
--  Date        "200903311713Z"  - Tue Mar 31 17:13 UTC 2009
    DESCRIPTION
        "Enterasys S-Series S150 Class I/O Module with
         48 ports of 1000BASE-X Ethernet via SFP and two Type 2 option 
         slots."
    ::= { etsysOidPhy 430 }

etsysOidPhySOptModType1Slot OBJECT-IDENTITY
    STATUS      current
--  Name        "S-Series Option Module Type 1 Slot"
--  Date        "200903311713Z"  - Tue Mar 31 17:13 UTC 2009
    DESCRIPTION
        "Enterasys S-Series Type 1 Option Module slot."
    ::= { etsysOidPhy 431 }

etsysOidPhySOptModType2Slot OBJECT-IDENTITY
    STATUS      current
--  Name        "S-Series Option Module Type 2 Slot"
--  Date        "200903311713Z"  - Tue Mar 31 17:13 UTC 2009
    DESCRIPTION
        "Enterasys S-Series Type 2 Option Module slot."
    ::= { etsysOidPhy 432 }

etsysOidPhySOK1208x0104 OBJECT-IDENTITY
    STATUS      current
--  Name        "SOK1208-0104"
--  Date        "200903311713Z"  - Tue Mar 31 17:13 UTC 2009
    DESCRIPTION
        "Enterasys S-Series Type 1 Option Module with 4 ports of 
         10GBASE-X Ethernet via SFP+ connectors."
    ::= { etsysOidPhy 433 }

etsysOidPhySOK1208x0102 OBJECT-IDENTITY
    STATUS      current
--  Name        "SOK1208-0102"
--  Date        "200903311713Z"  - Tue Mar 31 17:13 UTC 2009
    DESCRIPTION
        "Enterasys S-Series Type 1 Option Module with 2 ports of 
         10GBASE-X Ethernet via SFP+ connectors."
    ::= { etsysOidPhy 434 }

etsysOidPhySOK1208x0204 OBJECT-IDENTITY
    STATUS      current
--  Name        "SOK1208-0204"
--  Date        "200903311713Z"  - Tue Mar 31 17:13 UTC 2009
    DESCRIPTION
        "Enterasys S-Series Type 2 Option Module with 4 ports of 
         10GBASE-X Ethernet via SFP+ connectors."
    ::= { etsysOidPhy 435 }

etsysOidPhySOG1201x0112 OBJECT-IDENTITY
    STATUS      current
--  Name        "SOG1201-0112"
--  Date        "200903311713Z"  - Tue Mar 31 17:13 UTC 2009
    DESCRIPTION
        "Enterasys S-Series Type 1 Option Module with 12 ports of 
         1000BASE-X Ethernet via SFP connectors."
    ::= { etsysOidPhy 436 }

etsysOidPhyNN0100x0100xF2 OBJECT-IDENTITY
    STATUS      current
--  Name        "NN0100-0100-F2"
--  Date        "200903311713Z"  - Tue Mar 31 17:13 UTC 2009
    DESCRIPTION
        "Enterasys NGN-Series I/O-Fabric with one NGN option module slot."
    ::= { etsysOidPhy 437 }

etsysOidPhyNT4106x0248 OBJECT-IDENTITY
    STATUS      current
--  Name        "NT4106-0248"
--  Date        "200903311713Z"  - Tue Mar 31 17:13 UTC 2009
    DESCRIPTION
        "Enterasys NGN-Series S130 Class I/O Module with 48 ports of 
         1000BASE-T Ethernet via RJ45 with PoE (802.3at) and one 
         NGN option slot."
    ::= { etsysOidPhy 438 }

etsysOidPhyNT4006x0272 OBJECT-IDENTITY
    STATUS      current
--  Name        "NT4006-0272"
--  Date        "200903311713Z"  - Tue Mar 31 17:13 UTC 2009
    DESCRIPTION
        "Enterasys NGN-Series S130 Class I/O Module with 72 ports of 
         1000BASE-T Ethernet via RJ45 with PoE (802.3at)."
    ::= { etsysOidPhy 439 }

etsysOidPhyNT1006x0448 OBJECT-IDENTITY
    STATUS      current
--  Name        "NT1006-0448"
--  Date        "200903311713Z"  - Tue Mar 31 17:13 UTC 2009
    DESCRIPTION
        "Enterasys NGN-Series S150 Class I/O Module with
         48 ports of 1000BASE-T Ethernet via RJ45 with PoE (802.3at)."
    ::= { etsysOidPhy 440 }

etsysOidPhyNK1008x0408 OBJECT-IDENTITY
    STATUS      current
--  Name        "NK1008-0408"
--  Date        "200903311713Z"  - Tue Mar 31 17:13 UTC 2009
    DESCRIPTION
        "Enterasys NGN-Series S150 Class I/O Module with
         8 ports of 10GBASE-X Ethernet via SFP+."
    ::= { etsysOidPhy 441 }

etsysOidPhyNG1001x0448 OBJECT-IDENTITY
    STATUS      current
--  Name        "NG1001-0448"
--  Date        "200903311713Z"  - Tue Mar 31 17:13 UTC 2009
    DESCRIPTION
        "Enterasys NGN-Series S150 Class I/O Module with 
         48 ports of 1000BASE-X Ethernet via SFP."
    ::= { etsysOidPhy 442 }

etsysOidPhyNG4101x0248 OBJECT-IDENTITY
    STATUS      current
--  Name        "NG4101-0248"
--  Date        "200903311713Z"  - Tue Mar 31 17:13 UTC 2009
    DESCRIPTION
        "Enterasys NGN-Series S130 Class I/O Module with 48 ports of 
         1000BASE-X Ethernet via SFP and one NGN option slot."
    ::= { etsysOidPhy 443 }

etsysOidPhyNGNOptModSlot OBJECT-IDENTITY
    STATUS      current
--  Name        "NGN-Series Option Module Slot"
--  Date        "200903311713Z"  - Tue Mar 31 17:13 UTC 2009
    DESCRIPTION
        "Enterasys NGN-Series Option Module slot."
    ::= { etsysOidPhy 444 }

etsysOidPhyNOK1208x0102 OBJECT-IDENTITY
    STATUS      current
--  Name        "NOK1208-0102"
--  Date        "200903311713Z"  - Tue Mar 31 17:13 UTC 2009
    DESCRIPTION
        "Enterasys NGN-Series Option Module with 2 ports of 
         10GBASE-X Ethernet via SFP+ connectors."
    ::= { etsysOidPhy 445 }

etsysOidPhyNOK1208x0104 OBJECT-IDENTITY
    STATUS      current
--  Name        "NOK1208-0104"
--  Date        "200903311713Z"  - Tue Mar 31 17:13 UTC 2009
    DESCRIPTION
        "Enterasys NGN-Series Option Module with 4 ports of 
         10GBASE-X Ethernet via SFP+ connectors."
    ::= { etsysOidPhy 446 }

etsysOidPhyNOG1201x0112 OBJECT-IDENTITY
    STATUS      current
--  Name        "NOG1201-0112"
--  Date        "200903311713Z"  - Tue Mar 31 17:13 UTC 2009
    DESCRIPTION
        "Enterasys NGN-Series Option Module with 12 ports of 
         1000BASE-X Ethernet via SFP connectors."
    ::= { etsysOidPhy 447 }

etsysOidPhySSAxACxPSx600W OBJECT-IDENTITY
    STATUS      current
--  Name        "SSA-AC-PS-625W"
--  Date        "201010041255Z"  - Mon Oct  4 12:55 UTC 2010
    DESCRIPTION
        "Enterasys S-Series Standalone (SSA) 625W AC power supply."
    ::= { etsysOidPhy 448 }

etsysOidPhySSAxACxPSx1000W OBJECT-IDENTITY
    STATUS      current
--  Name        "SSA-AC-PS-1000W"
--  Date        "200903311713Z"  - Tue Mar 31 17:13 UTC 2009
    DESCRIPTION
        "Enterasys S-Series Standalone (SSA) 1000W AC and PoE power 
         supply."
    ::= { etsysOidPhy 449 }

etsysOidPhySSAPowerSupplySlot OBJECT-IDENTITY
    STATUS      current
--  Name        "S-Series SSA Power Supply Slot"
--  Date        "200903311713Z"  - Tue Mar 31 17:13 UTC 2009
    DESCRIPTION
        "Enterasys S-Series Standalone (SSA) power supply slot."
    ::= { etsysOidPhy 450 }

etsysOidPhy10GBxERxSFPP OBJECT-IDENTITY
    STATUS      current
--  Name        "10GB-ER-SFPP"
--  Date        "200903311713Z"  - Tue Mar 31 17:13 UTC 2009
    DESCRIPTION
        "Enterasys SFP+ 10GBASE-ER Ethernet interface with 
         1440 nm Long Wave Length optics for IEEE 802.3 SM fiber (SMF)
         via a LC connector. 40 Km fiber length."
    ::= { etsysOidPhy 451 }

etsysOidPhyUSBAPort OBJECT-IDENTITY
    STATUS      current
--  Name        "USB-A Receptacle"
--  Date        "200903311713Z"  - Tue Mar 31 17:13 UTC 2009
    DESCRIPTION
        "Enterasys USB-A receptacle."
    ::= { etsysOidPhy 452 }

etsysOidPhyUSBMicroABPort OBJECT-IDENTITY
    STATUS      current
--  Name        "USB Micro-AB Receptacle"
--  Date        "200903311713Z"  - Tue Mar 31 17:13 UTC 2009
    DESCRIPTION
        "Enterasys USB Micro-AB receptacle."
    ::= { etsysOidPhy 453 }

etsysOidPhyS8Backplane OBJECT-IDENTITY
    STATUS      current 
--  Name        "" 
--  Date        "200904071602Z"  - Tue Apr  7 16:02 UTC 2009
    DESCRIPTION 
        "Enterasys S-Series backplane for the S8 chassis."
    ::= { etsysOidPhy 454 } 

etsysOidPhyS4Backplane OBJECT-IDENTITY
    STATUS      current 
--  Name        "" 
--  Date        "200904071602Z"  - Tue Apr  7 16:02 UTC 2009
    DESCRIPTION 
        "Enterasys S-Series backplane for the S4 chassis."
    ::= { etsysOidPhy 455 } 

etsysOidPhyS3Backplane OBJECT-IDENTITY
    STATUS      current 
--  Name        "" 
--  Date        "200904071602Z"  - Tue Apr  7 16:02 UTC 2009
    DESCRIPTION 
        "Enterasys S-Series backplane for the S3 chassis."
    ::= { etsysOidPhy 456 } 

etsysOidPhyN5Backplane OBJECT-IDENTITY
    STATUS      current 
--  Name        "" 
--  Date        "200904071602Z"  - Tue Apr  7 16:02 UTC 2009
    DESCRIPTION 
        "Enterasys backplane for the N5 chassis."
    ::= { etsysOidPhy 457 } 

etsysOidPhyN3Backplane OBJECT-IDENTITY
    STATUS      current 
--  Name        "" 
--  Date        "200904071602Z"  - Tue Apr  7 16:02 UTC 2009
    DESCRIPTION 
        "Enterasys backplane for the N3 chassis."
    ::= { etsysOidPhy 458 } 

etsysOidPhyN1Backplane OBJECT-IDENTITY
    STATUS      current 
--  Name        "" 
--  Date        "200904071602Z"  - Tue Apr  7 16:02 UTC 2009
    DESCRIPTION 
        "Enterasys backplane for the N1 chassis."
    ::= { etsysOidPhy 459 } 

etsysOidPhySOT1206x0112 OBJECT-IDENTITY
    STATUS      current
--  Name        "SOT1206-0112"
--  Date        "200906221944Z"  - Mon Jun 22 19:44 UTC 2009
    DESCRIPTION
        "Enterasys S-Series Type 1 Option Module with 12 ports of
         1000BASE-T Ethernet via RJ45 with PoE (802.3at)."
    ::= { etsysOidPhy 460 }

etsysOidPhyNOT1206x0112 OBJECT-IDENTITY
    STATUS      current
--  Name        "NOT1206-0112"
--  Date        "200907021738Z"  - Thu Jul  2 17:38 UTC 2009
    DESCRIPTION
        "Enterasys NGN-Series Option Module with 12 ports of
         1000BASE-T Ethernet via RJ45 with PoE (802.3at)."
    ::= { etsysOidPhy 461 }

etsysOidPhyConsolePortUsbMicroAB OBJECT-IDENTITY
    STATUS      current
--  Name        ""
--  Date        "200907081537Z"  - Wed Jul  8 15:37 UTC 2009
    DESCRIPTION 
        "Enterasys local management console port via a Serial-to-USB 
         Bridge with a USB Micro-AB receptacle."
    ::= { etsysOidPhy 462 }

etsysOidPhySSAxFAN OBJECT-IDENTITY
    STATUS      current
--  Name        "SSA-FAN"
--  Date        "200909302004Z"  - Wed Sep 30 20:04 UTC 2009
    DESCRIPTION
        "Enterasys S-Series Standalone (SSA) fan."
    ::= { etsysOidPhy 463 }

etsysOidPhyNSAxFAN OBJECT-IDENTITY
    STATUS      current
--  Name        ""
--  Date        "200910261715Z"  - Mon Oct 26 17:15 UTC 2009
    DESCRIPTION
        "Enterasys N-Series Standalone (NSA) internal fan assembly.  This
         assembly is not field upgradeable."
    ::= { etsysOidPhy 464 }

etsysOidPhyNSAxACxPS OBJECT-IDENTITY
    STATUS      current
--  Name        ""
--  Date        "200910261715Z"  - Mon Oct 26 17:15 UTC 2009
    DESCRIPTION
        "Enterasys N-Series Standalone (NSA) internal power supply.  This
         assembly is not field upgradeable."
    ::= { etsysOidPhy 465 }

etsysOidPhyN1xFAN OBJECT-IDENTITY
    STATUS      current
--  Name        ""
--  Date        "200910261715Z"  - Mon Oct 26 17:15 UTC 2009
    DESCRIPTION
        "Enterasys N-1 chassis internal fan assembly.  This assembly is 
         not field upgradeable."
    ::= { etsysOidPhy 466 }

etsysOidPhyN1xACxPS OBJECT-IDENTITY
    STATUS      current
--  Name        ""
--  Date        "200910261715Z"  - Mon Oct 26 17:15 UTC 2009
    DESCRIPTION
        "Enterasys N-1 chassis internal power supply.  This assembly is 
         not field upgradeable."
    ::= { etsysOidPhy 467 }

etsysOidPhy10GBxLWxSFPP OBJECT-IDENTITY
    STATUS      current
--  Name        "10GB-LW-SFPP"
--  Date        "201005041953Z"  - Tue May  4 19:53 UTC 2010
    DESCRIPTION
        "10Gb, Laserwire(R) SFP+ adapter for use with Laserwire cable 
         assembly.*

         * The Laserwire(R) mark is a registered trademark and is the 
           property of Finisar Corporation."
    ::= { etsysOidPhy 468 }

etsysOidPhy10GBxLWxXFP OBJECT-IDENTITY
    STATUS      current
--  Name        "10GB-LW-XFP"
--  Date        "201005041953Z"  - Tue May  4 19:53 UTC 2010
    DESCRIPTION
        "10Gb, Laserwire(R) XFP adapter for use with Laserwire cable 
         assembly.*

         * The Laserwire(R) mark is a registered trademark and is the 
           property of Finisar Corporation."
    ::= { etsysOidPhy 469 }

etsysOidPhy10GBxLWx20 OBJECT-IDENTITY
    STATUS      current
--  Name        "10GB-LW-20"
--  Date        "201005041953Z"  - Tue May  4 19:53 UTC 2010
    DESCRIPTION
        "10Gb, 20 meter Laserwire(R) cable assembly.*

         * The Laserwire(R) mark is a registered trademark and is the 
           property of Finisar Corporation."
    ::= { etsysOidPhy 470 }

etsysOidPhy10GBxLWx10 OBJECT-IDENTITY
    STATUS      current
--  Name        "10GB-LW-10"
--  Date        "201005041953Z"  - Tue May  4 19:53 UTC 2010
    DESCRIPTION
        "10Gb, 10 meter Laserwire(R) cable assembly.*

         * The Laserwire(R) mark is a registered trademark and is the 
           property of Finisar Corporation."
    ::= { etsysOidPhy 471 }

etsysOidPhy10GBxLWx05 OBJECT-IDENTITY
    STATUS      current
--  Name        "10GB-LW-05"
--  Date        "201005041953Z"  - Tue May  4 19:53 UTC 2010
    DESCRIPTION
        "10Gb, 5 meter Laserwire(R) cable assembly.*

         * The Laserwire(R) mark is a registered trademark and is the 
           property of Finisar Corporation."
    ::= { etsysOidPhy 472 }

etsysOidPhy10GBxLWx03 OBJECT-IDENTITY
    STATUS      current
--  Name        "10GB-LW-03"
--  Date        "201005041953Z"  - Tue May  4 19:53 UTC 2010
    DESCRIPTION
        "10Gb, 3 meter Laserwire(R) cable assembly.*

         * The Laserwire(R) mark is a registered trademark and is the 
           property of Finisar Corporation."
    ::= { etsysOidPhy 473 }

etsysOidPhyMGBICxBX10xD OBJECT-IDENTITY
    STATUS      current
--  Name        "MGBIC-BX10-D"
--  Date        "201006101427Z"  - Thu Jun 10 14:27 UTC 2010
    DESCRIPTION
        "Enterasys MGBIC-BX10-D, a 1000BASE-BX10 Downstream Single 
         Fiber SM, Bidirectional, 1490nm Tx / 1310nm Rx, 10 km, Simplex 
         LC SFP.  This part must be paired with MGBIC-BX10-U."
    ::= { etsysOidPhy 474 }
 
etsysOidPhyMGBICxBX10xU OBJECT-IDENTITY
    STATUS      current
--  Name        "MGBIC-BX10-U"
--  Date        "201006101427Z"  - Thu Jun 10 14:27 UTC 2010
    DESCRIPTION
        "Enterasys MGBIC-BX10-D, a 1000BASE-BX10 Upstream Single Fiber 
         SM, Bidirectional, 1310nm Tx / 1490nm Rx, 10 km, Simplex LC SFP.
         This part must be paired with MGBIC-BX10-D."
    ::= { etsysOidPhy 475 }

etsysOidPhyIncompatiblePluggable OBJECT-IDENTITY
    STATUS      current
    DESCRIPTION
--  Date        "201009081439Z"  - Wed Sep  8 14:39 UTC 2010
        "Enterasys pluggable port slot with an incompatible pluggable 
         module inserted."
    ::= { etsysOidPhy 476 }
 
etsysOidPhySK5208x0808xF6 OBJECT-IDENTITY
    STATUS      current
--  Name        "SK5208-0808-F6"
--  Date        "201011181815Z"  - Thu Nov 18 18:15 UTC 2010
    DESCRIPTION
        "Enterasys S-Series S155 Class I/O-Fabric Module with
         8 ports of 10GBASE-X Ethernet via SFP+ and two Type 2 options
         slots."
    ::= { etsysOidPhy 477 }

etsysOidPhyST5206x0848xF6 OBJECT-IDENTITY
    STATUS      current
--  Name        "ST5206-0848-F6"
--  Date        "201011181815Z"  - Thu Nov 18 18:15 UTC 2010
    DESCRIPTION
       "Enterasys S-Series S155 Class I/O-Fabric Module with
        48 ports of 1000BASE-T Ethernet via RJ45 with PoE (802.3at) and
        two Type 2 option slots."
    ::= { etsysOidPhy 478 }

etsysOidPhySG5201x0848xF6 OBJECT-IDENTITY 
    STATUS      current 
--  Name        "SG5201-0848-F6" 
--  Date        "201011181815Z"  - Thu Nov 18 18:15 UTC 2010
    DESCRIPTION 
        "Enterasys S-Series S155 Class I/O-Fabric Module with 
         48 ports of 1000BASE-X Ethernet via SFP and two Type 2 option 
         slots." 
    ::= { etsysOidPhy 479 }

etsysOidPhyK6xCHASSIS OBJECT-IDENTITY
    STATUS      current
--  Name        "K6-CHASSIS"
--  Date        "201011181818Z"  - Thu Nov 18 18:18 UTC 2010
    DESCRIPTION
        "Enterasys 6 slot modular chassis frame for the K-Series family."
    ::= { etsysOidPhy 480 }

etsysOidPhyK10xCHASSIS OBJECT-IDENTITY
    STATUS      current
--  Name        "K10-CHASSIS"
--  Date        "201011181818Z"  - Thu Nov 18 18:18 UTC 2010
    DESCRIPTION
        "Enterasys 10 slot modular chassis frame for the K-Series family."
    ::= { etsysOidPhy 481 }

etsysOidPhyK6xFAN OBJECT-IDENTITY
    STATUS      current
--  Name        "K6-FAN"
--  Date        "201011181818Z"  - Thu Nov 18 18:18 UTC 2010
    DESCRIPTION
        "Enterasys K-Series fan tray for the K6 chassis."
    ::= { etsysOidPhy 482 }

etsysOidPhyK10xFAN OBJECT-IDENTITY
    STATUS      current
--  Name        "K10-FAN"
--  Date        "201011181818Z"  - Thu Nov 18 18:18 UTC 2010
    DESCRIPTION
        "Enterasys K-Series fan tray for the K10 chassis."
    ::= { etsysOidPhy 483 }

etsysOidPhyKxACxPSx1440W OBJECT-IDENTITY
    STATUS      current
--  Name        "K-AC-PS-1400W"
--  Date        "201011181818Z"  - Thu Nov 18 18:18 UTC 2010
    DESCRIPTION
        "Enterasys K-Series AC and PoE power supplie, 15A, 110-240VAC 
         input, 1400W."
    ::= { etsysOidPhy 484 }

etsysOidPhyKxPOExExtConn OBJECT-IDENTITY
    STATUS      current
--  Name        "K-Series External PoE Power Connector"
--  Date        "201011181818Z"  - Thu Nov 18 18:18 UTC 2010
    DESCRIPTION
        "Enterasys K-Series physical power connector for an external PoE
         shelf."
    ::= { etsysOidPhy 485 }

etsysOidPhyKPowerSupplySlot OBJECT-IDENTITY
    STATUS      current
--  Name        "K-Series Chassis Power Supply Slot"
--  Date        "200903311713Z"  - Tue Mar 31 17:13 UTC 2009
    DESCRIPTION
        "Enterasys K-Series chassis power supply slot for the 
         K6 and K10 chassis."
    ::= { etsysOidPhy 486 }

etsysOidPhyK6FanTraySlot OBJECT-IDENTITY
    STATUS      current
--  Name        "K6 Chassis Fan Tray Slot"
--  Date        "201011181818Z"  - Thu Nov 18 18:18 UTC 2010
    DESCRIPTION
        "Enterasys K-Series fan tray slot for the K6 chassis."
    ::= { etsysOidPhy 487 }

etsysOidPhyK10FanTraySlot OBJECT-IDENTITY
    STATUS      current
--  Name        "K10 Chassis Fan Tray Slot"
--  Date        "201011181818Z"  - Thu Nov 18 18:18 UTC 2010
    DESCRIPTION
        "Enterasys K-Series fan tray slot for the K10 chassis."
    ::= { etsysOidPhy 488 }

etsysOidPhyKLineCardSlot OBJECT-IDENTITY
    STATUS      current
--  Name        "K-Series Chassis Linecard Slot"
--  Date        "201011181818Z"  - Thu Nov 18 18:18 UTC 2010
    DESCRIPTION
        "Enterasys K-Series linecard slot for the K6 and K10 chassis."
    ::= { etsysOidPhy 489 }

etsysOidPhyKFabricModuleSlot OBJECT-IDENTITY
    STATUS      current
--  Name        "K-Series Chassis Fabric Module Slot"
--  Date        "201011181818Z"  - Thu Nov 18 18:18 UTC 2010
    DESCRIPTION
        "Enterasys K-Series Fabric Module slot for the K6 and K10 chassis."
    ::= { etsysOidPhy 490 }

etsysOidPhyKK2008x0204xF1 OBJECT-IDENTITY
    STATUS      current
--  Name        "KK2008-0204-F1"
--  Date        "201011181818Z"  - Thu Nov 18 18:18 UTC 2010
    DESCRIPTION
        "Enterasys K-Series Fabric Module with 4 ports of 10GBASE-X 
         Ethernet via SFP+ for the K6 chassis."
    ::= { etsysOidPhy 491 }
 
etsysOidPhyKK2008x0204xF2 OBJECT-IDENTITY
    STATUS      current
--  Name        "KK2008-0204-F2"
--  Date        "201011181818Z"  - Thu Nov 18 18:18 UTC 2010
    DESCRIPTION
        "Enterasys K-Series Fabric Module with 4 ports of 10GBASE-X 
         Ethernet via SFP+ for the K10 chassis."
    ::= { etsysOidPhy 492 }
 
etsysOidPhyKK2000x0000xF1 OBJECT-IDENTITY
    STATUS      current
--  Name        "KK2000-0000-F1"
--  Date        "201011181818Z"  - Thu Nov 18 18:18 UTC 2010
    DESCRIPTION
        "Enterasys K-Series Fabric Module for the K6 chassis."
    ::= { etsysOidPhy 493 }
 
etsysOidPhyKK2000x0000xF2 OBJECT-IDENTITY
    STATUS      current
--  Name        "KK2000-0000-F2"
--  Date        "201011181818Z"  - Thu Nov 18 18:18 UTC 2010
    DESCRIPTION
        "Enterasys K-Series Fabric Module for the K10 chassis."
    ::= { etsysOidPhy 494 }
 
etsysOidPhyKT2006x0224 OBJECT-IDENTITY
    STATUS      current
--  Name        "KT2006-0224"
--  Date        "201011181818Z"  - Thu Nov 18 18:18 UTC 2010
    DESCRIPTION
        "Enterasys K-Series Linecard with 24 ports of 1000BASE-T 
         Ethernet via RJ45 with PoE (802.3at)."
    ::= { etsysOidPhy 495 }

etsysOidPhyKG2001x0224 OBJECT-IDENTITY
    STATUS      current
--  Name        "KG2001-0224"
--  Date        "201011181818Z"  - Thu Nov 18 18:18 UTC 2010
    DESCRIPTION
        "Enterasys K-Series Linecard with 24 ports of 1000BASE-X 
         Ethernet via SFP connectors."
    ::= { etsysOidPhy 496 }

etsysOidPhyKK2008x0204 OBJECT-IDENTITY
    STATUS      current
--  Name        "KK2008-0204"
--  Date        "201011181818Z"  - Thu Nov 18 18:18 UTC 2010
    DESCRIPTION
        "Enterasys K-Series Linecard with 4 ports of 10GBASE-X 
         Ethernet via SFP+ connectors."
    ::= { etsysOidPhy 497 }

etsysOidPhyK6Backplane OBJECT-IDENTITY
    STATUS      current 
--  Name        "" 
--  Date        "201011181818Z"  - Thu Nov 18 18:18 UTC 2010
    DESCRIPTION 
        "Enterasys K-Series backplane for the K6 chassis."
    ::= { etsysOidPhy 498 } 

etsysOidPhyK10Backplane OBJECT-IDENTITY
    STATUS      current 
--  Name        "" 
--  Date        "201011181818Z"  - Thu Nov 18 18:18 UTC 2010
    DESCRIPTION 
        "Enterasys K-Series backplane for the K10 chassis."
    ::= { etsysOidPhy 499 } 

etsysOidPhySxDCxPS OBJECT-IDENTITY
    STATUS      current
--  Name        "S-DC-PS"
--  Date        "201012021833Z"  - Thu Dec  2 18:33 UTC 2010
    DESCRIPTION
        "Enterasys S-Series 1200W DC power supplies for the S3, S4 
         and S8 chassis."
    ::= { etsysOidPhy 500 }

etsysOidPhyMGBICxBX40xD OBJECT-IDENTITY
    STATUS      current
--  Name        "MGBIC-BX40-D"
--  Date        "201012141337Z"  - Tue Dec 14 13:37 UTC 2010
    DESCRIPTION
        "Enterasys MGBIC-BX10-D, a 1000BASE-BX40 Downstream Single
         Fiber SM, Bidirectional, 1490nm Tx / 1310nm Rx, 40 km, Simplex
         LC SFP.  This part must be paired with MGBIC-BX40-U."
    ::= { etsysOidPhy 501 }

etsysOidPhyMGBICxBX40xU OBJECT-IDENTITY
    STATUS      current
--  Name        "MGBIC-BX40-U"
--  Date        "201012141337Z"  - Tue Dec 14 13:37 UTC 2010
    DESCRIPTION
        "Enterasys MGBIC-BX10-D, a 1000BASE-BX40 Upstream Single Fiber
         SM, Bidirectional, 1310nm Tx / 1490nm Rx, 40 km, Simplex LC SFP.
         This part must be paired with MGBIC-BX40-D."
    ::= { etsysOidPhy 502 }

etsysOidPhyMGBICxBX120xD OBJECT-IDENTITY
    STATUS      current
--  Name        "MGBIC-BX120-D"
--  Date        "201012141337Z"  - Tue Dec 14 13:37 UTC 2010
    DESCRIPTION
        "Enterasys MGBIC-BX10-D, a 1000BASE-BX120 Downstream Single
         Fiber SM, Bidirectional, 1590nm Tx / 1490nm Rx, 120 km, Simplex
         LC SFP.  This part must be paired with MGBIC-BX120-U."
    ::= { etsysOidPhy 503 }

etsysOidPhyMGBICxBX120xU OBJECT-IDENTITY
    STATUS      current
--  Name        "MGBIC-BX120-U"
--  Date        "201012141337Z"  - Tue Dec 14 13:37 UTC 2010
    DESCRIPTION
        "Enterasys MGBIC-BX10-D, a 1000BASE-BX120 Upstream Single Fiber
         SM, Bidirectional, 1490nm Tx / 1590nm Rx, 120 km, Simplex LC SFP.
         This part must be paired with MGBIC-BX120-D."
    ::= { etsysOidPhy 504 }

etsysOidDevSSAxT5068x0652 OBJECT-IDENTITY
    STATUS    current
--  Name      "SSA-T5068-0652"
--  Date      "201012201841Z"  - Mon Dec 20 18:41 UTC 2010
    DESCRIPTION
        "Enterasys S-Series S155 Class Standalone (SSA) device
         with 48 ports of 1000BASE-T Ethernet via RJ45 with PoE (802.3at)
         and 4 10GBASE-X Ethernet ports via SFP+."
    ::= { etsysOidDevice 505 }

etsysOidDevSSAxG5018x0652 OBJECT-IDENTITY
    STATUS    current
--  Name      "SSA-G5018-0652"
--  Date      "201012201841Z"  - Mon Dec 20 18:41 UTC 2010
    DESCRIPTION
        "Enterasys S-Series S155 Class Standalone (SSA) device
         with 48 ports of 1000BASE-X Ethernet via SFP and 4 10GBASE-X
         Ethernet ports via SFP+."
    ::= { etsysOidDevice 506 }

etsysOidPhyS6xCHASSIS OBJECT-IDENTITY
    STATUS      current
--  Name        "S6-CHASSIS"
--  Date        "201101131927Z"  - Thu Jan 13 19:27 UTC 2011
    DESCRIPTION
        "Enterasys 6 slot modular chassis frame for the S-Series family."
    ::= { etsysOidPhy 507 }

etsysOidPhyS6Backplane OBJECT-IDENTITY
    STATUS      current 
--  Name        "" 
--  Date        "201101131927Z"  - Thu Jan 13 19:27 UTC 2011
    DESCRIPTION 
        "Enterasys S-Series backplane for the S6 chassis."
    ::= { etsysOidPhy 508 } 

--  This part of the OID tree is used for OID assignments for all
--  other uses.  Objects under this branch MAY NOT include
--  physical components or SNMP manageable entities.  Such assignments
--  may include, but are not limited to:
--     o Firmware version
--     o Software version

etsysOidOther OBJECT IDENTIFIER ::= { etsysOids 3 }

etsysOidIEEE8023adLagInterface OBJECT-IDENTITY
    STATUS      current
--  Date        "200206061841Z"  - Thu Jun  6 18:41 GMT 2002
    DESCRIPTION
        "IEEE 802.3ad Link Aggregation virtual interface corresponding
         to the IANAifType ieee8023agLag (161)."
    ::= { etsysOidOther 1 }

etsysOidOtherLicenseKeyId OBJECT IDENTIFIER ::= { etsysOidOther 2 }


END
