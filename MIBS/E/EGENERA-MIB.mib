--
-- egenera.v1.mib
--
-- Copyright 2000 Egenera, Inc. All rights reserved.
-- This software is the proprietary information of Egenera, Inc.
--
-- This MIB exposes attributes of Egenera BladeFrames in the Egenera PAN.
--
-- Egenera Enterprise Support:
-- phone:   1 866 301 3117
-- email:   support@egenera.com
-- Address:
--          165 Forest Street
--          Marlboro, MA 01752
--
-- Last Updated: 08/30/05
--
-- 08/30/05 - Addition of Power Input Module (PIM) table and traps.
--            Support for cBlade Etherenet Link and REth Membership
--            state, and REth State."

-- 01/15/04 - Enchancements for the "New Logical Model" (Release 4.0)
--            Including new traps so that every user visible event is
--            supported by a trap.  Deprected existing traps that are
--            no longer driven by any PAN Manager event.
--
--            Also introduced additional application visibility in the MIB
--            to support new application event/traps.

-- 09/29/03 - Set of traps expanded.  The goal is to provide a trap for each
--            user visible event type.  Initially, traps only added for sev
--            1-3 event types not previously supported by traps.
--
--            Additionally, traps defined due to early requirements documents
--            that no longer have an event type to drive the trap have been
--            identified as deprecated in the trap definitions.

EGENERA-MIB DEFINITIONS ::= BEGIN

IMPORTS
    Counter, Gauge, TimeTicks, IpAddress, enterprises
        FROM RFC1155-SMI

    TRAP-TYPE
        FROM RFC-1215

    OBJECT-TYPE
        FROM RFC-1212;

    DisplayString ::=
        OCTET STRING

TruthValue ::= INTEGER {
        true(1),
        false(2)
    }

PhysAddress ::=
    OCTET STRING



-- Egenera proprietary OIDs

egenera         OBJECT IDENTIFIER ::= { enterprises 7559 }


-- Egenera proprietary OIDs

management      OBJECT IDENTIFIER ::= { egenera 1 }
thirdParty      OBJECT IDENTIFIER ::= { egenera 100 }
-- experimental    OBJECT IDENTIFIER ::= { egenera 200 }

panManager      OBJECT IDENTIFIER ::= { management 1 }



-- panManager group
--   Contains information about the Egenera PAN Manager agent.


panManagerPANName OBJECT-TYPE
    SYNTAX      DisplayString
    ACCESS      read-only
    STATUS      mandatory
    DESCRIPTION
            "A textual string identifying the Egenera PAN represented by
            this PAN Manager agent."

        ::=     { panManager 1 }


panManagerId OBJECT-TYPE
    SYNTAX      DisplayString
    ACCESS      read-only
    STATUS      mandatory
    DESCRIPTION
            "A textual string uniquely identifying the PAN Manager agent."

        ::=     { panManager 2 }


panManagerHostname OBJECT-TYPE
    SYNTAX      DisplayString
    ACCESS      read-only
    STATUS      mandatory
    DESCRIPTION
            "A textual string identifying the hostname on which the
            master PAN Manager agent is running."

        ::=     { panManager 3 }


panManagerAgentType OBJECT-TYPE
    SYNTAX      DisplayString
    ACCESS      read-only
    STATUS      mandatory
    DESCRIPTION
            "An OID representing the agent type of the agent.
            Possible values include PAN, LPAN, and BladeFrame.
            
            NOTE:  BladeFrame agent types are deprecated and subject
            to removal."

        ::=     { panManager 4 }




agentTypes      OBJECT IDENTIFIER ::= { panManager 5 }

pan             OBJECT IDENTIFIER ::= { agentTypes 1 }
lPan            OBJECT IDENTIFIER ::= { agentTypes 2 }
bladeFrame      OBJECT IDENTIFIER ::= { agentTypes 3 }



roles           OBJECT IDENTIFIER ::= { panManager 9 }
panRoles        OBJECT IDENTIFIER ::= { roles 1 }
bladeFrameRoles OBJECT IDENTIFIER ::= { roles 2 }
lpanRoles       OBJECT IDENTIFIER ::= { roles 3 }


-- pan roles

panRoleTable    OBJECT-TYPE
    SYNTAX      SEQUENCE OF PanRoleEntry
    ACCESS      not-accessible
    STATUS      mandatory
    DESCRIPTION
            "A table of PAN panRoles."

        ::=     { panRoles 1 }


panRoleEntry OBJECT-TYPE
    SYNTAX      PanRoleEntry
    ACCESS      not-accessible
    STATUS      mandatory
    DESCRIPTION
            "A panRoleEntry contains general information about each
            PAN Role."

    INDEX       { panRoleIndex }
        ::=     { panRoleTable 1 }


PanRoleEntry ::=
    SEQUENCE {
        panRoleIndex
            INTEGER (1..2147483647),
        panRoleName
            DisplayString,
        panRoleDescription
            DisplayString
    }

panRoleIndex OBJECT-TYPE
    SYNTAX      INTEGER (1..2147483647)
    ACCESS      read-only
    STATUS      mandatory
    DESCRIPTION
            "An integer value uniquely identifying the PAN role:
                1: Administrator, 2: Operator, 3: Monitor"

        ::=     { panRoleEntry 1 }


panRoleName OBJECT-TYPE
    SYNTAX      DisplayString
    ACCESS      read-only
    STATUS      mandatory
    DESCRIPTION
            "The human readable name of the PAN role."

        ::=     { panRoleEntry 2 }


panRoleDescription OBJECT-TYPE
    SYNTAX      DisplayString
    ACCESS      read-only
    STATUS      mandatory
    DESCRIPTION
            "The human readable description of the PAN role."

        ::=     { panRoleEntry 3 }



-- BladeFrame roles

bladeFrameRoleTable  OBJECT-TYPE
    SYNTAX      SEQUENCE OF BladeFrameRoleEntry
    ACCESS      not-accessible
    STATUS      mandatory
    DESCRIPTION
            "A table of BladeFrame roles.
            
            NOTE: BladeFrame roles are deprecated and subject to removal."

        ::=     { bladeFrameRoles 1 }


bladeFrameRoleEntry OBJECT-TYPE
    SYNTAX      BladeFrameRoleEntry
    ACCESS      not-accessible
    STATUS      mandatory
    DESCRIPTION
            "A bladeFrameRoleEntry contains general information about each
            BladeFrame Role.
            
            NOTE: BladeFrame roles are deprecated and subject to removal."

    INDEX       { bladeFrameIndex, bladeFrameRoleIndex }
        ::=     { bladeFrameRoleTable 1 }


BladeFrameRoleEntry ::=
    SEQUENCE {
        bladeFrameRoleIndex
            INTEGER (1..2147483647),
        bladeFrameRoleBladeFrameIndex
            INTEGER,
        bladeFrameRoleName
            DisplayString,
        bladeFrameRoleDescription
            DisplayString
    }

bladeFrameRoleIndex OBJECT-TYPE
    SYNTAX      INTEGER (1..2147483647)
    ACCESS      read-only
    STATUS      mandatory
    DESCRIPTION
            "An integer value uniquely identifying the BladeFrame role:
                1: Administrator, 2: Operator, 3: Monitor
                
                NOTE: BladeFrame roles are deprecated and subject to removal."

        ::=     { bladeFrameRoleEntry 1 }


bladeFrameRoleBladeFrameIndex OBJECT-TYPE
    SYNTAX      INTEGER
    ACCESS      read-only
    STATUS      mandatory
    DESCRIPTION
            "The bladeFrameIndex value of the BladeFrame that this role applies
            to.
            
            NOTE: BladeFrame roles are deprecated and subject to removal."

        ::=     { bladeFrameRoleEntry 2 }


bladeFrameRoleName OBJECT-TYPE
    SYNTAX      DisplayString
    ACCESS      read-only
    STATUS      mandatory
    DESCRIPTION
            "The human readable name of the BladeFrame role.
            
            NOTE: BladeFrame roles are deprecated and subject to removal."

        ::=     { bladeFrameRoleEntry 3 }


bladeFrameRoleDescription OBJECT-TYPE
    SYNTAX      DisplayString
    ACCESS      read-only
    STATUS      mandatory
    DESCRIPTION
            "The human readable description of the BladeFrame role.
            
            NOTE: BladeFrame roles are deprecated and subject to removal."

        ::=     { bladeFrameRoleEntry 4 }


-- LPAN Roles

lpanRoleTable  OBJECT-TYPE
    SYNTAX      SEQUENCE OF LpanRoleEntry
    ACCESS      not-accessible
    STATUS      mandatory
    DESCRIPTION
            "A table of LPAN roles."

        ::=     { lpanRoles 1 }

lpanRoleEntry OBJECT-TYPE
    SYNTAX      LpanRoleEntry
    ACCESS      not-accessible
    STATUS      mandatory
    DESCRIPTION
            "A lpanRoleEntry contains general information about each
            LPAN Role."

    INDEX       { lPanIndex,  lpanRoleIndex }
        ::=     { lpanRoleTable 1 }


LpanRoleEntry ::=
    SEQUENCE {
        lpanRoleIndex
            INTEGER (1..2147483647),
        lpanRoleLpanIndex
            INTEGER,
        lpanRoleName
            DisplayString,
        lpanRoleDescription
            DisplayString
    }

lpanRoleIndex OBJECT-TYPE
    SYNTAX      INTEGER (1..2147483647)
    ACCESS      read-only
    STATUS      mandatory
    DESCRIPTION
            "An integer value uniquely identifying the LPAN role:
                1: Administrator, 2: Operator, 3: Monitor"

        ::=     { lpanRoleEntry 1 }


lpanRoleLpanIndex OBJECT-TYPE
    SYNTAX      INTEGER
    ACCESS      read-only
    STATUS      mandatory
    DESCRIPTION
            "The lpanIndex of value of the LPAN that this role applies to."

        ::=     { lpanRoleEntry 2 }


lpanRoleName OBJECT-TYPE
    SYNTAX      DisplayString
    ACCESS      read-only
    STATUS      mandatory
    DESCRIPTION
            "The human readable name of the LPAN role."

        ::=     { lpanRoleEntry 3 }


lpanRoleDescription OBJECT-TYPE
    SYNTAX      DisplayString
    ACCESS      read-only
    STATUS      mandatory
    DESCRIPTION
            "The human readable description of the BladeFrame role."

        ::=     { lpanRoleEntry 4 }



-- panUsers group
--    Countains information about authorized users

userTable  OBJECT-TYPE
    SYNTAX      SEQUENCE OF UserEntry
    ACCESS      not-accessible
    STATUS      mandatory
    DESCRIPTION
            "A table of PAN users."

        ::=     { panManager 10 }


userEntry OBJECT-TYPE
    SYNTAX      UserEntry
    ACCESS      not-accessible
    STATUS      mandatory
    DESCRIPTION
            "A UserEntry contains general information about each
            user in the Egenera PAN."

    INDEX       { userIndex }
        ::=     { userTable 1 }


UserEntry ::=
    SEQUENCE {
        userIndex
            INTEGER (1..2147483647),
        userName
            DisplayString,
        userFullName
            DisplayString,
        userTitle
            DisplayString,
        userDescription
            DisplayString,
        userDepartment
            DisplayString,
        userEmail
            DisplayString
    }


userIndex OBJECT-TYPE
    SYNTAX      INTEGER (1..2147483647)
    ACCESS      read-only
    STATUS      mandatory
    DESCRIPTION
            "An integer value uniquely identifying the user."

        ::=     { userEntry 1 }


userName OBJECT-TYPE
    SYNTAX      DisplayString
    ACCESS      read-only
    STATUS      mandatory
    DESCRIPTION
            "The username for this user."

        ::=     { userEntry 2 }


userFullName OBJECT-TYPE
    SYNTAX      DisplayString
    ACCESS      read-only
    STATUS      mandatory
    DESCRIPTION
            "The full name for this user."

        ::=     { userEntry 3 }


userTitle OBJECT-TYPE
    SYNTAX      DisplayString
    ACCESS      read-only
    STATUS      mandatory
    DESCRIPTION
            "The title of this user."

        ::=     { userEntry 4 }


userDescription OBJECT-TYPE
    SYNTAX      DisplayString
    ACCESS      read-only
    STATUS      mandatory
    DESCRIPTION
            "The description of this user."

        ::=     { userEntry 5 }


userDepartment OBJECT-TYPE
    SYNTAX      DisplayString
    ACCESS      read-only
    STATUS      mandatory
    DESCRIPTION
            "The department of this user."

        ::=     { userEntry 6 }


userEmail OBJECT-TYPE
    SYNTAX      DisplayString
    ACCESS      read-only
    STATUS      mandatory
    DESCRIPTION
            "The email address for this user."

        ::=     { userEntry 7 }


userRoleTable  OBJECT-TYPE
    SYNTAX      SEQUENCE OF UserRoleEntry
    ACCESS      not-accessible
    STATUS      mandatory
    DESCRIPTION
            "A table indicating the set of roles that each user belongs
            to.  There are three types of roles; Administrator, Operator,
            and Monitor.  Each of these roles exists for each LPAN, for
            each BladeFrame, and for the PAN.
            
            NOTE: BladeFrame roles are deprecated and subject to removal."

        ::=     { panManager 12 }


userRoleEntry OBJECT-TYPE
    SYNTAX      UserRoleEntry
    ACCESS      not-accessible
    STATUS      mandatory
    DESCRIPTION
            "Each UserRoleEntry indicates a role that a user belongs to."

    INDEX       { userIndex, userRoleIndex }
        ::=     { userRoleTable 1 }


UserRoleEntry ::=
    SEQUENCE {
        userRoleUserIndex
            INTEGER (1..2147483647),
        userRoleIndex
            INTEGER (1..2147483647),
        userRoleRoleOid
            OBJECT IDENTIFIER
    }


userRoleUserIndex OBJECT-TYPE
    SYNTAX      INTEGER (1..2147483647)
    ACCESS      read-only
    STATUS      mandatory
    DESCRIPTION
            "The userIndex of the user that belongs to this role."

        ::=     { userRoleEntry 1 }


userRoleIndex OBJECT-TYPE
    SYNTAX      INTEGER (1..2147483647)
    ACCESS      read-only
    STATUS      mandatory
    DESCRIPTION
            "An integer index identifying this user/role relationship."

        ::=     { userRoleEntry 2 }


userRoleRoleOid OBJECT-TYPE
    SYNTAX      OBJECT IDENTIFIER
    ACCESS      read-only
    STATUS      mandatory
    DESCRIPTION
            "The fully qualified index OID of the role assigned to this user.
            The OID will uniquely identify a panRoleIndex, bladeFrameRoleIndex,
            or lpanRoleIndex instance.
            
            NOTE: BladeFrame roles are deprecated and subject to removal."

        ::=     { userRoleEntry 3 }


-- bladeFrames group
--   Contains information about BladeFrames in the Egenera PAN.

PowerStatusType ::= INTEGER {
        on(1),
        off(2),
        undefined(999)
    }

HealthStatusType ::= INTEGER {
        green(1),
        yellow(2),
        red(3),
        undefined(999)
    }

PlatformRole ::= INTEGER {
        pan-bf-master(1),
        pan-bf-slave(2),
        bf-master(3),
        bf-slave(4),
        unknown(999)
    }

bladeFrames     OBJECT IDENTIFIER ::= { management 2 }

bladeFramesInPAN OBJECT-TYPE
    SYNTAX      INTEGER
    ACCESS      read-only
    STATUS      mandatory
    DESCRIPTION
            "The number of BladeFrames in the Egenera PAN."

        ::=     { bladeFrames 1 }

bladeFrameTable  OBJECT-TYPE
    SYNTAX      SEQUENCE OF BladeFrameEntry
    ACCESS      not-accessible
    STATUS      mandatory
    DESCRIPTION
            "A list of BladeFrame entries.  The number of entries is given by
            the value of bladeFramesInPAN.  This is a sparse table."

        ::=     { bladeFrames 2 }


bladeFrameEntry OBJECT-TYPE
    SYNTAX      BladeFrameEntry
    ACCESS      not-accessible
    STATUS      mandatory
    DESCRIPTION
            "A BladeFrame entry contains general information about each
            BladeFrame in the Egenera PAN."

    INDEX       { bladeFrameIndex }
        ::=     { bladeFrameTable 1 }


BladeFrameEntry ::=
    SEQUENCE {
        bladeFrameIndex
            INTEGER (1..2147483647),
        bladeFrameName
            DisplayString,
        bladeFrameHealthStatus
            HealthStatusType,
        bladeFrameUpTime
            TimeTicks,
        bladeFrameNumControlBlades
            INTEGER,
        bladeFrameMaxControlBlades
            INTEGER,
        bladeFrameNumSwitchBlades
            INTEGER,
        bladeFrameMaxSwitchBlades
            INTEGER,
        bladeFrameNumProcessingBlades
            INTEGER,
        bladeFrameMaxProcessingBlades
            INTEGER,
        bladeFrameType
            DisplayString,
        bladeFramePIMVoltageTrigger
            INTEGER,
        bladeFrameRole
            PlatformRole
    }


bladeFrameIndex OBJECT-TYPE
    SYNTAX      INTEGER (1..2147483647)
    ACCESS      read-only
    STATUS      mandatory
    DESCRIPTION
            "An integer value uniquely identifying the BladeFrame."

        ::=     { bladeFrameEntry 1 }


bladeFrameName OBJECT-TYPE
    SYNTAX      DisplayString
    ACCESS      read-only
    STATUS      mandatory
    DESCRIPTION
            "A textual string identifying the BladeFrame."

        ::=     { bladeFrameEntry 2 }


bladeFrameHealthStatus OBJECT-TYPE
    SYNTAX      HealthStatusType
    ACCESS      read-only
    STATUS      mandatory
    DESCRIPTION
            "An indication of the health of the BladeFrame."

        ::=     { bladeFrameEntry 3 }


bladeFrameUpTime OBJECT-TYPE
    SYNTAX      TimeTicks
    ACCESS      read-only
    STATUS      mandatory
    DESCRIPTION
            "The amount of time that the BladeFrame has been up."

        ::=     { bladeFrameEntry 4 }


bladeFrameNumControlBlades OBJECT-TYPE
    SYNTAX      INTEGER
    ACCESS      read-only
    STATUS      mandatory
    DESCRIPTION
            "The number of cBlades present in the BladeFrame."

        ::=     { bladeFrameEntry 5 }


bladeFrameMaxControlBlades OBJECT-TYPE
    SYNTAX      INTEGER
    ACCESS      read-only
    STATUS      mandatory
    DESCRIPTION
            "The maximum number of cBlades that may be present in the
            BladeFrame."

        ::=     { bladeFrameEntry 6 }


bladeFrameNumSwitchBlades OBJECT-TYPE
    SYNTAX      INTEGER
    ACCESS      read-only
    STATUS      mandatory
    DESCRIPTION
            "The number of sBlades contained in the BladeFrame."

        ::=     { bladeFrameEntry 7 }


bladeFrameMaxSwitchBlades OBJECT-TYPE
    SYNTAX      INTEGER
    ACCESS      read-only
    STATUS      mandatory
    DESCRIPTION
            "The maximum number of sBlades that may be contained in the
            BladeFrame."

        ::=     { bladeFrameEntry 8 }


bladeFrameNumProcessingBlades OBJECT-TYPE
    SYNTAX      INTEGER
    ACCESS      read-only
    STATUS      mandatory
    DESCRIPTION
            "The number of pBlades contained in the BladeFrame."

        ::=     { bladeFrameEntry 9 }


bladeFrameMaxProcessingBlades OBJECT-TYPE
    SYNTAX      INTEGER
    ACCESS      read-only
    STATUS      mandatory
    DESCRIPTION
            "The maximum number of pBlades that may be contained in
            the BladeFrame."

        ::=     { bladeFrameEntry 10 }


bladeFrameType OBJECT-TYPE
    SYNTAX      DisplayString
    ACCESS      read-only
    STATUS      mandatory
    DESCRIPTION
            "The type of BladeFrame managed by this agent."

        ::=     { bladeFrameEntry 11 }



bladeFramePIMVoltageTrigger OBJECT-TYPE
    SYNTAX      INTEGER
    ACCESS  read-only
    STATUS      mandatory
    DESCRIPTION
            "If the BladeFrame is equiped with PIMs, this column
            will represent the PIM voltage threshold for PIM
            power failover"

        ::=     { bladeFrameEntry 12 }


bladeFrameRole OBJECT-TYPE
    SYNTAX      PlatformRole
    ACCESS      read-only
    STATUS      mandatory
    DESCRIPTION
            "The role of this BladeFrame in the PAN; either pan-bf-master(1)
            or bf-master(3)"

        ::=     { bladeFrameEntry 13 }

--
-- blades group (cBlades, sBlades, & pBlades)
--

blades      OBJECT IDENTIFIER ::= { bladeFrames 3 }


-- cBlades group

cBlades   OBJECT IDENTIFIER ::= { blades 1 }

-- cBlade table
-- The cBlade table contains information about cBlades in
-- BladeFrames.

cBladeTable  OBJECT-TYPE
    SYNTAX      SEQUENCE OF CBladeEntry
    ACCESS      not-accessible
    STATUS      mandatory
    DESCRIPTION
            "A list of cBlade entries conaining information for Control
            Blades in the Egenera PAN."

        ::=     { cBlades 1 }


cBladeEntry OBJECT-TYPE
    SYNTAX      CBladeEntry
    ACCESS      not-accessible
    STATUS      mandatory
    DESCRIPTION
            "A cBlade entry contains information for cBlades in
            the Egenera PAN."

    INDEX       { bladeFrameIndex, cBladeIndex }
        ::=     { cBladeTable 1 }


CBladeEntry ::=
    SEQUENCE {
        cBladeIndex
            INTEGER (1..2147483647),
        cBladeFrameIndex
            INTEGER (1..2147483647),
        cBladeName
            DisplayString,
        cBladeSerialNumber
            DisplayString,
        cBladePartNumber
            DisplayString,
        cBladePowerStatus
            PowerStatusType,
        cBladePowerSupply
            DisplayString,
        cBladeMasterStatus
            TruthValue,
        cBladeActiveStatus
            TruthValue,
        cBladeEnabledStatus
            TruthValue,
        cBladeSelectedStatus
            TruthValue,
        cBladeRecognizedStatus
            TruthValue,
        cBladeHealthStatus
            HealthStatusType,
        cBladeUpTime
            TimeTicks,
        cBladeSwitchPowerStatus
            PowerStatusType,
        cBladeRole
            PlatformRole
    }

cBladeIndex OBJECT-TYPE
    SYNTAX      INTEGER (1..2147483647)
    ACCESS      read-only
    STATUS      mandatory
    DESCRIPTION
            "An integer value uniquely identifying the cBlade within
            the BladeFrame. This corresponds to the physical location of the
            cBlade within the BladeFrame."

        ::=     { cBladeEntry 1 }


cBladeFrameIndex OBJECT-TYPE
    SYNTAX      INTEGER (1..2147483647)
    ACCESS      read-only
    STATUS      mandatory
    DESCRIPTION
            "An integer value identifying the bladeFrameIndex value of the
            Blade Frame that hosts this cBlade."

        ::=     { cBladeEntry 2 }


cBladeName OBJECT-TYPE
    SYNTAX      DisplayString
    ACCESS      read-only
    STATUS      mandatory
    DESCRIPTION
            "A textual string identifying cBlade."

        ::=     { cBladeEntry 3 }


cBladeSerialNumber OBJECT-TYPE
    SYNTAX      DisplayString
    ACCESS      read-only
    STATUS      mandatory
    DESCRIPTION
            "Describes the serial number of this cBlade."

        ::=     { cBladeEntry 4 }


cBladePartNumber OBJECT-TYPE
    SYNTAX      DisplayString
    ACCESS      read-only
    STATUS      mandatory
    DESCRIPTION
            "Describes the part number of this cBlade."

        ::=     { cBladeEntry 5 }


cBladePowerStatus OBJECT-TYPE
    SYNTAX      PowerStatusType
    ACCESS      read-only
    STATUS      mandatory
    DESCRIPTION
            "The power status of the cBlade."

        ::=     { cBladeEntry 6 }


cBladePowerSupply OBJECT-TYPE
    SYNTAX      DisplayString
    ACCESS      read-only
    STATUS      mandatory
    DESCRIPTION
            "The name of the power supply used by this cBlade."

        ::=     { cBladeEntry 7 }


cBladeMasterStatus OBJECT-TYPE
    SYNTAX      TruthValue
    ACCESS      read-only
    STATUS      mandatory
    DESCRIPTION
            "True if this cBlade is a Frame master, false if this cBlade is a Frame slave"

        ::=     { cBladeEntry 8 }


cBladeActiveStatus OBJECT-TYPE
    SYNTAX      TruthValue
    ACCESS      read-only
    STATUS      mandatory
    DESCRIPTION
            "Indicates whether or not the cBlade is active."

        ::=     { cBladeEntry 9 }


cBladeEnabledStatus OBJECT-TYPE
    SYNTAX      TruthValue
    ACCESS      read-only
    STATUS      mandatory
    DESCRIPTION
            "Indicates whether the cBlade is enabled or disabled."

        ::=     { cBladeEntry 10 }


cBladeSelectedStatus OBJECT-TYPE
    SYNTAX      TruthValue
    ACCESS      read-only
    STATUS      mandatory
    DESCRIPTION
            "Indicates whether the cBlade is selected."

        ::=     { cBladeEntry 11 }


cBladeRecognizedStatus OBJECT-TYPE
    SYNTAX      TruthValue
    ACCESS      read-only
    STATUS      mandatory
    DESCRIPTION
            "Indicates whether the blade has been recognized by the PAN Manager."

        ::=     { cBladeEntry 12 }


cBladeHealthStatus OBJECT-TYPE
    SYNTAX      HealthStatusType
    ACCESS      read-only
    STATUS      mandatory
    DESCRIPTION
            "An indication of the health of the BladeFrame."

        ::=     { cBladeEntry 13 }


cBladeUpTime OBJECT-TYPE
    SYNTAX      TimeTicks
    ACCESS      read-only
    STATUS      mandatory
    DESCRIPTION
            "The amount of time that the BladeFrame has been up."

        ::=     { cBladeEntry 14 }


cBladeSwitchPowerStatus OBJECT-TYPE
    SYNTAX      PowerStatusType
    ACCESS      read-only
    STATUS      mandatory
    DESCRIPTION
            "Indicates the power status of the daughter switch card for cBlade ES blades
            in the BladeFrame ES.  This object does not appear on non BladeFrame ES
            systems."

        ::=     { cBladeEntry 15 }


cBladeRole OBJECT-TYPE
    SYNTAX      PlatformRole
    ACCESS      read-only
    STATUS      mandatory
    DESCRIPTION
            "Indicates the role of the cBlade in the PAN."

        ::=     { cBladeEntry 16 }

-- cBlade SystemMonitor


-- contains runtime statistics for each cBlade.  This table is present when
-- the Egenera management agent is running on the cBlade, and statistic
-- collection is enabled.

cBladeStatsTable  OBJECT-TYPE
    SYNTAX      SEQUENCE OF CBladeStatsEntry
    ACCESS      not-accessible
    STATUS      mandatory
    DESCRIPTION
            "A list of cBlade Monitor entries containing runtime statistics
            for cBlades."

        ::=     { cBlades 2 }


cBladeStatsEntry OBJECT-TYPE
    SYNTAX      CBladeStatsEntry
    ACCESS      not-accessible
    STATUS      mandatory
    DESCRIPTION
            "A cBlade Monitor entry contains runtime statistics for
            cBlades."

    INDEX       { bladeFrameIndex, cBladeIndex }
        ::=     { cBladeStatsTable 1 }


CBladeStatsEntry ::=
    SEQUENCE {
        cBladeStatsUpTime
            TimeTicks,
        cBladeStatsLoadAvg1
            Gauge,
        cBladeStatsLoadAvg5
            Gauge,
        cBladeStatsLoadAvg15
            Gauge,
        cBladeStatsCpuUser
            Counter,
        cBladeStatsCpuSystem
            Counter,
        cBladeStatsCpuIdle
            Counter,
        cBladeStatsLoadScale
            Gauge,
        cBladeStatsNumProcs
            Gauge,
        cBladeStatsLastPid
            INTEGER,
        cBladeStatsContextSwitch
            Counter,
        cBladeStatsInterrupt
            Counter,
        cBladeStatsMemTotal
            Gauge,
        cBladeStatsMemFree
            Gauge,
        cBladeStatsSwapTotal
            Gauge,
        cBladeStatsSwapFree
            Gauge,
        cBladeStatsPageIn
            Counter,
        cBladeStatsPageOut
            Counter,
        cBladeStatsSwapIn
            Counter,
        cBladeStatsSwapOut
            Counter,
        cBladeStatsDiskReads
            Counter,
        cBladeStatsDiskWrites
            Counter,
        cBladeStatsDiskBlkReads
            Counter,
        cBladeStatsDiskBlkWrites
            Counter,
        cBladeStatsCpuUserNice
            Counter
    }

cBladeStatsUpTime OBJECT-TYPE
    SYNTAX      TimeTicks
    ACCESS      read-only
    STATUS      mandatory
    DESCRIPTION
            "The uptime in 1/100ths of a second for this cBlade."

        ::=     { cBladeStatsEntry 1 }


cBladeStatsLoadAvg1 OBJECT-TYPE
    SYNTAX      Gauge
    ACCESS      read-only
    STATUS      mandatory
    DESCRIPTION
            "100 * the average number of jobs in the run queue over the
            previous minute."

        ::=     { cBladeStatsEntry 2 }


cBladeStatsLoadAvg5 OBJECT-TYPE
    SYNTAX      Gauge
    ACCESS      read-only
    STATUS      mandatory
    DESCRIPTION
            "100 * the average number of jobs in the run queue over the
            previous five minutes."

        ::=     { cBladeStatsEntry 3 }


cBladeStatsLoadAvg15 OBJECT-TYPE
    SYNTAX      Gauge
    ACCESS      read-only
    STATUS      mandatory
    DESCRIPTION
            "100 * the average number of jobs in the run queue over the
            previous fifteen minutes."

        ::=     { cBladeStatsEntry 4 }


cBladeStatsCpuUser OBJECT-TYPE
    SYNTAX      Counter
    ACCESS      read-only
    STATUS      mandatory
    DESCRIPTION
            "The number of (1/100)ths of a second that the cBlade spent in
            user mode since boot."

        ::=     { cBladeStatsEntry 5 }


cBladeStatsCpuSystem OBJECT-TYPE
    SYNTAX      Counter
    ACCESS      read-only
    STATUS      mandatory
    DESCRIPTION
            "The number of (1/100)ths of a second that the cBlade spent in
            system mode since boot."

        ::=     { cBladeStatsEntry 6 }


cBladeStatsCpuIdle OBJECT-TYPE
    SYNTAX      Counter
    ACCESS      read-only
    STATUS      mandatory
    DESCRIPTION
            "The number of (1/100)ths of a second that the cBlade spent in
            idle mode since boot."

        ::=     { cBladeStatsEntry 7 }


cBladeStatsLoadScale OBJECT-TYPE
    SYNTAX      Gauge
    ACCESS      read-only
    STATUS      mandatory
    DESCRIPTION
            "The load scale."

        ::=     { cBladeStatsEntry 8 }


cBladeStatsNumProcs OBJECT-TYPE
    SYNTAX      Gauge
    ACCESS      read-only
    STATUS      mandatory
    DESCRIPTION
            "The number of processes running on the cBlade."

        ::=     { cBladeStatsEntry 9 }


cBladeStatsLastPid OBJECT-TYPE
    SYNTAX      INTEGER
    ACCESS      read-only
    STATUS      mandatory
    DESCRIPTION
            "The highest allocated process ID on the cBlade."

        ::=     { cBladeStatsEntry 10 }


cBladeStatsContextSwitch OBJECT-TYPE
    SYNTAX      Counter
    ACCESS      read-only
    STATUS      mandatory
    DESCRIPTION
            "The number of context switches undergone by this cBlade since
            boot."

        ::=     { cBladeStatsEntry 11 }


cBladeStatsInterrupt OBJECT-TYPE
    SYNTAX      Counter
    ACCESS      read-only
    STATUS      mandatory
    DESCRIPTION
            "The number of interrupts encountered by this cBlade since
            boot."

        ::=     { cBladeStatsEntry 12 }


cBladeStatsMemTotal OBJECT-TYPE
    SYNTAX      Gauge
    ACCESS      read-only
    STATUS      mandatory
    DESCRIPTION
            "The total amount of physical RAM in kB for this cBlade."

        ::=     { cBladeStatsEntry 13 }


cBladeStatsMemFree OBJECT-TYPE
    SYNTAX      Gauge
    ACCESS      read-only
    STATUS      mandatory
    DESCRIPTION
            "The amount of free physcial RAM in kB for this cBlade."

        ::=     { cBladeStatsEntry 14 }


cBladeStatsSwapTotal OBJECT-TYPE
    SYNTAX      Gauge
    ACCESS      read-only
    STATUS      mandatory
    DESCRIPTION
            "The total amount of configured swap memory in kB for this
            cBlade."

        ::=     { cBladeStatsEntry 15 }


cBladeStatsSwapFree OBJECT-TYPE
    SYNTAX      Gauge
    ACCESS      read-only
    STATUS      mandatory
    DESCRIPTION
            "The amount of free swap memory in kB for this cBlade."

        ::=     { cBladeStatsEntry 16 }


cBladeStatsPageIn OBJECT-TYPE
    SYNTAX      Counter
    ACCESS      read-only
    STATUS      mandatory
    DESCRIPTION
            "The number of pages paged in since boot."

        ::=     { cBladeStatsEntry 17 }


cBladeStatsPageOut OBJECT-TYPE
    SYNTAX      Counter
    ACCESS      read-only
    STATUS      mandatory
    DESCRIPTION
            "The number of pages paged out since boot."

        ::=     { cBladeStatsEntry 18 }


cBladeStatsSwapIn OBJECT-TYPE
    SYNTAX      Counter
    ACCESS      read-only
    STATUS      mandatory
    DESCRIPTION
            "The number of swap pages paged in since boot."

        ::=     { cBladeStatsEntry 19 }


cBladeStatsSwapOut OBJECT-TYPE
    SYNTAX      Counter
    ACCESS      read-only
    STATUS      mandatory
    DESCRIPTION
            "The number of swap pages paged out since boot."

        ::=     { cBladeStatsEntry 20 }


cBladeStatsDiskReads OBJECT-TYPE
    SYNTAX      Counter
    ACCESS      read-only
    STATUS      mandatory
    DESCRIPTION
            "The number of disk reads since boot."

        ::=     { cBladeStatsEntry 21 }


cBladeStatsDiskWrites OBJECT-TYPE
    SYNTAX      Counter
    ACCESS      read-only
    STATUS      mandatory
    DESCRIPTION
            "The number of disk writes since boot."

        ::=     { cBladeStatsEntry 22 }


cBladeStatsDiskBlkReads OBJECT-TYPE
    SYNTAX      Counter
    ACCESS      read-only
    STATUS      mandatory
    DESCRIPTION
            "The number of 1 kB blocks read from disk since boot."

        ::=     { cBladeStatsEntry 23 }


cBladeStatsDiskBlkWrites OBJECT-TYPE
    SYNTAX      Counter
    ACCESS      read-only
    STATUS      mandatory
    DESCRIPTION
            "The number of of 1 kB blocks written to disk since boot."

        ::=     { cBladeStatsEntry 24 }

cBladeStatsCpuUserNice OBJECT-TYPE
    SYNTAX      Counter
    ACCESS      read-only
    STATUS      mandatory
    DESCRIPTION
            "The number of (1/100)ths of a second that the pServer spent in
            user nice mode since boot."

        ::=     { cBladeStatsEntry 25 }

-- cBlade CPU Table
-- Contains information about each CPU on each cBlade

cBladeCpuTable   OBJECT-TYPE
    SYNTAX      SEQUENCE OF CBladeCpuEntry
    ACCESS      not-accessible
    STATUS      mandatory
    DESCRIPTION
            "A list of CPU statisitcs for each CPU on each cBlade."

        ::=     { cBlades 3 }


cBladeCpuEntry OBJECT-TYPE
    SYNTAX      CBladeCpuEntry
    ACCESS      not-accessible
    STATUS      mandatory
    DESCRIPTION
            "Statistics for each CPU on the cBlade."

    INDEX       { bladeFrameIndex, cBladeIndex, cBladeCpuIndex }
        ::=     { cBladeCpuTable 1 }


CBladeCpuEntry ::=
    SEQUENCE {
        cBladeCpuIndex
            INTEGER (1..2147483647),
        cBladeCpuCBladeIndex
            INTEGER (1..2147483647),
        cBladeCpuLPanIndex
            INTEGER (1..2147483647),
        cBladeCpuModelName
            DisplayString,
        cBladeCpuModel
            INTEGER,
        cBladeCpuFamily
            INTEGER,
        cBladeCpuVendorId
            DisplayString,
        cBladeCpuMhz
            INTEGER,
        cBladeCpuCacheSize
            INTEGER,
        cBladeCpuName
            DisplayString,
        cBladeCpuUser
            Counter,
        cBladeCpuUserNice
            Counter,
        cBladeCpuSystem
            Counter,
        cBladeCpuIdle
            Counter
    }


cBladeCpuIndex OBJECT-TYPE
    SYNTAX      INTEGER (1..2147483647)
    ACCESS      read-only
    STATUS      mandatory
    DESCRIPTION
            "An integer uniquely identifying this CPU within the cBlade."

        ::=     { cBladeCpuEntry 1 }


cBladeCpuCBladeIndex OBJECT-TYPE
    SYNTAX      INTEGER (1..2147483647)
    ACCESS      read-only
    STATUS      mandatory
    DESCRIPTION
            "An integer value identifying the cBladeIndex value of the
            cBlade that hosts this CPU."

        ::=     { cBladeCpuEntry 2 }


cBladeCpuLPanIndex OBJECT-TYPE
    SYNTAX      INTEGER (1..2147483647)
    ACCESS      read-only
    STATUS      mandatory
    DESCRIPTION
            "This object is deprecated."

        ::=     { cBladeCpuEntry 3 }


cBladeCpuModelName OBJECT-TYPE
    SYNTAX      DisplayString
    ACCESS      read-only
    STATUS      mandatory
    DESCRIPTION
            "A textual string representing the CPU model."

        ::=     { cBladeCpuEntry 4 }


cBladeCpuModel OBJECT-TYPE
    SYNTAX      INTEGER
    ACCESS      read-only
    STATUS      mandatory
    DESCRIPTION
            "An integer value representing the CPU model."

        ::=     { cBladeCpuEntry 5 }


cBladeCpuFamily OBJECT-TYPE
    SYNTAX      INTEGER
    ACCESS      read-only
    STATUS      mandatory
    DESCRIPTION
            "An integer value representing the CPU family."

        ::=     { cBladeCpuEntry 6 }


cBladeCpuVendorId OBJECT-TYPE
    SYNTAX      DisplayString
    ACCESS      read-only
    STATUS      mandatory
    DESCRIPTION
            "A textual string representing the CPU vendor."

        ::=     { cBladeCpuEntry 7 }


cBladeCpuMhz OBJECT-TYPE
    SYNTAX      INTEGER
    ACCESS      read-only
    STATUS      mandatory
    DESCRIPTION
            "The speed of the CPU in Mhz."

        ::=     { cBladeCpuEntry 8 }


cBladeCpuCacheSize OBJECT-TYPE
    SYNTAX      INTEGER
    ACCESS      read-only
    STATUS      mandatory
    DESCRIPTION
            "The cache size of the CPU in MB."

        ::=     { cBladeCpuEntry 9 }


cBladeCpuName OBJECT-TYPE
    SYNTAX      DisplayString
    ACCESS      read-only
    STATUS      mandatory
    DESCRIPTION
            "A textual string uniquely identifying this CPU."

        ::=     { cBladeCpuEntry 10 }


cBladeCpuUser OBJECT-TYPE
    SYNTAX      Counter
    ACCESS      read-only
    STATUS      mandatory
    DESCRIPTION
            "The number of (1/100)ths of a second that this CPU spent in
            user mode since boot."

        ::=     { cBladeCpuEntry 11 }


cBladeCpuUserNice OBJECT-TYPE
    SYNTAX      Counter
    ACCESS      read-only
    STATUS      mandatory
    DESCRIPTION
            "The number of (1/100)ths of a second that this CPU spent in
            user nice mode since boot."

        ::=     { cBladeCpuEntry 12 }


cBladeCpuSystem OBJECT-TYPE
    SYNTAX      Counter
    ACCESS      read-only
    STATUS      mandatory
    DESCRIPTION
            "The number of (1/100)ths of a second that this CPU spent in
            system mode since boot."

        ::=     { cBladeCpuEntry 13 }


cBladeCpuIdle OBJECT-TYPE
    SYNTAX      Counter
    ACCESS      read-only
    STATUS      mandatory
    DESCRIPTION
            "The number of (1/100)ths of a second that this CPU spent in
            idle mode since boot."

        ::=     { cBladeCpuEntry 14 }




-- cBlade Disk Table
-- Contains information about each disk on the cBlade.

cBladeDiskTable OBJECT-TYPE

    SYNTAX      SEQUENCE OF CBladeDiskEntry
    ACCESS      not-accessible
    STATUS      mandatory
    DESCRIPTION
            "A list of disk statisitcs for each disk on the
            cBlade."

        ::=     { cBlades 4 }


cBladeDiskEntry OBJECT-TYPE
    SYNTAX      CBladeDiskEntry
    ACCESS      not-accessible
    STATUS      mandatory
    DESCRIPTION
            "Disk statisitcs for each disk on the cBlade."

    INDEX       { bladeFrameIndex, cBladeIndex,
                  IMPLIED cBladeDiskNameOctets }
        ::=     { cBladeDiskTable 1 }

CBladeDiskEntry ::=
    SEQUENCE {
        cBladeDiskNameOctets
            OCTET STRING (SIZE(0..63)),
        cBladeDiskCBladeIndex
            INTEGER,
        cBladeDiskBladeFrameIndex
            INTEGER,
        cBladeDiskName
            DisplayString,
        cBladeDiskBlocks
            Gauge,
        cBladeDiskMajor
            INTEGER,
        cBladeDiskMinor
            INTEGER
    }

cBladeDiskNameOctets OBJECT-TYPE
    SYNTAX      OCTET STRING (SIZE(0..32))
    ACCESS      read-only
    STATUS      mandatory
    DESCRIPTION
            "An octet string representing the device special file name
            representing this disk."

        ::=     { cBladeDiskEntry 1 }


cBladeDiskCBladeIndex OBJECT-TYPE
    SYNTAX      INTEGER
    ACCESS      read-only
    STATUS      mandatory
    DESCRIPTION
            "An integer value identifying the cBladeIndex value of the
            cBlade that utilizes this disk."

        ::=     { cBladeDiskEntry 2 }


cBladeDiskBladeFrameIndex OBJECT-TYPE
    SYNTAX      INTEGER
    ACCESS      read-only
    STATUS      mandatory
    DESCRIPTION
            "An integer value indentifying the bladeFrameIndex value of the
            BladeFrame that hosts this disk."

        ::=     { cBladeDiskEntry 3 }

cBladeDiskName OBJECT-TYPE
    SYNTAX      DisplayString
    ACCESS      read-only
    STATUS      mandatory
    DESCRIPTION
            "The human readable device special file name representing this
            disk."

        ::=     { cBladeDiskEntry 4 }


cBladeDiskBlocks OBJECT-TYPE
    SYNTAX      Gauge
    ACCESS      read-only
    STATUS      mandatory
    DESCRIPTION
            "The size of this disk in 1kB blocks"

        ::=     { cBladeDiskEntry 5 }


cBladeDiskMajor OBJECT-TYPE
    SYNTAX      INTEGER
    ACCESS      read-only
    STATUS      mandatory
    DESCRIPTION
            "The major ID of this disk."

        ::=     { cBladeDiskEntry 6 }


cBladeDiskMinor OBJECT-TYPE
    SYNTAX      INTEGER
    ACCESS      read-only
    STATUS      mandatory
    DESCRIPTION
            "The minor ID of this disk."

        ::=     { cBladeDiskEntry 7 }


-- cBlade Partition Table
-- Contains information about each disk partition on the cBlade.



cBladePartitionTable   OBJECT-TYPE
    SYNTAX      SEQUENCE OF CBladePartitionEntry
    ACCESS      not-accessible
    STATUS      mandatory
    DESCRIPTION
            "A list of partition statisitcs for each partition on the
            cBlade."

        ::=     { cBlades 5 }


cBladePartitionEntry OBJECT-TYPE
    SYNTAX      CBladePartitionEntry
    ACCESS      not-accessible
    STATUS      mandatory
    DESCRIPTION
            "Partition statisitcs for each partition on the cBlade."
    INDEX       { bladeFrameIndex, cBladeIndex,
                  IMPLIED cBladePartitionNameOctets }
        ::=     { cBladePartitionTable 1 }


CBladePartitionEntry ::=
    SEQUENCE {
        cBladePartitionNameOctets
            OCTET STRING (SIZE(0..63)),
        cBladePartitionCBladeIndex
            INTEGER,
        cBladePartitionLPanIndex
            INTEGER,
        cBladePartitionName
            DisplayString (SIZE(0..63)),
        cBladePartitionBlocks
            Gauge,
        cBladePartitionMajor
            INTEGER,
        cBladePartitionMinor
            INTEGER,
        cBladePartitionFSBlocks
            Gauge,
        cBladePartitionFSUsedBlocks
            Gauge,
        cBladePartitionFSAvailableBlocks
            Gauge,
        cBladePartitionFSUtil
            Gauge
    }


cBladePartitionNameOctets OBJECT-TYPE
    SYNTAX      OCTET STRING (SIZE(0..63))
    ACCESS      read-only
    STATUS      mandatory
    DESCRIPTION
            "An octet string representing the device special file name
            representing this disk."

        ::=     { cBladePartitionEntry 1 }


cBladePartitionCBladeIndex OBJECT-TYPE
    SYNTAX      INTEGER
    ACCESS      read-only
    STATUS      mandatory
    DESCRIPTION
            "An integer value identifying the cBladeIndex value of the
            cBlade that utilizes this disk partition."

        ::=     { cBladePartitionEntry 2 }


cBladePartitionLPanIndex OBJECT-TYPE
    SYNTAX      INTEGER
    ACCESS      read-only
    STATUS      mandatory
    DESCRIPTION
            "This object is deprecated."

        ::=     { cBladePartitionEntry 3 }


cBladePartitionName OBJECT-TYPE
    SYNTAX      DisplayString (SIZE(0..32))
    ACCESS      read-only
    STATUS      mandatory
    DESCRIPTION
            "A textual string identifying the device file that represents
            this partition."

        ::=     { cBladePartitionEntry 4 }


cBladePartitionBlocks OBJECT-TYPE
    SYNTAX      Gauge
    ACCESS      read-only
    STATUS      mandatory
    DESCRIPTION
            "The size of this partition in 1kB blocks"

        ::=     { cBladePartitionEntry 5 }


cBladePartitionMajor OBJECT-TYPE
    SYNTAX      INTEGER
    ACCESS      read-only
    STATUS      mandatory
    DESCRIPTION
            "The major ID of this partition."

        ::=     { cBladePartitionEntry 6 }


cBladePartitionMinor OBJECT-TYPE
    SYNTAX      INTEGER
    ACCESS      read-only
    STATUS      mandatory
    DESCRIPTION
            "The minor ID of this partition."

        ::=     { cBladePartitionEntry 7 }


cBladePartitionFSBlocks OBJECT-TYPE
    SYNTAX      Gauge
    ACCESS      read-only
    STATUS      mandatory
    DESCRIPTION
            "If the partition contains a mounted filesystem, filesystem size
            in 1k blocks, otherwise 0."

        ::=     { cBladePartitionEntry 8 }


cBladePartitionFSUsedBlocks OBJECT-TYPE
    SYNTAX      Gauge
    ACCESS      read-only
    STATUS      mandatory
    DESCRIPTION
            "If the partition contains a mounted filesystem, the number of
            used 1k blocks, otherwise 0."

        ::=     { cBladePartitionEntry 9 }


cBladePartitionFSAvailableBlocks OBJECT-TYPE
    SYNTAX      Gauge
    ACCESS      read-only
    STATUS      mandatory
    DESCRIPTION
            "If the partition contains a mounted filesystem, the number of
            available 1k blocks, otherwise 0."

        ::=     { cBladePartitionEntry 10 }


cBladePartitionFSUtil OBJECT-TYPE
    SYNTAX      Gauge
    ACCESS      read-only
    STATUS      mandatory
    DESCRIPTION
            "If the partition contains a mounted filesystem, the number of
            available 1k blocks, otherwise 0."

        ::=     { cBladePartitionEntry 11 }

-- cBlade Virtual Ethernet table
-- Contains information about each network interface on the cBlade.


InterfaceOperStatus ::= INTEGER {
        up(1),        -- ready to pass packets
        down(2),
        testing(3),   -- in some test mode
        unknown(4),   -- status can not be determined
                      -- for some reason.
        dormant(5),
        notPresent(6),    -- some component is missing
        lowerLayerDown(7) -- down due to state of
                          -- lower-layer interface(s)
    }

EthRethStatus ::= INTEGER {
        active(1),      -- actively communcating
        standby(2),     -- waiting to take over in case of failure
        failed(3),      -- link or ping failure detected
        unconfigured(4),-- not part of a Reth
        unknown(999)
    }

cBladeEthTable   OBJECT-TYPE
    SYNTAX      SEQUENCE OF CBladeEthEntry
    ACCESS      not-accessible
    STATUS      mandatory
    DESCRIPTION
            "physical Network Interface Cards (NICs) on a BladeFrame's
             cBlades (cBlades), used for creating rEths.  This table
             provides information similar to that found with the 'eth'
             command.

             Note that this excludes eth0, the management NIC.

             cBlades contain Ethernet NICs for IP communication.  This can
             include:
                o   Gigabit Ethernet connections, either copper or fibre
                    (for I/O)

                o   10/100/1000 Ethernet connections (for management)

             For more information about cBlade configuration options, refer
             to the Egenera web site (www.egenera.com) or contact Egenera
             Enterprise Services (EES).
            "

        ::=     { cBlades 6 }


cBladeEthEntry OBJECT-TYPE
    SYNTAX      CBladeEthEntry
    ACCESS      not-accessible
    STATUS      mandatory
    DESCRIPTION
            "Information specific to each cBlade Eth in the PAN."

    INDEX       { bladeFrameIndex, cBladeIndex, cBladeEthIndex }
        ::=     { cBladeEthTable 1 }

CBladeEthEntry ::=
    SEQUENCE {
        cBladeEthIndex
            INTEGER (1..2147483647),
        cBladeEthCBladeIndex
            INTEGER (1..2147483647),
        cBladeEthBladeFrameIndex
            INTEGER (1..2147483647),
        cBladeEthName
            DisplayString,
        cBladeEthFullName
            DisplayString,
        cBladeEthHwMACAddressOctets
            PhysAddress,
        cBladeEthHwMACAddressString
            DisplayString,
        cBladeEthSwMACAddressOctets
            PhysAddress,
        cBladeEthSwMACAddressString
            DisplayString,
        cBladeEthNICType
            DisplayString,
        cBladeEthFiltered
            TruthValue,
        cBladeEthUplinkName
            DisplayString,
        cBladeEthUplinkPort
            INTEGER,
        cBladeEthLinkState
            InterfaceOperStatus,
        cBladeEthRethStatus
            EthRethStatus
    }

cBladeEthIndex OBJECT-TYPE
    SYNTAX      INTEGER (1..2147483647)
    ACCESS      read-only
    STATUS      mandatory
    DESCRIPTION
            "An integer value uniquely identifying the cBladeEth within the
            cBlade."

        ::=     { cBladeEthEntry 1 }


cBladeEthCBladeIndex OBJECT-TYPE
    SYNTAX      INTEGER (1..2147483647)
    ACCESS      read-only
    STATUS      mandatory
    DESCRIPTION
            "An integer value identifying the cBladeIndex value of the
            cBlade that hosts this Eth."

        ::=     { cBladeEthEntry 2 }


cBladeEthBladeFrameIndex OBJECT-TYPE
    SYNTAX      INTEGER (1..2147483647)
    ACCESS      read-only
    STATUS      mandatory
    DESCRIPTION
            "An integer value identifying the bladeFrameIndex value of the
            BladeFrame that hosts this Eth."

        ::=     { cBladeEthEntry 3 }


cBladeEthName OBJECT-TYPE
    SYNTAX      DisplayString
    ACCESS      read-only
    STATUS      mandatory
    DESCRIPTION
            "A human readable string uniquely identifying the cBlade Eth."

        ::=     { cBladeEthEntry 4 }


cBladeEthFullName OBJECT-TYPE
    SYNTAX      DisplayString
    ACCESS      read-only
    STATUS      mandatory
    DESCRIPTION
            "A human readable string uniquely identifying the cBlade Eth,
            including the host cBlade and BladeFrame."

        ::=     { cBladeEthEntry 5 }


cBladeEthHwMACAddressOctets OBJECT-TYPE
    SYNTAX      PhysAddress
    ACCESS      read-only
    STATUS      mandatory
    DESCRIPTION
            "An encoding of the cBlade Eth hardware MAC address."

        ::=     { cBladeEthEntry 6 }


cBladeEthHwMACAddressString OBJECT-TYPE
    SYNTAX      DisplayString
    ACCESS      read-only
    STATUS      mandatory
    DESCRIPTION
            "A human readable string representing the cBlade Eth hardware
            MAC address in the form: '6E:4A:1F:00:01:06'."

        ::=     { cBladeEthEntry 7 }


cBladeEthSwMACAddressOctets OBJECT-TYPE
    SYNTAX      PhysAddress
    ACCESS      read-only
    STATUS      mandatory
    DESCRIPTION
            "This object is deprecated.  As of release 5.0, software MA
            addresses are not supported on cBlade eths."

        ::=     { cBladeEthEntry 8 }


cBladeEthSwMACAddressString OBJECT-TYPE
    SYNTAX      DisplayString
    ACCESS      read-only
    STATUS      mandatory
    DESCRIPTION
            "This object is deprecated.  As of release 5.0, software MA
            addresses are not supported on cBlade eths."

        ::=     { cBladeEthEntry 9 }


cBladeEthNICType OBJECT-TYPE
    SYNTAX      DisplayString
    ACCESS      read-only
    STATUS      mandatory
    DESCRIPTION
            "Specifies the cBlade ETH NIC type, such as e100 or e1000."

        ::=     { cBladeEthEntry 10 }


cBladeEthFiltered OBJECT-TYPE
    SYNTAX      TruthValue
    ACCESS      read-only
    STATUS      mandatory
    DESCRIPTION
            "This object is deprecated.  As of release 5.0, filtered mode
            is not supported on cBlade eths."


        ::=     { cBladeEthEntry 11 }


cBladeEthUplinkName OBJECT-TYPE
    SYNTAX      DisplayString
    ACCESS      read-only
    STATUS      mandatory
    DESCRIPTION
            "A human readable string that a PAN or BladeFrame Administrator
            assigns to describe the uplink port."

        ::=     { cBladeEthEntry 12 }


cBladeEthUplinkPort OBJECT-TYPE
    SYNTAX      INTEGER
    ACCESS      read-only
    STATUS      mandatory
    DESCRIPTION
            "An integer value that a PAN or BladeFrame Administrator assigns
            to identify the uplink port."

        ::=     { cBladeEthEntry 13 }


cBladeEthLinkState OBJECT-TYPE
    SYNTAX      InterfaceOperStatus
    ACCESS      read-only
    STATUS      mandatory
    DESCRIPTION
            "The Link State of the Eth."

        ::=     { cBladeEthEntry 14 }


cBladeEthRethStatus OBJECT-TYPE
    SYNTAX      EthRethStatus
    ACCESS      read-only
    STATUS      mandatory
    DESCRIPTION
            "The State of the Eth with respect to REth membership."

        ::=     { cBladeEthEntry 15 }



-- table of VLANs for each cBlade Eth

cBladeEthVLANTable   OBJECT-TYPE
    SYNTAX      SEQUENCE OF CBladeEthVLANEntry
    ACCESS      not-accessible
    STATUS      mandatory
    DESCRIPTION
            "A list of VLAN IDs and descriptions associated with each Eth."

        ::=     { cBlades 7 }


cBladeEthVLANEntry OBJECT-TYPE
    SYNTAX      CBladeEthVLANEntry
    ACCESS      not-accessible
    STATUS      mandatory
    DESCRIPTION
            "Information specific to each VLAN for cBlade cBladeEths."

    INDEX       { bladeFrameIndex, cBladeIndex, cBladeEthIndex, cBladeEthVLANId }
        ::=     { cBladeEthVLANTable 1 }

CBladeEthVLANEntry ::=
    SEQUENCE {
        cBladeEthVLANId
            INTEGER (1..4094),
        cBladeEthVLANEthIndex
            INTEGER,
        cBladeEthVLANcBladeIndex
            INTEGER,
        cBladeEthVLANBladeFrameIndex
            INTEGER,
        cBladeEthVLANEthName
            DisplayString,
        cBladeEthVLANName
            DisplayString
    }


cBladeEthVLANId OBJECT-TYPE
    SYNTAX      INTEGER (1..4094)
    ACCESS      read-only
    STATUS      mandatory
    DESCRIPTION
            "specifies a VLAN ID assigned to the uplink port on the physical
            network component connected to the cBlade NIC"

        ::=     { cBladeEthVLANEntry 1 }


cBladeEthVLANEthIndex OBJECT-TYPE
    SYNTAX      INTEGER
    ACCESS      read-only
    STATUS      mandatory
    DESCRIPTION
            "An integer value identifying the cBladeEthIndex value of the
            cBlade Eth that hosts this Eth VLAN."

        ::=     { cBladeEthVLANEntry 2 }


cBladeEthVLANcBladeIndex OBJECT-TYPE
    SYNTAX      INTEGER
    ACCESS      read-only
    STATUS      mandatory
    DESCRIPTION
            "An integer value identifying the cBladeIndex value of the
            cBlade that hosts this Eth VLAN."

        ::=     { cBladeEthVLANEntry 3 }


cBladeEthVLANBladeFrameIndex OBJECT-TYPE
    SYNTAX      INTEGER
    ACCESS      read-only
    STATUS      mandatory
    DESCRIPTION
            "An integer value identifying the bladeFrameIndex value of the
            BladeFrame that hosts this Eth VLAN."

        ::=     { cBladeEthVLANEntry 4 }


cBladeEthVLANEthName OBJECT-TYPE
    SYNTAX      DisplayString
    ACCESS      read-only
    STATUS      mandatory
    DESCRIPTION
            "The full name of the ethernet interface associated with this VLAN."

        ::=     { cBladeEthVLANEntry 5 }


cBladeEthVLANName OBJECT-TYPE
    SYNTAX      DisplayString
    ACCESS      read-only
    STATUS      mandatory
    DESCRIPTION
            "A human readable string that a PAN or BladeFrame Administrator
            assigns to the VLAN."

        ::=     { cBladeEthVLANEntry 6 }


-- table of cBlade Eth Stats (not yet implemented)

cBladeVEthStatsTable   OBJECT-TYPE
    SYNTAX      SEQUENCE OF CBladeVEthStatsEntry
    ACCESS      not-accessible
    STATUS      mandatory
    DESCRIPTION
            "A list of interface statisitcs for each virtual interface in the
            cBlade.

            Since REths remove their composit Eths from the Linux network
            stack, physical Eth statistics are not avaialble.  This table
            exports statistics for cBlade Eths, including the internal and
            external management network VEths."

        ::=     { cBlades 8 }


cBladeVEthStatsEntry OBJECT-TYPE
    SYNTAX      CBladeVEthStatsEntry
    ACCESS      not-accessible
    STATUS      mandatory
    DESCRIPTION
            "VEthStats statisitcs for each virtual interface in the cBlade."

    INDEX       { bladeFrameIndex, cBladeIndex, cBladeVEthIndex }
        ::=     { cBladeVEthStatsTable 1 }


CBladeVEthStatsEntry ::=
    SEQUENCE {
        cBladeVEthIndex
            INTEGER (1..2147483647),
        cBladeVEthCBladeIndex
            INTEGER (1..2147483647),
        cBladeVEthBladeFrameIndex
            INTEGER (1..2147483647),
        cBladeVEthName
            DisplayString,
        cBladeVEthStatsInBytes
            Counter,
        cBladeVEthStatsInPackets
            Counter,
        cBladeVEthStatsInErrs
            Counter,
        cBladeVEthStatsInDrops
            Counter,
        cBladeVEthStatsInOverrun
            Counter,
        cBladeVEthStatsInMulticast
            Counter,
        cBladeVEthStatsOutBytes
            Counter,
        cBladeVEthStatsOutPackets
            Counter,
        cBladeVEthStatsOutErrs
            Counter,
        cBladeVEthStatsOutDrops
            Counter,
        cBladeVEthStatsOutOverrun
            Counter,
        cBladeVEthStatsOutCollisions
            Counter,
        cBladeVEthStatsOutCarrierDctFail
            Counter,
        cBladeVEthStatsOutCompressed
            Counter,
        cBladeVEthStatsOperStatus
            InterfaceOperStatus
    }


cBladeVEthIndex OBJECT-TYPE
    SYNTAX      INTEGER (1..2147483647)
    ACCESS      read-only
    STATUS      mandatory
    DESCRIPTION
            "An integer value uniquely identifying the VEth within the cBlade."

        ::=     { cBladeVEthStatsEntry 1 }


cBladeVEthCBladeIndex OBJECT-TYPE
    SYNTAX      INTEGER (1..2147483647)
    ACCESS      read-only
    STATUS      mandatory
    DESCRIPTION
           "The cBladeIndex value of the cBlade hosting this VEth."

        ::=     { cBladeVEthStatsEntry 2 }


cBladeVEthBladeFrameIndex OBJECT-TYPE
    SYNTAX      INTEGER (1..2147483647)
    ACCESS      read-only
    STATUS      mandatory
    DESCRIPTION
           "The bladeFrameIndex value of the BladeFrame hosting this VEth."

        ::=     { cBladeVEthStatsEntry 3 }


cBladeVEthName OBJECT-TYPE
    SYNTAX      DisplayString
    ACCESS      read-only
    STATUS      mandatory
    DESCRIPTION
            "A string uniquely identifying this VEth on this cBlade."

        ::=     { cBladeVEthStatsEntry 4 }


cBladeVEthStatsInBytes OBJECT-TYPE
    SYNTAX      Counter
    ACCESS      read-only
    STATUS      mandatory
    DESCRIPTION
            "The number of bytes received on this interface since interface
            reset"

        ::=     { cBladeVEthStatsEntry 5 }


cBladeVEthStatsInPackets OBJECT-TYPE
    SYNTAX      Counter
    ACCESS      read-only
    STATUS      mandatory
    DESCRIPTION
            "The number of packets received on this interface since interface
            reset"

        ::=     { cBladeVEthStatsEntry 6 }


cBladeVEthStatsInErrs OBJECT-TYPE
    SYNTAX      Counter
    ACCESS      read-only
    STATUS      mandatory
    DESCRIPTION
            "The number of errors received on this interface since interface
            reset"

        ::=     { cBladeVEthStatsEntry 7 }


cBladeVEthStatsInDrops OBJECT-TYPE
    SYNTAX      Counter
    ACCESS      read-only
    STATUS      mandatory
    DESCRIPTION
            "The number of dropped incoming packets on this interface since
            interface reset."

        ::=     { cBladeVEthStatsEntry 8 }


cBladeVEthStatsInOverrun OBJECT-TYPE
    SYNTAX      Counter
    ACCESS      read-only
    STATUS      mandatory
    DESCRIPTION
            "The number of overrun incoming packets on this interface since
            interface reset."

        ::=     { cBladeVEthStatsEntry 9 }


cBladeVEthStatsInMulticast OBJECT-TYPE
    SYNTAX      Counter
    ACCESS      read-only
    STATUS      mandatory
    DESCRIPTION
            "The number of multicast packets received on this interface since
            interface reset."

        ::=     { cBladeVEthStatsEntry 10 }


cBladeVEthStatsOutBytes OBJECT-TYPE
    SYNTAX      Counter
    ACCESS      read-only
    STATUS      mandatory
    DESCRIPTION
            "The number of bytes transmitted from this interface since
            interface reset."

        ::=     { cBladeVEthStatsEntry 11 }


cBladeVEthStatsOutPackets OBJECT-TYPE
    SYNTAX      Counter
    ACCESS      read-only
    STATUS      mandatory
    DESCRIPTION
            "The number of packets transmitted from this interface since
            interface reset."

        ::=     { cBladeVEthStatsEntry 12 }


cBladeVEthStatsOutErrs OBJECT-TYPE
    SYNTAX      Counter
    ACCESS      read-only
    STATUS      mandatory
    DESCRIPTION
            "The number of errors encountered while transmitting from this
            interface since interface reset."

        ::=     { cBladeVEthStatsEntry 13 }


cBladeVEthStatsOutDrops OBJECT-TYPE
    SYNTAX      Counter
    ACCESS      read-only
    STATUS      mandatory
    DESCRIPTION
            "The number of dropped packets intended for transmission from this
            interface since interface reset."

        ::=     { cBladeVEthStatsEntry 14 }


cBladeVEthStatsOutOverrun OBJECT-TYPE
    SYNTAX      Counter
    ACCESS      read-only
    STATUS      mandatory
    DESCRIPTION
            "The number of overrun packets intended for transmission from this
            interface since interface reset."

        ::=     { cBladeVEthStatsEntry 15 }


cBladeVEthStatsOutCollisions OBJECT-TYPE
    SYNTAX      Counter
    ACCESS      read-only
    STATUS      mandatory
    DESCRIPTION
            "The number of collisions detetced while transmitting from this
            interface since interface reset."

        ::=     { cBladeVEthStatsEntry 16 }


cBladeVEthStatsOutCarrierDctFail OBJECT-TYPE
    SYNTAX      Counter
    ACCESS      read-only
    STATUS      mandatory
    DESCRIPTION
            "The number of carrier detect failures detetced while transmitting
            from this interface since interface reset."

        ::=     { cBladeVEthStatsEntry 17 }


cBladeVEthStatsOutCompressed OBJECT-TYPE
    SYNTAX      Counter
    ACCESS      read-only
    STATUS      mandatory
    DESCRIPTION
            "The number of compressed packets transmitted from this interface
            since interface reset."

        ::=     { cBladeVEthStatsEntry 18 }


cBladeVEthStatsOperStatus OBJECT-TYPE
    SYNTAX      InterfaceOperStatus
    ACCESS      read-only
    STATUS      mandatory
    DESCRIPTION
            "The operational state of the interface."

        ::=     { cBladeVEthStatsEntry 19 }


-- table of IP addresses assigned to each cBlade VEth (not yet implemented)
cBladeVEthIpTable     OBJECT-TYPE
    SYNTAX      SEQUENCE OF CBladeVEthIpEntry
    ACCESS      not-accessible
    STATUS      mandatory
    DESCRIPTION
            "A list of IP addresses, broadcast addresses, and nework masks
            configured on each cBlade VEth interface."

        ::=     { cBlades 9 }


cBladeVEthIpEntry     OBJECT-TYPE
    SYNTAX      CBladeVEthIpEntry
    ACCESS      not-accessible
    STATUS      mandatory
    DESCRIPTION
            "the IP address, broadcast address, and network mask
            for a cBlade VEth cBlade or alias."

    INDEX       { bladeFrameIndex, cBladeIndex, cBladeVEthIndex, IMPLIED cBladeVEthIpAliasName }
        ::=     { cBladeVEthIpTable 1 }


CBladeVEthIpEntry ::=
    SEQUENCE {
        cBladeVEthIpAliasName
            DisplayString (SIZE(0..63)),
        cBladeVEthIpVEthIndex
            INTEGER,
        cBladeVEthIpCBladeIndex
            INTEGER,
        cBladeVEthIpBladeFrameIndex
            INTEGER,
        cBladeVEthIpAddress
            IpAddress,
        cBladeVEthIpBroadcast
            IpAddress,
        cBladeVEthIpMask
            IpAddress
    }


cBladeVEthIpAliasName OBJECT-TYPE
    SYNTAX      DisplayString (SIZE(0..63))
    ACCESS      read-only
    STATUS      mandatory
    DESCRIPTION
            "The name of this network interface or alias, i.e. lo, vVEth31, VEth10:1"

        ::=     { cBladeVEthIpEntry 1 }


cBladeVEthIpVEthIndex OBJECT-TYPE
    SYNTAX      INTEGER
    ACCESS      read-only
    STATUS      mandatory
    DESCRIPTION
            "An integer value identifying the cBladeVEthIndex of the cBlade VEth
            that hosts this IP configuraion."

        ::=     { cBladeVEthIpEntry 2 }


cBladeVEthIpCBladeIndex OBJECT-TYPE
    SYNTAX      INTEGER
    ACCESS      read-only
    STATUS      mandatory
    DESCRIPTION
            "An integer value identifying the cBladeIndex of the cBlade
            that hosts this IP configuraion."

        ::=     { cBladeVEthIpEntry 3 }


cBladeVEthIpBladeFrameIndex OBJECT-TYPE
    SYNTAX      INTEGER
    ACCESS      read-only
    STATUS      mandatory
    DESCRIPTION
            "An integer value identifying the bladeFrameIndex of the
            BladeFrame that hosts this IP configuraion."

        ::=     { cBladeVEthIpEntry 4 }


cBladeVEthIpAddress OBJECT-TYPE
    SYNTAX      IpAddress
    ACCESS      read-only
    STATUS      mandatory
    DESCRIPTION
            "The IP address configured on this cBlade VEth (or alias)"

        ::=     { cBladeVEthIpEntry 5 }


cBladeVEthIpBroadcast OBJECT-TYPE
    SYNTAX      IpAddress
    ACCESS      read-only
    STATUS      mandatory
    DESCRIPTION
            "The broadcast address configured on this cBlade VEth (or alias)"

        ::=     { cBladeVEthIpEntry 6 }


cBladeVEthIpMask OBJECT-TYPE
    SYNTAX      IpAddress
    ACCESS      read-only
    STATUS      mandatory
    DESCRIPTION
            "The network mask configured on this cBlade VEth (or alias)"

        ::=     { cBladeVEthIpEntry 7 }


-- table of cBlade HW controls

cBladeControlTable  OBJECT-TYPE
    SYNTAX      SEQUENCE OF CBladeControlEntry
    ACCESS      not-accessible
    STATUS      mandatory
    DESCRIPTION
            "A list of cBlade entries containing controls for Control
            Blades in discovered Egenera BladeFrames."

        ::=     { cBlades 10 }


cBladeControlEntry OBJECT-TYPE
    SYNTAX      CBladeControlEntry
    ACCESS      not-accessible
    STATUS      mandatory
    DESCRIPTION
            "An cBlade Control entry contains controls for Control
            Blades in the Egenera PAN."

    INDEX       { bladeFrameIndex, cBladeIndex }
        ::=     { cBladeControlTable 1 }


CBladeControlEntry ::=
    SEQUENCE {
        cBladeControlPowerUp
            INTEGER,
        cBladeControlPowerDown
            INTEGER,
        cBladeControlColdReset
            INTEGER,
        cBladeControlWarmReset
            INTEGER,
        cBladeControlNmi
            INTEGER,
        cBladeControlSwitchPowerUp
            INTEGER,
        cBladeControlSwitchPowerDown
            INTEGER,
        cBladeControlSwitchPowerCycle
            INTEGER
    }


cBladeControlPowerUp OBJECT-TYPE
    SYNTAX      INTEGER
    ACCESS      read-write
    STATUS      mandatory
    DESCRIPTION
            "When set to 1, initiates a power up operation on this Control
            Blade.  When read, returns 0."

        ::=     { cBladeControlEntry 1 }


cBladeControlPowerDown OBJECT-TYPE
    SYNTAX      INTEGER
    ACCESS      read-write
    STATUS      mandatory
    DESCRIPTION
            "When set to 1, initiates a power down operation on this Control
            Blade.  When read, returns 0."

        ::=     { cBladeControlEntry 2 }


cBladeControlColdReset OBJECT-TYPE
    SYNTAX      INTEGER
    ACCESS      read-write
    STATUS      mandatory
    DESCRIPTION
            "When set to 1, initiates a cold reset operation on this Control
            Blade. When read, returns 0."

        ::=     { cBladeControlEntry 3 }


cBladeControlWarmReset OBJECT-TYPE
    SYNTAX  INTEGER
    ACCESS      read-write
    STATUS  mandatory
    DESCRIPTION
            "When set to 1, initiates a warm reset operation on this Control
            Blade.  When read, returns 0."

        ::=     { cBladeControlEntry 4 }


cBladeControlNmi OBJECT-TYPE
    SYNTAX      INTEGER
    ACCESS      read-write
    STATUS      mandatory
    DESCRIPTION
            "When set to 1, initiates an non-maskable interrupt operation on
            this cBlade. When read, returns 0."

        ::=     { cBladeControlEntry 5 }


cBladeControlSwitchPowerUp OBJECT-TYPE
    SYNTAX      INTEGER
    ACCESS      read-write
    STATUS      mandatory
    DESCRIPTION
            "When set to 1, initiates a power down operation on the switch
            component of this cBlade.  When read, returns 0."

        ::=     { cBladeControlEntry 6 }


cBladeControlSwitchPowerDown OBJECT-TYPE
    SYNTAX      INTEGER
    ACCESS      read-write
    STATUS      mandatory
    DESCRIPTION
            "When set to 1, initiates a power up operation on the switch
            component of this cBlade.  When read, returns 0."

        ::=     { cBladeControlEntry 7 }


cBladeControlSwitchPowerCycle  OBJECT-TYPE
    SYNTAX      INTEGER
    ACCESS      read-write
    STATUS      mandatory
    DESCRIPTION
            "When set to 1, initiates a power cycle operation on the switch
            component of this cBlade.  When read, returns 0."

        ::=     { cBladeControlEntry 8 }


-- cBlade Hardware Monitors

HardwareMonitorType ::= INTEGER {
    voltage(1),
    temperature(2),
    fanspeed(3),
    undefined(999)
}

cBladeHwMonitorTable OBJECT-TYPE
    SYNTAX      SEQUENCE OF CBladeMonitorEntry
    ACCESS      not-accessible
    STATUS      mandatory
    DESCRIPTION
            "A list of cBlade monitor entries for each cBlade in the PAN.
            Voltage is measured in Volts, Temperature in degrees Celcius,
            and fan speed in Revolutions Per Minute"

        ::=     { cBlades 11 }


cBladeMonitorEntry OBJECT-TYPE
    SYNTAX      CBladeMonitorEntry
    ACCESS      not-accessible
    STATUS      mandatory
    DESCRIPTION
            "Attributes of a specific cBlade hardware monitor."


    INDEX       { bladeFrameIndex, cBladeIndex, cBladeHwMonitorIndex }
        ::=     { cBladeHwMonitorTable 1 }


CBladeMonitorEntry ::=
    SEQUENCE {
        cBladeHwMonitorIndex
            INTEGER  (1..2147483647),
        cBladeHwMonitorName
            DisplayString,
        cBladeHwMonitorType
            HardwareMonitorType,
        cBladeHwMonitorValue
            INTEGER,
        cBladeHwMonitorValueDenomonator
            INTEGER
    }


cBladeHwMonitorIndex OBJECT-TYPE
    SYNTAX      INTEGER (1..2147483647)
    ACCESS      read-only
    STATUS      mandatory
    DESCRIPTION
            "An integer value uniquely identifying the monitor within the
            cBlade."

        ::=     { cBladeMonitorEntry 1 }


cBladeHwMonitorName OBJECT-TYPE
    SYNTAX      DisplayString
    ACCESS      read-only
    STATUS      mandatory
    DESCRIPTION
            "An String identifying the name of the hardware monitor."

        ::=     { cBladeMonitorEntry 2 }


cBladeHwMonitorType OBJECT-TYPE
    SYNTAX      HardwareMonitorType
    ACCESS      read-only
    STATUS      mandatory
    DESCRIPTION
            "An integer encoding of the monitor type; voltage, temperature, or
            fanspeed."

        ::=     { cBladeMonitorEntry 3 }


cBladeHwMonitorValue OBJECT-TYPE
    SYNTAX      INTEGER
    ACCESS      read-only
    STATUS      mandatory
    DESCRIPTION
            "The integer representation of the current hardware sensor value.
            Voltage values are multiplied by 100 and rounted to convert from
            float to integer.  Thus 0.530 => 53"

        ::=     { cBladeMonitorEntry 4 }


cBladeHwMonitorValueDenomonator OBJECT-TYPE
    SYNTAX      INTEGER
    ACCESS      read-only
    STATUS      mandatory
    DESCRIPTION
            "The integer representation of the denomonator required to convert
            the integer incoding of the sensor value to the float value.
            For voltage sensors, this value is 100, for all other sensors,
            this value is 1."

        ::=     { cBladeMonitorEntry 5 }


cBladeHbaTable   OBJECT-TYPE
    SYNTAX      SEQUENCE OF CBladeHbaEntry
    ACCESS      not-accessible
    STATUS      mandatory
    DESCRIPTION
            "physical HBA on a BladeFrame's cBlades (cBlades)."


        ::=     { cBlades 12 }


cBladeHbaEntry OBJECT-TYPE
    SYNTAX      CBladeHbaEntry
    ACCESS      not-accessible
    STATUS      mandatory
    DESCRIPTION
            "Information specific to each HBA in the PAN."

    INDEX       { bladeFrameIndex, cBladeIndex, cBladeHbaIndex }
        ::=     { cBladeHbaTable 1 }

CBladeHbaEntry ::=
    SEQUENCE {
        cBladeHbaIndex
            INTEGER,
        cBladeHbaCBladeIndex
            INTEGER,
        cBladeHbaBladeFrameIndex
            INTEGER,
        cBladeHbaName
            DisplayString,
        cBladeHbaStatus
            DisplayString,
        cBladeHbaEnableState
            TruthValue
    }

cBladeHbaIndex OBJECT-TYPE
    SYNTAX      INTEGER (1..2147483647)
    ACCESS      read-only
    STATUS      mandatory
    DESCRIPTION
            "An integer value uniquely identifying the HBA within the
            cBlade."

        ::=     { cBladeHbaEntry 1 }


cBladeHbaCBladeIndex OBJECT-TYPE
    SYNTAX      INTEGER (1..2147483647)
    ACCESS      read-only
    STATUS      mandatory
    DESCRIPTION
            "An integer value identifying the cBladeIndex value of the
            cBlade that hosts this HBA."

        ::=     { cBladeHbaEntry 2 }


cBladeHbaBladeFrameIndex OBJECT-TYPE
    SYNTAX      INTEGER (1..2147483647)
    ACCESS      read-only
    STATUS      mandatory
    DESCRIPTION
            "An integer value identifying the bladeFrameIndex value of the
            BladeFrame that hosts this HBA."

        ::=     { cBladeHbaEntry 3 }

cBladeHbaName OBJECT-TYPE
    SYNTAX      DisplayString
    ACCESS      read-only
    STATUS      mandatory
    DESCRIPTION
            "A human readable string uniquely identifying the cBlade HBA."

        ::=     { cBladeHbaEntry 4 }


cBladeHbaStatus OBJECT-TYPE
    SYNTAX      DisplayString
    ACCESS      read-only
    STATUS      mandatory
    DESCRIPTION
            "A human readable string identifying the status of the cBlade HBA."

        ::=     { cBladeHbaEntry 5 }

cBladeHbaEnableState OBJECT-TYPE
    SYNTAX      TruthValue
    ACCESS      read-only
    STATUS      mandatory
    DESCRIPTION
            "Indicates whether the cBlade HBA is enabled."

        ::=     { cBladeHbaEntry 6 }


-- sBlades group

sBlades OBJECT IDENTIFIER ::= { blades 2 }

-- sBlade table
-- The sBlade table contains information about sBlades in each
-- BladeFrame.

sBladeTable OBJECT-TYPE
    SYNTAX      SEQUENCE OF SBladeEntry
    ACCESS      not-accessible
    STATUS      mandatory
    DESCRIPTION
            "A list of sBlade entries containing information for Switch
            Blades in the Egenera PAN."

        ::=     { sBlades 1 }


sBladeEntry OBJECT-TYPE
    SYNTAX      SBladeEntry
    ACCESS      not-accessible
    STATUS      mandatory
    DESCRIPTION
            "A sBlade entry contains information for sBlades in
            the Egenera PAN."

    INDEX       { bladeFrameIndex, sBladeIndex }
        ::=     { sBladeTable 1 }


SBladeEntry ::=
    SEQUENCE {
        sBladeIndex
            INTEGER (1..2147483647),
        sBladeFrameIndex
            INTEGER (1..2147483647),
        sBladeName
            DisplayString,
        sBladeSerialNumber
            DisplayString,
        sBladePartNumber
            DisplayString,
        sBladePowerStatus
            PowerStatusType,
        sBladePowerSupply
            DisplayString,
        sBladeMasterStatus
            TruthValue,
        sBladeActiveStatus
            TruthValue,
        sBladeEnabledStatus
            TruthValue,
        sBladeSelectedStatus
            TruthValue,
        sBladeRecognizedStatus
            TruthValue,
        sBladeHealthStatus
            HealthStatusType,
        sBladeUpTime
            TimeTicks
    }


sBladeIndex OBJECT-TYPE
    SYNTAX      INTEGER (1..2147483647)
    ACCESS      read-only
    STATUS      mandatory
    DESCRIPTION
            "An integer value uniquely identifying the sBlade within the
            BladeFrame.  This corresponds to the physical location of the
            sBlade within the BladeFrame."

        ::=     { sBladeEntry 1 }


sBladeFrameIndex OBJECT-TYPE
    SYNTAX      INTEGER (1..2147483647)
    ACCESS      read-only
    STATUS      mandatory
    DESCRIPTION
            "An integer value identifying the bladeFrameIndex value of the
            BladeFrame that hosts this sBlade."

        ::=     { sBladeEntry 2 }


sBladeName OBJECT-TYPE
    SYNTAX      DisplayString
    ACCESS      read-only
    STATUS      mandatory
    DESCRIPTION
            "A textual string identifying the sBlade."

        ::=     { sBladeEntry 3 }


sBladeSerialNumber OBJECT-TYPE
    SYNTAX      DisplayString
    ACCESS      read-only
    STATUS      mandatory
    DESCRIPTION
            "Describes the serial number of this sBlade."

        ::=     { sBladeEntry 4 }


sBladePartNumber OBJECT-TYPE
    SYNTAX      DisplayString
    ACCESS      read-only
    STATUS      mandatory
    DESCRIPTION
            "Describes the part number of this sBlade."

        ::=     { sBladeEntry 5 }


sBladePowerStatus OBJECT-TYPE
    SYNTAX      PowerStatusType
    ACCESS      read-only
    STATUS      mandatory
    DESCRIPTION
            "The power status of the sBlade."

        ::=     { sBladeEntry 6 }


sBladePowerSupply OBJECT-TYPE
    SYNTAX      DisplayString
    ACCESS      read-only
    STATUS      mandatory
    DESCRIPTION
            "The name of the power supply used by this sBlade."

        ::=     { sBladeEntry 7 }

sBladeMasterStatus OBJECT-TYPE
    SYNTAX      TruthValue
    ACCESS      read-only
    STATUS      mandatory
    DESCRIPTION
            "Indicates that the switch is acting as the master switch."

        ::=     { sBladeEntry 8 }


sBladeActiveStatus OBJECT-TYPE
    SYNTAX      TruthValue
    ACCESS      read-only
    STATUS      mandatory
    DESCRIPTION
            "Indicates whether or not the sBlade is active."

        ::=     { sBladeEntry 9 }


sBladeEnabledStatus OBJECT-TYPE
    SYNTAX      TruthValue
    ACCESS      read-only
    STATUS      mandatory
    DESCRIPTION
            "Indicates whether the sBlade is enabled or disabled."

        ::=     { sBladeEntry 10 }


sBladeSelectedStatus OBJECT-TYPE
    SYNTAX      TruthValue
    ACCESS      read-only
    STATUS      mandatory
    DESCRIPTION
            "Indicates whether the sBlade is selected."

        ::=     { sBladeEntry 11 }


sBladeRecognizedStatus OBJECT-TYPE
    SYNTAX      TruthValue
    ACCESS      read-only
    STATUS      mandatory
    DESCRIPTION
            "Indicates whether the blade has been recognized by the PAN Manager."

        ::=     { sBladeEntry 12 }


sBladeHealthStatus OBJECT-TYPE
    SYNTAX      HealthStatusType
    ACCESS      read-only
    STATUS      mandatory
    DESCRIPTION
            "An indication of the health of the BladeFrame."

        ::=     { sBladeEntry 13 }


sBladeUpTime OBJECT-TYPE
    SYNTAX      TimeTicks
    ACCESS      read-only
    STATUS      mandatory
    DESCRIPTION
            "The amount of time that the BladeFrame has been up."

        ::=     { sBladeEntry 14 }


-- Switch controls

sBladeControlTable OBJECT-TYPE
    SYNTAX      SEQUENCE OF SBladeControlEntry
    ACCESS      not-accessible
    STATUS      mandatory
    DESCRIPTION
            "A list of sBlade Control entries containing controls for
            sBlades the Egenera PAN."

        ::=     { sBlades 2 }


sBladeControlEntry OBJECT-TYPE
    SYNTAX      SBladeControlEntry
    ACCESS      not-accessible
    STATUS      mandatory
    DESCRIPTION
            "A sBlade Control entry contains controls for sBlades
            in the Egenera PAN."

    INDEX       { bladeFrameIndex, sBladeIndex }
        ::=     { sBladeControlTable 1 }


SBladeControlEntry ::=
    SEQUENCE {
        sBladeControlPowerUp
            INTEGER,
        sBladeControlPowerDown
            INTEGER
    }


sBladeControlPowerUp OBJECT-TYPE
    SYNTAX      INTEGER
    ACCESS      read-write
    STATUS      mandatory
    DESCRIPTION
            "When set to 1, initiates a power up operation on this
            sBlade.  When read, returns 0."

        ::=     { sBladeControlEntry 1 }


sBladeControlPowerDown OBJECT-TYPE
    SYNTAX      INTEGER
    ACCESS      read-write
    STATUS      mandatory
    DESCRIPTION
            "When set to 1, initiates a power down operation on this
            sBlade.  When read, returns 0."

        ::=     { sBladeControlEntry 2 }

-- sBlade hardware monitors

sBladeHwMonitorTable OBJECT-TYPE
    SYNTAX      SEQUENCE OF SBladeMonitorEntry
    ACCESS      not-accessible
    STATUS      mandatory
    DESCRIPTION
            "A list of sBlade monitor entries for each sBlade in the PAN."

        ::=     { sBlades 3 }


sBladeMonitorEntry OBJECT-TYPE
    SYNTAX      SBladeMonitorEntry
    ACCESS      not-accessible
    STATUS      mandatory
    DESCRIPTION
            "Attributes of a specific sBlade hardware monitor."


    INDEX       { bladeFrameIndex, sBladeIndex, sBladeHwMonitorIndex }
        ::=     { sBladeHwMonitorTable 1 }


SBladeMonitorEntry ::=
    SEQUENCE {
        sBladeHwMonitorIndex
            INTEGER  (1..2147483647),
        sBladeHwMonitorName
            DisplayString,
        sBladeHwMonitorType
            HardwareMonitorType,
        sBladeHwMonitorValue
            INTEGER,
        sBladeHwMonitorValueDenomonator
            INTEGER
    }


sBladeHwMonitorIndex OBJECT-TYPE
    SYNTAX      INTEGER (1..2147483647)
    ACCESS      read-only
    STATUS      mandatory
    DESCRIPTION
            "An integer value uniquely identifying the monitor within the
            sBlade."

        ::=     { sBladeMonitorEntry 1 }


sBladeHwMonitorName OBJECT-TYPE
    SYNTAX      DisplayString
    ACCESS      read-only
    STATUS      mandatory
    DESCRIPTION
            "An String identifying the name of the hardware monitor."

        ::=     { sBladeMonitorEntry 2 }


sBladeHwMonitorType OBJECT-TYPE
    SYNTAX      HardwareMonitorType
    ACCESS      read-only
    STATUS      mandatory
    DESCRIPTION
            "An integer encoding of the monitor type; voltage, temperature, or
            fanspeed."

        ::=     { sBladeMonitorEntry 3 }


sBladeHwMonitorValue OBJECT-TYPE
    SYNTAX      INTEGER
    ACCESS      read-only
    STATUS      mandatory
    DESCRIPTION
            "The integer representation of the current hardware sensor value.
            Voltage values are multiplied by 100 and rounted to convert from
            float to integer.  Thus 0.530 => 53"

        ::=     { sBladeMonitorEntry 4 }


sBladeHwMonitorValueDenomonator OBJECT-TYPE
    SYNTAX      INTEGER
    ACCESS      read-only
    STATUS      mandatory
    DESCRIPTION
            "The integer representation of the denomonator required to convert
            the integer incoding of the sensor value to the float value.
            For voltage sensors, this value is 100, for all other sensors,
            this value is 1."

        ::=     { sBladeMonitorEntry 5 }


sBladeEthTable   OBJECT-TYPE
    SYNTAX      SEQUENCE OF SBladeEthEntry
    ACCESS      not-accessible
    STATUS      mandatory
    DESCRIPTION
            "physical Network Interface Cards (NICs) on a BladeFrame's
                   sBlades (sBlades)."

        ::=     { sBlades 4 }


sBladeEthEntry OBJECT-TYPE
    SYNTAX      SBladeEthEntry
    ACCESS      not-accessible
    STATUS      mandatory
    DESCRIPTION
            "Information specific to each sBlade Eth in the PAN."

    INDEX       { bladeFrameIndex, sBladeIndex, sBladeEthIndex }
        ::=     { sBladeEthTable 1 }

SBladeEthEntry ::=
    SEQUENCE {
        sBladeEthIndex
            INTEGER,
        sBladeEthSBladeIndex
            INTEGER,
        sBladeEthBladeFrameIndex
            INTEGER,
        sBladeEthName
            DisplayString,
        sBladeEthFullName
            DisplayString,
        sBladeEthHwMACAddressOctets
            PhysAddress,
        sBladeEthHwMACAddressString
            DisplayString,
        sBladeEthNICType
            DisplayString,
        sBladeEthFiltered
            TruthValue,
        sBladeEthUplinkName
            DisplayString,
        sBladeEthUplinkPort
            INTEGER,
        sBladeEthLinkState
            InterfaceOperStatus,
        sBladeEthRethStatus
            EthRethStatus
    }

sBladeEthIndex OBJECT-TYPE
    SYNTAX      INTEGER (1..2147483647)
    ACCESS      read-only
    STATUS      mandatory
    DESCRIPTION
            "An integer value uniquely identifying the sBlade within the
            sBlade."

        ::=     { sBladeEthEntry 1 }


sBladeEthSBladeIndex OBJECT-TYPE
    SYNTAX      INTEGER (1..2147483647)
    ACCESS      read-only
    STATUS      mandatory
    DESCRIPTION
            "An integer value identifying the sBladeIndex value of the
            sBlade that hosts this Eth."

        ::=     { sBladeEthEntry 2 }


sBladeEthBladeFrameIndex OBJECT-TYPE
    SYNTAX      INTEGER (1..2147483647)
    ACCESS      read-only
    STATUS      mandatory
    DESCRIPTION
            "An integer value identifying the bladeFrameIndex value of the
            BladeFrame that hosts this Eth."

        ::=     { sBladeEthEntry 3 }


sBladeEthName OBJECT-TYPE
    SYNTAX      DisplayString
    ACCESS      read-only
    STATUS      mandatory
    DESCRIPTION
            "A human readable string uniquely identifying the sBlade Eth."

        ::=     { sBladeEthEntry 4 }


sBladeEthFullName OBJECT-TYPE
    SYNTAX      DisplayString
    ACCESS      read-only
    STATUS      mandatory
    DESCRIPTION
            "A human readable string uniquely identifying the sBlade Eth,
            including the host sBlade and BladeFrame."

        ::=     { sBladeEthEntry 5 }


sBladeEthHwMACAddressOctets OBJECT-TYPE
    SYNTAX      PhysAddress
    ACCESS      read-only
    STATUS      mandatory
    DESCRIPTION
            "An encoding of the sBlade Eth hardware MAC address."

        ::=     { sBladeEthEntry 6 }


sBladeEthHwMACAddressString OBJECT-TYPE
    SYNTAX      DisplayString
    ACCESS      read-only
    STATUS      mandatory
    DESCRIPTION
            "A human readable string representing the sBlade Eth hardware
            MAC address in the form: '6E:4A:1F:00:01:06'."

        ::=     { sBladeEthEntry 7 }



sBladeEthNICType OBJECT-TYPE
    SYNTAX      DisplayString
    ACCESS      read-only
    STATUS      mandatory
    DESCRIPTION
            "Specifies the sBlade ETH NIC type, such as e100 or e1000."

        ::=     { sBladeEthEntry 10 }


sBladeEthFiltered OBJECT-TYPE
    SYNTAX      TruthValue
    ACCESS      read-only
    STATUS      mandatory
    DESCRIPTION
            "indicates whether filtered mode is enabled.  unfiltered mode
            allows the sBlade NICs to admit all external network traffic sent
            by their connecting switch. Filtered mode enables the sBlade
            NICs to filter incoming traffic  based  on  a  single  MAC
            address assigned to the NIC. Unfiltered mode is the default
            configuration. "

        ::=     { sBladeEthEntry 11 }


sBladeEthUplinkName OBJECT-TYPE
    SYNTAX      DisplayString
    ACCESS      read-only
    STATUS      mandatory
    DESCRIPTION
            "A human readable string that a PAN or BladeFrame Administrator
            assigns to describe the uplink port."

        ::=     { sBladeEthEntry 12 }


sBladeEthUplinkPort OBJECT-TYPE
    SYNTAX      INTEGER
    ACCESS      read-only
    STATUS      mandatory
    DESCRIPTION
            "An integer value that a PAN or BladeFrame Administrator assigns
            to identify the uplink port."

        ::=     { sBladeEthEntry 13 }


sBladeEthLinkState OBJECT-TYPE
    SYNTAX      InterfaceOperStatus
    ACCESS      read-only
    STATUS      mandatory
    DESCRIPTION
            "The Link State of the Eth."

        ::=     { sBladeEthEntry 14 }


sBladeEthRethStatus OBJECT-TYPE
    SYNTAX      EthRethStatus
    ACCESS      read-only
    STATUS      mandatory
    DESCRIPTION
            "The State of the Eth with respect to REth membership."

        ::=     { sBladeEthEntry 15 }

-- table of VLANs for each sBlade Eth

sBladeEthVLANTable   OBJECT-TYPE
    SYNTAX      SEQUENCE OF SBladeEthVLANEntry
    ACCESS  not-accessible
    STATUS      mandatory
    DESCRIPTION
            "A list of VLAN IDs and descriptions associated with each Eth."

        ::=     { sBlades 5 }


sBladeEthVLANEntry OBJECT-TYPE
    SYNTAX      SBladeEthVLANEntry
    ACCESS      not-accessible
    STATUS      mandatory
    DESCRIPTION
            "Information specific to each VLAN for sBlade sBladeEths."

    INDEX       { bladeFrameIndex, sBladeIndex, sBladeEthIndex, sBladeEthVLANId }
        ::=     { sBladeEthVLANTable 1 }

SBladeEthVLANEntry ::=
    SEQUENCE {
        sBladeEthVLANId
            INTEGER (1..2147483647),
        sBladeEthVLANEthIndex
            INTEGER,
        sBladeEthVLANsBladeIndex
            INTEGER,
        sBladeEthVLANBladeFrameIndex
            INTEGER,
        sBladeEthVLANEthName
            DisplayString,
        sBladeEthVLANName
            DisplayString
    }


sBladeEthVLANId OBJECT-TYPE
    SYNTAX      INTEGER (1..2147483647)
    ACCESS      read-only
    STATUS      mandatory
    DESCRIPTION
            "specifies a VLAN ID assigned to the uplink port on the physical
            network component connected to the sBlade NIC"

        ::=     { sBladeEthVLANEntry 1 }


sBladeEthVLANEthIndex OBJECT-TYPE
    SYNTAX      INTEGER
    ACCESS      read-only
    STATUS      mandatory
    DESCRIPTION
            "An integer value identifying the sBladeEthIndex value of the
            sBlade Eth that hosts this Eth VLAN."

        ::=     { sBladeEthVLANEntry 2 }


sBladeEthVLANsBladeIndex OBJECT-TYPE
    SYNTAX      INTEGER
    ACCESS      read-only
    STATUS      mandatory
    DESCRIPTION
            "An integer value identifying the sBladeIndex value of the
            sBlade that hosts this Eth VLAN."

        ::=     { sBladeEthVLANEntry 3 }


sBladeEthVLANBladeFrameIndex OBJECT-TYPE
    SYNTAX      INTEGER
    ACCESS      read-only
    STATUS      mandatory
    DESCRIPTION
            "An integer value identifying the bladeFrameIndex value of the
            BladeFrame that hosts this Eth VLAN."

        ::=     { sBladeEthVLANEntry 4 }


sBladeEthVLANEthName OBJECT-TYPE
    SYNTAX      DisplayString
    ACCESS      read-only
    STATUS      mandatory
    DESCRIPTION
            "The full name of the ethernet interface associated with this VLAN."

        ::=     { sBladeEthVLANEntry 5 }


sBladeEthVLANName OBJECT-TYPE
    SYNTAX      DisplayString
    ACCESS      read-only
    STATUS      mandatory
    DESCRIPTION
            "A human readable string that a PAN or BladeFrame Administrator
            assigns to the VLAN."

        ::=     { sBladeEthVLANEntry 6 }


        



-- pBlades group

pBlades OBJECT IDENTIFIER ::= { blades 3 }

-- pBlade table
-- The pBlade table contains information about pBlades in
-- BladeFrames.

pBladeTable OBJECT-TYPE
    SYNTAX      SEQUENCE OF PBladeEntry
    ACCESS      not-accessible
    STATUS      mandatory
    DESCRIPTION
            "A list of pBlade entries containing information
            for pBlades the Egenera PAN."

        ::=     { pBlades 1 }


pBladeEntry OBJECT-TYPE
    SYNTAX      PBladeEntry
    ACCESS      not-accessible
    STATUS      mandatory
    DESCRIPTION
            "An pBlade entry contains information for Processing
            Blades in the Egenera PAN."

    INDEX       { bladeFrameIndex, pBladeIndex }
        ::=     { pBladeTable 1 }


PBladeEntry ::=
    SEQUENCE {
        pBladeIndex
            INTEGER (1..2147483647),
        pBladeFrameIndex
            INTEGER (1..2147483647),
        pBladePServerIndex
            INTEGER (1..2147483647),
        pBladeLPanIndex
            INTEGER (1..2147483647),
        pBladeName
            DisplayString,
        pBladeBladeFrameName
            DisplayString,
        pBladePServerName
            DisplayString,
        pBladeLPanName
            DisplayString,
        pBladeDescription
            DisplayString,
        pBladeHostName
            DisplayString,
        pBladeNumCpus
            INTEGER,
        pBladeCpuSpeed
            INTEGER,
        pBladeCpuModel
            DisplayString,
        pBladeMemorySize
            INTEGER,
        pBladeCache
            INTEGER,
        pBladeArchitecture
            DisplayString,
        pBladeSerialNumber
            DisplayString,
        pBladePartNumber
            DisplayString,
        pBladePowerStatus
            PowerStatusType,
        pBladePowerSupply
            DisplayString,
        pBladeActiveStatus
            TruthValue,
        pBladeAllocationStatus
            TruthValue,
        pBladeEnabledStatus
            TruthValue,
        pBladeSelectedStatus
            TruthValue,
        pBladeRecognizedStatus
            TruthValue,
        pBladeHealthStatus
            HealthStatusType,
        pBladeInDebugger
            TruthValue,
        pBladeOutOfService
            TruthValue,
        pBladeOutOfServicePending
            TruthValue,
        pBladeBootStatus
            DisplayString,
        pBladeUpTime
            TimeTicks,
        pBladePoolIndex
            INTEGER
    }


pBladeIndex OBJECT-TYPE
    SYNTAX      INTEGER (1..2147483647)
    ACCESS      read-only
    STATUS      mandatory
    DESCRIPTION
            "An integer value uniquely identifying the pBlade within
            the BladeFrame.  This corresponds to the physical location of the
            pBlade within the BladeFrame."

        ::=     { pBladeEntry 1 }


pBladeFrameIndex OBJECT-TYPE
    SYNTAX      INTEGER (1..2147483647)
    ACCESS      read-only
    STATUS      mandatory
    DESCRIPTION
            "An integer value identifying the bladeFrameIndex value of the
            BladeFrame that hosts this pBlade."

        ::=     { pBladeEntry 2 }


pBladePServerIndex OBJECT-TYPE
    SYNTAX      INTEGER (1..2147483647)
    ACCESS      read-only
    STATUS      mandatory
    DESCRIPTION
            "An integer value identifying the pServerIndex of the pServer
            running on this pBlade, or -1 if the pBlade is not occupied
            by a pServer."

        ::=     { pBladeEntry 3 }


pBladeLPanIndex OBJECT-TYPE
    SYNTAX      INTEGER (1..2147483647)
    ACCESS      read-only
    STATUS      mandatory
    DESCRIPTION
            "An integer value identifying the lPanIndex of the LPAN
            containing the pServer running on this pBlade, or -1 if the
            pBlade is not occupied by a pServer."

        ::=     { pBladeEntry 4 }


pBladeName OBJECT-TYPE
    SYNTAX      DisplayString
    ACCESS      read-only
    STATUS      mandatory
    DESCRIPTION
            "A textual string identifying this pBlade."

        ::=     { pBladeEntry 5 }


pBladeBladeFrameName OBJECT-TYPE
    SYNTAX      DisplayString
    ACCESS      read-only
    STATUS      mandatory
    DESCRIPTION
            "A textual string identifying the BladeFrame containing this
            pBlade."

        ::=     { pBladeEntry 6 }


pBladePServerName OBJECT-TYPE
    SYNTAX      DisplayString
    ACCESS      read-only
    STATUS      mandatory
    DESCRIPTION
            "A textual string identifying the pServer running on this pBlade."

        ::=     { pBladeEntry 7 }

pBladeLPanName OBJECT-TYPE
    SYNTAX      DisplayString
    ACCESS      read-only
    STATUS      mandatory
    DESCRIPTION
            "A textual string identifying the LPAN containing the pServer
            running on this pBlade."

        ::=     { pBladeEntry 8 }


pBladeDescription OBJECT-TYPE
    SYNTAX      DisplayString
    ACCESS      read-only
    STATUS      mandatory
    DESCRIPTION
            "A textual string describing this pBlade."

        ::=     { pBladeEntry 9 }


pBladeHostName OBJECT-TYPE
    SYNTAX      DisplayString
    ACCESS      read-only
    STATUS      mandatory
    DESCRIPTION
            "The hostname of the PServer running on this pBlade."

        ::=     { pBladeEntry 10 }


pBladeNumCpus OBJECT-TYPE
    SYNTAX      INTEGER
    ACCESS      read-only
    STATUS      mandatory
    DESCRIPTION
            "The number of CPUs on the pBlade."

        ::=     { pBladeEntry 11 }


pBladeCpuSpeed OBJECT-TYPE
    SYNTAX      INTEGER
    ACCESS      read-only
    STATUS      mandatory
    DESCRIPTION
            "The speed of the CPUs on the pBlade in Mhz."

        ::=     { pBladeEntry 12 }


pBladeCpuModel OBJECT-TYPE
    SYNTAX      DisplayString
    ACCESS      read-only
    STATUS      mandatory
    DESCRIPTION
            "A textual string representing the CPU model this pBlade."

        ::=     { pBladeEntry 13 }


pBladeMemorySize OBJECT-TYPE
    SYNTAX      INTEGER
    ACCESS      read-only
    STATUS      mandatory
    DESCRIPTION
            "The size of the physical RAM installed on the pBlade,
            in MB."

        ::=     { pBladeEntry 14 }


pBladeCache OBJECT-TYPE
    SYNTAX      INTEGER
    ACCESS      read-only
    STATUS      mandatory
    DESCRIPTION
            "The size of the CPU cache installed on the pBlade,
            in kB."

        ::=     { pBladeEntry 15 }


pBladeArchitecture OBJECT-TYPE
    SYNTAX      DisplayString
    ACCESS      read-only
    STATUS      mandatory
    DESCRIPTION
            "Describes the pBlade hardware architecture."

        ::=     { pBladeEntry 16 }


pBladeSerialNumber OBJECT-TYPE
    SYNTAX      DisplayString
    ACCESS      read-only
    STATUS      mandatory
    DESCRIPTION
            "Describes the serial number of this pBlade."

        ::=     { pBladeEntry 17 }


pBladePartNumber OBJECT-TYPE
    SYNTAX      DisplayString
    ACCESS      read-only
    STATUS      mandatory
    DESCRIPTION
            "Describes the part number of this pBlade."

        ::=     { pBladeEntry 18 }


pBladePowerStatus OBJECT-TYPE
    SYNTAX      PowerStatusType
    ACCESS      read-only
    STATUS      mandatory
    DESCRIPTION
            "The power status of the pBlade."

        ::=     { pBladeEntry 19 }


pBladePowerSupply OBJECT-TYPE
    SYNTAX      DisplayString
    ACCESS      read-only
    STATUS      mandatory
    DESCRIPTION
            "The name of the power supply used by this pBlade."

        ::=     { pBladeEntry 20 }


pBladeActiveStatus OBJECT-TYPE
    SYNTAX      TruthValue
    ACCESS      read-only
    STATUS      mandatory
    DESCRIPTION
            "Indicates whether or not the blade is active."

        ::=     { pBladeEntry 21 }


pBladeAllocationStatus OBJECT-TYPE
    SYNTAX      TruthValue
    ACCESS      read-only
    STATUS      mandatory
    DESCRIPTION
            "Indicates whether or not the blade is allocated."

        ::=     { pBladeEntry 22 }


pBladeEnabledStatus OBJECT-TYPE
    SYNTAX      TruthValue
    ACCESS      read-only
    STATUS      mandatory
    DESCRIPTION
            "Indicates whether the blade is enabled or disabled."

        ::=     { pBladeEntry 23 }


pBladeSelectedStatus OBJECT-TYPE
    SYNTAX      TruthValue
    ACCESS      read-only
    STATUS      mandatory
    DESCRIPTION
            "Indicates whether the blade is selected."

        ::=     { pBladeEntry 24 }


pBladeRecognizedStatus OBJECT-TYPE
    SYNTAX      TruthValue
    ACCESS      read-only
    STATUS      mandatory
    DESCRIPTION
            "Indicates whether the blade has been recognized by the PAN Manager."

        ::=     { pBladeEntry 25 }


pBladeHealthStatus OBJECT-TYPE
    SYNTAX      HealthStatusType
    ACCESS      read-only
    STATUS      mandatory
    DESCRIPTION
            "An indication of the health of the BladeFrame."

        ::=     { pBladeEntry 26 }


pBladeInDebugger OBJECT-TYPE
    SYNTAX      TruthValue
    ACCESS      read-only
    STATUS      mandatory
    DESCRIPTION
            "Indicates whether or not the kernel kernel on the pBlade has
            entered the debugger."

        ::=     { pBladeEntry 27 }


pBladeOutOfService OBJECT-TYPE
    SYNTAX      TruthValue
    ACCESS      read-only
    STATUS      mandatory
    DESCRIPTION
            "Indicates whether this pBlade has been designated 'Out Of
            Service'."

        ::=     { pBladeEntry 28 }


pBladeOutOfServicePending OBJECT-TYPE
    SYNTAX      TruthValue
    ACCESS      read-only
    STATUS      mandatory
    DESCRIPTION
            "Indicates whether this pBlade has a pending designation of
            'Out Of Service'."

        ::=     { pBladeEntry 29 }


pBladeBootStatus OBJECT-TYPE
    SYNTAX      DisplayString
    ACCESS      read-only
    STATUS      mandatory
    DESCRIPTION
            "Indicates the boot status of this pBlade."

        ::=     { pBladeEntry 30 }


pBladeUpTime OBJECT-TYPE
    SYNTAX      TimeTicks
    ACCESS      read-only
    STATUS      mandatory
    DESCRIPTION
            "The amount of time that the pBlade has been up."

        ::=     { pBladeEntry 31 }

pBladePoolIndex OBJECT-TYPE
    SYNTAX      INTEGER (1..2147483647)
    ACCESS      read-only
    STATUS      mandatory
    DESCRIPTION
            "An integer value identifying the poolindex of the pool containing
             the pBlade ."

        ::=     { pBladeEntry 32 }

-- pBlade controls

pBladeControlTable OBJECT-TYPE
    SYNTAX      SEQUENCE OF PBladeControlEntry
    ACCESS      not-accessible
    STATUS      mandatory
    DESCRIPTION
            "A list of pBlade entries containing controls for
            pBlades in the Egenera PAN."

        ::=     { pBlades 2 }


pBladeControlEntry OBJECT-TYPE
    SYNTAX      PBladeControlEntry
    ACCESS      not-accessible
    STATUS      mandatory
    DESCRIPTION
            "An pBlade entry contains controls for Processing
            Blades in the Egenera PAN."


    INDEX       { bladeFrameIndex, pBladeIndex }
        ::=     { pBladeControlTable 1 }


PBladeControlEntry ::=
    SEQUENCE {
        pBladeControlPowerUp
            INTEGER,
        pBladeControlPowerDown
            INTEGER,
        pBladeControlColdReset
            INTEGER,
        pBladeControlWarmReset
            INTEGER,
        pBladeControlNmi
            INTEGER
    }


pBladeControlPowerUp OBJECT-TYPE
    SYNTAX      INTEGER
    ACCESS      read-write
    STATUS      mandatory
    DESCRIPTION
            "When set to 1, initiates a power up operation on this Processing
            Blade. When read, returns 0."

        ::=     { pBladeControlEntry 1 }


pBladeControlPowerDown OBJECT-TYPE
    SYNTAX      INTEGER
    ACCESS      read-write
    STATUS      mandatory
    DESCRIPTION
            "When set to 1, initiates a power down operation on this
            pBlade. When read, returns 0."

        ::=     { pBladeControlEntry 2 }


pBladeControlColdReset OBJECT-TYPE
    SYNTAX      INTEGER
    ACCESS      read-write
    STATUS      mandatory
    DESCRIPTION
            "When set to 1, initiates a cold reset operation on this
            pBlade. When read, returns 0."

        ::=     { pBladeControlEntry 3 }


pBladeControlWarmReset OBJECT-TYPE
    SYNTAX      INTEGER
    ACCESS      read-write
    STATUS      mandatory
    DESCRIPTION
            "When set to 1, initiates a warm reset operation on this
            pBlade. When read, returns 0."

        ::=     { pBladeControlEntry 4 }


pBladeControlNmi OBJECT-TYPE
    SYNTAX      INTEGER
    ACCESS      read-write
    STATUS      mandatory
    DESCRIPTION
            "When set to 1, initiates a non-maskable interrupt operation on
            this pBlade. When read, returns 0."

        ::=     { pBladeControlEntry 5 }

-- pBlade hardware monitors

pBladeHwMonitorTable OBJECT-TYPE
    SYNTAX      SEQUENCE OF PBladeMonitorEntry
    ACCESS      not-accessible
    STATUS      mandatory
    DESCRIPTION
            "A list of pBlade monitor entries for each pBlade in the PAN."

        ::=     { pBlades 3 }


pBladeMonitorEntry OBJECT-TYPE
    SYNTAX      PBladeMonitorEntry
    ACCESS      not-accessible
    STATUS      mandatory
    DESCRIPTION
            "A list of pBlade monitor entries for each pBlade in the PAN.
            Voltage is measured in Volts, Temperature in degrees Celcius,
            and fan speed in Revolutions Per Minute"


    INDEX       { bladeFrameIndex, pBladeIndex, pBladeHwMonitorIndex }
        ::=     { pBladeHwMonitorTable 1 }


PBladeMonitorEntry ::=
    SEQUENCE {
        pBladeHwMonitorIndex
            INTEGER  (1..2147483647),
        pBladeHwMonitorName
            DisplayString,
        pBladeHwMonitorType
            HardwareMonitorType,
        pBladeHwMonitorValue
            INTEGER,
        pBladeHwMonitorValueDenomonator
            INTEGER,
        pBladeHwMonitorUnits
            DisplayString
    }


pBladeHwMonitorIndex OBJECT-TYPE
    SYNTAX      INTEGER (1..2147483647)
    ACCESS      read-only
    STATUS      mandatory
    DESCRIPTION
            "An integer value uniquely identifying the monitor within the
            pBlade."

        ::=     { pBladeMonitorEntry 1 }


pBladeHwMonitorName OBJECT-TYPE
    SYNTAX      DisplayString
    ACCESS      read-only
    STATUS      mandatory
    DESCRIPTION
            "An String identifying the name of the hardware monitor."

        ::=     { pBladeMonitorEntry 2 }


pBladeHwMonitorType OBJECT-TYPE
    SYNTAX      HardwareMonitorType
    ACCESS      read-only
    STATUS      mandatory
    DESCRIPTION
            "An integer encoding of the monitor type; voltage, temperature, or
            fanspeed."

        ::=     { pBladeMonitorEntry 3 }


pBladeHwMonitorValue OBJECT-TYPE
    SYNTAX      INTEGER
    ACCESS      read-only
    STATUS      mandatory
    DESCRIPTION
            "The integer representation of the current hardware sensor value.
            Voltage values are multiplied by 100 and rounted to convert from
            float to integer.  Thus 0.530 => 53"

        ::=     { pBladeMonitorEntry 4 }


pBladeHwMonitorValueDenomonator OBJECT-TYPE
    SYNTAX      INTEGER
    ACCESS      read-only
    STATUS      mandatory
    DESCRIPTION
            "The integer representation of the denomonator required to convert
            the integer incoding of the sensor value to the float value.
            For voltage sensors, this value is 100, for all other sensors,
            this value is 1."

        ::=     { pBladeMonitorEntry 5 }


pBladeHwMonitorUnits OBJECT-TYPE
    SYNTAX      DisplayString
    ACCESS      read-only
    STATUS      mandatory
    DESCRIPTION
            "Monitor units."

        ::=     { pBladeMonitorEntry 6 }




-- vBlades, virtual machine slices of pBlades

vBladeTable OBJECT-TYPE
    SYNTAX      SEQUENCE OF VBladeEntry
    ACCESS      not-accessible
    STATUS      mandatory
    DESCRIPTION
            "A list of vBlade entries containing information
            for vBlades the Egenera PAN."

        ::=     { pBlades 4 }


vBladeEntry OBJECT-TYPE
    SYNTAX      VBladeEntry
    ACCESS      not-accessible
    STATUS      mandatory
    DESCRIPTION
            "An vBlade entry contains information for Processing
            Blades in the Egenera PAN."

    INDEX       { bladeFrameIndex, pBladeIndex, vBladeIndex }
        ::=     { vBladeTable 1 }


VBladeEntry ::=
    SEQUENCE {
        vBladeIndex
            INTEGER (1..2147483647),
        vBladePBladeIndex
            INTEGER (1..2147483647),
        vBladeFrameIndex
            INTEGER (1..2147483647),
        vBladePServerIndex
            INTEGER (1..2147483647),
        vBladeLPanIndex
            INTEGER (1..2147483647),
        vBladeName
            DisplayString,
        vBladeBladeFrameName
            DisplayString,
        vBladePServerName
            DisplayString,
        vBladeLPanName
            DisplayString,
        vBladeDescription
            DisplayString,
        vBladeHostName
            DisplayString,
        vBladeNumCpus
            INTEGER,
        vBladeCpuSpeed
            INTEGER,
        vBladeCpuModel
            DisplayString,
        vBladeMemorySize
            INTEGER,
        vBladeCache
            INTEGER,
        vBladeArchitecture
            DisplayString,
        vBladeSerialNumber
            DisplayString,
        vBladePartNumber
            DisplayString,
        vBladePowerStatus
            PowerStatusType,
        vBladePowerSupply
            DisplayString,
        vBladeActiveStatus
            TruthValue,
        vBladeAllocationStatus
            TruthValue,
        vBladeHealthStatus
            HealthStatusType,
        vBladeInDebugger
            TruthValue,
        vBladeBootStatus
            DisplayString,
        vBladeUpTime
            TimeTicks,
        vBladePoolIndex
            INTEGER
    }

vBladeIndex OBJECT-TYPE
    SYNTAX      INTEGER (1..2147483647)
    ACCESS      read-only
    STATUS      mandatory
    DESCRIPTION
            "An integer value uniquely identifying the vBlade within
            the pBlade."

        ::=     { vBladeEntry 1 }

vBladePBladeIndex OBJECT-TYPE
    SYNTAX      INTEGER (1..2147483647)
    ACCESS      read-only
    STATUS      mandatory
    DESCRIPTION
            "An integer value uniquely identifying the pBladeIndex value
            of the pBlade hosting this vBlade.  The pBladeIndex is the
            slot of the pBlade."

        ::=     { vBladeEntry 2 }


vBladeFrameIndex OBJECT-TYPE
    SYNTAX      INTEGER (1..2147483647)
    ACCESS      read-only
    STATUS      mandatory
    DESCRIPTION
            "An integer value identifying the bladeFrameIndex value of the
            BladeFrame that hosts this vBlade."

        ::=     { vBladeEntry 3 }


vBladePServerIndex OBJECT-TYPE
    SYNTAX      INTEGER (1..2147483647)
    ACCESS      read-only
    STATUS      mandatory
    DESCRIPTION
            "An integer value identifying the pServerIndex of the pServer
            running on this vBlade, or -1 if the vBlade is not occupied
            by a pServer."

        ::=     { vBladeEntry 4 }


vBladeLPanIndex OBJECT-TYPE
    SYNTAX      INTEGER (1..2147483647)
    ACCESS      read-only
    STATUS      mandatory
    DESCRIPTION
            "An integer value identifying the lPanIndex of the LPAN
            containing the pServer running on this vBlade, or -1 if the
            vBlade is not occupied by a pServer."

        ::=     { vBladeEntry 5 }


vBladeName OBJECT-TYPE
    SYNTAX      DisplayString
    ACCESS      read-only
    STATUS      mandatory
    DESCRIPTION
            "A textual string identifying this vBlade."

        ::=     { vBladeEntry 6 }


vBladeBladeFrameName OBJECT-TYPE
    SYNTAX      DisplayString
    ACCESS      read-only
    STATUS      mandatory
    DESCRIPTION
            "A textual string identifying the BladeFrame containing this
            vBlade."

        ::=     { vBladeEntry 7 }


vBladePServerName OBJECT-TYPE
    SYNTAX      DisplayString
    ACCESS      read-only
    STATUS      mandatory
    DESCRIPTION
            "A textual string identifying the pServer running on this vBlade."

        ::=     { vBladeEntry 8 }

vBladeLPanName OBJECT-TYPE
    SYNTAX      DisplayString
    ACCESS      read-only
    STATUS      mandatory
    DESCRIPTION
            "A textual string identifying the LPAN containing the pServer
            running on this vBlade."

        ::=     { vBladeEntry 9 }


vBladeDescription OBJECT-TYPE
    SYNTAX      DisplayString
    ACCESS      read-only
    STATUS      mandatory
    DESCRIPTION
            "A textual string describing this vBlade."

        ::=     { vBladeEntry 10 }


vBladeHostName OBJECT-TYPE
    SYNTAX      DisplayString
    ACCESS      read-only
    STATUS      mandatory
    DESCRIPTION
            "The hostname of the PServer running on this vBlade."

        ::=     { vBladeEntry 11 }


vBladeNumCpus OBJECT-TYPE
    SYNTAX      INTEGER
    ACCESS      read-only
    STATUS      mandatory
    DESCRIPTION
            "The number of CPUs on the vBlade."

        ::=     { vBladeEntry 12 }


vBladeCpuSpeed OBJECT-TYPE
    SYNTAX      INTEGER
    ACCESS      read-only
    STATUS      mandatory
    DESCRIPTION
            "The speed of the CPUs on the vBlade in Mhz."

        ::=     { vBladeEntry 13 }


vBladeCpuModel OBJECT-TYPE
    SYNTAX      DisplayString
    ACCESS      read-only
    STATUS      mandatory
    DESCRIPTION
            "A textual string representing the CPU model this vBlade."

        ::=     { vBladeEntry 14 }


vBladeMemorySize OBJECT-TYPE
    SYNTAX      INTEGER
    ACCESS      read-only
    STATUS      mandatory
    DESCRIPTION
            "The size of the physical RAM installed on the vBlade,
            in MB."

        ::=     { vBladeEntry 15 }


vBladeCache OBJECT-TYPE
    SYNTAX      INTEGER
    ACCESS      read-only
    STATUS      mandatory
    DESCRIPTION
            "The size of the CPU cache installed on the vBlade,
            in kB."

        ::=     { vBladeEntry 16 }


vBladeArchitecture OBJECT-TYPE
    SYNTAX      DisplayString
    ACCESS      read-only
    STATUS      mandatory
    DESCRIPTION
            "Describes the vBlade hardware architecture."

        ::=     { vBladeEntry 17 }


vBladeSerialNumber OBJECT-TYPE
    SYNTAX      DisplayString
    ACCESS      read-only
    STATUS      mandatory
    DESCRIPTION
            "Describes the serial number of this vBlade."

        ::=     { vBladeEntry 18 }


vBladePartNumber OBJECT-TYPE
    SYNTAX      DisplayString
    ACCESS      read-only
    STATUS      mandatory
    DESCRIPTION
            "Describes the part number of this vBlade."

        ::=     { vBladeEntry 19 }


vBladePowerStatus OBJECT-TYPE
    SYNTAX      PowerStatusType
    ACCESS      read-only
    STATUS      mandatory
    DESCRIPTION
            "The power status of the vBlade."

        ::=     { vBladeEntry 20 }


vBladePowerSupply OBJECT-TYPE
    SYNTAX      DisplayString
    ACCESS      read-only
    STATUS      mandatory
    DESCRIPTION
            "The name of the power supply used by this vBlade."

        ::=     { vBladeEntry 21 }


vBladeActiveStatus OBJECT-TYPE
    SYNTAX      TruthValue
    ACCESS      read-only
    STATUS      mandatory
    DESCRIPTION
            "Indicates whether or not the blade is active."

        ::=     { vBladeEntry 22 }


vBladeAllocationStatus OBJECT-TYPE
    SYNTAX      TruthValue
    ACCESS      read-only
    STATUS      mandatory
    DESCRIPTION
            "Indicates whether or not the blade is allocated."

        ::=     { vBladeEntry 23 }


vBladeHealthStatus OBJECT-TYPE
    SYNTAX      HealthStatusType
    ACCESS      read-only
    STATUS      mandatory
    DESCRIPTION
            "An indication of the health of the BladeFrame."

        ::=     { vBladeEntry 24 }


vBladeInDebugger OBJECT-TYPE
    SYNTAX      TruthValue
    ACCESS      read-only
    STATUS      mandatory
    DESCRIPTION
            "Indicates whether or not the kernel kernel on the vBlade has
            entered the debugger."

        ::=     { vBladeEntry 25 }


vBladeBootStatus OBJECT-TYPE
    SYNTAX      DisplayString
    ACCESS      read-only
    STATUS      mandatory
    DESCRIPTION
            "Indicates the boot status of this vBlade."

        ::=     { vBladeEntry 26 }


vBladeUpTime OBJECT-TYPE
    SYNTAX      TimeTicks
    ACCESS      read-only
    STATUS      mandatory
    DESCRIPTION
            "The amount of time that the vBlade has been up."

        ::=     { vBladeEntry 27 }


vBladePoolIndex OBJECT-TYPE
    SYNTAX      INTEGER (1..2147483647)
    ACCESS      read-only
    STATUS      mandatory
    DESCRIPTION
            "An integer value identifying the poolindex of the pool containing
             the vBlade ."

        ::=     { vBladeEntry 28 }

-- vBlade controls

vBladeControlTable OBJECT-TYPE
    SYNTAX      SEQUENCE OF VBladeControlEntry
    ACCESS      not-accessible
    STATUS      mandatory
    DESCRIPTION
            "A list of vBlade entries containing controls for
            vBlades in the Egenera PAN."

        ::=     { pBlades 5 }

VBladeControlEntry ::=
    SEQUENCE {
        vBladeControlBoot
            INTEGER,
        vBladeControlShutdown
            INTEGER,
        vBladeControlReboot
            INTEGER,
        vBladeControlNmi
            INTEGER
}

vBladeControlEntry OBJECT-TYPE
    SYNTAX      VBladeControlEntry
    ACCESS      not-accessible
    STATUS      mandatory
    DESCRIPTION
            "An vBlade entry contains controls for Processing
            Blades in the Egenera PAN."


    INDEX       { bladeFrameIndex, pBladeIndex, vBladeIndex }
    ::=     { vBladeControlTable 1 }

vBladeControlBoot OBJECT-TYPE
    SYNTAX      INTEGER
    ACCESS      read-write
    STATUS      mandatory
    DESCRIPTION
            "When set to 1, initiates a boot operation on this Processing
            Blade. When read, returns 0."

    ::=     { vBladeControlEntry 1 }


vBladeControlShutdown OBJECT-TYPE
    SYNTAX      INTEGER
    ACCESS      read-write
    STATUS      mandatory
    DESCRIPTION
            "When set to 1, initiates a shutdown operation on this
            vBlade. When read, returns 0."

    ::=     { vBladeControlEntry 2 }


vBladeControlReboot OBJECT-TYPE
    SYNTAX      INTEGER
    ACCESS      read-write
    STATUS      mandatory
    DESCRIPTION
            "When set to 1, initiates a reboot operation on this
            vBlade. When read, returns 0."

    ::=     { vBladeControlEntry 3 }


vBladeControlNmi OBJECT-TYPE
    SYNTAX      INTEGER
    ACCESS      read-write
    STATUS      mandatory
    DESCRIPTION
            "When set to 1, initiates a non-maskable interrupt operation on
            this vBlade. When read, returns 0.  NMI is currently not supported,
            this is a no op."

    ::=     { vBladeControlEntry 4 }


-- pims group

pims OBJECT IDENTIFIER ::= { blades 4 }

-- PIM table
-- The PIM table contains information about PIMs in
-- BladeFrames.

pimTable OBJECT-TYPE
    SYNTAX      SEQUENCE OF PIMEntry
    ACCESS      not-accessible
    STATUS      mandatory
    DESCRIPTION
            "A list of PIM entries containing information
            for PIMs the Egenera PAN."

        ::=     { pims 1 }


pimEntry OBJECT-TYPE
    SYNTAX      PIMEntry
    ACCESS      not-accessible
    STATUS      mandatory
    DESCRIPTION
            "An PIM entry contains information for PIMs in the Egenera PAN."

    INDEX       { bladeFrameIndex, pimIndex }
        ::=     { pimTable 1 }


PIMEntry ::=
    SEQUENCE {
        pimIndex
            INTEGER (1..2147483647),
        pimFrameIndex
            INTEGER (1..2147483647),
        pimName
            DisplayString,
        pimBladeFrameName
            DisplayString,
        pimSerialNumber
            DisplayString,
        pimPartNumber
            DisplayString,
        pimFirmWare
            DisplayString,
        pimSelectedPower
            DisplayString,
        pimOutputPower
            INTEGER,
        pimOutputCurrent
            INTEGER,
        pimPreferredPower
            DisplayString,
        pimManualPowerPreference
            TruthValue,
        pimCurrentLimit
            INTEGER,
        pimPowerLimit
            INTEGER,
        pimInputVoltageA
            DisplayString,
        pimInputVoltageB
            DisplayString,
        pimInputFreq
            INTEGER,
        pimVoltageFailoverTriggerRange
            INTEGER,
        pimSelectedStatus
            TruthValue
    }


pimIndex OBJECT-TYPE
    SYNTAX      INTEGER (1..2147483647)
    ACCESS      read-only
    STATUS      mandatory
    DESCRIPTION
            "An integer value uniquely identifying the PIM within
            the BladeFrame.  This corresponds to the physical location of the
            PIM within the BladeFrame."

        ::=     { pimEntry 1 }


pimFrameIndex OBJECT-TYPE
    SYNTAX      INTEGER
    ACCESS      read-only
    STATUS      mandatory
    DESCRIPTION
            "An integer value identifying the bladeFrameIndex value of the
            BladeFrame that hosts this PIM."

        ::=     { pimEntry 2 }


pimName OBJECT-TYPE
    SYNTAX      DisplayString
    ACCESS      read-only
    STATUS      mandatory
    DESCRIPTION
            "A textual string identifying this PIM."

        ::=     { pimEntry 3 }


pimBladeFrameName OBJECT-TYPE
    SYNTAX      DisplayString
    ACCESS      read-only
    STATUS      mandatory
    DESCRIPTION
            "A textual string identifying the BladeFrame containing this
            PIM."

        ::=     { pimEntry 4 }


pimSerialNumber OBJECT-TYPE
    SYNTAX      DisplayString
    ACCESS      read-only
    STATUS      mandatory
    DESCRIPTION
            "Describes the serial number of this PIM."

        ::=     { pimEntry 5 }


pimPartNumber OBJECT-TYPE
    SYNTAX      DisplayString
    ACCESS      read-only
    STATUS      mandatory
    DESCRIPTION
            "Describes the part number of this PIM."

        ::=     { pimEntry 6 }


pimFirmWare OBJECT-TYPE
    SYNTAX      DisplayString
    ACCESS      read-only
    STATUS      mandatory
    DESCRIPTION
            "The firmware of the PIM."

        ::=     { pimEntry 7 }


pimSelectedPower OBJECT-TYPE
    SYNTAX      DisplayString
    ACCESS      read-only
    STATUS      mandatory
    DESCRIPTION
            "The selected power of the PIM."

        ::=     { pimEntry 8 }


pimOutputPower OBJECT-TYPE
    SYNTAX      INTEGER
    ACCESS      read-only
    STATUS      mandatory
    DESCRIPTION
            "The output power of the PIM."

        ::=     { pimEntry 9 }


pimOutputCurrent OBJECT-TYPE
    SYNTAX      INTEGER
    ACCESS      read-only
    STATUS      mandatory
    DESCRIPTION
            "The outpur current of the PIM."

        ::=     { pimEntry 10 }


pimPreferredPower OBJECT-TYPE
    SYNTAX      DisplayString
    ACCESS      read-only
    STATUS      mandatory
    DESCRIPTION
            "The preferred power of the PIM."

        ::=     { pimEntry 11 }


pimManualPowerPreference OBJECT-TYPE
    SYNTAX      TruthValue
    ACCESS      read-only
    STATUS      mandatory
    DESCRIPTION
            "The manual power preference of the PIM."

        ::=     { pimEntry 12 }


pimCurrentLimit OBJECT-TYPE
    SYNTAX      INTEGER
    ACCESS      read-only
    STATUS      mandatory
    DESCRIPTION
            "The current limit of the PIM."

        ::=     { pimEntry 13 }


pimPowerLimit OBJECT-TYPE
    SYNTAX      INTEGER
    ACCESS      read-only
    STATUS      mandatory
    DESCRIPTION
            "The power limit of the PIM."

        ::=     { pimEntry 14 }


pimInputVoltageA OBJECT-TYPE
    SYNTAX      DisplayString
    ACCESS      read-only
    STATUS      mandatory
    DESCRIPTION
            "The input voltage A of the PIM."

        ::=     { pimEntry 15 }

pimInputVoltageB OBJECT-TYPE
    SYNTAX      DisplayString
    ACCESS      read-only
    STATUS      mandatory
    DESCRIPTION
            "The InputVoltageB of the PIM."

        ::=     { pimEntry 16 }

pimInputFreq OBJECT-TYPE
    SYNTAX      INTEGER
    ACCESS      read-only
    STATUS      mandatory
    DESCRIPTION
            "The input frequency of the PIM."

        ::=     { pimEntry 17 }

pimVoltageFailoverTriggerRange OBJECT-TYPE
    SYNTAX      INTEGER
    ACCESS      read-only
    STATUS      mandatory
    DESCRIPTION
            "This attribute is deprecated.  The trigger value
            is fixed at 85% of PIM maximum voltage"

        ::=     { pimEntry 18 }


pimSelectedStatus OBJECT-TYPE
    SYNTAX      TruthValue
    ACCESS      read-only
    STATUS      mandatory
    DESCRIPTION
            "Indicates whether or not the PIM is selected."

        ::=     { pimEntry 19 }

chassisTable  OBJECT-TYPE
    SYNTAX      SEQUENCE OF ChassisEntry
    ACCESS      not-accessible
    STATUS      mandatory
    DESCRIPTION
            "A list of Chassis entries describing attributes of non-egenera
            hardware chassis contained in the PAN.  This is a sparse table."

        ::=     { bladeFrames 4 }


chassisEntry OBJECT-TYPE
    SYNTAX      ChassisEntry
    ACCESS      not-accessible
    STATUS      mandatory
    DESCRIPTION
            "A Chassis entry contains general information about each
            Chassis in the Egenera PAN."

    INDEX       { bladeFrameIndex, chassisIndex }
        ::=     { chassisTable 1 }


ChassisEntry ::=
    SEQUENCE {
        chassisIndex
            INTEGER (1..2147483647),
        chassisBladeFrameIndex
            INTEGER (1..2147483647),
        chassisName
            DisplayString,
        chassisType
            DisplayString,
        chassisManagementIp
            IpAddress
    }

-- other attributes may be added in the future as needed

chassisIndex OBJECT-TYPE
    SYNTAX      INTEGER (1..2147483647)
    ACCESS      read-only
    STATUS      mandatory
    DESCRIPTION
            "An integer value uniquely identifying the hardware chassis."

        ::=     { chassisEntry 1 }


chassisBladeFrameIndex OBJECT-TYPE
    SYNTAX      INTEGER (1..2147483647)
    ACCESS      read-only
    STATUS      mandatory
    DESCRIPTION
            "An integer value identifying the bladeFrameIndex value of the
            BladeFrame that this chassis contributes to."

        ::=     { chassisEntry 2 }


chassisName OBJECT-TYPE
    SYNTAX      DisplayString
    ACCESS      read-only
    STATUS      mandatory
    DESCRIPTION
            "A textual string identifying the chassis."

        ::=     { chassisEntry 3 }


chassisType OBJECT-TYPE
    SYNTAX      DisplayString
    ACCESS      read-only
    STATUS      mandatory
    DESCRIPTION
            "A textual string identifying the type chassis."

        ::=     { chassisEntry 4 }


chassisManagementIp OBJECT-TYPE
    SYNTAX      IpAddress
    ACCESS      read-only
    STATUS      mandatory
    DESCRIPTION
            "The management IP address of the chassis."

        ::=     { chassisEntry 5 }




devices   OBJECT IDENTIFIER ::= { management 3 }

-- cBlade CD-ROMs connected to the PAN

cdroms    OBJECT IDENTIFIER ::= { devices 1 }


cdromTable   OBJECT-TYPE
    SYNTAX      SEQUENCE OF CDRomEntry
    ACCESS      not-accessible
    STATUS      mandatory
    DESCRIPTION
            "A list of cdrom entries containing information about each
            cdrom allocated to this LPAN."

        ::=     { cdroms 1 }


cdromEntry OBJECT-TYPE
    SYNTAX      CDRomEntry
    ACCESS      not-accessible
    STATUS      mandatory
    DESCRIPTION
            "Information specific to each cdrom in the PAN, or allocated to
            the LPAN if LPAN agent."

    INDEX       { cdromBladeFrameIndex, cdromCBladeIndex,
                  IMPLIED cdromIdOctets }
        ::=     { cdromTable 1 }

CDRomEntry ::=
    SEQUENCE {
        cdromIdOctets
            OCTET STRING (SIZE(4)),
        cdromCBladeIndex
            INTEGER (1..2147483647),
        cdromBladeFrameIndex
            INTEGER (1..2147483647),
        cdromId
            DisplayString,
        cdromLPANIndex
            INTEGER,
        cdromMajor
            INTEGER,
        cdromMinor
            INTEGER,
        cdromVendor
            DisplayString,
        cdromModel
            DisplayString,
        cdromSerialNumber
            DisplayString,
        cdromRev
            DisplayString,
        cdromEnabled
            TruthValue,
        cdromCapacity
            INTEGER
    }


cdromIdOctets OBJECT-TYPE
    SYNTAX      OCTET STRING (SIZE(4))
    ACCESS      read-only
    STATUS      mandatory
    DESCRIPTION
            "A sequence of 4 bytes encoding the values of HBA number,
            BUS ID, target device ID and LUN."

        ::=     { cdromEntry 1 }

cdromCBladeIndex OBJECT-TYPE
    SYNTAX      INTEGER (1..2147483647)
    ACCESS      read-only
    STATUS      mandatory
    DESCRIPTION
            "The cBladeIndex value of the cBlade hosting this CD-Rom."

        ::=     { cdromEntry 2 }

cdromBladeFrameIndex OBJECT-TYPE
    SYNTAX      INTEGER (1..2147483647)
    ACCESS      read-only
    STATUS      mandatory
    DESCRIPTION
            "The bladeFrameIndex value of the BladeFrame hosting this CD-Rom."

        ::=     { cdromEntry 3 }

cdromId OBJECT-TYPE
    SYNTAX      DisplayString
    ACCESS      read-only
    STATUS      mandatory
    DESCRIPTION
            "A human readable string consisting of dot separated values
            of HBA number, BUS ID, target device ID and LUN."

        ::=     { cdromEntry 4 }

cdromLPANIndex OBJECT-TYPE
    SYNTAX      INTEGER
    ACCESS      read-only
    STATUS      mandatory
    DESCRIPTION
            "The lpanIndex value of the LPAN this cdrom is allocated to, or
            0 if not allocated."

        ::=     { cdromEntry 5}


cdromMajor OBJECT-TYPE
    SYNTAX      INTEGER
    ACCESS      read-only
    STATUS      mandatory
    DESCRIPTION
            "The minor number of this CD-Rom device."

        ::=     { cdromEntry 6 }


cdromMinor OBJECT-TYPE
    SYNTAX      INTEGER
    ACCESS      read-only
    STATUS      mandatory
    DESCRIPTION
            "The minor number of this CD-Rom device."

        ::=     { cdromEntry 7 }

cdromVendor OBJECT-TYPE
    SYNTAX      DisplayString
    ACCESS      read-only
    STATUS      mandatory
    DESCRIPTION
            "A textual string identifying the cdrom vendor."

        ::=     { cdromEntry 8 }


cdromModel OBJECT-TYPE
    SYNTAX      DisplayString
    ACCESS      read-only
    STATUS      mandatory
    DESCRIPTION
            "A textual string identifying the cdrom model."

        ::=     { cdromEntry 9 }


cdromSerialNumber OBJECT-TYPE
    SYNTAX      DisplayString
    ACCESS      read-only
    STATUS      mandatory
    DESCRIPTION
            "A textual string providing the serial number of the cdrom."

        ::=     { cdromEntry 10 }


cdromRev OBJECT-TYPE
    SYNTAX      DisplayString
    ACCESS      read-only
    STATUS      mandatory
    DESCRIPTION
            "The firmare revision used by this CD-ROM."

        ::=     { cdromEntry 11 }


cdromEnabled OBJECT-TYPE
    SYNTAX      TruthValue
    ACCESS      read-only
    STATUS      mandatory
    DESCRIPTION
            "Indicates wether the cdrom is enabled (true), or disabled
            (false)."

        ::=     { cdromEntry 12 }


cdromCapacity OBJECT-TYPE
    SYNTAX      INTEGER
    ACCESS      read-only
    STATUS      mandatory
    DESCRIPTION
            "The storage capacity of the cdrom in megabytes."

        ::=     { cdromEntry 13 }



-- CD-ROM LPAN allocations

cdromLPanAllocTable  OBJECT-TYPE
    SYNTAX      SEQUENCE OF CDRomLPanAllocEntry
    ACCESS      not-accessible
    STATUS      mandatory
    DESCRIPTION
            "A list of LPAN indicies identifying LPAN cdrom allocations."

        ::=     { cdroms 2 }


cdromLPanAllocEntry OBJECT-TYPE
    SYNTAX      CDRomLPanAllocEntry
    ACCESS      not-accessible
    STATUS      mandatory
    DESCRIPTION
            "Information specific to each pServer cdrom allocation."

    INDEX       { lPanIndex, cdromBladeFrameIndex,
                  cdromCBladeIndex, IMPLIED cdromIdOctets }
        ::=     { cdromLPanAllocTable 1 }


CDRomLPanAllocEntry ::=
    SEQUENCE {
        cdromLPanAllocIdOctets
            OCTET STRING (SIZE(4)),
        cdromLPanAllocBladeFrameIndex
            INTEGER,
        cdromLPanAllocCBladeIndex
            INTEGER,
        cdromLPanAllocLPanIndex
            INTEGER,
        cdromLPanAllocEnabled
            TruthValue
    }


cdromLPanAllocIdOctets OBJECT-TYPE
    SYNTAX      OCTET STRING (SIZE(4))
    ACCESS      read-only
    STATUS      mandatory
    DESCRIPTION
            "A sequence of 4 bytes encoding the values of HBA number,
            BUS ID, target device ID and LUN of the cdrom."

        ::=     { cdromLPanAllocEntry 1 }


cdromLPanAllocBladeFrameIndex OBJECT-TYPE
    SYNTAX      INTEGER
    ACCESS      read-only
    STATUS      mandatory
    DESCRIPTION
            "The bladeFrameIndex value of the BladeFrame hosting this
            CD-ROM."

        ::=     { cdromLPanAllocEntry 2 }

cdromLPanAllocCBladeIndex OBJECT-TYPE
    SYNTAX      INTEGER
    ACCESS      read-only
    STATUS      mandatory
    DESCRIPTION
            "The cBladeIndex value of the cBlade hosting this
            CD-ROM."

        ::=     { cdromLPanAllocEntry 3 }


cdromLPanAllocLPanIndex OBJECT-TYPE
    SYNTAX      INTEGER
    ACCESS      read-only
    STATUS      mandatory
    DESCRIPTION
            "The lpanIndex of the LPAN hosting the LPAN this cdrom is
            allocated to."

        ::=     { cdromLPanAllocEntry 4 }


cdromLPanAllocEnabled OBJECT-TYPE
    SYNTAX      TruthValue
    ACCESS      read-only
    STATUS      mandatory
    DESCRIPTION
            "Indicates whether the LPAN cdrom mapping is currently
            enabled."

        ::=     { cdromLPanAllocEntry 5 }



cdromPSvrAllocTable   OBJECT-TYPE
    SYNTAX      SEQUENCE OF CDRomPSvrAllocEntry
    ACCESS      not-accessible
    STATUS      mandatory
    DESCRIPTION
            "A list of LPAN, pServer index pairs identifying pServer cdrom
            allocations."

        ::=     { cdroms 3 }


cdromPSvrAllocEntry OBJECT-TYPE
    SYNTAX      CDRomPSvrAllocEntry
    ACCESS      not-accessible
    STATUS      mandatory
    DESCRIPTION
            "Information specific to each pServer cdrom allocation."

    INDEX       { lPanIndex, pServerIndex, bladeFrameIndex, cBladeIndex,
                  IMPLIED cdromIdOctets }
        ::=     { cdromPSvrAllocTable 1 }

CDRomPSvrAllocEntry ::=
    SEQUENCE {
        cdromPSvrAllocIdOctets
            OCTET STRING  (SIZE(4)),
        cdromPSvrAllocCBladeIndex
            INTEGER,
        cdromPSvrAllocBladeFrameIndex
            INTEGER,
        cdromPSvrAllocpSvrIndex
            INTEGER,
        cdromPSvrAllocLPanIndex
            INTEGER
    }



cdromPSvrAllocIdOctets OBJECT-TYPE
    SYNTAX      OCTET STRING (SIZE(4))
    ACCESS      read-only
    STATUS      mandatory
    DESCRIPTION
            "A sequence of 4 bytes encoding the values of HBA number,
            BUS ID, target device ID and LUN of the cdrom."

        ::=     { cdromPSvrAllocEntry 1 }


cdromPSvrAllocBladeFrameIndex OBJECT-TYPE
    SYNTAX      INTEGER
    ACCESS      read-only
    STATUS      mandatory
    DESCRIPTION
            "The bladeFrameIndex value of the BladeFrame hosting this
            CD-ROM."

        ::=     { cdromPSvrAllocEntry 2 }

cdromPSvrAllocCBladeIndex OBJECT-TYPE
    SYNTAX      INTEGER
    ACCESS      read-only
    STATUS      mandatory
    DESCRIPTION
            "The cBladeIndex value of the cBlade hosting this
            CD-ROM."

        ::=     { cdromPSvrAllocEntry 3 }


cdromPSvrAllocLPanIndex OBJECT-TYPE
    SYNTAX      INTEGER
    ACCESS      read-only
    STATUS      mandatory
    DESCRIPTION
            "The lpanIndex of the LPAN hosting the pServer this cdrom is
            allocated to."

        ::=     { cdromPSvrAllocEntry 4 }

cdromPSvrAllocpSvrIndex OBJECT-TYPE
    SYNTAX      INTEGER
    ACCESS      read-only
    STATUS      mandatory
    DESCRIPTION
            "The lpanIndex of the pServer hosting the pServer this cdrom is
            allocated to."

        ::=     { cdromPSvrAllocEntry 5 }



-- disks connected to the PAN

disks     OBJECT IDENTIFIER ::= { devices 2 }

diskTable   OBJECT-TYPE
    SYNTAX      SEQUENCE OF DiskEntry
    ACCESS      not-accessible
    STATUS      mandatory
    DESCRIPTION
            "A list of disk entries containing information about each
            disk allocated to this LPAN."

        ::=     { disks 1 }


diskEntry OBJECT-TYPE
    SYNTAX      DiskEntry
    ACCESS      not-accessible
    STATUS      mandatory
    DESCRIPTION
            "Information specific to each disk in the PAN, or allocated to
            the LPAN if LPAN agent."

    INDEX       { IMPLIED diskIdOctets }
        ::=     { diskTable 1 }

DiskEntry ::=
    SEQUENCE {
        diskIdOctets
            OCTET STRING (SIZE(4)),
        diskId
            DisplayString,
        diskMajor
            INTEGER,
        diskMinor
            INTEGER,
        diskVendor
            DisplayString,
        diskModel
            DisplayString,
        diskSerialNumber
            DisplayString,
        diskRev
            DisplayString,
        diskEnabled
            TruthValue,
        diskCapacity
            INTEGER,
        diskDescription
            DisplayString
    }


diskIdOctets OBJECT-TYPE
    SYNTAX      OCTET STRING (SIZE(4))
    ACCESS      read-only
    STATUS      mandatory
    DESCRIPTION
            "A sequence of 4 bytes encoding the values of HBA number,
            BUS ID, target device ID and LUN."

        ::=     { diskEntry 1}


diskId OBJECT-TYPE
    SYNTAX      DisplayString
    ACCESS      read-only
    STATUS      mandatory
    DESCRIPTION
            "A human readable string consisting of dot separated values
            of HBA number, BUS ID, target device ID and LUN."

        ::=     { diskEntry 2}


diskMajor OBJECT-TYPE
    SYNTAX      INTEGER
    ACCESS      read-only
    STATUS      mandatory
    DESCRIPTION
            "The major number of this disk device.  This object is deprecated
            and will be removed in future releases."

        ::=     { diskEntry 3 }


diskMinor OBJECT-TYPE
    SYNTAX      INTEGER
    ACCESS      read-only
    STATUS      mandatory
    DESCRIPTION
            "The minor number of this disk device.  This object is deprectated
            and will be removed in future releases"

        ::=     { diskEntry 4 }


diskVendor OBJECT-TYPE
    SYNTAX      DisplayString
    ACCESS      read-only
    STATUS      mandatory
    DESCRIPTION
            "A textual string identifying the disk vendor."

        ::=     { diskEntry 5 }


diskModel OBJECT-TYPE
    SYNTAX      DisplayString
    ACCESS      read-only
    STATUS      mandatory
    DESCRIPTION
            "A textual string identifying the disk model."

        ::=     { diskEntry 6 }


diskSerialNumber OBJECT-TYPE
    SYNTAX      DisplayString
    ACCESS      read-only
    STATUS      mandatory
    DESCRIPTION
            "A textual string providing the serial number of the disk"

        ::=     { diskEntry 7 }


diskRev OBJECT-TYPE
    SYNTAX      DisplayString
    ACCESS      read-only
    STATUS      mandatory
    DESCRIPTION
            "The firmare revision used by this disk."

        ::=     { diskEntry 8 }


diskEnabled OBJECT-TYPE
    SYNTAX      TruthValue
    ACCESS      read-only
    STATUS      mandatory
    DESCRIPTION
            "Indicates wether the disk is enabled (true), or disabled
            (false)."

        ::=     { diskEntry 9 }


diskCapacity OBJECT-TYPE
    SYNTAX      INTEGER
    ACCESS      read-only
    STATUS      mandatory
    DESCRIPTION
            "The storage capacity of the disk in megabytes."

        ::=     { diskEntry 10 }


diskDescription OBJECT-TYPE
    SYNTAX      DisplayString
    ACCESS      read-only
    STATUS      mandatory
    DESCRIPTION
            "Disk description string."

        ::=     { diskEntry 11 }


-- LPAN disk allocations

diskLPanAllocTable  OBJECT-TYPE
    SYNTAX      SEQUENCE OF DiskLPanAllocEntry
    ACCESS      not-accessible
    STATUS      mandatory
    DESCRIPTION
            "A list of LPAN indicies identifying LPAN disk allocations."

        ::=     { disks 2 }


diskLPanAllocEntry OBJECT-TYPE
    SYNTAX      DiskLPanAllocEntry
    ACCESS      not-accessible
    STATUS      mandatory
    DESCRIPTION
            "Information specific to each LPAN disk allocation."

    INDEX       { lPanIndex, IMPLIED diskIdOctets }
        ::=     { diskLPanAllocTable 1 }


DiskLPanAllocEntry ::=
    SEQUENCE {
        diskLPanAllocIdOctets
            OCTET STRING (SIZE(4)),
        diskLPanAllocLPanIndex
            INTEGER,
        diskLPanAllocEnabled
            TruthValue
    }


diskLPanAllocIdOctets OBJECT-TYPE
    SYNTAX      OCTET STRING (SIZE(4))
    ACCESS      read-only
    STATUS      mandatory
    DESCRIPTION
            "A sequence of 4 bytes encoding the values of HBA number,
            BUS ID, target device ID and LUN of the disk."

        ::=     { diskLPanAllocEntry 1 }


diskLPanAllocLPanIndex OBJECT-TYPE
    SYNTAX      INTEGER
    ACCESS      read-only
    STATUS      mandatory
    DESCRIPTION
            "The lpanIndex of the LPAN hosting the LPAN this disk is
            allocated to."

        ::=     { diskLPanAllocEntry 2 }

diskLPanAllocEnabled OBJECT-TYPE
    SYNTAX      TruthValue
    ACCESS      read-only
    STATUS      mandatory
    DESCRIPTION
            "Indicates whether the disk is currently enabled within the LPAN."

        ::=     { diskLPanAllocEntry 3 }


-- pServer disk allocations

-- in this context, diskIdOctets is a 4 byte OCTET STRING encoding of
-- the disk's HBA number, BUS ID, target device ID, and LUN values.
--
-- diskNameOctets is the OCTET STRING encoding of the asscii codes
-- comprising the name of the device special file that the disk is
-- mapped to.

diskPSvrAllocTable   OBJECT-TYPE
    SYNTAX      SEQUENCE OF DiskPSvrAllocEntry
    ACCESS      not-accessible
    STATUS      mandatory
    DESCRIPTION
            "A list of LPAN, pServer index pairs identifying pServer disk
            allocations."

        ::=     { disks 3 }


diskPSvrAllocEntry OBJECT-TYPE
    SYNTAX      DiskPSvrAllocEntry
    ACCESS      not-accessible
    STATUS      mandatory
    DESCRIPTION
            "Information specific to each pServer disk allocation."

    INDEX       { lPanIndex, pServerIndex, IMPLIED diskIdOctets }
        ::=     { diskPSvrAllocTable 1 }

DiskPSvrAllocEntry ::=
    SEQUENCE {
        diskPSvrAllocIdOctets
            OCTET STRING (SIZE(4)),
        diskPSvrAllocPSvrIndex
            INTEGER,
        diskPSvrAllocLPanIndex
            INTEGER
    }



diskPSvrAllocIdOctets OBJECT-TYPE
    SYNTAX      OCTET STRING (SIZE(4))
    ACCESS      read-only
    STATUS      mandatory
    DESCRIPTION
            "A sequence of 4 bytes encoding the values of HBA number,
            BUS ID, target device ID and LUN of the disk."

        ::=     { diskPSvrAllocEntry 1 }


diskPSvrAllocPSvrIndex OBJECT-TYPE
    SYNTAX      INTEGER
    ACCESS      read-only
    STATUS      mandatory
    DESCRIPTION
            "The lpanIndex of the pServer hosting the pServer this disk is
            allocated to."

        ::=     { diskPSvrAllocEntry 2 }


diskPSvrAllocLPanIndex OBJECT-TYPE
    SYNTAX      INTEGER
    ACCESS      read-only
    STATUS      mandatory
    DESCRIPTION
            "The lpanIndex of the LPAN hosting the pServer this disk is
            allocated to."

        ::=     { diskPSvrAllocEntry 3 }



-- tapes connected to the PAN
tapes OBJECT IDENTIFIER ::= { devices 5 }



tapeTable   OBJECT-TYPE
    SYNTAX      SEQUENCE OF TapeEntry
    ACCESS      not-accessible
    STATUS      mandatory
    DESCRIPTION
            "A list of tape entries containing information about each
            tape allocated to this LPAN."

        ::=     { tapes 1 }


tapeEntry OBJECT-TYPE
    SYNTAX      TapeEntry
    ACCESS      not-accessible
    STATUS      mandatory
    DESCRIPTION
            "Information specific to each tape in the PAN, or allocated to
            the LPAN if LPAN agent."

    INDEX       { IMPLIED tapeIdOctets }
        ::=     { tapeTable 1 }

TapeEntry ::=
    SEQUENCE {
        tapeIdOctets
            OCTET STRING (SIZE(4)),
        tapeId
            DisplayString,
        tapeMajor
            INTEGER,
        tapeMinor
            INTEGER,
        tapeVendor
            DisplayString,
        tapeModel
            DisplayString,
        tapeSerialNumber
            DisplayString,
        tapeRev
            DisplayString,
        tapeEnabled
            TruthValue
    }


tapeIdOctets OBJECT-TYPE
    SYNTAX      OCTET STRING (SIZE(4))
    ACCESS      read-only
    STATUS      mandatory
    DESCRIPTION
            "A sequence of 4 bytes encoding the values of HBA number,
            BUS ID, target device ID and LUN."

        ::=     { tapeEntry 1}


tapeId OBJECT-TYPE
    SYNTAX      DisplayString
    ACCESS      read-only
    STATUS      mandatory
    DESCRIPTION
            "A human readable string consisting of dot separated values
            of HBA number, BUS ID, target device ID and LUN."

        ::=     { tapeEntry 2}


tapeMajor OBJECT-TYPE
    SYNTAX      INTEGER
    ACCESS      read-only
    STATUS      mandatory
    DESCRIPTION
            "The major number of this tape device."

        ::=     { tapeEntry 3 }


tapeMinor OBJECT-TYPE
    SYNTAX      INTEGER
    ACCESS      read-only
    STATUS      mandatory
    DESCRIPTION
            "The minor number of this tape device."

        ::=     { tapeEntry 4 }


tapeVendor OBJECT-TYPE
    SYNTAX      DisplayString
    ACCESS      read-only
    STATUS      mandatory
    DESCRIPTION
            "A textual string identifying the tape vendor."

        ::=     { tapeEntry 5 }


tapeModel OBJECT-TYPE
    SYNTAX      DisplayString
    ACCESS      read-only
    STATUS      mandatory
    DESCRIPTION
            "A textual string identifying the tape model."

        ::=     { tapeEntry 6 }


tapeSerialNumber OBJECT-TYPE
    SYNTAX      DisplayString
    ACCESS      read-only
    STATUS      mandatory
    DESCRIPTION
            "A textual string providing the serial number of the tape"

        ::=     { tapeEntry 7 }


tapeRev OBJECT-TYPE
    SYNTAX      DisplayString
    ACCESS      read-only
    STATUS      mandatory
    DESCRIPTION
            "The firmare revision used by this tape."

        ::=     { tapeEntry 8 }


tapeEnabled OBJECT-TYPE
    SYNTAX      TruthValue
    ACCESS      read-only
    STATUS      mandatory
    DESCRIPTION
            "Indicates wether the tape is enabled (true), or disabled
            (false)."

        ::=     { tapeEntry 9 }


-- LPAN tape allocations

tapeLPanAllocTable  OBJECT-TYPE
    SYNTAX      SEQUENCE OF TapeLPanAllocEntry
    ACCESS      not-accessible
    STATUS      mandatory
    DESCRIPTION
            "A list of LPAN indicies identifying LPAN tape allocations."

        ::=     { tapes 2 }


tapeLPanAllocEntry OBJECT-TYPE
    SYNTAX      TapeLPanAllocEntry
    ACCESS      not-accessible
    STATUS      mandatory
    DESCRIPTION
            "Information specific to each LPAN tape allocation."

    INDEX       { lPanIndex, IMPLIED tapeIdOctets }
        ::=     { tapeLPanAllocTable 1 }


TapeLPanAllocEntry ::=
    SEQUENCE {
        tapeLPanAllocIdOctets
            OCTET STRING (SIZE(4)),
        tapeLPanAllocLPanIndex
            INTEGER,
        tapeLPanAllocEnabled
            TruthValue
    }


tapeLPanAllocIdOctets OBJECT-TYPE
    SYNTAX      OCTET STRING (SIZE(4))
    ACCESS      read-only
    STATUS      mandatory
    DESCRIPTION
            "A sequence of 4 bytes encoding the values of HBA number,
            BUS ID, target device ID and LUN of the tape."

        ::=     { tapeLPanAllocEntry 1 }


tapeLPanAllocLPanIndex OBJECT-TYPE
    SYNTAX      INTEGER
    ACCESS      read-only
    STATUS      mandatory
    DESCRIPTION
            "The lpanIndex of the LPAN hosting the LPAN this tape is
            allocated to."

        ::=     { tapeLPanAllocEntry 2 }

tapeLPanAllocEnabled OBJECT-TYPE
    SYNTAX      TruthValue
    ACCESS      read-only
    STATUS      mandatory
    DESCRIPTION
            "Indicates whether the tape is currently enabled within the LPAN."

        ::=     { tapeLPanAllocEntry 3 }


-- pServer tape allocations

-- in this context, tapeIdOctets is a 4 byte OCTET STRING encoding of
-- the tape's HBA number, BUS ID, target device ID, and LUN values.
--
-- tapeNameOctets is the OCTET STRING encoding of the asscii codes
-- comprising the name of the device special file that the tape is
-- mapped to.

tapePSvrAllocTable   OBJECT-TYPE
    SYNTAX      SEQUENCE OF TapePSvrAllocEntry
    ACCESS      not-accessible
    STATUS      mandatory
    DESCRIPTION
            "A list of LPAN, pServer index pairs identifying pServer tape
            allocations."

        ::=     { tapes 3 }


tapePSvrAllocEntry OBJECT-TYPE
    SYNTAX      TapePSvrAllocEntry
    ACCESS      not-accessible
    STATUS      mandatory
    DESCRIPTION
            "Information specific to each pServer tape allocation."

    INDEX       { lPanIndex, pServerIndex, IMPLIED tapeIdOctets }
        ::=     { tapePSvrAllocTable 1 }

TapePSvrAllocEntry ::=
    SEQUENCE {
        tapePSvrAllocIdOctets
            OCTET STRING (SIZE(4)),
        tapePSvrAllocPSvrIndex
            INTEGER,
        tapePSvrAllocLPanIndex
            INTEGER
    }



tapePSvrAllocIdOctets OBJECT-TYPE
    SYNTAX      OCTET STRING (SIZE(4))
    ACCESS      read-only
    STATUS      mandatory
    DESCRIPTION
            "A sequence of 4 bytes encoding the values of HBA number,
            BUS ID, target device ID and LUN of the tape."

        ::=     { tapePSvrAllocEntry 1 }


tapePSvrAllocPSvrIndex OBJECT-TYPE
    SYNTAX      INTEGER
    ACCESS      read-only
    STATUS      mandatory
    DESCRIPTION
            "The lpanIndex of the pServer hosting the pServer this tape is
            allocated to."

        ::=     { tapePSvrAllocEntry 2 }


tapePSvrAllocLPanIndex OBJECT-TYPE
    SYNTAX      INTEGER
    ACCESS      read-only
    STATUS      mandatory
    DESCRIPTION
            "The lpanIndex of the LPAN hosting the pServer this tape is
            allocated to."

        ::=     { tapePSvrAllocEntry 3 }




rEths OBJECT IDENTIFIER ::= { devices 3 }

LoadBalanceType ::= INTEGER {
    pair(1),        -- (default) packets are transmitted on the same cBlade
                    --      that is receiving packets.
    inverse(2),     -- packets are transmitted on the failover partner not currently
                    --      enabled
    balance(3),     -- packets are transmitted via either cBlade. With this option, a
                    --      pBlade attempts to load-balance between both cBlades.
                    --      NOTE: Certain external switches may not allow this
                    --              configuration.
    undefined(999)
}

REthStateType ::= INTEGER {
        redundant(1),       -- both eths are not failed
        not-redundant(2),   -- one of the two eths is known to be failed
        degraded(3),        -- one of the two eths is known to be failed,
                            -- and the other is unknown
        failed(4),          -- both eths are known to be failed
        unknown(999)
}

rEthTable   OBJECT-TYPE
    SYNTAX      SEQUENCE OF REthEntry
    ACCESS      not-accessible
    STATUS      mandatory
    DESCRIPTION
            "A list of rEth entries containing information about each
            redundant Ethernet (rEth) in the PAN.  A rEth is a pair of
            Ethernet Network Interface Cards (NICs), one on each cBlade,
            with the same configuration and external connectivity.  A rEth
            provides  redundant load-balancing and failover capability for
            BladeFrame network connectivity.

           Egenera rEth Naming Conventions

           ethx@bladeframename/cn
                  Reference  to a cBlade Network Interface Card (NIC).
                  BladeFrame naming conventions require you to use a '/'
                  between the BladeFrame name and cBlade number. For example
                  eth1 on cBlade 2 on the BladeFrame named Egenera, would be
                  referred  to as 'eth1@Egenera/c2'."

        ::=     { rEths 1 }


rEthEntry OBJECT-TYPE
    SYNTAX      REthEntry
    ACCESS      not-accessible
    STATUS      mandatory
    DESCRIPTION
            "Information specific to each rEth in the PAN."

    INDEX       { rEthIndex }
        ::=     { rEthTable 1 }

REthEntry ::=
    SEQUENCE {
        rEthIndex
            INTEGER (1..2147483647),
        rEthName
            DisplayString,
        rEthPrimaryEth
            DisplayString,
        rEthPrimaryEthIndexOid
            OBJECT IDENTIFIER,
        rEthInterface1
            DisplayString,
        rEthInterface1IndexOid
            OBJECT IDENTIFIER,
        rEthInterface2
            DisplayString,
        rEthInterface2IndexOid
            OBJECT IDENTIFIER,
        rEthMACAddressOctets
            PhysAddress,
        rEthMACAddressString
            DisplayString,
        rEthAutoMACAssign
            TruthValue,
        rEthFlowControlOn
            TruthValue,
        rEthLoadBalancePolicy
            LoadBalanceType,
        rEthState
            REthStateType,
        rEthFrameIndex
            INTEGER (1..2147483647),
        rEthMTUSize
            INTEGER (1..2147483647)
    }

rEthIndex OBJECT-TYPE
    SYNTAX      INTEGER (1..2147483647)
    ACCESS      read-only
    STATUS      mandatory
    DESCRIPTION
            "An integer value uniquely identifying the rEth within the PAN"

        ::=     { rEthEntry 1 }

rEthName OBJECT-TYPE
    SYNTAX      DisplayString
    ACCESS      read-only
    STATUS      mandatory
    DESCRIPTION
            "A human readable string uniquely identifying the rEth."

        ::=     { rEthEntry 2 }


rEthPrimaryEth OBJECT-TYPE
    SYNTAX      DisplayString
    ACCESS      read-only
    STATUS      mandatory
    DESCRIPTION
            "Identifies the primary Eth of the Reth."

        ::=     { rEthEntry 3 }


rEthPrimaryEthIndexOid OBJECT-TYPE
    SYNTAX      OBJECT IDENTIFIER
    ACCESS      read-only
    STATUS      mandatory
    DESCRIPTION
            "An encoding of the cBlade Eth BladeFrameIndex, cBladeIndex, and
            cBladeEth index, uniquely identifying the cBlade Eth configured
            as the primary Eth."

        ::=     { rEthEntry 4 }


rEthInterface1 OBJECT-TYPE
    SYNTAX      DisplayString
    ACCESS      read-only
    STATUS      mandatory
    DESCRIPTION
            "Specifies the first cBlade NIC of a rEth."

        ::=     { rEthEntry 5 }


rEthInterface1IndexOid OBJECT-TYPE
    SYNTAX      OBJECT IDENTIFIER
    ACCESS      read-only
    STATUS      mandatory
    DESCRIPTION
            "An encoding of the cBlade Eth BladeFrameIndex, cBladeIndex, and
            cBladeEth index, uniquely identifying the cBlade Eth configured
            as 'interface1'."

        ::=     { rEthEntry 6 }


rEthInterface2 OBJECT-TYPE
    SYNTAX      DisplayString
    ACCESS      read-only
    STATUS      mandatory
    DESCRIPTION
            "Specifies the second cBlade NIC of a rEth."

        ::=     { rEthEntry 7 }


rEthInterface2IndexOid OBJECT-TYPE
    SYNTAX      OBJECT IDENTIFIER
    ACCESS      read-only
    STATUS      mandatory
    DESCRIPTION
            "An encoding of the cBlade Eth BladeFrameIndex, cBladeIndex, and
            cBladeEth index, uniquely identifying the cBlade Eth configured
            as 'interface2'."

        ::=     { rEthEntry 8 }


rEthMACAddressOctets OBJECT-TYPE
    SYNTAX      PhysAddress
    ACCESS      read-only
    STATUS      mandatory
    DESCRIPTION
            "This object is deprecated"

        ::=     { rEthEntry 9 }


rEthMACAddressString OBJECT-TYPE
    SYNTAX      DisplayString
    ACCESS      read-only
    STATUS      mandatory
    DESCRIPTION
            "This object is deprecated"

        ::=     { rEthEntry 10 }


rEthFlowControlOn OBJECT-TYPE
    SYNTAX      TruthValue
    ACCESS      read-only
    STATUS      mandatory
    DESCRIPTION
            "Indicates whether flow-control is currently enabled for this
            rEth."

        ::=     { rEthEntry 11 }


rEthAutoMACAssign OBJECT-TYPE
    SYNTAX      TruthValue
    ACCESS      read-only
    STATUS      mandatory
    DESCRIPTION
            "This object is deprecated"

        ::=     { rEthEntry 12 }


rEthLoadBalancePolicy OBJECT-TYPE
    SYNTAX      LoadBalanceType
    ACCESS      read-only
    STATUS      mandatory
    DESCRIPTION
            "Describes the rEth Load Balancing Policy:
              pair(1)
                (default) packets are transmitted on the same cBlade
                that is receiving packets.
              inverse(2)
                packets are transmitted on the failover partner not currently
                enabled
              balance(3)
                packets are transmitted via either cBlade. With this option, a
                pBlade attempts to load-balance between both cBlades.
                NOTE: Certain external switches may not allow this
                configuration.
              undefined(999)"

        ::=     { rEthEntry 13 }


rEthState OBJECT-TYPE
    SYNTAX      REthStateType
    ACCESS      read-only
    STATUS      mandatory
    DESCRIPTION
            "Describes the current State of the REth:
                redundant(1)
                    both eths are not failed
                not-redundant(2)
                    one of the two eths is known to be failed
                degraded(3)
                    one of the two eths is known to be failed,
                    and the other is unknown
                failed(4)
                    both eths are known to be failed
                unknown(999)"

        ::=     { rEthEntry 14 }

rEthFrameIndex OBJECT-TYPE
    SYNTAX      INTEGER (1..2147483647)
    ACCESS      read-only
    STATUS      mandatory
    DESCRIPTION
            "An integer value uniquely identifying the BladeFrame that hosts
            this rEth.  Prior to PAN Manager 5.0, all rEths belonged to the
            same BladeFrame.  With BladeFarms, we need to identify the
            BladeFrame that hosts each rEth."

        ::=     { rEthEntry 15 }

rEthMTUSize OBJECT-TYPE
    SYNTAX      INTEGER (1..2147483647)
    ACCESS      read-only
    STATUS      mandatory
    DESCRIPTION
            "Defines the MTU size of a rEth."

        ::=     { rEthEntry 16 }


-- Mega REths comprised on REths on multiple Frames in the PAN,
-- provide consistant network access to pServers, so that pServers
-- may failover from a Blade in one Frame to a Blade in another.
megaREths OBJECT IDENTIFIER ::= { devices 6 }

megaREthTable   OBJECT-TYPE
    SYNTAX      SEQUENCE OF MegaREthEntry
    ACCESS      not-accessible
    STATUS      mandatory
    DESCRIPTION
            "A list of MegaREth entries containing information about each
            Mega REth in the PAN.  An MegaREth consists of zero or more REths,
            usually each on a different Frame."

        ::=     { megaREths 1 }


megaREthEntry OBJECT-TYPE
    SYNTAX      MegaREthEntry
    ACCESS      not-accessible
    STATUS      mandatory
    DESCRIPTION
            "Information specific to each rEth in the PAN."

    INDEX       { megaREthIndex }
        ::=     { megaREthTable 1 }

MegaREthEntry ::=
    SEQUENCE {
        megaREthIndex
            INTEGER (1..2147483647),
        megaREthName
            DisplayString
    }

megaREthIndex OBJECT-TYPE
    SYNTAX      INTEGER (1..2147483647)
    ACCESS      read-only
    STATUS      mandatory
    DESCRIPTION
            "An integer value uniquely identifying the MegaREth within the PAN"

        ::=     { megaREthEntry 1 }

megaREthName OBJECT-TYPE
    SYNTAX      DisplayString
    ACCESS      read-only
    STATUS      mandatory
    DESCRIPTION
            "A human readable string uniquely identifying the MegaREth."

        ::=     { megaREthEntry 2 }


-- identify REths belonging to an MegaREth
megaREthMemberTable   OBJECT-TYPE
    SYNTAX      SEQUENCE OF MegaREthMemberEntry
    ACCESS      not-accessible
    STATUS      mandatory
    DESCRIPTION
            "A list of REths belonging to each MegaREth."
        ::=     { megaREths 2 }


megaREthMemberEntry OBJECT-TYPE
    SYNTAX      MegaREthMemberEntry
    ACCESS      not-accessible
    STATUS      mandatory
    DESCRIPTION
            "Information specific to each rEth in the PAN."

    INDEX       { megaREthMemberMegaREthIndex, megaREthMemberREthIndex }
        ::=     { megaREthMemberTable 1 }

MegaREthMemberEntry ::=
    SEQUENCE {
        megaREthMemberMegaREthIndex
            INTEGER (1..2147483647),
        megaREthMemberREthIndex
            INTEGER (1..2147483647),
        megaREthMemberREthName
            DisplayString
    }

megaREthMemberMegaREthIndex OBJECT-TYPE
    SYNTAX      INTEGER (1..2147483647)
    ACCESS      read-only
    STATUS      mandatory
    DESCRIPTION
            "An integer value identifying the megaREthIndex value of the
            MegaREth containing the REth indentified by this entry."

        ::=     { megaREthMemberEntry 1 }

megaREthMemberREthIndex OBJECT-TYPE
    SYNTAX      INTEGER (1..2147483647)
    ACCESS      read-only
    STATUS      mandatory
    DESCRIPTION
            "An integer value identifying the rEthIndex value of the
            REth contained by the MegaREth indentified by this entry."

        ::=     { megaREthMemberEntry 2 }

megaREthMemberREthName OBJECT-TYPE
    SYNTAX      DisplayString
    ACCESS      read-only
    STATUS      mandatory
    DESCRIPTION
            "A human readable string uniquely identifying the REth
            conainted by the MegaREth identified by this entry"

        ::=     { megaREthMemberEntry 3 }




vSwitches OBJECT IDENTIFIER ::= { devices 4 }

vSwitchTable   OBJECT-TYPE
    SYNTAX      SEQUENCE OF VSwitchEntry
    ACCESS      not-accessible
    STATUS      mandatory
    DESCRIPTION
            "A Table of information specific to vSwitches within the PAN.

            vSwitches establish connectivity between pServers and external
            networks or between pServers.

            Internal  Connectivity  -  LPAN Administrators can create Eths
                for pBlade-to-pBlade communication using any vSwitch they
                have permission to access. If two pServers connect to the
                same vSwitch, the two pServers can communicate via IP.

            External Connectivity - BladeFrame architecture only supports
                external network communication through a Redundant Ethernet
                (rEth) configuration. PAN or BladeFrame Administrators can
                only create vSwitches for external connectivity using an
                uplink configured with the 'reth' command. "

        ::=     { vSwitches 1 }


vSwitchEntry OBJECT-TYPE
    SYNTAX      VSwitchEntry
    ACCESS      not-accessible
    STATUS      mandatory
    DESCRIPTION
            "Information specific to each vSwitch in the PAN, or allocated to
            the LPAN if LPAN agent."

    INDEX       { vSwitchIndex }
        ::=     { vSwitchTable 1 }

VSwitchEntry ::=
    SEQUENCE {
        vSwitchIndex
            INTEGER (1..2147483647),
        vSwitchName
            DisplayString,
        vSwitchRedundant
            TruthValue,
        vSwitchExternal
            TruthValue,
        vSwitchRouterIp
            DisplayString,
        vSwitchDHCPProxyIp
            DisplayString,
        vSwitchRethName
            DisplayString,
        vSwitchRethIndex
            INTEGER,
        vSwitchUplinkName
            DisplayString,
        vSwitchUplinkPort
            INTEGER,
        vSwitchVLANId
            INTEGER,
        vSwitchVLANName
            DisplayString,
        vSwitchMRethName
            DisplayString,
        vSwitchMRethIndex
            INTEGER (1..2147483647)
    }


vSwitchIndex OBJECT-TYPE
    SYNTAX      INTEGER (1..2147483647)
    ACCESS      read-only
    STATUS      mandatory
    DESCRIPTION
            "An integer value uniquely identifying this vSwitch"

        ::=     { vSwitchEntry 1 }


vSwitchName OBJECT-TYPE
    SYNTAX      DisplayString
    ACCESS      read-only
    STATUS      mandatory
    DESCRIPTION
            "A human readable string uniquely identifying this switch."

        ::=     { vSwitchEntry 2 }


vSwitchRedundant OBJECT-TYPE
    SYNTAX      TruthValue
    ACCESS      read-only
    STATUS      mandatory
    DESCRIPTION
            "indicates whether or not this vSwitch is configured for
            uplink redundancy."

        ::=     { vSwitchEntry 3 }


vSwitchExternal OBJECT-TYPE
    SYNTAX      TruthValue
    ACCESS      read-only
    STATUS      mandatory
    DESCRIPTION
            "indicates whether or not this vSwitch is configured provide
            external IP connectivity."

        ::=     { vSwitchEntry 4 }


vSwitchRouterIp OBJECT-TYPE
    SYNTAX      DisplayString
    ACCESS      read-only
    STATUS      mandatory
    DESCRIPTION
            "This object is deprecated."

        ::=     { vSwitchEntry 5 }


vSwitchDHCPProxyIp OBJECT-TYPE
    SYNTAX      DisplayString
    ACCESS      read-only
    STATUS      mandatory
    DESCRIPTION
            "This object is deprecated."

        ::=     { vSwitchEntry 6 }


vSwitchRethName OBJECT-TYPE
    SYNTAX      DisplayString
    ACCESS      read-only
    STATUS      mandatory
    DESCRIPTION
            "A textual string identifying the name of the rEth uplink,
            if configured."

        ::=     { vSwitchEntry 7 }

vSwitchRethIndex OBJECT-TYPE
    SYNTAX      INTEGER
    ACCESS      read-only
    STATUS      mandatory
    DESCRIPTION
            "An encoding of the rEthIndex value of the rEth uplink,
            or -1 if none."

        ::=     { vSwitchEntry 8 }


vSwitchUplinkName OBJECT-TYPE
    SYNTAX      DisplayString
    ACCESS      read-only
    STATUS      mandatory
    DESCRIPTION
            "This object is deprecated.  As of release 4.0, uplink names and ports
             are associated with cBlade eths, not vSwitches."

        ::=     { vSwitchEntry 9 }


vSwitchUplinkPort OBJECT-TYPE
    SYNTAX      INTEGER
    ACCESS      read-only
    STATUS      mandatory
    DESCRIPTION
            "This object is deprecated.  As of release 4.0, uplink names and ports
             are associated with cBlade eths, not vSwitches."

        ::=     { vSwitchEntry 10 }


vSwitchVLANId OBJECT-TYPE
    SYNTAX      INTEGER
    ACCESS      read-only
    STATUS      mandatory
    DESCRIPTION
            "specifies a VLAN ID assigned to the uplink port of this vSwitch,
             or -1 for none"

        ::=     { vSwitchEntry 11 }


vSwitchVLANName OBJECT-TYPE
    SYNTAX      DisplayString
    ACCESS      read-only
    STATUS      mandatory
    DESCRIPTION
            "specifies a VLAN Name assigned to the uplink port of this vSwitch."

        ::=     { vSwitchEntry 12 }


vSwitchMRethName OBJECT-TYPE
    SYNTAX      DisplayString
    ACCESS      read-only
    STATUS      mandatory
    DESCRIPTION
            "A textual string identifying the name of the Mega REth uplink,
            if configured."

        ::=     { vSwitchEntry 13 }

vSwitchMRethIndex OBJECT-TYPE
    SYNTAX      INTEGER
    ACCESS      read-only
    STATUS      mandatory
    DESCRIPTION
            "An encoding of the megaREthIndex value of the Mega REth uplink,
            or -1 if none."

        ::=     { vSwitchEntry 14 }



-- vSwitch to LPAN allocations

vSwitchLPanAllocTable  OBJECT-TYPE
    SYNTAX      SEQUENCE OF VSwitchLPanAllocEntry
    ACCESS      not-accessible
    STATUS      mandatory
    DESCRIPTION
            "A list of LPAN indicies identifying LPAN vSwitch allocations."

        ::=     { vSwitches 2 }


vSwitchLPanAllocEntry OBJECT-TYPE
    SYNTAX      VSwitchLPanAllocEntry
    ACCESS      not-accessible
    STATUS      mandatory
    DESCRIPTION
            "Information specific to each LPAN vSwitch allocation."

    INDEX       { lPanIndex, vSwitchIndex }
        ::=     { vSwitchLPanAllocTable 1 }


VSwitchLPanAllocEntry ::=
    SEQUENCE {
        vSwitchLPanAllocVSwitchIndex
             INTEGER,
        vSwitchLPanAllocLPanIndex
            INTEGER
    }


vSwitchLPanAllocVSwitchIndex OBJECT-TYPE
    SYNTAX      INTEGER
    ACCESS      read-only
    STATUS      mandatory
    DESCRIPTION
            "An integer index unquely identifying the vSwitch within the
            LPAN."

        ::=     { vSwitchLPanAllocEntry 1 }


vSwitchLPanAllocLPanIndex OBJECT-TYPE
    SYNTAX      INTEGER
    ACCESS      read-only
    STATUS      mandatory
    DESCRIPTION
            "The lpanIndex of the LPAN hosting the LPAN this vSwitch is
            allocated to."

        ::=     { vSwitchLPanAllocEntry 2 }


-- vSwitch to pServer allocations

vSwitchPSvrAllocTable   OBJECT-TYPE
    SYNTAX      SEQUENCE OF VSwitchPSvrAllocEntry
    ACCESS      not-accessible
    STATUS      mandatory
    DESCRIPTION
            "A list of LPAN, pServer index pairs identifying pServer vSwitch
            allocations."

        ::=     { vSwitches 3 }


vSwitchPSvrAllocEntry OBJECT-TYPE
    SYNTAX      VSwitchPSvrAllocEntry
    ACCESS      not-accessible
    STATUS      mandatory
    DESCRIPTION
            "Information specific to each pServer vSwitch allocation."

    INDEX       { vSwitchIndex, lPanIndex, pServerIndex, pServerEthIndex }
        ::=     { vSwitchPSvrAllocTable 1 }


VSwitchPSvrAllocEntry ::=
    SEQUENCE {
        vSwitchPSvrAllocVSwitchIndex
            INTEGER (1..2147483647),
        vSwitchPSvrAllocLPanIndex
            INTEGER (1..2147483647),
        vSwitchPSvrAllocPSvrIndex
            INTEGER (1..2147483647),
        vSwtichPSvrAllocEthIndex
            INTEGER (1..2147483647)
    }


vSwitchPSvrAllocVSwitchIndex OBJECT-TYPE
    SYNTAX      INTEGER (1..2147483647)
    ACCESS      read-only
    STATUS      mandatory
    DESCRIPTION
            "The vSwitchIndex value of the switch that this allocation
            applies to."

        ::=     { vSwitchPSvrAllocEntry 1 }


vSwitchPSvrAllocLPanIndex OBJECT-TYPE
    SYNTAX      INTEGER (1..2147483647)
    ACCESS      read-only
    STATUS      mandatory
    DESCRIPTION
            "The lpanIndex of the LPAN hosting the pServer this vSwitch is
            allocated to."

        ::=     { vSwitchPSvrAllocEntry 2 }


vSwitchPSvrAllocPSvrIndex OBJECT-TYPE
    SYNTAX      INTEGER (1..2147483647)
    ACCESS      read-only
    STATUS      mandatory
    DESCRIPTION
            "The pServerIndex value of the pServer hosting the pServer this
            vSwitch is allocated to."

        ::=     { vSwitchPSvrAllocEntry 3 }


vSwtichPSvrAllocEthIndex OBJECT-TYPE
    SYNTAX      INTEGER (1..2147483647)
    ACCESS      read-only
    STATUS      mandatory
    DESCRIPTION
            "The pServerEthIndex value of the Eth on the pServer indicated by
            vSwitchPSvrAllocLPanIndex, vSwitchPSvrAllocPSvrIndex that this vSwitch
            is mapped to."

        ::=     { vSwitchPSvrAllocEntry 4 }



-- LPANs group
--   Contains information & controls for logical PANs in the Egenera PAN.


-- LPANs group
--
-- Information about LPANs and LPAN subelements (pServers, applications)

lPans     OBJECT IDENTIFIER ::= { management 4 }


lPanTable OBJECT-TYPE
    SYNTAX      SEQUENCE OF LPanEntry
    ACCESS      not-accessible
    STATUS      mandatory
    DESCRIPTION
            "A list of entries containing information and controls for
            LPANs."
        ::=     { lPans 1 }


lPanEntry OBJECT-TYPE
    SYNTAX      LPanEntry
    ACCESS      not-accessible
    STATUS      mandatory
    DESCRIPTION
            "A LPAN entry contains information and controls for
            LPANs."

    INDEX       { lPanIndex }
        ::=     { lPanTable 1}


LPanEntry ::=
    SEQUENCE {
        lPanIndex
            INTEGER (1..2147483647),
        lPanName
            DisplayString,
        lPanHealthStatus
            HealthStatusType,
        lPanUpTime
            TimeTicks
    }


lPanIndex OBJECT-TYPE
    SYNTAX      INTEGER (1..2147483647)
    ACCESS      read-only
    STATUS      mandatory
    DESCRIPTION
            "An integer value uniquely identifying the LPAN."

        ::=     { lPanEntry 1}


lPanName OBJECT-TYPE
    SYNTAX      DisplayString
    ACCESS      read-only
    STATUS      mandatory
    DESCRIPTION
            "A textual string identifying the LPAN."

        ::=     { lPanEntry 2 }

lPanHealthStatus OBJECT-TYPE
    SYNTAX      HealthStatusType
    ACCESS      read-only
    STATUS      mandatory
    DESCRIPTION
            "An indication of the health of the LPAN."

        ::=     { lPanEntry 3 }


lPanUpTime OBJECT-TYPE
    SYNTAX      TimeTicks
    ACCESS      read-only
    STATUS      mandatory
    DESCRIPTION
            "Deprecated, as of release 4.0, LPANs no longer have a concept
            of uptime."

        ::=     { lPanEntry 4 }


-- LogicalPAN Control Table
-- The table provides controls for logical PANs.

lPanControlTable OBJECT-TYPE
    SYNTAX      SEQUENCE OF LPanControlEntry
    ACCESS      not-accessible
    STATUS      mandatory
    DESCRIPTION
            "A list of LPAN control entries containing controls for
            LPANs in the Egenera PAN."

        ::=     { lPans 2 }


lPanControlEntry OBJECT-TYPE
    SYNTAX      LPanControlEntry
    ACCESS      not-accessible
    STATUS      mandatory
    DESCRIPTION
            "A logical PAN entry contains controls for LPANs in the
            Egenera PAN."

    INDEX       { lPanIndex }
        ::=     { lPanControlTable 1}


LPanControlEntry ::=
    SEQUENCE {
        lPanBoot
            INTEGER,
        lPanReboot
            INTEGER,
        lPanDoShutdown
            INTEGER,
        lPanCheckHealth
            INTEGER,
        lPanUpdate
            INTEGER
    }


lPanBoot OBJECT-TYPE
    SYNTAX      INTEGER
    ACCESS      read-write
    STATUS      mandatory
    DESCRIPTION
            "When set to 1, invokes a boot operation on the LPAN.
            When read, returns 0."

        ::=     { lPanControlEntry 1 }


lPanReboot OBJECT-TYPE
    SYNTAX      INTEGER
    ACCESS      read-write
    STATUS      mandatory
    DESCRIPTION
            "When set to 1, invokes a reboot operation on the LPAN.
            When read, returns 0."

        ::=     { lPanControlEntry 2 }


lPanDoShutdown OBJECT-TYPE
    SYNTAX      INTEGER
    ACCESS      read-write
    STATUS      mandatory
    DESCRIPTION
            "When set to 1, invokes a shutdown operation on the LPAN.
            When read, returns 0."

        ::=     { lPanControlEntry 3 }


lPanCheckHealth OBJECT-TYPE
    SYNTAX      INTEGER
    ACCESS      read-write
    STATUS      mandatory
    DESCRIPTION
            "When set to 1, invokes a checkhealth operation on the Logical
            PAN. When read, returns 0."

        ::=     { lPanControlEntry 4 }


lPanUpdate OBJECT-TYPE
    SYNTAX      INTEGER
    ACCESS      read-write
    STATUS      mandatory
    DESCRIPTION
            "When set to 1, invokes a update operation on the LPAN.
            When read, returns 0."

        ::=     { lPanControlEntry 5 }


-- Pools group
-- Information about Pools(Global Pools and Local Pools)


PoolType ::= INTEGER {
        global(1),
        local(2),
        unknown(999)
    }

pools     OBJECT IDENTIFIER ::= { management 5 }

poolTable OBJECT-TYPE
    SYNTAX      SEQUENCE OF PoolEntry
    ACCESS      not-accessible
    STATUS      mandatory
    DESCRIPTION
            "A list of entries containing information for
             Global Pools and Local Pools."
        ::=     { pools 1 }


poolEntry OBJECT-TYPE
    SYNTAX      PoolEntry
    ACCESS      not-accessible
    STATUS      mandatory
    DESCRIPTION
            "A Pool entry contains information for
            Global Pools and Local Pools."

    INDEX       { poolIndex }
        ::=     { poolTable 1}


PoolEntry ::=
    SEQUENCE {
        poolIndex
            INTEGER (1..2147483647),
        poolName
            DisplayString,
        poolDescription
            DisplayString,
        poolLinkedIndex
            INTEGER,
        poolType
            PoolType,
        poolAvailableBlades
            INTEGER
    }


poolIndex OBJECT-TYPE
    SYNTAX      INTEGER (1..2147483647)
    ACCESS      read-only
    STATUS      mandatory
    DESCRIPTION
            "An integer value uniquely identifying the pool."

        ::=     { poolEntry 1}


poolName OBJECT-TYPE
    SYNTAX      DisplayString
    ACCESS      read-only
    STATUS      mandatory
    DESCRIPTION
            "A textual string identifying the pool."

        ::=     { poolEntry 2 }


poolDescription OBJECT-TYPE
    SYNTAX      DisplayString
    ACCESS      read-only
    STATUS      mandatory
    DESCRIPTION
            "A textual string describing the pool."

        ::=     { poolEntry 3 }


poolLinkedIndex OBJECT-TYPE
    SYNTAX      INTEGER
    ACCESS      read-only
    STATUS      mandatory
    DESCRIPTION
            "For local pools, the poolIndex of the global pool that
            the local pool is linked to, or -1 if not linked.  For
            Global Pools, this value is -1."

        ::=     { poolEntry 4}


poolType OBJECT-TYPE
    SYNTAX      PoolType
    ACCESS      read-only
    STATUS      mandatory
    DESCRIPTION
            "Indicates the type of pool (global or local)."

        ::=     { poolEntry 5}


poolAvailableBlades OBJECT-TYPE
    SYNTAX      INTEGER
    ACCESS      read-only
    STATUS      mandatory
    DESCRIPTION
            "Indicates the number of blades currently available in
            the pool."

        ::=     { poolEntry 6}


-- pServers group
-- Contains information and controls for pServers.  A pServer is the
-- combination of a single pBlade, disk resources, and network
-- resources which provides the capabilities of a conventional server.

pServers        OBJECT IDENTIFIER ::= { lPans 3 }


pServerTable   OBJECT-TYPE
    SYNTAX      SEQUENCE OF PServerEntry
    ACCESS      not-accessible
    STATUS      mandatory
    DESCRIPTION
            "A list of pServer entries containing information about each
            pServer."

        ::=     { pServers 1 }


pServerEntry OBJECT-TYPE
    SYNTAX      PServerEntry
    ACCESS      not-accessible
    STATUS      mandatory
    DESCRIPTION
            "Information regarding each pServer."

    INDEX       { lPanIndex, pServerIndex }
        ::=     { pServerTable 1 }


PServerEntry ::=
    SEQUENCE {
        pServerIndex
            INTEGER (1..2147483647),
        pServerLPanIndex
            INTEGER (1..2147483647),
        pServerBladeIndex
            INTEGER (-1..2147483647),
        pServerBladeFrameIndex
            INTEGER (-1..2147483647),
        pServerName
            DisplayString,
        pServerFullName
            DisplayString,
        pServerDescription
            DisplayString,
        pServerBladeFrameName
            DisplayString,
        pServerPBladeName
            DisplayString,
        pServerLPanName
            DisplayString,
        pServerValidBootDisk
            TruthValue,
        pServerHostname
            DisplayString,
        pServerAgentAvailable
            TruthValue,
        pServerHealthStatus
            HealthStatusType,
        pServerInDebugger
            TruthValue,
        pServerAutoActivate
            TruthValue,
        pServerAutoBoot
            TruthValue,
        pServerActivateOrder
            INTEGER,
        pServerActive
            TruthValue,
        pServerBootStatus
            DisplayString,
        pServerUptime
            TimeTicks,
        pServerFailedOver
            TruthValue,
        pServerOptional
            TruthValue,
        pServerShutdownTimeout
            INTEGER,
        pServerPrimaryPBladeIndex
            INTEGER (-2..2147483647),
        pServerPrimaryPBladeFrameIndex
            INTEGER (-2..2147483647),
        pServerPrimaryPBladeName
            DisplayString,
        pServerFailoverPBladeIndex
            INTEGER (-2..2147483647),
        pServerFailoverPBladeFrameIndex
            INTEGER (-2..2147483647),
        pServerFailoverPBladeName
            DisplayString,
        pServerVBladeIndex
            INTEGER (-2..2147483647)
    }


pServerIndex OBJECT-TYPE
    SYNTAX      INTEGER (1..2147483647)
    ACCESS      read-only
    STATUS      mandatory
    DESCRIPTION
            "An integer value uniquely identifying pServer within Logical
            PAN."

        ::=     { pServerEntry 1 }

pServerLPanIndex OBJECT-TYPE
    SYNTAX      INTEGER (1..2147483647)
    ACCESS      read-only
    STATUS      mandatory
    DESCRIPTION
            "An integer value identifying the lPanIndex value of the
            LPAN that hosts this pServer."

        ::=     { pServerEntry 2 }


pServerBladeIndex OBJECT-TYPE
    SYNTAX      INTEGER (-1..2147483647)
    ACCESS      read-only
    STATUS      mandatory
    DESCRIPTION
            "An integer value identifying the pBladeIndex value of
            the pBlade that currently hosts this pServer, -1 if no
            current pBlade.  See pServerVBladeIndex"

        ::=     { pServerEntry 3 }


pServerBladeFrameIndex OBJECT-TYPE
    SYNTAX      INTEGER (-1..2147483647)
    ACCESS      read-only
    STATUS      mandatory
    DESCRIPTION
            "An integer value identifying the bladeFrameIndex value of the
            BladeFrame that hosts this pServer."

        ::=     { pServerEntry 4 }


pServerName OBJECT-TYPE
    SYNTAX      DisplayString
    ACCESS      read-only
    STATUS      mandatory
    DESCRIPTION
            "A textual string identifying this pServer."

        ::=     { pServerEntry 5 }


pServerFullName OBJECT-TYPE
    SYNTAX      DisplayString
    ACCESS      read-only
    STATUS      mandatory
    DESCRIPTION
            "A textual string fully identifying this pServer and its LPAN."

        ::=     { pServerEntry 6 }


pServerDescription OBJECT-TYPE
    SYNTAX      DisplayString
    ACCESS      read-only
    STATUS      mandatory
    DESCRIPTION
            "A textual string describing this pServer."

        ::=     { pServerEntry 7 }


pServerBladeFrameName OBJECT-TYPE
    SYNTAX      DisplayString
    ACCESS      read-only
    STATUS      mandatory
    DESCRIPTION
            "A textual string identifying the BladeFrame hosting this
            PServer."

        ::=     { pServerEntry 8 }


pServerPBladeName OBJECT-TYPE
    SYNTAX      DisplayString
    ACCESS      read-only
    STATUS      mandatory
    DESCRIPTION
            "A textual string identifying the pBlade currently hosting this
            pServer."

        ::=     { pServerEntry 9 }


pServerLPanName OBJECT-TYPE
    SYNTAX      DisplayString
    ACCESS      read-only
    STATUS      mandatory
    DESCRIPTION
            "A textual string identifying the LPAN containing this pServer."

        ::=     { pServerEntry 10 }


pServerValidBootDisk OBJECT-TYPE
    SYNTAX      TruthValue
    ACCESS      read-only
    STATUS      mandatory
    DESCRIPTION
            "This object is deprecated"

        ::=     { pServerEntry 11 }


pServerHostname OBJECT-TYPE
    SYNTAX      DisplayString
    ACCESS      read-only
    STATUS      mandatory
    DESCRIPTION
            "The hostname of this pServer."

        ::=     { pServerEntry 12 }


pServerAgentAvailable OBJECT-TYPE
    SYNTAX      TruthValue
    ACCESS      read-only
    STATUS      mandatory
    DESCRIPTION
            "Indicates whether the Egenera management agent is running
            on the pBlade hosting this pServer."

        ::=     { pServerEntry 13 }


pServerHealthStatus OBJECT-TYPE
    SYNTAX      HealthStatusType
    ACCESS      read-only
    STATUS      mandatory
    DESCRIPTION
            "Indicates the health of the pServer."

        ::=     { pServerEntry 14 }


pServerInDebugger OBJECT-TYPE
    SYNTAX      TruthValue
    ACCESS      read-only
    STATUS      mandatory
    DESCRIPTION
            "This object is deprecated as of PAN Manager release 4.0.  The
            value may be obtained via the pBlade table."

        ::=     { pServerEntry 15 }


pServerAutoActivate OBJECT-TYPE
    SYNTAX      TruthValue
    ACCESS      read-only
    STATUS      mandatory
    DESCRIPTION
            "This object is deprecated as of PAN Manager release 4.0."

        ::=     { pServerEntry 16 }


pServerAutoBoot OBJECT-TYPE
    SYNTAX      TruthValue
    ACCESS      read-only
    STATUS      mandatory
    DESCRIPTION
            "This object is deprecated as of PAN Manager release 4.0."

        ::=     { pServerEntry 17 }


pServerActivateOrder OBJECT-TYPE
    SYNTAX      INTEGER
    ACCESS      read-only
    STATUS      mandatory
    DESCRIPTION
            "Indicates the order within the LPAN that this pServer is
            activated."

        ::=     { pServerEntry 18 }


pServerActive OBJECT-TYPE
    SYNTAX      TruthValue
    ACCESS      read-only
    STATUS      mandatory
    DESCRIPTION
            "This object is deprecated as of PAN Manager release 4.0."

        ::=     { pServerEntry 19 }


pServerBootStatus OBJECT-TYPE
    SYNTAX      DisplayString
    ACCESS      read-only
    STATUS      mandatory
    DESCRIPTION
            "Describes the boot status"

        ::=     { pServerEntry 20 }


pServerUptime OBJECT-TYPE
    SYNTAX      TimeTicks
    ACCESS      read-only
    STATUS      mandatory
    DESCRIPTION
            "The length of time the pServer has been up in 1/100ths of a
            second."

        ::=     { pServerEntry 21 }


pServerFailedOver OBJECT-TYPE
    SYNTAX      TruthValue
    ACCESS      read-only
    STATUS      mandatory
    DESCRIPTION
            "This object is deprecated as of PAN Manager release 4.0."

        ::=     { pServerEntry 22 }


pServerOptional OBJECT-TYPE
    SYNTAX      TruthValue
    ACCESS      read-only
    STATUS      mandatory
    DESCRIPTION
            "Indicates whether this pServer has been designated as optional."

        ::=     { pServerEntry 23 }


pServerShutdownTimeout OBJECT-TYPE
    SYNTAX      INTEGER
    ACCESS      read-only
    STATUS      mandatory
    DESCRIPTION
            "The amount of time given for the pServer to shutdown before the
            shutdown operation is deemed to have failed."

        ::=     { pServerEntry 24 }


pServerPrimaryPBladeIndex OBJECT-TYPE
    SYNTAX      INTEGER (-2..2147483647)
    ACCESS      read-only
    STATUS      mandatory
    DESCRIPTION
            "The pBladeIndex value of the pServer's configured primary pBlade.
            -1 indicates none, -2 indicates global or local pool."

        ::=     { pServerEntry 25 }


pServerPrimaryPBladeFrameIndex OBJECT-TYPE
    SYNTAX      INTEGER  (-2..2147483647)
    ACCESS      read-only
    STATUS      mandatory
    DESCRIPTION
            "The bladeFrameIndex value of BladeFrame hosting the pServer's
            configured primary pBlade.  -1 indicates none, -2 indicates global
            or local pool."

        ::=     { pServerEntry 26 }


pServerPrimaryPBladeName OBJECT-TYPE
    SYNTAX      DisplayString
    ACCESS      read-only
    STATUS      mandatory
    DESCRIPTION
            "A textual string including the Frame and pBlade name of this
            pServer's configured primary pBlade.  'pool' indicates global
            or local pool."

        ::=     { pServerEntry 27 }


pServerFailoverPBladeIndex OBJECT-TYPE
    SYNTAX      INTEGER (-2..2147483647)
    ACCESS      read-only
    STATUS      mandatory
    DESCRIPTION
            "The pBladeIndex value of the pServer's configured failover pBlade.
            -1 indicates none, -2 indicates global or local pool."

        ::=     { pServerEntry 28 }



pServerFailoverPBladeFrameIndex OBJECT-TYPE
    SYNTAX      INTEGER  (-2..2147483647)
    ACCESS      read-only
    STATUS      mandatory
    DESCRIPTION
            "The bladeFrameIndex value of BladeFrame hosting the pServer's
            configured failover pBlade.  -1 indicates none, -2 indicates global
            or local pool."

        ::=     { pServerEntry 29 }


pServerFailoverPBladeName OBJECT-TYPE
    SYNTAX      DisplayString
    ACCESS      read-only
    STATUS      mandatory
    DESCRIPTION
            "A textual string including the Frame and pBlade name of this
            pServer's configured failover pBlade.  'pool' indicates global
            or local pool."

        ::=     { pServerEntry 30 }

pServerVBladeIndex OBJECT-TYPE
    SYNTAX      INTEGER (-1..2147483647)
    ACCESS      read-only
    STATUS      mandatory
    DESCRIPTION
            "An integer value identifying the vBladeIndex value of
            the vBlade that currently hosts this pServer, -1 if no
            current vBlade, or if the pServer is hosted by a pBlade.
            See pServerBladeIndex"

        ::=     { pServerEntry 31 }




-- pServerStatsTable
-- contains runtime statistics for each pServer.  This table is present when
-- the Egenera management agent is running on the pBlade, and statistic
-- collection is enabled.

pServerStatsTable  OBJECT-TYPE
    SYNTAX      SEQUENCE OF PServerStatsEntry
    ACCESS      not-accessible
    STATUS      mandatory
    DESCRIPTION
            "A list of pServer Monitor entries containing runtime statistics
            for pServers."

        ::=     { pServers 2 }


pServerStatsEntry OBJECT-TYPE
    SYNTAX      PServerStatsEntry
    ACCESS      not-accessible
    STATUS      mandatory
    DESCRIPTION
            "A pServer Monitor entry contains runtime statistics for
            pServers."

    INDEX       { lPanIndex, pServerIndex }
        ::=     { pServerStatsTable 1 }


PServerStatsEntry ::=
    SEQUENCE {
        pServerStatsUpTime
            TimeTicks,
        pServerStatsLoadAvg1
            Gauge,
        pServerStatsLoadAvg5
            Gauge,
        pServerStatsLoadAvg15
            Gauge,
        pServerStatsCpuUser
            Counter,
        pServerStatsCpuSystem
            Counter,
        pServerStatsCpuIdle
            Counter,
        pServerStatsLoadScale
            Gauge,
        pServerStatsNumProcs
            Gauge,
        pServerStatsLastPid
            INTEGER,
        pServerStatsContextSwitch
            Counter,
        pServerStatsInterrupt
            Counter,
        pServerStatsMemTotal
            Gauge,
        pServerStatsMemFree
            Gauge,
        pServerStatsSwapTotal
            Gauge,
        pServerStatsSwapFree
            Gauge,
        pServerStatsPageIn
            Counter,
        pServerStatsPageOut
            Counter,
        pServerStatsSwapIn
            Counter,
        pServerStatsSwapOut
            Counter,
        pServerStatsDiskReads
            Counter,
        pServerStatsDiskWrites
            Counter,
        pServerStatsDiskBlkReads
            Counter,
        pServerStatsDiskBlkWrites
            Counter,
        pServerStatsCpuUserNice
            Counter
    }

pServerStatsUpTime OBJECT-TYPE
    SYNTAX      TimeTicks
    ACCESS      read-only
    STATUS      mandatory
    DESCRIPTION
            "The uptime in 1/100ths of a second for this pServer."

        ::=     { pServerStatsEntry 1 }


pServerStatsLoadAvg1 OBJECT-TYPE
    SYNTAX      Gauge
    ACCESS      read-only
    STATUS      mandatory
    DESCRIPTION
            "100 * the average number of jobs in the run queue over the
            previous minute.  Returns 0 for Windows pServers."

        ::=     { pServerStatsEntry 2 }


pServerStatsLoadAvg5 OBJECT-TYPE
    SYNTAX      Gauge
    ACCESS      read-only
    STATUS      mandatory
    DESCRIPTION
            "100 * the average number of jobs in the run queue over the
            previous five minutes.  Returns 0 for Windows pServers."

        ::=     { pServerStatsEntry 3 }


pServerStatsLoadAvg15 OBJECT-TYPE
    SYNTAX      Gauge
    ACCESS      read-only
    STATUS      mandatory
    DESCRIPTION
            "100 * the average number of jobs in the run queue over the
            previous fifteen minutes.  Returns 0 for Windows pServers."

        ::=     { pServerStatsEntry 4 }


pServerStatsCpuUser OBJECT-TYPE
    SYNTAX      Counter
    ACCESS      read-only
    STATUS      mandatory
    DESCRIPTION
            "The number of (1/100)ths of a second that the pServer spent in
            user mode since boot."

        ::=     { pServerStatsEntry 5 }


pServerStatsCpuSystem OBJECT-TYPE
    SYNTAX      Counter
    ACCESS      read-only
    STATUS      mandatory
    DESCRIPTION
            "The number of (1/100)ths of a second that the pServer spent in
            system mode since boot."

        ::=     { pServerStatsEntry 6 }


pServerStatsCpuIdle OBJECT-TYPE
    SYNTAX      Counter
    ACCESS      read-only
    STATUS      mandatory
    DESCRIPTION
            "The number of (1/100)ths of a second that the pServer spent in
            idle mode since boot."

        ::=     { pServerStatsEntry 7 }


pServerStatsLoadScale OBJECT-TYPE
    SYNTAX      Gauge
    ACCESS      read-only
    STATUS      mandatory
    DESCRIPTION
            "The load scale.  Returns 0 for Windows pServers."

        ::=     { pServerStatsEntry 8 }


pServerStatsNumProcs OBJECT-TYPE
    SYNTAX      Gauge
    ACCESS      read-only
    STATUS      mandatory
    DESCRIPTION
            "The number of processes running on the pServer."

        ::=     { pServerStatsEntry 9 }


pServerStatsLastPid OBJECT-TYPE
    SYNTAX      INTEGER
    ACCESS      read-only
    STATUS      mandatory
    DESCRIPTION
            "The highest allocated process ID on the pServer.  Returns 0
            for Windows pServers."

        ::=     { pServerStatsEntry 10 }


pServerStatsContextSwitch OBJECT-TYPE
    SYNTAX      Counter
    ACCESS      read-only
    STATUS      mandatory
    DESCRIPTION
            "The number of context switches undergone by this pServer since
            boot."

        ::=     { pServerStatsEntry 11 }


pServerStatsInterrupt OBJECT-TYPE
    SYNTAX      Counter
    ACCESS      read-only
    STATUS      mandatory
    DESCRIPTION
            "The number of interrupts encountered by this pServer since
            boot."

        ::=     { pServerStatsEntry 12 }


pServerStatsMemTotal OBJECT-TYPE
    SYNTAX      Gauge
    ACCESS      read-only
    STATUS      mandatory
    DESCRIPTION
            "The total amount of physical RAM in kB for this pServer."

        ::=     { pServerStatsEntry 13 }


pServerStatsMemFree OBJECT-TYPE
    SYNTAX      Gauge
    ACCESS      read-only
    STATUS      mandatory
    DESCRIPTION
            "The amount of free physcial RAM in kB for this pServer."

        ::=     { pServerStatsEntry 14 }


pServerStatsSwapTotal OBJECT-TYPE
    SYNTAX      Gauge
    ACCESS      read-only
    STATUS      mandatory
    DESCRIPTION
            "The total amount of configured swap memory in kB for this
            pServer."

        ::=     { pServerStatsEntry 15 }


pServerStatsSwapFree OBJECT-TYPE
    SYNTAX      Gauge
    ACCESS      read-only
    STATUS      mandatory
    DESCRIPTION
            "The amount of free swap memory in kB for this pServer."

        ::=     { pServerStatsEntry 16 }


pServerStatsPageIn OBJECT-TYPE
    SYNTAX      Counter
    ACCESS      read-only
    STATUS      mandatory
    DESCRIPTION
            "The number of pages paged in since boot."

        ::=     { pServerStatsEntry 17 }


pServerStatsPageOut OBJECT-TYPE
    SYNTAX      Counter
    ACCESS      read-only
    STATUS      mandatory
    DESCRIPTION
            "The number of pages paged out since boot."

        ::=     { pServerStatsEntry 18 }


pServerStatsSwapIn OBJECT-TYPE
    SYNTAX      Counter
    ACCESS      read-only
    STATUS      mandatory
    DESCRIPTION
            "The number of swap pages paged in since boot."

        ::=     { pServerStatsEntry 19 }


pServerStatsSwapOut OBJECT-TYPE
    SYNTAX      Counter
    ACCESS      read-only
    STATUS      mandatory
    DESCRIPTION
            "The number of swap pages paged out since boot."

        ::=     { pServerStatsEntry 20 }


pServerStatsDiskReads OBJECT-TYPE
    SYNTAX      Counter
    ACCESS      read-only
    STATUS      mandatory
    DESCRIPTION
            "The number of disk reads since boot."

        ::=     { pServerStatsEntry 21 }


pServerStatsDiskWrites OBJECT-TYPE
    SYNTAX      Counter
    ACCESS      read-only
    STATUS      mandatory
    DESCRIPTION
            "The number of disk writes since boot."

        ::=     { pServerStatsEntry 22 }


pServerStatsDiskBlkReads OBJECT-TYPE
    SYNTAX      Counter
    ACCESS      read-only
    STATUS      mandatory
    DESCRIPTION
            "The number of 1 kB blocks read from disk since boot.
            Returns 0 for Windows pServers."

        ::=     { pServerStatsEntry 23 }


pServerStatsDiskBlkWrites OBJECT-TYPE
    SYNTAX      Counter
    ACCESS      read-only
    STATUS      mandatory
    DESCRIPTION
            "The number of of 1 kB blocks written to disk since boot.
            Returns 0 for Windows pServers."

        ::=     { pServerStatsEntry 24 }


pServerStatsCpuUserNice OBJECT-TYPE
    SYNTAX      Counter
    ACCESS      read-only
    STATUS      mandatory
    DESCRIPTION
            "The number of (1/100)ths of a second that the pServer spent in
            user nice mode since boot.  Returns 0 for Windows pServers."

        ::=     { pServerStatsEntry 25 }

-- pServer CPU Table
-- Contains information about each CPU on each pServer

pServerCpuTable   OBJECT-TYPE
    SYNTAX      SEQUENCE OF PServerCpuEntry
    ACCESS      not-accessible
    STATUS      mandatory
    DESCRIPTION
            "A list of CPU statisitcs for each CPU on each pServer."

        ::=     { pServers 3 }


pServerCpuEntry OBJECT-TYPE
    SYNTAX      PServerCpuEntry
    ACCESS      not-accessible
    STATUS      mandatory
    DESCRIPTION
            "Statistics for each CPU on the pServer."

    INDEX       { lPanIndex, pServerIndex, pServerCpuIndex }
        ::=     { pServerCpuTable 1 }


PServerCpuEntry ::=
    SEQUENCE {
        pServerCpuIndex
            INTEGER (1..2147483647),
        pServerCpuPServerIndex
            INTEGER (1..2147483647),
        pServerCpuLPanIndex
            INTEGER (1..2147483647),
        pServerCpuModelName
            DisplayString,
        pServerCpuModel
            INTEGER,
        pServerCpuFamily
            INTEGER,
        pServerCpuVendorId
            DisplayString,
        pServerCpuMhz
            INTEGER,
        pServerCpuCacheSize
            INTEGER,
        pServerCpuName
            DisplayString,
        pServerCpuUser
            Counter,
        pServerCpuUserNice
            Counter,
        pServerCpuSystem
            Counter,
        pServerCpuIdle
            Counter
    }


pServerCpuIndex OBJECT-TYPE
    SYNTAX      INTEGER (1..2147483647)
    ACCESS      read-only
    STATUS      mandatory
    DESCRIPTION
            "An integer uniquely identifying this CPU within the pServer."

        ::=     { pServerCpuEntry 1 }


pServerCpuPServerIndex OBJECT-TYPE
    SYNTAX      INTEGER (1..2147483647)
    ACCESS      read-only
    STATUS      mandatory
    DESCRIPTION
            "An integer value identifying the pServerIndex value of the
            pServer that hosts this CPU."

        ::=     { pServerCpuEntry 2 }


pServerCpuLPanIndex OBJECT-TYPE
    SYNTAX      INTEGER (1..2147483647)
    ACCESS      read-only
    STATUS      mandatory
    DESCRIPTION
            "An integer value identifying the lPanIndex value of the
            LPAN that hosts this CPU."

        ::=     { pServerCpuEntry 3 }


pServerCpuModelName OBJECT-TYPE
    SYNTAX      DisplayString
    ACCESS      read-only
    STATUS      mandatory
    DESCRIPTION
            "A textual string representing the CPU model."

        ::=     { pServerCpuEntry 4 }


pServerCpuModel OBJECT-TYPE
    SYNTAX      INTEGER
    ACCESS      read-only
    STATUS      mandatory
    DESCRIPTION
            "An integer value representing the CPU model."

        ::=     { pServerCpuEntry 5 }


pServerCpuFamily OBJECT-TYPE
    SYNTAX      INTEGER
    ACCESS      read-only
    STATUS      mandatory
    DESCRIPTION
            "An integer value representing the CPU family."

        ::=     { pServerCpuEntry 6 }


pServerCpuVendorId OBJECT-TYPE
    SYNTAX      DisplayString
    ACCESS      read-only
    STATUS      mandatory
    DESCRIPTION
            "A textual string representing the CPU vendor."

        ::=     { pServerCpuEntry 7 }


pServerCpuMhz OBJECT-TYPE
    SYNTAX      INTEGER
    ACCESS      read-only
    STATUS      mandatory
    DESCRIPTION
            "The speed of the CPU in Mhz."

        ::=     { pServerCpuEntry 8 }


pServerCpuCacheSize OBJECT-TYPE
    SYNTAX      INTEGER
    ACCESS      read-only
    STATUS      mandatory
    DESCRIPTION
            "The cache size of the CPU in MB."

        ::=     { pServerCpuEntry 9 }


pServerCpuName OBJECT-TYPE
    SYNTAX      DisplayString
    ACCESS      read-only
    STATUS      mandatory
    DESCRIPTION
            "A textual string uniquely identifying this CPU."

        ::=     { pServerCpuEntry 10 }


pServerCpuUser OBJECT-TYPE
    SYNTAX      Counter
    ACCESS      read-only
    STATUS      mandatory
    DESCRIPTION
            "The number of (1/100)ths of a second that this CPU spent in
            user mode since boot."

        ::=     { pServerCpuEntry 11 }


pServerCpuUserNice OBJECT-TYPE
    SYNTAX      Counter
    ACCESS      read-only
    STATUS      mandatory
    DESCRIPTION
            "The number of (1/100)ths of a second that this CPU spent in
            user nice mode since boot."

        ::=     { pServerCpuEntry 12 }


pServerCpuSystem OBJECT-TYPE
    SYNTAX      Counter
    ACCESS      read-only
    STATUS      mandatory
    DESCRIPTION
            "The number of (1/100)ths of a second that this CPU spent in
            system mode since boot."

        ::=     { pServerCpuEntry 13 }


pServerCpuIdle OBJECT-TYPE
    SYNTAX      Counter
    ACCESS      read-only
    STATUS      mandatory
    DESCRIPTION
            "The number of (1/100)ths of a second that this CPU spent in
            idle mode since boot."

        ::=     { pServerCpuEntry 14 }



-- pServer Disk Table
-- Contains information about each disk on the pServer.

pServerDiskTable OBJECT-TYPE

    SYNTAX      SEQUENCE OF PServerDiskEntry
    ACCESS      not-accessible
    STATUS      mandatory
    DESCRIPTION
            "A list of disk statisitcs for each disk on the
            pServer."

        ::=     { pServers 4 }


pServerDiskEntry OBJECT-TYPE
    SYNTAX      PServerDiskEntry
    ACCESS      not-accessible
    STATUS      mandatory
    DESCRIPTION
            "Disk statisitcs for each disk on the pServer."

    INDEX       { lPanIndex, pServerIndex,
                  IMPLIED pServerDiskNameOctets }
        ::=     { pServerDiskTable 1 }


PServerDiskEntry ::=
    SEQUENCE {
        pServerDiskNameOctets
            OCTET STRING (SIZE(0..63)),
        pServerDiskPServerIndex
            INTEGER,
        pServerDiskLPanIndex
            INTEGER,
        pServerDiskName
            DisplayString,
        pServerDiskBlocks
            Gauge,
        pServerDiskMajor
            INTEGER,
        pServerDiskMinor
            INTEGER
    }

pServerDiskNameOctets OBJECT-TYPE
    SYNTAX      OCTET STRING (SIZE(0..63))
    ACCESS      read-only
    STATUS      mandatory
    DESCRIPTION
            "An octet string representing the device special file name
            representing this disk."

        ::=     { pServerDiskEntry 1 }


pServerDiskPServerIndex OBJECT-TYPE
    SYNTAX      INTEGER
    ACCESS      read-only
    STATUS      mandatory
    DESCRIPTION
            "An integer value identifying the pServerIndex value of the
            pServer that utilizes this disk."

        ::=     { pServerDiskEntry 2 }


pServerDiskLPanIndex OBJECT-TYPE
    SYNTAX      INTEGER
    ACCESS      read-only
    STATUS      mandatory
    DESCRIPTION
            "An integer value indentifying the lPanIndex value of the
            LPAN that hosts this disk."

        ::=     { pServerDiskEntry 3 }

pServerDiskName OBJECT-TYPE
    SYNTAX      DisplayString
    ACCESS      read-only
    STATUS      mandatory
    DESCRIPTION
            "The human readable device special file name representing this
            disk."

        ::=     { pServerDiskEntry 4 }

pServerDiskBlocks OBJECT-TYPE
    SYNTAX      Gauge
    ACCESS      read-only
    STATUS      mandatory
    DESCRIPTION
            "The size of this disk in 1kB blocks"

        ::=     { pServerDiskEntry 5 }


pServerDiskMajor OBJECT-TYPE
    SYNTAX      INTEGER
    ACCESS      read-only
    STATUS      mandatory
    DESCRIPTION
            "The major ID of this disk."

        ::=     { pServerDiskEntry 6 }


pServerDiskMinor OBJECT-TYPE
    SYNTAX      INTEGER
    ACCESS      read-only
    STATUS      mandatory
    DESCRIPTION
            "The minor ID of this disk."

        ::=     { pServerDiskEntry 7 }


-- pServer Partition Table
-- Contains information about each disk partition on the pServer.



pServerPartitionTable   OBJECT-TYPE
    SYNTAX      SEQUENCE OF PServerPartitionEntry
    ACCESS      not-accessible
    STATUS      mandatory
    DESCRIPTION
            "A list of partition statisitcs for each partition on the
            pServer."

        ::=     { pServers 5 }


pServerPartitionEntry OBJECT-TYPE
    SYNTAX      PServerPartitionEntry
    ACCESS      not-accessible
    STATUS      mandatory
    DESCRIPTION
            "Partition statisitcs for each partition on the pServer."

    INDEX       { lPanIndex, pServerIndex,
                  IMPLIED pServerPartitionNameOctets }
        ::=     { pServerPartitionTable 1 }


PServerPartitionEntry ::=
    SEQUENCE {
        pServerPartitionNameOctets
            OCTET STRING (SIZE(0..63)),
        pServerPartitionPServerIndex
            INTEGER,
        pServerPartitionLPanIndex
            INTEGER,
        pServerPartitionName
            DisplayString (SIZE(0..63)),
        pServerPartitionBlocks
            Gauge,
        pServerPartitionMajor
            INTEGER,
        pServerPartitionMinor
            INTEGER,
        pServerPartitionFSBlocks
            Gauge,
        pServerPartitionFSUsedBlocks
            Gauge,
        pServerPartitionFSAvailableBlocks
            Gauge,
        pServerPartitionFSUtil
            Gauge
    }


pServerPartitionNameOctets OBJECT-TYPE
    SYNTAX      OCTET STRING (SIZE(0..63))
    ACCESS      read-only
    STATUS      mandatory
    DESCRIPTION
            "An octet string representing the device special file name
            representing this disk."

        ::=     { pServerPartitionEntry 1 }


pServerPartitionPServerIndex OBJECT-TYPE
    SYNTAX      INTEGER
    ACCESS      read-only
    STATUS      mandatory
    DESCRIPTION
            "An integer value identifying the pServerIndex value of the
            pServer that utilizes this disk partition."

        ::=     { pServerPartitionEntry 2 }


pServerPartitionLPanIndex OBJECT-TYPE
    SYNTAX      INTEGER
    ACCESS      read-only
    STATUS      mandatory
    DESCRIPTION
            "An integer value indentifying the lPanIndex value of the
            LPAN that hosts this partition."

        ::=     { pServerPartitionEntry 3 }


pServerPartitionName OBJECT-TYPE
    SYNTAX      DisplayString (SIZE(0..63))
    ACCESS      read-only
    STATUS      mandatory
    DESCRIPTION
            "A textual string identifying the device file that represents
            this partition."

        ::=     { pServerPartitionEntry 4 }


pServerPartitionBlocks OBJECT-TYPE
    SYNTAX      Gauge
    ACCESS      read-only
    STATUS      mandatory
    DESCRIPTION
            "The size of this partition in 1kB blocks"

        ::=     { pServerPartitionEntry 5 }


pServerPartitionMajor OBJECT-TYPE
    SYNTAX      INTEGER
    ACCESS      read-only
    STATUS      mandatory
    DESCRIPTION
            "The major ID of this partition."

        ::=     { pServerPartitionEntry 6 }


pServerPartitionMinor OBJECT-TYPE
    SYNTAX      INTEGER
    ACCESS      read-only
    STATUS      mandatory
    DESCRIPTION
            "The minor ID of this partition."

        ::=     { pServerPartitionEntry 7 }


pServerPartitionFSBlocks OBJECT-TYPE
    SYNTAX      Gauge
    ACCESS      read-only
    STATUS      mandatory
    DESCRIPTION
            "If the partition contains a mounted filesystem, filesystem size
            in 1k blocks, otherwise 0."

        ::=     { pServerPartitionEntry 8 }


pServerPartitionFSUsedBlocks OBJECT-TYPE
    SYNTAX      Gauge
    ACCESS      read-only
    STATUS      mandatory
    DESCRIPTION
            "If the partition contains a mounted filesystem, the number of
            used 1k blocks, otherwise 0."

        ::=     { pServerPartitionEntry 9 }


pServerPartitionFSAvailableBlocks OBJECT-TYPE
    SYNTAX      Gauge
    ACCESS      read-only
    STATUS      mandatory
    DESCRIPTION
            "If the partition contains a mounted filesystem, the number of
            available 1k blocks, otherwise 0."

        ::=     { pServerPartitionEntry 10 }


pServerPartitionFSUtil OBJECT-TYPE
    SYNTAX      Gauge
    ACCESS      read-only
    STATUS      mandatory
    DESCRIPTION
            "If the partition contains a mounted filesystem, the number of
            available 1k blocks, otherwise 0."

        ::=     { pServerPartitionEntry 11 }


-- pServer Virtual Ethernet table
-- Contains information about each network interface on the pServer.


pServerEthTable   OBJECT-TYPE
    SYNTAX      SEQUENCE OF PServerEthEntry
    ACCESS      not-accessible
    STATUS      mandatory
    DESCRIPTION
            "Information regarding each virtual Eth interface on a pServer."


        ::=     { pServers 6 }


pServerEthEntry OBJECT-TYPE
    SYNTAX      PServerEthEntry
    ACCESS      not-accessible
    STATUS      mandatory
    DESCRIPTION
            "Information specific to each cBlade Eth in the PAN."

    INDEX       { lPanIndex, pServerIndex, pServerEthIndex }
        ::=     { pServerEthTable 1 }

PServerEthEntry ::=
    SEQUENCE {
        pServerEthIndex
            INTEGER (1..2147483647),
        pServerEthPServerIndex
            INTEGER (1..2147483647),
        pServerEthLPanIndex
            INTEGER (1..2147483647),
        pServerEthName
            DisplayString,
        pServerEthMACAddressOctets
            PhysAddress,
        pServerEthMACAddressString
            DisplayString,
        pServerEthRateLimit
            INTEGER
    }


pServerEthIndex OBJECT-TYPE
    SYNTAX      INTEGER (1..2147483647)
    ACCESS      read-only
    STATUS      mandatory
    DESCRIPTION
            "An integer uniquely identifying this interface within the
            pServer."

        ::=     { pServerEthEntry 1 }


pServerEthPServerIndex OBJECT-TYPE
    SYNTAX      INTEGER (1..2147483647)
    ACCESS      read-only
    STATUS      mandatory
    DESCRIPTION
            "An integer value identifying the pServerIndex of the
            pServer that hosts this interface."

        ::=     { pServerEthEntry 2 }


pServerEthLPanIndex OBJECT-TYPE
    SYNTAX      INTEGER (1..2147483647)
    ACCESS      read-only
    STATUS      mandatory
    DESCRIPTION
            "An integer value identifying the lPanIndex value of the
            LPAN that hosts this interface."

        ::=     { pServerEthEntry 3 }


pServerEthName OBJECT-TYPE
    SYNTAX      DisplayString
    ACCESS      read-only
    STATUS      mandatory
    DESCRIPTION
            "A textual string identifying the network interface."

        ::=     { pServerEthEntry 4 }


pServerEthMACAddressOctets OBJECT-TYPE
    SYNTAX      PhysAddress
    ACCESS      read-only
    STATUS      mandatory
    DESCRIPTION
            "An encoding of the eth MAC address."

        ::=     { pServerEthEntry 5 }


pServerEthMACAddressString OBJECT-TYPE
    SYNTAX      DisplayString
    ACCESS      read-only
    STATUS      mandatory
    DESCRIPTION
            "A human readable string representing the eth MAC address
             in the form: '6E:4A:1F:00:01:06'."

        ::=     { pServerEthEntry 6 }


pServerEthRateLimit OBJECT-TYPE
    SYNTAX      INTEGER
    ACCESS      read-only
    STATUS      mandatory
    DESCRIPTION
            "The configured rate limit for the pServer Eth in Mbps.
            0 indicates unlimited."

        ::=     { pServerEthEntry 7 }



pServerEthStatsTable   OBJECT-TYPE
    SYNTAX      SEQUENCE OF PServerEthStatsEntry
    ACCESS      not-accessible
    STATUS      mandatory
    DESCRIPTION
            "A list of interface statisitcs for each interface in the
            pServer."

        ::=     { pServers 7 }


pServerEthStatsEntry OBJECT-TYPE
    SYNTAX      PServerEthStatsEntry
    ACCESS      not-accessible
    STATUS      mandatory
    DESCRIPTION
            "Eth statisitcs for each interface in the pServer."

    INDEX       { lPanIndex, pServerIndex, pServerEthIndex }
        ::=     { pServerEthStatsTable 1 }


PServerEthStatsEntry ::=
    SEQUENCE {
        pServerEthStatsInBytes
            Counter,
        pServerEthStatsInPackets
            Counter,
        pServerEthStatsInErrs
            Counter,
        pServerEthStatsInDrops
            Counter,
        pServerEthStatsInOverrun
            Counter,
        pServerEthStatsInMulticast
            Counter,
        pServerEthStatsOutBytes
            Counter,
        pServerEthStatsOutPackets
            Counter,
        pServerEthStatsOutErrs
            Counter,
        pServerEthStatsOutDrops
            Counter,
        pServerEthStatsOutOverrun
            Counter,
        pServerEthStatsOutCollisions
            Counter,
        pServerEthStatsOutCarrierDctFail
            Counter,
        pServerEthStatsOutCompressed
            Counter,
        pServerEthStatsOperStatus
            InterfaceOperStatus
    }


pServerEthStatsInBytes OBJECT-TYPE
    SYNTAX      Counter
    ACCESS      read-only
    STATUS      mandatory
    DESCRIPTION
            "The number of bytes received on this interface since interface
            reset"

        ::=     { pServerEthStatsEntry 1 }


pServerEthStatsInPackets OBJECT-TYPE
    SYNTAX      Counter
    ACCESS      read-only
    STATUS      mandatory
    DESCRIPTION
            "The number of packets received on this interface since interface
            reset"

        ::=     { pServerEthStatsEntry 2 }


pServerEthStatsInErrs OBJECT-TYPE
    SYNTAX      Counter
    ACCESS      read-only
    STATUS      mandatory
    DESCRIPTION
            "The number of errors received on this interface since interface
            reset"

        ::=     { pServerEthStatsEntry 3 }


pServerEthStatsInDrops OBJECT-TYPE
    SYNTAX      Counter
    ACCESS      read-only
    STATUS      mandatory
    DESCRIPTION
            "The number of dropped incoming packets on this interface since
            interface reset."

        ::=     { pServerEthStatsEntry 4 }


pServerEthStatsInOverrun OBJECT-TYPE
    SYNTAX      Counter
    ACCESS      read-only
    STATUS      mandatory
    DESCRIPTION
            "The number of overrun incoming packets on this interface since
            interface reset."

        ::=     { pServerEthStatsEntry 5 }


pServerEthStatsInMulticast OBJECT-TYPE
    SYNTAX      Counter
    ACCESS      read-only
    STATUS      mandatory
    DESCRIPTION
            "The number of multicast packets received on this interface since
            interface reset."

        ::=     { pServerEthStatsEntry 6 }


pServerEthStatsOutBytes OBJECT-TYPE
    SYNTAX      Counter
    ACCESS      read-only
    STATUS      mandatory
    DESCRIPTION
            "The number of bytes transmitted from this interface since
            interface reset."

        ::=     { pServerEthStatsEntry 7 }


pServerEthStatsOutPackets OBJECT-TYPE
    SYNTAX      Counter
    ACCESS      read-only
    STATUS      mandatory
    DESCRIPTION
            "The number of packets transmitted from this interface since
            interface reset."

        ::=     { pServerEthStatsEntry 8 }


pServerEthStatsOutErrs OBJECT-TYPE
    SYNTAX      Counter
    ACCESS      read-only
    STATUS      mandatory
    DESCRIPTION
            "The number of errors encountered while transmitting from this
            interface since interface reset."

        ::=     { pServerEthStatsEntry 9 }


pServerEthStatsOutDrops OBJECT-TYPE
    SYNTAX      Counter
    ACCESS      read-only
    STATUS      mandatory
    DESCRIPTION
            "The number of dropped packets intended for transmission from this
            interface since interface reset."

        ::=     { pServerEthStatsEntry 10 }


pServerEthStatsOutOverrun OBJECT-TYPE
    SYNTAX      Counter
    ACCESS      read-only
    STATUS      mandatory
    DESCRIPTION
            "The number of overrun packets intended for transmission from this
            interface since interface reset."

        ::=     { pServerEthStatsEntry 11 }


pServerEthStatsOutCollisions OBJECT-TYPE
    SYNTAX      Counter
    ACCESS      read-only
    STATUS      mandatory
    DESCRIPTION
            "The number of collisions detetced while transmitting from this
            interface since interface reset."

        ::=     { pServerEthStatsEntry 12 }


pServerEthStatsOutCarrierDctFail OBJECT-TYPE
    SYNTAX      Counter
    ACCESS      read-only
    STATUS      mandatory
    DESCRIPTION
            "The number of carrier detect failures detetced while transmitting
            from this interface since interface reset."

        ::=     { pServerEthStatsEntry 13 }


pServerEthStatsOutCompressed OBJECT-TYPE
    SYNTAX      Counter
    ACCESS      read-only
    STATUS      mandatory
    DESCRIPTION
            "The number of compressed packets transmitted from this interface
            since interface reset."

        ::=     { pServerEthStatsEntry 14 }


pServerEthStatsOperStatus OBJECT-TYPE
    SYNTAX      InterfaceOperStatus
    ACCESS      read-only
    STATUS      mandatory
    DESCRIPTION
            "The operational state of the interface."

        ::=     { pServerEthStatsEntry 15 }
-- table of IP address information per pServer Eth

pServerEthIpTable     OBJECT-TYPE
    SYNTAX      SEQUENCE OF PServerEthIpEntry
    ACCESS      not-accessible
    STATUS      mandatory
    DESCRIPTION
            "A list of IP addresses, broadcast addresses, and nework masks
            configured on each pServer Eth interface."

        ::=     { pServers 8 }


pServerEthIpEntry     OBJECT-TYPE
    SYNTAX      PServerEthIpEntry
    ACCESS      not-accessible
    STATUS      mandatory
    DESCRIPTION
            "The IP address, broadcast address, and network mask
            for a pServer Eth interface or alias."

    INDEX       { lPanIndex, pServerIndex, pServerEthIndex, IMPLIED pServerEthIpAliasName }
        ::=     { pServerEthIpTable 1 }


PServerEthIpEntry ::=
    SEQUENCE {
        pServerEthIpAliasName
            DisplayString (SIZE(0..63)),
        pServerEthIpEthIndex
            INTEGER,
        pServerEthIpPServerIndex
            INTEGER,
        pServerEthIpLPanIndex
            INTEGER,
        pServerEthIpAddress
            IpAddress,
        pServerEthIpBroadcast
            IpAddress,
        pServerEthIpMask
            IpAddress
    }


pServerEthIpAliasName OBJECT-TYPE
    SYNTAX      DisplayString (SIZE(0..63))
    ACCESS      read-only
    STATUS      mandatory
    DESCRIPTION
            "The name of this network interface or alias, i.e. lo, veth31, eht10:1"

        ::=     { pServerEthIpEntry 1 }


pServerEthIpEthIndex OBJECT-TYPE
    SYNTAX      INTEGER
    ACCESS      read-only
    STATUS      mandatory
    DESCRIPTION
            "An integer value identifying the pServerEthIndex of the pServer Eth
            that hosts this IP configuraion."

        ::=     { pServerEthIpEntry 2 }


pServerEthIpPServerIndex OBJECT-TYPE
    SYNTAX      INTEGER
    ACCESS      read-only
    STATUS      mandatory
    DESCRIPTION
            "An integer value identifying the pServerIndex of the pServer
            that hosts this IP configuraion."

        ::=     { pServerEthIpEntry 3 }


pServerEthIpLPanIndex OBJECT-TYPE
    SYNTAX      INTEGER
    ACCESS      read-only
    STATUS      mandatory
    DESCRIPTION
            "An integer value identifying the lpanIndex of the LPAN
            that hosts this IP configuraion."

        ::=     { pServerEthIpEntry 4 }


pServerEthIpAddress OBJECT-TYPE
    SYNTAX      IpAddress
    ACCESS      read-only
    STATUS      mandatory
    DESCRIPTION
            "The IP address configured on this pServer eth (or alias)"

        ::=     { pServerEthIpEntry 5 }


pServerEthIpBroadcast OBJECT-TYPE
    SYNTAX      IpAddress
    ACCESS      read-only
    STATUS      mandatory
    DESCRIPTION
            "The broadcast address configured on this pServer eth (or alias)"

        ::=     { pServerEthIpEntry 6 }


pServerEthIpMask OBJECT-TYPE
    SYNTAX      IpAddress
    ACCESS      read-only
    STATUS      mandatory
    DESCRIPTION
            "The network mask configured on this pServer eth (or alias)"

        ::=     { pServerEthIpEntry 7 }





-- pServer Controls

pServerControlTable   OBJECT-TYPE
    SYNTAX      SEQUENCE OF PServerControlEntry
    ACCESS      not-accessible
    STATUS      mandatory
    DESCRIPTION
            "A list of pServer controls for each pServer."

        ::=     { pServers 9 }


pServerControlEntry OBJECT-TYPE
    SYNTAX      PServerControlEntry
    ACCESS      not-accessible
    STATUS      mandatory
    DESCRIPTION
            "Controls for each pServer."

    INDEX       { lPanIndex, pServerIndex }
        ::=     { pServerControlTable 1 }


PServerControlEntry ::=
    SEQUENCE {
        pServerControlPowerUp
            INTEGER,
        pServerControlPowerDown
            INTEGER,
        pServerControlColdReset
            INTEGER,
        pServerControlWarmReset
            INTEGER,
        pServerControlNmi
            INTEGER,
        pServerBoot
            INTEGER,
        pServerShutdown
            INTEGER,
        pServerForceShutdown
            INTEGER,
        pServerReboot
            INTEGER,
        pServerForceReboot
            INTEGER
    }

pServerControlPowerUp OBJECT-TYPE
    SYNTAX      INTEGER
    ACCESS      read-write
    STATUS      mandatory
    DESCRIPTION
            "This object is deprecated as of PAN Manager release 4.0.
            This control is available via the pBladeControlTable"


        ::=     { pServerControlEntry 1 }


pServerControlPowerDown OBJECT-TYPE
    SYNTAX      INTEGER
    ACCESS      read-write
    STATUS      mandatory
    DESCRIPTION
            "This object is deprecated as of PAN Manager release 4.0.
            This control is available via the pBladeControlTable"

        ::=     { pServerControlEntry 2 }


pServerControlColdReset OBJECT-TYPE
    SYNTAX      INTEGER
    ACCESS      read-write
    STATUS      mandatory
    DESCRIPTION
            "This object is deprecated as of PAN Manager release 4.0.
            This control is available via the pBladeControlTable"

        ::=     { pServerControlEntry 3 }


pServerControlWarmReset OBJECT-TYPE
    SYNTAX  INTEGER
    ACCESS      read-write
    STATUS  mandatory
    DESCRIPTION
            "This object is deprecated as of PAN Manager release 4.0.
            This control is available via the pBladeControlTable"

        ::=     { pServerControlEntry 4 }


pServerControlNmi OBJECT-TYPE
    SYNTAX      INTEGER
    ACCESS      read-write
    STATUS      mandatory
    DESCRIPTION
            "This object is deprecated as of PAN Manager release 4.0.
            This control is available via the pBladeControlTable"

        ::=     { pServerControlEntry 5 }


pServerBoot OBJECT-TYPE
    SYNTAX      INTEGER
    ACCESS      read-write
    STATUS      mandatory
    DESCRIPTION
            "When set to 1, initiates a boot operation on this pServer.
            When read, returns 0."

        ::=     { pServerControlEntry 6 }


pServerShutdown OBJECT-TYPE
    SYNTAX      INTEGER
    ACCESS      read-write
    STATUS      mandatory
    DESCRIPTION
            "When set to 1, initiates a shutdown operation on this pServer.
            When read, returns 0."

        ::=     { pServerControlEntry 7 }


pServerForceShutdown OBJECT-TYPE
    SYNTAX      INTEGER
    ACCESS      read-write
    STATUS      mandatory
    DESCRIPTION
            "When set to 1, initiates a force shutdown operation on this pServer.
            When read, returns 0."

        ::=     { pServerControlEntry 8 }


pServerReboot OBJECT-TYPE
    SYNTAX      INTEGER
    ACCESS      read-write
    STATUS      mandatory
    DESCRIPTION
            "When set to 1, initiates a reboot operation on this pServer.
            When read, returns 0."

        ::=     { pServerControlEntry 9 }


pServerForceReboot OBJECT-TYPE
    SYNTAX      INTEGER
    ACCESS      read-write
    STATUS      mandatory
    DESCRIPTION
            "When set to 1, initiates a force reboot operation on this pServer.
            When read, returns 0."

        ::=     { pServerControlEntry 10 }


-- applications group
-- contains information and controls for applications under PAN Manager
-- control.

applications OBJECT IDENTIFIER ::= { lPans 4 }


applicationTable   OBJECT-TYPE
    SYNTAX      SEQUENCE OF ApplicationEntry
    ACCESS      not-accessible
    STATUS      mandatory
    DESCRIPTION
            "A list of Application entries containing information about each
            application configured for PAN Manager control."

        ::=     { applications 1 }


applicationEntry OBJECT-TYPE
    SYNTAX      ApplicationEntry
    ACCESS      not-accessible
    STATUS      mandatory
    DESCRIPTION
            "Information regarding each application."

    INDEX       { lPanIndex, applicationIndex }
        ::=     { applicationTable 1 }


ApplicationEntry ::=
    SEQUENCE {
        applicationIndex
            INTEGER (1..2147483647),
        applicationLPanIndex
            INTEGER (1..2147483647),
        applicationName
            DisplayString,
        applicationDescription
            DisplayString,
        applicationStatus
            DisplayString,
        applicationHealth
            DisplayString,
        appCurrentPServerIndex
            INTEGER,
        appPrimaryPServerIndex
            INTEGER
    }

applicationIndex OBJECT-TYPE
    SYNTAX      INTEGER (1..2147483647)
    ACCESS      read-only
    STATUS      mandatory
    DESCRIPTION
            "An integer value uniquely identifying the application within the
            LPAN."

        ::=     { applicationEntry 1 }


applicationLPanIndex OBJECT-TYPE
    SYNTAX      INTEGER (1..2147483647)
    ACCESS      read-only
    STATUS      mandatory
    DESCRIPTION
            "An integer value identifying the lPanIndex value of the
            LPAN that hosts this application."

        ::=     { applicationEntry 2 }


applicationName OBJECT-TYPE
    SYNTAX      DisplayString
    ACCESS      read-only
    STATUS      mandatory
    DESCRIPTION
            "A textual string identifying the application."

        ::=     { applicationEntry 3 }


applicationDescription OBJECT-TYPE
    SYNTAX      DisplayString
    ACCESS      read-only
    STATUS      mandatory
    DESCRIPTION
            "A textual string describing the application."

        ::=     { applicationEntry 4 }


applicationStatus OBJECT-TYPE
    SYNTAX      DisplayString
    ACCESS      read-only
    STATUS      mandatory
    DESCRIPTION
            "A textual string describing the operational status of the
            application."

        ::=     { applicationEntry 5 }


applicationHealth OBJECT-TYPE
    SYNTAX      DisplayString
    ACCESS      read-only
    STATUS      mandatory
    DESCRIPTION
            "This object is deprecated"

        ::=     { applicationEntry 6 }


appCurrentPServerIndex OBJECT-TYPE
    SYNTAX      INTEGER
    ACCESS      read-only
    STATUS      mandatory
    DESCRIPTION
            "An integer value identifying the pServerIndex value of the
            pServer currently hosting this application."

        ::=     { applicationEntry 7 }


appPrimaryPServerIndex OBJECT-TYPE
    SYNTAX      INTEGER
    ACCESS      read-only
    STATUS      mandatory
    DESCRIPTION
            "An integer value identifying the pServerIndex value of the
            pServer configured as the application's primary pServer."

        ::=     { applicationEntry 8 }


applicationControlTable   OBJECT-TYPE
    SYNTAX      SEQUENCE OF ApplicationControlEntry
    ACCESS      not-accessible
    STATUS      mandatory
    DESCRIPTION
            "A list of application entries containing controls for each
            application configured for PAN Manager control."

        ::=     { applications 2 }


applicationControlEntry OBJECT-TYPE
    SYNTAX      ApplicationControlEntry
    ACCESS      not-accessible
    STATUS      mandatory
    DESCRIPTION
            "Controls for each application."

    INDEX       { lPanIndex, applicationIndex }
        ::=     { applicationControlTable 1 }


ApplicationControlEntry ::=
    SEQUENCE {
        applicationStart
            INTEGER,
        applicationStop
            INTEGER,
        applicationForceStop
            INTEGER,
        applicationMove
            INTEGER
    }


applicationStart OBJECT-TYPE
    SYNTAX      INTEGER
    ACCESS      read-write
    STATUS      mandatory
    DESCRIPTION
            "When set to 1, initiates a start operation on this application.
            When read, returns 0."

        ::=     { applicationControlEntry 1 }


applicationStop OBJECT-TYPE
    SYNTAX      INTEGER
    ACCESS      read-write
    STATUS      mandatory
    DESCRIPTION
            "When set to 1, initiates a stop operation on this
            application. When read, returns 0."

        ::=     { applicationControlEntry 2 }


applicationForceStop OBJECT-TYPE
    SYNTAX      INTEGER
    ACCESS      read-write
    STATUS      mandatory
    DESCRIPTION
            "When set to 1, initiates a force stop operation on this
            application. When read, returns 0."

        ::=     { applicationControlEntry 3 }


applicationMove OBJECT-TYPE
    SYNTAX      INTEGER
    ACCESS      read-write
    STATUS      mandatory
    DESCRIPTION
            "When set to 1, initiates a move operation on this
            application. When read, returns 0."

        ::=     { applicationControlEntry 4 }


-- configured failover policies
applicationFOPTable   OBJECT-TYPE
    SYNTAX      SEQUENCE OF ApplicationFOPEntry
    ACCESS      not-accessible
    STATUS      mandatory
    DESCRIPTION
            "A list of Application failover policy assignments."

        ::=     { applications 3 }


applicationFOPEntry OBJECT-TYPE
    SYNTAX      ApplicationFOPEntry
    ACCESS      not-accessible
    STATUS      mandatory
    DESCRIPTION
            "Indicates a failover policy to application assignment by
            identifying failoverPolicyIndex of the failover policy
            assigned to the application"

    INDEX       { lPanIndex, applicationIndex, applicationFOPIndex }
        ::=     { applicationFOPTable 1 }


ApplicationFOPEntry ::=
    SEQUENCE {
        applicationFOPIndex
            INTEGER (1..2147483647)
    }


applicationFOPIndex OBJECT-TYPE
    SYNTAX      INTEGER (1..2147483647)
    ACCESS      read-only
    STATUS      mandatory
    DESCRIPTION
            "An integer value identifying the failoverPolicyIndex of the
            failover policy mapped to the application."

        ::=     { applicationFOPEntry 1 }

-- configured health monitors
applicationHMONTable   OBJECT-TYPE
    SYNTAX      SEQUENCE OF ApplicationHMONEntry
    ACCESS      not-accessible
    STATUS      mandatory
    DESCRIPTION
            "A list of Application health monitor assignments."

        ::=     { applications 4 }


applicationHMONEntry OBJECT-TYPE
    SYNTAX      ApplicationHMONEntry
    ACCESS      not-accessible
    STATUS      mandatory
    DESCRIPTION
            "Indicates a health monitor to application assignment by
            identifying healthMonitorIndex of the health monitor
            assigned to the application"

    INDEX       { lPanIndex, applicationIndex, applicationHMONIndex }
        ::=     { applicationHMONTable 1 }


ApplicationHMONEntry ::=
    SEQUENCE {
        applicationHMONIndex
            INTEGER (1..2147483647)
    }


applicationHMONIndex OBJECT-TYPE
    SYNTAX      INTEGER (1..2147483647)
    ACCESS      read-only
    STATUS      mandatory
    DESCRIPTION
            "An integer value identifying the healthMonitorIndex of the
            health monitor mapped to the application."

        ::=     { applicationHMONEntry 1 }


-- configured executable resources
applicationExResTable   OBJECT-TYPE
    SYNTAX      SEQUENCE OF ApplicationExResEntry
    ACCESS      not-accessible
    STATUS      mandatory
    DESCRIPTION
            "A list of Application executable resource assignments."

        ::=     { applications 5 }


applicationExResEntry OBJECT-TYPE
    SYNTAX      ApplicationExResEntry
    ACCESS      not-accessible
    STATUS      mandatory
    DESCRIPTION
            "Indicates a executable resource to application assignment by
            identifying executableResourceIndex of the executable resource
            assigned to the application"

    INDEX       { lPanIndex, applicationIndex, applicationExResIndex }
        ::=     { applicationExResTable 1 }


ApplicationExResEntry ::=
    SEQUENCE {
        applicationExResIndex
            INTEGER (1..2147483647)
    }


applicationExResIndex OBJECT-TYPE
    SYNTAX      INTEGER (1..2147483647)
    ACCESS      read-only
    STATUS      mandatory
    DESCRIPTION
            "An integer value identifying the executableResourceIndex of the
            executable resource mapped to the application."

        ::=     { applicationExResEntry 1 }


-- configured SCSI disk resources
applicationSCSIResTable   OBJECT-TYPE
    SYNTAX      SEQUENCE OF ApplicationSCSIResEntry
    ACCESS      not-accessible
    STATUS      mandatory
    DESCRIPTION
            "A list of Application SCSI disk resource assignments."

        ::=     { applications 6 }


applicationSCSIResEntry OBJECT-TYPE
    SYNTAX      ApplicationSCSIResEntry
    ACCESS      not-accessible
    STATUS      mandatory
    DESCRIPTION
            "Indicates a SCSIRes disk resource to application assignment by
            identifying scsiDiskResourceIndex of the SCSI disk resource
            assigned to the application"

    INDEX       { lPanIndex, applicationIndex, applicationSCSIResIndex }
        ::=     { applicationSCSIResTable 1 }


ApplicationSCSIResEntry ::=
    SEQUENCE {
        applicationSCSIResIndex
            INTEGER (1..2147483647)
    }


applicationSCSIResIndex OBJECT-TYPE
    SYNTAX      INTEGER (1..2147483647)
    ACCESS      read-only
    STATUS      mandatory
    DESCRIPTION
            "An integer value identifying the scsiDiskResourceIndex of the
            SCSI disk resource mapped to the application."

        ::=     { applicationSCSIResEntry 1 }


-- configured NFS resources
applicationNFSResTable   OBJECT-TYPE
    SYNTAX      SEQUENCE OF ApplicationNFSResEntry
    ACCESS      not-accessible
    STATUS      mandatory
    DESCRIPTION
            "A list of Application NFS resource assignments."

        ::=     { applications 7 }


applicationNFSResEntry OBJECT-TYPE
    SYNTAX      ApplicationNFSResEntry
    ACCESS      not-accessible
    STATUS      mandatory
    DESCRIPTION
            "Indicates an NFS resource to application assignment by
            identifying nfsResourceIndex of the NFS resource
            assigned to the application"

    INDEX       { lPanIndex, applicationIndex, applicationNFSResIndex }
        ::=     { applicationNFSResTable 1 }


ApplicationNFSResEntry ::=
    SEQUENCE {
        applicationNFSResIndex
            INTEGER (1..2147483647)
    }


applicationNFSResIndex OBJECT-TYPE
    SYNTAX      INTEGER (1..2147483647)
    ACCESS      read-only
    STATUS      mandatory
    DESCRIPTION
            "An integer value identifying the nfsResourceIndex of the
            NFS resource mapped to the application."

        ::=     { applicationNFSResEntry 1 }


-- configured network resources
applicationNetResTable   OBJECT-TYPE
    SYNTAX      SEQUENCE OF ApplicationNetResEntry
    ACCESS      not-accessible
    STATUS      mandatory
    DESCRIPTION
            "A list of Application Network resource assignments."

        ::=     { applications 8 }


applicationNetResEntry OBJECT-TYPE
    SYNTAX      ApplicationNetResEntry
    ACCESS      not-accessible
    STATUS      mandatory
    DESCRIPTION
            "Indicates a Network resource to application assignment by
            identifying networkResourceIndex of the Network resource
            assigned to the application"

    INDEX       { lPanIndex, applicationIndex, applicationNetResIndex }
        ::=     { applicationNetResTable 1 }


ApplicationNetResEntry ::=
    SEQUENCE {
        applicationNetResIndex
            INTEGER (1..2147483647)
    }


applicationNetResIndex OBJECT-TYPE
    SYNTAX      INTEGER (1..2147483647)
    ACCESS      read-only
    STATUS      mandatory
    DESCRIPTION
            "An integer value identifying the networkResourceIndex of the
            executable resource mapped to the application."

        ::=     { applicationNetResEntry 1 }



loadBalancers OBJECT IDENTIFIER ::= { lPans 5 }

-- load balancers
loadBalancerTable   OBJECT-TYPE
    SYNTAX      SEQUENCE OF LoadBalancerEntry
    ACCESS      not-accessible
    STATUS      mandatory
    DESCRIPTION
            "A list of load balancer entries containing information about each
            load balancer configured for PAN Manager control."

        ::=     { loadBalancers 1 }


loadBalancerEntry OBJECT-TYPE
    SYNTAX      LoadBalancerEntry
    ACCESS      not-accessible
    STATUS      mandatory
    DESCRIPTION
            "Information regarding each load balancer."

    INDEX       { lPanIndex, loadBalancerIndex }
        ::=     { loadBalancerTable 1 }


LoadBalancerEntry ::=
    SEQUENCE {
        loadBalancerIndex
            INTEGER (1..2147483647),
        loadBalancerLPanIndex
            INTEGER (1..2147483647),
        loadBalancerName
            DisplayString,
        loadBalancerDescription
            DisplayString,
        loadBalancerStatus
            DisplayString,
        lbCurrentPServerIndex
            INTEGER (1..2147483647),
        lbPrimaryPServerIndex
            INTEGER (1..2147483647),
        loadBalancerAutoStart
            TruthValue
    }

loadBalancerIndex OBJECT-TYPE
    SYNTAX      INTEGER (1..2147483647)
    ACCESS      read-only
    STATUS      mandatory
    DESCRIPTION
            "An integer value uniquely identifying the load balancer within the
            LPAN."

        ::=     { loadBalancerEntry 1 }

loadBalancerLPanIndex OBJECT-TYPE
    SYNTAX      INTEGER (1..2147483647)
    ACCESS      read-only
    STATUS      mandatory
    DESCRIPTION
            "An integer value identifying the lPanIndex value of the
            LPAN that hosts this loadBalancer."

        ::=     { loadBalancerEntry 2 }


loadBalancerName OBJECT-TYPE
    SYNTAX      DisplayString
    ACCESS      read-only
    STATUS      mandatory
    DESCRIPTION
            "A textual string identifying the load balancer."

        ::=     { loadBalancerEntry 3 }


loadBalancerDescription OBJECT-TYPE
    SYNTAX      DisplayString
    ACCESS      read-only
    STATUS      mandatory
    DESCRIPTION
            "A textual string describing the load balancer."

        ::=     { loadBalancerEntry 4 }


loadBalancerStatus OBJECT-TYPE
    SYNTAX      DisplayString
    ACCESS      read-only
    STATUS      mandatory
    DESCRIPTION
            "A textual string describing the operational status of the
            loadBalancer."

        ::=     { loadBalancerEntry 5 }


lbCurrentPServerIndex OBJECT-TYPE
    SYNTAX      INTEGER (1..2147483647)
    ACCESS      read-only
    STATUS      mandatory
    DESCRIPTION
            "An integer value identifying the pServerIndex value of the
            pServer currently hosting this load balancer."

        ::=     { loadBalancerEntry 6 }


lbPrimaryPServerIndex OBJECT-TYPE
    SYNTAX      INTEGER (1..2147483647)
    ACCESS      read-only
    STATUS      mandatory
    DESCRIPTION
            "An integer value identifying the pServerIndex value of the
            pServer configured as the load balancer's primare pServer."

        ::=     { loadBalancerEntry 7 }


loadBalancerAutoStart OBJECT-TYPE
    SYNTAX      TruthValue
    ACCESS      read-only
    STATUS      mandatory
    DESCRIPTION
            "A boolean value indicating whether or not the load balancer
            is configured for auto-start."

        ::=     { loadBalancerEntry 8 }



loadBalancerControlTable   OBJECT-TYPE
    SYNTAX      SEQUENCE OF LoadBalancerControlEntry
    ACCESS      not-accessible
    STATUS      mandatory
    DESCRIPTION
            "A list of load balancer entries containing controls for each
            load balancer configured for PAN Manager control."

        ::=     { loadBalancers 2 }


loadBalancerControlEntry OBJECT-TYPE
    SYNTAX      LoadBalancerControlEntry
    ACCESS      not-accessible
    STATUS      mandatory
    DESCRIPTION
            "Controls for each load balancer."

    INDEX       { lPanIndex, loadBalancerIndex }
        ::=     { loadBalancerControlTable 1 }


LoadBalancerControlEntry ::=
    SEQUENCE {
        loadBalancerStart
            INTEGER,
        loadBalancerStop
            INTEGER,
        loadBalancerForceStop
            INTEGER,
        loadBalancerMove
            INTEGER
    }


loadBalancerStart OBJECT-TYPE
    SYNTAX      INTEGER
    ACCESS      read-write
    STATUS      mandatory
    DESCRIPTION
            "When set to 1, initiates a start operation on this load balancer.
            When read, returns 0."

        ::=     { loadBalancerControlEntry 1 }


loadBalancerStop OBJECT-TYPE
    SYNTAX      INTEGER
    ACCESS      read-write
    STATUS      mandatory
    DESCRIPTION
            "When set to 1, initiates a stop operation on this
            load balancer. When read, returns 0."

        ::=     { loadBalancerControlEntry 2 }


loadBalancerForceStop OBJECT-TYPE
    SYNTAX      INTEGER
    ACCESS      read-write
    STATUS      mandatory
    DESCRIPTION
            "When set to 1, initiates a force stop operation on this
            load balancer. When read, returns 0."

        ::=     { loadBalancerControlEntry 3 }


loadBalancerMove OBJECT-TYPE
    SYNTAX      INTEGER
    ACCESS      read-write
    STATUS      mandatory
    DESCRIPTION
            "When set to 1, initiates a move operation on this
            load balancer. When read, returns 0."

        ::=     { loadBalancerControlEntry 4 }


ProtocolType ::= INTEGER {
    tcp(1),
    udp(2),
    undefined(999)
}

SchedulePolicyType ::= INTEGER {
    round-robin(1),             -- distribute jobs equally among available pServers.
    weighted-round-robin(2),    -- assign relatively more jobs to pServers with larger capacity.
    least-connection(3),        -- assign relatively more jobs to pServers with fewer scheduled jobs.
    weighted-least-connected(4),-- assign relatively more jobs to pServers with less scheduled jobs relative to their capacity.
    undefined(999)
}


loadBalancerConnectionTable   OBJECT-TYPE
    SYNTAX      SEQUENCE OF LoadBalancerConnectionEntry
    ACCESS      not-accessible
    STATUS      mandatory
    DESCRIPTION
            "A list of configured connections to the load balancer service."

        ::=     { loadBalancers 3 }


loadBalancerConnectionEntry OBJECT-TYPE
    SYNTAX      LoadBalancerConnectionEntry
    ACCESS      not-accessible
    STATUS      mandatory
    DESCRIPTION
            "Attributes of each load balancer connection"

    INDEX       { lPanIndex, loadBalancerIndex, loadBalancerConnectionIndex }
        ::=     { loadBalancerConnectionTable 1 }


LoadBalancerConnectionEntry ::=
    SEQUENCE {
        loadBalancerConnectionIndex
            INTEGER (1..2147483647),
        loadBalancerConnectionProto
            ProtocolType,
        loadBalancerConnectionPort
            INTEGER,
        lbConnectionStartSchedPolicy
            SchedulePolicyType,
        loadBalancerPersistConnection
            TruthValue
    }


loadBalancerConnectionIndex OBJECT-TYPE
    SYNTAX      INTEGER (1..2147483647)
    ACCESS      read-only
    STATUS      mandatory
    DESCRIPTION
            "An integer value uniquely identifying the connection within the
            load balancer."

        ::=     { loadBalancerConnectionEntry 1 }


loadBalancerConnectionProto OBJECT-TYPE
    SYNTAX      ProtocolType
    ACCESS      read-only
    STATUS      mandatory
    DESCRIPTION
            "Indicates the connection protocol; TCP or UDP."

        ::=     { loadBalancerConnectionEntry 2 }


loadBalancerConnectionPort OBJECT-TYPE
    SYNTAX      INTEGER
    ACCESS      read-only
    STATUS      mandatory
    DESCRIPTION
            "Indicates the connection port."

        ::=     { loadBalancerConnectionEntry 3 }


lbConnectionStartSchedPolicy OBJECT-TYPE
    SYNTAX      SchedulePolicyType
    ACCESS      read-only
    STATUS      mandatory
    DESCRIPTION
            "Indicates the scheduling policy for the connection.
            - rr-round robin (default): distribute jobs equally among available pServers.
            - wrr-weighted-round-robin: assign relatively more jobs to pServers with larger
                    capacity.
            - lc-least-connection-assign: relatively more jobs to pServers with fewer
                    scheduled jobs.
            - wlc-weighted-least-connected: assign relatively more jobs to pServers with less
                    scheduled jobs relative to their capacity."

        ::=     { loadBalancerConnectionEntry 4 }


loadBalancerPersistConnection OBJECT-TYPE
    SYNTAX      TruthValue
    ACCESS      read-only
    STATUS      mandatory
    DESCRIPTION
            "Indicates the whether or not established connections from clients should
            always be serviced by the same load balancer member."

        ::=     { loadBalancerConnectionEntry 5 }


loadBalancerMemberTable   OBJECT-TYPE
    SYNTAX      SEQUENCE OF LoadBalancerMemberEntry
    ACCESS      not-accessible
    STATUS      mandatory
    DESCRIPTION
            "A list of applications that are members of the load balancer
            service."

        ::=     { loadBalancers 4 }


loadBalancerMemberEntry OBJECT-TYPE
    SYNTAX      LoadBalancerMemberEntry
    ACCESS      not-accessible
    STATUS      mandatory
    DESCRIPTION
            "Attributes of each application that is a member of the load
            balancer service."

    INDEX       { lPanIndex, loadBalancerIndex, loadBalancerMemberIndex }
        ::=     { loadBalancerMemberTable 1 }


LoadBalancerMemberEntry ::=
    SEQUENCE {
        loadBalancerMemberIndex
            INTEGER (1..2147483647),
        loadBalancerMemberWeight
            INTEGER,
        lbMemberStartWithService
            TruthValue
    }


loadBalancerMemberIndex OBJECT-TYPE
    SYNTAX      INTEGER (1..2147483647)
    ACCESS      read-only
    STATUS      mandatory
    DESCRIPTION
            "An integer value identifying the applicationIndex value of the
            application that is a member of this load balancer service."

        ::=     { loadBalancerMemberEntry 1 }


loadBalancerMemberWeight OBJECT-TYPE
    SYNTAX      INTEGER
    ACCESS      read-only
    STATUS      mandatory
    DESCRIPTION
            "An integer value identifying the weight criteria for the member,
            a member with weight 2 will handle twice the load as a member of
            weight 1."

        ::=     { loadBalancerMemberEntry 2 }


lbMemberStartWithService OBJECT-TYPE
    SYNTAX      TruthValue
    ACCESS      read-only
    STATUS      mandatory
    DESCRIPTION
            "Indicates whether or not this member is configured to start when
            the load balancer service is started."

        ::=     { loadBalancerMemberEntry 3 }

-- configured failover policies
loadBalancerFOPTable   OBJECT-TYPE
    SYNTAX      SEQUENCE OF LoadBalancerFOPEntry
    ACCESS      not-accessible
    STATUS      mandatory
    DESCRIPTION
            "A list of load balancer failover policy assignments."

        ::=     { loadBalancers 5 }


loadBalancerFOPEntry OBJECT-TYPE
    SYNTAX      LoadBalancerFOPEntry
    ACCESS      not-accessible
    STATUS      mandatory
    DESCRIPTION
            "Indicates a failover policy to load balancer assignment by
            identifying failoverPolicyIndex of the failover policy
            assigned to the load balancer"

    INDEX       { lPanIndex, loadBalancerIndex, loadBalancerFOPIndex }
        ::=     { loadBalancerFOPTable 1 }


LoadBalancerFOPEntry ::=
    SEQUENCE {
        loadBalancerFOPIndex
            INTEGER (1..2147483647)
    }


loadBalancerFOPIndex OBJECT-TYPE
    SYNTAX      INTEGER (1..2147483647)
    ACCESS      read-only
    STATUS      mandatory
    DESCRIPTION
            "An integer value identifying the failoverPolicyIndex of the
            failover policy mapped to the load balancer."

        ::=     { loadBalancerFOPEntry 1 }

-- configured health monitors
loadBalancerHMONTable   OBJECT-TYPE
    SYNTAX      SEQUENCE OF LoadBalancerHMONEntry
    ACCESS      not-accessible
    STATUS      mandatory
    DESCRIPTION
            "A list of load balancer health monitor assignments."

        ::=     { loadBalancers 6 }


loadBalancerHMONEntry OBJECT-TYPE
    SYNTAX      LoadBalancerHMONEntry
    ACCESS      not-accessible
    STATUS      mandatory
    DESCRIPTION
            "Indicates a health monitor to load balancer assignment by
            identifying healthMonitorIndex of the health monitor
            assigned to the load balancer"

    INDEX       { lPanIndex, loadBalancerIndex, loadBalancerHMONIndex }
        ::=     { loadBalancerHMONTable 1 }


LoadBalancerHMONEntry ::=
    SEQUENCE {
        loadBalancerHMONIndex
            INTEGER (1..2147483647)
    }


loadBalancerHMONIndex OBJECT-TYPE
    SYNTAX      INTEGER (1..2147483647)
    ACCESS      read-only
    STATUS      mandatory
    DESCRIPTION
            "An integer value identifying the healthMonitorIndex of the
            health monitor mapped to the load balancer."

        ::=     { loadBalancerHMONEntry 1 }


-- configured executable resources
loadBalancerExResTable   OBJECT-TYPE
    SYNTAX      SEQUENCE OF LoadBalancerExResEntry
    ACCESS      not-accessible
    STATUS      mandatory
    DESCRIPTION
            "A list of load balancer executable resource assignments."

        ::=     { loadBalancers 7 }


loadBalancerExResEntry OBJECT-TYPE
    SYNTAX      LoadBalancerExResEntry
    ACCESS      not-accessible
    STATUS      mandatory
    DESCRIPTION
            "Indicates a executable resource to load balancer assignment by
            identifying executableResourceIndex of the executable resource
            assigned to the load balancer"

    INDEX       { lPanIndex, loadBalancerIndex, loadBalancerExResIndex }
        ::=     { loadBalancerExResTable 1 }


LoadBalancerExResEntry ::=
    SEQUENCE {
        loadBalancerExResIndex
            INTEGER (1..2147483647)
    }


loadBalancerExResIndex OBJECT-TYPE
    SYNTAX      INTEGER (1..2147483647)
    ACCESS      read-only
    STATUS      mandatory
    DESCRIPTION
            "An integer value identifying the executableResourceIndex of the
            executable resource mapped to the load balancer."

        ::=     { loadBalancerExResEntry 1 }


-- configured SCSI disk resources
loadBalancerSCSIResTable   OBJECT-TYPE
    SYNTAX      SEQUENCE OF LoadBalancerSCSIResEntry
    ACCESS      not-accessible
    STATUS      mandatory
    DESCRIPTION
            "A list of load balancer SCSI disk resource assignments."

        ::=     { loadBalancers 8 }


loadBalancerSCSIResEntry OBJECT-TYPE
    SYNTAX      LoadBalancerSCSIResEntry
    ACCESS      not-accessible
    STATUS      mandatory
    DESCRIPTION
            "Indicates a SCSIRes disk resource to load balancer assignment by
            identifying scsiDiskResourceIndex of the SCSI disk resource
            assigned to the load balancer"

    INDEX       { lPanIndex, loadBalancerIndex, loadBalancerSCSIResIndex }
        ::=     { loadBalancerSCSIResTable 1 }


LoadBalancerSCSIResEntry ::=
    SEQUENCE {
        loadBalancerSCSIResIndex
            INTEGER (1..2147483647)
    }


loadBalancerSCSIResIndex OBJECT-TYPE
    SYNTAX      INTEGER (1..2147483647)
    ACCESS      read-only
    STATUS      mandatory
    DESCRIPTION
            "An integer value identifying the scsiDiskResourceIndex of the
            SCSI disk resource mapped to the load balancer."

        ::=     { loadBalancerSCSIResEntry 1 }


-- configured NFS resources
loadBalancerNFSResTable   OBJECT-TYPE
    SYNTAX      SEQUENCE OF LoadBalancerNFSResEntry
    ACCESS      not-accessible
    STATUS      mandatory
    DESCRIPTION
            "A list of load balancer NFS resource assignments."

        ::=     { loadBalancers 9 }


loadBalancerNFSResEntry OBJECT-TYPE
    SYNTAX      LoadBalancerNFSResEntry
    ACCESS      not-accessible
    STATUS      mandatory
    DESCRIPTION
            "Indicates an NFS resource to load balancer assignment by
            identifying nfsResourceIndex of the NFS resource
            assigned to the load balancer"

    INDEX       { lPanIndex, loadBalancerIndex, loadBalancerNFSResIndex }
        ::=     { loadBalancerNFSResTable 1 }


LoadBalancerNFSResEntry ::=
    SEQUENCE {
        loadBalancerNFSResIndex
            INTEGER (1..2147483647)
    }


loadBalancerNFSResIndex OBJECT-TYPE
    SYNTAX      INTEGER (1..2147483647)
    ACCESS      read-only
    STATUS      mandatory
    DESCRIPTION
            "An integer value identifying the nfsResourceIndex of the
            NFS resource mapped to the load balancer."

        ::=     { loadBalancerNFSResEntry 1 }


-- configured network resources
loadBalancerNetResTable   OBJECT-TYPE
    SYNTAX      SEQUENCE OF LoadBalancerNetResEntry
    ACCESS      not-accessible
    STATUS      mandatory
    DESCRIPTION
            "A list of load balancer Network resource assignments."

        ::=     { loadBalancers 10 }


loadBalancerNetResEntry OBJECT-TYPE
    SYNTAX      LoadBalancerNetResEntry
    ACCESS      not-accessible
    STATUS      mandatory
    DESCRIPTION
            "Indicates a Network resource to load balancer assignment by
            identifying networkResourceIndex of the Network resource
            assigned to the load balancer"

    INDEX       { lPanIndex, loadBalancerIndex, loadBalancerNetResIndex }
        ::=     { loadBalancerNetResTable 1 }


LoadBalancerNetResEntry ::=
    SEQUENCE {
        loadBalancerNetResIndex
            INTEGER (1..2147483647)
    }


loadBalancerNetResIndex OBJECT-TYPE
    SYNTAX      INTEGER (1..2147483647)
    ACCESS      read-only
    STATUS      mandatory
    DESCRIPTION
            "An integer value identifying the networkResourceIndex of the
            executable resource mapped to the load balancer."

        ::=     { loadBalancerNetResEntry 1 }


applicationResources OBJECT IDENTIFIER ::= { lPans 6 }

failoverPolicies OBJECT IDENTIFIER ::= { applicationResources 1 }

FOPSelectionPolicyType ::= INTEGER {
    ordered(1),
    round-robin(2),
    undefined(999)
}

failoverPolicyTable   OBJECT-TYPE
    SYNTAX      SEQUENCE OF FailoverPolicyEntry
    ACCESS      not-accessible
    STATUS      mandatory
    DESCRIPTION
            "A list of entries describing failover policies."

        ::=     { failoverPolicies 1 }


failoverPolicyEntry OBJECT-TYPE
    SYNTAX      FailoverPolicyEntry
    ACCESS      not-accessible
    STATUS      mandatory
    DESCRIPTION
            "A list of attributes describing a failover policy"

    INDEX       { lPanIndex, failoverPolicyIndex }
        ::=     { failoverPolicyTable 1 }


FailoverPolicyEntry ::=
    SEQUENCE {
        failoverPolicyIndex
            INTEGER (1..2147483647),
        failoverPolicyLPANIndex
            INTEGER (1..2147483647),
        failoverPolicyName
            DisplayString,
        failoverPolicyDescription
            DisplayString,
        failoverPolicySelectionPolicy
            FOPSelectionPolicyType,
        failoverPolicyAutoFailback
            TruthValue,
        failoverPolicyRebootPServer
            TruthValue
    }


failoverPolicyIndex OBJECT-TYPE
    SYNTAX      INTEGER (1..2147483647)
    ACCESS      read-only
    STATUS      mandatory
    DESCRIPTION
            "An integer value identifying the failover policy within the
            LPAN."

        ::=     { failoverPolicyEntry 1 }


failoverPolicyLPANIndex OBJECT-TYPE
    SYNTAX      INTEGER (1..2147483647)
    ACCESS      read-only
    STATUS      mandatory
    DESCRIPTION
            "An integer value identifying the lPanIndex value of the
            LPAN that hosts this failover policy."

        ::=     { failoverPolicyEntry 2 }

failoverPolicyName OBJECT-TYPE
    SYNTAX      DisplayString
    ACCESS      read-only
    STATUS      mandatory
    DESCRIPTION
            "A textual String identifying the failover policy."

        ::=     { failoverPolicyEntry 3 }


failoverPolicyDescription OBJECT-TYPE
    SYNTAX      DisplayString
    ACCESS      read-only
    STATUS      mandatory
    DESCRIPTION
            "A textual string describing the failover policy."

        ::=     { failoverPolicyEntry 4 }


failoverPolicySelectionPolicy OBJECT-TYPE
    SYNTAX      FOPSelectionPolicyType
    ACCESS      read-only
    STATUS      mandatory
    DESCRIPTION
            "Indicates the selection policy used by the failover policy
            to determine the next pServer to host the application or
            load balancer."

        ::=     { failoverPolicyEntry 5 }


failoverPolicyAutoFailback OBJECT-TYPE
    SYNTAX      TruthValue
    ACCESS      read-only
    STATUS      mandatory
    DESCRIPTION
            "Indicates whether or not the failover policy is configured for
            auto-failback"

        ::=     { failoverPolicyEntry 6 }


failoverPolicyRebootPServer OBJECT-TYPE
    SYNTAX      TruthValue
    ACCESS      read-only
    STATUS      mandatory
    DESCRIPTION
            "Indicates wether or not the pServer failed over from should
            be rebooted"

        ::=     { failoverPolicyEntry 7 }

-- failover policy member pServers
failoverPolicyPServerTable   OBJECT-TYPE
    SYNTAX      SEQUENCE OF FailoverPolicyPServerEntry
    ACCESS      not-accessible
    STATUS      mandatory
    DESCRIPTION
            "A list of entries describing failover policy member pServers."

        ::=     { failoverPolicies 2 }


failoverPolicyPServerEntry OBJECT-TYPE
    SYNTAX      FailoverPolicyPServerEntry
    ACCESS      not-accessible
    STATUS      mandatory
    DESCRIPTION
            "A list of attributes describing each failover policy pServer
            member"

    INDEX       { lPanIndex, failoverPolicyIndex, failoverPolicyPServerIndex }
        ::=     { failoverPolicyPServerTable 1 }


FailoverPolicyPServerEntry ::=
    SEQUENCE {
        failoverPolicyPServerIndex
            INTEGER (1..2147483647),
        failoverPolicyPServerOrder
            INTEGER
    }


failoverPolicyPServerIndex OBJECT-TYPE
    SYNTAX      INTEGER (1..2147483647)
    ACCESS      read-only
    STATUS      mandatory
    DESCRIPTION
            "An integer value identifying the pServerIndex value of the
            pServer member of this failover policy."

        ::=     { failoverPolicyPServerEntry 1 }

failoverPolicyPServerOrder OBJECT-TYPE
    SYNTAX      INTEGER
    ACCESS      read-only
    STATUS      mandatory
    DESCRIPTION
            "An integer value identifying the activation order of this pServer
            within the failover policy."

        ::=     { failoverPolicyPServerEntry 2 }


healthMonitors OBJECT IDENTIFIER ::= { applicationResources 2 }

HealthMonPolicyType ::= INTEGER {
    any-started(1),
    all-started(2),
    undefined(999)
}


healthMonitorTable   OBJECT-TYPE
    SYNTAX      SEQUENCE OF HealthMonitorEntry
    ACCESS      not-accessible
    STATUS      mandatory
    DESCRIPTION
            "A list of entries describing application/load balancer
            health monitors."

        ::=     { healthMonitors 1 }


healthMonitorEntry OBJECT-TYPE
    SYNTAX      HealthMonitorEntry
    ACCESS      not-accessible
    STATUS      mandatory
    DESCRIPTION
            "A list of attributes describing a failover policy"

    INDEX       { lPanIndex, healthMonitorIndex }
        ::=     { healthMonitorTable 1 }


HealthMonitorEntry ::=
    SEQUENCE {
        healthMonitorIndex
            INTEGER (1..2147483647),
        healthMonitorLPANIndex
            INTEGER (1..2147483647),
        healthMonitorName
            DisplayString,
        healthMonitorDescription
            DisplayString,
        healthMonitorScript
            DisplayString,
        healthMonitorRestartPolicy
            HealthMonPolicyType,
        healthMonitorRestartThreshold
            INTEGER,
        healthMonitorFailoverPolicy
            HealthMonPolicyType,
        healthMonitorFailoverThreshold
            INTEGER,
        healthMonitorGiveupPolicy
            HealthMonPolicyType,
        healthMonitorGiveupThreshold
            INTEGER
    }

healthMonitorIndex OBJECT-TYPE
    SYNTAX      INTEGER (1..2147483647)
    ACCESS      read-only
    STATUS      mandatory
    DESCRIPTION
            "An integer value identifying the health monitor within the
            LPAN."

        ::=     { healthMonitorEntry 1 }


healthMonitorLPANIndex OBJECT-TYPE
    SYNTAX      INTEGER (1..2147483647)
    ACCESS      read-only
    STATUS      mandatory
    DESCRIPTION
            "An integer value identifying the lPanIndex value of the
            LPAN that hosts this health monitor."

        ::=     { healthMonitorEntry 2 }


healthMonitorName OBJECT-TYPE
    SYNTAX      DisplayString
    ACCESS      read-only
    STATUS      mandatory
    DESCRIPTION
            "A textual string identifying the health monitor."

        ::=     { healthMonitorEntry 3 }


healthMonitorDescription OBJECT-TYPE
    SYNTAX      DisplayString
    ACCESS      read-only
    STATUS      mandatory
    DESCRIPTION
            "A textual string describing the health monitor."

        ::=     { healthMonitorEntry 4 }


healthMonitorScript OBJECT-TYPE
    SYNTAX      DisplayString
    ACCESS      read-only
    STATUS      mandatory
    DESCRIPTION
            "The health monitor script (and arguments) used to test the
            health of the application."

        ::=     { healthMonitorEntry 5 }


healthMonitorRestartPolicy OBJECT-TYPE
    SYNTAX      HealthMonPolicyType
    ACCESS      read-only
    STATUS      mandatory
    DESCRIPTION
            "Indicates whether any health monitor or all health monitors
            must reach the configured threshold before a restart is invoked."

        ::=     { healthMonitorEntry 6 }


healthMonitorRestartThreshold OBJECT-TYPE
    SYNTAX      INTEGER
    ACCESS      read-only
    STATUS      mandatory
    DESCRIPTION
            "The number of consecutive health monitor detected failures
            required before a restart is invoked on the monitored application
            or load balancer"

        ::=     { healthMonitorEntry 7 }


healthMonitorFailoverPolicy OBJECT-TYPE
    SYNTAX      HealthMonPolicyType
    ACCESS      read-only
    STATUS      mandatory
    DESCRIPTION
            "Indicates whether any health monitor or all health monitors
            must reach the configured threshold before a failover is invoked."

        ::=     { healthMonitorEntry 8 }


healthMonitorFailoverThreshold OBJECT-TYPE
    SYNTAX      INTEGER
    ACCESS      read-only
    STATUS      mandatory
    DESCRIPTION
            "The number of consecutive health monitor detected failures
            required before a failover is invoked on the monitored application
            or load balancer"

        ::=     { healthMonitorEntry 9 }


healthMonitorGiveupPolicy OBJECT-TYPE
    SYNTAX      HealthMonPolicyType
    ACCESS      read-only
    STATUS      mandatory
    DESCRIPTION
            "Indicates whether any health monitor or all health monitors
            must reach the configured threshold before a give-up occurs."

        ::=     { healthMonitorEntry 10 }


healthMonitorGiveupThreshold OBJECT-TYPE
    SYNTAX      INTEGER (1..2147483647)
    ACCESS      read-only
    STATUS      mandatory
    DESCRIPTION
            "The number of consecutive health monitor detected failures
            required before a givup occurs for the monitored application
            or load balancer"

        ::=     { healthMonitorEntry 11 }


healthMonitorPServerTable   OBJECT-TYPE
    SYNTAX      SEQUENCE OF HealthMonitorPServerEntry
    ACCESS      not-accessible
    STATUS      mandatory
    DESCRIPTION
            "A list of entries describing pServers that host this
            health monitor."

        ::=     { healthMonitors 2 }


healthMonitorPServerEntry OBJECT-TYPE
    SYNTAX      HealthMonitorPServerEntry
    ACCESS      not-accessible
    STATUS      mandatory
    DESCRIPTION
            "A list of attributes describing a health monitor host pServer."

    INDEX       { lPanIndex, healthMonitorIndex, healthMonitorPServerIndex }
        ::=     { healthMonitorPServerTable 1 }


HealthMonitorPServerEntry ::=
    SEQUENCE {
        healthMonitorPServerIndex
            INTEGER (1..2147483647),
        healthMonitorInterval
            INTEGER,
        healthMonitorStartupDelay
            INTEGER
    }

healthMonitorPServerIndex OBJECT-TYPE
    SYNTAX      INTEGER (1..2147483647)
    ACCESS      read-only
    STATUS      mandatory
    DESCRIPTION
            "An integer value identifying the pServerIndex value of the
            pServer that hosts this health monitor.  The value 999 is used
            to identify the 'local' pServer.  If local settings are configured,
            the health monitor will use these settings whenever the monitor
            and the monitored application or load balancer are hosted by the
            same pServer."

        ::=     { healthMonitorPServerEntry 1 }


healthMonitorInterval OBJECT-TYPE
    SYNTAX      INTEGER
    ACCESS      read-only
    STATUS      mandatory
    DESCRIPTION
            "The polling frequency in seconds that this monitor test an
            application or loadbalancer health."

        ::=     { healthMonitorPServerEntry 2 }


healthMonitorStartupDelay OBJECT-TYPE
    SYNTAX      INTEGER
    ACCESS      read-only
    STATUS      mandatory
    DESCRIPTION
            "The startup dely in seconds that this monitor waits after
            application or loadbalancer start before the monitor begins
            checking the health of the application or load balancer."

        ::=     { healthMonitorPServerEntry 3 }


executableResources OBJECT IDENTIFIER ::= { applicationResources 3 }


executableResourceTable   OBJECT-TYPE
    SYNTAX      SEQUENCE OF ExecutableResourceEntry
    ACCESS      not-accessible
    STATUS      mandatory
    DESCRIPTION
            "A list of entries describing application/load balancer
            executable resources."

        ::=     { executableResources 1 }


executableResourceEntry OBJECT-TYPE
    SYNTAX      ExecutableResourceEntry
    ACCESS      not-accessible
    STATUS      mandatory
    DESCRIPTION
            "A list of attributes describing an executable resource."

    INDEX       { lPanIndex, executableResourceIndex }
        ::=     { executableResourceTable 1 }


ExecutableResourceEntry ::=
    SEQUENCE {
        executableResourceIndex
            INTEGER (1..2147483647),
        executableResourceLPANIndex
            INTEGER (1..2147483647),
        executableResourceName
            DisplayString,
        executableResourceDescription
            DisplayString,
        executableResourceUser
            DisplayString,
        executableResourceCommand
            DisplayString,
        executableResourceStartArgs
            DisplayString,
        executableResourceStopArgs
            DisplayString,
        executableResourceExecuteArgs
            DisplayString
    }


executableResourceIndex OBJECT-TYPE
    SYNTAX      INTEGER (1..2147483647)
    ACCESS      read-only
    STATUS      mandatory
    DESCRIPTION
            "An integer value identifying the executable resource within the
            LPAN."

        ::=     { executableResourceEntry 1 }


executableResourceLPANIndex OBJECT-TYPE
    SYNTAX      INTEGER (1..2147483647)
    ACCESS      read-only
    STATUS      mandatory
    DESCRIPTION
            "An integer value identifying the lPanIndex value of the
            LPAN that hosts this executable resource."

        ::=     { executableResourceEntry 2 }


executableResourceName OBJECT-TYPE
    SYNTAX      DisplayString
    ACCESS      read-only
    STATUS      mandatory
    DESCRIPTION
            "A textual string identifying the executable resource."

        ::=     { executableResourceEntry 3 }


executableResourceDescription OBJECT-TYPE
    SYNTAX      DisplayString
    ACCESS      read-only
    STATUS      mandatory
    DESCRIPTION
            "A textual string describing the executable resource."

        ::=     { executableResourceEntry 4 }


executableResourceUser OBJECT-TYPE
    SYNTAX      DisplayString
    ACCESS      read-only
    STATUS      mandatory
    DESCRIPTION
            "A textual string identifying the user that will execute
            the resource."

        ::=     { executableResourceEntry 5 }

executableResourceCommand OBJECT-TYPE
    SYNTAX      DisplayString
    ACCESS      read-only
    STATUS      mandatory
    DESCRIPTION
            "A textual string identifying the command used to start, stop,
            or execute the application or resource."

        ::=     { executableResourceEntry 6 }


executableResourceStartArgs OBJECT-TYPE
    SYNTAX      DisplayString
    ACCESS      read-only
    STATUS      mandatory
    DESCRIPTION
            "A textual string identifying the arguments passed to the
            command when starting an application or resoruce."

        ::=     { executableResourceEntry 7 }


executableResourceStopArgs OBJECT-TYPE
    SYNTAX      DisplayString
    ACCESS      read-only
    STATUS      mandatory
    DESCRIPTION
            "A textual string identifying the arguments passed to the
            command when stopping an application or resource."

        ::=     { executableResourceEntry 8 }

executableResourceExecuteArgs OBJECT-TYPE
    SYNTAX      DisplayString
    ACCESS      read-only
    STATUS      mandatory
    DESCRIPTION
            "A textual string identifying the arguments passed to the
            command when executing an application or resource."

        ::=     { executableResourceEntry 9 }


scsiDiskResources OBJECT IDENTIFIER ::= { applicationResources 4 }


scsiDiskResourceTable   OBJECT-TYPE
    SYNTAX      SEQUENCE OF ScsiDiskResourceEntry
    ACCESS      not-accessible
    STATUS      mandatory
    DESCRIPTION
            "A list of entries describing SCSI disk resources."

        ::=     { scsiDiskResources 1 }


scsiDiskResourceEntry OBJECT-TYPE
    SYNTAX      ScsiDiskResourceEntry
    ACCESS      not-accessible
    STATUS      mandatory
    DESCRIPTION
            "A list of attributes describing each SCSI disk resource."

    INDEX       { lPanIndex, scsiDiskResourceIndex }
        ::=     { scsiDiskResourceTable 1 }


ScsiDiskResourceEntry ::=
    SEQUENCE {
        scsiDiskResourceIndex
            INTEGER (1..2147483647),
        scsiDiskResourceLPANIndex
            INTEGER (1..2147483647),
        scsiDiskResourceName
            DisplayString,
        scsiDiskResourceDescription
            DisplayString,
        scsiDiskResourceDiskId
            DisplayString,
        scsiDiskResourceDiskIdOctets
            OCTET STRING (SIZE(4))
    }


scsiDiskResourceIndex OBJECT-TYPE
    SYNTAX      INTEGER (1..2147483647)
    ACCESS      read-only
    STATUS      mandatory
    DESCRIPTION
            "An integer value identifying the SCSI disk resource within the
            LPAN."

        ::=     { scsiDiskResourceEntry 1 }


scsiDiskResourceLPANIndex OBJECT-TYPE
    SYNTAX      INTEGER (1..2147483647)
    ACCESS      read-only
    STATUS      mandatory
    DESCRIPTION
            "An integer value identifying the lPanIndex value of the
            LPAN that hosts this SCSI disk resource."

        ::=     { scsiDiskResourceEntry 2 }


scsiDiskResourceName OBJECT-TYPE
    SYNTAX      DisplayString
    ACCESS      read-only
    STATUS      mandatory
    DESCRIPTION
            "A textual string identifying the SCSI disk resource."

        ::=     { scsiDiskResourceEntry 3 }


scsiDiskResourceDescription OBJECT-TYPE
    SYNTAX      DisplayString
    ACCESS      read-only
    STATUS      mandatory
    DESCRIPTION
            "A textual string describing the SCSI disk resource."

        ::=     { scsiDiskResourceEntry 4 }


scsiDiskResourceDiskId OBJECT-TYPE
    SYNTAX      DisplayString
    ACCESS      read-only
    STATUS      mandatory
    DESCRIPTION
            "A human readable string consisting of dot separated values
            of HBA number, BUS ID, target device ID and LUN of the SCSI
            disk contained in this resource. 0.0.0.0 indicates an
            unconfigured disk."

        ::=     { scsiDiskResourceEntry 5 }


scsiDiskResourceDiskIdOctets OBJECT-TYPE
    SYNTAX      OCTET STRING (SIZE(4))
    ACCESS      read-only
    STATUS      mandatory
    DESCRIPTION
            "A sequence of 4 bytes encoding the values of HBA number,
            BUS ID, target device ID and LUN of the SCSI disk contained
            in this resource.  0.0.0.0 indicates an unconfigured disk."

        ::=     { scsiDiskResourceEntry 6 }



AccessMode ::= INTEGER {
    access-read-only(1),
    access-read-write(2),
    undefined(999)
}

scsiDiskResMountPtTable   OBJECT-TYPE
    SYNTAX      SEQUENCE OF ScsiDiskResMountPtEntry
    ACCESS      not-accessible
    STATUS      mandatory
    DESCRIPTION
            "A list of entries describing SCSI disk resources mount
            points."

        ::=     { scsiDiskResources 2 }


scsiDiskResMountPtEntry OBJECT-TYPE
    SYNTAX      ScsiDiskResMountPtEntry
    ACCESS      not-accessible
    STATUS      mandatory
    DESCRIPTION
            "A list of attributes describing each SCSI disk resource
            mount point"

    INDEX       { lPanIndex, scsiDiskResourceIndex, scsiDiskResMountPtIndex }
        ::=     { scsiDiskResMountPtTable 1 }


ScsiDiskResMountPtEntry ::=
    SEQUENCE {
        scsiDiskResMountPtIndex
            INTEGER (1..2147483647),
        scsiDiskResMountPtName
            DisplayString,
        scsiDiskResMountPtPartition
            DisplayString,
        scsiDiskResMountPtAccessMode
            AccessMode,
        scsiDiskResMountPtCreateMount
            TruthValue,
        scsiDiskResMountPtScanDisk
            TruthValue,
        scsiDiskResMountPtOrder
            INTEGER,
        scsiDiskResMountPtMountOption
            DisplayString
    }


scsiDiskResMountPtIndex OBJECT-TYPE
    SYNTAX      INTEGER (1..2147483647)
    ACCESS      read-only
    STATUS      mandatory
    DESCRIPTION
            "An integer value identifying the SCSI disk resource mount point
            within the SCSI disk resource."

        ::=     { scsiDiskResMountPtEntry 1 }


scsiDiskResMountPtName OBJECT-TYPE
    SYNTAX      DisplayString
    ACCESS      read-only
    STATUS      mandatory
    DESCRIPTION
            "The path name of the mount point"

        ::=     { scsiDiskResMountPtEntry 2 }


scsiDiskResMountPtPartition OBJECT-TYPE
    SYNTAX      DisplayString
    ACCESS      read-only
    STATUS      mandatory
    DESCRIPTION
            "An integer value identifying the partition number on the SCSI
            disk containing the file system to be mounted."

        ::=     { scsiDiskResMountPtEntry 3 }


scsiDiskResMountPtAccessMode OBJECT-TYPE
    SYNTAX      AccessMode
    ACCESS      read-only
    STATUS      mandatory
    DESCRIPTION
            "Indicates whether the file system is mounted read-only or
            read-write."

        ::=     { scsiDiskResMountPtEntry 4 }


scsiDiskResMountPtCreateMount OBJECT-TYPE
    SYNTAX      TruthValue
    ACCESS      read-only
    STATUS      mandatory
    DESCRIPTION
            "Indicates whether or not the mount point should be created
            if it does not exist."

        ::=     { scsiDiskResMountPtEntry 5 }


scsiDiskResMountPtScanDisk OBJECT-TYPE
    SYNTAX      TruthValue
    ACCESS      read-only
    STATUS      mandatory
    DESCRIPTION
            "Indicates whether or not the disk should be scanned
            prior to mounting."

        ::=     { scsiDiskResMountPtEntry 6 }


scsiDiskResMountPtOrder OBJECT-TYPE
    SYNTAX      INTEGER
    ACCESS      read-only
    STATUS      mandatory
    DESCRIPTION
            "Indicates the order in which the file system should be mounted.
            0 indicates unordered mounting."

        ::=     { scsiDiskResMountPtEntry 7 }


scsiDiskResMountPtMountOption OBJECT-TYPE
    SYNTAX      DisplayString
    ACCESS      read-only
    STATUS      mandatory
    DESCRIPTION
            "Indicates any options to be used when mounting the filesystem."

        ::=     { scsiDiskResMountPtEntry 8 }


nfsResources OBJECT IDENTIFIER ::= { applicationResources 5 }


nfsResourceTable   OBJECT-TYPE
    SYNTAX      SEQUENCE OF NfsResourceEntry
    ACCESS      not-accessible
    STATUS      mandatory
    DESCRIPTION
            "A list of entries describing NFS resources."

        ::=     { nfsResources 1 }


nfsResourceEntry OBJECT-TYPE
    SYNTAX      NfsResourceEntry
    ACCESS      not-accessible
    STATUS      mandatory
    DESCRIPTION
            "A list of attributes describing each NFS resource."

    INDEX       { lPanIndex, nfsResourceIndex }
        ::=     { nfsResourceTable 1 }


NfsResourceEntry ::=
    SEQUENCE {
        nfsResourceIndex
            INTEGER (1..2147483647),
        nfsResourceLPANIndex
            INTEGER (1..2147483647),
        nfsResourceName
            DisplayString,
        nfsResourceDescription
            DisplayString,
        nfsResourceHostName
            DisplayString,
        nfsResourceHostFileSystem
            DisplayString,
        nfsResourceAccessMode
            AccessMode,
        nfsResourceUser
            DisplayString,
        nfsResourceMountPoint
            DisplayString,
        nfsResourceCreateMountPt
            TruthValue,
        nfsResourceMountOption
            DisplayString
    }


nfsResourceIndex OBJECT-TYPE
    SYNTAX      INTEGER (1..2147483647)
    ACCESS      read-only
    STATUS      mandatory
    DESCRIPTION
            "An integer value identifying the NFS resource resource within the
            LPAN."

        ::=     { nfsResourceEntry 1 }


nfsResourceLPANIndex OBJECT-TYPE
    SYNTAX      INTEGER (1..2147483647)
    ACCESS      read-only
    STATUS      mandatory
    DESCRIPTION
            "An integer value identifying the lPanIndex value of the
            LPAN that hosts this NFS resource."

        ::=     { nfsResourceEntry 2 }


nfsResourceName OBJECT-TYPE
    SYNTAX      DisplayString
    ACCESS      read-only
    STATUS      mandatory
    DESCRIPTION
            "A textual string identifying the NFS resource."

        ::=     { nfsResourceEntry 3 }


nfsResourceDescription OBJECT-TYPE
    SYNTAX      DisplayString
    ACCESS      read-only
    STATUS      mandatory
    DESCRIPTION
            "A textual string describing the NFS resource."

        ::=     { nfsResourceEntry 4 }


nfsResourceHostName OBJECT-TYPE
    SYNTAX      DisplayString
    ACCESS      read-only
    STATUS      mandatory
    DESCRIPTION
            "A textual string identifying the host name (or IP address) that
            hosts this resource."

        ::=     { nfsResourceEntry 5 }


nfsResourceHostFileSystem OBJECT-TYPE
    SYNTAX      DisplayString
    ACCESS      read-only
    STATUS      mandatory
    DESCRIPTION
            "The path name of the exported NFS filesystem."

        ::=     { nfsResourceEntry 7 }


nfsResourceAccessMode OBJECT-TYPE
    SYNTAX      AccessMode
    ACCESS      read-only
    STATUS      mandatory
    DESCRIPTION
            "Indicates whether the NFS filesystem is mounted read-only or
            read-write."

        ::=     { nfsResourceEntry 8 }


nfsResourceUser OBJECT-TYPE
    SYNTAX      DisplayString
    ACCESS      read-only
    STATUS      mandatory
    DESCRIPTION
            "A textual string identifying the user that will mount
            the NFS resource."

        ::=     { nfsResourceEntry 9 }


nfsResourceMountPoint OBJECT-TYPE
    SYNTAX      DisplayString
    ACCESS      read-only
    STATUS      mandatory
    DESCRIPTION
            "The path of the mount point for the NFS resource."

        ::=     { nfsResourceEntry 10 }


nfsResourceCreateMountPt OBJECT-TYPE
    SYNTAX      TruthValue
    ACCESS      read-only
    STATUS      mandatory
    DESCRIPTION
            "Indicates whether or not the mount point should be created
            if it doesn't already exist."

        ::=     { nfsResourceEntry 11 }


nfsResourceMountOption OBJECT-TYPE
    SYNTAX      DisplayString
    ACCESS      read-only
    STATUS      mandatory
    DESCRIPTION
            "Indicates any options to be used when mounting the NFS resource."

        ::=     { nfsResourceEntry 12 }


networkResources OBJECT IDENTIFIER ::= { applicationResources 6 }

NetworkResourceType ::= INTEGER {
     vEth(1),       -- network resource is associated with a specific vEth
     vSwitch(2),    -- network resource is associated with a specific vSwtich
     undefined(999)
}

networkResourceTable   OBJECT-TYPE
    SYNTAX      SEQUENCE OF NetworkResourceEntry
    ACCESS      not-accessible
    STATUS      mandatory
    DESCRIPTION
            "A list of entries describing NFS resources."

        ::=     { networkResources 1 }


networkResourceEntry OBJECT-TYPE
    SYNTAX      NetworkResourceEntry
    ACCESS      not-accessible
    STATUS      mandatory
    DESCRIPTION
            "A list of attributes describing each NFS resource."

    INDEX       { lPanIndex, networkResourceIndex }
        ::=     { networkResourceTable 1 }


NetworkResourceEntry ::=
    SEQUENCE {
        networkResourceIndex
            INTEGER (1..2147483647),
        networkResourceLPANIndex
            INTEGER (1..2147483647),
        networkResourceName
            DisplayString,
        networkResourceDescription
            DisplayString,
        networkResourceType
            NetworkResourceType,
        networkResourceMACAddressOctets
            PhysAddress,
        networkResourceMACAddressString
            DisplayString,
        networkResourceRateLimit
            INTEGER
    }


networkResourceIndex OBJECT-TYPE
    SYNTAX      INTEGER (1..2147483647)
    ACCESS      read-only
    STATUS      mandatory
    DESCRIPTION
            "An integer value identifying the network resource within
            the LPAN."

        ::=     { networkResourceEntry 1 }


networkResourceLPANIndex OBJECT-TYPE
    SYNTAX      INTEGER (1..2147483647)
    ACCESS      read-only
    STATUS      mandatory
    DESCRIPTION
            "An integer value identifying the lPanIndex value of the
            LPAN that hosts this network resource."

        ::=     { networkResourceEntry 2 }


networkResourceName OBJECT-TYPE
    SYNTAX      DisplayString
    ACCESS      read-only
    STATUS      mandatory
    DESCRIPTION
            "A textual string identifying the network resource."

        ::=     { networkResourceEntry 3 }


networkResourceDescription OBJECT-TYPE
    SYNTAX      DisplayString
    ACCESS      read-only
    STATUS      mandatory
    DESCRIPTION
            "A textual string describing the network resource."

        ::=     { networkResourceEntry 4 }


networkResourceType OBJECT-TYPE
    SYNTAX      NetworkResourceType
    ACCESS      read-only
    STATUS      mandatory
    DESCRIPTION
            "Indicates whether the network resource is assigned to a specific
            vEth or to a specific vSwitch."

        ::=     { networkResourceEntry 5 }


networkResourceMACAddressOctets OBJECT-TYPE
    SYNTAX      PhysAddress
    ACCESS      read-only
    STATUS      mandatory
    DESCRIPTION
            "An encoding of the network resource MAC address."

        ::=     { networkResourceEntry 6 }


networkResourceMACAddressString OBJECT-TYPE
    SYNTAX      DisplayString
    ACCESS      read-only
    STATUS      mandatory
    DESCRIPTION
            "A human readable string representing the newtork resource
            MAC address in the form: '6E:4A:1F:00:01:06'."

        ::=     { networkResourceEntry 7 }


networkResourceRateLimit OBJECT-TYPE
    SYNTAX      INTEGER
    ACCESS      read-only
    STATUS      mandatory
    DESCRIPTION
            "The configured rate limit for the network resource in Mbps, 0
            indicates none or not applicable."

        ::=     { networkResourceEntry 8 }


networkResourceIPTable   OBJECT-TYPE
    SYNTAX      SEQUENCE OF NetworkResourceIPEntry
    ACCESS      not-accessible
    STATUS      mandatory
    DESCRIPTION
            "A list of IP entries associated with each network resource."

        ::=     { networkResources 2 }


networkResourceIPEntry OBJECT-TYPE
    SYNTAX      NetworkResourceIPEntry
    ACCESS      not-accessible
    STATUS      mandatory
    DESCRIPTION
            "A list of attributes describing IP addresses associated with each
            network resource."

    INDEX       { lPanIndex, networkResourceIndex, networkResourceIPIndex }
        ::=     { networkResourceIPTable 1 }


NetworkResourceIPEntry ::=
    SEQUENCE {
        networkResourceIPIndex
            INTEGER (1..2147483647),
        networkResourceIPAddress
            IpAddress,
        networkResourceIPBroadcast
            IpAddress,
        networkResourceIPMask
            IpAddress
    }


networkResourceIPIndex OBJECT-TYPE
    SYNTAX      INTEGER (1..2147483647)
    ACCESS      read-only
    STATUS      mandatory
    DESCRIPTION
            "An integer value identifying the network resource IP address
            within the network resource."

        ::=     { networkResourceIPEntry 1 }


networkResourceIPAddress OBJECT-TYPE
    SYNTAX      IpAddress
    ACCESS      read-only
    STATUS      mandatory
    DESCRIPTION
            "The IP address configured on this network resource"

        ::=     { networkResourceIPEntry 2 }


networkResourceIPBroadcast OBJECT-TYPE
    SYNTAX      IpAddress
    ACCESS      read-only
    STATUS      mandatory
    DESCRIPTION
            "The broadcast address configured on this network resource)"

        ::=     { networkResourceIPEntry 3 }


networkResourceIPMask OBJECT-TYPE
    SYNTAX      IpAddress
    ACCESS      read-only
    STATUS      mandatory
    DESCRIPTION
            "The network mask configured on this network resource"

        ::=     { networkResourceIPEntry 4 }



-- egenera notifications

egeneraNotifications OBJECT IDENTIFIER ::= { management 1000 }

egeneraNotificationObjects OBJECT IDENTIFIER ::= { egeneraNotifications 1 }

-- The following objects can not be read from agents, they exist
-- only in traps sent by the agents.

egeneraTrapSeverity OBJECT-TYPE
    SYNTAX      INTEGER
    ACCESS      read-only
    STATUS      mandatory
    DESCRIPTION
            "An integer variable identifying trap severity.  This value is
            set and packaged in every notification or trap sent."

        ::=     { egeneraNotificationObjects 1 }


egeneraTrapMessage OBJECT-TYPE
    SYNTAX      DisplayString
    ACCESS      read-only
    STATUS      mandatory
    DESCRIPTION
            "An string containing a message associated with each trap.  This
            value is set and packaged in every notification or trap sent."

        ::=     { egeneraNotificationObjects 2 }



snmpManagerAddress OBJECT-TYPE
    SYNTAX      DisplayString
    ACCESS      read-only
    STATUS      mandatory
    DESCRIPTION
            "A string containing the source IP address of illegal SNMP
            requests."

        ::=     { egeneraNotificationObjects 3 }


sensorName OBJECT-TYPE
    SYNTAX      DisplayString
    ACCESS      read-only
    STATUS      mandatory
    DESCRIPTION
            "The textual name of the hardware sensor contained in pBlade, cBlade
            and sBlade voltage, temperature, and fanspeed hardware sensor
            threshold events"

        ::=     { egeneraNotificationObjects 6 }

sensorThreshold OBJECT-TYPE
    SYNTAX      INTEGER
    ACCESS      read-only
    STATUS      mandatory
    DESCRIPTION
            "The integer representation of the hardware threshold exceeded contained in
            hardware sensor threshold events.  Voltage values are multiplied by 100 and
            rounded to convert from float to integer, thus 2.98 => 298"

        ::=     { egeneraNotificationObjects 7 }


sensorValue OBJECT-TYPE
    SYNTAX      INTEGER
    ACCESS      read-only
    STATUS      mandatory
    DESCRIPTION
            "The integer representation of the hardware sensor value contained in hardware
            sensor threshold events.  Voltage values are multiplied by 100 and rounted to
            convert from float to integer.  Thus 0.530 => 53"

        ::=     { egeneraNotificationObjects 8 }

monitorName OBJECT-TYPE
    SYNTAX      DisplayString
    ACCESS      read-only
    STATUS      mandatory
    DESCRIPTION
            "The textual name of User Defined Monitor driving pServerUserMonitorTraps."

        ::=     { egeneraNotificationObjects 9 }


ruleName OBJECT-TYPE
    SYNTAX      DisplayString
    ACCESS      read-only
    STATUS      mandatory
    DESCRIPTION
            "The textual name of User Defined Monitor Rule that was matched that drives
            pServerUserMonitorTraps."

        ::=     { egeneraNotificationObjects 10 }



-- v1 Trap definitions



bladeFrameUpTrap TRAP-TYPE
    ENTERPRISE  egenera
    VARIABLES {
                bladeFrameIndex,
                bladeFrameName,
                egeneraTrapSeverity,
                egeneraTrapMessage
            }
    DESCRIPTION
            "The notification generated when a BladeFrame enters the Egenera
            PAN (generally when powered on).

            This trap is driven by the 'frame.discover' event type.  This event
            type occurs early during PAN Manager startup, and indicates that the
            BladeFrame has been discovered and that the physical model is being
            constructed.  This trap is primarily intended for environments where
            multiple BladeFrames are managed in the same PAN, however multi-
            BladeFrame management is not yet supported.

            This event type is not user visible, and will not appear in
            CLI or GUI event queries.  The trap exists to satisfy early
            requirements documents.

            Severity: 5"
    --#TYPE         "BladeFrame Up"
    --#SUMMARY      "%s"
    --#ARGUMENTS    { 3 }
    --#SEVERITY     INFORMATIONAL
    --#TIMEINDEX    99
    --#STATE        OPERATIONAL

        ::=     101


bladeFrameDownTrap TRAP-TYPE
    ENTERPRISE  egenera
    VARIABLES {
                bladeFrameIndex,
                bladeFrameName,
                egeneraTrapSeverity,
                egeneraTrapMessage
            }
    DESCRIPTION
            "The notification generated when a BladeFrame departs the Egenera
            PAN (generally when powered off).

            This trap is currently not driven by any event, and thus is not
            emmitted.  The trap is intended to communicate when a BladeFrame
            departs from a BladeFarm in environments where multiple BladeFrames
            are managed in the same PAN, however multi-BladeFrame management
            is not yet supported.  The trap exists to satisfy early
            requirements documents."
     --#TYPE         "BladeFrame Down"
     --#SUMMARY      "%s"
     --#ARGUMENTS    { 3 }
     --#SEVERITY     INFORMATIONAL
     --#TIMEINDEX    99
     --#STATE        NONOPERATIONAL

        ::=     102


bladeFrameDeviceIdMismatchTrap TRAP-TYPE
    ENTERPRISE  egenera
    VARIABLES {
                bladeFrameIndex,
                bladeFrameName,
                egeneraTrapSeverity,
                egeneraTrapMessage
            }
    DESCRIPTION
            "The notification generated Master and Slave cBlades do not
            agree on SCSI device IDs.

            This trap is driven by the 'PAN Manager Device ID Mismatch'
            event type.

            Severity: 1"
    --#TYPE         "BladeFrame Device ID Mismatch"
    --#SUMMARY      "%s"
    --#ARGUMENTS    { 3 }
    --#SEVERITY     CRITICAL
    --#TIMEINDEX    99
    --#STATE        NONOPERATIONAL

        ::=     103

bladeFramePowerOverCommitTrap TRAP-TYPE
    ENTERPRISE  egenera
    VARIABLES {
                bladeFrameIndex,
                bladeFrameName,
                egeneraTrapSeverity,
                egeneraTrapMessage
            }
    DESCRIPTION
            "The notification generated when a power domain has been
            overcommited.

            This trap is driven by 'BladeFrame <framename> Power Domain
            <A|B|C|D> Over Attached Event' event types.

            Severity: 1"
    --#TYPE         "BladeFrame Power Overcommit"
    --#SUMMARY      "%s"
    --#ARGUMENTS    { 3 }
    --#SEVERITY     CRITICAL
    --#TIMEINDEX    99
    --#STATE        DEGRADED

        ::=     104

bladeFramePowerOverDrawTrap TRAP-TYPE
    ENTERPRISE  egenera
    VARIABLES {
                bladeFrameIndex,
                bladeFrameName,
                egeneraTrapSeverity,
                egeneraTrapMessage
            }
    DESCRIPTION
            "The notification generated when a power domain has been
            over drawn.

            This trap is driven by 'BladeFrame <framename> Power Domain
            <A|B|C|D> Over Powered Event' event types.

            Severity: 1"
    --#TYPE         "BladeFrame Power Overdraw"
    --#SUMMARY      "%s"
    --#ARGUMENTS    { 3 }
    --#SEVERITY     CRITICAL
    --#TIMEINDEX    99
    --#STATE        DEGRADED

        ::=     105


bladeFramePowerDeniedTrap TRAP-TYPE
    ENTERPRISE  egenera
    VARIABLES {
                bladeFrameIndex,
                bladeFrameName,
                egeneraTrapSeverity,
                egeneraTrapMessage
            }
    DESCRIPTION
            "The notification generated when a blade power-on is denied
            due to lack of power.

            This trap is driven by 'BladeFrame <framename> Power Domain
            <A|B|C|D> Power On Denied Event' event types.

            Severity: 1"
    --#TYPE         "BladeFrame Power Denied"
    --#SUMMARY      "%s"
    --#ARGUMENTS    { 3 }
    --#SEVERITY     CRITICAL
    --#TIMEINDEX    99
    --#STATE        DEGRADED

        ::=     106


bfArchiveCreateTrap TRAP-TYPE
    ENTERPRISE  egenera
    VARIABLES {
                bladeFrameIndex,
                bladeFrameName,
                egeneraTrapSeverity,
                egeneraTrapMessage
            }
    DESCRIPTION
            "The notification generated when an archive has been created.

            This trap is driven by the 'Archive creation' event type.

            Severity: 5"
     --#TYPE         "Archive Created"
     --#SUMMARY      "%s"
     --#ARGUMENTS    { 3 }
     --#SEVERITY     INFORMATIONAL
     --#TIMEINDEX    99
     --#STATE        OPERATIONAL

        ::=     107


bfArchiveDeleteTrap TRAP-TYPE
    ENTERPRISE  egenera
    VARIABLES {
                bladeFrameIndex,
                bladeFrameName,
                egeneraTrapSeverity,
                egeneraTrapMessage
            }
    DESCRIPTION
            "The notification generated when an archive has been deleted.

            This trap is driven by the 'Archive deletion' event type.

            Severity: 5"
     --#TYPE         "Archive Deleted"
    --#SUMMARY      "%s"
    --#ARGUMENTS    { 3 }
    --#SEVERITY     INFORMATIONAL
    --#TIMEINDEX    99
    --#STATE        OPERATIONAL
        ::=     108


bfArchiveSchedCreateTrap TRAP-TYPE
    ENTERPRISE  egenera
    VARIABLES {
                bladeFrameIndex,
                bladeFrameName,
                egeneraTrapSeverity,
                egeneraTrapMessage
            }
    DESCRIPTION
            "The notification generated when an archive schedule has been
            created.

            This trap is driven by the 'Archive schedule creation' event
            type.

            Severity: 5"
    --#TYPE         "Archive Schedule Created"
    --#SUMMARY      "%s"
    --#ARGUMENTS    { 3 }
    --#SEVERITY     INFORMATIONAL
    --#TIMEINDEX    99
    --#STATE        OPERATIONAL

        ::=     109


bfArchiveSchedDeleteTrap TRAP-TYPE
    ENTERPRISE  egenera
    VARIABLES {
                bladeFrameIndex,
                bladeFrameName,
                egeneraTrapSeverity,
                egeneraTrapMessage
            }
    DESCRIPTION
            "The notification generated when an archive schedule has been
            deleted.

            This trap is driven by the 'Archive schedule deletion' event
            type.

            Severity: 5"
    --#TYPE         "Archive Schedule Deleted"
    --#SUMMARY      "%s"
    --#ARGUMENTS    { 3 }
    --#SEVERITY     INFORMATIONAL
    --#TIMEINDEX    99
    --#STATE        OPERATIONAL

        ::=     110


bfArchiveSchedFailedTrap TRAP-TYPE
    ENTERPRISE  egenera
    VARIABLES {
                bladeFrameIndex,
                bladeFrameName,
                egeneraTrapSeverity,
                egeneraTrapMessage
            }
    DESCRIPTION
            "The notification generated when a scheduled archive fails in the
            PAN.

            This trap is driven by the 'Archive schedule failed' event type.

            Severity: 3"
    --#TYPE         "Archive Schedule Failed"
    --#SUMMARY      "%s"
    --#ARGUMENTS    { 3 }
    --#SEVERITY     MINOR
    --#TIMEINDEX    99
    --#STATE        OPERATIONAL

        ::=     111


bfArchiveSchedModifiedTrap TRAP-TYPE
    ENTERPRISE  egenera
    VARIABLES {
                bladeFrameIndex,
                bladeFrameName,
                egeneraTrapSeverity,
                egeneraTrapMessage
            }
    DESCRIPTION
            "The notification generated when an archive schedule has been
            modified.

            This trap is driven by the 'Archive schedule modification' event
            type.

            Severity: 5"
     --#TYPE         "Archive Schedule Modified"
    --#SUMMARY      "%s"
    --#ARGUMENTS    { 3 }
    --#SEVERITY     INFORMATIONAL
    --#TIMEINDEX    99
    --#STATE        OPERATIONAL

        ::=     112


bfArchiveSchedRunningTrap TRAP-TYPE
    ENTERPRISE  egenera
    VARIABLES {
                bladeFrameIndex,
                bladeFrameName,
                egeneraTrapSeverity,
                egeneraTrapMessage
            }
    DESCRIPTION
            "The notification generated when an archive schedule is run.

            This trap is driven by the 'Archive schedule running' event
            type.

            Severity: 5"
    --#TYPE         "Archive Schedule Running"
    --#SUMMARY      "%s"
    --#ARGUMENTS    { 3 }
    --#SEVERITY     INFORMATIONAL
    --#TIMEINDEX    99
    --#STATE        OPERATIONAL

        ::=     113


bladeFrameMasterRecoveredTrap TRAP-TYPE
    ENTERPRISE  egenera
    VARIABLES {
                bladeFrameIndex,
                bladeFrameName,
                egeneraTrapSeverity,
                egeneraTrapMessage
            }
    DESCRIPTION
            "The notification generated when a BladeFrame is available after
            a failover .

            This trap is driven by the 'BladeFrame Master Recovered Event'
            event type.

            This trap is deprecate as of 4.0.0.

            Severity: 5"
     --#TYPE         "bladeFrame Master Recovered"
    --#SUMMARY      "%s"
    --#ARGUMENTS    { 3 }
    --#SEVERITY     INFORMATIONAL
    --#TIMEINDEX    99
    --#STATE        OPERATIONAL

        ::= 114


bladeFrameREthMisconfigTrap TRAP-TYPE
    ENTERPRISE  egenera
    VARIABLES {
                bladeFrameIndex,
                bladeFrameName,
                egeneraTrapSeverity,
                egeneraTrapMessage
            }
    DESCRIPTION
            "The notification generated when a REth misconfiguration is
            detected.

            This trap is driven by the 'Reth Misconfiguration Event'
            event type.

            Severity: 3"
    --#TYPE         "Reth Misconfigured"
    --#SUMMARY      "%s"
    --#ARGUMENTS    { 3 }
    --#SEVERITY     MINOR
    --#TIMEINDEX    99
    --#STATE        OPERATIONAL

        ::= 115


bfPANManagerDowntimeTrap TRAP-TYPE
    ENTERPRISE  egenera
    VARIABLES {
                bladeFrameIndex,
                bladeFrameName,
                egeneraTrapSeverity,
                egeneraTrapMessage
            }
    DESCRIPTION
            "The notification generated when a PAN Manager reports its own
            downtime.

            This trap is driven by the 'PAN Manager <bladeframe>/c<1|2> Downtime
            Report Event' event type.

            Severity: 5"
    --#TYPE         "PAN Manager Downtime Reported"
    --#SUMMARY      "%s"
    --#ARGUMENTS    { 3 }
    --#SEVERITY     INFORMATIONAL
    --#TIMEINDEX    99
    --#STATE        OPERATIONAL

        ::= 116


bfRccReportPeriodStartTrap TRAP-TYPE
    ENTERPRISE  egenera
    VARIABLES {
                bladeFrameIndex,
                bladeFrameName,
                egeneraTrapSeverity,
                egeneraTrapMessage
            }
    DESCRIPTION
            "The notification generated when the Resource Configuration
            Collector begins a reporting period.

            This trap is driven by the 'RCC Reporting Period Started Event'
            event type.

            Severity: 5"
    --#TYPE         "RCC Reporting Period Started"
    --#SUMMARY      "%s"
    --#ARGUMENTS    { 3 }
    --#SEVERITY     INFORMATIONAL
    --#TIMEINDEX    99
    --#STATE        OPERATIONAL

        ::= 117


bfRccReportPeriodEndTrap TRAP-TYPE
    ENTERPRISE  egenera
    VARIABLES {
                bladeFrameIndex,
                bladeFrameName,
                egeneraTrapSeverity,
                egeneraTrapMessage
            }
    DESCRIPTION
            "The notification generated when the Resource Configuration
            Collector ends a reporting period.

            This trap is driven by the 'RCC Reporting Period Ended Event'
            event type.

            Severity: 5"
     --#TYPE         "RCC Reporting Period Ended"
     --#SUMMARY      "%s"
     --#ARGUMENTS    { 3 }
     --#SEVERITY     INFORMATIONAL
     --#TIMEINDEX    99
     --#STATE        OPERATIONAL

        ::= 118


bfRccExpiredFilesDeletedTrap TRAP-TYPE
    ENTERPRISE  egenera
    VARIABLES {
                bladeFrameIndex,
                bladeFrameName,
                egeneraTrapSeverity,
                egeneraTrapMessage
            }
    DESCRIPTION
            "The notification generated when the Resource Configuration
            Collector deletes expired files.

            This trap is driven by the 'RCC Expired Files Deleted'
            event type.

            Severity: 5"
     --#TYPE         "RCC Expired Files Deleted"
    --#SUMMARY      "%s"
    --#ARGUMENTS    { 3 }
    --#SEVERITY     INFORMATIONAL
    --#TIMEINDEX    99
    --#STATE        OPERATIONAL

        ::= 119

chassisOOBFailureTrap TRAP-TYPE
    ENTERPRISE egenera
    VARIABLES {
                bladeFrameIndex,
                bladeFrameName,
                egeneraTrapSeverity,
                egeneraTrapmessage
              }
    DESCRIPTION
            "The notification generated when there is a failure to execute
            an Out of Band control operation on the chassis.

            This trap is driven by the 'Chassis OOB Failure' event type.

            Severity: 2"
     --#TYPE         "Chassis OOB Failure"
    --#SUMMARY      "%s"
    --#ARGUMENTS    { 3 }
    --#SEVERITY     MAJOR
    --#TIMEINDEX    99
    --#STATE        OPERATIONAL

        ::= 120

bladeDiscoveryCompletedTrap TRAP-TYPE
    ENTERPRISE egenera
    VARIABLES {
                bladeFrameIndex,
                bladeFrameName,
                egeneraTrapSeverity,
                egeneraTrapMessage
              }
    DESCRIPTION
            "The notification generated when we finish the hardware discovery
            process of a blade successfully.  This trap will not be generated
            on all hardware platforms.

            This trap is driven by the 'Blade Discovery Completed'
            event type.

            Severity: 5"
     --#TYPE         "Blade Discovery Completed"
    --#SUMMARY      "%s"
    --#ARGUMENTS    { 3 }
    --#SEVERITY     INFORMATIONAL
    --#TIMEINDEX    99
    --#STATE        OPERATIONAL

        ::= 121

bladeDiscoveryFailedTrap TRAP-TYPE
    ENTERPRISE egenera
    VARIABLES {
                bladeFrameIndex,
                bladeFrameName,
                egeneraTrapSeverity,
                egeneraTrapMessage
              }
    DESCRIPTION
            "The notification generated when we finish the hardware discovery
            process of a blade unsuccessfully.  This trap will not be generated
            on all hardware platforms.

            This trap is driven by the 'Blade Discovery Failed'
            event type.

            Severity: 2"
     --#TYPE         "Blade Discovery Failed"
    --#SUMMARY      "%s"
    --#ARGUMENTS    { 3 }
    --#SEVERITY     MAJOR
    --#TIMEINDEX    99
    --#STATE        OPERATIONAL

        ::= 122

bladeUndiscoveryCompletedTrap TRAP-TYPE
    ENTERPRISE egenera
    VARIABLES {
                bladeFrameIndex,
                bladeFrameName,
                egeneraTrapSeverity,
                egeneraTrapMessage
              }
    DESCRIPTION
            "The notification generated when we finish the hardware undiscovery
            process of a blade successfully.  This trap will not be generated
            on all hardware platforms.

            This trap is driven by the 'Blade Undiscovery Completed'
            event type.

            Severity: 5"
     --#TYPE         "Blade Undiscovery Completed"
    --#SUMMARY      "%s"
    --#ARGUMENTS    { 3 }
    --#SEVERITY     INFORMATIONAL
    --#TIMEINDEX    99
    --#STATE        OPERATIONAL

        ::= 123

bladeUndiscoveryFailedTrap TRAP-TYPE
    ENTERPRISE egenera
    VARIABLES {
                bladeFrameIndex,
                bladeFrameName,
                egeneraTrapSeverity,
                egeneraTrapMessage
              }
    DESCRIPTION
            "The notification generated when we finish the hardware undiscovery
            process of a blade unsuccessfully.  This trap will not be generated
            on all hardware platforms.

            This trap is driven by the 'Blade Undiscovery Failed'
            event type.

            Severity: 2"
     --#TYPE         "Blade Undiscovery Failed"
    --#SUMMARY      "%s"
    --#ARGUMENTS    { 3 }
    --#SEVERITY     MAJOR
    --#TIMEINDEX    99
    --#STATE        OPERATIONAL

        ::= 124

bfIArchiveExportStartTrap TRAP-TYPE
    ENTERPRISE egenera
    VARIABLES {
                bladeFrameIndex,
                bladeFrameName,
                egeneraTrapSeverity,
                egeneraTrapMessage
              }
    DESCRIPTION
            "The notification generated when a blade frame image archive export
            starts.
  
            This trap is driven by the 'Image Archive Export Start' event type.
  
            Severity: 5"
     --#TYPE         "Image Archive Export Start"
    --#SUMMARY      "%s"
    --#ARGUMENTS    { 3 }
    --#SEVERITY     INFORMATIONAL
    --#TIMEINDEX    99
    --#STATE        OPERATIONAL
  
        ::= 125

bfIArchiveExportFinishTrap TRAP-TYPE
    ENTERPRISE egenera
    VARIABLES {
                bladeFrameIndex,
                bladeFrameName,
                egeneraTrapSeverity,
                egeneraTrapMessage
              }
    DESCRIPTION
            "The notification generated when a blade frame image archive export
            finishes.

            This trap is driven by the 'Image Archive Export Finish' event type.

            Severity: 5"
     --#TYPE         "Image Archive Export Finish"
    --#SUMMARY      "%s"
    --#ARGUMENTS    { 3 }
    --#SEVERITY     INFORMATIONAL
    --#TIMEINDEX    99
    --#STATE        OPERATIONAL
  
        ::= 126

bfIArchiveExportFailureTrap TRAP-TYPE
    ENTERPRISE egenera
    VARIABLES {
                bladeFrameIndex,
                bladeFrameName,
                egeneraTrapSeverity,
                egeneraTrapMessage
              }
    DESCRIPTION
            "The notification generated when a blade frame image archive export
            fails.
  
            This trap is driven by the 'Image Archive Export Failure' event type.

            Severity: 2"
     --#TYPE         "Image Archive Export Failure"
    --#SUMMARY      "%s"
    --#ARGUMENTS    { 3 }
    --#SEVERITY     MAJOR
    --#TIMEINDEX    99
    --#STATE        OPERATIONAL

        ::= 127

bfIArchiveRestoreStartTrap TRAP-TYPE
    ENTERPRISE egenera
    VARIABLES {
                bladeFrameIndex,
                bladeFrameName,
                egeneraTrapSeverity,
                egeneraTrapMessage
              }
    DESCRIPTION
            "The notification generated when a blade frame image archive
            restore starts.

            This trap is driven by the 'Image Archive Restore Start' event type.

            Severity: 5"
     --#TYPE         "Image Archive Restore Start"
    --#SUMMARY      "%s"
    --#ARGUMENTS    { 3 }
    --#SEVERITY     INFORMATIONAL
    --#TIMEINDEX    99
    --#STATE        OPERATIONAL
  
        ::= 128

bfIArchiveRestoreFinishTrap TRAP-TYPE
    ENTERPRISE egenera
    VARIABLES {
                bladeFrameIndex,
                bladeFrameName,
                egeneraTrapSeverity,
                egeneraTrapMessage
              }
    DESCRIPTION
            "The notification generated when a blade frame image archive
            restore finishes.
  
            This trap is driven by the 'Image Archive Restore Finish' event type.

            Severity: 5"
     --#TYPE         "Image Archive Restore Finish"
    --#SUMMARY      "%s"
    --#ARGUMENTS    { 3 }
    --#SEVERITY     INFORMATIONAL
    --#TIMEINDEX    99
    --#STATE        OPERATIONAL

        ::= 129

bfIArchiveRestoreFailureTrap TRAP-TYPE
    ENTERPRISE egenera
    VARIABLES {
                bladeFrameIndex,
                bladeFrameName,
                egeneraTrapSeverity,
                egeneraTrapMessage
              }
    DESCRIPTION
            "The notification generated when a blade frame image archive
            restore fails.

            This trap is driven by the 'Image Archive Restore Failure' event type.

            Severity: 2"
     --#TYPE         "Image Archive Restore Failure"
    --#SUMMARY      "%s"
    --#ARGUMENTS    { 3 }
    --#SEVERITY     MAJOR
    --#TIMEINDEX    99
    --#STATE        OPERATIONAL

        ::= 130

licenseAcquiredTrap TRAP-TYPE
    ENTERPRISE egenera
    VARIABLES {
                bladeFrameIndex,
                bladeFrameName,
                egeneraTrapSeverity,
                egeneraTrapMessage
              }
    DESCRIPTION
            "The notification generated when a license is used / acquired.

            This trap is driven by the 'License Acquired' event type.

            Severity: 5"
     --#TYPE         "License Acquired"
    --#SUMMARY      "%s"
    --#ARGUMENTS    { 3 }
    --#SEVERITY     INFORMATIONAL
    --#TIMEINDEX    99
    --#STATE        OPERATIONAL

        ::= 131

licenseReleasedTrap TRAP-TYPE
    ENTERPRISE egenera
    VARIABLES {
                bladeFrameIndex,
                bladeFrameName,
                egeneraTrapSeverity,
                egeneraTrapMessage
              }
    DESCRIPTION
            "The notification generated when a license is released.
  
            This trap is driven by the 'License Released' event type.

            Severity: 5"
     --#TYPE         "License Released"
    --#SUMMARY      "%s"
    --#ARGUMENTS    { 3 }
    --#SEVERITY     INFORMATIONAL
    --#TIMEINDEX    99
    --#STATE        OPERATIONAL
  
        ::= 132

licenseAcquireFailedTrap TRAP-TYPE
    ENTERPRISE egenera
    VARIABLES {
                bladeFrameIndex,
                bladeFrameName,
                egeneraTrapSeverity,
                egeneraTrapMessage
              }
    DESCRIPTION
            "The notification generated when a license acquire attempt fails.

            This trap is driven by the 'License Acquire Failed' event type.

            Severity: 3"
     --#TYPE         "License Acquire Failed"
    --#SUMMARY      "%s"
    --#ARGUMENTS    { 3 }
    --#SEVERITY     MINOR
    --#TIMEINDEX    99
    --#STATE        OPERATIONAL
  
        ::= 133

licenseAddedTrap TRAP-TYPE
    ENTERPRISE egenera
    VARIABLES {
                bladeFrameIndex,
                bladeFrameName,
                egeneraTrapSeverity,
                egeneraTrapMessage
              }
    DESCRIPTION
            "The notification generated when a license is added.

            This trap is driven by the 'License Added' event type.

            Severity: 5"
     --#TYPE         "License Added"
    --#SUMMARY      "%s"
    --#ARGUMENTS    { 3 }
    --#SEVERITY     INFORMATIONAL
    --#TIMEINDEX    99
    --#STATE        OPERATIONAL

        ::= 134

licenseUpdatedTrap TRAP-TYPE
    ENTERPRISE egenera
    VARIABLES {
                bladeFrameIndex,
                bladeFrameName,
                egeneraTrapSeverity,
                egeneraTrapMessage
              }
    DESCRIPTION
            "The notification generated when a license is updated.

            This trap is driven by the 'License Updated' event type.

            Severity: 5"
     --#TYPE         "License Updated"
    --#SUMMARY      "%s"
    --#ARGUMENTS    { 3 }
    --#SEVERITY     INFORMATIONAL
    --#TIMEINDEX    99
    --#STATE        OPERATIONAL
  
        ::= 135

licenseRemovedTrap TRAP-TYPE
    ENTERPRISE egenera
    VARIABLES {
                bladeFrameIndex,
                bladeFrameName,
                egeneraTrapSeverity,
                egeneraTrapMessage
              }
    DESCRIPTION
            "The notification generated when a license is removed.

            This trap is driven by the 'License Removed' event type.

            Severity: 5"
     --#TYPE         "License Removed"
    --#SUMMARY      "%s"
    --#ARGUMENTS    { 3 }
    --#SEVERITY     INFORMATIONAL
    --#TIMEINDEX    99
    --#STATE        OPERATIONAL

        ::= 136

licenseInvalidTrap TRAP-TYPE
    ENTERPRISE egenera
    VARIABLES {
                bladeFrameIndex,
                bladeFrameName,
                egeneraTrapSeverity,
                egeneraTrapMessage
              }
    DESCRIPTION
            "The notification generated when a license is found to be invalid.
  
            This trap is driven by the 'License Invalid' event type.

            Severity: 3"
     --#TYPE         "License Invalid"
    --#SUMMARY      "%s"
    --#ARGUMENTS    { 3 }
    --#SEVERITY     MINOR
    --#TIMEINDEX    99
    --#STATE        OPERATIONAL
  
        ::= 137

rethStatusRedundantTrap TRAP-TYPE
    ENTERPRISE  egenera
    VARIABLES {
                bladeFrameIndex,
                bladeFrameName,
                rEthIndex,
                rEthName,
                egeneraTrapSeverity,
                egeneraTrapMessage
            }
    DESCRIPTION
            "The notification when a Redundant Ethernet transitions to
            the Redundant state (both Eths are known not to be Failed).

            This trap is driven by the 'reth <rethname> Redundant Event'
            event type.

            Severity: 5"
     --#TYPE         "reth Status Redundant"
    --#SUMMARY      "%s"
    --#ARGUMENTS    { 5 }
    --#SEVERITY     INFORMATIONAL
    --#TIMEINDEX    99
    --#STATE        OPERATIONAL

        ::= 150


rethStatusNotRedundantTrap TRAP-TYPE
    ENTERPRISE  egenera
    VARIABLES {
                bladeFrameIndex,
                bladeFrameName,
                rEthIndex,
                rEthName,
                egeneraTrapSeverity,
                egeneraTrapMessage
            }
    DESCRIPTION
            "The notification when a Redundant Ethernet transitions to
            the Not-Redundant state (One Eth is known not to be Failed,
            the other Eth is either Failed or Unknown).

            This trap is driven by the 'reth <rethname> Not-Redundant Event'
            event type.

            Severity: 2"
     --#TYPE         "reth Status Not Redundant"
    --#SUMMARY      "%s"
    --#ARGUMENTS    { 5 }
    --#SEVERITY     MAJOR
    --#TIMEINDEX    99

        ::= 151


rethStatusDegradedTrap TRAP-TYPE
    ENTERPRISE  egenera
    VARIABLES {
                bladeFrameIndex,
                bladeFrameName,
                rEthIndex,
                rEthName,
                egeneraTrapSeverity,
                egeneraTrapMessage
            }
    DESCRIPTION
            "The notification when a Redundant Ethernet transitions to
            the Degraded state (One Eth is known to be Failed, the other
            Eth is Unknown).

            This trap is driven by the 'reth <rethname> Degraded Event'
            event type.

            Severity: 1"
     --#TYPE         "reth Status Degraded"
    --#SUMMARY      "%s"
    --#ARGUMENTS    { 5 }
    --#SEVERITY     CRITICAL
    --#TIMEINDEX    99

        ::= 152


rethStatusFailedTrap TRAP-TYPE
    ENTERPRISE  egenera
    VARIABLES {
                bladeFrameIndex,
                bladeFrameName,
                rEthIndex,
                rEthName,
                egeneraTrapSeverity,
                egeneraTrapMessage
            }
    DESCRIPTION
            "The notification when a Redundant Ethernet transitions to
            the Failed state (both Eths are known to be Failed).

            This trap is driven by the 'reth <rethname> Failed Event'
            event type.

            Severity: 1"
    --#TYPE         "reth Status Failed"
    --#SUMMARY      "%s"
    --#ARGUMENTS    { 5 }
    --#SEVERITY     CRITICAL
    --#TIMEINDEX    99
    --#STATE        NONOPERATIONAL

        ::= 153


bladeFramePanJoinTrap TRAP-TYPE
    ENTERPRISE  egenera
    VARIABLES {
                bladeFrameIndex,
                bladeFrameName,
                egeneraTrapSeverity,
                egeneraTrapMessage
            }
    DESCRIPTION
            "The notification generated when the bladeFrame joined PAN.

            This trap is driven by the 'PAN Join Event'
            event type.

            Severity: 5"

        ::= 120


cBladeInsertedTrap TRAP-TYPE
    ENTERPRISE  egenera
    VARIABLES {
                cBladeIndex,
                cBladeFrameIndex,
                cBladeName,
                egeneraTrapSeverity,
                egeneraTrapMessage
            }
    DESCRIPTION
            "The notification generated when a cBlade is inserted into
            a BladeFrame.

            This trap is driven by 'BladeFrame <framename> Blade Inserted Event'
            event types that describe cBlade insertions.

            Since the underlying event type describes pBlade, cBlade, and sBlade
            insertions, enabling/disabling this SNMP trap as an event action is
            bound to the enabling/disabling of pBladeInsertedTrap and
            sBladeInsertedTrap.

            Severity: 5"
    --#TYPE         "BladeFrame cBlade Inserted"
    --#SUMMARY      "%s"
    --#ARGUMENTS    { 4 }
    --#SEVERITY     INFORMATIONAL
    --#TIMEINDEX    99
    --#STATE        OPERATIONAL

        ::=     201


cBladeRemovedTrap TRAP-TYPE
    ENTERPRISE  egenera
    VARIABLES {
                cBladeIndex,
                cBladeFrameIndex,
                cBladeName,
                egeneraTrapSeverity,
                egeneraTrapMessage
            }
    DESCRIPTION
            "The notification generated when a cBlade is removed from
            a BladeFrame.

            This trap is driven by 'BladeFrame <framename> Blade Removed Event'
            event types that describe cBlade removal events.

            Since the underlying event type describes pBlade, cBlade, and sBlade
            removal, enabling/disabling this SNMP trap as an event action is
            bound to the enabling/disabling of pBladeRemovedTrap and
            sBladeRemovedTrap.

            Severity: 3"
    --#TYPE         "BladeFrame cBlade Removed"
    --#SUMMARY      "%s"
    --#ARGUMENTS    { 4 }
    --#SEVERITY     MINOR
    --#TIMEINDEX    99
    --#STATE        NONOPERATIONAL

        ::=    202


cBladePowerOnTrap TRAP-TYPE
    ENTERPRISE  egenera
    VARIABLES {
                cBladeIndex,
                cBladeFrameIndex,
                cBladeName,
                egeneraTrapSeverity,
                egeneraTrapMessage
            }
    DESCRIPTION
            "The notification generated when a cBlade is powered on.

            This trap is driven by 'Blade <framename>/c<1|2> Power Status Event'
            event types describing power on events.

            Since the underlying event type describes cBlade power on and off
            events, enabling/disabling this SNMP trap as an event action is bound
            to the enabling/disabling of cBladePowerOffTrap.  On BladeFrame ES
            Systems, this event type also comminicates power events for the
            cBlade daughter switch card, and thus enabling/disabling this trap
            is bound to enabling/disabling cBladeSwitchCardOnTrap and
            cBladeSwitchCardOffTrap.

            Severity: 5"
     --#TYPE         "BladeFrame cBlade Power On"
    --#SUMMARY      "%s"
    --#ARGUMENTS    { 4 }
    --#SEVERITY     INFORMATIONAL
    --#TIMEINDEX    99
    --#STATE        OPERATIONAL

        ::=    203


cBladePowerOffTrap TRAP-TYPE
    ENTERPRISE  egenera
    VARIABLES {
                cBladeIndex,
                cBladeFrameIndex,
                cBladeName,
                egeneraTrapSeverity,
                egeneraTrapMessage
            }
    DESCRIPTION
            "The notification generated when a cBlade is powered off.

            This trap is driven by 'Blade <framename>/c<1|2> Power Status Event'
            event types describing power off events.

            Since the underlying event type describes cBlade power on and off
            events, enabling/disabling this SNMP trap as an event action is bound
            to the enabling/disabling of cBladePowerOnTrap.  On BladeFrame ES
            Systems, this event type also comminicates power events for the
            cBlade daughter switch card, and thus enabling/disabling this trap
            is bound to enabling/disabling cBladeSwitchCardOnTrap and
            cBladeSwitchCardOffTrap.

            Severity: 5"
     --#TYPE         "BladeFrame cBlade Power Off"
    --#SUMMARY      "%s"
    --#ARGUMENTS    { 4 }
    --#SEVERITY     INFORMATIONAL
    --#TIMEINDEX    99
    --#STATE        NONOPERATIONAL

        ::=     204


cBladeBootedTrap TRAP-TYPE
    ENTERPRISE  egenera
    VARIABLES {
                cBladeIndex,
                cBladeFrameIndex,
                cBladeName,
                egeneraTrapSeverity,
                egeneraTrapMessage
            }
    DESCRIPTION
            "The notification generated when a cBlade has successfully
            booted.

            This trap is driven by 'blade.status.monitor.event' event types
            that describe a cBlade transition from the booting state to the
            running state.

            This event type is not user visible, and will not appear in
            CLI or GUI event queries.  The trap exists to satisfy early
            requirements documents.

            Severity: 5"
    --#TYPE         "BladeFrame cBlade Booted"
    --#SUMMARY      "%s"
    --#ARGUMENTS    { 4 }
    --#SEVERITY     INFORMATIONAL
    --#TIMEINDEX    99
    --#STATE        OPERATIONAL

        ::=    205


cBladeShutdownTrap TRAP-TYPE
    ENTERPRISE  egenera
    VARIABLES {
                cBladeIndex,
                cBladeFrameIndex,
                cBladeName,
                egeneraTrapSeverity,
                egeneraTrapMessage
            }
    DESCRIPTION
            "The notification generated when a cBlade has been shut
             down.

            This trap is driven by 'blade.status.monitor.event' event types
            that describe a cBlade transition from the shutting down state to
            the shutdown state.

            This event type is not user visible, and will not appear in
            CLI or GUI event queries.  The trap exists to satisfy early
            requirements documents.

            Severity: 5"
    --#TYPE         "BladeFrame cBlade Shutdown"
    --#SUMMARY      "%s"
    --#ARGUMENTS    { 4 }
    --#SEVERITY     INFORMATIONAL
    --#TIMEINDEX    99
    --#STATE        NONOPERATIONAL

        ::=    206


cBladeEnabledTrap TRAP-TYPE
    ENTERPRISE  egenera
    VARIABLES {
                cBladeIndex,
                cBladeFrameIndex,
                cBladeName,
                egeneraTrapSeverity,
                egeneraTrapMessage
            }
    DESCRIPTION
            "The notification generated when a cBlade has been enabled
            (returns to service).

             This trap is driven by 'Blade <framename>/c<1|2> Out of Service Status
             false Event' event types.

             Severity: 5"
     --#TYPE         "BladeFrame cBlade Enabled"
    --#SUMMARY      "%s"
    --#ARGUMENTS    { 4 }
    --#SEVERITY     INFORMATIONAL
    --#TIMEINDEX    99
    --#STATE        OPERATIONAL

        ::=    207


cBladeDisabledTrap TRAP-TYPE
    ENTERPRISE  egenera
    VARIABLES {
                cBladeIndex,
                cBladeFrameIndex,
                cBladeName,
                egeneraTrapSeverity,
                egeneraTrapMessage
            }
    DESCRIPTION
            "The notification generated when a cBlade has been disabled
            (removed from service).

             This trap is driven by 'Blade <framename>/c<1|2> Out of Service Status
             true Event' event types.

             Severity: 5"
    --#TYPE         "BladeFrame cBlade Disabled"
    --#SUMMARY      "%s"
    --#ARGUMENTS    { 4 }
    --#SEVERITY     INFORMATIONAL
    --#TIMEINDEX    99
    --#STATE        NONOPERATIONAL

        ::=    208


cBladeSelectedTrap TRAP-TYPE
    ENTERPRISE  egenera
    VARIABLES {
                cBladeIndex,
                cBladeFrameIndex,
                cBladeName,
                egeneraTrapSeverity,
                egeneraTrapMessage
            }
    DESCRIPTION
            "The notification generated when a cBlade has been selected.

             This trap is driven by 'Blade <framename>/c<1|2> Selected Status
             true Event' even types.

             Severity: 5"
     --#TYPE         "BladeFrame cBlade Selected"
    --#SUMMARY      "%s"
    --#ARGUMENTS    { 4 }
    --#SEVERITY     INFORMATIONAL
    --#TIMEINDEX    99
    --#STATE        OPERATIONAL

        ::=    209


cBladeDeselectedTrap TRAP-TYPE
    ENTERPRISE  egenera
    VARIABLES {
                cBladeIndex,
                cBladeFrameIndex,
                cBladeName,
                egeneraTrapSeverity,
                egeneraTrapMessage
            }
    DESCRIPTION
            "The notification generated when a cBlade has been unselected.

             This trap is driven by 'Blade <framename>/c<1|2> Selected Status
             false Event' even types.

             Severity: 5"
     --#TYPE         "BladeFrame cBlade Deselected"
    --#SUMMARY      "%s"
    --#ARGUMENTS    { 4 }
    --#SEVERITY     INFORMATIONAL
    --#TIMEINDEX    99
    --#STATE        OPERATIONAL

        ::=    210


cBladeMasterTrap TRAP-TYPE
    ENTERPRISE  egenera
    VARIABLES {
                cBladeIndex,
                cBladeFrameIndex,
                cBladeName,
                egeneraTrapSeverity,
                egeneraTrapMessage
            }
    DESCRIPTION
            "The notification generated when a cBlade has assumed the
            role of PAN Master.

            This trap is driven by 'PAN Manager <framename>/c<1|2> Start Event'
            event types that describe PAN Master initialization.

            Since the underlying event type describes PAN Manager started and
            master or slave initialization, enabling/disabling this SNMP trap
            as an event action is bound to the enabling/disabling of
            cBladeSlaveTrap and cBladePanManagerStartedTrap.

            Severity: 5"
    --#TYPE         "BladeFrame cBlade Became Master"
    --#SUMMARY      "%s"
    --#ARGUMENTS    { 4 }
    --#SEVERITY     INFORMATIONAL
    --#TIMEINDEX    99
    --#STATE        OPERATIONAL

        ::=     211


cBladeSlaveTrap TRAP-TYPE
    ENTERPRISE  egenera
    VARIABLES {
                cBladeIndex,
                cBladeFrameIndex,
                cBladeName,
                egeneraTrapSeverity,
                egeneraTrapMessage
            }
    DESCRIPTION
            "The notification generated when a cBlade has assumed the
            role of a PAN Slave.

            This trap is driven by 'PAN Manager <framename>/c<1|2> Start Event'
            event types that describe PAN Slave initialization.

            Since the underlying event type describes PAN Manager started and
            master or slave initialization, enabling/disabling this SNMP trap
            as an event action is bound to the enabling/disabling of
            cBladeMasterTrap and cBladePanManagerStartedTrap.

            Severity: 5"
    --#TYPE         "BladeFrame cBlade Became Slave"
    --#SUMMARY      "%s"
    --#ARGUMENTS    { 4 }
    --#SEVERITY     INFORMATIONAL
    --#TIMEINDEX    99
    --#STATE        OPERATIONAL

        ::=     212


cBladeHwEventTrap TRAP-TYPE
    ENTERPRISE  egenera
    VARIABLES {
                cBladeIndex,
                cBladeFrameIndex,
                cBladeName,
                egeneraTrapSeverity,
                egeneraTrapMessage
            }
    DESCRIPTION
            "Encapsulates generic events from hardware.

            This trap is driven by 'Blade <framename>/c<1|2> non-sensor Event'
            event types that do not indicate panic, commanded shutdown,
            commanded reboot, or init level events.  Examples message contents
            include:

            OEM Type 0xe0, value = 0x64:0x21:0xce:0xe0:0x1d:0x00:0x00:0x00...
            bmc reset
            deasserted, value = 0x0211
            system booted

            Contact EES for more specific information.

            Since the underlying event type describes cBlade all non-sensor hardware
            events, and since there are specific traps for panic, commanded shutdown,
            commanded reboot, and init level events, enabling/disabling this SNMP trap
            as an event action is bound to the enabling/disabling of cBladePanicTrap,
            cBladeCmdShutdownTrap, cBladeCmdRebootTrap, cBladeCmdHaltTrap, and
            cBladeInitTrap.

            Severity: 3"
    --#TYPE         "BladeFrame cBlade Hardware Event"
    --#SUMMARY      "%s"
    --#ARGUMENTS    { 4 }
    --#SEVERITY     MINOR
    --#TIMEINDEX    99


        ::=     213

--cBladeHwThreshTrap TRAP-TYPE
--    ENTERPRISE egenera
--    VARIABLES {
--                cBladeIndex,
--                cBladeFrameIndex,
--                cBladeName,
--                hwTheshComponent,
--                hwTheshLevel,
--                egeneraTrapSeverity,
--                egeneraTrapMessage
--            }
--    DESCRIPTION
--            "Encapsulates hardward threshold events.
--
--            This trap has been deprecated in favor of cBladeVoltageUpperTrap,
--            cBladeVoltageLowerTrap, cBladeFanSpeedUpperTrap, cBladeFanSpeedLowerTrap,
--            cBladeTempUpperTrap, and cBladeTempLowerTrap."
--
--
--        ::=     214

cBladeSwitchCardOnTrap TRAP-TYPE
    ENTERPRISE egenera
    VARIABLES {
                cBladeIndex,
                cBladeFrameIndex,
                cBladeName,
                egeneraTrapSeverity,
                egeneraTrapMessage
            }
    DESCRIPTION
            "Inicates the daughter switch card of cBladeES blades has
            been powered on.  This trap is only emitted from BladeFrame ES
            systems.

            This trap is driven by 'Blade <framename>/c<1|2> Power Status Event'
            event types describing cBladeES daughter switch card power on events.

            Since the underlying event type describes cBlade power on and off
            events, enabling/disabling this SNMP trap as an event action is bound
            to the enabling/disabling of cBladeSwitchCardOffTrap, cBladePowerOnTrap,
            and cBladePowerOffTrap.

            Severity: 5"
    --#TYPE         "cBladeES Daughter Switch Card Power On"
    --#SUMMARY      "%s"
    --#ARGUMENTS    { 4 }
    --#SEVERITY     INFORMATIONAL
    --#TIMEINDEX    99
    --#STATE        OPERATIONAL

        ::=     215

cBladeSwitchCardOffTrap TRAP-TYPE
    ENTERPRISE egenera
    VARIABLES {
                cBladeIndex,
                cBladeFrameIndex,
                cBladeName,
                egeneraTrapSeverity,
                egeneraTrapMessage
            }
    DESCRIPTION
            "Inicates the daughter switch card of cBladeES blades has
            been powered on.  This trap is only emitted from BladeFrame ES
            systems.

            This trap is driven by 'Blade <framename>/c<1|2> Power Status Event'
            event types describing cBladeES daughter switch card power off events.

            Since the underlying event type describes cBlade power on and off
            events, enabling/disabling this SNMP trap as an event action is bound
            to the enabling/disabling of cBladeSwitchCardOnTrap, cBladePowerOnTrap,
            and cBladePowerOffTrap.

            Severity: 5"
    --#TYPE         "cBladeES Daughter Switch Card Power Off"
    --#SUMMARY      "%s"
    --#ARGUMENTS    { 4 }
    --#SEVERITY     INFORMATIONAL
    --#TIMEINDEX    99
    --#STATE        OPERATIONAL

        ::=     216


cBladeFailureTrap TRAP-TYPE
    ENTERPRISE  egenera
    VARIABLES {
                cBladeIndex,
                cBladeFrameIndex,
                cBladeName,
                egeneraTrapSeverity,
                egeneraTrapMessage
            }
    DESCRIPTION
            "The notification generated when a cBlade fails.

            This trap is driven by 'PAN Manager cBlade Failure Event' event
            types.

            Severity: 1"
    --#TYPE         "PAN Manager cBlade Failed"
    --#SUMMARY      "%s"
    --#ARGUMENTS    { 4 }
    --#SEVERITY     CRITICAL
    --#TIMEINDEX    99
    --#STATE        NONOPERATIONAL

        ::=     217


cBladeMasterFailoverTrap TRAP-TYPE
    ENTERPRISE  egenera
    VARIABLES {
                cBladeIndex,
                cBladeFrameIndex,
                cBladeName,
                egeneraTrapSeverity,
                egeneraTrapMessage
            }
    DESCRIPTION
            "The notification generated when a cBlade has assumed the
            role of PAN Master after a failover.

            This trap is driven by 'PAN Manager <framename>/c<1|2> Failover Event'
            event types.

            Severity: 1"
     --#TYPE         "PAN Manager cBlade Failed Over"
    --#SUMMARY      "%s"
    --#ARGUMENTS    { 4 }
    --#SEVERITY     CRITICAL
    --#TIMEINDEX    99
    --#STATE        OPERATIONAL

        ::=     218


cBladeStonithTrap TRAP-TYPE
    ENTERPRISE  egenera
    VARIABLES {
                cBladeIndex,
                cBladeFrameIndex,
                cBladeName,
                egeneraTrapSeverity,
                egeneraTrapMessage
            }
    DESCRIPTION
            "The notification generated when one cBlade has stonithed
            the other.

            This trap is driven by 'PAN Manager cBlade Stonithed Event'
            event types.

            Severity: 1"
    --#TYPE         "PAN Manager cBlade Stonithed"
    --#SUMMARY      "%s"
    --#ARGUMENTS    { 4 }
    --#SEVERITY     CRITICAL
    --#TIMEINDEX    99
    --#STATE        NONOPERATIONAL

        ::=     219

-- The PAN Manager provides functionality to monitor messages from syslogd.
-- When properly configured and enabled, EES defines a set of strings to
-- search syslog messages for.  When encountered, these syslog messages are
-- promoted to Egenera PAN Manager events.  The search strings and event
-- severities are defined by EES.  There are 10 event types reserved for
-- cBlade syslog messages, and 10 event types reserved for pServer syslog
-- messages.  Contact EES for more information.

cBladeSyslogEventTrap TRAP-TYPE
    ENTERPRISE  egenera
    VARIABLES {
                cBladeIndex,
                cBladeFrameIndex,
                cBladeName,
                egeneraTrapSeverity,
                egeneraTrapMessage
            }
    DESCRIPTION
            "The notification sent when a syslog target string is emmited
            from the system logger.

            This trap is driven by 'Blade <framename>/c<1|2> Custom Linux
            System Message <1..10>' event types.  See 'eventtype -l' for
            more information.

            There are 10 cBlade syslog event types.  This trap can be
            enabled/disabled for each syslog event type independently.

            Severity: (configurable by EES, generally 1, 2 or 3)"
     --#TYPE         "BladeFrame cBlade Syslog Event"
    --#SUMMARY      "%s"
    --#ARGUMENTS    { 4 }
    --#SEVERITY     CRITICAL
    --#TIMEINDEX    99

        ::=     220


cBladeSyslogDroppedTrap TRAP-TYPE
    ENTERPRISE  egenera
    VARIABLES {
                cBladeIndex,
                cBladeFrameIndex,
                cBladeName,
                egeneraTrapSeverity,
                egeneraTrapMessage
            }
    DESCRIPTION
            "The notification sent when a syslog target string message
            is dropped due to rate limiting.

            This trap is driven by 'Blade <framename>/c<1|2> Custom Linux System
            Messages dropped' event types.  System message events are subject
            to rate limiting.  By default, no more than 5 messages can be emitted
            during a 5 minute period.  If more than 5 target strings are
            encountered, events will only be created for the first 5 messages,
            subsequent messages will be dropped.  At the end of the 5 minute
            period, a 'Messages Dropped' event will be emmitted to indicate
            the number of dropped messages during the 5 minute period.
            Contact EES for more information.

            Severity: 3"
    --#TYPE         "BladeFrame cBlade Syslog Dropped"
    --#SUMMARY      "%s"
    --#ARGUMENTS    { 4 }
    --#SEVERITY     MINOR
    --#TIMEINDEX    99

        ::=     221


cBladeSyslogPollingStoppedTrap TRAP-TYPE
    ENTERPRISE  egenera
    VARIABLES {
                cBladeIndex,
                cBladeFrameIndex,
                cBladeName,
                egeneraTrapSeverity,
                egeneraTrapMessage
            }
    DESCRIPTION
            "The notification sent when a syslog polling has stopped
            due to rate limiting.

            This trap is driven by the 'Blade MyBladeFrame/c1 Custom Linux
            System Messages polling stopped' event type.  System message events
            are subject to rate limiting.  By default, no more than 5 messages
            can be emitted during a 5 minute period.  If more than 5 target
            strings are encountered, events will only be created for the first
            5 messages, subsequent messages will be dropped.  If messages are
            dropped for 5 consecutive 5 minute periods, syslog message polling
            will be disabled on that cBlade.  Contact EES for more information.

            Severity: 2"
    --#TYPE         "BladeFrame cBlade Syslog Polling Stopped"
    --#SUMMARY      "%s"
    --#ARGUMENTS    { 4 }
    --#SEVERITY     MAJOR
    --#TIMEINDEX    99

        ::=     222


-- The Egenera Precise Error Deamon (PED) is a component of cBlades that
-- corrolates egenera proprietary system messages.  A subset of these messages
-- are promoted to PAN Manager events, and exported via the following traps.
-- Contact EES for more information.

cBladePedDeadlockTrap TRAP-TYPE
    ENTERPRISE  egenera
    VARIABLES {
                cBladeIndex,
                cBladeFrameIndex,
                cBladeName,
                egeneraTrapSeverity,
                egeneraTrapMessage
            }
    DESCRIPTION
            "PED deadlock message.

            This trap is driven by 'Blade <framename>/c<1|2> PED Deadlock Avoidance
            Message' event types.  This trap encapsulates the following PED message
            types:
                EM24585
                EM24586

            Severity: 2"
    --#TYPE         "BladeFrame cBlade PED Deadlock Message"
    --#SUMMARY      "%s"
    --#ARGUMENTS    { 4 }
    --#SEVERITY     MAJOR
    --#TIMEINDEX    99

        ::=     223


cBladePedFabricTrap TRAP-TYPE
    ENTERPRISE  egenera
    VARIABLES {
                cBladeIndex,
                cBladeFrameIndex,
                cBladeName,
                egeneraTrapSeverity,
                egeneraTrapMessage
            }
    DESCRIPTION
            "PED fabric message.

            This trap is driven by 'Blade <framename>/c<1|2> PED Fabric Message
            event types.  This trap encapsulates the following PED message
            types:
                EM16387
                EM16388
                EM16389
                EM16390
                EM16391
                EM16392
                EM24576
                EM24580
                EM24581
                EM24582
                EM24583
                EM24584
                EM24587
                EM24588
                EM24589
                EM24590
                EM24591
                EM24592

            Severity: 2"
     --#TYPE         "BladeFrame cBlade PED Fabric Message"
    --#SUMMARY      "%s"
    --#ARGUMENTS    { 4 }
    --#SEVERITY     MAJOR
    --#TIMEINDEX    99

        ::=     224

cBladePedLegacyTrap TRAP-TYPE
    ENTERPRISE  egenera
    VARIABLES {
                cBladeIndex,
                cBladeFrameIndex,
                cBladeName,
                egeneraTrapSeverity,
                egeneraTrapMessage
            }
    DESCRIPTION
            "PED legacy message

            This trap is driven by 'Blade <framename>/c<1|2> PED Legacy Message
            event types.  This trap encapsulates the following PED message
            types:
                EM24595

            Severity: 3"
     --#TYPE         "BladeFrame cBlade PED Legacy Message"
    --#SUMMARY      "%s"
    --#ARGUMENTS    { 4 }
    --#SEVERITY     MINOR
    --#TIMEINDEX    99

        ::=     225


cBladePedOtherTrap TRAP-TYPE
    ENTERPRISE  egenera
    VARIABLES {
                cBladeIndex,
                cBladeFrameIndex,
                cBladeName,
                egeneraTrapSeverity,
                egeneraTrapMessage
            }
    DESCRIPTION
            "PED other message.

            This trap is driven by 'Blade <framename>/c<1|2> PED Message'
            event types.  This trap encapsulates any PED message not contained
            in any other specific PED event/trap types.

            Severity: 3"
    --#TYPE         "BladeFrame cBlade PED Other Message"
    --#SUMMARY      "%s"
    --#ARGUMENTS    { 4 }
    --#SEVERITY     MINOR
    --#TIMEINDEX    99

        ::=     226


cBladePedNodeTrap TRAP-TYPE
    ENTERPRISE  egenera
    VARIABLES {
                cBladeIndex,
                cBladeFrameIndex,
                cBladeName,
                egeneraTrapSeverity,
                egeneraTrapMessage
            }
    DESCRIPTION
            "PED node message.

            This trap is driven by 'Blade <framename>/c<1|2> PED Node Message'
            event types.  This trap encapsulates the following PED message
            types:
                EM16385
                EM16386

            Severity: 3"
    --#TYPE         "BladeFrame cBlade PED Node Message"
    --#SUMMARY      "%s"
    --#ARGUMENTS    { 4 }
    --#SEVERITY     MINOR
    --#TIMEINDEX    99

        ::=     227


cBladePedPathErrorTrap TRAP-TYPE
    ENTERPRISE  egenera
    VARIABLES {
                cBladeIndex,
                cBladeFrameIndex,
                cBladeName,
                egeneraTrapSeverity,
                egeneraTrapMessage
            }
    DESCRIPTION
            "PED path error message.

            This trap is driven by 'Blade <framename>/c<1|2> PED Path Error
            Message' event types.  This trap encapsulates the following PED
            message types:
                EM24593
                EM24594

            Severity: 2"
    --#TYPE         "BladeFrame cBlade PED Path Error Message"
    --#SUMMARY      "%s"
    --#ARGUMENTS    { 4 }
    --#SEVERITY     MAJOR
    --#TIMEINDEX    99

        ::=     228


cBladePedSerialBitTrap TRAP-TYPE
    ENTERPRISE  egenera
    VARIABLES {
                cBladeIndex,
                cBladeFrameIndex,
                cBladeName,
                egeneraTrapSeverity,
                egeneraTrapMessage
            }
    DESCRIPTION
            "PED serial bit message.

            This trap is driven by 'Blade <framename>/c<1|2> PED Serial Bit Message'
            event types.  This trap encapsulates the following PED message types:
                EM24577
                EM24578
                EM24579

            Severity: 2"
    --#TYPE         "BladeFrame cBlade PED Serial Bit Message"
    --#SUMMARY      "%s"
    --#ARGUMENTS    { 4 }
    --#SEVERITY     MAJOR
    --#TIMEINDEX    99

        ::=     229


cBladePedSwitchTrap TRAP-TYPE
    ENTERPRISE  egenera
    VARIABLES {
                cBladeIndex,
                cBladeFrameIndex,
                cBladeName,
                egeneraTrapSeverity,
                egeneraTrapMessage
            }
    DESCRIPTION
            "PED serial bit message.

            This trap is driven by 'Blade <framename>/c<1|2> PED Switch Message'
            event types.  This trap encapsulates the following PED message types:
                EM16384
                EM16393
                EM16394
                EM16395
                EM16396
                EM16397
                EM16398
                EM16399
                EM16400

            Severity: 2"
    --#TYPE         "BladeFrame cBlade PED Switch Messaget"
    --#SUMMARY      "%s"
    --#ARGUMENTS    { 4 }
    --#SEVERITY     MAJOR
    --#TIMEINDEX    99

        ::=     230


cBladePedErrorTrap TRAP-TYPE
    ENTERPRISE  egenera
    VARIABLES {
                cBladeIndex,
                cBladeFrameIndex,
                cBladeName,
                egeneraTrapSeverity,
                egeneraTrapMessage
            }
    DESCRIPTION
            "PED error message.

            This trap is driven by 'Blade <framename>/c<1|2> PED Error Message'
            event types.  This trap encapsulates the following PED message types:
                EM24596
                EM24597
                EM24598

            Severity: 2"
    --#TYPE         "BladeFrame cBlade PED Error Message"
    --#SUMMARY      "%s"
    --#ARGUMENTS    { 4 }
    --#SEVERITY     MAJOR
    --#TIMEINDEX    99

        ::=     246



cBladePanicTrap TRAP-TYPE
    ENTERPRISE  egenera
    VARIABLES {
                cBladeIndex,
                cBladeFrameIndex,
                cBladeName,
                egeneraTrapSeverity,
                egeneraTrapMessage
            }
    DESCRIPTION
            "Encapsulates hardware events identifying cBlade panics that
            cause the cBlade to enter KDB, reboot, or halt'

            This trap is driven by 'Blade <framename>/c<1|2> non-sensor Event'
            event types that describe kernel panics.

            Contact EES for more specific information.

            Since the underlying event type describes cBlade non-sensor hardware
            events, and since there are specific traps for panic, commanded shutdown,
            commanded reboot, and init level events, enabling/disabling this SNMP trap
            as an event action is bound to the enabling/disabling of cBladeHwEventTrap,
            cBladeCmdShutdownTrap, cBladeCmdRebootTrap, cBladeCmdHaltTrap, and
            cBladeInitTrap.

            Severity: 3"
    --#TYPE         "BladeFrame cBlade Panic"
    --#SUMMARY      "%s"
    --#ARGUMENTS    { 4 }
    --#SEVERITY     MINOR
    --#TIMEINDEX    99

        ::=     231


cBladeCmdHaltTrap TRAP-TYPE
    ENTERPRISE  egenera
    VARIABLES {
                cBladeIndex,
                cBladeFrameIndex,
                cBladeName,
                egeneraTrapSeverity,
                egeneraTrapMessage
            }
    DESCRIPTION
            "Encapsulates hardware events indicating intentional cBlade
            halt.

            This trap is driven by 'Blade <framename>/c<1|2> non-sensor Event'
            event types that describe commanded halts.

            Contact EES for more specific information.

            Since the underlying event type describes cBlade non-sensor hardware
            events, and since there are specific traps for panic, commanded shutdown,
            commanded reboot, and init level events, enabling/disabling this SNMP trap
            as an event action is bound to the enabling/disabling of cBladeHwEventTrap,
            cBladeCmdShutdownTrap, cBladeCmdRebootTrap, cBladePanicTrap, and
            cBladeInitTrap.

            Severity: 3"
    --#TYPE         "BladeFrame cBlade Cmd Halt"
    --#SUMMARY      "%s"
    --#ARGUMENTS    { 4 }
    --#SEVERITY     MINOR
    --#TIMEINDEX    99

        ::=     232


cBladeCmdRebootTrap TRAP-TYPE
    ENTERPRISE  egenera
    VARIABLES {
                cBladeIndex,
                cBladeFrameIndex,
                cBladeName,
                egeneraTrapSeverity,
                egeneraTrapMessage
            }
    DESCRIPTION
            "Encapsulates hardware events indicating intentional cBlade
            reboot.

            This trap is driven by 'Blade <framename>/c<1|2> non-sensor Event'
            event types that describe commanded reboots.

            Contact EES for more specific information.

            Since the underlying event type describes cBlade non-sensor hardware
            events, and since there are specific traps for panic, commanded shutdown,
            commanded reboot, and init level events, enabling/disabling this SNMP trap
            as an event action is bound to the enabling/disabling of cBladeHwEventTrap,
            cBladeCmdShutdownTrap, cBladeCmdHaltTrap, cBladePanicTrap, and
            cBladeInitTrap.

            Severity: 3"
    --#TYPE         "BladeFrame cBlade Cmd Reboot"
    --#SUMMARY      "%s"
    --#ARGUMENTS    { 4 }
    --#SEVERITY     MINOR
    --#TIMEINDEX    99

        ::=     233


cBladeInitTrap TRAP-TYPE
    ENTERPRISE  egenera
    VARIABLES {
                cBladeIndex,
                cBladeFrameIndex,
                cBladeName,
                egeneraTrapSeverity,
                egeneraTrapMessage
            }
    DESCRIPTION
            "Encapsulates hardware events indicating intentional cBlade
            has reached an init level.

            This trap is driven by 'Blade <framename>/c<1|2> non-sensor Event'
            event types that describe init level reached.

            Contact EES for more specific information.

            Since the underlying event type describes cBlade non-sensor hardware
            events, and since there are specific traps for panic, commanded shutdown,
            commanded reboot, and init level events, enabling/disabling this SNMP trap
            as an event action is bound to the enabling/disabling of cBladeHwEventTrap,
            cBladeCmdShutdownTrap, cBladeCmdHaltTrap, cBladeCmdRebootTrap, and
            cBladePanicTrap.

            Severity: 3"
    --#TYPE         "BladeFrame cBlade Init"
    --#SUMMARY      "%s"
    --#ARGUMENTS    { 4 }
    --#SEVERITY     MINOR
    --#TIMEINDEX    99

        ::=     234



cBladeVoltageUpperTrap TRAP-TYPE
    ENTERPRISE egenera
    VARIABLES {
                cBladeIndex,
                cBladeFrameIndex,
                cBladeName,
                sensorName,
                sensorThreshold,
                sensorValue,
                egeneraTrapSeverity,
                egeneraTrapMessage
            }
    DESCRIPTION
            "Encapsulates cBlade critical high voltage sensor events.

            This trap is driven by 'Blade <framename>/c<1|2> <voltage-sensor-name>
            Critical High Event' event types.

            The sensorValue and sensorThreshold fields are ingeter representations
            of real numbers.  The real numbers are multiplied by 100 and rounded
            to produce an integer, thus 0.530 => 53.

            This trap replaces cBladeHwThreshTrap.

            Severity: 3"
    --#TYPE         "BladeFrame cBlade Voltage Upper"
    --#SUMMARY      "%s"
    --#ARGUMENTS    { 7 }
    --#SEVERITY     MINOR
    --#TIMEINDEX    99

        ::=     235


cBladeVoltageLowerTrap TRAP-TYPE
    ENTERPRISE egenera
    VARIABLES {
                cBladeIndex,
                cBladeFrameIndex,
                cBladeName,
                sensorName,
                sensorThreshold,
                sensorValue,
                egeneraTrapSeverity,
                egeneraTrapMessage
            }
    DESCRIPTION
            "Encapsulates cBlade critical low voltage sensor events.

            This trap is driven by 'Blade <framename>/c<1|2> <voltage-sensor-name>
            Critical Low Event' event types.

            The sensorValue and sensorThreshold fields are ingeter representations
            of real numbers.  The real numbers are multiplied by 100 and rounded
            to produce an integer, thus 0.530 => 53.

            This trap replaces cBladeHwThreshTrap.

            Severity: 3"
    --#TYPE         "BladeFrame cBlade Voltage Lower"
    --#SUMMARY      "%s"
    --#ARGUMENTS    { 7 }
    --#SEVERITY     MINOR
    --#TIMEINDEX    99

        ::=     236


cBladeFanSpeedUpperTrap TRAP-TYPE
    ENTERPRISE egenera
    VARIABLES {
                cBladeIndex,
                cBladeFrameIndex,
                cBladeName,
                sensorName,
                sensorThreshold,
                sensorValue,
                egeneraTrapSeverity,
                egeneraTrapMessage
            }
    DESCRIPTION
            "Encapsulates cBlade critical high fan speed  sensor events.

            This trap is driven by 'Blade <framename>/c<1|2> <fan-sensor-name>
            Critical High Event' event types.

            This trap replaces cBladeHwThreshTrap.

            Severity: 3"
    --#TYPE         "BladeFrame cBlade Fan Speed Upper"
    --#SUMMARY      "%s"
    --#ARGUMENTS    { 7 }
    --#SEVERITY     MINOR
    --#TIMEINDEX    99

        ::=     237


cBladeFanSpeedLowerTrap TRAP-TYPE
    ENTERPRISE egenera
    VARIABLES {
                cBladeIndex,
                cBladeFrameIndex,
                cBladeName,
                sensorName,
                sensorThreshold,
                sensorValue,
                egeneraTrapSeverity,
                egeneraTrapMessage
            }
    DESCRIPTION
            "Encapsulates cBlade critical low fan speed sensor events.

            This trap is driven by 'Blade <framename>/c<1|2> <fan-sensor-name>
            Critical Low Event' event types.

            This trap replaces cBladeHwThreshTrap.

            Severity: 3"
    --#TYPE         "BladeFrame cBlade Fan Speed Lower"
    --#SUMMARY      "%s"
    --#ARGUMENTS    { 7 }
    --#SEVERITY     MINOR
    --#TIMEINDEX    99

        ::=     238



cBladeTempUpperTrap TRAP-TYPE
    ENTERPRISE egenera
    VARIABLES {
                cBladeIndex,
                cBladeFrameIndex,
                cBladeName,
                sensorName,
                sensorThreshold,
                sensorValue,
                egeneraTrapSeverity,
                egeneraTrapMessage
            }
    DESCRIPTION
            "Encapsulates cBlade critical high temperature sensor events.

            This trap is driven by 'Blade <framename>/c<1|2> <temp-sensor-name>
            Critical High Event' event types.

            This trap replaces cBladeHwThreshTrap.

            Severity: 3"
     --#TYPE         "BladeFrame cBlade Temperature Upper"
    --#SUMMARY      "%s"
    --#ARGUMENTS    { 7 }
    --#SEVERITY     MINOR
    --#TIMEINDEX    99

        ::=     239


cBladeTempLowerTrap TRAP-TYPE
    ENTERPRISE egenera
    VARIABLES {
                cBladeIndex,
                cBladeFrameIndex,
                cBladeName,
                sensorName,
                sensorThreshold,
                sensorValue,
                egeneraTrapSeverity,
                egeneraTrapMessage
            }
    DESCRIPTION
            "Encapsulates cBlade critical low temperature sensor events.

            This trap is driven by 'Blade <framename>/c<1|2> <temp-sensor-name>
            Critical Low Event' event types.

            This trap replaces cBladeHwThreshTrap.

            Severity: 3"
     --#TYPE         "BladeFrame cBlade Temperature Lower"
    --#SUMMARY      "%s"
    --#ARGUMENTS    { 7 }
    --#SEVERITY     MINOR
    --#TIMEINDEX    99

        ::=     240


cBladePowerOnOpTrap TRAP-TYPE
    ENTERPRISE egenera
    VARIABLES {
                cBladeIndex,
                cBladeFrameIndex,
                cBladeName,
                egeneraTrapSeverity,
                egeneraTrapMessage
            }
    DESCRIPTION
            "Encapsulates cBlade power on operation event.

            This trap is driven by 'cBlade <framename>/c<1|2> Hardware Operation
            Event' event types.

            Since the underlying event type describes cBlade power on and off
            operation events, enabling/disabling this SNMP trap as an event action
            is bound to the enabling/disabling of cBladePowerOffOpTrap,
            cBladePowerCycleTrap, cBladeResetOpTrap, and cBladeNMIOpTrap.

            Severity: 5"
     --#TYPE         "BladeFrame cBlade Power On Operation"
    --#SUMMARY      "%s"
    --#ARGUMENTS    { 4 }
    --#SEVERITY     INFORMATIONAL
    --#TIMEINDEX    99
    --#STATE        OPERATIONAL

        ::=     241


cBladePowerOffOpTrap TRAP-TYPE
    ENTERPRISE egenera
    VARIABLES {
                cBladeIndex,
                cBladeFrameIndex,
                cBladeName,
                egeneraTrapSeverity,
                egeneraTrapMessage
            }
    DESCRIPTION
            "Encapsulates cBlade power off operation event.

            This trap is driven by 'cBlade <framename>/c<1|2> Hardware Operation
            Event' event types.

            Since the underlying event type describes cBlade power on and off
            operation events, enabling/disabling this SNMP trap as an event action
            is bound to the enabling/disabling of cBladePowerOnOpTrap,
            cBladePowerCycleTrap, cBladeResetOpTrap, and cBladeNMIOpTrap.

            Severity: 5"
    --#TYPE         "BladeFrame cBlade Power Off Operation"
    --#SUMMARY      "%s"
    --#ARGUMENTS    { 4 }
    --#SEVERITY     INFORMATIONAL
    --#TIMEINDEX    99
    --#STATE        OPERATIONAL

        ::=     242


cBladePowerCycleOpTrap TRAP-TYPE
    ENTERPRISE egenera
    VARIABLES {
                cBladeIndex,
                cBladeFrameIndex,
                cBladeName,
                egeneraTrapSeverity,
                egeneraTrapMessage
            }
    DESCRIPTION
            "Encapsulates cBlade power cycle operation event.

            This trap is driven by 'cBlade <framename>/c<1|2> Hardware Operation
            Event' event types.

            Since the underlying event type describes cBlade power on and off
            operation events, enabling/disabling this SNMP trap as an event action
            is bound to the enabling/disabling of cBladePowerOnOpTrap,
            cBladePowerCycleTrap, cBladeResetOpTrap, and cBladeNMIOpTrap.

            Severity: 5"
     --#TYPE         "BladeFrame cBlade Power Cycle Operation"
    --#SUMMARY      "%s"
    --#ARGUMENTS    { 4 }
    --#SEVERITY     INFORMATIONAL
    --#TIMEINDEX    99
    --#STATE        OPERATIONAL

        ::=     243


cBladeResetOpTrap TRAP-TYPE
    ENTERPRISE egenera
    VARIABLES {
                cBladeIndex,
                cBladeFrameIndex,
                cBladeName,
                egeneraTrapSeverity,
                egeneraTrapMessage
            }
    DESCRIPTION
            "Encapsulates cBlade reset operation event.

            This trap is driven by 'cBlade <framename>/c<1|2> Hardware Operation
            Event' event types.

            Since the underlying event type describes cBlade power on and off
            operation events, enabling/disabling this SNMP trap as an event action
            is bound to the enabling/disabling of cBladePowerOnOpTrap,
            cBladePowerCycleTrap, cBladePowerCycleOpTrap, and cBladeNMIOpTrap.

            Severity: 5"
    --#TYPE         "BladeFrame cBlade Reset Operation"
    --#SUMMARY      "%s"
    --#ARGUMENTS    { 4 }
    --#SEVERITY     INFORMATIONAL
    --#TIMEINDEX    99
    --#STATE        OPERATIONAL

        ::=     244


cBladeNMIOpTrap TRAP-TYPE
    ENTERPRISE egenera
    VARIABLES {
                cBladeIndex,
                cBladeFrameIndex,
                cBladeName,
                egeneraTrapSeverity,
                egeneraTrapMessage
            }
    DESCRIPTION
            "Encapsulates cBlade reset operation event.

            This trap is driven by 'cBlade <framename>/c<1|2> Hardware Operation
            Event' event types.

            Since the underlying event type describes cBlade power on and off
            operation events, enabling/disabling this SNMP trap as an event action
            is bound to the enabling/disabling of cBladePowerOnOpTrap,
            cBladePowerCycleTrap, cBladePowerCycleOpTrap, and cBladeResetOpTrap.

            Severity: 5"
    --#TYPE         "BladeFrame cBlade NMI Operation"
    --#SUMMARY      "%s"
    --#ARGUMENTS    { 4 }
    --#SEVERITY     INFORMATIONAL
    --#TIMEINDEX    99
    --#STATE        OPERATIONAL

        ::=     245


cBladeSystemThresholdHighTrap TRAP-TYPE
    ENTERPRISE  egenera
    VARIABLES {
                cBladeIndex,
                cBladeFrameIndex,
                cBladeName,
                egeneraTrapSeverity,
                egeneraTrapMessage
            }
    DESCRIPTION
            "The notification generated when a cBlade system monitor has
            exceeded its high threshold, or returns below the high threshold.

            This trap is driven by 'cBlade <bladeframe>/c<1|2> <monitorname>
            event' event types.  Note that a severity 3 event is emmitted when
            the threshold is crossed in the rising direction, while a severity
            5 event is emmitted when the monitored value returns below the threshold.
            Thus it is possible to recieve a severity 5 cBladeSystemThresholdHighTrap
            with a message like:

            sagan/c1 5 Minute Load Average returned below 10.0 on average
            for 300 seconds, Current value = 4.79

            Severity: 3/5"
     --#TYPE         "BladeFrame cBlade System Threshold High"
    --#SUMMARY      "%s"
    --#ARGUMENTS    { 4 }
    --#SEVERITY     MINOR
    --#TIMEINDEX    99
    --#STATE        OPERATIONAL

        ::=     250


cBladeNonFatalHwErrorTrap TRAP-TYPE
    ENTERPRISE  egenera
    VARIABLES {
                cBladeIndex,
                cBladeFrameIndex,
                cBladeName,
                egeneraTrapSeverity,
                egeneraTrapMessage
            }
    DESCRIPTION
            "The notification generated when cBlade hardware detects a non-fatal
            error, such as a correctable ECC memory error.

            This trap is driven by 'cBlade <bladeframe>/c<1|2> NonFatal Hardware
            Error Event' event types.

            Severity: 3"
    --#TYPE         "BladeFrame cBlade Non-fatal Hw Error"
    --#SUMMARY      "%s"
    --#ARGUMENTS    { 4 }
    --#SEVERITY     MINOR
    --#TIMEINDEX    99
    --#STATE        OPERATIONAL

        ::=     251


cBladeFatalHwErrorTrap TRAP-TYPE
    ENTERPRISE  egenera
    VARIABLES {
                cBladeIndex,
                cBladeFrameIndex,
                cBladeName,
                egeneraTrapSeverity,
                egeneraTrapMessage
            }
    DESCRIPTION
            "The notification generated when cBlade hardware detects a fatal
            error, such as an uncorrectable ECC memory error.

            This trap is driven by 'cBlade <bladeframe>/c<1|2> Fatal Hardware
            Error Event' event types.

            Severity: 1"
    --#TYPE         "BladeFrame cBlade Fatal Hw Error"
    --#SUMMARY      "%s"
    --#ARGUMENTS    { 4 }
    --#SEVERITY     CRITICAL
    --#TIMEINDEX    99

        ::=     252


cBladePanManagerStartedTrap TRAP-TYPE
    ENTERPRISE  egenera
    VARIABLES {
                cBladeIndex,
                cBladeFrameIndex,
                cBladeName,
                egeneraTrapSeverity,
                egeneraTrapMessage
            }
    DESCRIPTION
            "The notification generated when the PAN Manager has been started
            on a cBlade.

            This trap is driven by 'PAN Manager <bladeframe>/c<1|2> Start Event'
            event types that do not indicate Master or Slave initialization.

            Since the underlying event type describes PAN Manager started and
            master or slave initialization, enabling/disabling this SNMP trap
            as an event action is bound to the enabling/disabling of
            cBladeMasterTrap and cBladeSlaveTrap.

            Severity: 5"
    --#TYPE         "PAN Manager Started"
    --#SUMMARY      "%s"
    --#ARGUMENTS    { 4 }
    --#SEVERITY     INFORMATIONAL
    --#TIMEINDEX    99
    --#STATE        OPERATIONAL

        ::=     253


cBladeNonUniqueDiskIdTrap TRAP-TYPE
    ENTERPRISE  egenera
    VARIABLES {
                cBladeIndex,
                cBladeFrameIndex,
                cBladeName,
                diskIdOctets,
                egeneraTrapSeverity,
                egeneraTrapMessage
            }
    DESCRIPTION
            "The notification generated when a cBlade detects multiple disks
            with the same Unique ID.

            This trap is driven by 'Non-unique disk ID Event' event types.

            Severity: 1"
    --#TYPE         "cBlade Non-unique Disk ID"
    --#SUMMARY      "%s"
    --#ARGUMENTS    { 5 }
    --#SEVERITY     CRITICAL
    --#TIMEINDEX    99

        ::=     254


cBladeOutOfServicePendingTrap TRAP-TYPE
    ENTERPRISE  egenera
    VARIABLES {
                cBladeIndex,
                cBladeFrameIndex,
                cBladeName,
                egeneraTrapSeverity,
                egeneraTrapMessage
            }
    DESCRIPTION
            "The notification generated when a cBlade enters the 'out of service
            pending' state.

            This trap is driven by 'cBlade <bladeframe>/c<1|2> Out of Service Pending
            Event' event types

            Severity: 5"
    --#TYPE         "cBlade Out Of Service Pending"
    --#SUMMARY      "%s"
    --#ARGUMENTS    { 4 }
    --#SEVERITY     INFORMATIONAL
    --#TIMEINDEX    99
    --#STATE        OPERATIONAL

        ::=     255


cBladeDiskIOAvailableTrap TRAP-TYPE
    ENTERPRISE  egenera
    VARIABLES {
                cBladeIndex,
                cBladeFrameIndex,
                cBladeName,
                diskIdOctets,
                diskId,
                egeneraTrapSeverity,
                egeneraTrapMessage
            }
    DESCRIPTION
            "The notification generated when disk I/O becomes available on
            a cBlade.

            This trap is driven by 'Device IO Available Event' event types
            that describe Disk I/O availability.

            Severity: 5"
    --#TYPE         "cBlade Disk IO Available"
    --#SUMMARY      "%s"
    --#ARGUMENTS    { 6 }
    --#SEVERITY     INFORMATIONAL
    --#TIMEINDEX    99
    --#STATE        OPERATIONAL

        ::=     256


cBladeDiskIOUnvailableTrap TRAP-TYPE
    ENTERPRISE  egenera
    VARIABLES {
                cBladeIndex,
                cBladeFrameIndex,
                cBladeName,
                diskIdOctets,
                diskId,
                egeneraTrapSeverity,
                egeneraTrapMessage
            }
    DESCRIPTION
            "The notification generated when disk I/O becomes unavailable on
            a cBlade.

            This trap is driven by 'Device IO Unvailable Event' event types
            that describe disk I/O unavailability.

            Severity: 5"
    --#TYPE         "cBlade Disk IO Unavailable"
    --#SUMMARY      "%s"
    --#ARGUMENTS    { 6 }
    --#SEVERITY     INFORMATIONAL
    --#TIMEINDEX    99
    --#STATE        OPERATIONAL

        ::=     257


cBladeEthIOAvailableTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when ethernet I/O becomes available on
            a cBlade.

            This trap is driven by 'Device IO Available Event' event types that
            describe ethernet I/O availability.

            Severity: 5"
    --#TYPE         "cBlade Eth IO Available"
    --#SUMMARY      "%s"
    --#ARGUMENTS    { 6 }
    --#SEVERITY     INFORMATIONAL
    --#TIMEINDEX    99
    --#STATE        OPERATIONAL

        ::=     258


cBladeEthIOUnvailableTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when ethernet I/O becomes unavailable on
            a cBlade.

            This trap is driven by 'Device IO Unvailable Event' event types
            that describe ethernet I/O unavailability.

            Severity: 5"
    --#TYPE         "cBlade Disk Eth IO Unavailable"
    --#SUMMARY      "%s"
    --#ARGUMENTS    { 6 }
    --#SEVERITY     INFORMATIONAL
    --#TIMEINDEX    99
    --#STATE        OPERATIONAL

        ::=     259


cBladeCDROMIOAvailableTrap TRAP-TYPE
    ENTERPRISE  egenera
    VARIABLES {
                cBladeIndex,
                cBladeFrameIndex,
                cBladeName,
                cdromIdOctets,
                cdromId,
                egeneraTrapSeverity,
                egeneraTrapMessage
            }
    DESCRIPTION
            "The notification generated when cd-rom I/O becomes available on
            a cBlade.

            This trap is driven by 'Device IO Available Event' event types that
            describe cd-rom I/O availability.

            Severity: 5"
    --#TYPE         "cBlade CDROM IO Available"
    --#SUMMARY      "%s"
    --#ARGUMENTS    { 6 }
    --#SEVERITY     INFORMATIONAL
    --#TIMEINDEX    99
    --#STATE        OPERATIONAL

        ::=     260


cBladeCDROMIOUnvailableTrap TRAP-TYPE
    ENTERPRISE  egenera
    VARIABLES {
                cBladeIndex,
                cBladeFrameIndex,
                cBladeName,
                cdromIdOctets,
                cdromId,
                egeneraTrapSeverity,
                egeneraTrapMessage
            }
    DESCRIPTION
            "The notification generated when cd-rom I/O becomes unavailable on
            a cBlade.

            This trap is driven by 'Device IO Unvailable Event' event types
            that describe cd-rom I/O unavailability.

            Severity: 5"
    --#TYPE         "cBlade CDROM IO Unavailable"
    --#SUMMARY      "%s"
    --#ARGUMENTS    { 6 }
    --#SEVERITY     INFORMATIONAL
    --#TIMEINDEX    99
    --#STATE        OPERATIONAL

        ::=     261


cBladeEthLinkUpTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when a cBlade Eth Link Status is
            detected to be Up.

            This trap is driven by 'ethernet <ethname>@<framename>/c<1|2>
            Link Up Event' event type.

            Severity: 5"
    --#TYPE         "cBlade Eth Link Status Up"
    --#SUMMARY      "%s"
    --#ARGUMENTS    { 6 }
    --#SEVERITY     INFORMATIONAL
    --#TIMEINDEX    99
    --#STATE        OPERATIONAL

        ::=     262


cBladeEthLinkDownTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when a cBlade Eth Link Status is
            detected to be Down.

            This trap is driven by 'ethernet <ethname>@<framename>/c<1|2>
            Link Down Event' event type.

            Severity: 5"
    --#TYPE         "cBlade Eth Link Status Down"
    --#SUMMARY      "%s"
    --#ARGUMENTS    { 6 }
    --#SEVERITY     INFORMATIONAL
    --#TIMEINDEX    99
    --#STATE        NONOPERATIONAL

        ::=     263


cBladeEthStatusActiveTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when a cBlade Eth Reth Status is
            detected to be Active.

            This trap is driven by 'ethernet <ethname>@<framename>/c<1|2>
            Reth Status Active Event' event type.

            Severity: 5"
    --#TYPE         "cBlade Eth Reth Status Active"
    --#SUMMARY      "%s"
    --#ARGUMENTS    { 6 }
    --#SEVERITY     INFORMATIONAL
    --#TIMEINDEX    99
    --#STATE        OPERATIONAL

        ::=     264


cBladeEthStatusStandbyTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when a cBlade Eth Reth Status is
            detected to be Standby.

            This trap is driven by 'ethernet <ethname>@<framename>/c<1|2>
            Reth Status Standby Event' event type.

            Severity: 5"
    --#TYPE         "cBlade Eth Reth Status Standby"
    --#SUMMARY      "%s"
    --#ARGUMENTS    { 6 }
    --#SEVERITY     INFORMATIONAL
    --#TIMEINDEX    99
    --#STATE        OPERATIONAL

        ::=     265


cBladeEthStatusFailedTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when a cBlade Eth Reth Status is
            detected to be Failed.

            This trap is driven by 'ethernet <ethname>@<framename>/c<1|2>
            Reth Status Failed Event' event type.

            Severity: 2"
    --#TYPE         "cBlade Eth Reth Status Failed"
    --#SUMMARY      "%s"
    --#ARGUMENTS    { 6 }
    --#SEVERITY     MAJOR
    --#TIMEINDEX    99
    --#STATE        NONOPERATIONAL

        ::=     266


cBladeEthStatusUnconfiguredTrap TRAP-TYPE
    ENTERPRISE  egenera
    VARIABLES {
                cBladeIndex,
                cBladeFrameIndex,
                cBladeName,
                cBladeEthIndex,
                cBladeEthName,
                egeneraTrapSeverity,
                egeneraTrapMessage
            }
    DESCRIPTION
            "The notification generated when a cBlade Eth Reth Status is
            detected to be Unconfigured (not part of a Reth).  An
            Unconfigured cBlade Eth has Link Status Down.

            This trap is driven by 'ethernet <ethname>@<framename>/c<1|2>
            Reth Status Unconfigured Event' event type.

            Severity: 5"
    --#TYPE         "cBlade Eth Reth Status Unconfigured"
    --#SUMMARY      "%s"
    --#ARGUMENTS    { 6 }
    --#SEVERITY     INFORMATIONAL
    --#TIMEINDEX    99

        ::=     267


cBladeHbaEnabledTrap TRAP-TYPE
    ENTERPRISE  egenera
    VARIABLES {
                cBladeIndex,
                cBladeFrameIndex,
                cBladeHbaIndex,
                cBladeHbaName,
                egeneraTrapSeverity,
                egeneraTrapMessage
            }
    DESCRIPTION
            "The notification generated when a cBlade HBA set to enabled.

            Severity: 5"
    --#TYPE         "cBlade Hba Enabled"
    --#SUMMARY      "%s"
    --#ARGUMENTS    { 5 }
    --#SEVERITY     INFORMATIONAL
    --#TIMEINDEX    99
    --#STATE        OPERATIONAL

        ::=     268

cBladeHbaDisabledTrap TRAP-TYPE
    ENTERPRISE  egenera
    VARIABLES {
                cBladeIndex,
                cBladeFrameIndex,
                cBladeHbaIndex,
                cBladeHbaName,
                egeneraTrapSeverity,
                egeneraTrapMessage
            }
    DESCRIPTION
            "The notification generated when a cBlade HBA set to disabled.

            Severity: 3"
    --#TYPE         "cBlade Hba Disabled"
    --#SUMMARY      "%s"
    --#ARGUMENTS    { 5 }
    --#SEVERITY     MINOR
    --#TIMEINDEX    99

        ::=     269

cBladeHbaStatusDownTrap TRAP-TYPE
    ENTERPRISE  egenera
    VARIABLES {
                cBladeIndex,
                cBladeFrameIndex,
                cBladeHbaIndex,
                cBladeHbaName,
                egeneraTrapSeverity,
                egeneraTrapMessage
            }
    DESCRIPTION
            "The notification generated when a cBlade HBA status is down.

            Severity: 3"
    --#TYPE         "cBlade Hba Status Down"
    --#SUMMARY      "%s"
    --#ARGUMENTS    { 5 }
    --#SEVERITY     MINOR
    --#TIMEINDEX    99

        ::=     270

cBladeHbaStatusChangedTrap TRAP-TYPE
    ENTERPRISE  egenera
    VARIABLES {
                cBladeIndex,
                cBladeFrameIndex,
                cBladeHbaIndex,
                cBladeHbaName,
                egeneraTrapSeverity,
                egeneraTrapMessage
            }
    DESCRIPTION
            "The notification generated when a cBlade HBA status is changed.

            Severity: 5"
    --#TYPE         "cBlade Hba Status Changed"
    --#SUMMARY      "%s"
    --#ARGUMENTS    { 5 }
    --#SEVERITY     INFORMATIONAL
    --#TIMEINDEX    99

        ::=     271


sBladeInsertedTrap TRAP-TYPE
    ENTERPRISE  egenera
    VARIABLES {
                sBladeIndex,
                sBladeFrameIndex,
                sBladeName,
                egeneraTrapSeverity,
                egeneraTrapMessage
            }
    DESCRIPTION
            "The notification generated when an sBlade is inserted into
            a BladeFrame.

            This trap is driven by 'BladeFrame <framename> Blade Inserted Event'
            event types that describe sBlade insertions.

            Since the underlying event type describes pBlade, cBlade, and sBlade
            insertions, enabling/disabling this SNMP trap as an event action is
            bound to the enabling/disabling of pBladeInsertedTrap and
            cBladeInsertedTrap.

            Since BladeFrame ES Systems do not utilize dedicated sBlades, this
            trap is not relevant to BladeFrame ES systems.

            Severity: 5"
    --#TYPE         "BladeFrame sBlade Inserted"
    --#SUMMARY      "%s"
    --#ARGUMENTS    { 4 }
    --#SEVERITY     INFORMATIONAL
    --#TIMEINDEX    99
    --#STATE        OPERATIONAL

        ::=     301


sBladeRemovedTrap TRAP-TYPE
    ENTERPRISE  egenera
    VARIABLES {
                sBladeIndex,
                sBladeFrameIndex,
                sBladeName,
                egeneraTrapSeverity,
                egeneraTrapMessage
            }
    DESCRIPTION
            "The notification generated when an sBlade is removed from
            a BladeFrame.

            This trap is driven by 'BladeFrame <framename> Blade Removed Event'
            event types that describe sBlade removal events.

            Since the underlying event type describes pBlade, cBlade, and sBlade
            removal, enabling/disabling this SNMP trap as an event action is
            bound to the enabling/disabling of pBladeRemovedTrap and
            cBladeRemovedTrap.

            Since BladeFrame ES Systems do not utilize dedicated sBlades, this
            trap is not relevant to BladeFrame ES systems.

            Severity: 3"
    --#TYPE         "BladeFrame sBlade Removed"
    --#SUMMARY      "%s"
    --#ARGUMENTS    { 4 }
    --#SEVERITY     INFORMATIONAL
    --#TIMEINDEX    99
    --#STATE        NONOPERATIONAL

        ::=     302


sBladePowerOnTrap TRAP-TYPE
    ENTERPRISE  egenera
    VARIABLES {
                sBladeIndex,
                sBladeFrameIndex,
                sBladeName,
                egeneraTrapSeverity,
                egeneraTrapMessage
            }
    DESCRIPTION
            "The notification generated when an sBlade is powered on.

            This trap is driven by 'Blade <framename>/s<1|2> Power Status Event'
            event types describing power on events.

            Since the underlying event type describes sBlade power on and off
            events, enabling/disabling this SNMP trap as an event action is bound
            to the enabling/disabling of sBladePowerOffTrap.

            Since BladeFrame ES Systems do not utilize dedicated sBlades, this
            trap is not relevant to BladeFrame ES systems.  BladeFrame ES systems
            emit the cBladeSwitchCardOnTrap to indicate the switch card of the
            cBlade has been powered on.

            Severity: 5"
    --#TYPE         "BladeFrame sBlade Power On"
    --#SUMMARY      "%s"
    --#ARGUMENTS    { 4 }
    --#SEVERITY     INFORMATIONAL
    --#TIMEINDEX    99
    --#STATE        OPERATIONAL

        ::=    303


sBladePowerOffTrap TRAP-TYPE
    ENTERPRISE  egenera
    VARIABLES {
                sBladeIndex,
                sBladeFrameIndex,
                sBladeName,
                egeneraTrapSeverity,
                egeneraTrapMessage
            }
    DESCRIPTION
            "The notification generated when an sBlade is powered off.

            This trap is driven by 'Blade <framename>/s<1|2> Power Status Event'
            event types describing power on events.

            Since the underlying event type describes sBlade power on and off
            events, enabling/disabling this SNMP trap as an event action is bound
            to the enabling/disabling of sBladePowerOnTrap.

            Since BladeFrame ES Systems do not utilize dedicated sBlades, this
            trap is not relevant to BladeFrame ES systems.  BladeFrame ES systems
            emit the cBladeSwitchCardOffTrap to indicate the switch card of the
            cBlade has been powered off.

            Severity: 5"
    --#TYPE         "BladeFrame sBlade Power Off"
    --#SUMMARY      "%s"
    --#ARGUMENTS    { 4 }
    --#SEVERITY     INFORMATIONAL
    --#TIMEINDEX    99
    --#STATE        NONOPERATIONAL

        ::=    304


sBladeEnabledTrap TRAP-TYPE
    ENTERPRISE  egenera
    VARIABLES {
                sBladeIndex,
                sBladeFrameIndex,
                sBladeName,
                egeneraTrapSeverity,
                egeneraTrapMessage
            }
    DESCRIPTION
            "The notification generated when an sBlade is enabled (returns
             to service).

             This trap is driven by 'Blade <framename>/s<1|2> Out of Service Status
             false Event' event types.

             Since BladeFrame ES Systems do not utilize dedicated sBlades, this
             trap is not relevant to BladeFrame ES systems.

             Severity: 5"
    --#TYPE         "BladeFrame sBlade Enabled"
    --#SUMMARY      "%s"
    --#ARGUMENTS    { 4 }
    --#SEVERITY     INFORMATIONAL
    --#TIMEINDEX    99
    --#STATE        OPERATIONAL

        ::=    305


sBladeDisabledTrap TRAP-TYPE
    ENTERPRISE  egenera
    VARIABLES {
                sBladeIndex,
                sBladeFrameIndex,
                sBladeName,
                egeneraTrapSeverity,
                egeneraTrapMessage
            }
    DESCRIPTION
            "The notification generated when an SBlade is disabled. (removed
             from service).

             This trap is driven by 'Blade <framename>/s<1|2> Out of Service Status
             true Event' event types.

             Since BladeFrame ES Systems do not utilize dedicated sBlades, this
             trap is not relevant to BladeFrame ES systems.

             Severity: 5"
    --#TYPE         "BladeFrame sBlade Disabled"
    --#SUMMARY      "%s"
    --#ARGUMENTS    { 4 }
    --#SEVERITY     INFORMATIONAL
    --#TIMEINDEX    99
    --#STATE        NONOPERATIONAL

        ::=    306


sBladeSelectedTrap TRAP-TYPE
    ENTERPRISE  egenera
    VARIABLES {
                sBladeIndex,
                sBladeFrameIndex,
                sBladeName,
                egeneraTrapSeverity,
                egeneraTrapMessage
            }
    DESCRIPTION
            "The notification generated when an sBlade has been
             selected.

             This trap is driven by 'Blade <framename>/s<1|2> Selected Status
             true Event' even types.

             Since BladeFrame ES Systems do not utilize dedicated sBlades, this
             trap is not relevant to BladeFrame ES systems.

             Severity: 5"
    --#TYPE         "BladeFrame sBlade Selected"
    --#SUMMARY      "%s"
    --#ARGUMENTS    { 4 }
    --#SEVERITY     INFORMATIONAL
    --#TIMEINDEX    99
    --#STATE        OPERATIONAL

        ::=    307


sBladeDeselectedTrap TRAP-TYPE
    ENTERPRISE  egenera
    VARIABLES {
                sBladeIndex,
                sBladeFrameIndex,
                sBladeName,
                egeneraTrapSeverity,
                egeneraTrapMessage
            }
    DESCRIPTION
            "The notification generated when a sBlade has been
             de-selected.

             This trap is driven by 'Blade <framename>/s<1|2> Selected Status
             false Event' even types.

             Since BladeFrame ES Systems do not utilize dedicated sBlades, this
             trap is not relevant to BladeFrame ES systems.

             Severity: 5"
    --#TYPE         "BladeFrame sBlade Deselected"
    --#SUMMARY      "%s"
    --#ARGUMENTS    { 4 }
    --#SEVERITY     INFORMATIONAL
    --#TIMEINDEX    99
    --#STATE        OPERATIONAL

        ::=    308


--sBladeHwThreshTrap TRAP-TYPE
--    ENTERPRISE egenera
--    VARIABLES {
--                sBladeIndex,
--                sBladeFrameIndex,
--                sBladeName,
--                hwTheshComponent,
--                hwTheshLevel,
--                egeneraTrapSeverity,
--                egeneraTrapMessage
--            }
--    DESCRIPTION
--            "Encapsulates hardward threshold events.
--
--            This trap has been deprecated in favor of sBladeVoltageUpperTrap,
--            sBladeVoltageLowerTrap, sBladeFanSpeedUpperTrap, sBladeFanSpeedLowerTrap,
--            sBladeTempUpperTrap, and sBladeTempLowerTrap."
--
--
--        ::=     309

sBladeHwEventTrap TRAP-TYPE
    ENTERPRISE  egenera
    VARIABLES {
                sBladeIndex,
                sBladeFrameIndex,
                sBladeName,
                egeneraTrapSeverity,
                egeneraTrapMessage
            }
    DESCRIPTION
            "Encapsulates generic events from hardware.

             This trap is driven by 'Blade <framename>/s<1|2> non-sensor
             Event' event types Examples message contents include:

             bmc reset

             Contact EES for more specific information.

             Since BladeFrame ES Systems do not utilize dedicated sBlades, this
             trap is not relevant to BladeFrame ES systems.

             Severity: 3"
    --#TYPE         "BladeFrame sBlade Hw Event"
    --#SUMMARY      "%s"
    --#ARGUMENTS    { 4 }
    --#SEVERITY     MINOR
    --#TIMEINDEX    99

        ::=     310



sBladeVoltageUpperTrap TRAP-TYPE
    ENTERPRISE egenera
    VARIABLES {
                sBladeIndex,
                sBladeFrameIndex,
                sBladeName,
                sensorName,
                sensorThreshold,
                sensorValue,
                egeneraTrapSeverity,
                egeneraTrapMessage
            }
    DESCRIPTION
            "Encapsulates sBlade critical high voltage sensor events.

             This trap is driven by 'Blade <framename>/s<1|2> <voltage-sensor-name>
             Critical High Event' event types.

             The sensorValue and sensorThreshold fields are ingeter representations
             of real numbers.  The real numbers are multiplied by 100 and rounded
             to produce an integer, thus 0.530 => 53.

             This trap replaces sBladeHwThreshTrap.

             Since BladeFrame ES Systems do not utilize dedicated sBlades, this
             trap is not relevant to BladeFrame ES systems.

             Severity: 3"
    --#TYPE         "BladeFrame sBlade Voltage Upper"
    --#SUMMARY      "%s"
    --#ARGUMENTS    { 7 }
    --#SEVERITY     MINOR
    --#TIMEINDEX    99

        ::=     311


sBladeVoltageLowerTrap TRAP-TYPE
    ENTERPRISE egenera
    VARIABLES {
                sBladeIndex,
                sBladeFrameIndex,
                sBladeName,
                sensorName,
                sensorThreshold,
                sensorValue,
                egeneraTrapSeverity,
                egeneraTrapMessage
            }
    DESCRIPTION
            "Encapsulates sBlade critical low voltage sensor events.

             This trap is driven by 'Blade <framename>/s<1|2> <voltage-sensor-name>
             Critical Low Event' event types.

             The sensorValue and sensorThreshold fields are ingeter representations
             of real numbers.  The real numbers are multiplied by 100 and rounded
             to produce an integer, thus 0.530 => 53.

             This trap replaces sBladeHwThreshTrap.

             Since BladeFrame ES Systems do not utilize dedicated sBlades, this
             trap is not relevant to BladeFrame ES systems.

             Severity: 3"
    --#TYPE         "BladeFrame sBlade Voltage Lower"
    --#SUMMARY      "%s"
    --#ARGUMENTS    { 7 }
    --#SEVERITY     MINOR
    --#TIMEINDEX    99

        ::=     312


sBladeFanSpeedUpperTrap TRAP-TYPE
    ENTERPRISE egenera
    VARIABLES {
                sBladeIndex,
                sBladeFrameIndex,
                sBladeName,
                sensorName,
                sensorThreshold,
                sensorValue,
                egeneraTrapSeverity,
                egeneraTrapMessage
            }
    DESCRIPTION
            "Encapsulates sBlade critical high fan speed  sensor events.

             This trap is driven by 'Blade <framename>/s<1|2> <fan-sensor-name>
             Critical High Event' event types.

             This trap replaces sBladeHwThreshTrap.

             Since BladeFrame ES Systems do not utilize dedicated sBlades, this
             trap is not relevant to BladeFrame ES systems.

             Severity: 3"
    --#TYPE         "BladeFrame sBlade Fan Speed Upper"
    --#SUMMARY      "%s"
    --#ARGUMENTS    { 7 }
    --#SEVERITY     MINOR
    --#TIMEINDEX    99

        ::=     313


sBladeFanSpeedLowerTrap TRAP-TYPE
    ENTERPRISE egenera
    VARIABLES {
                sBladeIndex,
                sBladeFrameIndex,
                sBladeName,
                sensorName,
                sensorThreshold,
                sensorValue,
                egeneraTrapSeverity,
                egeneraTrapMessage
            }
    DESCRIPTION
            "Encapsulates sBlade critical low fan speed sensor events.

             This trap is driven by 'Blade <framename>/s<1|2> <fan-sensor-name>
             Critical Low Event' event types.

             This trap replaces sBladeHwThreshTrap.

             Since BladeFrame ES Systems do not utilize dedicated sBlades, this
             trap is not relevant to BladeFrame ES systems.

             Severity: 3"
    --#TYPE         "BladeFrame sBlade Fan Speed Lower"
    --#SUMMARY      "%s"
    --#ARGUMENTS    { 7 }
    --#SEVERITY     MINOR
    --#TIMEINDEX    99

        ::=     314



sBladeTempUpperTrap TRAP-TYPE
    ENTERPRISE egenera
    VARIABLES {
                sBladeIndex,
                sBladeFrameIndex,
                sBladeName,
                sensorName,
                sensorThreshold,
                sensorValue,
                egeneraTrapSeverity,
                egeneraTrapMessage
            }
    DESCRIPTION
            "Encapsulates cBlade critical high temperature sensor events.

             This trap is driven by 'Blade <framename>/s<1|2> <temp-sensor-name>
             Critical High Event' event types.

             This trap replaces sBladeHwThreshTrap.

             Since BladeFrame ES Systems do not utilize dedicated sBlades, this
             trap is not relevant to BladeFrame ES systems.

             Severity: 3"
    --#TYPE         "BladeFrame sBlade Temp Upper"
    --#SUMMARY      "%s"
    --#ARGUMENTS    { 7 }
    --#SEVERITY     MINOR
    --#TIMEINDEX    99

        ::=     315


sBladeTempLowerTrap TRAP-TYPE
    ENTERPRISE egenera
    VARIABLES {
                sBladeIndex,
                sBladeFrameIndex,
                sBladeName,
                sensorName,
                sensorThreshold,
                sensorValue,
                egeneraTrapSeverity,
                egeneraTrapMessage
            }
    DESCRIPTION
            "Encapsulates sBlade critical low temperature sensor events.

             This trap is driven by 'Blade <framename>/s<1|2> <temp-sensor-name>
             Critical Low Event' event types.

             This trap replaces sBladeHwThreshTrap.

             Since BladeFrame ES Systems do not utilize dedicated sBlades, this
             trap is not relevant to BladeFrame ES systems.

             Severity: 3"
    --#TYPE         "BladeFrame sBlade Temp Lower"
    --#SUMMARY      "%s"
    --#ARGUMENTS    { 7 }
    --#SEVERITY     MINOR
    --#TIMEINDEX    99

        ::=     316



sBladePowerOnOpTrap TRAP-TYPE
    ENTERPRISE egenera
    VARIABLES {
                sBladeIndex,
                sBladeFrameIndex,
                sBladeName,
                egeneraTrapSeverity,
                egeneraTrapMessage
            }
    DESCRIPTION
            "Encapsulates sBlade power on operation event.

            This trap is driven by 'sBlade <framename>/s<1|2> Hardware Operation
            Event' event types.

            Since the underlying event type describes sBlade power on and off
            operation events, enabling/disabling this SNMP trap as an event action
            is bound to the enabling/disabling of sBladePowerOffOpTrap,
            sBladePowerCycleTrap, and sBladeResetOpTrap.

            Severity: 5"
    --#TYPE         "BladeFrame sBlade Power On Operation"
    --#SUMMARY      "%s"
    --#ARGUMENTS    { 4 }
    --#SEVERITY     INFORMATIONAL
    --#TIMEINDEX    99
    --#STATE        OPERATIONAL

        ::=     317


sBladePowerOffOpTrap TRAP-TYPE
    ENTERPRISE egenera
    VARIABLES {
                sBladeIndex,
                sBladeFrameIndex,
                sBladeName,
                egeneraTrapSeverity,
                egeneraTrapMessage
            }
    DESCRIPTION
            "Encapsulates sBlade power off operation event.

            This trap is driven by 'sBlade <framename>/s<1|2> Hardware Operation
            Event' event types.

            Since the underlying event type describes sBlade power on and off
            operation events, enabling/disabling this SNMP trap as an event action
            is bound to the enabling/disabling of sBladePowerOnOpTrap,
            sBladePowerCycleTrap, and sBladeResetOpTrap.

            Severity: 5"
    --#TYPE         "BladeFrame sBlade Power Off Operation"
    --#SUMMARY      "%s"
    --#ARGUMENTS    { 4 }
    --#SEVERITY     INFORMATIONAL
    --#TIMEINDEX    99
    --#STATE        OPERATIONAL

        ::=     318


sBladePowerCycleOpTrap TRAP-TYPE
    ENTERPRISE egenera
    VARIABLES {
                sBladeIndex,
                sBladeFrameIndex,
                sBladeName,
                egeneraTrapSeverity,
                egeneraTrapMessage
            }
    DESCRIPTION
            "Encapsulates sBlade power cycle operation event.

            This trap is driven by 'sBlade <framename>/s<1|2> Hardware Operation
            Event' event types.

            Since the underlying event type describes sBlade power on and off
            operation events, enabling/disabling this SNMP trap as an event action
            is bound to the enabling/disabling of sBladePowerOnOpTrap,
            sBladePowerCycleTrap, and sBladeResetOpTrap.

            Severity: 5"
    --#TYPE         "BladeFrame sBlade Power Cycle Operation"
    --#SUMMARY      "%s"
    --#ARGUMENTS    { 4 }
    --#SEVERITY     INFORMATIONAL
    --#TIMEINDEX    99
    --#STATE        OPERATIONAL

        ::=     319


sBladeResetOpTrap TRAP-TYPE
    ENTERPRISE egenera
    VARIABLES {
                sBladeIndex,
                sBladeFrameIndex,
                sBladeName,
                egeneraTrapSeverity,
                egeneraTrapMessage
            }
    DESCRIPTION
            "Encapsulates sBlade reset operation event.

            This trap is driven by 'sBlade <framename>/s<1|2> Hardware Operation
            Event' event types.

            Since the underlying event type describes sBlade power on and off
            operation events, enabling/disabling this SNMP trap as an event action
            is bound to the enabling/disabling of sBladePowerOnOpTrap,
            sBladePowerCycleTrap, and sBladePowerCycleOpTrap.

            Severity: 5"
    --#TYPE         "BladeFrame sBlade Reset Operation"
    --#SUMMARY      "%s"
    --#ARGUMENTS    { 4 }
    --#SEVERITY     INFORMATIONAL
    --#TIMEINDEX    99
    --#STATE        OPERATIONAL

        ::=     320


sBladeNonFatalHwErrorTrap TRAP-TYPE
    ENTERPRISE  egenera
    VARIABLES {
                sBladeIndex,
                sBladeFrameIndex,
                sBladeName,
                egeneraTrapSeverity,
                egeneraTrapMessage
            }
    DESCRIPTION
            "The notification generated when sBlade hardware detects a non-fatal
            error.

            This trap is driven by 'sBlade <bladeframe>/s<1|2> NonFatal Hardware
            Error Event' event types.

            Severity: 3"
    --#TYPE         "BladeFrame sBlade Non-Fatal Hw Error"
    --#SUMMARY      "%s"
    --#ARGUMENTS    { 4 }
    --#SEVERITY     MINOR
    --#TIMEINDEX    99
    --#STATE        OPERATIONAL

        ::=     321


sBladeFatalHwErrorTrap TRAP-TYPE
    ENTERPRISE  egenera
    VARIABLES {
                sBladeIndex,
                sBladeFrameIndex,
                sBladeName,
                egeneraTrapSeverity,
                egeneraTrapMessage
            }
    DESCRIPTION
            "The notification generated when sBlade hardware detects a fatal
            error.

            This trap is driven by 'sBlade <bladeframe>/s<1|2> Fatal Hardware
            Error Event' event types.

            Severity: 1"
    --#TYPE         "BladeFrame sBlade Fatal Hw Error"
    --#SUMMARY      "%s"
    --#ARGUMENTS    { 4 }
    --#SEVERITY     CRITICAL
    --#TIMEINDEX    99

        ::=     322


sBladeOutOfServicePendingTrap TRAP-TYPE
    ENTERPRISE  egenera
    VARIABLES {
                sBladeIndex,
                sBladeFrameIndex,
                sBladeName,
                egeneraTrapSeverity,
                egeneraTrapMessage
            }
    DESCRIPTION
            "The notification generated when a sBlade enters the 'out of service
            pending' state.

            This trap is driven by 'cBlade <bladeframe>/s<1|2> Out of Service Pending
            Event' event types

            Severity: 5"
    --#TYPE         "BladeFrame sBlade Out of Service Pending"
    --#SUMMARY      "%s"
    --#ARGUMENTS    { 4 }
    --#SEVERITY     INFORMATIONAL
    --#TIMEINDEX    99
    --#STATE        OPERATIONAL

        ::=     323



pBladeInsertedTrap TRAP-TYPE
    ENTERPRISE  egenera
    VARIABLES {
                pBladeIndex,
                pBladeFrameIndex,
                pBladeName,
                egeneraTrapSeverity,
                egeneraTrapMessage
            }
    DESCRIPTION
            "The notification generated when a pBlade is inserted into
            a BladeFrame.

            This trap is driven by 'BladeFrame <framename> Blade Inserted Event'
            event types that describe pBlade insertions.

            Since the underlying event type describes pBlade, sBlade, and sBlade
            insertions, enabling/disabling this SNMP trap as an event action is
            bound to the enabling/disabling of sBladeInsertedTrap and
            sBladeInsertedTrap.

            Severity: 5"
    --#TYPE         "BladeFrame pBlade Inserted"
    --#SUMMARY      "%s"
    --#ARGUMENTS    { 4 }
    --#SEVERITY     INFORMATIONAL
    --#TIMEINDEX    99
    --#STATE        OPERATIONAL

        ::=     401


pBladeRemovedTrap TRAP-TYPE
    ENTERPRISE  egenera
    VARIABLES {
                pBladeIndex,
                pBladeFrameIndex,
                pBladeName,
                egeneraTrapSeverity,
                egeneraTrapMessage
            }
    DESCRIPTION
            "The notification generated when a pBlade is removed from
            a BladeFrame.

            This trap is driven by 'BladeFrame <framename> Blade Removed Event'
            event types that describe pBlade removal events.

            Since the underlying event type describes pBlade, cBlade, and sBlade
            removal, enabling/disabling this SNMP trap as an event action is
            bound to the enabling/disabling of sBladeRemovedTrap and
            cBladeRemovedTrap.

            Severity: 3"
    --#TYPE         "BladeFrame pBlade Removed"
    --#SUMMARY      "%s"
    --#ARGUMENTS    { 4 }
    --#SEVERITY     MINOR
    --#TIMEINDEX    99
    --#STATE        NONOPERATIONAL

        ::=     402


pBladePowerOnTrap TRAP-TYPE
    ENTERPRISE  egenera
    VARIABLES {
                pBladeIndex,
                pBladeFrameIndex,
                pBladeName,
                egeneraTrapSeverity,
                egeneraTrapMessage
            }
    DESCRIPTION
            "The notification generated when a pBlade is powered on.

            This trap is driven by 'Blade <framename>/p<1..24> Power Status Event'
            event types describing power on events.

            Since the underlying event type describes pBlade power on and off
            events, enabling/disabling this SNMP trap as an event action is bound
            to the enabling/disabling of pBladePowerOffTrap.

            Severity: 5"
    --#TYPE         "BladeFrame pBlade Power On"
    --#SUMMARY      "%s"
    --#ARGUMENTS    { 4 }
    --#SEVERITY     INFORMATIONAL
    --#TIMEINDEX    99
    --#STATE        OPERATIONAL

        ::=     403


pBladePowerOffTrap TRAP-TYPE
    ENTERPRISE  egenera
    VARIABLES {
                pBladeIndex,
                pBladeFrameIndex,
                pBladeName,
                egeneraTrapSeverity,
                egeneraTrapMessage
            }
    DESCRIPTION
            "The notification generated when a pBlade is powered off.

            This trap is driven by 'Blade <framename>/p<1..24> Power Status Event'
            event types describing power on events.

            Since the underlying event type describes sBlade power on and off
            events, enabling/disabling this SNMP trap as an event action is bound
            to the enabling/disabling of pBladePowerOnTrap.

            Severity: 5"
    --#TYPE         "BladeFrame pBlade Power Off"
    --#SUMMARY      "%s"
    --#ARGUMENTS    { 4 }
    --#SEVERITY     INFORMATIONAL
    --#TIMEINDEX    99
    --#STATE        NONOPERATIONAL

        ::=     404


pBladeBootedTrap TRAP-TYPE
    ENTERPRISE  egenera
    VARIABLES {
                pBladeIndex,
                pBladeFrameIndex,
                pBladeName,
                egeneraTrapSeverity,
                egeneraTrapMessage
            }
    DESCRIPTION
            "The notification generated when a pBlade has successfully
            booted.

            This trap is driven by 'blade.status.monitor.event' event types
            that describe a pBlade transition from the booting state to the
            running state.

            This event type is not user visible, and will not appear in
            CLI or GUI event queries.  The trap exists to satisfy early
            requirements documents.

            Severity: 5"
    --#TYPE         "BladeFrame pBlade Booted"
    --#SUMMARY      "%s"
    --#ARGUMENTS    { 4 }
    --#SEVERITY     INFORMATIONAL
    --#TIMEINDEX    99
    --#STATE        OPERATIONAL

        ::=     405


pBladeShutdownTrap TRAP-TYPE
    ENTERPRISE  egenera
    VARIABLES {
                pBladeIndex,
                pBladeFrameIndex,
                pBladeName,
                egeneraTrapSeverity,
                egeneraTrapMessage
            }
    DESCRIPTION
            "The notification generated when a pBlade has been shut
             down.

            This trap is driven by 'blade.status.monitor.event' event types
            that describe a pBlade transition from the shutting down state to
            the shutdown state.

            This event type is not user visible, and will not appear in
            CLI or GUI event queries.  The trap exists to satisfy early
            requirements documents.

            Severity: 5"
    --#TYPE         "BladeFrame pBlade Shut Down"
    --#SUMMARY      "%s"
    --#ARGUMENTS    { 4 }
    --#SEVERITY     INFORMATIONAL
    --#TIMEINDEX    99
    --#STATE        NONOPERATIONAL

        ::=     406


pBladeEnabledTrap TRAP-TYPE
    ENTERPRISE  egenera
    VARIABLES {
                pBladeIndex,
                pBladeFrameIndex,
                pBladeName,
                egeneraTrapSeverity,
                egeneraTrapMessage
            }
    DESCRIPTION
            "The notification generated when a pBlade has been enabled
             (returns to service).

             This trap is driven by 'Blade <framename>/p<1..24> Out of Service Status
             false Event' event types.

             Severity: 5"
    --#TYPE         "BladeFrame pBlade Enabled"
    --#SUMMARY      "%s"
    --#ARGUMENTS    { 4 }
    --#SEVERITY     INFORMATIONAL
    --#TIMEINDEX    99
    --#STATE        OPERATIONAL

        ::=     407


pBladeDisabledTrap TRAP-TYPE
    ENTERPRISE  egenera
    VARIABLES {
                pBladeIndex,
                pBladeFrameIndex,
                pBladeName,
                egeneraTrapSeverity,
                egeneraTrapMessage
            }
    DESCRIPTION
            "The notification generated when a pBlade has been disabled
             (removed from service).

             This trap is driven by 'Blade <framename>/p<1..24> Out of Service Status
             true Event' event types.

             Severity: 5"
    --#TYPE         "BladeFrame pBlade Disabled"
    --#SUMMARY      "%s"
    --#ARGUMENTS    { 4 }
    --#SEVERITY     INFORMATIONAL
    --#TIMEINDEX    99
    --#STATE        NONOPERATIONAL

        ::=     408


pBladeSelectedTrap TRAP-TYPE
    ENTERPRISE  egenera
    VARIABLES {
                pBladeIndex,
                pBladeFrameIndex,
                pBladeName,
                egeneraTrapSeverity,
                egeneraTrapMessage
            }
    DESCRIPTION
            "The notification generated when a pBlade has been selected.

             This trap is driven by 'Blade <framename>/p<1..24> Selected Status
             true Event' even types.

             Severity: 5"
    --#TYPE         "BladeFrame pBlade Selected"
    --#SUMMARY      "%s"
    --#ARGUMENTS    { 4 }
    --#SEVERITY     INFORMATIONAL
    --#TIMEINDEX    99
    --#STATE        OPERATIONAL

        ::=     409


pBladeDeselectedTrap TRAP-TYPE
    ENTERPRISE  egenera
    VARIABLES {
                pBladeIndex,
                pBladeFrameIndex,
                pBladeName,
                egeneraTrapSeverity,
                egeneraTrapMessage
            }
    DESCRIPTION
            "The notification generated when a pBlade has been unselected.

             This trap is driven by 'Blade <framename>/p<1..24> Selected Status
             false Event' even types.

             Severity: 5"
    --#TYPE         "BladeFrame pBlade Deselected"
    --#SUMMARY      "%s"
    --#ARGUMENTS    { 4 }
    --#SEVERITY     INFORMATIONAL
    --#TIMEINDEX    99
    --#STATE        OPERATIONAL

        ::=     410


pBladeHwEventTrap TRAP-TYPE
    ENTERPRISE  egenera
    VARIABLES {
                pBladeIndex,
                pBladeFrameIndex,
                pBladeName,
                egeneraTrapSeverity,
                egeneraTrapMessage
            }
    DESCRIPTION
            "Encapsulates generic events from hardware.

            This trap is driven by 'Blade <framename>/p<1..24> non-sensor Event'
            event types that do not indicate panic, commanded shutdown,
            commanded reboot, or init level events.  Examples message contents
            include:

            OEM Type 0xe0, value = 0x64:0x21:0xce:0xe0:0x1d:0x00:0x00:0x00...
            bmc reset
            deasserted, value = 0x0211
            system booted

            Contact EES for more specific information.

            Since the underlying event type describes pBlade all non-sensor hardware
            events, and since there are specific traps for panic, commanded shutdown,
            commanded reboot, and init level events, enabling/disabling this SNMP trap
            as an event action is bound to the enabling/disabling of pBladePanicTrap,
            pBladeCmdShutdownTrap, pBladeCmdRebootTrap, pBladeCmdHaltTrap, and
            pBladeInitTrap.

            Severity: 3"
    --#TYPE         "BladeFrame pBlade Hw Event"
    --#SUMMARY      "%s"
    --#ARGUMENTS    { 4 }
    --#SEVERITY     MINOR
    --#TIMEINDEX    99

        ::=     411


--pBladeHwThreshTrap TRAP-TYPE
--    ENTERPRISE egenera
--    VARIABLES {
--                pBladeIndex,
--                pBladeFrameIndex,
--                pBladeName,
--                hwTheshComponent,
--                hwTheshLevel,
--                egeneraTrapSeverity,
--                egeneraTrapMessage
--            }
--    DESCRIPTION
--            "Encapsulates hardward threshold events.
--
--            This trap has been deprecated in favor of pBladeVoltageUpperTrap,
--            pBladeVoltageLowerTrap, pBladeFanSpeedUpperTrap, pBladeFanSpeedLowerTrap,
--            pBladeTempUpperTrap, and pBladeTempLowerTrap."
--
--        ::=     412


pBladePanicTrap TRAP-TYPE
    ENTERPRISE  egenera
    VARIABLES {
                pBladeIndex,
                pBladeFrameIndex,
                pBladeName,
                egeneraTrapSeverity,
                egeneraTrapMessage
            }
    DESCRIPTION
            "Encapsulates hardware events identifying pBlade panics that
            cause the cBlade to enter KDB, reboot, or halt'

            This trap is driven by 'Blade <framename>/p<1..24> non-sensor Event'
            event types that describe kernel panics.

            Contact EES for more specific information.

            Since the underlying event type describes pBlade non-sensor hardware
            events, and since there are specific traps for panic, commanded shutdown,
            commanded reboot, and init level events, enabling/disabling this SNMP trap
            as an event action is bound to the enabling/disabling of pBladeHwEventTrap,
            pBladeCmdShutdownTrap, pBladeCmdRebootTrap, pBladeCmdHaltTrap, and
            pBladeInitTrap.

            Severity: 3"
    --#TYPE         "BladeFrame pBlade Panic"
    --#SUMMARY      "%s"
    --#ARGUMENTS    { 4 }
    --#SEVERITY     MINOR
    --#TIMEINDEX    99

        ::=     413


pBladeCmdHaltTrap TRAP-TYPE
    ENTERPRISE  egenera
    VARIABLES {
                pBladeIndex,
                pBladeFrameIndex,
                pBladeName,
                egeneraTrapSeverity,
                egeneraTrapMessage
            }
    DESCRIPTION
            "Encapsulates hardware events indicating intentional pBlade
            halt.

            This trap is driven by 'Blade <framename>/p<1..24> non-sensor Event'
            event types that describe commanded halts.

            Contact EES for more specific information.

            Since the underlying event type describes pBlade non-sensor hardware
            events, and since there are specific traps for panic, commanded shutdown,
            commanded reboot, and init level events, enabling/disabling this SNMP trap
            as an event action is bound to the enabling/disabling of pBladeHwEventTrap,
            pBladeCmdShutdownTrap, pBladeCmdRebootTrap, pBladePanicTrap, and
            pBladeInitTrap.

            Severity: 3"
    --#TYPE         "BladeFrame pBlade Cmd Halt"
    --#SUMMARY      "%s"
    --#ARGUMENTS    { 4 }
    --#SEVERITY     MINOR
    --#TIMEINDEX    99

        ::=     414


pBladeCmdRebootTrap TRAP-TYPE
    ENTERPRISE  egenera
    VARIABLES {
                pBladeIndex,
                pBladeFrameIndex,
                pBladeName,
                egeneraTrapSeverity,
                egeneraTrapMessage
            }
    DESCRIPTION
            "Encapsulates hardware events indicating intentional pBlade
            reboot.

            This trap is driven by 'Blade <framename>/p<1..24> non-sensor Event'
            event types that describe commanded reboots.

            Contact EES for more specific information.

            Since the underlying event type describes pBlade non-sensor hardware
            events, and since there are specific traps for panic, commanded shutdown,
            commanded reboot, and init level events, enabling/disabling this SNMP trap
            as an event action is bound to the enabling/disabling of pBladeHwEventTrap,
            pBladeCmdShutdownTrap, pBladeCmdHaltTrap, pBladePanicTrap, and
            pBladeInitTrap.

            Severity: 3"
    --#TYPE         "BladeFrame pBlade Cmd Reboot"
    --#SUMMARY      "%s"
    --#ARGUMENTS    { 4 }
    --#SEVERITY     MINOR
    --#TIMEINDEX    99

        ::=     415


pBladeInitTrap TRAP-TYPE
    ENTERPRISE  egenera
    VARIABLES {
                pBladeIndex,
                pBladeFrameIndex,
                pBladeName,
                egeneraTrapSeverity,
                egeneraTrapMessage
            }
    DESCRIPTION
            "Encapsulates hardware events indicating intentional pBlade
            has reached an init level.

            This trap is driven by 'Blade <framename>/p<1..24> non-sensor Event'
            event types that describe init level reached.

            Contact EES for more specific information.

            Since the underlying event type describes pBlade non-sensor hardware
            events, and since there are specific traps for panic, commanded shutdown,
            commanded reboot, and init level events, enabling/disabling this SNMP trap
            as an event action is bound to the enabling/disabling of pBladeHwEventTrap,
            pBladeCmdShutdownTrap, pBladeCmdHaltTrap, pBladeCmdRebootTrap, and
            pBladePanicTrap.

            Severity: 3"
    --#TYPE         "BladeFrame pBlade Cmd Init"
    --#SUMMARY      "%s"
    --#ARGUMENTS    { 4 }
    --#SEVERITY     MINOR
    --#TIMEINDEX    99

        ::=     416



pBladeVoltageUpperTrap TRAP-TYPE
    ENTERPRISE egenera
    VARIABLES {
                pBladeIndex,
                pBladeFrameIndex,
                pBladeName,
                sensorName,
                sensorThreshold,
                sensorValue,
                egeneraTrapSeverity,
                egeneraTrapMessage
            }
    DESCRIPTION
            "Encapsulates pBlade critical high voltage sensor events.

            This trap is driven by 'Blade <framename>/p<1..24> <voltage-sensor-name>
            Critical High Event' event types.

            The sensorValue and sensorThreshold fields are ingeter representations
            of real numbers.  The real numbers are multiplied by 100 and rounded
            to produce an integer, thus 0.530 => 53.

            This trap replaces pBladeHwThreshTrap.

            Severity: 3"
    --#TYPE         "BladeFrame pBlade Voltage Upper"
    --#SUMMARY      "%s"
    --#ARGUMENTS    { 7 }
    --#SEVERITY     MINOR
    --#TIMEINDEX    99

        ::=     417


pBladeVoltageLowerTrap TRAP-TYPE
    ENTERPRISE egenera
    VARIABLES {
                pBladeIndex,
                pBladeFrameIndex,
                pBladeName,
                sensorName,
                sensorThreshold,
                sensorValue,
                egeneraTrapSeverity,
                egeneraTrapMessage
            }
    DESCRIPTION
            "Encapsulates pBlade critical low voltage sensor events.

            This trap is driven by 'Blade <framename>/p<1..24> <voltage-sensor-name>
            Critical Low Event' event types.

            The sensorValue and sensorThreshold fields are ingeter representations
            of real numbers.  The real numbers are multiplied by 100 and rounded
            to produce an integer, thus 0.530 => 53.

            This trap replaces pBladeHwThreshTrap.

            Severity: 3"
    --#TYPE         "BladeFrame pBlade Voltage Lower"
    --#SUMMARY      "%s"
    --#ARGUMENTS    { 7 }
    --#SEVERITY     MINOR
    --#TIMEINDEX    99

        ::=     418


pBladeFanSpeedUpperTrap TRAP-TYPE
    ENTERPRISE egenera
    VARIABLES {
                pBladeIndex,
                pBladeFrameIndex,
                pBladeName,
                sensorName,
                sensorThreshold,
                sensorValue,
                egeneraTrapSeverity,
                egeneraTrapMessage
            }
    DESCRIPTION
            "Encapsulates pBlade critical high fan speed  sensor events.

            This trap is driven by 'Blade <framename>/p<1..24> <fan-sensor-name>
            Critical High Event' event types.

            This trap replaces pBladeHwThreshTrap.

            Severity: 3"
    --#TYPE         "BladeFrame pBlade Fan Speed Upper"
    --#SUMMARY      "%s"
    --#ARGUMENTS    { 7 }
    --#SEVERITY     MINOR
    --#TIMEINDEX    99

        ::=     419


pBladeFanSpeedLowerTrap TRAP-TYPE
    ENTERPRISE egenera
    VARIABLES {
                pBladeIndex,
                pBladeFrameIndex,
                pBladeName,
                sensorName,
                sensorThreshold,
                sensorValue,
                egeneraTrapSeverity,
                egeneraTrapMessage
            }
    DESCRIPTION
            "Encapsulates pBlade critical low fan speed sensor events.

            This trap is driven by 'Blade <framename>/p<1..24> <fan-sensor-name>
            Critical Low Event' event types.

            This trap replaces pBladeHwThreshTrap.

            Severity: 3"
    --#TYPE         "BladeFrame pBlade Fan Speed Lower"
    --#SUMMARY      "%s"
    --#ARGUMENTS    { 7 }
    --#SEVERITY     MINOR
    --#TIMEINDEX    99

        ::=     420



pBladeTempUpperTrap TRAP-TYPE
    ENTERPRISE egenera
    VARIABLES {
                pBladeIndex,
                pBladeFrameIndex,
                pBladeName,
                sensorName,
                sensorThreshold,
                sensorValue,
                egeneraTrapSeverity,
                egeneraTrapMessage
            }
    DESCRIPTION
            "Encapsulates pBlade critical high temperature sensor events.

            This trap is driven by 'Blade <framename>/p<1..24> <temp-sensor-name>
            Critical High Event' event types.

            This trap replaces pBladeHwThreshTrap.

            Severity: 3"
    --#TYPE         "BladeFrame pBlade Temp Upper"
    --#SUMMARY      "%s"
    --#ARGUMENTS    { 7 }
    --#SEVERITY     MINOR
    --#TIMEINDEX    99

        ::=     421


pBladeTempLowerTrap TRAP-TYPE
    ENTERPRISE egenera
    VARIABLES {
                pBladeIndex,
                pBladeFrameIndex,
                pBladeName,
                sensorName,
                sensorThreshold,
                sensorValue,
                egeneraTrapSeverity,
                egeneraTrapMessage
            }
    DESCRIPTION
            "Encapsulates pBlade critical low temperature sensor events.

            This trap is driven by 'Blade <framename>/p<1..24> <temp-sensor-name>
            Critical Low Event' event types.

            This trap replaces pBladeHwThreshTrap.

            Severity: 3"
    --#TYPE         "BladeFrame pBlade Temp Lower"
    --#SUMMARY      "%s"
    --#ARGUMENTS    { 7 }
    --#SEVERITY     MINOR
    --#TIMEINDEX    99

        ::=     422


pBladeWinkoutTrap TRAP-TYPE
    ENTERPRISE egenera
    VARIABLES {
                pBladeIndex,
                pBladeFrameIndex,
                pBladeName,
                egeneraTrapSeverity,
                egeneraTrapMessage
            }
    DESCRIPTION
            "Encapsulates pBlade wink-out events..

            This trap is driven by 'pBlade <framename>/p<1..24> Winked Out Event
            event types.

            Severity: 3"
    --#TYPE         "BladeFrame pBlade Winked out"
    --#SUMMARY      "%s"
    --#ARGUMENTS    { 4 }
    --#SEVERITY     MINOR
    --#TIMEINDEX    99

        ::=     423


pBladePowerOnOpTrap TRAP-TYPE
    ENTERPRISE egenera
    VARIABLES {
                pBladeIndex,
                pBladeFrameIndex,
                pBladeName,
                egeneraTrapSeverity,
                egeneraTrapMessage
            }
    DESCRIPTION
            "Encapsulates pBlade power on operation event.

            This trap is driven by 'pBlade <framename>/p<1..24> Hardware Operation
            Event' event types.

            Since the underlying event type describes pBlade power on and off
            operation events, enabling/disabling this SNMP trap as an event action
            is bound to the enabling/disabling of pBladePowerOffOpTrap,
            pBladePowerCycleTrap, pBladeResetOpTrap, and pBladeNMIOpTrap.

            Severity: 5"
    --#TYPE         "BladeFrame pBlade Power On Operation"
    --#SUMMARY      "%s"
    --#ARGUMENTS    { 4 }
    --#SEVERITY     INFORMATIONAL
    --#TIMEINDEX    99
    --#STATE        OPERATIONAL

        ::=     424


pBladePowerOffOpTrap TRAP-TYPE
    ENTERPRISE egenera
    VARIABLES {
                pBladeIndex,
                pBladeFrameIndex,
                pBladeName,
                egeneraTrapSeverity,
                egeneraTrapMessage
            }
    DESCRIPTION
            "Encapsulates pBlade power off operation event.

            This trap is driven by 'pBlade <framename>/p<1..24> Hardware Operation
            Event' event types.

            Since the underlying event type describes pBlade power on and off
            operation events, enabling/disabling this SNMP trap as an event action
            is bound to the enabling/disabling of pBladePowerOnOpTrap,
            pBladePowerCycleTrap, pBladeResetOpTrap, and pBladeNMIOpTrap.

            Severity: 5"
    --#TYPE         "BladeFrame pBlade Power Off Operation"
    --#SUMMARY      "%s"
    --#ARGUMENTS    { 4 }
    --#SEVERITY     INFORMATIONAL
    --#TIMEINDEX    99
    --#STATE        OPERATIONAL

        ::=     425


pBladePowerCycleOpTrap TRAP-TYPE
    ENTERPRISE egenera
    VARIABLES {
                pBladeIndex,
                pBladeFrameIndex,
                pBladeName,
                egeneraTrapSeverity,
                egeneraTrapMessage
            }
    DESCRIPTION
            "Encapsulates pBlade power cycle operation event.

            This trap is driven by 'pBlade <framename>/p<1..24> Hardware Operation
            Event' event types.

            Since the underlying event type describes pBlade power on and off
            operation events, enabling/disabling this SNMP trap as an event action
            is bound to the enabling/disabling of pBladePowerOnOpTrap,
            pBladePowerCycleTrap, pBladeResetOpTrap, and pBladeNMIOpTrap.

            Severity: 5"
    --#TYPE         "BladeFrame pBlade Power Cycle Operation"
    --#SUMMARY      "%s"
    --#ARGUMENTS    { 4 }
    --#SEVERITY     INFORMATIONAL
    --#TIMEINDEX    99
    --#STATE        OPERATIONAL

        ::=     426


pBladeResetOpTrap TRAP-TYPE
    ENTERPRISE egenera
    VARIABLES {
                pBladeIndex,
                pBladeFrameIndex,
                pBladeName,
                egeneraTrapSeverity,
                egeneraTrapMessage
            }
    DESCRIPTION
            "Encapsulates pBlade reset operation event.

            This trap is driven by 'pBlade <framename>/p<1..24> Hardware Operation
            Event' event types.

            Since the underlying event type describes pBlade power on and off
            operation events, enabling/disabling this SNMP trap as an event action
            is bound to the enabling/disabling of pBladePowerOnOpTrap,
            pBladePowerCycleTrap, pBladePowerCycleOpTrap, and pBladeNMIOpTrap.

            Severity: 5"
    --#TYPE         "BladeFrame pBlade Reset Operation"
    --#SUMMARY      "%s"
    --#ARGUMENTS    { 4 }
    --#SEVERITY     INFORMATIONAL
    --#TIMEINDEX    99
    --#STATE        OPERATIONAL

        ::=     427


pBladeNMIOpTrap TRAP-TYPE
    ENTERPRISE egenera
    VARIABLES {
                pBladeIndex,
                pBladeFrameIndex,
                pBladeName,
                egeneraTrapSeverity,
                egeneraTrapMessage
            }
    DESCRIPTION
            "Encapsulates pBlade reset operation event.

            This trap is driven by 'pBlade <framename>/p<1..24> Hardware Operation
            Event' event types.

            Since the underlying event type describes pBlade power on and off
            operation events, enabling/disabling this SNMP trap as an event action
            is bound to the enabling/disabling of pBladePowerOnOpTrap,
            pBladePowerCycleTrap, pBladePowerCycleOpTrap, and pBladeResetOpTrap.

            Severity: 5"
    --#TYPE         "BladeFrame pBlade NMI Operation"
    --#SUMMARY      "%s"
    --#ARGUMENTS    { 4 }
    --#SEVERITY     INFORMATIONAL
    --#TIMEINDEX    99
    --#STATE        OPERATIONAL

        ::=     428



pBladeNonFatalHwErrorTrap TRAP-TYPE
    ENTERPRISE  egenera
    VARIABLES {
                pBladeIndex,
                pBladeFrameIndex,
                pBladeName,
                egeneraTrapSeverity,
                egeneraTrapMessage
            }
    DESCRIPTION
            "The notification generated when pBlade hardware detects a non-fatal
            error, such as a correctable ECC memory error.

            This trap is driven by 'pBlade <bladeframe>/p<1..24> NonFatal Hardware
            Error Event' event types.

            Severity: 3"
    --#TYPE         "BladeFrame pBlade Non-Fatal Hw Error"
    --#SUMMARY      "%s"
    --#ARGUMENTS    { 4 }
    --#SEVERITY     MINOR
    --#TIMEINDEX    99
    --#STATE        OPERATIONAL

        ::=     429


pBladeFatalHwErrorTrap TRAP-TYPE
    ENTERPRISE  egenera
    VARIABLES {
                pBladeIndex,
                pBladeFrameIndex,
                pBladeName,
                egeneraTrapSeverity,
                egeneraTrapMessage
            }
    DESCRIPTION
            "The notification generated when pBlade hardware detects a fatal
            error, such as an uncorrectable ECC memory error.

            This trap is driven by 'pBlade <bladeframe>/p<1..24> Fatal Hardware
            Error Event' event types.

            Severity: 1"
    --#TYPE         "BladeFrame pBlade Fatal Hw Error"
    --#SUMMARY      "%s"
    --#ARGUMENTS    { 4 }
    --#SEVERITY     CRITICAL
    --#TIMEINDEX    99
    --#STATE        OPERATIONAL

        ::=     430



pBladeHwErrorThresholdTrap TRAP-TYPE
    ENTERPRISE  egenera
    VARIABLES {
                pBladeIndex,
                pBladeFrameIndex,
                pBladeName,
                egeneraTrapSeverity,
                egeneraTrapMessage
            }
    DESCRIPTION
            "The notification generated when pBlade is shutdown and marked
            out-of-service due to excessive fatal hardware errors

            This trap is driven by 'pBlade <bladeframe>/p<1..24> Hardware Error
            Threshold Event' event types

            Severity: 1"
    --#TYPE         "BladeFrame pBlade Hw Error Threshold"
    --#SUMMARY      "%s"
    --#ARGUMENTS    { 4 }
    --#SEVERITY     CRITICAL
    --#TIMEINDEX    99
    --#STATE        NONOPERATIONAL

        ::=     431


pBladeOutOfServicePendingTrap TRAP-TYPE
    ENTERPRISE  egenera
    VARIABLES {
                pBladeIndex,
                pBladeFrameIndex,
                pBladeName,
                egeneraTrapSeverity,
                egeneraTrapMessage
            }
    DESCRIPTION
            "The notification generated when a pBlade enters the 'out of service
            pending' state.

            This trap is driven by 'cBlade <bladeframe>/p<1..24> Out of Service Pending
            Event' event types

            Severity: 5"
    --#TYPE         "pBlade Out Of Service Pending"
    --#SUMMARY      "%s"
    --#ARGUMENTS    { 4 }
    --#SEVERITY     INFORMATIONAL
    --#TIMEINDEX    99
    --#STATE        OPERATIONAL

        ::=     432


pBladeBootImageChangedTrap TRAP-TYPE
    ENTERPRISE  egenera
    VARIABLES {
                pBladeIndex,
                pBladeFrameIndex,
                pBladeName,
                egeneraTrapSeverity,
                egeneraTrapMessage
            }
    DESCRIPTION
            "The notification generated when a pBlade boot image is changed.

            This trap is driven by 'pBlade <bladeframe>/p<1..24> Boot Image Changed
            Event' event types

            Severity: 5"
    --#TYPE         "pBlade Boot Image Changed"
    --#SUMMARY      "%s"
    --#ARGUMENTS    { 4 }
    --#SEVERITY     INFORMATIONAL
    --#TIMEINDEX    99
    --#STATE        OPERATIONAL

        ::=     433


pBladeVbladeRamOvercommitTrap TRAP-TYPE
    ENTERPRISE  egenera
    VARIABLES {
                pBladeIndex,
                pBladeFrameIndex,
                pBladeName,
                egeneraTrapSeverity,
                egeneraTrapMessage
            }
    DESCRIPTION
            "The notification generated when vBlade RAM is overcommited on pBlade insert.

            This trap is driven by 'pBlade <bladeframe>/p<1..24> vBlade RAM Overcommit
            Event' event types

            Severity: 3"
    --#TYPE         "pBlade Vblade Ram Overcommitted"
    --#SUMMARY      "%s"
    --#ARGUMENTS    { 4 }
    --#SEVERITY     MINOR
    --#TIMEINDEX    99

        ::=     434


pBladeIpmiCeccThresholdTrap TRAP-TYPE
    ENTERPRISE  egenera
    VARIABLES {
                pBladeIndex,
                pBladeFrameIndex,
                pBladeName,
                egeneraTrapSeverity,
                egeneraTrapMessage
            }
    DESCRIPTION
            "The notification generated when a pBlade has met the Correctable ECC Event Threshold.

            This trap is driven by 'pBlade <bladeframe>/p<1..24> Ipmi Cecc Threshold
            Event' event types

            Severity: 2"
    --#TYPE         "pBlade Ipmi Cecc Threshold"
    --#SUMMARY      "%s"
    --#ARGUMENTS    { 4 }
    --#SEVERITY     MAJOR
    --#TIMEINDEX    99

        ::=     435


pBladeWarmedTrap TRAP-TYPE
    ENTERPRISE  egenera
    VARIABLES {
                pBladeIndex,
                pBladeFrameIndex,
                pBladeName,
                egeneraTrapSeverity,
                egeneraTrapMessage
            }
    DESCRIPTION
            "The notification generated when a pBlade is set to the warm
             state.

             This trap is driven by 'pBlade <framename>/p<1..24> Warmed Event'
             event types.

             Severity: 5"
    --#TYPE         "pBlade Warmed"
    --#SUMMARY      "%s"
    --#ARGUMENTS    { 4 }
    --#SEVERITY     INFORMATIONAL
    --#TIMEINDEX    99
    --#STATE        OPERATIONAL
        ::=     438


lPanCreatedTrap TRAP-TYPE
    ENTERPRISE  egenera
    VARIABLES {
                lPanIndex,
                lPanName,
                egeneraTrapSeverity,
                egeneraTrapMessage
            }
    DESCRIPTION
            "The notification generated when an LPAN is created.

            This trap is driven by 'LPAN <lpanname> create event' event types.

            Severity: 5"
    --#TYPE         "LPAN Created"
    --#SUMMARY      "%s"
    --#ARGUMENTS    { 3 }
    --#SEVERITY     INFORMATIONAL
    --#TIMEINDEX    99

        ::=     501


lPanDeletedTrap TRAP-TYPE
    ENTERPRISE  egenera
    VARIABLES {
                lPanIndex,
                lPanName,
                egeneraTrapSeverity,
                egeneraTrapMessage
            }
    DESCRIPTION
            "The notification generated when an LPAN is deleted.

            This trap is driven by 'LPAN <lpanname> delete event' event types.

            Severity: 5"
    --#TYPE         "LPAN Deleted"
    --#SUMMARY      "%s"
    --#ARGUMENTS    { 3 }
    --#SEVERITY     INFORMATIONAL
    --#TIMEINDEX    99
    --#STATE        NONOPERATIONAL

        ::=     502


lPanBootedTrap TRAP-TYPE
    ENTERPRISE  egenera
    VARIABLES {
                lPanIndex,
                lPanName,
                egeneraTrapSeverity,
                egeneraTrapMessage
            }
    DESCRIPTION
            "The notification generated when an LPAN is booted.

            This trap is driven by 'LPAN <lpanname> boot event' event types.
            This trap is deprecate as of 4.0.0.

            Severity: 5"
    --#TYPE         "LPAN Booted"
    --#SUMMARY      "%s"
    --#ARGUMENTS    { 3 }
    --#SEVERITY     INFORMATIONAL
    --#TIMEINDEX    99
    --#STATE        OPERATIONAL

        ::=     503


lPanShutdownTrap TRAP-TYPE
    ENTERPRISE  egenera
    VARIABLES {
                lPanIndex,
                lPanName,
                egeneraTrapSeverity,
                egeneraTrapMessage
            }
    DESCRIPTION
            "The notification generated when an LPAN is shutdown.

            This trap is driven by 'LPAN <lpanname> shutdown event' event types.
            This trap is deprecate as of 4.0.0.

            Severity: 5"
    --#TYPE         "LPAN Shutdown"
    --#SUMMARY      "%s"
    --#ARGUMENTS    { 3 }
    --#SEVERITY     INFORMATIONAL
    --#TIMEINDEX    99
    --#STATE        NONOPERATIONAL

        ::=     504


lPanResourceUnavailableTrap TRAP-TYPE
    ENTERPRISE  egenera
    VARIABLES {
                lPanIndex,
                lPanName,
                egeneraTrapSeverity,
                egeneraTrapMessage
            }
    DESCRIPTION
            "The notification generated when a resource required by the
            LPAN is unavailable.

            This trap is driven by 'LPAN <lpanname> resource unavailable event'
            This trap is deprecate as of 4.0.0.
            event types.

            Severity: 3"
    --#TYPE         "LPAN Resource Unavailable"
    --#SUMMARY      "%s"
    --#ARGUMENTS    { 3 }
    --#SEVERITY     MINOR
    --#TIMEINDEX    99

        ::=     505


lPanModifyTrap TRAP-TYPE
    ENTERPRISE  egenera
    VARIABLES {
                lPanIndex,
                lPanName,
                egeneraTrapSeverity,
                egeneraTrapMessage
            }
    DESCRIPTION
            "The notification generated when when a logical PAN is
            modified.

            This trap is driven by 'LPAN <lpanname> Configuration Change
            Event' event types.

            Severity: 5"
    --#TYPE         "LPAN Modified"
    --#SUMMARY      "%s"
    --#ARGUMENTS    { 3 }
    --#SEVERITY     INFORMATIONAL
    --#TIMEINDEX    99
    --#STATE        OPERATIONAL

        ::=     506


lPanActivatedTrap TRAP-TYPE
    ENTERPRISE  egenera
    VARIABLES {
                lPanIndex,
                lPanName,
                egeneraTrapSeverity,
                egeneraTrapMessage
            }
    DESCRIPTION
            "The notification generated when when an LPAN is
            activated.

            This trap is driven by 'LPAN <lpanname> Activated Event'
            event types.

            Severity: 5"
    --#TYPE         "LPAN Activated"
    --#SUMMARY      "%s"
    --#ARGUMENTS    { 3 }
    --#SEVERITY     INFORMATIONAL
    --#TIMEINDEX    99
    --#STATE        OPERATIONAL

        ::=     507


lPanDeactivatedTrap TRAP-TYPE
    ENTERPRISE  egenera
    VARIABLES {
                lPanIndex,
                lPanName,
                egeneraTrapSeverity,
                egeneraTrapMessage
            }
    DESCRIPTION
            "The notification generated when when an LPAN is
            deactivated.

            This trap is driven by 'LPAN <lpanname> Deactivated Event'
            event types.

            Severity: 5"
    --#TYPE         "LPAN Deactivated"
    --#SUMMARY      "%s"
    --#ARGUMENTS    { 3 }
    --#SEVERITY     INFORMATIONAL
    --#TIMEINDEX    99
    --#STATE        OPERATIONAL

        ::=     508


lPanDeviceAvailableTrap TRAP-TYPE
    ENTERPRISE  egenera
    VARIABLES {
                lPanIndex,
                lPanName,
                egeneraTrapSeverity,
                egeneraTrapMessage
            }
    DESCRIPTION
            "The notification generated when when a device becomes available
            to an LPAN.

            This trap is driven by 'LPAN <lpanname> Device Available Event'
            event types.

            Severity: 5"
    --#TYPE         "LPAN Device Available"
    --#SUMMARY      "%s"
    --#ARGUMENTS    { 3 }
    --#SEVERITY     INFORMATIONAL
    --#TIMEINDEX    99
    --#STATE        OPERATIONAL

        ::=     509


lPanDeviceUnavailableTrap TRAP-TYPE
    ENTERPRISE  egenera
    VARIABLES {
                lPanIndex,
                lPanName,
                egeneraTrapSeverity,
                egeneraTrapMessage
            }
    DESCRIPTION
            "The notification generated when when a device becomes unavailable
            to an LPAN.

            This trap is driven by 'LPAN <lpanname> Device Unavailable Event'
            event types.

            Severity: 5"
    --#TYPE         "LPAN Device Unavailable"
    --#SUMMARY      "%s"
    --#ARGUMENTS    { 3 }
    --#SEVERITY     INFORMATIONAL
    --#TIMEINDEX    99
    --#STATE        OPERATIONAL

        ::=     510


lPanPBladeAvailableTrap TRAP-TYPE
    ENTERPRISE  egenera
    VARIABLES {
                lPanIndex,
                lPanName,
                pBladeIndex,
                pBladeFrameIndex,
                pBladeName,
                egeneraTrapSeverity,
                egeneraTrapMessage
            }
    DESCRIPTION
            "The notification generated when when a pBlade becomes available
            to an LPAN.

            This trap is driven by 'LPAN <lpanname> pBlade Available Event'
            event types.

            Severity: 5"
    --#TYPE         "LPAN pBlade Available"
    --#SUMMARY      "%s"
    --#ARGUMENTS    { 6 }
    --#SEVERITY     INFORMATIONAL
    --#TIMEINDEX    99
    --#STATE        OPERATIONAL

        ::=     511


lPanPBladeUnavailableTrap TRAP-TYPE
    ENTERPRISE  egenera
    VARIABLES {
                lPanIndex,
                lPanName,
                pBladeIndex,
                pBladeFrameIndex,
                pBladeName,
                egeneraTrapSeverity,
                egeneraTrapMessage
            }
    DESCRIPTION
            "The notification generated when when a pBlade becomes unavailable
            to an LPAN.

            This trap is driven by 'LPAN <lpanname> pBlade Unavailable Event'
            event types.

            Severity: 5"
    --#TYPE         "LPAN pBlade Unavailable"
    --#SUMMARY      "%s"
    --#ARGUMENTS    { 6 }
    --#SEVERITY     INFORMATIONAL
    --#TIMEINDEX    99
    --#STATE        OPERATIONAL

        ::=     512


lPanPBladeAllocatedTrap TRAP-TYPE
    ENTERPRISE  egenera
    VARIABLES {
                lPanIndex,
                lPanName,
                pBladeIndex,
                pBladeFrameIndex,
                pBladeName,
                egeneraTrapSeverity,
                egeneraTrapMessage
            }
    DESCRIPTION
            "The notification generated when when a pBlade is allocated
            to an LPAN.

            This trap is driven by 'pBlade <framename>/p<1..24> Allocated Event'
            event types.

            Severity: 5"
    --#TYPE         "LPAN pBlade Allocated"
    --#SUMMARY      "%s"
    --#ARGUMENTS    { 6 }
    --#SEVERITY     INFORMATIONAL
    --#TIMEINDEX    99
    --#STATE        OPERATIONAL

        ::=     513


lPanPBladeDeallocatedTrap TRAP-TYPE
    ENTERPRISE  egenera
    VARIABLES {
                lPanIndex,
                lPanName,
                pBladeIndex,
                pBladeFrameIndex,
                pBladeName,
                egeneraTrapSeverity,
                egeneraTrapMessage
            }
    DESCRIPTION
            "The notification generated when when a pBlade is deallocated
            from an LPAN.

            This trap is driven by 'pBlade <framename>/p<1..24> Deallocated Event'
            event types.

            Severity: 5"
    --#TYPE         "LPAN pBlade Deallocated"
    --#SUMMARY      "%s"
    --#ARGUMENTS    { 6 }
    --#SEVERITY     INFORMATIONAL
    --#TIMEINDEX    99
    --#STATE        OPERATIONAL

        ::=     514


lPanUserMonitorCreatedTrap TRAP-TYPE
    ENTERPRISE  egenera
    VARIABLES {
                lPanIndex,
                lPanName,
                egeneraTrapSeverity,
                egeneraTrapMessage
            }
    DESCRIPTION
            "The notification generated when when a User Defined Monitor is created
            in an LPAN.

            This trap is driven by 'LPAN <lpanname> User Monitor Create Event'
            event types.

            Severity: 5"
    --#TYPE         "LPAN User Monitor Created"
    --#SUMMARY      "%s"
    --#ARGUMENTS    { 3 }
    --#SEVERITY     INFORMATIONAL
    --#TIMEINDEX    99
    --#STATE        OPERATIONAL

        ::=     515


lPanUserMonitorModifiedTrap TRAP-TYPE
    ENTERPRISE  egenera
    VARIABLES {
                lPanIndex,
                lPanName,
                egeneraTrapSeverity,
                egeneraTrapMessage
            }
    DESCRIPTION
            "The notification generated when when a User Defined Monitor is modified
            in an LPAN.

            This trap is driven by 'LPAN <lpanname> User Monitor Modified Event'
            event types.

            Severity: 5"
    --#TYPE         "LPAN User Monitor Modified"
    --#SUMMARY      "%s"
    --#ARGUMENTS    { 3 }
    --#SEVERITY     INFORMATIONAL
    --#TIMEINDEX    99
    --#STATE        OPERATIONAL

        ::=     516


lPanUserMonitorDeletedTrap TRAP-TYPE
    ENTERPRISE  egenera
    VARIABLES {
                lPanIndex,
                lPanName,
                egeneraTrapSeverity,
                egeneraTrapMessage
            }
    DESCRIPTION
            "The notification generated when when a User Defined Monitor is deleted
            in an LPAN.

            This trap is driven by 'LPAN <lpanname> User Monitor Delete Event'
            event types.

            Severity: 5"
    --#TYPE         "LPAN User Monitor Deleted"
    --#SUMMARY      "%s"
    --#ARGUMENTS    { 3 }
    --#SEVERITY     INFORMATIONAL
    --#TIMEINDEX    99
    --#STATE        OPERATIONAL

        ::=     517


lPanOperationStartedTrap TRAP-TYPE
    ENTERPRISE  egenera
    VARIABLES {
                lPanIndex,
                lPanName,
                egeneraTrapSeverity,
                egeneraTrapMessage
            }
    DESCRIPTION
            "The notification generated when LPAN operation is initiated.

            This trap is driven by 'LPAN <lpanname> Operation Started Event'
            event types.

            Severity: 5"
    --#TYPE         "LPAN Operation Started"
    --#SUMMARY      "%s"
    --#ARGUMENTS    { 3 }
    --#SEVERITY     INFORMATIONAL
    --#TIMEINDEX    99
    --#STATE        OPERATIONAL

        ::=     518


lPanOperationCompletedTrap TRAP-TYPE
    ENTERPRISE  egenera
    VARIABLES {
                lPanIndex,
                lPanName,
                egeneraTrapSeverity,
                egeneraTrapMessage
            }
    DESCRIPTION
            "The notification generated when LPAN operation completes.

            This trap is driven by 'LPAN <lpanname> Operation Completed Event'
            event types.

            Severity: 5"
    --#TYPE         "LPAN Operation Completed"
    --#SUMMARY      "%s"
    --#ARGUMENTS    { 3 }
    --#SEVERITY     INFORMATIONAL
    --#TIMEINDEX    99
    --#STATE        OPERATIONAL

        ::=     519


lPanOperationAbortedTrap TRAP-TYPE
    ENTERPRISE  egenera
    VARIABLES {
                lPanIndex,
                lPanName,
                egeneraTrapSeverity,
                egeneraTrapMessage
            }
    DESCRIPTION
            "The notification generated when LPAN operation is aborted.

            This trap is driven by 'LPAN <lpanname> Operation Aborted Event'
            event types.

            Severity: 5"
    --#TYPE         "LPAN Operation Aborted"
    --#SUMMARY      "%s"
    --#ARGUMENTS    { 3 }
    --#SEVERITY     INFORMATIONAL
    --#TIMEINDEX    99
    --#STATE        OPERATIONAL

        ::=     520




-- pServer traps

pServerBootedTrap TRAP-TYPE
    ENTERPRISE  egenera
    VARIABLES {
                pServerIndex,
                pServerLPanIndex,
                pServerName,
                lPanName,
                egeneraTrapSeverity,
                egeneraTrapMessage
            }
    DESCRIPTION
            "The notification generated when a pServer is booted.

            This trap is driven by 'pServer <lpanname>/<pservername> boot
            event' event types.

            Severity: 5"
    --#TYPE         "pServer Booted"
    --#SUMMARY      "%s"
    --#ARGUMENTS    { 5 }
    --#SEVERITY     INFORMATIONAL
    --#TIMEINDEX    99
    --#STATE        OPERATIONAL


        ::=     601


pServerBootFailedTrap TRAP-TYPE
    ENTERPRISE  egenera
    VARIABLES {
                pServerIndex,
                pServerLPanIndex,
                pServerName,
                lPanName,
                egeneraTrapSeverity,
                egeneraTrapMessage
            }
    DESCRIPTION
            "The notification generated when a pServer fails to boot.

            This trap is driven by 'pServer <lpanname>/<pservername> Boot Failed
            Event' event types.

            Severity: 2"
    --#TYPE         "pServer Boot Failed"
    --#SUMMARY      "%s"
    --#ARGUMENTS    { 5 }
    --#SEVERITY     MAJOR
    --#TIMEINDEX    99

        ::=     603


pServerShutdownTrap TRAP-TYPE
    ENTERPRISE  egenera
    VARIABLES {
                pServerIndex,
                pServerLPanIndex,
                pServerName,
                lPanName,
                egeneraTrapSeverity,
                egeneraTrapMessage
            }
    DESCRIPTION
            "The notification generated when a pServer is shutdown.

            This trap is driven by 'pServer <lpanname>/<pservername> shutdown
            event' event types.

            Severity: 5"
    --#TYPE         "pServer Shut Down"
    --#SUMMARY      "%s"
    --#ARGUMENTS    { 5 }
    --#SEVERITY     INFORMATIONAL
    --#TIMEINDEX    99
    --#STATE        NONOPERATIONAL

        ::=     602


pServerShutdownFailedTrap TRAP-TYPE
    ENTERPRISE  egenera
    VARIABLES {
                pServerIndex,
                pServerLPanIndex,
                pServerName,
                lPanName,
                egeneraTrapSeverity,
                egeneraTrapMessage
            }
    DESCRIPTION
            "The notification sent when a pServer shutdown fails.

            This trap is driven by the 'pServer <lpanname>/<pservername>
            Shutdown Failed Event' event type.

            Severity: 3"
    --#TYPE         "pServer Shut Down Failed"
    --#SUMMARY      "%s"
    --#ARGUMENTS    { 5 }
    --#SEVERITY     MINOR
    --#TIMEINDEX    99

        ::=     623


pServerDebuggerEnterTrap TRAP-TYPE
    ENTERPRISE  egenera
    VARIABLES {
                pServerIndex,
                pServerLPanIndex,
                pServerName,
                lPanName,
                egeneraTrapSeverity,
                egeneraTrapMessage
            }
    DESCRIPTION
            "The notification generated when the debbugger has been invoked
            on the pServer.

            This trap is driven by 'blade.status.monitor.event' event types
            that describe a pBlade transition to the 'in kdb' state.

            This event type is not user visible, and will not appear in
            CLI or GUI event queries.  The trap exists to satisfy early
            requirements documents.

            Severity: 3"
    --#TYPE         "pServer Debugger Invoked"
    --#SUMMARY      "%s"
    --#ARGUMENTS    { 5 }
    --#SEVERITY     MINOR
    --#TIMEINDEX    99
    --#STATE        OPERATIONAL

        ::=     605


pServerDebuggerExitTrap TRAP-TYPE
    ENTERPRISE  egenera
    VARIABLES {
                pServerIndex,
                pServerLPanIndex,
                pServerName,
                lPanName,
                egeneraTrapSeverity,
                egeneraTrapMessage
            }
    DESCRIPTION
            "The notification generated when the debbugger has been exited
            on the pServer.

            This trap is driven by 'blade.status.monitor.event' event types
            that describe a pBlade transition from the 'in kdb' state.

            This event type is not user visible, and will not appear in
            CLI or GUI event queries.  The trap exists to satisfy early
            requirements documents.

            Severity: 3"
    --#TYPE         "pServer Debugger Exit"
    --#SUMMARY      "%s"
    --#ARGUMENTS    { 5 }
    --#SEVERITY     MINOR
    --#TIMEINDEX    99
    --#STATE        OPERATIONAL

        ::=     606


pServerResourceUnavailableTrap TRAP-TYPE
    ENTERPRISE  egenera
    VARIABLES {
                pServerIndex,
                pServerLPanIndex,
                pServerName,
                lPanName,
                egeneraTrapSeverity,
                egeneraTrapMessage
            }
    DESCRIPTION
            "This trap is deprecated as of PAN Manager release 4.0."
    --#TYPE         "pServer Resource Unavailable"
    --#SUMMARY      "%s"
    --#ARGUMENTS    { 5 }
    --#SEVERITY     MINOR
    --#TIMEINDEX    99

        ::=     607


pServerSystemThresholdHighTrap TRAP-TYPE
    ENTERPRISE  egenera
    VARIABLES {
                pServerIndex,
                pServerLPanIndex,
                pServerName,
                lPanName,
                egeneraTrapSeverity,
                egeneraTrapMessage
            }
    DESCRIPTION
            "The notification generated when a pServer system monitor has
            exceeded its high threshold, or returns below the high threshold.

            This trap is driven by 'pServer <lpanname>/<pservername> <monitorname>
            event' event types.  Note that a severity 3 event is emmitted when
            the threshold is crossed in the rising direction, while a severity
            5 event is emmitted when the monitored value returns below the threshold.
            Thus it is possible to recieve a severity 5 pServerSystemThresholdHighTrap
            with a message like:

            pcw/p2 pServer pcw/p2 5 Minute Load Average returned below 10.0 on average
            for 300 seconds, Current value = 4.79

            Severity: 3/5"
    --#TYPE         "pServer System Threshold High"
    --#SUMMARY      "%s"
    --#ARGUMENTS    { 5 }
    --#SEVERITY     MINOR
    --#TIMEINDEX    99
    --#STATE        OPERATIONAL

        ::=     608


pServerSystemThresholdlowTrap TRAP-TYPE
    ENTERPRISE  egenera
    VARIABLES {
                pServerIndex,
                pServerLPanIndex,
                pServerName,
                lPanName,
                egeneraTrapSeverity,
                egeneraTrapMessage
            }
    DESCRIPTION
            "The notification generated when a pServer system monitor has
            exceeded its low threshold, or returns above the low threshold.

            Currently, no software values are monitored for critically low
            values, and this trap is not emitted.  Because there is no
            driving event type, there is no severity."
    --#TYPE         "pServer System Threshold Low"
    --#SUMMARY      "%s"
    --#ARGUMENTS    { 5 }
    --#SEVERITY     MINOR
    --#TIMEINDEX    99

        ::=     609


pServerFailedTrap TRAP-TYPE
    ENTERPRISE  egenera
    VARIABLES {
                pServerIndex,
                pServerLPanIndex,
                pServerName,
                lPanName,
                egeneraTrapSeverity,
                egeneraTrapMessage
            }
    DESCRIPTION
            "The notification generated when a booted pServer fails.

            This trap is driven by 'pServer <lpanname>/<pservername> failed
            event' event types.

            Severity: 2"
    --#TYPE         "pServer Failed"
    --#SUMMARY      "%s"
    --#ARGUMENTS    { 5 }
    --#SEVERITY     MAJOR
    --#TIMEINDEX    99
    --#STATE        NONOPERATIONAL

        ::=     610


pServerRecoverTrap TRAP-TYPE
    ENTERPRISE  egenera
    VARIABLES {
                pServerIndex,
                pServerLPanIndex,
                pServerName,
                lPanName,
                egeneraTrapSeverity,
                egeneraTrapMessage
            }
    DESCRIPTION
            "The notification generated when a failed pServer has been
            successfully recovered, generally due to pBlade failover.

            This trap is driven by 'pServer <lpanname>/<pservername> recover
            event' event types.

            Severity: 5"
    --#TYPE         "pServer Recovered"
    --#SUMMARY      "%s"
    --#ARGUMENTS    { 5 }
    --#SEVERITY     INFORMATIONAL
    --#TIMEINDEX    99
    --#STATE        OPERATIONAL

        ::=     611


pServerBootingTrap TRAP-TYPE
    ENTERPRISE  egenera
    VARIABLES {
                pServerIndex,
                pServerLPanIndex,
                pServerName,
                lPanName,
                egeneraTrapSeverity,
                egeneraTrapMessage
            }
    DESCRIPTION
            "The notification generated when a pServer begins the process
            of booting.

            This trap is driven by 'pServer <lpanname>/<pservername> Booting
            Event' event types.

            Severity: 5"
    --#TYPE         "pServer Booting"
    --#SUMMARY      "%s"
    --#ARGUMENTS    { 5 }
    --#SEVERITY     INFORMATIONAL
    --#TIMEINDEX    99

        ::=     612


pServerCreatedTrap TRAP-TYPE
    ENTERPRISE  egenera
    VARIABLES {
                pServerIndex,
                pServerLPanIndex,
                pServerName,
                lPanName,
                egeneraTrapSeverity,
                egeneraTrapMessage
            }
    DESCRIPTION
            "The notification generated when a pServer is created.

            This trap is driven by 'pServer <lpanname>/<pservername> create
            event' event types.

            Severity: 5"
    --#TYPE         "pServer Created"
    --#SUMMARY      "%s"
    --#ARGUMENTS    { 5 }
    --#SEVERITY     INFORMATIONAL
    --#TIMEINDEX    99

        ::=     613


pServerDeletedTrap TRAP-TYPE
    ENTERPRISE  egenera
    VARIABLES {
                pServerIndex,
                pServerLPanIndex,
                pServerName,
                lPanName,
                egeneraTrapSeverity,
                egeneraTrapMessage
            }
    DESCRIPTION
            "The notification generated when a pServer is deleted.

            This trap is driven by 'pServer <lpanname>/<pservername> delete
            event' event types.

            Severity: 5"
    --#TYPE         "pServer Deleted"
    --#SUMMARY      "%s"
    --#ARGUMENTS    { 5 }
    --#SEVERITY     INFORMATIONAL
    --#TIMEINDEX    99
    --#STATE        NONOPERATIONAL

        ::=     614


pServerFailoverTrap TRAP-TYPE
    ENTERPRISE  egenera
    VARIABLES {
                pServerIndex,
                pServerLPanIndex,
                pServerName,
                lPanName,
                egeneraTrapSeverity,
                egeneraTrapMessage
            }
    DESCRIPTION
            "The notification generated when a pServer begins the process
            of failing over.

            This trap is driven by 'pServer <lpanname>/<pservername> Failover
            attempted Event' event types.

            Severity: 3"
    --#TYPE         "pServer Failing over"
    --#SUMMARY      "%s"
    --#ARGUMENTS    { 5 }
    --#SEVERITY     MINOR
    --#TIMEINDEX    99

        ::=     615


pServerModifiedTrap TRAP-TYPE
   ENTERPRISE  egenera
   VARIABLES {
               pServerIndex,
               pServerLPanIndex,
               pServerName,
               lPanName,
               egeneraTrapSeverity,
               egeneraTrapMessage
           }
   DESCRIPTION
           "The notification generated when a pServer configuration is
           modified.

           This trap is driven by 'pServer <lpanname>/<pservername> Configuration
           Change Event' event types.

           Severity: 5"
    --#TYPE         "pServer Modified"
    --#SUMMARY      "%s"
    --#ARGUMENTS    { 5 }
    --#SEVERITY     INFORMATIONAL
    --#TIMEINDEX    99
    --#STATE        OPERATIONAL

       ::=     616


pServerRebootingTrap TRAP-TYPE
    ENTERPRISE  egenera
    VARIABLES {
                pServerIndex,
                pServerLPanIndex,
                pServerName,
                lPanName,
                egeneraTrapSeverity,
                egeneraTrapMessage
            }
    DESCRIPTION
            "The notification generated when a pServer reboot has initiated.

            This trap is driven by 'pServer decker/ps1 Rebooting Event' event
            types.

            Severity: 5"
    --#TYPE         "pServer Rebooting"
    --#SUMMARY      "%s"
    --#ARGUMENTS    { 5 }
    --#SEVERITY     INFORMATIONAL
    --#TIMEINDEX    99

        ::=     617


pServerShuttingDownTrap TRAP-TYPE
    ENTERPRISE  egenera
    VARIABLES {
                pServerIndex,
                pServerLPanIndex,
                pServerName,
                lPanName,
                egeneraTrapSeverity,
                egeneraTrapMessage
            }
    DESCRIPTION
            "The notification generated when a pServer shutdown has initiated.

            This trap is driven by 'pServer <lpanname>/<pservername> Shutting
            Down Event' event types.

            Severity: 5"
    --#TYPE         "pServer Shutting Down"
    --#SUMMARY      "%s"
    --#ARGUMENTS    { 5 }
    --#SEVERITY     INFORMATIONAL
    --#TIMEINDEX    99

        ::=     618


pServerAgentArrivedTrap TRAP-TYPE
    ENTERPRISE  egenera
    VARIABLES {
                pServerIndex,
                pServerLPanIndex,
                pServerName,
                lPanName,
                egeneraTrapSeverity,
                egeneraTrapMessage
            }
    DESCRIPTION
            "The notification generated when a pServer agent has arrived.

            This trap is driven by 'pServer <lpanname>/<pservername> Agent
            Available Event' event types

            Severity: 5"
    --#TYPE         "pServer Agent Arrived"
    --#SUMMARY      "%s"
    --#ARGUMENTS    { 5 }
    --#SEVERITY     INFORMATIONAL
    --#TIMEINDEX    99
    --#STATE        OPERATIONAL

        ::=     619


pServerAgentDepartedTrap TRAP-TYPE
    ENTERPRISE  egenera
    VARIABLES {
                pServerIndex,
                pServerLPanIndex,
                pServerName,
                lPanName,
                egeneraTrapSeverity,
                egeneraTrapMessage
            }
    DESCRIPTION
            "The notification generated when a pServer agent has departed.

            This trap is driven by  'pServer <lpanname>/<pservername> PAN
            Agent Unavailable Event' event types.

            Severity: 3"
    --#TYPE         "pServer Agent Departed"
    --#SUMMARY      "%s"
    --#ARGUMENTS    { 5 }
    --#SEVERITY     MINOR
    --#TIMEINDEX    99

        ::=     620

pServerAgentGetDataFailedTrap TRAP-TYPE
    ENTERPRISE  egenera
    VARIABLES {
                pServerIndex,
                pServerLPanIndex,
                pServerName,
                lPanName,
                egeneraTrapSeverity,
                egeneraTrapMessage
            }
    DESCRIPTION
            "The notification generated when a pServer agent does not return
            requests for statistical data.

            This trap is driven by  'pServer <lpanname>/<pservername> PAN
            Agent ' event types.

            Severity: 3"
    --#TYPE         "pServer Agent Get Data"
    --#SUMMARY      "%s"
    --#ARGUMENTS    { 5 }
    --#SEVERITY     MINOR
    --#TIMEINDEX    99

        ::=     647


pServerPBladeAllocatedTrap TRAP-TYPE
    ENTERPRISE  egenera
    VARIABLES {
                pServerIndex,
                pServerLPanIndex,
                pServerName,
                lPanName,
                pBladeIndex,
                pBladeFrameIndex,
                pBladeName,
                egeneraTrapSeverity,
                egeneraTrapMessage
            }
    DESCRIPTION
            "The notification generated when when a pBlade is allocated
            to a pServer.

            This trap is driven by 'pBlade <framename>/p<1..24> Allocated Event'
            event types.

            Severity: 5"
    --#TYPE         "pServer pBlade Allocated"
    --#SUMMARY      "%s"
    --#ARGUMENTS    { 8 }
    --#SEVERITY     INFORMATIONAL
    --#TIMEINDEX    99
    --#STATE        OPERATIONAL

        ::=     624


pServerPBladeDeallocatedTrap TRAP-TYPE
    ENTERPRISE  egenera
    VARIABLES {
                pServerIndex,
                pServerLPanIndex,
                pServerName,
                lPanName,
                pBladeIndex,
                pBladeFrameIndex,
                pBladeName,
                egeneraTrapSeverity,
                egeneraTrapMessage
            }
    DESCRIPTION
            "The notification generated when when a pBlade is deallocated
            from a pServer.

            This trap is driven by 'pBlade <framename>/p<1..24> Deallocated Event'
            event types.

            Severity: 5"
    --#TYPE         "pServer pBlade Deallocated"
    --#SUMMARY      "%s"
    --#ARGUMENTS    { 8 }
    --#SEVERITY     INFORMATIONAL
    --#TIMEINDEX    99
    --#STATE        OPERATIONAL

        ::=     625


pServerPanicCycleTrap TRAP-TYPE
    ENTERPRISE  egenera
    VARIABLES {
                pServerIndex,
                pServerLPanIndex,
                pServerName,
                lPanName,
                egeneraTrapSeverity,
                egeneraTrapMessage
            }
    DESCRIPTION
            "The notification generated when when a pServer panic cycle
            is detected.

            This trap is driven by 'pServer <lpanname>/<pservername> Panic Cycle
            Event'

            Severity: 2"
    --#TYPE         "pServer Panic Cycle"
    --#SUMMARY      "%s"
    --#ARGUMENTS    { 5 }
    --#SEVERITY     MAJOR
    --#TIMEINDEX    99
    --#STATE        NONOPERATIONAL

        ::=     626


pServerUserMonitorTrap TRAP-TYPE
    ENTERPRISE  egenera
    VARIABLES {
                pServerIndex,
                pServerLPanIndex,
                pServerName,
                lPanName,
                monitorName,
                ruleName,
                egeneraTrapSeverity,
                egeneraTrapMessage
            }
    DESCRIPTION
            "The notification generated when a user defined monitor rule is matched.

            This trap is driven by 'pServer <lpanname>/<pservername> User Monitor Event:
            <lpanname>/<pservername>/<monitorname>

            Severity: 1"
    --#TYPE         "pServer User Monitor Rule Matched"
    --#SUMMARY      "%s"
    --#ARGUMENTS    { 7 }
    --#SEVERITY     CRITICAL
    --#TIMEINDEX    99

        ::=     627


pServerHardwareOnlineTrap TRAP-TYPE
    ENTERPRISE  egenera
    VARIABLES {
                pServerIndex,
                pServerLPanIndex,
                pServerName,
                lPanName,
                egeneraTrapSeverity,
                egeneraTrapMessage
            }
    DESCRIPTION
            "The notification generated when hardware for a pServer agent
            goes online.

            This trap is driven by  'pServer <lpanname>/<pservername> Hardware
            Online Event' event types.

            Severity: 5"
    --#TYPE         "pServer Hardware Online"
    --#SUMMARY      "%s"
    --#ARGUMENTS    { 5 }
    --#SEVERITY     INFORMATIONAL
    --#TIMEINDEX    99
    --#STATE        OPERATIONAL

        ::=     628


pServerHardwareOfflineTrap TRAP-TYPE
    ENTERPRISE  egenera
    VARIABLES {
                pServerIndex,
                pServerLPanIndex,
                pServerName,
                lPanName,
                egeneraTrapSeverity,
                egeneraTrapMessage
            }
    DESCRIPTION
            "The notification generated when hardware for a pServer agent
            goes offline.

            This trap is driven by  'pServer <lpanname>/<pservername> Hardware
            Offline Event' event types.

            Severity: 5"
    --#TYPE         "pServer Hardware Offline"
    --#SUMMARY      "%s"
    --#ARGUMENTS    { 5 }
    --#SEVERITY     INFORMATIONAL
    --#TIMEINDEX    99
    --#STATE        OPERATIONAL

        ::=     629


pServerRecoveredTrap TRAP-TYPE
    ENTERPRISE  egenera
    VARIABLES {
                pServerIndex,
                pServerLPanIndex,
                pServerName,
                lPanName,
                egeneraTrapSeverity,
                egeneraTrapMessage
            }
    DESCRIPTION
            "The notification generated when pServer recovers from a failure.

            This trap is driven by  'pServer <lpanname>/<pservername> Recovered
            Event' event types.

            Severity: 5"
    --#TYPE         "pServer Recovered"
    --#SUMMARY      "%s"
    --#ARGUMENTS    { 5 }
    --#SEVERITY     INFORMATIONAL
    --#TIMEINDEX    99
    --#STATE        OPERATIONAL

        ::=     630


pServerDiskAvailableTrap TRAP-TYPE
    ENTERPRISE  egenera
    VARIABLES {
                pServerIndex,
                pServerLPanIndex,
                pServerName,
                lPanName,
                diskId,
                egeneraTrapSeverity,
                egeneraTrapMessage
            }
    DESCRIPTION
            "The notification generated when a disk on a pServer becomes available.

            This trap is driven by  'pServer <lpanname>/<pservername> Disk
            Available Event' event types.

            Severity: 5"
    --#TYPE         "pServer Disk Available"
    --#SUMMARY      "%s"
    --#ARGUMENTS    { 6 }
    --#SEVERITY     INFORMATIONAL
    --#TIMEINDEX    99
    --#STATE        OPERATIONAL

        ::=     631


pServerDiskUnavailableTrap TRAP-TYPE
    ENTERPRISE  egenera
    VARIABLES {
                pServerIndex,
                pServerLPanIndex,
                pServerName,
                lPanName,
                diskId,
                egeneraTrapSeverity,
                egeneraTrapMessage
            }
    DESCRIPTION
            "The notification generated when a disk on a pServer is unavailable
            at boot time.

            This trap is driven by  'pServer <lpanname>/<pservername> Disk
            Unavailable Event' event types.

            Severity: 3"
    --#TYPE         "pServer Disk Unavailable"
    --#SUMMARY      "%s"
    --#ARGUMENTS    { 6 }
    --#SEVERITY     MINOR
    --#TIMEINDEX    99
    --#STATE        OPERATIONAL

        ::=     632


pServerOperationStartedTrap TRAP-TYPE
    ENTERPRISE  egenera
    VARIABLES {
                pServerIndex,
                pServerLPanIndex,
                pServerName,
                lPanName,
                egeneraTrapSeverity,
                egeneraTrapMessage
            }
    DESCRIPTION
            "The notification generated when a pServer operation has been
            invoked.

            This trap is driven by  'pServer <lpanname>/<pservername> Operation
            Started' event types.

            Severity: 5"
    --#TYPE         "pServer Operation Started"
    --#SUMMARY      "%s"
    --#ARGUMENTS    { 5 }
    --#SEVERITY     INFORMATIONAL
    --#TIMEINDEX    99
    --#STATE        OPERATIONAL

        ::=     633


pServerPBladeAvailableTrap TRAP-TYPE
    ENTERPRISE  egenera
    VARIABLES {
                pServerIndex,
                pServerLPanIndex,
                pServerName,
                lPanName,
                egeneraTrapSeverity,
                egeneraTrapMessage
            }
    DESCRIPTION
            "The notification generated when a pServer pBlade becomes available.

            This trap is driven by  'pServer <lpanname>/<pservername> pBlade
            Available Event' event types.

            Severity: 5"
    --#TYPE         "pServer pBlade Available"
    --#SUMMARY      "%s"
    --#ARGUMENTS    { 5 }
    --#SEVERITY     INFORMATIONAL
    --#TIMEINDEX    99
    --#STATE        OPERATIONAL

        ::=     634


pServerMigratingTrap TRAP-TYPE
    ENTERPRISE  egenera
    VARIABLES {
                pServerIndex,
                pServerLPanIndex,
                pServerName,
                lPanName,
                egeneraTrapSeverity,
                egeneraTrapMessage
            }
    DESCRIPTION
            "The notification generated when a pServer starts to migrate.

            This trap is driven by  'pServer <lpanname>/<pservername> Migrating
            Event' event types.

            Severity: 5"
    --#TYPE         "pServer Migrating"
    --#SUMMARY      "%s"
    --#ARGUMENTS    { 5 }
    --#SEVERITY     INFORMATIONAL
    --#TIMEINDEX    99
    --#STATE        OPERATIONAL

        ::=     635


pServerMigratedTrap TRAP-TYPE
    ENTERPRISE  egenera
    VARIABLES {
                pServerIndex,
                pServerLPanIndex,
                pServerName,
                lPanName,
                egeneraTrapSeverity,
                egeneraTrapMessage
            }
    DESCRIPTION
            "The notification generated when a pServer is migrated.

            This trap is driven by  'pServer <lpanname>/<pservername> Migrate
            Succeeded Event' event types.

            Severity: 5"
    --#TYPE         "pServer Migrated"
    --#SUMMARY      "%s"
    --#ARGUMENTS    { 5 }
    --#SEVERITY     INFORMATIONAL
    --#TIMEINDEX    99
    --#STATE        OPERATIONAL

        ::=     636


pServerMigrateFailedTrap TRAP-TYPE
    ENTERPRISE  egenera
    VARIABLES {
                pServerIndex,
                pServerLPanIndex,
                pServerName,
                lPanName,
                egeneraTrapSeverity,
                egeneraTrapMessage
            }
    DESCRIPTION
            "The notification generated when a pServer fails to migrate.

            This trap is driven by  'pServer <lpanname>/<pservername> Migrate
            Failed Event' event types."
    --#TYPE         "pServer Migrated Failed"
    --#SUMMARY      "%s"
    --#ARGUMENTS    { 5 }
    --#SEVERITY     MINOR
    --#TIMEINDEX    99

        ::=     637


pServerSuspendingTrap TRAP-TYPE
    ENTERPRISE  egenera
    VARIABLES {
                pServerIndex,
                pServerLPanIndex,
                pServerName,
                lPanName,
                egeneraTrapSeverity,
                egeneraTrapMessage
            }
    DESCRIPTION
            "The notification generated when a pServer starts to  suspend.

            This trap is driven by  'pServer <lpanname>/<pservername> Suspending
            Event' event types.

            Severity: 5"
    --#TYPE         "pServer Suspending"
    --#SUMMARY      "%s"
    --#ARGUMENTS    { 5 }
    --#SEVERITY     INFORMATIONAL
    --#TIMEINDEX    99
    --#STATE        OPERATIONAL

        ::=     638


pServerSuspendedTrap TRAP-TYPE
    ENTERPRISE  egenera
    VARIABLES {
                pServerIndex,
                pServerLPanIndex,
                pServerName,
                lPanName,
                egeneraTrapSeverity,
                egeneraTrapMessage
            }
    DESCRIPTION
            "The notification generated when a pServer suspend is completed.

            This trap is driven by  'pServer <lpanname>/<pservername> Suspend
            Completed Event' event types.

            Severity: 5"
    --#TYPE         "pServer Suspended"
    --#SUMMARY      "%s"
    --#ARGUMENTS    { 5 }
    --#SEVERITY     INFORMATIONAL
    --#TIMEINDEX    99
    --#STATE        OPERATIONAL

        ::=     639


pServerSuspendFailedTrap TRAP-TYPE
    ENTERPRISE  egenera
    VARIABLES {
                pServerIndex,
                pServerLPanIndex,
                pServerName,
                lPanName,
                egeneraTrapSeverity,
                egeneraTrapMessage
            }
    DESCRIPTION
            "The notification generated when a pServer fails to suspend.

            This trap is driven by  'pServer <lpanname>/<pservername> Suspend
            Failed Event' event types."
    --#TYPE         "pServer Suspend Failed"
    --#SUMMARY      "%s"
    --#ARGUMENTS    { 5 }
    --#SEVERITY     MINOR
    --#TIMEINDEX    99

        ::=     640


pServerResumingTrap TRAP-TYPE
    ENTERPRISE  egenera
    VARIABLES {
                pServerIndex,
                pServerLPanIndex,
                pServerName,
                lPanName,
                egeneraTrapSeverity,
                egeneraTrapMessage
            }
    DESCRIPTION
            "The notification generated when a pServer starts to resume.

            This trap is driven by  'pServer <lpanname>/<pservername> Resume
            Started Event' event types."
    --#TYPE         "pServer Resuming"
    --#SUMMARY      "%s"
    --#ARGUMENTS    { 5 }
    --#SEVERITY     INFORMATIONAL
    --#TIMEINDEX    99
    --#STATE        OPERATIONAL

        ::=     641


pServerResumedTrap TRAP-TYPE
    ENTERPRISE  egenera
    VARIABLES {
                pServerIndex,
                pServerLPanIndex,
                pServerName,
                lPanName,
                egeneraTrapSeverity,
                egeneraTrapMessage
            }
    DESCRIPTION
            "The notification generated when a pServer resume is completed.

            This trap is driven by  'pServer <lpanname>/<pservername> Resume
            Completed Event' event types."
    --#TYPE         "pServer Resumed"
    --#SUMMARY      "%s"
    --#ARGUMENTS    { 5 }
    --#SEVERITY     INFORMATIONAL
    --#TIMEINDEX    99
    --#STATE        OPERATIONAL

        ::=     642


pServerResumeFailedTrap TRAP-TYPE
    ENTERPRISE  egenera
    VARIABLES {
                pServerIndex,
                pServerLPanIndex,
                pServerName,
                lPanName,
                egeneraTrapSeverity,
                egeneraTrapMessage
            }
    DESCRIPTION
            "The notification generated when a pServer fails to resume.

            This trap is driven by  'pServer <lpanname>/<pservername> Resume
            Failed Event' event types."
    --#TYPE         "pServer Resume Failed"
    --#SUMMARY      "%s"
    --#ARGUMENTS    { 5 }
    --#SEVERITY     MINOR
    --#TIMEINDEX    99

        ::=     643

pServerUserMonitorFailedTrap TRAP-TYPE
    ENTERPRISE  egenera
    VARIABLES {
                pServerIndex,
                pServerLPanIndex,
                pServerName,
                lPanName,
                monitorName,
                ruleName,
                egeneraTrapSeverity,
                egeneraTrapMessage
            }
    DESCRIPTION
            "The notification generated when a user defined monitor is failed.

            This trap is driven by 'pServer <lpanname>/<pservername> User Monitor Failed Event:
            <lpanname>/<pservername>/<monitorname>

            Severity: 1"

        ::=     644

pServerVBladeAllocatedTrap TRAP-TYPE
    ENTERPRISE  egenera
    VARIABLES {
                pServerIndex,
                pServerLPanIndex,
                pServerName,
                lPanName,
                vBladeIndex,
                vBladePBladeIndex,
                vBladeFrameIndex,
                vBladeName,
                egeneraTrapSeverity,
                egeneraTrapMessage
            }
    DESCRIPTION
            "The notification generated when when a vBlade is allocated
            to a pServer.

            This trap is driven by 'vBlade <framename>/p<1..24-1..n> Allocated Event'
            event types.

            Severity: 5"
    --#TYPE         "pServer pBlade Allocated"
    --#SUMMARY      "%s"
    --#ARGUMENTS    { 8 }
    --#SEVERITY     INFORMATIONAL
    --#TIMEINDEX    99
    --#STATE        OPERATIONAL

        ::=     645


pServerVBladeDeallocatedTrap TRAP-TYPE
    ENTERPRISE  egenera
    VARIABLES {
                pServerIndex,
                pServerLPanIndex,
                pServerName,
                lPanName,
                vBladeIndex,
                vBladePBladeIndex,
                vBladeFrameIndex,
                vBladeName,
                egeneraTrapSeverity,
                egeneraTrapMessage
            }
    DESCRIPTION
            "The notification generated when when a pBlade is deallocated
            from a pServer.

            This trap is driven by 'vBlade <framename>/p<1..24-1..n> Deallocated Event'
            event types.

            Severity: 5"
    --#TYPE         "pServer pBlade Allocated"
    --#SUMMARY      "%s"
    --#ARGUMENTS    { 8 }
    --#SEVERITY     INFORMATIONAL
    --#TIMEINDEX    99
    --#STATE        OPERATIONAL

        ::=     646

-- The PAN Manager provides functionality to monitor messages from syslogd.
-- When properly configured and enabled, EES defines a set of strings to
-- search syslog messages for.  When encountered, these syslog messages are
-- promoted to Egenera PAN Manager events.  The search strings and event
-- severities are defined by EES.  There are 10 event types reserved for
-- cBlade syslog messages, and 10 event types reserved for pServer syslog
-- messages.  Contact EES for more information.

pServerSyslogEventTrap TRAP-TYPE
    ENTERPRISE  egenera
    VARIABLES {
                pServerIndex,
                pServerLPanIndex,
                pServerName,
                lPanName,
                egeneraTrapSeverity,
                egeneraTrapMessage
            }
    DESCRIPTION
            "The notification sent when a syslog target string is emmited
            from the system logger.

            This trap is driven by 'pServer <lpanname>/<pservername> Custom
            Linux System Message <1..10>' event types.  See 'eventtype -l' for
            more information.

            There are 10 pServer syslog event types.  This trap can be
            enabled/disabled for each syslog event type independently.

            Severity: (configurable by EES, generally 1, 2 or 3)"
    --#TYPE         "pServer Syslog Event"
    --#SUMMARY      "%s"
    --#ARGUMENTS    { 5 }
    --#SEVERITY     CRITICAL
    --#TIMEINDEX    99

        ::=     604


pServerSyslogDroppedTrap TRAP-TYPE
    ENTERPRISE  egenera
    VARIABLES {
                pServerIndex,
                pServerLPanIndex,
                pServerName,
                lPanName,
                egeneraTrapSeverity,
                egeneraTrapMessage
            }
    DESCRIPTION
            "The notification sent when a syslog target string message
            is dropped due to rate limiting.

            This trap is driven by 'pServer <lpanname>/<pservername> Custom Linux
            System Messages dropped' event types.  System message events are
            subject to rate limiting.  By default, no more than 5 messages can be
            emitted during a 5 minute period.  If more than 5 target strings are
            encountered, events will only be created for the first 5 messages,
            subsequent messages will be dropped.  At the end of the 5 minute
            period, a 'Messages Dropped' event will be emmitted to indicate
            the number of dropped messages during the 5 minute period.
            Contact EES for more information.

            Severity: 3"
    --#TYPE         "pServer Syslog Dropped"
    --#SUMMARY      "%s"
    --#ARGUMENTS    { 5 }
    --#SEVERITY     MINOR
    --#TIMEINDEX    99

        ::=     621


pServerSyslogPollingStoppedTrap TRAP-TYPE
    ENTERPRISE  egenera
    VARIABLES {
                pServerIndex,
                pServerLPanIndex,
                pServerName,
                lPanName,
                egeneraTrapSeverity,
                egeneraTrapMessage
            }
    DESCRIPTION
            "The notification sent when a syslog polling has stopped
            due to rate limiting.

            This trap is driven by the 'pServer <lpanname>/<pservername> Custom
            Linux System Messages polling stopped' event type.  System message
            events are subject to rate limiting.  By default, no more than 5
            messages can be emitted during a 5 minute period.  If more than 5
            target strings are encountered, events will only be created for the
            first 5 messages, subsequent messages will be dropped.  If messages
            are dropped for 5 consecutive 5 minute periods, syslog message
            polling will be disabled on that cBlade.  Contact EES for more
            information.

            Severity: 2"
    --#TYPE         "pServer Syslog Polling Stopped"
    --#SUMMARY      "%s"
    --#ARGUMENTS    { 5 }
    --#SEVERITY     MAJOR
    --#TIMEINDEX    99

        ::=     622


failoverPoolExaustedTrap TRAP-TYPE
    ENTERPRISE  egenera
    VARIABLES {
                bladeFrameIndex,
                bladeFrameName,
                egeneraTrapSeverity,
                egeneraTrapMessage
            }
    DESCRIPTION
            "The notification generated when a failover blade pool is
            exhausted.

            This trap is deprecated because there is no underlying event
            to drive the trap.  The trap definition exists to satisfy early
            requirements documents."
    --#TYPE         "failover Poll Exausted"
    --#SUMMARY      "%s"
    --#ARGUMENTS    { 3 }
    --#SEVERITY     INFORMATIONAL
    --#TIMEINDEX    99

        ::=     701


-- application traps are grouped by logical order.
-- the lexicographical ordering does not group associated
-- traps together due to deprecation of previous traps
-- and inclusion of new traps

-- app create/modify/delete
applicationCreatedTrap TRAP-TYPE
    ENTERPRISE  egenera
    VARIABLES {
                applicationIndex,
                applicationLPanIndex,
                applicationName,
                egeneraTrapSeverity,
                egeneraTrapMessage
            }
    DESCRIPTION
            "The notification generated when an application has been
            created.

            This trap is driven by 'LPAN <lpanname> application Create
            Event' event types.

            Severity: 5"
    --#TYPE         "Application Created"
    --#SUMMARY      "%s"
    --#ARGUMENTS    { 4 }
    --#SEVERITY     INFORMATIONAL
    --#TIMEINDEX    99

        ::=     817


applicationModifyTrap TRAP-TYPE
    ENTERPRISE  egenera
    VARIABLES {
                applicationIndex,
                applicationLPanIndex,
                applicationName,
                egeneraTrapSeverity,
                egeneraTrapMessage
            }
    DESCRIPTION
            "The notification generated when an application is modified.

            This trap is driven by 'application <lpanname>/<appname> Changed
            Event' event types.

            Severity: 5"
    --#TYPE         "Application Modified"
    --#SUMMARY      "%s"
    --#ARGUMENTS    { 4 }
    --#SEVERITY     INFORMATIONAL
    --#TIMEINDEX    99
    --#STATE        OPERATIONAL

        ::=     818


applicationDeletedTrap TRAP-TYPE
    ENTERPRISE  egenera
    VARIABLES {
                applicationIndex,
                applicationLPanIndex,
                applicationName,
                egeneraTrapSeverity,
                egeneraTrapMessage
            }
    DESCRIPTION
            "The notification generated when an application has been
            deleted.

            This trap is driven by 'LPAN <lpanname> application Delete
            Event' event types.

            Severity: 5"
    --#TYPE         "Application Deleted"
    --#SUMMARY      "%s"
    --#ARGUMENTS    { 4 }
    --#SEVERITY     INFORMATIONAL
    --#TIMEINDEX    99
    --#STATE        NONOPERATIONAL


        ::=     819


-- app starting/started/start failed
applicationStartingTrap TRAP-TYPE
    ENTERPRISE  egenera
    VARIABLES {
                applicationIndex,
                applicationLPanIndex,
                applicationName,
                egeneraTrapSeverity,
                egeneraTrapMessage
            }
    DESCRIPTION
            "The notification generated when an application start has been
            initiated.

            This trap is driven by 'application <lpanname>/<appname> Start
            Started Event' event types.

            Severity: 5"
    --#TYPE         "Application Starting"
    --#SUMMARY      "%s"
    --#ARGUMENTS    { 4 }
    --#SEVERITY     INFORMATIONAL
    --#TIMEINDEX    99

        ::=     820



applicationStartedTrap TRAP-TYPE
    ENTERPRISE  egenera
    VARIABLES {
                applicationIndex,
                applicationLPanIndex,
                applicationName,
                egeneraTrapSeverity,
                egeneraTrapMessage
            }
    DESCRIPTION
            "The notification generated when an application has started
            successfully.

            This trap is driven by 'application <lpanname>/<appname> Start Completed
            Event ' event types.

            Severity: 5"
    --#TYPE         "Application Started"
    --#SUMMARY      "%s"
    --#ARGUMENTS    { 4 }
    --#SEVERITY     INFORMATIONAL
    --#TIMEINDEX    99
    --#STATE        OPERATIONAL

        ::=     801


applicationStartFailedTrap TRAP-TYPE
    ENTERPRISE  egenera
    VARIABLES {
                applicationIndex,
                applicationLPanIndex,
                applicationName,
                egeneraTrapSeverity,
                egeneraTrapMessage
            }
    DESCRIPTION
            "The notification generated when an application start attempt
            has failed.

            This trap is driven by 'application <lpanname>/<appname> Start Failed
            Event' event types.

            Severity: 2"
    --#TYPE         "Application Start Failed"
    --#SUMMARY      "%s"
    --#ARGUMENTS    { 4 }
    --#SEVERITY     MAJOR
    --#TIMEINDEX    99
    --#STATE        NONOPERATIONAL

        ::=     821

-- app stopping/stopped/stop failed
applicationStoppingTrap TRAP-TYPE
    ENTERPRISE  egenera
    VARIABLES {
                applicationIndex,
                applicationLPanIndex,
                applicationName,
                egeneraTrapSeverity,
                egeneraTrapMessage
            }
    DESCRIPTION
            "The notification generated when an application stop has been
            initiated.

            This trap is driven by 'application <lpanname>/<appname> Stop
            Started Event' event types.

            Severity: 5"
    --#TYPE         "Application Stopping"
    --#SUMMARY      "%s"
    --#ARGUMENTS    { 4 }
    --#SEVERITY     INFORMATIONAL
    --#TIMEINDEX    99

        ::=     822

applicationStoppedTrap TRAP-TYPE
    ENTERPRISE  egenera
    VARIABLES {
                applicationIndex,
                applicationLPanIndex,
                applicationName,
                egeneraTrapSeverity,
                egeneraTrapMessage
            }
    DESCRIPTION
            "The notification generated when an application has been
            successfully stopped.

            This trap is driven by 'application <lpanname>/<appname> Stop
            Completed Event' event types.

            Severity: 5"
    --#TYPE         "Application Stopped"
    --#SUMMARY      "%s"
    --#ARGUMENTS    { 4 }
    --#SEVERITY     INFORMATIONAL
    --#TIMEINDEX    99
    --#STATE        NONOPERATIONAL

        ::=     802


applicationStopFailedTrap TRAP-TYPE
    ENTERPRISE  egenera
    VARIABLES {
                applicationIndex,
                applicationLPanIndex,
                applicationName,
                egeneraTrapSeverity,
                egeneraTrapMessage
            }
    DESCRIPTION
            "The notification generated when an application has failed
            to stop.

            This trap is driven by 'application <lpanname>/<appname> Stop
            Failed Event' event types.

            Severity: 2"
    --#TYPE         "Application Stop Failed"
    --#SUMMARY      "%s"
    --#ARGUMENTS    { 4 }
    --#SEVERITY     MAJOR
    --#TIMEINDEX    99

        ::=     823


-- app moving/moved/move failed
applicationMovingTrap TRAP-TYPE
    ENTERPRISE  egenera
    VARIABLES {
                applicationIndex,
                applicationLPanIndex,
                applicationName,
                egeneraTrapSeverity,
                egeneraTrapMessage
            }
    DESCRIPTION
            "The notification generated when an application move
            has been initiated.

            This trap is driven by 'application <lpanname>/<appname> Move
            Started Event' event types.

            Severity: 5"
    --#TYPE         "Application Moving"
    --#SUMMARY      "%s"
    --#ARGUMENTS    { 4 }
    --#SEVERITY     INFORMATIONAL
    --#TIMEINDEX    99

        ::=     824


applicationMovedTrap TRAP-TYPE
    ENTERPRISE  egenera
    VARIABLES {
                applicationIndex,
                applicationLPanIndex,
                applicationName,
                egeneraTrapSeverity,
                egeneraTrapMessage
            }
    DESCRIPTION
            "The notification generated when an application move
            has successfully completed.

            This trap is driven by 'application <lpanname>/<appname> Move
            Completed Event' event types.

            Severity: 5"
    --#TYPE         "Application Moved"
    --#SUMMARY      "%s"
    --#ARGUMENTS    { 4 }
    --#SEVERITY     INFORMATIONAL
    --#TIMEINDEX    99
    --#STATE        OPERATIONAL

        ::=     825


applicationMoveFailedTrap TRAP-TYPE
    ENTERPRISE  egenera
    VARIABLES {
                applicationIndex,
                applicationLPanIndex,
                applicationName,
                egeneraTrapSeverity,
                egeneraTrapMessage
            }
    DESCRIPTION
            "The notification generated when an application move
            has failed.

            This trap is driven by 'application <lpanname>/<appname> Move
            Failed Event' event types.

            Severity: 5"
    --#TYPE         "Application Move Failed"
    --#SUMMARY      "%s"
    --#ARGUMENTS    { 4 }
    --#SEVERITY     INFORMATIONAL
    --#TIMEINDEX    99

        ::=     826


-- app failing over/failed over/failover failed
applicationFailingOverTrap TRAP-TYPE
    ENTERPRISE  egenera
    VARIABLES {
                applicationIndex,
                applicationLPanIndex,
                applicationName,
                egeneraTrapSeverity,
                egeneraTrapMessage
            }
    DESCRIPTION
            "The notification generated when an application failover
            has been initiated.

            This trap is driven by 'application <lpanname>/<appname> Failover
            Started Event' event types.

            Severity: 3"
    --#TYPE         "Application Failing Over"
    --#SUMMARY      "%s"
    --#ARGUMENTS    { 4 }
    --#SEVERITY     MINOR
    --#TIMEINDEX    99

        ::=     827


applicationFailedOverTrap TRAP-TYPE
    ENTERPRISE  egenera
    VARIABLES {
                applicationIndex,
                applicationLPanIndex,
                applicationName,
                egeneraTrapSeverity,
                egeneraTrapMessage
            }
    DESCRIPTION
            "The notification generated when an application failover
            has successfully completed.

            This trap is driven by 'application <lpanname>/<appname> Failover
            Completed Event' event types.

            Severity: 5"
    --#TYPE         "Application Failed Over"
    --#SUMMARY      "%s"
    --#ARGUMENTS    { 4 }
    --#SEVERITY     INFORMATIONAL
    --#TIMEINDEX    99
    --#STATE        OPERATIONAL

        ::=     828


applicationFailoverFailedTrap TRAP-TYPE
    ENTERPRISE  egenera
    VARIABLES {
                applicationIndex,
                applicationLPanIndex,
                applicationName,
                egeneraTrapSeverity,
                egeneraTrapMessage
            }
    DESCRIPTION
            "The notification generated when an application failover
            has failed.

            This trap is driven by 'application <lpanname>/<appname> Failover
            Failed Event' event types.

            Severity: 2"
    --#TYPE         "Application Failover Failed"
    --#SUMMARY      "%s"
    --#ARGUMENTS    { 4 }
    --#SEVERITY     MAJOR
    --#TIMEINDEX    99
    --#STATE        NONOPERATIONAL

        ::=     829


-- health monitor induced actions
applicationFailureDetectedTrap TRAP-TYPE
    ENTERPRISE  egenera
    VARIABLES {
                applicationIndex,
                applicationLPanIndex,
                applicationName,
                egeneraTrapSeverity,
                egeneraTrapMessage
            }
    DESCRIPTION
            "The notification generated when an application health monitor
            has detected an application failure.  These failures are counted,
            and compared to 'restart after', 'failover after', and 'giveup
            after' thresholds of the health monitor to trigger application
            actions.

            This trap is driven by 'application <lpanname>/<appname> Health
            Monitor Detected Failure Event' event types.

            Severity: 4"
    --#TYPE         "Application Failure Detected"
    --#SUMMARY      "%s"
    --#ARGUMENTS    { 4 }
    --#SEVERITY     INFORMATIONAL
    --#TIMEINDEX    99

        ::=     830

applicationRestartedTrap TRAP-TYPE
    ENTERPRISE  egenera
    VARIABLES {
                applicationIndex,
                applicationLPanIndex,
                applicationName,
                egeneraTrapSeverity,
                egeneraTrapMessage
            }
    DESCRIPTION
            "The notification generated when an application failures have
            been detected by the health monitor, and the 'restart' threshold
            has been reached or exceeded.  This results in an attempt to
            restart the application, for which further traps will be generated:

                applicationStartingTrap
                applicationStartedTrap
                applicationStartFailedTrap

            This trap is driven by 'application <lpanname>/<appname> Health
            Monitor Restart Event' event types.

            Severity: 3"
    --#TYPE         "Application Restarted"
    --#SUMMARY      "%s"
    --#ARGUMENTS    { 4 }
    --#SEVERITY     MINOR
    --#TIMEINDEX    99

        ::=     803


applicationFailoverTrap TRAP-TYPE
    ENTERPRISE  egenera
    VARIABLES {
                applicationIndex,
                applicationLPanIndex,
                applicationName,
                egeneraTrapSeverity,
                egeneraTrapMessage
            }
    DESCRIPTION
            "The notification generated when an application failures have
            been detected by the health monitor, and the 'failover' threshold
            has been reached or exceeded.  This results in an attempt to
            failover the application, for which further traps will be generated:

                applicationMovingTrap
                applicationMovedTrap
                applicationMoveFailedTrap

            This trap is driven by 'application <lpanname>/<appname> Health
            Monitor Failover Event' event types.

            Severity: 3"
    --#TYPE         "Application Failover"
    --#SUMMARY      "%s"
    --#ARGUMENTS    { 4 }
    --#SEVERITY     MINOR
    --#TIMEINDEX    99

        ::=     804


applicationGiveupTrap TRAP-TYPE
    ENTERPRISE  egenera
    VARIABLES {
                applicationIndex,
                applicationLPanIndex,
                applicationName,
                egeneraTrapSeverity,
                egeneraTrapMessage
            }
    DESCRIPTION
            "The notification generated when an application failures have
            been detected by the health monitor, and the 'giveup' threshold
            has been reached or exceeded.  This results in the PAN Manager
            stop, for which further traps will be generated:

                applicationStoppingTrap
                applicationStoppedTrap
                applicationStopFailed

            This trap is driven by 'application <lpanname>/<appname> Health
            Monitor GiveUp Event' event types.

            Severity: 2"
    --#TYPE         "Application Giveup"
    --#SUMMARY      "%s"
    --#ARGUMENTS    { 4 }
    --#SEVERITY     MAJOR
    --#TIMEINDEX    99
    --#STATE        NONOPERATIONAL

        ::=     805


applicationMonitorFailedTrap TRAP-TYPE
    ENTERPRISE  egenera
    VARIABLES {
                applicationIndex,
                applicationLPanIndex,
                applicationName,
                egeneraTrapSeverity,
                egeneraTrapMessage
            }
    DESCRIPTION
            "The notification generated when an application monitor failed,
            generally due to a missing PAN Agent.

            This trap is driven by 'application <lpanname>/<appname> Health
            Monitor Failed Event' event types.

            Severity: 3"
    --#TYPE         "Application Monitor Failed"
    --#SUMMARY      "%s"
    --#ARGUMENTS    { 4 }
    --#SEVERITY     MINOR
    --#TIMEINDEX    99


        ::=     814


applicationMonitorRecoveredTrap TRAP-TYPE
    ENTERPRISE  egenera
    VARIABLES {
                applicationIndex,
                applicationLPanIndex,
                applicationName,
                egeneraTrapSeverity,
                egeneraTrapMessage
            }
    DESCRIPTION
            "The notification generated when an application monitor recovers,
            generally due to a restored PAN Agent.

            This trap is driven by 'application <lpanname>/<appname> Health Monitor
            Recovered Event' event types.

            Severity: 5"
    --#TYPE         "Application Monitor Recovered"
    --#SUMMARY      "%s"
    --#ARGUMENTS    { 4 }
    --#SEVERITY     INFORMATIONAL
    --#TIMEINDEX    99
    --#STATE        OPERATIONAL


        ::=     815


applicationMonitorInvalidTrap TRAP-TYPE
    ENTERPRISE  egenera
    VARIABLES {
                applicationIndex,
                applicationLPanIndex,
                applicationName,
                egeneraTrapSeverity,
                egeneraTrapMessage
            }
    DESCRIPTION
            "The notification generated when an application monitor is,
            discovered to be invalid, generally due to misconfiguration.

            This trap is driven by 'application <lpanname>/<appname> Health
            Monitor Invalid Event' event types.

            Severity: 3"
    --#TYPE         "Application Monitor Invalid"
    --#SUMMARY      "%s"
    --#ARGUMENTS    { 4 }
    --#SEVERITY     MINOR
    --#TIMEINDEX    99

        ::=     816


applicationFailedTrap TRAP-TYPE
    ENTERPRISE  egenera
    VARIABLES {
                applicationIndex,
                applicationLPanIndex,
                applicationName,
                egeneraTrapSeverity,
                egeneraTrapMessage
            }
    DESCRIPTION
            "This trap is deprecated as of PAN Manager release 4.0.
            See the following more specific traps:

                applicationStartFailedTrap
                applicationStopFailed
                applicationMoveFailedTrap
                applicationRestartedTrap
                applicationFailoverTrap
                applicationGiveupTrap
            "
    --#TYPE         "Application Failed"
    --#SUMMARY      "%s"
    --#ARGUMENTS    { 4 }
    --#SEVERITY     INFORMATIONAL
    --#TIMEINDEX    99

        ::=     809


applicationConfigWarningTrap TRAP-TYPE
    ENTERPRISE  egenera
    VARIABLES {
                applicationIndex,
                applicationLPanIndex,
                applicationName,
                egeneraTrapSeverity,
                egeneraTrapMessage
            }
    DESCRIPTION
            "The notification generated when an application is
            potentially misconfigured.

            This trap is driven by 'application <lpanname>/<appname> Configuration
            Warning Event' event types.

            Severity: 3"
    --#TYPE         "Application Config Warning"
    --#SUMMARY      "%s"
    --#ARGUMENTS    { 4 }
    --#SEVERITY     MINOR
    --#TIMEINDEX    99

        ::=     831


applicationStatusWarningTrap TRAP-TYPE
    ENTERPRISE  egenera
    VARIABLES {
                applicationIndex,
                applicationLPanIndex,
                applicationName,
                egeneraTrapSeverity,
                egeneraTrapMessage
            }
    DESCRIPTION
            "The notification generated when an application operation results in a
            potentially inappropriate state.

            This trap is driven by 'application <lpanname>/<appname> Status
            Warning Event' event types.

            Severity: 3"
    --#TYPE         "Application Status Warning"
    --#SUMMARY      "%s"
    --#ARGUMENTS    { 4 }
    --#SEVERITY     MINOR
    --#TIMEINDEX    99

        ::=     832


-- load balancer traps mirror application traps
loadBalancerCreatedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer has been
            created.

            This trap is driven by 'LPAN <lpanname> load balancer Create
            Event' event types.

            Severity: 5"
    --#TYPE         "loadBalancer Created"
    --#SUMMARY      "%s"
    --#ARGUMENTS    { 4 }
    --#SEVERITY     INFORMATIONAL
    --#TIMEINDEX    99

        ::=     840


loadBalancerModifyTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer is modified.

            This trap is driven by 'load balancer <lpanname>/<lbname> Changed
            Event' event types.

            Severity: 5"
    --#TYPE         "loadBalancer Modified"
    --#SUMMARY      "%s"
    --#ARGUMENTS    { 4 }
    --#SEVERITY     INFORMATIONAL
    --#TIMEINDEX    99
    --#STATE        OPERATIONAL

        ::=     841


loadBalancerDeletedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer has been
            deleted.

            This trap is driven by 'LPAN <lpanname> load balancer Delete
            Event' event types.

            Severity: 5"
    --#TYPE         "loadBalancer Deleted"
    --#SUMMARY      "%s"
    --#ARGUMENTS    { 4 }
    --#SEVERITY     INFORMATIONAL
    --#TIMEINDEX    99
    --#STATE        NONOPERATIONAL

        ::=     842


-- load balancer starting/started/start failed
loadBalancerStartingTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer start has been
            initiated.

            This trap is driven by 'load balancer <lpanname>/<lbname> Start
            Started Event' event types.

            Severity: 5"
    --#TYPE         "loadBalancer Starting"
    --#SUMMARY      "%s"
    --#ARGUMENTS    { 4 }
    --#SEVERITY     INFORMATIONAL
    --#TIMEINDEX    99

        ::=     843



loadBalancerStartedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer has started
            successfully.

            This trap is driven by 'load balancer <lpanname>/<lbname> Start Completed
            Event ' event types.

            Severity: 5"
    --#TYPE         "loadBalancer Started"
    --#SUMMARY      "%s"
    --#ARGUMENTS    { 4 }
    --#SEVERITY     INFORMATIONAL
    --#TIMEINDEX    99
    --#STATE        OPERATIONAL

        ::=     844


loadBalancerStartFailedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer start attempt
            has failed.

            This trap is driven by 'load balancer <lpanname>/<lbname> Start Failed
            Event' event types.

            Severity: 2"
    --#TYPE         "loadBalancer Start Failed"
    --#SUMMARY      "%s"
    --#ARGUMENTS    { 4 }
    --#SEVERITY     MAJOR
    --#TIMEINDEX    99
    --#STATE        NONOPERATIONAL

        ::=     845

-- load balancer stopping/stopped/stop failed
loadBalancerStoppingTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer stop has been
            initiated.

            This trap is driven by 'load balancer <lpanname>/<lbname> Stop
            Started Event' event types.

            Severity: 5"
    --#TYPE         "loadBalancer Stopping"
    --#SUMMARY      "%s"
    --#ARGUMENTS    { 4 }
    --#SEVERITY     INFORMATIONAL
    --#TIMEINDEX    99

        ::=     846

loadBalancerStoppedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer has been
            successfully stopped.

            This trap is driven by 'load balancer <lpanname>/<lbname> Stop
            Completed Event' event types.

            Severity: 5"
    --#TYPE         "loadBalancer Stopped"
    --#SUMMARY      "%s"
    --#ARGUMENTS    { 4 }
    --#SEVERITY     INFORMATIONAL
    --#TIMEINDEX    99
    --#STATE        NONOPERATIONAL

        ::=     847


loadBalancerStopFailedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer has failed
            to stop.

            This trap is driven by 'load balancer <lpanname>/<lbname> Stop
            Failed Event' event types.

            Severity: 2"
    --#TYPE         "loadBalancer Stop Failed"
    --#SUMMARY      "%s"
    --#ARGUMENTS    { 4 }
    --#SEVERITY     MAJOR
    --#TIMEINDEX    99

        ::=     848


-- load balancer moving/moved/move failed
loadBalancerMovingTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer move
            has been initiated.

            This trap is driven by 'load balancer <lpanname>/<lbname> Move
            Started Event' event types.

            Severity: 5"
    --#TYPE         "loadBalancer Moving"
    --#SUMMARY      "%s"
    --#ARGUMENTS    { 4 }
    --#SEVERITY     INFORMATIONAL
    --#TIMEINDEX    99

        ::=     849


loadBalancerMovedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer move
            has successfully completed.

            This trap is driven by 'load balancer <lpanname>/<lbname> Move
            Completed Event' event types.

            Severity: 5"
    --#TYPE         "loadBalancer Moved"
    --#SUMMARY      "%s"
    --#ARGUMENTS    { 4 }
    --#SEVERITY     INFORMATIONAL
    --#TIMEINDEX    99
    --#STATE        OPERATIONAL

        ::=     850


loadBalancerMoveFailedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer move
            has failed.

            This trap is driven by 'load balancer <lpanname>/<lbname> Move
            Failed Event' event types.

            Severity: 5"
    --#TYPE         "loadBalancer Move Failed"
    --#SUMMARY      "%s"
    --#ARGUMENTS    { 4 }
    --#SEVERITY     INFORMATIONAL
    --#TIMEINDEX    99

        ::=     851


-- load balancer failing over/failed over/failover failed
loadBalancerFailingOverTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer failover
            has been initiated.

            This trap is driven by 'load balancer <lpanname>/<lbname> Failover
            Started Event' event types.

            Severity: 5"
    --#TYPE         "loadBalancer Failing Over"
    --#SUMMARY      "%s"
    --#ARGUMENTS    { 4 }
    --#SEVERITY     INFORMATIONAL
    --#TIMEINDEX    99

        ::=     852


loadBalancerFailedOverTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer failover
            has successfully completed.

            This trap is driven by 'load balancer <lpanname>/<lbname> Failover
            Completed Event' event types.

            Severity: 5"
    --#TYPE         "loadBalancer Failed Over"
    --#SUMMARY      "%s"
    --#ARGUMENTS    { 4 }
    --#SEVERITY     INFORMATIONAL
    --#TIMEINDEX    99
    --#STATE        OPERATIONAL

        ::=     853


loadBalancerFailoverFailedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer failover
            has failed.

            This trap is driven by 'load balancer <lpanname>/<lbname> Failover
            Failed Event' event types.

            Severity: 5"
    --#TYPE         "loadBalancer Failover Failed"
    --#SUMMARY      "%s"
    --#ARGUMENTS    { 4 }
    --#SEVERITY     INFORMATIONAL
    --#TIMEINDEX    99

        ::=     854


-- health monitor induced actions
loadBalancerFailureDetectedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer health monitor
            has detected a load balancer failure.  These failures are counted,
            and compared to 'restart after', 'failover after', and 'giveup
            after' thresholds of the health monitor to trigger load balancer
            actions.

            This trap is driven by 'load balancer <lpanname>/<lbname> Health
            Monitor Detected Failure Event' event types.

            Severity: 4"
    --#TYPE         "loadBalancer Failure Detected"
    --#SUMMARY      "%s"
    --#ARGUMENTS    { 4 }
    --#SEVERITY     INFORMATIONAL
    --#TIMEINDEX    99

        ::=     861

loadBalancerRestartedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer failures have
            been detected by the health monitor, and the 'restart' threshold
            has been reached or exceeded.  This results in an attempt to
            restart the load balancer, for which further traps will be generated:

                loadBalancerStartingTrap
                loadBalancerStartedTrap
                loadBalancerStartFailedTrap

            This trap is driven by 'load balancer <lpanname>/<lbname> Health
            Monitor Restart Event' event types.

            Severity: 5"
    --#TYPE         "loadBalancer Restarted"
    --#SUMMARY      "%s"
    --#ARGUMENTS    { 4 }
    --#SEVERITY     INFORMATIONAL
    --#TIMEINDEX    99

        ::=     855


loadBalancerFailoverTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer failures have
            been detected by the health monitor, and the 'failover' threshold
            has been reached or exceeded.  This results in an attempt to
            failover the load balancer, for which further traps will be generated:

                loadBalancerMovingTrap
                loadBalancerMovedTrap
                loadBalancerMoveFailedTrap

            This trap is driven by 'load balancer <lpanname>/<lbname> Health
            Monitor Failover Event' event types.

            Severity: 5"
    --#TYPE         "loadBalancer Failover"
    --#SUMMARY      "%s"
    --#ARGUMENTS    { 4 }
    --#SEVERITY     INFORMATIONAL
    --#TIMEINDEX    99

        ::=     856


loadBalancerGiveupTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer failures have
            been detected by the health monitor, and the 'giveup' threshold
            has been reached or exceeded.  This results in the PAN Manager
            stop, for which further traps will be generated:

                loadBalancerStoppingTrap
                loadBalancerStoppedTrap
                loadBalancerStopFailed

            This trap is driven by 'load balancer <lpanname>/<lbname> Health
            Monitor GiveUp Event' event types.

            Severity: 5"
    --#TYPE         "loadBalancer Giveup"
    --#SUMMARY      "%s"
    --#ARGUMENTS    { 4 }
    --#SEVERITY     INFORMATIONAL
    --#TIMEINDEX    99
    --#STATE        NONOPERATIONAL

        ::=     857


loadBalancerMonitorFailedTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer monitor failed,
            generally due to a missing PAN Agent.

            This trap is driven by 'load balancer <lpanname>/<lbname> Health
            Monitor Failed Event' event types.

            Severity: 2"
    --#TYPE         "loadBalancer Monitor Failed"
    --#SUMMARY      "%s"
    --#ARGUMENTS    { 4 }
    --#SEVERITY     MAJOR
    --#TIMEINDEX    99

        ::=     858


loadBalancerMonitorRecoveredTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer monitor recovers,
            generally due to a restored PAN Agent.

            This trap is driven by 'load balancer <lpanname>/<lbname> Health
            Monitor Recovered Event' event types.

            Severity: 5"
    --#TYPE         "loadBalancer Monitor Recovered"
    --#SUMMARY      "%s"
    --#ARGUMENTS    { 4 }
    --#SEVERITY     INFORMATIONAL
    --#TIMEINDEX    99
    --#STATE        OPERATIONAL

        ::=     859


loadBalancerMonitorInvalidTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer monitor is,
            discovered to be invalid, generally due to misconfiguration.

            This trap is driven by 'load balancer <lpanname>/<lbname> Health Monitor
            Invalid Event' event types.

            Severity: 2"
    --#TYPE         "loadBalancer Monitor Invalid"
    --#SUMMARY      "%s"
    --#ARGUMENTS    { 4 }
    --#SEVERITY     MAJOR
    --#TIMEINDEX    99

        ::=     860


loadBalancerConfigWarningTrap TRAP-TYPE
    ENTERPRISE  egenera
    VARIABLES {
                loadBalancerIndex,
                loadBalancerLPanIndex,
                loadBalancerName,
                egeneraTrapSeverity,
                egeneraTrapMessage
            }
    DESCRIPTION
            "The notification generated when a load balancer is
            potentially misconfigured.

            This trap is driven by 'application <lpanname>/<appname> Configuration
            Warning Event' event types.

            Severity: 3"
    --#TYPE         "loadBalancer Config Warning"
    --#SUMMARY      "%s"
    --#ARGUMENTS    { 4 }
    --#SEVERITY     MINOR
    --#TIMEINDEX    99

        ::=     862


loadBalancerStatusWarningTrap TRAP-TYPE
    ENTERPRISE  egenera
    VARIABLES {
                loadBalancerIndex,
                loadBalancerLPanIndex,
                loadBalancerName,
                egeneraTrapSeverity,
                egeneraTrapMessage
            }
    DESCRIPTION
            "The notification generated when an application operation results in a
            potentially inappropriate state.

            This trap is driven by 'application <lpanname>/<appname> Status
            Warning Event' event types.

            Severity: 3"
    --#TYPE         "loadBalancer Status Warning"
    --#SUMMARY      "%s"
    --#ARGUMENTS    { 4 }
    --#SEVERITY     MINOR
    --#TIMEINDEX    99

        ::=     863


-- applicaion/load balancer resource traps (create/modify/delete for each resource)

nfsResourceCreateTrap TRAP-TYPE
    ENTERPRISE  egenera
    VARIABLES {
                nfsResourceIndex,
                nfsResourceLPANIndex,
                nfsResourceName,
                egeneraTrapSeverity,
                egeneraTrapMessage
            }
    DESCRIPTION
            "The notification generated when an nfs resource is created.

            This trap is driven by 'LPAN <lpanname> NFS resource Create
            Event' event types.

            Severity: 5"
    --#TYPE         "nfsResourde Created"
    --#SUMMARY      "%s"
    --#ARGUMENTS    { 4 }
    --#SEVERITY     INFORMATIONAL
    --#TIMEINDEX    99

        ::=     871


nfsResourceModifyTrap TRAP-TYPE
    ENTERPRISE  egenera
    VARIABLES {
                nfsResourceIndex,
                nfsResourceLPANIndex,
                nfsResourceName,
                egeneraTrapSeverity,
                egeneraTrapMessage
            }
    DESCRIPTION
            "The notification generated when an nfs resource is created.

            This trap is driven by 'NFS resource <resourcename> Changed
            Event' event types.

            Severity: 5"
    --#TYPE         "nfsResourde Modified"
    --#SUMMARY      "%s"
    --#ARGUMENTS    { 4 }
    --#SEVERITY     INFORMATIONAL
    --#TIMEINDEX    99
    --#STATE        OPERATIONAL

        ::=     872


nfsResourceDeleteTrap TRAP-TYPE
    ENTERPRISE  egenera
    VARIABLES {
                nfsResourceIndex,
                nfsResourceLPANIndex,
                nfsResourceName,
                egeneraTrapSeverity,
                egeneraTrapMessage
            }
    DESCRIPTION
            "The notification generated when an nfs resource is deleted.

            This trap is driven by 'LPAN <lpanname> NFS resource Delete
            Event' event types.

            Severity: 5"
    --#TYPE         "nfsResourde Deleted"
    --#SUMMARY      "%s"
    --#ARGUMENTS    { 4 }
    --#SEVERITY     INFORMATIONAL
    --#TIMEINDEX    99
    --#STATE        NONOPERATIONAL

        ::=     873


nfsResourceConfigWarningTrap TRAP-TYPE
    ENTERPRISE  egenera
    VARIABLES {
                nfsResourceIndex,
                nfsResourceLPANIndex,
                nfsResourceName,
                egeneraTrapSeverity,
                egeneraTrapMessage
            }
    DESCRIPTION
            "The notification generated when an nfs resource is
            potentially misconfigured.

            This trap is driven by 'NFS resource <resourcename> Configuration
            Warning Event' event types.

            Severity: 3"
    --#TYPE         "nfsResourde Config Warning"
    --#SUMMARY      "%s"
    --#ARGUMENTS    { 4 }
    --#SEVERITY     MINOR
    --#TIMEINDEX    99

        ::=     889




scsiDiskResourceCreateTrap TRAP-TYPE
    ENTERPRISE  egenera
    VARIABLES {
                scsiDiskResourceIndex,
                scsiDiskResourceLPANIndex,
                scsiDiskResourceName,
                egeneraTrapSeverity,
                egeneraTrapMessage
            }
    DESCRIPTION
            "The notification generated when a scsi disk resource is created.

            This trap is driven by 'LPAN <lpanname> SCSI disk resource Create
            Event' event types.

            Severity: 5"
    --#TYPE         "scsiDiskResource Created"
    --#SUMMARY      "%s"
    --#ARGUMENTS    { 4 }
    --#SEVERITY     INFORMATIONAL
    --#TIMEINDEX    99

        ::=     874


scsiDiskResourceModifyTrap TRAP-TYPE
    ENTERPRISE  egenera
    VARIABLES {
                scsiDiskResourceIndex,
                scsiDiskResourceLPANIndex,
                scsiDiskResourceName,
                egeneraTrapSeverity,
                egeneraTrapMessage
            }
    DESCRIPTION
            "The notification generated when a scsi disk resource is modified.

            This trap is driven by 'SCSI disk resource <resourcename> Changed
            Event' event types.

            Severity: 5"
    --#TYPE         "scsiDiskResource Modified"
    --#SUMMARY      "%s"
    --#ARGUMENTS    { 4 }
    --#SEVERITY     INFORMATIONAL
    --#TIMEINDEX    99
    --#STATE        OPERATIONAL

        ::=     875


scsiDiskResourceDeleteTrap TRAP-TYPE
    ENTERPRISE  egenera
    VARIABLES {
                scsiDiskResourceIndex,
                scsiDiskResourceLPANIndex,
                scsiDiskResourceName,
                egeneraTrapSeverity,
                egeneraTrapMessage
            }
    DESCRIPTION
            "The notification generated when a scsi disk resource is deleted.

            This trap is driven by 'LPAN <lpanname> SCSI disk resource Delete
            Event' event types.

            Severity: 5"
    --#TYPE         "scsiDiskResource Deleted"
    --#SUMMARY      "%s"
    --#ARGUMENTS    { 4 }
    --#SEVERITY     INFORMATIONAL
    --#TIMEINDEX    99
    --#STATE        NONOPERATIONAL

        ::=     876


scsiDiskResourceConfigWarningTrap TRAP-TYPE
    ENTERPRISE  egenera
    VARIABLES {
                scsiDiskResourceIndex,
                scsiDiskResourceLPANIndex,
                scsiDiskResourceName,
                egeneraTrapSeverity,
                egeneraTrapMessage
            }
    DESCRIPTION
            "The notification generated when a scsi disk resource is
            potentially misconfigured.

            This trap is driven by 'SCSI disk resource <resourcename> Configuration
            Warning Event' event types.

            Severity: 3"
    --#TYPE         "scsiDiskResource Config Warning"
    --#SUMMARY      "%s"
    --#ARGUMENTS    { 4 }
    --#SEVERITY     MINOR
    --#TIMEINDEX    99

        ::=     890



networkResourceCreateTrap TRAP-TYPE
    ENTERPRISE  egenera
    VARIABLES {
                networkResourceIndex,
                networkResourceLPANIndex,
                networkResourceName,
                egeneraTrapSeverity,
                egeneraTrapMessage
            }
    DESCRIPTION
            "The notification generated when a network resource is created.

            This trap is driven by 'LPAN <lpanname> network resource Create
            Event' event types.

            Severity: 5"
    --#TYPE         "networkResource Created"
    --#SUMMARY      "%s"
    --#ARGUMENTS    { 4 }
    --#SEVERITY     INFORMATIONAL
    --#TIMEINDEX    99

        ::=     877


networkResourceModifyTrap TRAP-TYPE
    ENTERPRISE  egenera
    VARIABLES {
                networkResourceIndex,
                networkResourceLPANIndex,
                networkResourceName,
                egeneraTrapSeverity,
                egeneraTrapMessage
            }
    DESCRIPTION
            "The notification generated when a network resource is created.

            This trap is driven by 'network resource <resourcename> Changed
            Event' event types.

            Severity: 5"
    --#TYPE         "networkResource Modified"
    --#SUMMARY      "%s"
    --#ARGUMENTS    { 4 }
    --#SEVERITY     INFORMATIONAL
    --#TIMEINDEX    99
    --#STATE        OPERATIONAL

        ::=     878


networkResourceDeleteTrap TRAP-TYPE
    ENTERPRISE  egenera
    VARIABLES {
                networkResourceIndex,
                networkResourceLPANIndex,
                networkResourceName,
                egeneraTrapSeverity,
                egeneraTrapMessage
            }
    DESCRIPTION
            "The notification generated when a network resource is deleted.

            This trap is driven by 'LPAN <lpanname> network resource Delete
            Event' event types.

            Severity: 5"
    --#TYPE         "networkResource Deleted"
    --#SUMMARY      "%s"
    --#ARGUMENTS    { 4 }
    --#SEVERITY     INFORMATIONAL
    --#TIMEINDEX    99
    --#STATE        NONOPERATIONAL

        ::=     879


networkResourceConfigWarningTrap TRAP-TYPE
    ENTERPRISE  egenera
    VARIABLES {
                networkResourceIndex,
                networkResourceLPANIndex,
                networkResourceName,
                egeneraTrapSeverity,
                egeneraTrapMessage
            }
    DESCRIPTION
            "The notification generated when a network resource is
            potentially misconfigured.

            This trap is driven by 'network resource <resourcename> Configuration
            Warning Event' event types.

            Severity: 3"
    --#TYPE         "networkResource Config Warning"
    --#SUMMARY      "%s"
    --#ARGUMENTS    { 4 }
    --#SEVERITY     MINOR
    --#TIMEINDEX    99

        ::=     891



failoverPolicyCreateTrap TRAP-TYPE
    ENTERPRISE  egenera
    VARIABLES {
                failoverPolicyIndex,
                failoverPolicyLPANIndex,
                failoverPolicyName,
                egeneraTrapSeverity,
                egeneraTrapMessage
            }
    DESCRIPTION
            "The notification generated when a failover policy is created.

            This trap is driven by 'LPAN <lpanname> failover policy Create
            Event' event types.

            Severity: 5"
    --#TYPE         "failoverPolicy Created"
    --#SUMMARY      "%s"
    --#ARGUMENTS    { 4 }
    --#SEVERITY     INFORMATIONAL
    --#TIMEINDEX    99

        ::=     880


failoverPolicyModifyTrap TRAP-TYPE
    ENTERPRISE  egenera
    VARIABLES {
                failoverPolicyIndex,
                failoverPolicyLPANIndex,
                failoverPolicyName,
                egeneraTrapSeverity,
                egeneraTrapMessage
            }
    DESCRIPTION
            "The notification generated when a failover policy is created.

            This trap is driven by 'failover policy <resourcename> Changed
            Event' event types.

            Severity: 5"
    --#TYPE         "failoverPolicy Modified"
    --#SUMMARY      "%s"
    --#ARGUMENTS    { 4 }
    --#SEVERITY     INFORMATIONAL
    --#TIMEINDEX    99
    --#STATE        OPERATIONAL

        ::=     881


failoverPolicyDeleteTrap TRAP-TYPE
    ENTERPRISE  egenera
    VARIABLES {
                failoverPolicyIndex,
                failoverPolicyLPANIndex,
                failoverPolicyName,
                egeneraTrapSeverity,
                egeneraTrapMessage
            }
    DESCRIPTION
            "The notification generated when a failover policy is deleted.

            This trap is driven by 'LPAN <lpanname> failover policy Delete
            Event' event types.

            Severity: 5"
    --#TYPE         "failoverPolicy Deleted"
    --#SUMMARY      "%s"
    --#ARGUMENTS    { 4 }
    --#SEVERITY     INFORMATIONAL
    --#TIMEINDEX    99
    --#STATE        NONOPERATIONAL

        ::=     882


failoverPolicyConfigWarningTrap TRAP-TYPE
    ENTERPRISE  egenera
    VARIABLES {
                failoverPolicyIndex,
                failoverPolicyLPANIndex,
                failoverPolicyName,
                egeneraTrapSeverity,
                egeneraTrapMessage
            }
    DESCRIPTION
            "The notification generated when a failover policy is
            potentially misconfigured.

            This trap is driven by 'failover policy <resourcename> Configuration
            Warning Event' event types.

            Severity: 3"
    --#TYPE         "failoverPolicy Config Warning"
    --#SUMMARY      "%s"
    --#ARGUMENTS    { 4 }
    --#SEVERITY     MINOR
    --#TIMEINDEX    99

        ::=     892



executableResourceCreateTrap TRAP-TYPE
    ENTERPRISE  egenera
    VARIABLES {
                executableResourceIndex,
                executableResourceLPANIndex,
                executableResourceName,
                egeneraTrapSeverity,
                egeneraTrapMessage
            }
    DESCRIPTION
            "The notification generated when an executable resource is created.

            This trap is driven by 'LPAN <lpanname> executable resource Create
            Event' event types.

            Severity: 5"
    --#TYPE         "executableResource Created"
    --#SUMMARY      "%s"
    --#ARGUMENTS    { 4 }
    --#SEVERITY     INFORMATIONAL
    --#TIMEINDEX    99

        ::=     883


executableResourceModifyTrap TRAP-TYPE
    ENTERPRISE  egenera
    VARIABLES {
                executableResourceIndex,
                executableResourceLPANIndex,
                executableResourceName,
                egeneraTrapSeverity,
                egeneraTrapMessage
            }
    DESCRIPTION
            "The notification generated when an executable resource is modified.

            This trap is driven by 'executable resource <resourcename> Changed
            Event' event types.

            Severity: 5"
    --#TYPE         "executableResource Modified"
    --#SUMMARY      "%s"
    --#ARGUMENTS    { 4 }
    --#SEVERITY     INFORMATIONAL
    --#TIMEINDEX    99
    --#STATE        OPERATIONAL

        ::=     884


executableResourceDeleteTrap TRAP-TYPE
    ENTERPRISE  egenera
    VARIABLES {
                executableResourceIndex,
                executableResourceLPANIndex,
                executableResourceName,
                egeneraTrapSeverity,
                egeneraTrapMessage
            }
    DESCRIPTION
            "The notification generated when an executable resource is deleted.

            This trap is driven by 'LPAN <lpanname> executable resource Delete
            Event' event types.

            Severity: 5"
    --#TYPE         "executableResource Deleted"
    --#SUMMARY      "%s"
    --#ARGUMENTS    { 4 }
    --#SEVERITY     INFORMATIONAL
    --#TIMEINDEX    99
    --#STATE        NONOPERATIONAL

        ::=     885



executableResourceConfigWarningTrap TRAP-TYPE
    ENTERPRISE  egenera
    VARIABLES {
                executableResourceIndex,
                executableResourceLPANIndex,
                executableResourceName,
                egeneraTrapSeverity,
                egeneraTrapMessage
            }
    DESCRIPTION
            "The notification generated when an executable resource is
            potentially misconfigured.

            This trap is driven by 'executable resource <resourcename>
            Configuration Warning Event' event types.

            Severity: 3"
    --#TYPE         "executableResource Config Warning"
    --#SUMMARY      "%s"
    --#ARGUMENTS    { 4 }
    --#SEVERITY     MINOR
    --#TIMEINDEX    99

        ::=     893



healthMonitorCreateTrap TRAP-TYPE
    ENTERPRISE  egenera
    VARIABLES {
                healthMonitorIndex,
                healthMonitorLPANIndex,
                healthMonitorName,
                egeneraTrapSeverity,
                egeneraTrapMessage
            }
    DESCRIPTION
            "The notification generated when an health monitor is created.

            This trap is driven by 'LPAN <lpanname> health monitor Create
            Event' event types.

            Severity: 5"
    --#TYPE         "healthMonitor Created"
    --#SUMMARY      "%s"
    --#ARGUMENTS    { 4 }
    --#SEVERITY     INFORMATIONAL
    --#TIMEINDEX    99

        ::=     886


healthMonitorModifyTrap TRAP-TYPE
    ENTERPRISE  egenera
    VARIABLES {
                healthMonitorIndex,
                healthMonitorLPANIndex,
                healthMonitorName,
                egeneraTrapSeverity,
                egeneraTrapMessage
            }
    DESCRIPTION
            "The notification generated when an health monitor is created.

            This trap is driven by 'health monitor <resourcename> Changed
            Event' event types.

            Severity: 5"
    --#TYPE         "healthMonitor Modified"
    --#SUMMARY      "%s"
    --#ARGUMENTS    { 4 }
    --#SEVERITY     INFORMATIONAL
    --#TIMEINDEX    99
    --#STATE        OPERATIONAL

        ::=     887


healthMonitorDeleteTrap TRAP-TYPE
    ENTERPRISE  egenera
    VARIABLES {
                healthMonitorIndex,
                healthMonitorLPANIndex,
                healthMonitorName,
                egeneraTrapSeverity,
                egeneraTrapMessage
            }
    DESCRIPTION
            "The notification generated when an health monitor is deleted.

            This trap is driven by 'LPAN <lpanname> health monitor Delete
            Event' event types.

            Severity: 5"
    --#TYPE         "healthMonitor Deleted"
    --#SUMMARY      "%s"
    --#ARGUMENTS    { 4 }
    --#SEVERITY     INFORMATIONAL
    --#TIMEINDEX    99
    --#STATE        NONOPERATIONAL

        ::=     888


healthMonitorConfigWarningTrap TRAP-TYPE
    ENTERPRISE  egenera
    VARIABLES {
                healthMonitorIndex,
                healthMonitorLPANIndex,
                healthMonitorName,
                egeneraTrapSeverity,
                egeneraTrapMessage
            }
    DESCRIPTION
            "The notification generated when a health monitor is
            potentially misconfigured.

            This trap is driven by 'health monitor <resourcename>
            Configuration Warning Event' event types.

            Severity: 3"
    --#TYPE         "healthMonitor Config Warning"
    --#SUMMARY      "%s"
    --#ARGUMENTS    { 4 }
    --#SEVERITY     MINOR
    --#TIMEINDEX    99

        ::=     894


userCreatedTrap TRAP-TYPE
    ENTERPRISE  egenera
    VARIABLES {
                userIndex,
                userName,
                egeneraTrapSeverity,
                egeneraTrapMessage
            }
    DESCRIPTION
            "The notification generated when a user has been created.

            This trap is driven by 'User Added Event' event types.

            Severity: 5"
    --#TYPE         "User Created"
    --#SUMMARY      "%s"
    --#ARGUMENTS    { 3 }
    --#SEVERITY     INFORMATIONAL
    --#TIMEINDEX    99
    --#STATE        OPERATIONAL

        ::=     901



userDeletedTrap TRAP-TYPE
    ENTERPRISE  egenera
    VARIABLES {
                userIndex,
                userName,
                egeneraTrapSeverity,
                egeneraTrapMessage
            }
    DESCRIPTION
            "The notification generated when a user has been deleted.

            This trap is driven by 'User Deleted Event' event types.

            Severity: 5"
    --#TYPE         "User Deleted"
    --#SUMMARY      "%s"
    --#ARGUMENTS    { 3 }
    --#SEVERITY     INFORMATIONAL
    --#TIMEINDEX    99
    --#STATE        NONOPERATIONAL

        ::=     902


userLoginTrap TRAP-TYPE
    ENTERPRISE  egenera
    VARIABLES {
                userIndex,
                userName,
                egeneraTrapSeverity,
                egeneraTrapMessage
            }
    DESCRIPTION
            "The notification generated when a user has logged in to the PAN
            Manager.

            This trap is deprecated, as there is no underlying even to drive
            the trap.  The definition exists to satisfy early requirements
            documents."
    --#TYPE         "User Login"
    --#SUMMARY      "%s"
    --#ARGUMENTS    { 3 }
    --#SEVERITY     INFORMATIONAL
    --#TIMEINDEX    99
    --#STATE        OPERATIONAL

        ::=     903


userLogoutTrap TRAP-TYPE
    ENTERPRISE  egenera
    VARIABLES {
                userIndex,
                userName,
                egeneraTrapSeverity,
                egeneraTrapMessage
            }
    DESCRIPTION
            "The notification generated when a user has logged out of the PAN
            Manager.

            This trap is deprecated, as there is no underlying even to drive
            the trap.  The definition exists to satisfy early requirements
            documents."
    --#TYPE         "User Logout"
    --#SUMMARY      "%s"
    --#ARGUMENTS    { 3 }
    --#SEVERITY     INFORMATIONAL
    --#TIMEINDEX    99
    --#STATE        NONOPERATIONAL

        ::=     904

userModifiedTrap TRAP-TYPE
    ENTERPRISE  egenera
    VARIABLES {
                userIndex,
                userName,
                egeneraTrapSeverity,
                egeneraTrapMessage
            }
    DESCRIPTION
            "The notification generated when a user has been modified.

            This trap is driven by 'User Modified Event' event types.

            Severity: 5"
    --#TYPE         "User Modified"
    --#SUMMARY      "%s"
    --#ARGUMENTS    { 3 }
    --#SEVERITY     INFORMATIONAL
    --#TIMEINDEX    99
    --#STATE        OPERATIONAL

        ::=     905



invalidManagerRequestTrap TRAP-TYPE
    ENTERPRISE  egenera
    VARIABLES {
                snmpManagerAddress,
                egeneraTrapSeverity,
                egeneraTrapMessage
            }
    DESCRIPTION
            "The notification generated when an unauthorized SNMP manager
            sends a request to the agent.

            This event is driven by incoming SNMP packets, and currently is
            not logged."
    --#TYPE         "Invalid Manager Request"
    --#SUMMARY      "%s"
    --#ARGUMENTS    { 2 }
    --#SEVERITY     INFORMATIONAL
    --#TIMEINDEX    99

        ::=     1001


invalidCommStringRequestTrap TRAP-TYPE
    ENTERPRISE  egenera
    VARIABLES {
                snmpManagerAddress,
                egeneraTrapSeverity,
                egeneraTrapMessage
            }
    DESCRIPTION
            "The notification generated when an authorized SNMP manager
            sends a request containing an invalid community string.

            This event is driven by incoming SNMP packets, and currently is
            not logged."
    --#TYPE         "Invalid Community String Request"
    --#SUMMARY      "%s"
    --#ARGUMENTS    { 2 }
    --#SEVERITY     INFORMATIONAL
    --#TIMEINDEX    99

        ::=     1002

pimSelectedTrap TRAP-TYPE
    ENTERPRISE  egenera
    VARIABLES {
                pimIndex,
                pimFrameIndex,
                pimName,
                egeneraTrapSeverity,
                egeneraTrapMessage
            }
    DESCRIPTION
            "The notification generated when a pim has been selected.

             This trap is driven by 'PIM <framename>/pim<1..4> Selected Status
             false Event' even types.

             Severity: 5"
    --#TYPE         "PIM Selected"
    --#SUMMARY      "%s"
    --#ARGUMENTS    { 4 }
    --#SEVERITY     INFORMATIONAL
    --#TIMEINDEX    99
    --#STATE        OPERATIONAL

        ::=     1101


pimDeselectedTrap TRAP-TYPE
    ENTERPRISE  egenera
    VARIABLES {
                pimIndex,
                pimFrameIndex,
                pimName,
                egeneraTrapSeverity,
                egeneraTrapMessage
            }
    DESCRIPTION
            "The notification generated when a pim has been unselected.

             This trap is driven by 'PIM <framename>/pim<1..4> Selected Status
             false Event' even types.

             Severity: 5"
    --#TYPE         "PIM Deselected"
    --#SUMMARY      "%s"
    --#ARGUMENTS    { 4 }
    --#SEVERITY     INFORMATIONAL
    --#TIMEINDEX    99
    --#STATE        OPERATIONAL
        ::=     1102


pimPowerThresholdHighTrap TRAP-TYPE
    ENTERPRISE  egenera
    VARIABLES {
                pimIndex,
                pimFrameIndex,
                pimName,
                egeneraTrapSeverity,
                egeneraTrapMessage
            }
    DESCRIPTION
            "The notification generated when a pim's power threshold is high.

             This trap is driven by 'PIM <framename>/pim<1..4> Power Threshold High' event types.

             Severity: 3"
    --#TYPE         "PIM Power Threshold High"
    --#SUMMARY      "%s"
    --#ARGUMENTS    { 4 }
    --#SEVERITY     MINOR
    --#TIMEINDEX    99

        ::=     1103


pimCurrentThresholdHighTrap TRAP-TYPE
    ENTERPRISE  egenera
    VARIABLES {
                pimIndex,
                pimFrameIndex,
                pimName,
                egeneraTrapSeverity,
                egeneraTrapMessage
            }
    DESCRIPTION
            "The notification generated when a pim's current threshold is high.

             This trap is driven by 'PIM <framename>/pim<1..4> Current Threshold High' event types.

             Severity: 3"
    --#TYPE         "PIM Current Threshold High"
    --#SUMMARY      "%s"
    --#ARGUMENTS    { 4 }
    --#SEVERITY     MINOR
    --#TIMEINDEX    99

        ::=     1104


pimSourceTransitionTrap TRAP-TYPE
    ENTERPRISE  egenera
    VARIABLES {
                pimIndex,
                pimFrameIndex,
                pimName,
                egeneraTrapSeverity,
                egeneraTrapMessage
            }
    DESCRIPTION
            "The notification generated when a pim's source transition happened.

             This trap is driven by 'PIM <framename>/pim<1..4> Source Transition' event types.

             Severity: 4"
    --#TYPE         "PIM Source Transitioned"
    --#SUMMARY      "%s"
    --#ARGUMENTS    { 4 }
    --#SEVERITY     INFORMATIONAL
    --#TIMEINDEX    99
    --#STATE        OPERATIONAL
        ::=     1105


pimInsertedTrap TRAP-TYPE
    ENTERPRISE  egenera
    VARIABLES {
                pimIndex,
                pimFrameIndex,
                pimName,
                egeneraTrapSeverity,
                egeneraTrapMessage
            }
    DESCRIPTION
            "The notification generated when a pim is inserted.

             This trap is driven by 'PIM <framename>/pim<1..4> Inserted' event types.

             Severity: 5"
    --#TYPE         "PIM Inserted"
    --#SUMMARY      "%s"
    --#ARGUMENTS    { 4 }
    --#SEVERITY     INFORMATIONAL
    --#TIMEINDEX    99
    --#STATE        OPERATIONAL

        ::=     1106

pimRemovedTrap TRAP-TYPE
    ENTERPRISE  egenera
    VARIABLES {
                pimIndex,
                pimFrameIndex,
                pimName,
                egeneraTrapSeverity,
                egeneraTrapMessage
            }
    DESCRIPTION
            "The notification generated when a pim is ejected.

             This trap is driven by 'PIM <framename>/pim<1..4> Removed' event types.

             Severity: 5"
    --#TYPE         "PIM Removed"
    --#SUMMARY      "%s"
    --#ARGUMENTS    { 4 }
    --#SEVERITY     INFORMATIONAL
    --#TIMEINDEX    99
    --#STATE        NONOPERATIONAL
        ::=     1107

pimSourcePreferenceConfiguredTrap TRAP-TYPE
    ENTERPRISE  egenera
    VARIABLES {
                pimIndex,
                pimFrameIndex,
                pimName,
                egeneraTrapSeverity,
                egeneraTrapMessage
            }
    DESCRIPTION
            "The notification generated when a pim source preference is configured.

             This trap is driven by 'PIM <framename>/pim<1..4> Source Preference Configured' event types.

             Severity: 5"
    --#TYPE         "PIM Source Preference Configured"
    --#SUMMARY      "%s"
    --#ARGUMENTS    { 4 }
    --#SEVERITY     INFORMATIONAL
    --#TIMEINDEX    99
    --#STATE        OPERATIONAL
        ::=     1108

pimConfigErrorTrap TRAP-TYPE
    ENTERPRISE  egenera
    VARIABLES {
                pimIndex,
                pimFrameIndex,
                pimName,
                egeneraTrapSeverity,
                egeneraTrapMessage
            }
    DESCRIPTION
            "The notification generated when a pim encounters an error activating a configuration changea.

             This trap is driven by 'PIM <framename>/pim<1..4> Config Error Event' event types.

             Severity: 2"
    --#TYPE         "PIM Config Error"
    --#SUMMARY      "%s"
    --#ARGUMENTS    { 4 }
    --#SEVERITY     MAJOR
    --#TIMEINDEX    99

        ::=     1109


pimPowerOnTrap TRAP-TYPE
    ENTERPRISE  egenera
    VARIABLES {
                pimIndex,
                pimFrameIndex,
                pimName,
                egeneraTrapSeverity,
                egeneraTrapMessage
            }
    DESCRIPTION
            "The notification generated when an pim is powered on.

            This trap is driven by 'Blade <framename>/pim<1..4> Power Status Event'
            event types describing power on events.

            Since the underlying event type describes pim power on and off
            events, enabling/disabling this SNMP trap as an event action is bound
            to the enabling/disabling of pimPowerOffTrap.

            Severity: 5"
    --#TYPE         "BladeFrame pim Power On"
    --#SUMMARY      "%s"
    --#ARGUMENTS    { 4 }
    --#SEVERITY     INFORMATIONAL
    --#TIMEINDEX    99
    --#STATE        OPERATIONAL

        ::=    1110


pimPowerOffTrap TRAP-TYPE
    ENTERPRISE  egenera
    VARIABLES {
                pimIndex,
                pimFrameIndex,
                pimName,
                egeneraTrapSeverity,
                egeneraTrapMessage
            }
    DESCRIPTION
            "The notification generated when an pim is powered off.

            This trap is driven by 'Blade <framename>/pim<1..4> Power Status Event'
            event types describing power on events.

            Since the underlying event type describes pim power on and off
            events, enabling/disabling this SNMP trap as an event action is bound
            to the enabling/disabling of pimPowerOnTrap.

            Severity: 5"
    --#TYPE         "BladeFrame pim Power Off"
    --#SUMMARY      "%s"
    --#ARGUMENTS    { 4 }
    --#SEVERITY     INFORMATIONAL
    --#TIMEINDEX    99
    --#STATE        NONOPERATIONAL

        ::=    1111


pimEnabledTrap TRAP-TYPE
    ENTERPRISE  egenera
    VARIABLES {
                pimIndex,
                pimFrameIndex,
                pimName,
                egeneraTrapSeverity,
                egeneraTrapMessage
            }
    DESCRIPTION
            "The notification generated when an pim is enabled (returns
             to service).

             This trap is driven by 'Blade <framename>/pim<1..4> Out of Service Status
             false Event' event types.

             Severity: 5"
    --#TYPE         "BladeFrame pim Enabled"
    --#SUMMARY      "%s"
    --#ARGUMENTS    { 4 }
    --#SEVERITY     INFORMATIONAL
    --#TIMEINDEX    99
    --#STATE        OPERATIONAL

        ::=    1112


pimDisabledTrap TRAP-TYPE
    ENTERPRISE  egenera
    VARIABLES {
                pimIndex,
                pimFrameIndex,
                pimName,
                egeneraTrapSeverity,
                egeneraTrapMessage
            }
    DESCRIPTION
            "The notification generated when an pim is disabled. (removed
             from service).

             This trap is driven by 'Blade <framename>/pim<1..4> Out of Service Status
             true Event' event types.

             Severity: 5"
    --#TYPE         "BladeFrame pim Disabled"
    --#SUMMARY      "%s"
    --#ARGUMENTS    { 4 }
    --#SEVERITY     INFORMATIONAL
    --#TIMEINDEX    99
    --#STATE        NONOPERATIONAL

        ::=    1113


pimOutOfServicePendingTrap TRAP-TYPE
    ENTERPRISE  egenera
    VARIABLES {
                pimIndex,
                pimFrameIndex,
                pimName,
                egeneraTrapSeverity,
                egeneraTrapMessage
            }
    DESCRIPTION
            "The notification generated when a pBlade enters the 'out of service
            pending' state.

            This trap is driven by 'cBlade <bladeframe>/pim<1..4> Out of Service Pending
            Event' event types

            Severity: 5"
    --#TYPE         "pBlade Out Of Service Pending"
    --#SUMMARY      "%s"
    --#ARGUMENTS    { 4 }
    --#SEVERITY     INFORMATIONAL
    --#TIMEINDEX    99
    --#STATE        OPERATIONAL

        ::=     1114



pimPowerOnOpTrap TRAP-TYPE
    ENTERPRISE egenera
    VARIABLES {
                pimIndex,
                pimFrameIndex,
                pimName,
                egeneraTrapSeverity,
                egeneraTrapMessage
            }
    DESCRIPTION
            "Encapsulates pim power on operation event.

            This trap is driven by 'pim <framename>/pim<1..4> Hardware Operation
            Event' event types.

            Since the underlying event type describes pim power on and off
            operation events, enabling/disabling this SNMP trap as an event action
            is bound to the enabling/disabling of pimPowerOffOpTrap,
            pimPowerCycleTrap, and pimResetOpTrap.

            Severity: 5"
    --#TYPE         "BladeFrame pim Power On Operation"
    --#SUMMARY      "%s"
    --#ARGUMENTS    { 4 }
    --#SEVERITY     INFORMATIONAL
    --#TIMEINDEX    99
    --#STATE        OPERATIONAL

        ::=     1115


pimPowerOffOpTrap TRAP-TYPE
    ENTERPRISE egenera
    VARIABLES {
                pimIndex,
                pimFrameIndex,
                pimName,
                egeneraTrapSeverity,
                egeneraTrapMessage
            }
    DESCRIPTION
            "Encapsulates pim power off operation event.

            This trap is driven by 'pim <framename>/pim<1..4> Hardware Operation
            Event' event types.

            Since the underlying event type describes pim power on and off
            operation events, enabling/disabling this SNMP trap as an event action
            is bound to the enabling/disabling of pimPowerOnOpTrap,
            pimPowerCycleTrap, and pimResetOpTrap.

            Severity: 5"
    --#TYPE         "BladeFrame pim Power Off Operation"
    --#SUMMARY      "%s"
    --#ARGUMENTS    { 4 }
    --#SEVERITY     INFORMATIONAL
    --#TIMEINDEX    99
    --#STATE        OPERATIONAL

        ::=     1116


pimPowerCycleOpTrap TRAP-TYPE
    ENTERPRISE egenera
    VARIABLES {
                pimIndex,
                pimFrameIndex,
                pimName,
                egeneraTrapSeverity,
                egeneraTrapMessage
            }
    DESCRIPTION
            "Encapsulates pim power cycle operation event.

            This trap is driven by 'pim <framename>/pim<1..4> Hardware Operation
            Event' event types.

            Since the underlying event type describes pim power on and off
            operation events, enabling/disabling this SNMP trap as an event action
            is bound to the enabling/disabling of pimPowerOnOpTrap,
            pimPowerCycleTrap, and pimResetOpTrap.

            Severity: 5"
    --#TYPE         "BladeFrame pim Power Cycle Operation"
    --#SUMMARY      "%s"
    --#ARGUMENTS    { 4 }
    --#SEVERITY     INFORMATIONAL
    --#TIMEINDEX    99
    --#STATE        OPERATIONAL

        ::=     1117


pimResetOpTrap TRAP-TYPE
    ENTERPRISE egenera
    VARIABLES {
                pimIndex,
                pimFrameIndex,
                pimName,
                egeneraTrapSeverity,
                egeneraTrapMessage
            }
    DESCRIPTION
            "Encapsulates pim reset operation event.

            This trap is driven by 'pim <framename>/pim<1..4> Hardware Operation
            Event' event types.

            Since the underlying event type describes pim power on and off
            operation events, enabling/disabling this SNMP trap as an event action
            is bound to the enabling/disabling of pimPowerOnOpTrap,
            pimPowerCycleTrap, and pimPowerCycleOpTrap.

            Severity: 5"
    --#TYPE         "BladeFrame pim Reset Operation"
    --#SUMMARY      "%s"
    --#ARGUMENTS    { 4 }
    --#SEVERITY     INFORMATIONAL
    --#TIMEINDEX    99
    --#STATE        OPERATIONAL

        ::=     1118


pimHwEventTrap TRAP-TYPE
    ENTERPRISE  egenera
    VARIABLES {
                pimIndex,
                pimFrameIndex,
                pimName,
                egeneraTrapSeverity,
                egeneraTrapMessage
            }
    DESCRIPTION
            "Encapsulates generic events from hardware.

            This trap is driven by 'Blade <framename>/pim<1..4> non-sensor Event'
            event types.

            Severity: 3"
    --#TYPE         "BladeFrame pBlade Hw Event"
    --#SUMMARY      "%s"
    --#ARGUMENTS    { 4 }
    --#SEVERITY     MINOR
    --#TIMEINDEX    99

        ::=     1119


pimVoltageUpperTrap TRAP-TYPE
    ENTERPRISE egenera
    VARIABLES {
                pimIndex,
                pimFrameIndex,
                pimName,
                sensorName,
                sensorThreshold,
                sensorValue,
                egeneraTrapSeverity,
                egeneraTrapMessage
            }
    DESCRIPTION
            "Encapsulates pim critical high voltage sensor events.

            This trap is driven by 'Blade <framename>/pim<1..4> <voltage-sensor-name>
            Critical High Event' event types.

            The sensorValue and sensorThreshold fields are ingeter representations
            of real numbers.  The real numbers are multiplied by 100 and rounded
            to produce an integer, thus 0.530 => 53.

            This trap replaces pimHwThreshTrap.

            Severity: 3"
    --#TYPE         "BladeFrame pim Voltage Upper"
    --#SUMMARY      "%s"
    --#ARGUMENTS    { 7 }
    --#SEVERITY     MINOR
    --#TIMEINDEX    99

        ::=     1120


pimVoltageLowerTrap TRAP-TYPE
    ENTERPRISE egenera
    VARIABLES {
                pimIndex,
                pimFrameIndex,
                pimName,
                sensorName,
                sensorThreshold,
                sensorValue,
                egeneraTrapSeverity,
                egeneraTrapMessage
            }
    DESCRIPTION
            "Encapsulates pim critical low voltage sensor events.

            This trap is driven by 'Blade <framename>/pim<1..4> <voltage-sensor-name>
            Critical Low Event' event types.

            The sensorValue and sensorThreshold fields are ingeter representations
            of real numbers.  The real numbers are multiplied by 100 and rounded
            to produce an integer, thus 0.530 => 53.

            This trap replaces pimHwThreshTrap.

            Severity: 3"
    --#TYPE         "BladeFrame pim Voltage Lower"
    --#SUMMARY      "%s"
    --#ARGUMENTS    { 7 }
    --#SEVERITY     MINOR
    --#TIMEINDEX    99

        ::=     1121


pimFanSpeedUpperTrap TRAP-TYPE
    ENTERPRISE egenera
    VARIABLES {
                pimIndex,
                pimFrameIndex,
                pimName,
                sensorName,
                sensorThreshold,
                sensorValue,
                egeneraTrapSeverity,
                egeneraTrapMessage
            }
    DESCRIPTION
            "Encapsulates pim critical high fan speed  sensor events.

            This trap is driven by 'Blade <framename>/pim<1..4> <fan-sensor-name>
            Critical High Event' event types.

            This trap replaces pimHwThreshTrap.

            Severity: 3"
    --#TYPE         "BladeFrame pim Fan Speed Upper"
    --#SUMMARY      "%s"
    --#ARGUMENTS    { 7 }
    --#SEVERITY     MINOR
    --#TIMEINDEX    99

        ::=     1122


pimFanSpeedLowerTrap TRAP-TYPE
    ENTERPRISE egenera
    VARIABLES {
                pimIndex,
                pimFrameIndex,
                pimName,
                sensorName,
                sensorThreshold,
                sensorValue,
                egeneraTrapSeverity,
                egeneraTrapMessage
            }
    DESCRIPTION
            "Encapsulates pim critical low fan speed sensor events.

            This trap is driven by 'Blade <framename>/pim<1..4> <fan-sensor-name>
            Critical Low Event' event types.

            This trap replaces pimHwThreshTrap.

            Severity: 3"
    --#TYPE         "BladeFrame pim Fan Speed Lower"
    --#SUMMARY      "%s"
    --#ARGUMENTS    { 7 }
    --#SEVERITY     MINOR
    --#TIMEINDEX    99

        ::=     1123



pimTempUpperTrap TRAP-TYPE
    ENTERPRISE egenera
    VARIABLES {
                pimIndex,
                pimFrameIndex,
                pimName,
                sensorName,
                sensorThreshold,
                sensorValue,
                egeneraTrapSeverity,
                egeneraTrapMessage
            }
    DESCRIPTION
            "Encapsulates pim critical high temperature sensor events.

            This trap is driven by 'Blade <framename>/pim<1..4> <temp-sensor-name>
            Critical High Event' event types.

            This trap replaces pimHwThreshTrap.

            Severity: 3"
    --#TYPE         "BladeFrame pim Temp Upper"
    --#SUMMARY      "%s"
    --#ARGUMENTS    { 7 }
    --#SEVERITY     MINOR
    --#TIMEINDEX    99

        ::=     1124


pimTempLowerTrap TRAP-TYPE
    ENTERPRISE egenera
    VARIABLES {
                pimIndex,
                pimFrameIndex,
                pimName,
                sensorName,
                sensorThreshold,
                sensorValue,
                egeneraTrapSeverity,
                egeneraTrapMessage
            }
    DESCRIPTION
            "Encapsulates pim critical low temperature sensor events.

            This trap is driven by 'Blade <framename>/pim<1..4> <temp-sensor-name>
            Critical Low Event' event types.

            This trap replaces pimHwThreshTrap.

            Severity: 3"
    --#TYPE         "BladeFrame pim Temp Lower"
    --#SUMMARY      "%s"
    --#ARGUMENTS    { 7 }
    --#SEVERITY     MINOR
    --#TIMEINDEX    99

        ::=     1125


globalPoolCreatedTrap TRAP-TYPE
    ENTERPRISE  egenera
    VARIABLES {
                poolIndex,
                poolName,
                egeneraTrapSeverity,
                egeneraTrapMessage
            }
    DESCRIPTION
            "The notification generated when a global pool is created.

             Severity: 5"
    --#TYPE         "Global Pool Created"
    --#SUMMARY      "%s"
    --#ARGUMENTS    { 3 }
    --#SEVERITY     INFORMATIONAL
    --#TIMEINDEX    99
    --#STATE        OPERATIONAL

        ::=     1201

globalPoolDeletedTrap TRAP-TYPE
    ENTERPRISE  egenera
    VARIABLES {
                poolIndex,
                poolName,
                egeneraTrapSeverity,
                egeneraTrapMessage
            }
    DESCRIPTION
            "The notification generated when a global pool is deleted.

             Severity: 5"
    --#TYPE         "Global Pool Deleted"
    --#SUMMARY      "%s"
    --#ARGUMENTS    { 3 }
    --#SEVERITY     INFORMATIONAL
    --#TIMEINDEX    99
    --#STATE        NONOPERATIONAL

        ::=     1202

localPoolCreatedTrap TRAP-TYPE
    ENTERPRISE  egenera
    VARIABLES {
                poolIndex,
                poolName,
                egeneraTrapSeverity,
                egeneraTrapMessage
            }
    DESCRIPTION
            "The notification generated when a local pool is created.

             Severity: 5"
    --#TYPE         "Local Pool Created"
    --#SUMMARY      "%s"
    --#ARGUMENTS    { 3 }
    --#SEVERITY     INFORMATIONAL
    --#TIMEINDEX    99
    --#STATE        OPERATIONAL
        ::=     1203

localPoolDeletedTrap TRAP-TYPE
    ENTERPRISE  egenera
    VARIABLES {
                poolIndex,
                poolName,
                egeneraTrapSeverity,
                egeneraTrapMessage
            }
    DESCRIPTION
            "The notification generated when a local pool is deleted.

             Severity: 5"
    --#TYPE         "Local Pool Deleted"
    --#SUMMARY      "%s"
    --#ARGUMENTS    { 3 }
    --#SEVERITY     INFORMATIONAL
    --#TIMEINDEX    99
    --#STATE        NONOPERATIONAL
        ::=     1204

poolConfigChangedTrap TRAP-TYPE
    ENTERPRISE  egenera
    VARIABLES {
                poolIndex,
                poolName,
                egeneraTrapSeverity,
                egeneraTrapMessage
            }
    DESCRIPTION
            "The notification generated when a pool configuration is changed.

             Severity: 5"
    --#TYPE         "Pool Config Changed"
    --#SUMMARY      "%s"
    --#ARGUMENTS    { 3 }
    --#SEVERITY     INFORMATIONAL
    --#TIMEINDEX    99
    --#STATE        OPERATIONAL
        ::=     1205

poolPBladeArrivedTrap TRAP-TYPE
    ENTERPRISE  egenera
    VARIABLES {
                poolIndex,
                poolName,
                egeneraTrapSeverity,
                egeneraTrapMessage
            }
    DESCRIPTION
            "The notification generated when a pool pBlade is arrived.

             Severity: 5"
    --#TYPE         "Pool PBlade Arrived"
    --#SUMMARY      "%s"
    --#ARGUMENTS    { 3 }
    --#SEVERITY     INFORMATIONAL
    --#TIMEINDEX    99
    --#STATE        OPERATIONAL
        ::=     1206

poolPBladeDepartedTrap TRAP-TYPE
    ENTERPRISE  egenera
    VARIABLES {
                poolIndex,
                poolName,
                egeneraTrapSeverity,
                egeneraTrapMessage
            }
    DESCRIPTION
            "The notification generated when a pool pBlade is departed.

             Severity: 5"
    --#TYPE         "Pool PBlade Departed"
    --#SUMMARY      "%s"
    --#ARGUMENTS    { 3 }
    --#SEVERITY     INFORMATIONAL
    --#TIMEINDEX    99
    --#STATE        OPERATIONAL
        ::=     1207

diskPartitionedTrap TRAP-TYPE
    ENTERPRISE  egenera
    VARIABLES {
                diskId,
                egeneraTrapSeverity,
                egeneraTrapMessage
            }
    DESCRIPTION
            "The notification generated when a disk is partitioned.

             Severity: 5"
    --#TYPE         "Disk Partitioned"
    --#SUMMARY      "%s"
    --#ARGUMENTS    { 2 }
    --#SEVERITY     INFORMATIONAL
    --#TIMEINDEX    99
    --#STATE        OPERATIONAL
        ::=     1301

diskWinPeTrap TRAP-TYPE
    ENTERPRISE  egenera
    VARIABLES {
                diskId,
                egeneraTrapSeverity,
                egeneraTrapMessage
            }
    DESCRIPTION
            "The notification generated when the WinPe image is installed on a disk.

             Severity: 5"
    --#TYPE         "Disk WinPe"
    --#SUMMARY      "%s"
    --#ARGUMENTS    { 2 }
    --#SEVERITY     INFORMATIONAL
    --#TIMEINDEX    99
    --#STATE        OPERATIONAL
        ::=     1302

diskRootedTrap TRAP-TYPE
    ENTERPRISE  egenera
    VARIABLES {
                diskId,
                egeneraTrapSeverity,
                egeneraTrapMessage
            }
    DESCRIPTION
            "The notification generated when a root image is installed on a disk.

             Severity: 5"
    --#TYPE         "Disk Rooted"
    --#SUMMARY      "%s"
    --#ARGUMENTS    { 2 }
    --#SEVERITY     INFORMATIONAL
    --#TIMEINDEX    99
    --#STATE        OPERATIONAL
        ::=     1303

diskOpTrap TRAP-TYPE
    ENTERPRISE  egenera
    VARIABLES {
                diskId,
                egeneraTrapSeverity,
                egeneraTrapMessage
            }
    DESCRIPTION
            "The notification generated when an operation is performed on a disk

             Severity: 5"
    --#TYPE         "Disk Rooted"
    --#SUMMARY      "%s"
    --#ARGUMENTS    { 2 }
    --#SEVERITY     INFORMATIONAL
    --#TIMEINDEX    99
    --#STATE        OPERATIONAL
        ::=     1304



-- vBlade traps

-- power status
vBladePowerOnTrap TRAP-TYPE
    ENTERPRISE  egenera
    VARIABLES {
                vBladeIndex,
                vBladePBladeIndex,
                vBladeFrameIndex,
                vBladeName,
                egeneraTrapSeverity,
                egeneraTrapMessage
            }
    DESCRIPTION
            "The notification generated when a vBlade is powered on.

            This trap is driven by 'Blade <framename>/p<1|2> Power Status Trap'
            Trap types describing power on Traps.

            Since the underlying Trap type describes vBlade power on and off
            Traps, enabling/disabling this SNMP trap as an Trap action is bound
            to the enabling/disabling of vBladePowerOffTrap.

            Severity: 5"
    --#TYPE         "BladeFrame vBlade Power On"
    --#SUMMARY      "%s"
    --#ARGUMENTS    { 5 }
    --#SEVERITY     INFORMATIONAL
    --#TIMEINDEX    99
    --#STATE        OPERATIONAL

        ::=     1403


vBladePowerOffTrap TRAP-TYPE
    ENTERPRISE  egenera
    VARIABLES {
                vBladeIndex,
                vBladePBladeIndex,
                vBladeFrameIndex,
                vBladeName,
                egeneraTrapSeverity,
                egeneraTrapMessage
            }
    DESCRIPTION
            "The notification generated when a vBlade is powered off.

            This trap is driven by 'Blade <framename>/p<1|2> Power Status Trap'
            Trap types describing power on Traps.

            Since the underlying Trap type describes sBlade power on and off
            Traps, enabling/disabling this SNMP trap as an Trap action is bound
            to the enabling/disabling of vBladePowerOnTrap.

            Severity: 5"
    --#TYPE         "BladeFrame vBlade Power On"
    --#SUMMARY      "%s"
    --#ARGUMENTS    { 5 }
    --#SEVERITY     INFORMATIONAL
    --#TIMEINDEX    99
    --#STATE        OPERATIONAL

        ::=     1404


-- vBlade traps exists, vBlade equivalents not implemented (yet)
vBladeShutdownTrap TRAP-TYPE
    ENTERPRISE  egenera
    VARIABLES {
                vBladeIndex,
                vBladePBladeIndex,
                vBladeFrameIndex,
                vBladeName,
                egeneraTrapSeverity,
                egeneraTrapMessage
            }
    DESCRIPTION
            "The notification generated when a vBlade has been shut
             down.

            This trap is driven by 'blade.status.monitor.Trap' Trap types
            that describe a vBlade transition from the shutting down state to
            the shutdown state.

            This Trap type is not user visible, and will not appear in
            CLI or GUI Trap quieries.  The trap exists to satisfy early
           requirements documents.

            Severity: 5"
    --#TYPE         "BladeFrame vBlade Power Off"
    --#SUMMARY      "%s"
    --#ARGUMENTS    { 5 }
    --#SEVERITY     INFORMATIONAL
    --#TIMEINDEX    99
    --#STATE        OPERATIONAL

        ::=     1406


vBladeHwEventTrap TRAP-TYPE
    ENTERPRISE  egenera
    VARIABLES {
                vBladeIndex,
                vBladeFrameIndex,
                vBladeName,
                egeneraTrapSeverity,
                egeneraTrapMessage
            }
    DESCRIPTION
            "Encapsulates generic events from hardware.

            This trap is driven by 'Blade <framename>/p<1..24> non-sensor Event'
            event types that do not indicate panic, commanded shutdown,
            commanded reboot, or init level events.  Examples message contents
            include:

            OEM Type 0xe0, value = 0x64:0x21:0xce:0xe0:0x1d:0x00:0x00:0x00...
            bmc reset
            deasserted, value = 0x0211
            system booted

            Contact EES for more specific information.

            Since the underlying event type describes vBlade all non-sensor hardware
            events, and since there are specific traps for panic, commanded shutdown,
            commanded reboot, and init level events, enabling/disabling this SNMP trap
            as an event action is bound to the enabling/disabling of vBladePanicTrap,
            vBladeCmdShutdownTrap, vBladeCmdRebootTrap, vBladeCmdHaltTrap, and
            vBladeInitTrap.

            Severity: 3"
    --#TYPE         "BladeFrame vBlade hardware event"
    --#SUMMARY      "%s"
    --#ARGUMENTS    { 5 }
    --#SEVERITY     INFORMATIONAL
    --#TIMEINDEX    99
    --#STATE        OPERATIONAL

        ::=     1411



vBladeCmdRebootTrap TRAP-TYPE
    ENTERPRISE  egenera
    VARIABLES {
                vBladeIndex,
                vBladePBladeIndex,
                vBladeFrameIndex,
                vBladeName,
                egeneraTrapSeverity,
                egeneraTrapMessage
            }
    DESCRIPTION
            "Encapsulates hardware Traps indicating intentional vBlade
            reboot.

            This trap is driven by 'Blade <framename>/p<1..24> non-sensor Trap'
            Trap types that describe commanded reboots.

            Contact EES for more specific information.

            Since the underlying Trap type describes vBlade non-sensor hardware
            Traps, and since there are specific traps for panic, commanded shutdown,
            commanded reboot, and init level Traps, enabling/disabling this SNMP trap
            as an Trap action is bound to the enabling/disabling of vBladeHwTrapTrap,
            vBladeCmdShutdownTrap, vBladeCmdHaltTrap, vBladePanicTrap, and
            vBladeInitTrap.

            Severity: 3"
    --#TYPE         "BladeFrame vBlade reboot event"
    --#SUMMARY      "%s"
    --#ARGUMENTS    { 5 }
    --#SEVERITY     INFORMATIONAL
    --#TIMEINDEX    99
    --#STATE        OPERATIONAL

        ::=     1415


vBladePowerOnOpTrap TRAP-TYPE
    ENTERPRISE  egenera
    VARIABLES {
                vBladeIndex,
                vBladePBladeIndex,
                vBladeFrameIndex,
                vBladeName,
                egeneraTrapSeverity,
                egeneraTrapMessage
            }
    DESCRIPTION
            "Encapsulates vBlade power on operation Trap.

            This trap is driven by 'vBlade <framename>/c<1|2> Hardware Operation
            Trap' Trap types.

            Since the underlying Trap type describes vBlade power on and off
            operation Traps, enabling/disabling this SNMP trap as an Trap action
            is bound to the enabling/disabling of vBladePowerOffOpTrap,
            vBladePowerCycleTrap, vBladeResetOpTrap, and vBladeNMIOpTrap.

            Severity: 5"
    --#TYPE         "BladeFrame vBlade power on operation"
    --#SUMMARY      "%s"
    --#ARGUMENTS    { 5 }
    --#SEVERITY     INFORMATIONAL
    --#TIMEINDEX    99
    --#STATE        OPERATIONAL

        ::=     1424


vBladePowerOffOpTrap TRAP-TYPE
    ENTERPRISE  egenera
    VARIABLES {
                vBladeIndex,
                vBladePBladeIndex,
                vBladeFrameIndex,
                vBladeName,
                egeneraTrapSeverity,
                egeneraTrapMessage
            }
    DESCRIPTION
            "Encapsulates vBlade power off operation Trap.

            This trap is driven by 'vBlade <framename>/c<1|2> Hardware Operation
            Trap' Trap types.

            Since the underlying Trap type describes vBlade power on and off
            operation Traps, enabling/disabling this SNMP trap as an Trap action
            is bound to the enabling/disabling of vBladePowerOnOpTrap,
            vBladePowerCycleTrap, vBladeResetOpTrap, and vBladeNMIOpTrap.

            Severity: 5"
    --#TYPE         "BladeFrame vBlade power off operation"
    --#SUMMARY      "%s"
    --#ARGUMENTS    { 5}
    --#SEVERITY     INFORMATIONAL
    --#TIMEINDEX    99
    --#STATE        OPERATIONAL

        ::=     1425


vBladePowerCycleOpTrap TRAP-TYPE
    ENTERPRISE  egenera
    VARIABLES {
                vBladeIndex,
                vBladePBladeIndex,
                vBladeFrameIndex,
                vBladeName,
                egeneraTrapSeverity,
                egeneraTrapMessage
            }
    DESCRIPTION
            "Encapsulates vBlade power cycle operation Trap.

            This trap is driven by 'vBlade <framename>/c<1|2> Hardware Operation
            Trap' Trap types.

            Power cycle operations are currently not supported for vBlades.

            Since the underlying Trap type describes vBlade power on and off
            operation Traps, enabling/disabling this SNMP trap as an Trap action
            is bound to the enabling/disabling of vBladePowerOnOpTrap,
            vBladePowerCycleTrap, vBladeResetOpTrap, and vBladeNMIOpTrap.

            Severity: 5"
    --#TYPE         "BladeFrame vBlade power cycle operation"
    --#SUMMARY      "%s"
    --#ARGUMENTS    { 5 }
    --#SEVERITY     INFORMATIONAL
    --#TIMEINDEX    99
    --#STATE        OPERATIONAL

        ::=     1426


vBladeResetOpTrap TRAP-TYPE
    ENTERPRISE  egenera
    VARIABLES {
                vBladeIndex,
                vBladePBladeIndex,
                vBladeFrameIndex,
                vBladeName,
                egeneraTrapSeverity,
                egeneraTrapMessage
            }
    DESCRIPTION
            "Encapsulates vBlade reset operation Trap.

            This trap is driven by 'vBlade <framename>/c<1|2> Hardware Operation
            Trap' Trap types.

            Since the underlying Trap type describes vBlade power on and off
            operation Traps, enabling/disabling this SNMP trap as an Trap action
            is bound to the enabling/disabling of vBladePowerOnOpTrap,
            vBladePowerCycleTrap, vBladePowerCycleOpTrap, and vBladeNMIOpTrap.

            Severity: 5"
    --#TYPE         "BladeFrame vBlade reset operation"
    --#SUMMARY      "%s"
    --#ARGUMENTS    { 5 }
    --#SEVERITY     INFORMATIONAL
    --#TIMEINDEX    99
    --#STATE        OPERATIONAL

        ::=     1427


vBladeNMIOpTrap TRAP-TYPE
    ENTERPRISE  egenera
    VARIABLES {
                vBladeIndex,
                vBladePBladeIndex,
                vBladeFrameIndex,
                vBladeName,
                egeneraTrapSeverity,
                egeneraTrapMessage
            }
    DESCRIPTION
            "Encapsulates vBlade reset operation Trap.

            This trap is driven by 'vBlade <framename>/c<1|2> Hardware Operation
            Trap' Trap types.

            NMI operations are currently not supported for vBlades.

            Since the underlying Trap type describes vBlade power on and off
            operation Traps, enabling/disabling this SNMP trap as an Trap action
            is bound to the enabling/disabling of vBladePowerOnOpTrap,
            vBladePowerCycleTrap, vBladePowerCycleOpTrap, and vBladeResetOpTrap.

            Severity: 5"
    --#TYPE         "BladeFrame vBlade nmi operation"
    --#SUMMARY      "%s"
    --#ARGUMENTS    { 5 }
    --#SEVERITY     INFORMATIONAL
    --#TIMEINDEX    99
    --#STATE        OPERATIONAL

        ::=     1428



END
