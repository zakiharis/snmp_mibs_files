-- extracted from draft-shield-eos-capabilities-00.txt
-- at Wed Aug 28 06:10:43 2002

   EXTENDED-CAPABILITIES-TC DEFINITIONS ::= BEGIN

   IMPORTS
          MODULE-IDENTITY,
          enterprises             FROM SNMPv2-SMI
          TEXTUAL-CONVENTION      FROM SNMPv2-TC;

   extendedCapabilitiesList MODULE-IDENTITY
          LAST-UPDATED "200208170000Z"
          ORGANIZATION "University of Liverpool"
          CONTACT-INFO
              "Postal:    Dave Shield
                          Computer Science
                          University of Liverpool
                          Peach Street
                          Liverpool
                          L69 7ZF
                          United Kingdom

              E-Mail: D.T.Shield@csc.liv.ac.uk"
          DESCRIPTION
              "This MIB module defines a provisional textual
               convention for identifying extended SNMP capabilities."
          ::= { enterprises liv(1579) compsci(42) dts(1) eCap(3) 1 }

   ExtendedCapabilities ::= TEXTUAL-CONVENTION
      STATUS current
      DESCRIPTION
        "Provisional list of extended SNMP capabilities."
      SYNTAX BITS
        {
        oidDeltaCompression (0),
        oidPrefixCompression(1),
        fillHolesInTables   (2),
        dontColumnWrap      (3),
        errorString         (4)
        }

   END

--  
--    Copyright (C) The Internet Society (2002). All Rights Reserved. 
--     
--    This document and translations of it may be copied and furnished to 
--    others, and derivative works that comment on or otherwise explain it   
--    or assist in its implementation may be prepared, copied, published 
--    and distributed, in whole or in part, without restriction of any 
--    kind, provided that the above copyright notice and this paragraph 
--    are included on all such copies and derivative works.  However, this 
--    document itself may not be modified in any way, such as by removing 
--    the copyright notice or references to the Internet Society or other 
--    Internet organizations, except as needed for the purpose of 
--    developing Internet standards in which case the procedures for 
--    copyrights defined in the Internet Standards process must be 
--    followed, or as required to translate it into languages other than 
--    English. 
--     
--    The limited permissions granted above are perpetual and will not be 
--    revoked by the Internet Society or its successors or assigns. 
--     
--    This document and the information contained herein is provided on an 
--    "AS IS" basis and THE INTERNET SOCIETY AND THE INTERNET ENGINEERING 
--    TASK FORCE DISCLAIMS ALL WARRANTIES, EXPRESS OR IMPLIED, INCLUDING 
--    BUT NOT LIMITED TO ANY WARRANTY THAT THE USE OF THE INFORMATION 
--    HEREIN WILL NOT INFRINGE ANY RIGHTS OR ANY IMPLIED WARRANTIES OF 
--    MERCHANTABILITY OR FITNESS FOR A PARTICULAR PURPOSE. 
--  
-- 
-- 
-- This Internet Draft expires: February 2003
