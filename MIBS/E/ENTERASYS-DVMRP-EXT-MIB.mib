ENTERASYS-DVMRP-EXT-MIB DEFINITIONS ::= BEGIN

--  enterasys-dvmrp-ext-mib.txt
--
--  Part Number:
--
--

--  This module provides authoritative definitions for Enterasys 
--  Networks' DVMRP protocol.  This module extends the DVMRP-MIB.

--
--  This module will be extended, as needed.

--  Enterasys Networks reserves the right to make changes in this
--  specification and other information contained in this document
--  without prior notice.  The reader should consult Enterasys Networks
--  to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in 
--  connection with the management of Enterasys Networks products.

--  Copyright February, 2009 Enterasys Networks, Inc.

IMPORTS
    MODULE-IDENTITY, OBJECT-TYPE, Unsigned32, Gauge32
        FROM SNMPv2-SMI
    TEXTUAL-CONVENTION, TruthValue
        FROM SNMPv2-TC
    MODULE-COMPLIANCE, OBJECT-GROUP
        FROM SNMPv2-CONF
    dvmrpInterfaceEntry
        FROM DVMRP-MIB
    etsysModules
        FROM ENTERASYS-MIB-NAMES;

etsysDvmrpExtMIB MODULE-IDENTITY
    LAST-UPDATED "200902271929Z"  -- Fri Feb 27 19:29 UTC 2009
    ORGANIZATION "Enterasys Networks, Inc"
    CONTACT-INFO
        "Postal:  Enterasys Networks
                  50 Minuteman Rd.
                  Andover, MA 01810-1008
                  USA
         Phone:   +1 978 684 1000
         E-mail:  support@enterasys.com
         WWW:     http://www.enterasys.com"
    DESCRIPTION
        "This MIB module defines a portion of the SNMP MIB under
         the Enterasys Networks enterprise OID pertaining to 
         the DVMRP configuration.

         This MIB was designed to be used in conjunction with the
         DVMRP-MIB [THALER1] for configuring the DVMRP parameters."

    REVISION     "200902271929Z"  -- Fri Feb 27 19:29 UTC 2009
    DESCRIPTION  "The initial version of this MIB module"
    ::= { etsysModules 69 } 


-- Textual Conventions

-- -------------------------------------------------------------
-- Branches
-- -------------------------------------------------------------
etsysDvmrpExtObjects  OBJECT IDENTIFIER ::= { etsysDvmrpExtMIB 1 }

etsysDvmrpExtGlobals  OBJECT IDENTIFIER ::= { etsysDvmrpExtObjects 1 }
etsysDvmrpExtTables   OBJECT IDENTIFIER ::= { etsysDvmrpExtObjects 2 }

-- -------------------------------------------------------------
-- MIB Objects
-- -------------------------------------------------------------

--
-- Enterasys DVMRP Interface Table (extends dvmrpInterfaceTable)
--
etsysDvmrpExtIfTable OBJECT-TYPE
    SYNTAX       SEQUENCE OF EtsysDvmrpExtIfEntry
    MAX-ACCESS   not-accessible
    STATUS       current
    DESCRIPTION
        "This table provides addtional configuration objects that
        provide control for Enterasys DVMRP systems.  This table
        augments the dvmrpInterfaceTable."
    ::= { etsysDvmrpExtTables 1 }

etsysDvmrpExtIfEntry OBJECT-TYPE
    SYNTAX       EtsysDvmrpExtIfEntry
    MAX-ACCESS   not-accessible
    STATUS       current
    DESCRIPTION
        "An entry (conceptual row) in the etsysDvmrpExtIfTable."
    AUGMENTS     { dvmrpInterfaceEntry }
    ::= { etsysDvmrpExtIfTable 1 }

EtsysDvmrpExtIfEntry ::= SEQUENCE {
    etsysDvmrpExtIfAdminStatus               INTEGER,
    etsysDvmrpExtIfIfOperStatus              INTEGER,
    etsysDvmrpExtIfStubInterface             TruthValue,
    etsysDvmrpExtIfP2PNoHellos               TruthValue,
    etsysDvmrpExtIfHelloInterval             Unsigned32,
    etsysDvmrpExtIfHelloHoldtime             Unsigned32,
    etsysDvmrpExtIfReportInterval            Unsigned32
}

etsysDvmrpExtIfAdminStatus OBJECT-TYPE
    SYNTAX       INTEGER {
                     adminStatusUp(1),
                     adminStatusDown(2)
                 }
    MAX-ACCESS   read-create
    STATUS       current
    DESCRIPTION
        "The administrative state of DVMRP on this interface.

        When the status of this object is set to 'adminStatusDown', no
        DVMRP messages will be sent or received on this interface.  The
        TIB state pertaining to this interface is cleared, resulting in
        the removal of the associated routes from the MFIB.

        When the status of this object is set to 'adminStatusUp', normal
        DVMRP operation will proceed, and multicast state is stored in
        the TIB when it is learned."
    DEFVAL { adminStatusUp }
    ::= { etsysDvmrpExtIfEntry 1 }

etsysDvmrpExtIfIfOperStatus OBJECT-TYPE
    SYNTAX       INTEGER {
                     operStatusUp(1),          -- active
                     operStatusDown(2),        -- inactive
                     operStatusGoingUp(3),     -- activating
                     operStatusGoingDown(4),   -- deactivating
                     operStatusActFailed(5),   -- activation failed
                     operStatusFailed(8),      -- failed, will recover
                                               -- when possible
                     operStatusFailedPerm(10), -- operator intervention
                                               -- required
                     operStatusFailing(11)     -- failure in progress
                 }
    MAX-ACCESS   read-only
    STATUS       current
    DESCRIPTION
        "The current operational state of DVMRP on this interface."
    ::= { etsysDvmrpExtIfEntry 2 }

etsysDvmrpExtIfStubInterface OBJECT-TYPE
    SYNTAX       TruthValue
    MAX-ACCESS   read-create
    STATUS       current
    DESCRIPTION
        "Indicates whether this interface is a stub interface in
        relation to DVMRP.  If this object is set to 'true', no DVMRP
        packets are sent out this interface, and any received DVMRP
        packets are ignored.

        Setting this object to 'true' is a security measure for
        interfaces towards untrusted hosts.  To communicate with other
        DVMRP routers using this interface, this object must remain set
        to 'false'.

        Changing the value of this object while the interface is
        operationally active MAY cause the interface to be deactivated
        and then reactivated."
    DEFVAL { false }
    ::= { etsysDvmrpExtIfEntry 3 }

etsysDvmrpExtIfP2PNoHellos OBJECT-TYPE
    SYNTAX       TruthValue
    MAX-ACCESS   read-create
    STATUS       current
    DESCRIPTION
        "Indicates whether this interface is a point-to-point interface.

        If the value of this object is 'true', neighbors are not
        required to send DVMRP-Hello messages.  This is provided for
        backward-compatibility with some older implementations that do
        not send DVMRP-Hellos on point-to-point links.

        Changing the value of this object while the interface is
        operationally active MAY cause the interface to be deactivated
        and then reactivated."
    DEFVAL { false }
    ::= { etsysDvmrpExtIfEntry 4 }

etsysDvmrpExtIfHelloInterval OBJECT-TYPE
    SYNTAX       Unsigned32 (0..18000)
    UNITS        "seconds"
    MAX-ACCESS   read-create
    STATUS       current
    DESCRIPTION
        "The transmit frequency of DVMRP Hello messages on this
        interface.

        A value of 0 represents an infinite interval and periodic DVMRP
        Hello messages SHOULD not be sent on this interface."
    DEFVAL { 10 }
    ::= { etsysDvmrpExtIfEntry 5 }

etsysDvmrpExtIfHelloHoldtime OBJECT-TYPE
    SYNTAX       Unsigned32 (1..65535)
    UNITS        "seconds"
    MAX-ACCESS   read-create
    STATUS       current
    DESCRIPTION
        "The amount of time a DVMRP neighbor should consider this router
        operationally up."
    DEFVAL { 35 }
    ::= { etsysDvmrpExtIfEntry 6 }

etsysDvmrpExtIfReportInterval OBJECT-TYPE
    SYNTAX       Unsigned32 (0..18000)
    UNITS        "seconds"
    MAX-ACCESS   read-create
    STATUS       current
    DESCRIPTION
        "The transmit frequency of DVMRP Report messages on this
        interface.

        A value of 0 represents an infinite interval and periodic DVMRP
        Report messages SHOULD not be sent on this interface."
    DEFVAL { 60 }
    ::= { etsysDvmrpExtIfEntry 7 }


--
-- Enterasys DVMRP Tree Information Base (TIB) Manager Table
--
etsysDvmrpExtTibMgrTable OBJECT-TYPE
    SYNTAX       SEQUENCE OF EtsysDvmrpExtTibMgrEntry
    MAX-ACCESS   not-accessible
    STATUS       current
    DESCRIPTION
        "This table provides objects that manipulate the operation of
        the DVMRP Tree Information Base (TIB) Manager in order control
        the acceptable limits for the TIB."
    ::= { etsysDvmrpExtTables 2 }

etsysDvmrpExtTibMgrEntry OBJECT-TYPE
    SYNTAX       EtsysDvmrpExtTibMgrEntry
    MAX-ACCESS   not-accessible
    STATUS       current
    DESCRIPTION
        "An entry (conceptual row) in the etsysDvmrpExtTibMgrTable."
    INDEX        { etsysDvmrpExtTibMgrIndex }
    ::= { etsysDvmrpExtTibMgrTable 1 }

EtsysDvmrpExtTibMgrEntry ::= SEQUENCE {
    etsysDvmrpExtTibMgrIndex                 Unsigned32,
    etsysDvmrpExtTibMgrKeepalivePeriod       Unsigned32,
    etsysDvmrpExtTibMgrMetric                Unsigned32,
    etsysDvmrpExtTibMgrSGStateLimit          Unsigned32,
    etsysDvmrpExtTibMgrSGStateWarnThold      Unsigned32,
    etsysDvmrpExtTibMgrSGStateStored         Gauge32
}

etsysDvmrpExtTibMgrIndex OBJECT-TYPE
    SYNTAX       Unsigned32
    MAX-ACCESS   not-accessible
    STATUS       current
    DESCRIPTION
        "The DVMRP TIB Manager index."
    ::= { etsysDvmrpExtTibMgrEntry 1 }

etsysDvmrpExtTibMgrKeepalivePeriod OBJECT-TYPE
    SYNTAX       Unsigned32 (0..180)
    UNITS        "seconds"
    MAX-ACCESS   read-write
    STATUS       current
    DESCRIPTION
        "The amount of time to keep (S,G) state alive in the absence of
        DVMRP (S,G) Join messages or (S,G) data packets.

        Note:  Configuring different values for this object for
               different routers in the DVRMP domain may lead to
               incorrect protocol operation."
    DEFVAL { 120 }
    ::= { etsysDvmrpExtTibMgrEntry 2 }

etsysDvmrpExtTibMgrMetric OBJECT-TYPE
    SYNTAX       Unsigned32 (1..31)
    MAX-ACCESS   read-write
    STATUS       current
    DESCRIPTION
        "A global distance metric that is used to calculate distance
        vectors.  An interface SHOULD inherit this value if its default
        metric (dvmrpInterfaceMetric) has not been modified."
    DEFVAL { 1 }
    ::= { etsysDvmrpExtTibMgrEntry 3 }

etsysDvmrpExtTibMgrSGStateLimit OBJECT-TYPE
    SYNTAX       Unsigned32
    MAX-ACCESS   read-write
    STATUS       current
    DESCRIPTION
        "The maximum number of {source, group} pairs for which the DVMRP
         TIB Manager is allowed to store non-interface specific (S,G)
         state.  A value of zero means that there is no limit."
    DEFVAL { 0 }
    ::= { etsysDvmrpExtTibMgrEntry 4 }

etsysDvmrpExtTibMgrSGStateWarnThold OBJECT-TYPE
    SYNTAX       Unsigned32
    MAX-ACCESS   read-write
    STATUS       current
    DESCRIPTION
        "The DVMRP TIB Manager logs an exception if the number of
        {source, group} pairs for which it is storing non-interface
        specific (S,G) state exceeds this value.  A value of zero means
        that there is no warning threshold."
    DEFVAL { 0 }
    ::= { etsysDvmrpExtTibMgrEntry 5 }

etsysDvmrpExtTibMgrSGStateStored OBJECT-TYPE
    SYNTAX       Gauge32
    MAX-ACCESS   read-only
    STATUS       current
    DESCRIPTION
        "The number of {source, group} pairs for which the DVMRP TIB
        Manager is storing non-interface specific (S,G) state."
    ::= { etsysDvmrpExtTibMgrEntry 6 }


-- -------------------------------------------------------------
-- Conformance Information
-- -------------------------------------------------------------

etsysDvmrpExtConformance OBJECT IDENTIFIER ::= { etsysDvmrpExtMIB 2 }

etsysDvmrpExtGroups
    OBJECT IDENTIFIER ::= { etsysDvmrpExtConformance 1 }
etsysDvmrpExtCompliances
    OBJECT IDENTIFIER ::= { etsysDvmrpExtConformance 2 }

-- -------------------------------------------------------------
-- Units of conformance
-- -------------------------------------------------------------

etsysDvmrpExtIfGroup OBJECT-GROUP
    OBJECTS {
        etsysDvmrpExtIfAdminStatus,
        etsysDvmrpExtIfIfOperStatus,
        etsysDvmrpExtIfStubInterface,
        etsysDvmrpExtIfP2PNoHellos,
        etsysDvmrpExtIfHelloInterval,
        etsysDvmrpExtIfHelloHoldtime,
        etsysDvmrpExtIfReportInterval
    }
    STATUS       current
    DESCRIPTION
        "This group defines interface controls for Enterasys DVMRP
        systems."
    ::= { etsysDvmrpExtGroups 1 }

etsysDvmrpExtTibMgrGroup OBJECT-GROUP
    OBJECTS {
        etsysDvmrpExtTibMgrIndex,
        etsysDvmrpExtTibMgrKeepalivePeriod,
        etsysDvmrpExtTibMgrMetric,
        etsysDvmrpExtTibMgrSGStateLimit,
        etsysDvmrpExtTibMgrSGStateWarnThold,
        etsysDvmrpExtTibMgrSGStateStored
    }
    STATUS       current
    DESCRIPTION
        "This group defines the Tree Information Base (TIB) manager objects
        for Enterasys DVMRP systems."
    ::= { etsysDvmrpExtGroups 2 }

-- -------------------------------------------------------------
-- Compliance statements
-- -------------------------------------------------------------

etsysDvmrpExtCompliance MODULE-COMPLIANCE
    STATUS      current
    DESCRIPTION
        "The compliance statement for devices that support
        etsysDvmrpExt."

    MODULE
        MANDATORY-GROUPS {
            etsysDvmrpExtIfGroup,
            etsysDvmrpExtTibMgrGroup
        }
    ::= { etsysDvmrpExtCompliances 1 }

END
