-- ----------------------------------------------------------------------------
--                  HUAWEI MUSA Enterprise MIB   
--                                       MusaSys MIB 
--      Copyright (c) 1999-2002 HUA WEI TECH CO.,LTD,SHENZHEN.
--      All rights reserved.
--  Create date: 02-03-08
-- ----------------------------------------------------------------------------

HUAWEI-MUSA-MA5100-CONFMIB DEFINITIONS ::= BEGIN
IMPORTS
        IpAddress,Counter
                        FROM RFC1155-SMI
        OBJECT-TYPE
                        FROM RFC-1212                
        musa
                        FROM HUAWEI-MIB;
    
    DisplayString ::= OCTET STRING                  
    
    hwMa5100Mib     OBJECT IDENTIFIER ::= { musa 5 }
    hwMusaSysMib    OBJECT IDENTIFIER ::= { hwMa5100Mib 1 } 
    hwMusaEndOfMib  OBJECT IDENTIFIER ::= { hwMa5100Mib 100 } 



    -- -------------------------------------------------------------------------
    --  
    -- ------------------------------------------------------------------------- 
    hwMusaSlotGroup OBJECT IDENTIFIER ::= { hwMusaSysMib  6 }
    hwMusaFrame     OBJECT IDENTIFIER ::= { hwMusaSlotGroup 2 }
    hwMusaSlot      OBJECT IDENTIFIER ::= { hwMusaSlotGroup 3 }
    
    
   -- ----------------------------------------------------------------------------
   -- 
   -- ----------------------------------------------------------------------------
   hwMusaFrameNumber    OBJECT-TYPE
        SYNTAX      INTEGER
        ACCESS      read-only
        STATUS      mandatory
    DESCRIPTION  
    "Musa frame numbers."
    ::= { hwMusaFrame 1 }
    
    hwMusaFrameConfTable    OBJECT-TYPE
        SYNTAX      SEQUENCE OF HwMusaFrameConfEntry
        ACCESS      not-accessible
        STATUS      mandatory
    DESCRIPTION  
    "This table contains Musa Frame configuration parameters."
    ::= { hwMusaFrame 2 }

    hwMusaFrameConfEntry    OBJECT-TYPE
        SYNTAX         HwMusaFrameConfEntry
        ACCESS         not-accessible
        STATUS         mandatory
    DESCRIPTION
    "This list contains Musa Frame configuration parameters and status variables.
    ."
    INDEX { hwMusaShelfIndex,
            hwMusaFrameIndex }
    ::= { hwMusaFrameConfTable  1}
    
   HwMusaFrameConfEntry    ::= SEQUENCE  {
            hwMusaFrameIndex                    INTEGER
            }
            
   hwMusaFrameIndex OBJECT-TYPE
        SYNTAX     INTEGER
        ACCESS     not-accessible
        STATUS     mandatory
    DESCRIPTION
    "the Musa Frame number. 
    "
    ::= { hwMusaFrameConfEntry 1}
    
    hwMusaSlotConfTable    OBJECT-TYPE
        SYNTAX      SEQUENCE OF HwMusaSlotConfEntry
        ACCESS      not-accessible
        STATUS      mandatory
    DESCRIPTION  
    "This table contains Musa slot configuration
     parameters, one entry per Musa slot."
    ::= { hwMusaSlot 2 }

   hwMusaSlotConfEntry    OBJECT-TYPE
        SYNTAX         HwMusaSlotConfEntry
        ACCESS         not-accessible
        STATUS         mandatory
    DESCRIPTION
    "This list contains Musa slot configuration parameters and status variables.
    ."
    INDEX { 
            hwMusaFrameIndex,
            hwMusaSlotIndex }
    ::= { hwMusaSlotConfTable  1}
    
    HwMusaSlotConfEntry    ::= SEQUENCE  {
            hwMusaSlotIndex             INTEGER
            				}
            				
    hwMusaSlotIndex  OBJECT-TYPE
        SYNTAX     INTEGER(0..15)
        ACCESS     not-accessible
        STATUS     mandatory
    DESCRIPTION
    "the Musa slot number. "
    ::= { hwMusaSlotConfEntry 1 }            				
    
    -- ------------------------------------------------------------------------
    --  (adl-lan)
    -- ------------------------------------------------------------------------
    hwMusaRegionPvcConfTable    OBJECT-TYPE
        SYNTAX      SEQUENCE OF HwMusaRegionPvcConfEntry
        ACCESS      not-accessible
        STATUS      mandatory
    DESCRIPTION
    "Musa region pvc configuration table."
    ::= { hwMusaSysMib 15 }

   hwMusaRegionPvcConfEntry    OBJECT-TYPE
        SYNTAX         HwMusaRegionPvcConfEntry
        ACCESS         not-accessible
        STATUS         mandatory
    DESCRIPTION
    "This list contains Musa region pvc Configuration
     parameters and variables."
    INDEX       { 
                hwMusaFrameIndex, 
                hwMusaSlotIndex,
                hwMusaVlanId,
                hwMusaVlanIciIndex
                }
    ::= { hwMusaRegionPvcConfTable  1 }

   HwMusaRegionPvcConfEntry    ::= SEQUENCE  {
            hwMusaVlanId                INTEGER,
            hwMusaVlanIciIndex          INTEGER,
            hwMusaAdlFrameId            INTEGER,
            hwMusaAdlSlotId             INTEGER,
            hwMusaAdlPortId             INTEGER,
            hwMusaAdlVpi                INTEGER,
            hwMusaAdlVci                INTEGER,
            hwMusaToLanTrafficId        INTEGER,
            hwMusaFromLanTrafficId      INTEGER,
            hwMusaAdlPortOperat         INTEGER
          }

    hwMusaVlanId    OBJECT-TYPE
        SYNTAX          INTEGER(1..63)
        ACCESS          read-only
        STATUS          mandatory
    DESCRIPTION
    "Musa region VLan Id"
    ::= { hwMusaRegionPvcConfEntry  1 }   
    
    hwMusaVlanIciIndex    OBJECT-TYPE
        SYNTAX          INTEGER
        ACCESS          read-only
        STATUS          mandatory
    DESCRIPTION
    "Musa region VLanIciIndex."
    ::= { hwMusaRegionPvcConfEntry  2 }   
    
    hwMusaAdlFrameId    OBJECT-TYPE
        SYNTAX          INTEGER(0..4)
        ACCESS          read-write
        STATUS          mandatory
    DESCRIPTION
    "Musa region ADL frame ID."
    ::= { hwMusaRegionPvcConfEntry  4 }       
    
    hwMusaAdlSlotId    OBJECT-TYPE
        SYNTAX          INTEGER(1..15)
        ACCESS          read-write
        STATUS          mandatory
    DESCRIPTION
    "Musa region ADL slot ID."
    ::= { hwMusaRegionPvcConfEntry  5 }
    
    hwMusaAdlPortId    OBJECT-TYPE
        SYNTAX          INTEGER(0..15)
        ACCESS          read-write
        STATUS          mandatory
    DESCRIPTION
    "Musa region ADL port ID."
    ::= { hwMusaRegionPvcConfEntry  6 }                           

    hwMusaAdlVpi    OBJECT-TYPE
        SYNTAX          INTEGER(0..127)
        ACCESS          read-only
        STATUS          mandatory
    DESCRIPTION
    "Musa region VPI."
    ::= { hwMusaRegionPvcConfEntry  7 }       

    hwMusaAdlVci    OBJECT-TYPE
        SYNTAX          INTEGER(32..127)
        ACCESS          read-only
        STATUS          mandatory
    DESCRIPTION
    "Musa region VCI."
    ::= { hwMusaRegionPvcConfEntry  8 }       

    hwMusaToLanTrafficId    OBJECT-TYPE
        SYNTAX          INTEGER
        ACCESS          read-write
        STATUS          mandatory
    DESCRIPTION
    "Musa region to lan board traffic index."
    ::= { hwMusaRegionPvcConfEntry  9 }       

    hwMusaFromLanTrafficId    OBJECT-TYPE
        SYNTAX          INTEGER
        ACCESS          read-write
        STATUS          mandatory
    DESCRIPTION
    "Musa region from lan board traffic index."
    ::= { hwMusaRegionPvcConfEntry  10 }  

    hwMusaAdlPortOperat    OBJECT-TYPE
        SYNTAX          INTEGER
                        {
                        add(0),
                        del(1)
                        }
        ACCESS          read-write
        STATUS          mandatory
    DESCRIPTION
    "Musa region ADL Operat."
    ::= { hwMusaRegionPvcConfEntry  11 }   
    
   -- ******************************************************************
   -- 
   -- ******************************************************************

   hwMusaAllPvcConfTable   OBJECT-TYPE
       SYNTAX      SEQUENCE OF HwMusaAllPvcConfEntry
       ACCESS      not-accessible
       STATUS      mandatory
   DESCRIPTION
    "The  config talbe of all kinds of PVC."
   ::= { hwMusaSysMib 22 }
   
   hwMusaAllPvcConfEntry   OBJECT-TYPE
       SYNTAX      HwMusaAllPvcConfEntry
       ACCESS      not-accessible
       STATUS      mandatory
   DESCRIPTION
    "This lists config variables of all kinds of PVC."
   INDEX {  hwMusaTypeOfPvcPvpindex,
            hwMusaCidIndex }
   ::= { hwMusaAllPvcConfTable 1 }
   
   HwMusaAllPvcConfEntry   ::= SEQUENCE  {
             hwMusaCidIndex                  Counter,
             hwMusaSrcFrameId                INTEGER,
             hwMuasSrcSlotId                 INTEGER,
             hwMusaSrcPortVlanVccId          INTEGER,
             hwMusaSrcBoardVpi               INTEGER,
             hwMusaSrcBoardVci               INTEGER,
             hwMusaSrcUpcEpdPpd              INTEGER,
             hwMusaDestFrameId               INTEGER,
             hwMusaDestSlotId                INTEGER,
             hwMusaDestPortVlanVccId         INTEGER,
             hwMusaDestBoardVpi              INTEGER,
             hwMusaDestBoardVci              INTEGER,
             hwMusaDestUpcEpdPpd             INTEGER,
             hwMusaSrcToDestTraffic          INTEGER,
             hwMusaDestToSrcTraffic          INTEGER,
             hwMusaAllPvcOperater            INTEGER,
             hwMusaTypeOfPvcPvpindex         INTEGER,
             hwMusaPvcPvpState               INTEGER
             }
   
    hwMusaCidIndex    OBJECT-TYPE
        SYNTAX          Counter
        ACCESS          read-only
        STATUS          mandatory
    DESCRIPTION
    "The CID index."
    ::= { hwMusaAllPvcConfEntry  1 }
    
    hwMusaSrcFrameId    OBJECT-TYPE
        SYNTAX          INTEGER
        ACCESS          read-write
        STATUS          mandatory
    DESCRIPTION
    "The Frame id of source board."
    ::= { hwMusaAllPvcConfEntry  2 }
    
    hwMuasSrcSlotId    OBJECT-TYPE
        SYNTAX          INTEGER
        ACCESS          read-write
        STATUS          mandatory
    DESCRIPTION
    "The slot id of source board."
    ::= { hwMusaAllPvcConfEntry  3 }
    
    hwMusaSrcPortVlanVccId    OBJECT-TYPE
        SYNTAX          INTEGER
        ACCESS          read-write
        STATUS          mandatory
    DESCRIPTION
    "The Port/VlanID/VCC Index of source board."
    ::= { hwMusaAllPvcConfEntry  4 }
    
    hwMusaSrcBoardVpi    OBJECT-TYPE
        SYNTAX          INTEGER
        ACCESS          read-write
        STATUS          mandatory
    DESCRIPTION
    "Src board Port vpi Index."
    ::= { hwMusaAllPvcConfEntry  6 }   

    hwMusaSrcBoardVci    OBJECT-TYPE
        SYNTAX          INTEGER
        ACCESS          read-write
        STATUS          mandatory
    DESCRIPTION
    "Src board VCI Index."
    ::= { hwMusaAllPvcConfEntry  7 }
        
   hwMusaSrcUpcEpdPpd  OBJECT-TYPE
        SYNTAX  INTEGER
        ACCESS  read-write
        STATUS  mandatory
        DESCRIPTION
        "The flow control parameter of connection."
    ::= { hwMusaAllPvcConfEntry 16 } 
    
   hwMusaDestFrameId    OBJECT-TYPE
        SYNTAX          INTEGER
        ACCESS          read-write
        STATUS          mandatory
    DESCRIPTION
    "Destination frame Index."
    ::= { hwMusaAllPvcConfEntry  20 }
   
   hwMusaDestSlotId    OBJECT-TYPE
        SYNTAX          INTEGER
        ACCESS          read-write
        STATUS          mandatory
    DESCRIPTION
    "Destination slot Index."
    ::= { hwMusaAllPvcConfEntry  21 }
    
   hwMusaDestPortVlanVccId    OBJECT-TYPE
        SYNTAX          INTEGER
        ACCESS          read-write
        STATUS          mandatory
    DESCRIPTION
    "Destination port Index."
    ::= { hwMusaAllPvcConfEntry  22 }
    
    hwMusaDestBoardVpi    OBJECT-TYPE
        SYNTAX          INTEGER
        ACCESS          read-write
        STATUS          mandatory
    DESCRIPTION
    "Destination Port vpi Index."
    ::= { hwMusaAllPvcConfEntry  24 }   

    hwMusaDestBoardVci    OBJECT-TYPE
        SYNTAX          INTEGER
        ACCESS          read-write
        STATUS          mandatory
    DESCRIPTION
    "Destination VCI Index."
    ::= { hwMusaAllPvcConfEntry  25 }
    
   hwMusaDestUpcEpdPpd    OBJECT-TYPE
        SYNTAX          INTEGER
        ACCESS          read-write
        STATUS          mandatory
    DESCRIPTION
    "The flow control parameter of connection."
   ::= { hwMusaAllPvcConfEntry  34 }
   
   hwMusaSrcToDestTraffic  OBJECT-TYPE
        SYNTAX  INTEGER
        ACCESS  read-write
        STATUS  mandatory
        DESCRIPTION
        "The source board to destination traffic."
    ::= { hwMusaAllPvcConfEntry 38 }
    
   hwMusaDestToSrcTraffic  OBJECT-TYPE
        SYNTAX  INTEGER
        ACCESS  read-write
        STATUS  mandatory
        DESCRIPTION
        "The destination to source board traffic."
    ::= { hwMusaAllPvcConfEntry 39 }
       
   hwMusaAllPvcOperater    OBJECT-TYPE
        SYNTAX          INTEGER
                        {
                        add(0),
                        del(1)
                        }
        ACCESS          read-write
        STATUS          mandatory
    DESCRIPTION
    "Add or delete PVC."
    ::= { hwMusaAllPvcConfEntry  40}

   hwMusaTypeOfPvcPvpindex    OBJECT-TYPE
       SYNTAX          INTEGER
                        {
                        pvc(0),
                        pvp(1)
                        }
        ACCESS          read-write
        STATUS          mandatory
    DESCRIPTION
    "Identified type of Pvc or Pvp"
    ::= { hwMusaAllPvcConfEntry  41}
    
    hwMusaPvcPvpState  OBJECT-TYPE
       SYNTAX          INTEGER
                        {
                        normal(1),
                        invalid(2),
                        delete(3) 
                        }
        ACCESS          read-only
        STATUS          mandatory
    DESCRIPTION
    "Pvc or Pvp  state "
    ::= { hwMusaAllPvcConfEntry  42}
    
    
    hwMusaAdlb             OBJECT IDENTIFIER ::= { hwMa5100Mib 6 }
    hwMusaAdlbBoard        OBJECT IDENTIFIER ::= { hwMusaAdlb 1 }
    hwMusaAdlbChipset      OBJECT IDENTIFIER ::= { hwMusaAdlb 2 }
    hwMusaAdlbConf         OBJECT IDENTIFIER ::= { hwMusaAdlb 3 }
    hwMusaAdlbPfm          OBJECT IDENTIFIER ::= { hwMusaAdlb 4 }
    hwMusaAdlbTest         OBJECT IDENTIFIER ::= { hwMusaAdlb 5 }

    
    
     
     
    hwMusaAdlbBoardInfoTable    OBJECT-TYPE
        SYNTAX      SEQUENCE OF HwMusaAdlbBoardInfoEntry
        ACCESS      not-accessible
        STATUS      mandatory
    DESCRIPTION
    "Musa adlb board description table."
    ::= { hwMusaAdlbBoard 1 }

   hwMusaAdlbBoardInfoEntry    OBJECT-TYPE
        SYNTAX         HwMusaAdlbBoardInfoEntry
        ACCESS         not-accessible
        STATUS         mandatory
    DESCRIPTION
    "This list contains Musa adlb board description variables."
    INDEX { hwMusaFrameIndex,
            hwMusaSlotIndex }
    ::= { hwMusaAdlbBoardInfoTable  1 }

   HwMusaAdlbBoardInfoEntry    ::= SEQUENCE  {
            adlbProductId      		INTEGER,
            adlbCustomId      		INTEGER,
            adlbAtucRomSwVer   		DisplayString,
            adlbAtucRomSwBuildDate  DisplayString,
            adlbAtucOamSwVer  		DisplayString,
            adlbAtucOamSwBuildDate	DisplayString,
  			adlbByDiagCodeVer 		DisplayString,
    		adlbByModemCodeVer		DisplayString,
            adlbAtucVendorId        INTEGER,
            adlbAtucVersionNo       INTEGER,
            adlbItuCountryCode     	INTEGER,
            adlbItuProviderCode    	DisplayString
            }            
        
    adlbProductId  			OBJECT-TYPE
        SYNTAX  INTEGER
        ACCESS  read-only
        STATUS  mandatory
        DESCRIPTION ""
    ::= { hwMusaAdlbBoardInfoEntry 1 }

    adlbCustomId      		OBJECT-TYPE
        SYNTAX  INTEGER		{
                            unknown(0), 
                            isdn(1),
                            pots(2)
                       }
        ACCESS  read-only
        STATUS  mandatory
        DESCRIPTION ""
    ::= { hwMusaAdlbBoardInfoEntry 2 }
    
    adlbAtucRomSwVer   		OBJECT-TYPE
        SYNTAX  DisplayString
        ACCESS  read-only
        STATUS  mandatory
        DESCRIPTION ""
    ::= { hwMusaAdlbBoardInfoEntry 3 }
    
    adlbAtucRomSwBuildDate  OBJECT-TYPE
        SYNTAX  DisplayString
        ACCESS  read-only
        STATUS  mandatory
        DESCRIPTION ""
    ::= { hwMusaAdlbBoardInfoEntry 4 }
    
    adlbAtucOamSwVer  		OBJECT-TYPE
        SYNTAX  DisplayString
        ACCESS  read-only
        STATUS  mandatory
        DESCRIPTION ""
    ::= { hwMusaAdlbBoardInfoEntry 5 }
    
    adlbAtucOamSwBuildDate	OBJECT-TYPE
        SYNTAX  DisplayString
        ACCESS  read-only
        STATUS  mandatory
        DESCRIPTION ""
    ::= { hwMusaAdlbBoardInfoEntry 6 }
    
	adlbByDiagCodeVer 		OBJECT-TYPE
        SYNTAX  DisplayString
        ACCESS  read-only
        STATUS  mandatory
        DESCRIPTION ""
    ::= { hwMusaAdlbBoardInfoEntry 7 }
    
	adlbByModemCodeVer		OBJECT-TYPE
        SYNTAX  DisplayString
        ACCESS  read-only
        STATUS  mandatory
        DESCRIPTION ""
    ::= { hwMusaAdlbBoardInfoEntry 8 }
    
    adlbAtucVendorId        OBJECT-TYPE
        SYNTAX  INTEGER
        ACCESS  read-only
        STATUS  mandatory
        DESCRIPTION ""
    ::= { hwMusaAdlbBoardInfoEntry 9 }
    
    adlbAtucVersionNo       OBJECT-TYPE
        SYNTAX  INTEGER
        ACCESS  read-only
        STATUS  mandatory
        DESCRIPTION ""
    ::= { hwMusaAdlbBoardInfoEntry 10 }
    
    adlbItuCountryCode     	OBJECT-TYPE
        SYNTAX  INTEGER
        ACCESS  read-only
        STATUS  mandatory
        DESCRIPTION ""
    ::= { hwMusaAdlbBoardInfoEntry 11 }
    
    adlbItuProviderCode        	OBJECT-TYPE
        SYNTAX  DisplayString
        ACCESS  read-only
        STATUS  mandatory
        DESCRIPTION ""
    ::= { hwMusaAdlbBoardInfoEntry 12 }
    
   

    hwMusaAdlbChipsetMtTable    OBJECT-TYPE
        SYNTAX      SEQUENCE OF HwMusaAdlbChipsetMtEntry
        ACCESS      not-accessible
        STATUS      mandatory
    DESCRIPTION
    "Musa adlb board description table."
    ::= { hwMusaAdlbChipset 1 }

   hwMusaAdlbChipsetMtEntry    OBJECT-TYPE
        SYNTAX         HwMusaAdlbChipsetMtEntry
        ACCESS         not-accessible
        STATUS         mandatory
    DESCRIPTION
    "This list contains Musa chipset maintenance variables."
    INDEX { hwMusaFrameIndex,
            hwMusaSlotIndex,
            adlbChipsetIndex }
    ::= { hwMusaAdlbChipsetMtTable  1 }

   HwMusaAdlbChipsetMtEntry    ::= SEQUENCE  {
            adlbChipsetIndex	INTEGER,
            adlbChipsetOper     INTEGER
            }            
        
    adlbChipsetIndex			OBJECT-TYPE
        SYNTAX  INTEGER ( 0..3 )
        ACCESS  not-accessible
        STATUS  mandatory
        DESCRIPTION ""
    ::= { hwMusaAdlbChipsetMtEntry 1 }
	
	adlbChipsetOper				OBJECT-TYPE
        SYNTAX  INTEGER
        ACCESS  write-only
        STATUS  mandatory
        DESCRIPTION ""
    ::= { hwMusaAdlbChipsetMtEntry 2 }

    

    hwMusaAdlbPortDeviceTable    OBJECT-TYPE
        SYNTAX      SEQUENCE OF HwMusaAdlbPortDeviceEntry
        ACCESS      not-accessible
        STATUS      mandatory
    DESCRIPTION
    "Musa adlb port remote device table."
    ::= { hwMusaAdlbConf 1 }

   hwMusaAdlbPortDeviceEntry    OBJECT-TYPE
        SYNTAX         HwMusaAdlbPortDeviceEntry
        ACCESS         not-accessible
        STATUS         mandatory
    DESCRIPTION
    "This list contains Musa adlb port remote device variables."
    INDEX { hwMusaFrameIndex,
            hwMusaSlotIndex,
            adlbPortIndex }
    ::= { hwMusaAdlbPortDeviceTable  1 }

   HwMusaAdlbPortDeviceEntry    ::= SEQUENCE  {
            adlbPortIndex			INTEGER,
            adlbAturVendorId   		INTEGER,
            adlbAturVersion			INTEGER,
            adlbAturCountryCode		INTEGER,
	    	adlbAturProviderCode	INTEGER,
    		adlbAturAdslCapability	INTEGER
            }            
        
    adlbPortIndex			OBJECT-TYPE
        SYNTAX  INTEGER ( 0..15 )
        ACCESS  not-accessible
        STATUS  mandatory
        DESCRIPTION ""
    ::= { hwMusaAdlbPortDeviceEntry 1 }
	
    adlbAturVendorId   		OBJECT-TYPE
        SYNTAX  INTEGER
        ACCESS  read-only
        STATUS  mandatory
        DESCRIPTION ""
    ::= { hwMusaAdlbPortDeviceEntry 2 }
    
    adlbAturVersion			OBJECT-TYPE
        SYNTAX  INTEGER
        ACCESS  read-only
        STATUS  mandatory
        DESCRIPTION ""
    ::= { hwMusaAdlbPortDeviceEntry 3 }
    
    adlbAturCountryCode		OBJECT-TYPE
        SYNTAX  INTEGER
        ACCESS  read-only
        STATUS  mandatory
        DESCRIPTION ""
    ::= { hwMusaAdlbPortDeviceEntry 4 }
    
	adlbAturProviderCode	OBJECT-TYPE
        SYNTAX  INTEGER
        ACCESS  read-only
        STATUS  mandatory
        DESCRIPTION ""
    ::= { hwMusaAdlbPortDeviceEntry 5 }
    
	adlbAturAdslCapability	OBJECT-TYPE
        SYNTAX  INTEGER
        ACCESS  read-only
        STATUS  mandatory
        DESCRIPTION
        " 0:not support 1:support;
	       bit0--T1.413 issue2
	       bit2--g992.1 POTS non-overlapped spectrum
	       bit3--g992.1 POTS overlapped specturm
	       bit4--g992.1 ISDN non-overlapped spectrum
	       bit5--g992.1 ISDN overlapped spectrum
	       bit6--g992.1 operation in conjunction with TCM-ISDN non-overlapped spectrum
	       bit7--g992.1 operation in conjunction with TCM-ISDN overlapped spectrum
	       bit8--g992.2 POTS non-overlapped spectrum
	       bit9--g992.2 POTS overlapped specturm
	       bit10--g992.2 operation in conjunction with TCM-ISDN non-overlapped spectrum
	       bit11--g992.2 operation in conjunction with TCM-ISDN overlapped spectrum "
    ::= { hwMusaAdlbPortDeviceEntry 6 }
    
   

    hwMusaAdlbPortTable    OBJECT-TYPE
        SYNTAX      SEQUENCE OF HwMusaAdlbPortEntry
        ACCESS      not-accessible
        STATUS      mandatory
    DESCRIPTION
    "Musa adlb port table."
    ::= { hwMusaAdlbConf 2 }

   hwMusaAdlbPortEntry    OBJECT-TYPE
        SYNTAX         HwMusaAdlbPortEntry
        ACCESS         not-accessible
        STATUS         mandatory
    DESCRIPTION
    "This list contains Musa adlb port query and operation variables."
    INDEX { hwMusaFrameIndex,
            hwMusaSlotIndex,
            adlbPortIndex }
    ::= { hwMusaAdlbPortTable  1 }

   HwMusaAdlbPortEntry    ::= SEQUENCE  {
            adlbPortState   		INTEGER,
            adlbPortTrainStandard  	INTEGER,
            adlbPortOper	   		INTEGER,
            adlbPortTemplateId      INTEGER,
            adlbPortTxCell      INTEGER,
            adlbPortRxCell      INTEGER
            }            
        
    adlbPortState   		OBJECT-TYPE
        SYNTAX  INTEGER     {
                            active(0), 
                            deactive(1),
                            bad(2), 
                            activating(3),
                            deactivating(4),
                            block(5),
                            unblock(6),
                            other(255)
                       }

        ACCESS  read-only
        STATUS  mandatory
        DESCRIPTION ""
    ::= { hwMusaAdlbPortEntry 1 }
	
    adlbPortTrainStandard  	OBJECT-TYPE
        SYNTAX  INTEGER	{ none(0), dmt(1), glite(2), t1413(3) }
        ACCESS  read-only
        STATUS  mandatory
        DESCRIPTION ""
    ::= { hwMusaAdlbPortEntry 2 }
    
    adlbPortOper	   		OBJECT-TYPE
        SYNTAX  INTEGER		{
                            deact(0), 
                            block(1),
                            unblock(2),
                            clearCellStat(3)
                       }
        ACCESS  write-only
        STATUS  mandatory
        DESCRIPTION ""
    ::= { hwMusaAdlbPortEntry 3 }

    adlbPortTemplateId	   		OBJECT-TYPE
        SYNTAX  INTEGER(1..99)
        ACCESS  read-write
        STATUS  mandatory
        DESCRIPTION ""
    ::= { hwMusaAdlbPortEntry 4 }

    adlbPortTxCell	   		OBJECT-TYPE
        SYNTAX  INTEGER
        ACCESS  read-only
        STATUS  mandatory
        DESCRIPTION
        " ADL port Transfer cells. "
    ::= { hwMusaAdlbPortEntry 5 }

    adlbPortRxCell	   		OBJECT-TYPE
        SYNTAX  INTEGER
        ACCESS  read-only
        STATUS  mandatory
        DESCRIPTION
        " ADL port Receive cells. "
    ::= { hwMusaAdlbPortEntry 6 }

    hwMusaAdlbPortActTable    OBJECT-TYPE
        SYNTAX      SEQUENCE OF HwMusaAdlbPortActEntry
        ACCESS      not-accessible
        STATUS      mandatory
    DESCRIPTION
    "Musa adlb activate port table."
    ::= { hwMusaAdlbConf 3 }

   hwMusaAdlbPortActEntry    OBJECT-TYPE
        SYNTAX         HwMusaAdlbPortActEntry
        ACCESS         not-accessible
        STATUS         mandatory
    DESCRIPTION
    "This list contains activate adlb port variables."
    INDEX { adlbPortTemplateId }
    ::= { hwMusaAdlbPortActTable  1 }

   HwMusaAdlbPortActEntry    ::= SEQUENCE  {
		    adlbIfConfigSetToDefault	INTEGER, 
		    adlbServiceType 			INTEGER,
		    adlbConfigOrAutoDelay   	INTEGER,
		    adlbDelayOrDepth   			INTEGER,
		    adlbFrameMode   			INTEGER,
		    adlbNTROptionEnable    		INTEGER,
		    adlbTrellisModeEnable     	INTEGER,
		    adlbEocClearChannelMode    	INTEGER,
			adlbDsSingleOrDual			INTEGER,
			adlbUsSingleOrDual			INTEGER,
			adlbFastOrInterleave		INTEGER,
		    adlbDsTargetMargin 			INTEGER,
		    adlbDsMinMargin 			INTEGER,
		    adlbUsTargetMargin  		INTEGER,
		    adlbUsMinMargin     		INTEGER,
		    adlbMaxDsRateC0     		INTEGER,
		    adlbMinDsRateC0     		INTEGER,
		    adlbMaxUsRateC0     		INTEGER,
		    adlbMinUsRateC0     		INTEGER,
		    adlbUsMsOrDmtNumber			INTEGER,
		    adlbDsMsOrDmtNumber  		INTEGER,
		    adlbUsExcessRatio  			INTEGER,
		    adlbDsExcessRatio  			INTEGER,
		    adlbMaxDsRateC1  			INTEGER,
		    adlbMinDsRateC1  			INTEGER,
		    adlbMaxUsRateC1  			INTEGER,
		    adlbMinUsRateC1   			INTEGER,
		    adlbTemplateOperate			INTEGER
            }
        
    adlbIfConfigSetToDefault	OBJECT-TYPE
        SYNTAX  INTEGER	{ manual(0), 
                          default(1) }
        ACCESS  read-write
        STATUS  mandatory
        DESCRIPTION ""
    ::= { hwMusaAdlbPortActEntry 1 }
                
    adlbServiceType 			OBJECT-TYPE
        SYNTAX  INTEGER	{ all(0), 
                          fullrate(1),
                          glite(2),
                          t1413(3),
                          g9922(4),
                          ghs(5) }
        ACCESS  read-write
        STATUS  mandatory
        DESCRIPTION
        " ( 0:All (G992.1, G992.2, T1.413)(Default)
      		1:Full rate(G992.1 or T1.413)
      		2:G992.2(g.lite) only
      		3:T1.413 only
      		4:G992.2(g.dmt) only
      		5:g.hs (G992.1 and G992.2 with priority to G992.1) ) "
    ::= { hwMusaAdlbPortActEntry 2 }
                
    adlbConfigOrAutoDelay   	OBJECT-TYPE
        SYNTAX  INTEGER	{ manual(0), 
                          auto(1) }
        ACCESS  read-write
        STATUS  mandatory
        DESCRIPTION ""
    ::= { hwMusaAdlbPortActEntry 3 }
                
    adlbDelayOrDepth   			OBJECT-TYPE
        SYNTAX  INTEGER	{ depth(0), 
                          ms(1) }
        ACCESS  read-write
        STATUS  mandatory
        DESCRIPTION ""
    ::= { hwMusaAdlbPortActEntry 4 }
    
    adlbFrameMode   			OBJECT-TYPE
        SYNTAX  INTEGER	{ mode0(0), 
                          mode1(1),
                          mode2(2),
                          mode3(3) }
        ACCESS  read-write
        STATUS  mandatory
        DESCRIPTION
        " ( 0-Framing mode 0, Full overhead asynchronous mode
            1-Framing mode 1, Full overhead synchronous mode
            2-Framing mode 2, Dual latency with reduced overhead
            3-Framing mode 3(Default), Single latency with reduced overhead ) "
    ::= { hwMusaAdlbPortActEntry 5 }
                
    adlbNTROptionEnable    		OBJECT-TYPE
        SYNTAX  INTEGER	{ disable(0), 
                          enable(1) }
        ACCESS  read-write
        STATUS  mandatory
        DESCRIPTION ""
    ::= { hwMusaAdlbPortActEntry 6 }
                
    adlbTrellisModeEnable     	OBJECT-TYPE
        SYNTAX  INTEGER	{ disable(0), 
                          enable(1) }
        ACCESS  read-write
        STATUS  mandatory
        DESCRIPTION ""
    ::= { hwMusaAdlbPortActEntry 7 }
                
    adlbEocClearChannelMode    	OBJECT-TYPE
        SYNTAX  INTEGER	{ transparent(0), 
                          hdlcframing(1) }
        ACCESS  read-write
        STATUS  mandatory
        DESCRIPTION ""
    ::= { hwMusaAdlbPortActEntry 8 }
                
	adlbDsSingleOrDual			OBJECT-TYPE
        SYNTAX  INTEGER	{ single(1), 
                          dual(3) }
        ACCESS  read-write
        STATUS  mandatory
        DESCRIPTION
        " 
		  ( 1-single DS channel(AS0) (Default)
			3-dual DS channel(AS0 and AS1/LS0ds) ) "
    ::= { hwMusaAdlbPortActEntry 9 }
    
	adlbUsSingleOrDual			OBJECT-TYPE
        SYNTAX  INTEGER	{ single(1), 
                          dual(3) }
        ACCESS  read-write
        STATUS  mandatory
        DESCRIPTION
        " 
    	  ( 1-single US channel(LS0us) (Default)
			3-dual US channel(LS0us and LS1) ) "
    ::= { hwMusaAdlbPortActEntry 10 }
    
	adlbFastOrInterleave		OBJECT-TYPE
        SYNTAX  INTEGER	{ interleaved(2), 
                          fast(3) }
        ACCESS  read-write
        STATUS  mandatory
        DESCRIPTION
        " .
			( 2-Interleaved(default), 3-Fast) "
    ::= { hwMusaAdlbPortActEntry 11 }
    
	adlbDsTargetMargin 			OBJECT-TYPE
        SYNTAX  INTEGER	( 0..15 )
        ACCESS  read-write
        STATUS  mandatory
        DESCRIPTION
        "  (0-15dB) Default=6dB "
    ::= { hwMusaAdlbPortActEntry 13 }
                
    adlbDsMinMargin 			OBJECT-TYPE
        SYNTAX  INTEGER	
        ACCESS  read-write
        STATUS  mandatory
        DESCRIPTION
        "  Default=0dB  "
    ::= { hwMusaAdlbPortActEntry 14 }
                
    adlbUsTargetMargin  		OBJECT-TYPE
        SYNTAX  INTEGER	( 0..15 )
        ACCESS  read-write
        STATUS  mandatory
        DESCRIPTION
        "  (0-15dB) Default=6dB "
    ::= { hwMusaAdlbPortActEntry 15 }
                
    adlbUsMinMargin     		OBJECT-TYPE
        SYNTAX  INTEGER	
        ACCESS  read-write
        STATUS  mandatory
        DESCRIPTION
        "  Default=0dB  "
    ::= { hwMusaAdlbPortActEntry 16 }

    adlbMaxDsRateC0     		OBJECT-TYPE
        SYNTAX  INTEGER	
        ACCESS  read-write
        STATUS  mandatory
        DESCRIPTION
        " channel0
          ( :32kbits/sec 
            single channel,full rate, Default=255 -> 8.160Mbps 
            single channel,lite rate, Default=48 -> 1.536Mbps
            dual channel,full rate,Default=235 -> 7.520Mbps ) "
    ::= { hwMusaAdlbPortActEntry 17 }
                
    adlbMinDsRateC0     		OBJECT-TYPE
        SYNTAX  INTEGER	
        ACCESS  read-write
        STATUS  mandatory
        DESCRIPTION
        " channel0
          ( :32kbits/sec
            single channel,full rate, Default=1 -> 32Kbps 
            single channel,lite rate, Default=2 -> 64Kbps
            dual channel,full rate,Default=1 -> 32Kbps ) "
    ::= { hwMusaAdlbPortActEntry 18 }
                
    adlbMaxUsRateC0     		OBJECT-TYPE
        SYNTAX  INTEGER	
        ACCESS  read-write
        STATUS  mandatory
        DESCRIPTION
        " 
          ( :32kbits/sec
            Full rate, Default=28 -> 896Kbps 
            Lite     , Default=16 -> 512Kbps 
            single channel,full rate, Default=28 -> 896Kbps 
            single channel,lite rate, Default=16 -> 512Kbps 
            dual channel, Default=24 -> 768Kbps ) "
	::= { hwMusaAdlbPortActEntry 19 }
                
    adlbMinUsRateC0     		OBJECT-TYPE
        SYNTAX  INTEGER	
        ACCESS  read-write
        STATUS  mandatory
        DESCRIPTION
        " 
          ( :32kbits/sec
            single channel,full rate, Default=1 -> 32Kbps 
            single channel,lite rate, Default=1 -> 32Kbps
            dual channel, Default=1 -> 32Kbps ) "
	::= { hwMusaAdlbPortActEntry 20 }
                
    adlbUsMsOrDmtNumber			OBJECT-TYPE
        SYNTAX  INTEGER	
        ACCESS  read-write
        STATUS  mandatory
        DESCRIPTION
        "  ((5-255ms) Default=16ms,
          ,(2,4,8,16,32,64,128) Default=64) "
    ::= { hwMusaAdlbPortActEntry 21 }
                
    adlbDsMsOrDmtNumber  		OBJECT-TYPE
        SYNTAX  INTEGER	
        ACCESS  read-write
        STATUS  mandatory
        DESCRIPTION
        " ((5-255ms) Default=16ms,
          ,(2,4,8,16,32,64,128) Default=64) "
    ::= { hwMusaAdlbPortActEntry 22 }
                
    adlbUsExcessRatio  			OBJECT-TYPE
        SYNTAX  INTEGER	
        ACCESS  read-write
        STATUS  mandatory
        DESCRIPTION
        " 
          ( Single channel default=100
    		Dual channel default=50) "
    ::= { hwMusaAdlbPortActEntry 23 }
                
    adlbDsExcessRatio  			OBJECT-TYPE
        SYNTAX  INTEGER	
        ACCESS  read-write
        STATUS  mandatory
        DESCRIPTION
        " 
          ( Single channel default=100
    		Dual channel default=50) "
    ::= { hwMusaAdlbPortActEntry 24 }
                
    adlbMaxDsRateC1  			OBJECT-TYPE
        SYNTAX  INTEGER	
        ACCESS  read-write
        STATUS  mandatory
        DESCRIPTION
        "  	 channel 
        	:32kbits/sec
			dual channel default=20 -> 640Kbps "
    ::= { hwMusaAdlbPortActEntry 25 }
                
    adlbMinDsRateC1  			OBJECT-TYPE
        SYNTAX  INTEGER	
        ACCESS  read-write
        STATUS  mandatory
        DESCRIPTION
        "  	 channel 
        	:32kbits/sec
			dual channel default=20 -> 640Kbps "
    ::= { hwMusaAdlbPortActEntry 26 }
                
    adlbMaxUsRateC1  			OBJECT-TYPE
        SYNTAX  INTEGER	
        ACCESS  read-write
        STATUS  mandatory
        DESCRIPTION
        "  	 channel 
        	:32kbits/sec
			dual channel default=4 -> 128Kbps "
    ::= { hwMusaAdlbPortActEntry 27 }
                
    adlbMinUsRateC1   			OBJECT-TYPE
        SYNTAX  INTEGER	
        ACCESS  read-write
        STATUS  mandatory
        DESCRIPTION
        "  	 channel 
        	:32kbits/sec
			dual channel default=4 -> 128Kbps "
    ::= { hwMusaAdlbPortActEntry 28 }

    adlbTemplateOperate   			OBJECT-TYPE
        SYNTAX  INTEGER{add(0),
                        del(1)
                       }	
        ACCESS  read-write
        STATUS  mandatory
        DESCRIPTION
        "  	template add/del operate. "
    ::= { hwMusaAdlbPortActEntry 29 }


    hwMusaAdlbPortPfmThresTable    OBJECT-TYPE
        SYNTAX      SEQUENCE OF HwMusaAdlbPortPfmThresEntry
        ACCESS      not-accessible
        STATUS      mandatory
    DESCRIPTION
    "Musa adlb port performance statistic threshold table."
    ::= { hwMusaAdlbConf 4 }

   hwMusaAdlbPortPfmThresEntry    OBJECT-TYPE
        SYNTAX         HwMusaAdlbPortPfmThresEntry
        ACCESS         not-accessible
        STATUS         mandatory
    DESCRIPTION
    "This list contains adlb port performance statistic threshold variables."
    INDEX { hwMusaFrameIndex,
            hwMusaSlotIndex,
            adlbPortIndex }
    ::= { hwMusaAdlbPortPfmThresTable  1 }

   HwMusaAdlbPortPfmThresEntry    ::= SEQUENCE  {
		    adlbPortPfmThresId1			INTEGER, 
		    adlbPortPfmThresValue1		INTEGER,
		    adlbPortPfmThresId2			INTEGER, 
		    adlbPortPfmThresValue2		INTEGER,
		    adlbPortPfmThresId3			INTEGER, 
		    adlbPortPfmThresValue3		INTEGER,
		    adlbPortPfmThresId4			INTEGER, 
		    adlbPortPfmThresValue4		INTEGER,
		    adlbPortPfmThresId5			INTEGER, 
		    adlbPortPfmThresValue5		INTEGER,
		    adlbPortPfmThresId6			INTEGER, 
		    adlbPortPfmThresValue6		INTEGER,
		    adlbPortPfmThresId7			INTEGER, 
		    adlbPortPfmThresValue7		INTEGER,
		    adlbPortPfmThresId8			INTEGER, 
		    adlbPortPfmThresValue8		INTEGER
            }
        
    adlbPortPfmThresId1					OBJECT-TYPE
        SYNTAX  INTEGER	(0..30)
        ACCESS  read-write
        STATUS  mandatory
        DESCRIPTION ""
    ::= { hwMusaAdlbPortPfmThresEntry 1 }

	adlbPortPfmThresValue1				OBJECT-TYPE
        SYNTAX  INTEGER
        ACCESS  read-write
        STATUS  mandatory
        DESCRIPTION ""
    ::= { hwMusaAdlbPortPfmThresEntry 2 }
    
    adlbPortPfmThresId2					OBJECT-TYPE
        SYNTAX  INTEGER	(0..30)
        ACCESS  read-write
        STATUS  mandatory
        DESCRIPTION ""
    ::= { hwMusaAdlbPortPfmThresEntry 3 }

	adlbPortPfmThresValue2				OBJECT-TYPE
        SYNTAX  INTEGER
        ACCESS  read-write
        STATUS  mandatory
        DESCRIPTION ""
    ::= { hwMusaAdlbPortPfmThresEntry 4 }
    
    adlbPortPfmThresId3					OBJECT-TYPE
        SYNTAX  INTEGER	(0..30)
        ACCESS  read-write
        STATUS  mandatory
        DESCRIPTION ""
    ::= { hwMusaAdlbPortPfmThresEntry 5 }

	adlbPortPfmThresValue3				OBJECT-TYPE
        SYNTAX  INTEGER
        ACCESS  read-write
        STATUS  mandatory
        DESCRIPTION ""
    ::= { hwMusaAdlbPortPfmThresEntry 6 }
    
    adlbPortPfmThresId4					OBJECT-TYPE
        SYNTAX  INTEGER	(0..30)
        ACCESS  read-write
        STATUS  mandatory
        DESCRIPTION ""
    ::= { hwMusaAdlbPortPfmThresEntry 7 }

	adlbPortPfmThresValue4				OBJECT-TYPE
        SYNTAX  INTEGER
        ACCESS  read-write
        STATUS  mandatory
        DESCRIPTION ""
    ::= { hwMusaAdlbPortPfmThresEntry 8 }
    
    adlbPortPfmThresId5					OBJECT-TYPE
        SYNTAX  INTEGER	(0..30)
        ACCESS  read-write
        STATUS  mandatory
        DESCRIPTION ""
    ::= { hwMusaAdlbPortPfmThresEntry 9 }

	adlbPortPfmThresValue5				OBJECT-TYPE
        SYNTAX  INTEGER
        ACCESS  read-write
        STATUS  mandatory
        DESCRIPTION ""
    ::= { hwMusaAdlbPortPfmThresEntry 10 }
    
    adlbPortPfmThresId6					OBJECT-TYPE
        SYNTAX  INTEGER	(0..30)
        ACCESS  read-write
        STATUS  mandatory
        DESCRIPTION ""
    ::= { hwMusaAdlbPortPfmThresEntry 11 }

	adlbPortPfmThresValue6				OBJECT-TYPE
        SYNTAX  INTEGER
        ACCESS  read-write
        STATUS  mandatory
        DESCRIPTION ""
    ::= { hwMusaAdlbPortPfmThresEntry 12 }
    
    adlbPortPfmThresId7					OBJECT-TYPE
        SYNTAX  INTEGER	(0..30)
        ACCESS  read-write
        STATUS  mandatory
        DESCRIPTION ""
    ::= { hwMusaAdlbPortPfmThresEntry 13 }

	adlbPortPfmThresValue7				OBJECT-TYPE
        SYNTAX  INTEGER
        ACCESS  read-write
        STATUS  mandatory
        DESCRIPTION ""
    ::= { hwMusaAdlbPortPfmThresEntry 14 }
    
    adlbPortPfmThresId8					OBJECT-TYPE
        SYNTAX  INTEGER	(0..30)
        ACCESS  read-write
        STATUS  mandatory
        DESCRIPTION ""
    ::= { hwMusaAdlbPortPfmThresEntry 15 }

	adlbPortPfmThresValue8				OBJECT-TYPE
        SYNTAX  INTEGER
        ACCESS  read-write
        STATUS  mandatory
        DESCRIPTION ""
    ::= { hwMusaAdlbPortPfmThresEntry 16 }
    

    hwMusaAdlbPortLineDataTable    OBJECT-TYPE
        SYNTAX      SEQUENCE OF HwMusaAdlbPortLineDataEntry
        ACCESS      not-accessible
        STATUS      mandatory
    DESCRIPTION
    "Musa adlb port line operation data table."
    ::= { hwMusaAdlbPfm 1 }

   hwMusaAdlbPortLineDataEntry    OBJECT-TYPE
        SYNTAX         HwMusaAdlbPortLineDataEntry
        ACCESS         not-accessible
        STATUS         mandatory
    DESCRIPTION
    "This list contains adlb port line operation data variables."
    INDEX { hwMusaFrameIndex,
            hwMusaSlotIndex,
            adlbPortIndex }
    ::= { hwMusaAdlbPortLineDataTable  1 }

   HwMusaAdlbPortLineDataEntry    ::= SEQUENCE  {
		    adlbAs0DnRate            		INTEGER, 
		    adlbLs0DnRate            		INTEGER,
		    adlbAs1DnRate           		INTEGER, 
		    adlbLs0UpRate             		INTEGER,
		    adlbLs1UpRate             		INTEGER, 
		    adlbUpInterleaveDelay      		INTEGER,
		    adlbDnInterleaveDelay      		INTEGER, 
		    adlbDnNoiseMargin	   			INTEGER,
		    adlbUpNoiseMargin  	   			INTEGER, 
		    adlbDnAttenuation       		INTEGER,
		    adlbUpAttenuation         		INTEGER, 
		    adlbDnParityInterleave      	INTEGER,
		    adlbDnParityFast        		INTEGER, 
		    adlbUpParityInterleave        	INTEGER,
		    adlbUpParityFast          		INTEGER, 
		    adlbDnSymbolPerCodeInterleave 	INTEGER,
		    adlbDnSymbolPerCodeFast     	INTEGER,
		    adlbUpSymbolPerCodeInterleave   INTEGER,
		    adlbUpSymbolPerCodeFast     	INTEGER,
		    adlbDnInterleaveDepth         	INTEGER,
		    adlbUpInterleaveDepth         	INTEGER,
		    adlbMaxDnAttainableRate   		INTEGER,
		    adlbMaxUpAttainableRate   		INTEGER,
            adlbTotalOutputPower            INTEGER
          	}
                                                                                        
    adlbAs0DnRate				OBJECT-TYPE
        SYNTAX  INTEGER
        ACCESS  read-only
        STATUS  mandatory
        DESCRIPTION ""
    ::= { hwMusaAdlbPortLineDataEntry 1 }

    adlbLs0DnRate            		OBJECT-TYPE
        SYNTAX  INTEGER
        ACCESS  read-only
        STATUS  mandatory
        DESCRIPTION ""
    ::= { hwMusaAdlbPortLineDataEntry 2 }

    adlbAs1DnRate           		OBJECT-TYPE
        SYNTAX  INTEGER
        ACCESS  read-only
        STATUS  mandatory
        DESCRIPTION ""
    ::= { hwMusaAdlbPortLineDataEntry 3 }

    adlbLs0UpRate             		OBJECT-TYPE
        SYNTAX  INTEGER
        ACCESS  read-only
        STATUS  mandatory
        DESCRIPTION ""
    ::= { hwMusaAdlbPortLineDataEntry 4 }

    adlbLs1UpRate             		OBJECT-TYPE
        SYNTAX  INTEGER
        ACCESS  read-only
        STATUS  mandatory
        DESCRIPTION ""
    ::= { hwMusaAdlbPortLineDataEntry 5 }

    adlbUpInterleaveDelay      		OBJECT-TYPE
        SYNTAX  INTEGER
        ACCESS  read-only
        STATUS  mandatory
        DESCRIPTION ""
    ::= { hwMusaAdlbPortLineDataEntry 6 }

    adlbDnInterleaveDelay      		OBJECT-TYPE
        SYNTAX  INTEGER
        ACCESS  read-only
        STATUS  mandatory
        DESCRIPTION ""
    ::= { hwMusaAdlbPortLineDataEntry 7 }

    adlbDnNoiseMargin	   			OBJECT-TYPE
        SYNTAX  INTEGER
        ACCESS  read-only
        STATUS  mandatory
        DESCRIPTION ""
    ::= { hwMusaAdlbPortLineDataEntry 8 }

    adlbUpNoiseMargin  	   			OBJECT-TYPE
        SYNTAX  INTEGER
        ACCESS  read-only
        STATUS  mandatory
        DESCRIPTION ""
    ::= { hwMusaAdlbPortLineDataEntry 9 }

    adlbDnAttenuation       		OBJECT-TYPE
        SYNTAX  INTEGER
        ACCESS  read-only
        STATUS  mandatory
        DESCRIPTION ""
    ::= { hwMusaAdlbPortLineDataEntry 10 }

    adlbUpAttenuation         		OBJECT-TYPE
        SYNTAX  INTEGER
        ACCESS  read-only
        STATUS  mandatory
        DESCRIPTION ""
    ::= { hwMusaAdlbPortLineDataEntry 11 }

    adlbDnParityInterleave      	OBJECT-TYPE
        SYNTAX  INTEGER
        ACCESS  read-only
        STATUS  mandatory
        DESCRIPTION ""
    ::= { hwMusaAdlbPortLineDataEntry 12 }

    adlbDnParityFast        		OBJECT-TYPE
        SYNTAX  INTEGER
        ACCESS  read-only
        STATUS  mandatory
        DESCRIPTION ""
    ::= { hwMusaAdlbPortLineDataEntry 13 }

    adlbUpParityInterleave        	OBJECT-TYPE
        SYNTAX  INTEGER
        ACCESS  read-only
        STATUS  mandatory
        DESCRIPTION ""
    ::= { hwMusaAdlbPortLineDataEntry 14 }

    adlbUpParityFast          		OBJECT-TYPE
        SYNTAX  INTEGER
        ACCESS  read-only
        STATUS  mandatory
        DESCRIPTION ""
    ::= { hwMusaAdlbPortLineDataEntry 15 }

    adlbDnSymbolPerCodeInterleave 	OBJECT-TYPE
        SYNTAX  INTEGER
        ACCESS  read-only
        STATUS  mandatory
        DESCRIPTION ""
    ::= { hwMusaAdlbPortLineDataEntry 16 }

    adlbDnSymbolPerCodeFast     	OBJECT-TYPE
        SYNTAX  INTEGER
        ACCESS  read-only
        STATUS  mandatory
        DESCRIPTION ""
    ::= { hwMusaAdlbPortLineDataEntry 17 }

    adlbUpSymbolPerCodeInterleave   OBJECT-TYPE
        SYNTAX  INTEGER
        ACCESS  read-only
        STATUS  mandatory
        DESCRIPTION ""
    ::= { hwMusaAdlbPortLineDataEntry 18 }

    adlbUpSymbolPerCodeFast     	OBJECT-TYPE
        SYNTAX  INTEGER
        ACCESS  read-only
        STATUS  mandatory
        DESCRIPTION ""
    ::= { hwMusaAdlbPortLineDataEntry 19 }

    adlbDnInterleaveDepth         	OBJECT-TYPE
        SYNTAX  INTEGER
        ACCESS  read-only
        STATUS  mandatory
        DESCRIPTION ""
    ::= { hwMusaAdlbPortLineDataEntry 20 }

    adlbUpInterleaveDepth         	OBJECT-TYPE
        SYNTAX  INTEGER
        ACCESS  read-only
        STATUS  mandatory
        DESCRIPTION ""
    ::= { hwMusaAdlbPortLineDataEntry 21 }

    adlbMaxDnAttainableRate   		OBJECT-TYPE
        SYNTAX  INTEGER
        ACCESS  read-only
        STATUS  mandatory
        DESCRIPTION ""
    ::= { hwMusaAdlbPortLineDataEntry 22 }

    adlbMaxUpAttainableRate   		OBJECT-TYPE
        SYNTAX  INTEGER
        ACCESS  read-only
        STATUS  mandatory
        DESCRIPTION ""
    ::= { hwMusaAdlbPortLineDataEntry 23 }

    adlbTotalOutputPower            OBJECT-TYPE
        SYNTAX  INTEGER
        ACCESS  read-only
        STATUS  mandatory
        DESCRIPTION ""
    ::= { hwMusaAdlbPortLineDataEntry 24 }


    hwMusaAdlbAtucAlarmDataTable    OBJECT-TYPE
        SYNTAX      SEQUENCE OF HwMusaAdlbAtucAlarmDataEntry
        ACCESS      not-accessible
        STATUS      mandatory
    DESCRIPTION
    "Musa adlb port ATUC alarm statistic data table."
    ::= { hwMusaAdlbPfm 2 }

    hwMusaAdlbAtucAlarmDataEntry    OBJECT-TYPE
        SYNTAX         HwMusaAdlbAtucAlarmDataEntry
        ACCESS         not-accessible
        STATUS         mandatory
    DESCRIPTION
    "This list contains adlb port ATUC alarm statistic data variables."
    INDEX { hwMusaFrameIndex,
            hwMusaSlotIndex,
            adlbPortIndex }
    ::= { hwMusaAdlbAtucAlarmDataTable  1 }

    HwMusaAdlbAtucAlarmDataEntry    ::= SEQUENCE  {
		    adlbAtucLos						INTEGER,
    		adlbAtucHighBitErr				INTEGER,
   			adlbAtucRetrain					INTEGER,
    		adlbAtucLof						INTEGER,
    		adlbAtucAlarmValidIntervals		INTEGER,
		    adlbAtucPrev15MinLos			INTEGER,
    		adlbAtucPrev15MinHighBitErr		INTEGER,
   			adlbAtucPrev15MinRetrain		INTEGER,
    		adlbAtucPrev15MinLof			INTEGER,
		    adlbAtucCurr1DayLos				INTEGER,
    		adlbAtucCurr1DayHighBitErr		INTEGER,
   			adlbAtucCurr1DayRetrain			INTEGER,
    		adlbAtucCurr1DayLof				INTEGER,
		    adlbAtucPrev1DayLos				INTEGER,
    		adlbAtucPrev1DayHighBitErr		INTEGER,
   			adlbAtucPrev1DayRetrain			INTEGER,
    		adlbAtucPrev1DayLof				INTEGER,
    		adlbClearAlarmstatistics 	    INTEGER
          	}
                                                                                        
    adlbAtucLos						OBJECT-TYPE
        SYNTAX  INTEGER
        ACCESS  read-only
        STATUS  mandatory
        DESCRIPTION ""
    ::= { hwMusaAdlbAtucAlarmDataEntry 1 }

	adlbAtucHighBitErr				OBJECT-TYPE
        SYNTAX  INTEGER
        ACCESS  read-only
        STATUS  mandatory
        DESCRIPTION ""
    ::= { hwMusaAdlbAtucAlarmDataEntry 2 }

	adlbAtucRetrain					OBJECT-TYPE
        SYNTAX  INTEGER
        ACCESS  read-only
        STATUS  mandatory
        DESCRIPTION ""
    ::= { hwMusaAdlbAtucAlarmDataEntry 3 }

	adlbAtucLof						OBJECT-TYPE
        SYNTAX  INTEGER
        ACCESS  read-only
        STATUS  mandatory
        DESCRIPTION ""
    ::= { hwMusaAdlbAtucAlarmDataEntry 4 }

	adlbAtucAlarmValidIntervals		OBJECT-TYPE
        SYNTAX  INTEGER
        ACCESS  read-only
        STATUS  mandatory
        DESCRIPTION ""
    ::= { hwMusaAdlbAtucAlarmDataEntry 5 }

    adlbAtucPrev15MinLos			OBJECT-TYPE
        SYNTAX  INTEGER
        ACCESS  read-only
        STATUS  mandatory
        DESCRIPTION ""
    ::= { hwMusaAdlbAtucAlarmDataEntry 6 }

	adlbAtucPrev15MinHighBitErr		OBJECT-TYPE
        SYNTAX  INTEGER
        ACCESS  read-only
        STATUS  mandatory
        DESCRIPTION ""
    ::= { hwMusaAdlbAtucAlarmDataEntry 7 }

	adlbAtucPrev15MinRetrain		OBJECT-TYPE
        SYNTAX  INTEGER
        ACCESS  read-only
        STATUS  mandatory
        DESCRIPTION ""
    ::= { hwMusaAdlbAtucAlarmDataEntry 8 }

	adlbAtucPrev15MinLof			OBJECT-TYPE
        SYNTAX  INTEGER
        ACCESS  read-only
        STATUS  mandatory
        DESCRIPTION ""
    ::= { hwMusaAdlbAtucAlarmDataEntry 9 }

    adlbAtucCurr1DayLos				OBJECT-TYPE
        SYNTAX  INTEGER
        ACCESS  read-only
        STATUS  mandatory
        DESCRIPTION ""
    ::= { hwMusaAdlbAtucAlarmDataEntry 10 }

	adlbAtucCurr1DayHighBitErr		OBJECT-TYPE
        SYNTAX  INTEGER
        ACCESS  read-only
        STATUS  mandatory
        DESCRIPTION ""
    ::= { hwMusaAdlbAtucAlarmDataEntry 11 }

	adlbAtucCurr1DayRetrain			OBJECT-TYPE
        SYNTAX  INTEGER
        ACCESS  read-only
        STATUS  mandatory
        DESCRIPTION ""
    ::= { hwMusaAdlbAtucAlarmDataEntry 12 }

	adlbAtucCurr1DayLof				OBJECT-TYPE
        SYNTAX  INTEGER
        ACCESS  read-only
        STATUS  mandatory
        DESCRIPTION ""
    ::= { hwMusaAdlbAtucAlarmDataEntry 13 }

    adlbAtucPrev1DayLos				OBJECT-TYPE
        SYNTAX  INTEGER
        ACCESS  read-only
        STATUS  mandatory
        DESCRIPTION ""
    ::= { hwMusaAdlbAtucAlarmDataEntry 14 }

	adlbAtucPrev1DayHighBitErr		OBJECT-TYPE
        SYNTAX  INTEGER
        ACCESS  read-only
        STATUS  mandatory
        DESCRIPTION ""
    ::= { hwMusaAdlbAtucAlarmDataEntry 15 }

	adlbAtucPrev1DayRetrain			OBJECT-TYPE
        SYNTAX  INTEGER
        ACCESS  read-only
        STATUS  mandatory
        DESCRIPTION ""
    ::= { hwMusaAdlbAtucAlarmDataEntry 16 }

	adlbAtucPrev1DayLof				OBJECT-TYPE
        SYNTAX  INTEGER
        ACCESS  read-only
        STATUS  mandatory
        DESCRIPTION ""
    ::= { hwMusaAdlbAtucAlarmDataEntry 17 }
    
    adlbClearAlarmstatistics   OBJECT-TYPE
        SYNTAX  INTEGER
        ACCESS  write-only
        STATUS  mandatory
        DESCRIPTION ""
    ::= { hwMusaAdlbAtucAlarmDataEntry 18 }


    hwMusaAdlbAturAlarmDataTable    OBJECT-TYPE
        SYNTAX      SEQUENCE OF HwMusaAdlbAturAlarmDataEntry
        ACCESS      not-accessible
        STATUS      mandatory
    DESCRIPTION
    "Musa adlb port ATUR alarm statistic data table."
    ::= { hwMusaAdlbPfm 3 }

    hwMusaAdlbAturAlarmDataEntry    OBJECT-TYPE
        SYNTAX         HwMusaAdlbAturAlarmDataEntry
        ACCESS         not-accessible
        STATUS         mandatory
    DESCRIPTION
    "This list contains adlb port ATUR alarm statistic data variables."
    INDEX { hwMusaFrameIndex,
            hwMusaSlotIndex,
            adlbPortIndex }
    ::= { hwMusaAdlbAturAlarmDataTable  1 }

    HwMusaAdlbAturAlarmDataEntry    ::= SEQUENCE  {
		    adlbAturLos						INTEGER,
    		adlbAturHighBitErr				INTEGER,
   			adlbAturRfi						INTEGER,
    		adlbAturLpr						INTEGER,
    		adlbAturAlarmValidIntervals		INTEGER,
		    adlbAturPrev15MinLos			INTEGER,
    		adlbAturPrev15MinHighBitErr		INTEGER,
   			adlbAturPrev15MinRfi			INTEGER,
    		adlbAturPrev15MinLpr			INTEGER,
		    adlbAturCurr1DayLos				INTEGER,
    		adlbAturCurr1DayHighBitErr		INTEGER,
   			adlbAturCurr1DayRfi				INTEGER,
    		adlbAturCurr1DayLpr				INTEGER,
		    adlbAturPrev1DayLos				INTEGER,
    		adlbAturPrev1DayHighBitErr		INTEGER,
   			adlbAturPrev1DayRfi				INTEGER,
    		adlbAturPrev1DayLpr				INTEGER
          	}
                                                                                        
    adlbAturLos						OBJECT-TYPE
        SYNTAX  INTEGER
        ACCESS  read-only
        STATUS  mandatory
        DESCRIPTION ""
    ::= { hwMusaAdlbAturAlarmDataEntry 1 }

	adlbAturHighBitErr				OBJECT-TYPE
        SYNTAX  INTEGER
        ACCESS  read-only
        STATUS  mandatory
        DESCRIPTION ""
    ::= { hwMusaAdlbAturAlarmDataEntry 2 }

	adlbAturRfi						OBJECT-TYPE
        SYNTAX  INTEGER
        ACCESS  read-only
        STATUS  mandatory
        DESCRIPTION ""
    ::= { hwMusaAdlbAturAlarmDataEntry 3 }

	adlbAturLpr						OBJECT-TYPE
        SYNTAX  INTEGER
        ACCESS  read-only
        STATUS  mandatory
        DESCRIPTION ""
    ::= { hwMusaAdlbAturAlarmDataEntry 4 }

	adlbAturAlarmValidIntervals		OBJECT-TYPE
        SYNTAX  INTEGER
        ACCESS  read-only
        STATUS  mandatory
        DESCRIPTION ""
    ::= { hwMusaAdlbAturAlarmDataEntry 5 }

    adlbAturPrev15MinLos			OBJECT-TYPE
        SYNTAX  INTEGER
        ACCESS  read-only
        STATUS  mandatory
        DESCRIPTION ""
    ::= { hwMusaAdlbAturAlarmDataEntry 6 }

	adlbAturPrev15MinHighBitErr		OBJECT-TYPE
        SYNTAX  INTEGER
        ACCESS  read-only
        STATUS  mandatory
        DESCRIPTION ""
    ::= { hwMusaAdlbAturAlarmDataEntry 7 }

	adlbAturPrev15MinRfi			OBJECT-TYPE
        SYNTAX  INTEGER
        ACCESS  read-only
        STATUS  mandatory
        DESCRIPTION ""
    ::= { hwMusaAdlbAturAlarmDataEntry 8 }

	adlbAturPrev15MinLpr			OBJECT-TYPE
        SYNTAX  INTEGER
        ACCESS  read-only
        STATUS  mandatory
        DESCRIPTION ""
    ::= { hwMusaAdlbAturAlarmDataEntry 9 }

    adlbAturCurr1DayLos				OBJECT-TYPE
        SYNTAX  INTEGER
        ACCESS  read-only
        STATUS  mandatory
        DESCRIPTION ""
    ::= { hwMusaAdlbAturAlarmDataEntry 10 }

	adlbAturCurr1DayHighBitErr		OBJECT-TYPE
        SYNTAX  INTEGER
        ACCESS  read-only
        STATUS  mandatory
        DESCRIPTION ""
    ::= { hwMusaAdlbAturAlarmDataEntry 11 }

	adlbAturCurr1DayRfi				OBJECT-TYPE
        SYNTAX  INTEGER
        ACCESS  read-only
        STATUS  mandatory
        DESCRIPTION ""
    ::= { hwMusaAdlbAturAlarmDataEntry 12 }

	adlbAturCurr1DayLpr				OBJECT-TYPE
        SYNTAX  INTEGER
        ACCESS  read-only
        STATUS  mandatory
        DESCRIPTION ""
    ::= { hwMusaAdlbAturAlarmDataEntry 13 }

    adlbAturPrev1DayLos				OBJECT-TYPE
        SYNTAX  INTEGER
        ACCESS  read-only
        STATUS  mandatory
        DESCRIPTION ""
    ::= { hwMusaAdlbAturAlarmDataEntry 14 }

	adlbAturPrev1DayHighBitErr		OBJECT-TYPE
        SYNTAX  INTEGER
        ACCESS  read-only
        STATUS  mandatory
        DESCRIPTION ""
    ::= { hwMusaAdlbAturAlarmDataEntry 15 }

	adlbAturPrev1DayRfi				OBJECT-TYPE
        SYNTAX  INTEGER
        ACCESS  read-only
        STATUS  mandatory
        DESCRIPTION ""
    ::= { hwMusaAdlbAturAlarmDataEntry 16 }

	adlbAturPrev1DayLpr				OBJECT-TYPE
        SYNTAX  INTEGER
        ACCESS  read-only
        STATUS  mandatory
        DESCRIPTION ""
    ::= { hwMusaAdlbAturAlarmDataEntry 17 }


    hwMusaAdlbAtucPerfDataTable    OBJECT-TYPE
        SYNTAX      SEQUENCE OF HwMusaAdlbAtucPerfDataEntry
        ACCESS      not-accessible
        STATUS      mandatory
    DESCRIPTION
    "Musa adlb port ATUC performance statistic data table."
    ::= { hwMusaAdlbPfm 4 }

    hwMusaAdlbAtucPerfDataEntry    OBJECT-TYPE
        SYNTAX         HwMusaAdlbAtucPerfDataEntry
        ACCESS         not-accessible
        STATUS         mandatory
    DESCRIPTION
    "This list contains adlb port ATUC performance statistic total data until now variables."
    INDEX { hwMusaFrameIndex,
            hwMusaSlotIndex,
            adlbPortIndex }
    ::= { hwMusaAdlbAtucPerfDataTable  1 }

    HwMusaAdlbAtucPerfDataEntry    ::= SEQUENCE  {
       		adlbAtucCrcErrInterleave     	INTEGER,
		    adlbAtucCrcErrFast				INTEGER,
		    adlbAtucFecErrInterleave		INTEGER,
		    adlbAtucFecErrFast				INTEGER,
		    adlbAtucSuperFrameSent			INTEGER,
		    adlbAtucSuperFrameReceived	    INTEGER,
		    adlbAtucTimeCount	           	INTEGER,
		    adlbAtucErrFrames				INTEGER,
		    adlbAtucBgBENotSES				INTEGER,
		    adlbAtucErrSecond               INTEGER,
		    adlbAtucSevereErrSecond         INTEGER,
		    adlbAtucNonSESFrames            INTEGER,
		    adlbAtucUnavailableSecond       INTEGER,
		    adlbAtucBitswaps                INTEGER,
		    adlbAtucLossSecond              INTEGER,
		    adlbAtucFecSecond               INTEGER,
		    adlbAtucFastRetrain             INTEGER,
		    adlbAtucFastRetrainFail         INTEGER,
		    adlbAtucPerfValidIntervals      INTEGER,
		    adlbClearPerfstatistics         INTEGER
           	}                              
                                                                                        
    adlbAtucCrcErrInterleave			OBJECT-TYPE
        SYNTAX  INTEGER
        ACCESS  read-only
        STATUS  mandatory
        DESCRIPTION ""
    ::= { hwMusaAdlbAtucPerfDataEntry 1 }

    adlbAtucCrcErrFast				OBJECT-TYPE
        SYNTAX  INTEGER
        ACCESS  read-only
        STATUS  mandatory
        DESCRIPTION ""
    ::= { hwMusaAdlbAtucPerfDataEntry 2 }

    adlbAtucFecErrInterleave		OBJECT-TYPE
        SYNTAX  INTEGER
        ACCESS  read-only
        STATUS  mandatory
        DESCRIPTION ""
    ::= { hwMusaAdlbAtucPerfDataEntry 3 }

    adlbAtucFecErrFast				OBJECT-TYPE
        SYNTAX  INTEGER
        ACCESS  read-only
        STATUS  mandatory
        DESCRIPTION ""
    ::= { hwMusaAdlbAtucPerfDataEntry 4 }

    adlbAtucSuperFrameSent			OBJECT-TYPE
        SYNTAX  INTEGER
        ACCESS  read-only
        STATUS  mandatory
        DESCRIPTION ""
    ::= { hwMusaAdlbAtucPerfDataEntry 5 }

    adlbAtucSuperFrameReceived	    OBJECT-TYPE
        SYNTAX  INTEGER
        ACCESS  read-only
        STATUS  mandatory
        DESCRIPTION ""
    ::= { hwMusaAdlbAtucPerfDataEntry 6 }

    adlbAtucTimeCount	           	OBJECT-TYPE
        SYNTAX  INTEGER
        ACCESS  read-only
        STATUS  mandatory
        DESCRIPTION ""
    ::= { hwMusaAdlbAtucPerfDataEntry 7 }

    adlbAtucErrFrames				OBJECT-TYPE
        SYNTAX  INTEGER
        ACCESS  read-only
        STATUS  mandatory
        DESCRIPTION ""
    ::= { hwMusaAdlbAtucPerfDataEntry 8 }

    adlbAtucBgBENotSES				OBJECT-TYPE
        SYNTAX  INTEGER
        ACCESS  read-only
        STATUS  mandatory
        DESCRIPTION ""
    ::= { hwMusaAdlbAtucPerfDataEntry 9 }

    adlbAtucErrSecond               OBJECT-TYPE
        SYNTAX  INTEGER
        ACCESS  read-only
        STATUS  mandatory
        DESCRIPTION ""
    ::= { hwMusaAdlbAtucPerfDataEntry 10 }

    adlbAtucSevereErrSecond         OBJECT-TYPE
        SYNTAX  INTEGER
        ACCESS  read-only
        STATUS  mandatory
        DESCRIPTION ""
    ::= { hwMusaAdlbAtucPerfDataEntry 11 }

    adlbAtucNonSESFrames            OBJECT-TYPE
        SYNTAX  INTEGER
        ACCESS  read-only
        STATUS  mandatory
        DESCRIPTION ""
    ::= { hwMusaAdlbAtucPerfDataEntry 12 }

    adlbAtucUnavailableSecond       OBJECT-TYPE
        SYNTAX  INTEGER
        ACCESS  read-only
        STATUS  mandatory
        DESCRIPTION ""
    ::= { hwMusaAdlbAtucPerfDataEntry 13 }

    adlbAtucBitswaps                OBJECT-TYPE
        SYNTAX  INTEGER
        ACCESS  read-only
        STATUS  mandatory
        DESCRIPTION ""
    ::= { hwMusaAdlbAtucPerfDataEntry 14 }

    adlbAtucLossSecond              OBJECT-TYPE
        SYNTAX  INTEGER
        ACCESS  read-only
        STATUS  mandatory
        DESCRIPTION ""
    ::= { hwMusaAdlbAtucPerfDataEntry 15 }

    adlbAtucFecSecond               OBJECT-TYPE
        SYNTAX  INTEGER
        ACCESS  read-only
        STATUS  mandatory
        DESCRIPTION ""
    ::= { hwMusaAdlbAtucPerfDataEntry 16 }

    adlbAtucFastRetrain             OBJECT-TYPE
        SYNTAX  INTEGER
        ACCESS  read-only
        STATUS  mandatory
        DESCRIPTION ""
    ::= { hwMusaAdlbAtucPerfDataEntry 17 }

    adlbAtucFastRetrainFail         OBJECT-TYPE
        SYNTAX  INTEGER
        ACCESS  read-only
        STATUS  mandatory
        DESCRIPTION ""
    ::= { hwMusaAdlbAtucPerfDataEntry 18 }

	adlbAtucPerfValidIntervals		OBJECT-TYPE
        SYNTAX  INTEGER
        ACCESS  read-only
        STATUS  mandatory
        DESCRIPTION ""
    ::= { hwMusaAdlbAtucPerfDataEntry 19 }
    
    adlbClearPerfstatistics   OBJECT-TYPE
        SYNTAX  INTEGER
        ACCESS  write-only
        STATUS  mandatory
        DESCRIPTION ""
    ::= { hwMusaAdlbAtucPerfDataEntry 20 }
    

    hwMusaAdlbAtucPerfPrev15mDataTable    OBJECT-TYPE
        SYNTAX      SEQUENCE OF HwMusaAdlbAtucPerfPrev15mDataEntry
        ACCESS      not-accessible
        STATUS      mandatory
    DESCRIPTION
    "Musa adlb port ATUC performance statistic in previous 15 minutes data table."
    ::= { hwMusaAdlbPfm 5 }

    hwMusaAdlbAtucPerfPrev15mDataEntry    OBJECT-TYPE
        SYNTAX         HwMusaAdlbAtucPerfPrev15mDataEntry
        ACCESS         not-accessible
        STATUS         mandatory
    DESCRIPTION
    "This list contains adlb port ATUC performance statistic in previous 15 minutes data variables."
    INDEX { hwMusaFrameIndex,
            hwMusaSlotIndex,
            adlbPortIndex }
    ::= { hwMusaAdlbAtucPerfPrev15mDataTable  1 }

    HwMusaAdlbAtucPerfPrev15mDataEntry    ::= SEQUENCE  {
       		adlbAtucPrev15MinCrcErrInterleave     	INTEGER,
		    adlbAtucPrev15MinCrcErrFast				INTEGER,
		    adlbAtucPrev15MinFecErrInterleave		INTEGER,
		    adlbAtucPrev15MinFecErrFast				INTEGER,
		    adlbAtucPrev15MinSuperFrameSent			INTEGER,
		    adlbAtucPrev15MinSuperFrameReceived	    INTEGER,
		    adlbAtucPrev15MinTimeCount	           	INTEGER,
		    adlbAtucPrev15MinErrFrames				INTEGER,
		    adlbAtucPrev15MinBgBENotSES				INTEGER,
		    adlbAtucPrev15MinErrSecond              INTEGER,
		    adlbAtucPrev15MinSevereErrSecond        INTEGER,
		    adlbAtucPrev15MinNonSESFrames           INTEGER,
		    adlbAtucPrev15MinUnavailableSecond      INTEGER,
		    adlbAtucPrev15MinBitswaps               INTEGER,
		    adlbAtucPrev15MinLossSecond             INTEGER,
		    adlbAtucPrev15MinFecSecond              INTEGER,
		    adlbAtucPrev15MinFastRetrain            INTEGER,
		    adlbAtucPrev15MinFastRetrainFail        INTEGER
           	}                              

    adlbAtucPrev15MinCrcErrInterleave			OBJECT-TYPE
        SYNTAX  INTEGER
        ACCESS  read-only
        STATUS  mandatory
        DESCRIPTION ""
    ::= { hwMusaAdlbAtucPerfPrev15mDataEntry 1 }

    adlbAtucPrev15MinCrcErrFast				OBJECT-TYPE
        SYNTAX  INTEGER
        ACCESS  read-only
        STATUS  mandatory
        DESCRIPTION ""
    ::= { hwMusaAdlbAtucPerfPrev15mDataEntry 2 }

    adlbAtucPrev15MinFecErrInterleave		OBJECT-TYPE
        SYNTAX  INTEGER
        ACCESS  read-only
        STATUS  mandatory
        DESCRIPTION ""
    ::= { hwMusaAdlbAtucPerfPrev15mDataEntry 3 }

    adlbAtucPrev15MinFecErrFast				OBJECT-TYPE
        SYNTAX  INTEGER
        ACCESS  read-only
        STATUS  mandatory
        DESCRIPTION ""
    ::= { hwMusaAdlbAtucPerfPrev15mDataEntry 4 }

    adlbAtucPrev15MinSuperFrameSent			OBJECT-TYPE
        SYNTAX  INTEGER
        ACCESS  read-only
        STATUS  mandatory
        DESCRIPTION ""
    ::= { hwMusaAdlbAtucPerfPrev15mDataEntry 5 }

    adlbAtucPrev15MinSuperFrameReceived	    OBJECT-TYPE
        SYNTAX  INTEGER
        ACCESS  read-only
        STATUS  mandatory
        DESCRIPTION ""
    ::= { hwMusaAdlbAtucPerfPrev15mDataEntry 6 }

    adlbAtucPrev15MinTimeCount	           	OBJECT-TYPE
        SYNTAX  INTEGER
        ACCESS  read-only
        STATUS  mandatory
        DESCRIPTION ""
    ::= { hwMusaAdlbAtucPerfPrev15mDataEntry 7 }

    adlbAtucPrev15MinErrFrames				OBJECT-TYPE
        SYNTAX  INTEGER
        ACCESS  read-only
        STATUS  mandatory
        DESCRIPTION ""
    ::= { hwMusaAdlbAtucPerfPrev15mDataEntry 8 }

    adlbAtucPrev15MinBgBENotSES				OBJECT-TYPE
        SYNTAX  INTEGER
        ACCESS  read-only
        STATUS  mandatory
        DESCRIPTION ""
    ::= { hwMusaAdlbAtucPerfPrev15mDataEntry 9 }

    adlbAtucPrev15MinErrSecond               OBJECT-TYPE
        SYNTAX  INTEGER
        ACCESS  read-only
        STATUS  mandatory
        DESCRIPTION ""
    ::= { hwMusaAdlbAtucPerfPrev15mDataEntry 10 }

    adlbAtucPrev15MinSevereErrSecond         OBJECT-TYPE
        SYNTAX  INTEGER
        ACCESS  read-only
        STATUS  mandatory
        DESCRIPTION ""
    ::= { hwMusaAdlbAtucPerfPrev15mDataEntry 11 }

    adlbAtucPrev15MinNonSESFrames            OBJECT-TYPE
        SYNTAX  INTEGER
        ACCESS  read-only
        STATUS  mandatory
        DESCRIPTION ""
    ::= { hwMusaAdlbAtucPerfPrev15mDataEntry 12 }

    adlbAtucPrev15MinUnavailableSecond       OBJECT-TYPE
        SYNTAX  INTEGER
        ACCESS  read-only
        STATUS  mandatory
        DESCRIPTION ""
    ::= { hwMusaAdlbAtucPerfPrev15mDataEntry 13 }

    adlbAtucPrev15MinBitswaps                OBJECT-TYPE
        SYNTAX  INTEGER
        ACCESS  read-only
        STATUS  mandatory
        DESCRIPTION ""
    ::= { hwMusaAdlbAtucPerfPrev15mDataEntry 14 }

    adlbAtucPrev15MinLossSecond              OBJECT-TYPE
        SYNTAX  INTEGER
        ACCESS  read-only
        STATUS  mandatory
        DESCRIPTION ""
    ::= { hwMusaAdlbAtucPerfPrev15mDataEntry 15 }

    adlbAtucPrev15MinFecSecond               OBJECT-TYPE
        SYNTAX  INTEGER
        ACCESS  read-only
        STATUS  mandatory
        DESCRIPTION ""
    ::= { hwMusaAdlbAtucPerfPrev15mDataEntry 16 }

    adlbAtucPrev15MinFastRetrain             OBJECT-TYPE
        SYNTAX  INTEGER
        ACCESS  read-only
        STATUS  mandatory
        DESCRIPTION ""
    ::= { hwMusaAdlbAtucPerfPrev15mDataEntry 17 }

    adlbAtucPrev15MinFastRetrainFail         OBJECT-TYPE
        SYNTAX  INTEGER
        ACCESS  read-only
        STATUS  mandatory
        DESCRIPTION ""
    ::= { hwMusaAdlbAtucPerfPrev15mDataEntry 18 }


    hwMusaAdlbAtucPerfCurr24hDataTable    OBJECT-TYPE
        SYNTAX      SEQUENCE OF HwMusaAdlbAtucPerfCurr24hDataEntry
        ACCESS      not-accessible
        STATUS      mandatory
    DESCRIPTION
    "Musa adlb port ATUC performance statistic data in current 24 hours table."
    ::= { hwMusaAdlbPfm 6 }

    hwMusaAdlbAtucPerfCurr24hDataEntry    OBJECT-TYPE
        SYNTAX         HwMusaAdlbAtucPerfCurr24hDataEntry
        ACCESS         not-accessible
        STATUS         mandatory
    DESCRIPTION
    "This list contains adlb port ATUC performance statistic data in current 24 hours variables."
    INDEX { hwMusaFrameIndex,
            hwMusaSlotIndex,
            adlbPortIndex }
    ::= { hwMusaAdlbAtucPerfCurr24hDataTable  1 }

    HwMusaAdlbAtucPerfCurr24hDataEntry    ::= SEQUENCE  {
       		adlbAtucCurr1DayCrcErrInterleave     	INTEGER,
		    adlbAtucCurr1DayCrcErrFast				INTEGER,
		    adlbAtucCurr1DayFecErrInterleave		INTEGER,
		    adlbAtucCurr1DayFecErrFast				INTEGER,
		    adlbAtucCurr1DaySuperFrameSent			INTEGER,
		    adlbAtucCurr1DaySuperFrameReceived	    INTEGER,
		    adlbAtucCurr1DayTimeCount	           	INTEGER,
		    adlbAtucCurr1DayErrFrames				INTEGER,
		    adlbAtucCurr1DayBgBENotSES				INTEGER,
		    adlbAtucCurr1DayErrSecond              	INTEGER,
		    adlbAtucCurr1DaySevereErrSecond        	INTEGER,
		    adlbAtucCurr1DayNonSESFrames           	INTEGER,
		    adlbAtucCurr1DayUnavailableSecond      	INTEGER,
		    adlbAtucCurr1DayBitswaps               	INTEGER,
		    adlbAtucCurr1DayLossSecond             	INTEGER,
		    adlbAtucCurr1DayFecSecond              	INTEGER,
		    adlbAtucCurr1DayFastRetrain            	INTEGER,
		    adlbAtucCurr1DayFastRetrainFail        	INTEGER
           	}                              

    adlbAtucCurr1DayCrcErrInterleave		OBJECT-TYPE
        SYNTAX  INTEGER
        ACCESS  read-only
        STATUS  mandatory
        DESCRIPTION ""
    ::= { hwMusaAdlbAtucPerfCurr24hDataEntry 1 }

    adlbAtucCurr1DayCrcErrFast				OBJECT-TYPE
        SYNTAX  INTEGER
        ACCESS  read-only
        STATUS  mandatory
        DESCRIPTION ""
    ::= { hwMusaAdlbAtucPerfCurr24hDataEntry 2 }

    adlbAtucCurr1DayFecErrInterleave		OBJECT-TYPE
        SYNTAX  INTEGER
        ACCESS  read-only
        STATUS  mandatory
        DESCRIPTION ""
    ::= { hwMusaAdlbAtucPerfCurr24hDataEntry 3 }

    adlbAtucCurr1DayFecErrFast				OBJECT-TYPE
        SYNTAX  INTEGER
        ACCESS  read-only
        STATUS  mandatory
        DESCRIPTION ""
    ::= { hwMusaAdlbAtucPerfCurr24hDataEntry 4 }

    adlbAtucCurr1DaySuperFrameSent			OBJECT-TYPE
        SYNTAX  INTEGER
        ACCESS  read-only
        STATUS  mandatory
        DESCRIPTION ""
    ::= { hwMusaAdlbAtucPerfCurr24hDataEntry 5 }

    adlbAtucCurr1DaySuperFrameReceived	    OBJECT-TYPE
        SYNTAX  INTEGER
        ACCESS  read-only
        STATUS  mandatory
        DESCRIPTION ""
    ::= { hwMusaAdlbAtucPerfCurr24hDataEntry 6 }

    adlbAtucCurr1DayTimeCount	           	OBJECT-TYPE
        SYNTAX  INTEGER
        ACCESS  read-only
        STATUS  mandatory
        DESCRIPTION ""
    ::= { hwMusaAdlbAtucPerfCurr24hDataEntry 7 }

    adlbAtucCurr1DayErrFrames				OBJECT-TYPE
        SYNTAX  INTEGER
        ACCESS  read-only
        STATUS  mandatory
        DESCRIPTION ""
    ::= { hwMusaAdlbAtucPerfCurr24hDataEntry 8 }

    adlbAtucCurr1DayBgBENotSES				OBJECT-TYPE
        SYNTAX  INTEGER
        ACCESS  read-only
        STATUS  mandatory
        DESCRIPTION ""
    ::= { hwMusaAdlbAtucPerfCurr24hDataEntry 9 }

    adlbAtucCurr1DayErrSecond               OBJECT-TYPE
        SYNTAX  INTEGER
        ACCESS  read-only
        STATUS  mandatory
        DESCRIPTION ""
    ::= { hwMusaAdlbAtucPerfCurr24hDataEntry 10 }

    adlbAtucCurr1DaySevereErrSecond         OBJECT-TYPE
        SYNTAX  INTEGER
        ACCESS  read-only
        STATUS  mandatory
        DESCRIPTION ""
    ::= { hwMusaAdlbAtucPerfCurr24hDataEntry 11 }

    adlbAtucCurr1DayNonSESFrames            OBJECT-TYPE
        SYNTAX  INTEGER
        ACCESS  read-only
        STATUS  mandatory
        DESCRIPTION ""
    ::= { hwMusaAdlbAtucPerfCurr24hDataEntry 12 }

    adlbAtucCurr1DayUnavailableSecond       OBJECT-TYPE
        SYNTAX  INTEGER
        ACCESS  read-only
        STATUS  mandatory
        DESCRIPTION ""
    ::= { hwMusaAdlbAtucPerfCurr24hDataEntry 13 }

    adlbAtucCurr1DayBitswaps                OBJECT-TYPE
        SYNTAX  INTEGER
        ACCESS  read-only
        STATUS  mandatory
        DESCRIPTION ""
    ::= { hwMusaAdlbAtucPerfCurr24hDataEntry 14 }

    adlbAtucCurr1DayLossSecond              OBJECT-TYPE
        SYNTAX  INTEGER
        ACCESS  read-only
        STATUS  mandatory
        DESCRIPTION ""
    ::= { hwMusaAdlbAtucPerfCurr24hDataEntry 15 }

    adlbAtucCurr1DayFecSecond               OBJECT-TYPE
        SYNTAX  INTEGER
        ACCESS  read-only
        STATUS  mandatory
        DESCRIPTION ""
    ::= { hwMusaAdlbAtucPerfCurr24hDataEntry 16 }

    adlbAtucCurr1DayFastRetrain             OBJECT-TYPE
        SYNTAX  INTEGER
        ACCESS  read-only
        STATUS  mandatory
        DESCRIPTION ""
    ::= { hwMusaAdlbAtucPerfCurr24hDataEntry 17 }

    adlbAtucCurr1DayFastRetrainFail         OBJECT-TYPE
        SYNTAX  INTEGER
        ACCESS  read-only
        STATUS  mandatory
        DESCRIPTION ""
    ::= { hwMusaAdlbAtucPerfCurr24hDataEntry 18 }
    

    hwMusaAdlbAtucPerfPrev24hDataTable    OBJECT-TYPE
        SYNTAX      SEQUENCE OF HwMusaAdlbAtucPerfPrev24hDataEntry
        ACCESS      not-accessible
        STATUS      mandatory
    DESCRIPTION
    "Musa adlb port ATUC performance statistic data in previous 24 hours table."
    ::= { hwMusaAdlbPfm 7 }

    hwMusaAdlbAtucPerfPrev24hDataEntry    OBJECT-TYPE
        SYNTAX         HwMusaAdlbAtucPerfPrev24hDataEntry
        ACCESS         not-accessible
        STATUS         mandatory
    DESCRIPTION
    "This list contains adlb port ATUC performance statistic data in previous 24 hours variables."
    INDEX { hwMusaFrameIndex,
            hwMusaSlotIndex,
            adlbPortIndex }
    ::= { hwMusaAdlbAtucPerfPrev24hDataTable  1 }

    HwMusaAdlbAtucPerfPrev24hDataEntry    ::= SEQUENCE  {
       		adlbAtucPrev1DayCrcErrInterleave    	INTEGER,
		    adlbAtucPrev1DayCrcErrFast				INTEGER,
		    adlbAtucPrev1DayFecErrInterleave		INTEGER,
		    adlbAtucPrev1DayFecErrFast				INTEGER,
		    adlbAtucPrev1DaySuperFrameSent			INTEGER,
		    adlbAtucPrev1DaySuperFrameReceived	    INTEGER,
		    adlbAtucPrev1DayTimeCount	           	INTEGER,
		    adlbAtucPrev1DayErrFrames				INTEGER,
		    adlbAtucPrev1DayBgBENotSES				INTEGER,
		    adlbAtucPrev1DayErrSecond           	INTEGER,
		    adlbAtucPrev1DaySevereErrSecond        	INTEGER,
		    adlbAtucPrev1DayNonSESFrames           	INTEGER,
		    adlbAtucPrev1DayUnavailableSecond      	INTEGER,
		    adlbAtucPrev1DayBitswaps               	INTEGER,
		    adlbAtucPrev1DayLossSecond             	INTEGER,
		    adlbAtucPrev1DayFecSecond              	INTEGER,
		    adlbAtucPrev1DayFastRetrain            	INTEGER,
		    adlbAtucPrev1DayFastRetrainFail        	INTEGER
           	}                              

    adlbAtucPrev1DayCrcErrInterleave		OBJECT-TYPE
        SYNTAX  INTEGER
        ACCESS  read-only
        STATUS  mandatory
        DESCRIPTION ""
    ::= { hwMusaAdlbAtucPerfPrev24hDataEntry 1 }

    adlbAtucPrev1DayCrcErrFast				OBJECT-TYPE
        SYNTAX  INTEGER
        ACCESS  read-only
        STATUS  mandatory
        DESCRIPTION ""
    ::= { hwMusaAdlbAtucPerfPrev24hDataEntry 2 }

    adlbAtucPrev1DayFecErrInterleave		OBJECT-TYPE
        SYNTAX  INTEGER
        ACCESS  read-only
        STATUS  mandatory
        DESCRIPTION ""
    ::= { hwMusaAdlbAtucPerfPrev24hDataEntry 3 }

    adlbAtucPrev1DayFecErrFast				OBJECT-TYPE
        SYNTAX  INTEGER
        ACCESS  read-only
        STATUS  mandatory
        DESCRIPTION ""
    ::= { hwMusaAdlbAtucPerfPrev24hDataEntry 4 }

    adlbAtucPrev1DaySuperFrameSent			OBJECT-TYPE
        SYNTAX  INTEGER
        ACCESS  read-only
        STATUS  mandatory
        DESCRIPTION ""
    ::= { hwMusaAdlbAtucPerfPrev24hDataEntry 5 }

    adlbAtucPrev1DaySuperFrameReceived	    OBJECT-TYPE
        SYNTAX  INTEGER
        ACCESS  read-only
        STATUS  mandatory
        DESCRIPTION ""
    ::= { hwMusaAdlbAtucPerfPrev24hDataEntry 6 }

    adlbAtucPrev1DayTimeCount	           	OBJECT-TYPE
        SYNTAX  INTEGER
        ACCESS  read-only
        STATUS  mandatory
        DESCRIPTION ""
    ::= { hwMusaAdlbAtucPerfPrev24hDataEntry 7 }

    adlbAtucPrev1DayErrFrames				OBJECT-TYPE
        SYNTAX  INTEGER
        ACCESS  read-only
        STATUS  mandatory
        DESCRIPTION ""
    ::= { hwMusaAdlbAtucPerfPrev24hDataEntry 8 }

    adlbAtucPrev1DayBgBENotSES				OBJECT-TYPE
        SYNTAX  INTEGER
        ACCESS  read-only
        STATUS  mandatory
        DESCRIPTION ""
    ::= { hwMusaAdlbAtucPerfPrev24hDataEntry 9 }

    adlbAtucPrev1DayErrSecond               OBJECT-TYPE
        SYNTAX  INTEGER
        ACCESS  read-only
        STATUS  mandatory
        DESCRIPTION ""
    ::= { hwMusaAdlbAtucPerfPrev24hDataEntry 10 }

    adlbAtucPrev1DaySevereErrSecond         OBJECT-TYPE
        SYNTAX  INTEGER
        ACCESS  read-only
        STATUS  mandatory
        DESCRIPTION ""
    ::= { hwMusaAdlbAtucPerfPrev24hDataEntry 11 }

    adlbAtucPrev1DayNonSESFrames            OBJECT-TYPE
        SYNTAX  INTEGER
        ACCESS  read-only
        STATUS  mandatory
        DESCRIPTION ""
    ::= { hwMusaAdlbAtucPerfPrev24hDataEntry 12 }

    adlbAtucPrev1DayUnavailableSecond       OBJECT-TYPE
        SYNTAX  INTEGER
        ACCESS  read-only
        STATUS  mandatory
        DESCRIPTION ""
    ::= { hwMusaAdlbAtucPerfPrev24hDataEntry 13 }

    adlbAtucPrev1DayBitswaps                OBJECT-TYPE
        SYNTAX  INTEGER
        ACCESS  read-only
        STATUS  mandatory
        DESCRIPTION ""
    ::= { hwMusaAdlbAtucPerfPrev24hDataEntry 14 }

    adlbAtucPrev1DayLossSecond              OBJECT-TYPE
        SYNTAX  INTEGER
        ACCESS  read-only
        STATUS  mandatory
        DESCRIPTION ""
    ::= { hwMusaAdlbAtucPerfPrev24hDataEntry 15 }

    adlbAtucPrev1DayFecSecond               OBJECT-TYPE
        SYNTAX  INTEGER
        ACCESS  read-only
        STATUS  mandatory
        DESCRIPTION ""
    ::= { hwMusaAdlbAtucPerfPrev24hDataEntry 16 }

    adlbAtucPrev1DayFastRetrain             OBJECT-TYPE
        SYNTAX  INTEGER
        ACCESS  read-only
        STATUS  mandatory
        DESCRIPTION ""
    ::= { hwMusaAdlbAtucPerfPrev24hDataEntry 17 }

    adlbAtucPrev1DayFastRetrainFail         OBJECT-TYPE
        SYNTAX  INTEGER
        ACCESS  read-only
        STATUS  mandatory
        DESCRIPTION ""
    ::= { hwMusaAdlbAtucPerfPrev24hDataEntry 18 }


    hwMusaAdlbAturPerfDataTable    OBJECT-TYPE
        SYNTAX      SEQUENCE OF HwMusaAdlbAturPerfDataEntry
        ACCESS      not-accessible
        STATUS      mandatory
    DESCRIPTION
    "Musa adlb port ATUR performance statistic data until now table."
    ::= { hwMusaAdlbPfm 8 }

    hwMusaAdlbAturPerfDataEntry    OBJECT-TYPE
        SYNTAX         HwMusaAdlbAturPerfDataEntry
        ACCESS         not-accessible
        STATUS         mandatory
    DESCRIPTION
    "This list contains adlb port ATUR performance statistic data until now variables."
    INDEX { hwMusaFrameIndex,
            hwMusaSlotIndex,
            adlbPortIndex }
    ::= { hwMusaAdlbAturPerfDataTable  1 }

    HwMusaAdlbAturPerfDataEntry    ::= SEQUENCE  {
       		adlbAturCrcErrInterleave     	INTEGER,
		    adlbAturCrcErrFast				INTEGER,
		    adlbAturFecErrInterleave		INTEGER,
		    adlbAturFecErrFast				INTEGER,
		    adlbAturTimeCount	           	INTEGER,
		    adlbAturErrFrames				INTEGER,
		    adlbAturBgBENotSES				INTEGER,
		    adlbAturErrSecond               INTEGER,
		    adlbAturSevereErrSecond         INTEGER,
		    adlbAturNonSESFrames            INTEGER,
		    adlbAturUnavailableSecond       INTEGER,
		    adlbAturLossSecond              INTEGER,
		    adlbAturFecSecond               INTEGER,
		    adlbAturPerfValidIntervals      INTEGER
          	}
                                                                                        
    adlbAturCrcErrInterleave			OBJECT-TYPE
        SYNTAX  INTEGER
        ACCESS  read-only
        STATUS  mandatory
        DESCRIPTION ""
    ::= { hwMusaAdlbAturPerfDataEntry 1 }

    adlbAturCrcErrFast				OBJECT-TYPE
        SYNTAX  INTEGER
        ACCESS  read-only
        STATUS  mandatory
        DESCRIPTION ""
    ::= { hwMusaAdlbAturPerfDataEntry 2 }

    adlbAturFecErrInterleave		OBJECT-TYPE
        SYNTAX  INTEGER
        ACCESS  read-only
        STATUS  mandatory
        DESCRIPTION ""
    ::= { hwMusaAdlbAturPerfDataEntry 3 }

    adlbAturFecErrFast				OBJECT-TYPE
        SYNTAX  INTEGER
        ACCESS  read-only
        STATUS  mandatory
        DESCRIPTION ""
    ::= { hwMusaAdlbAturPerfDataEntry 4 }

    adlbAturTimeCount	           	OBJECT-TYPE
        SYNTAX  INTEGER
        ACCESS  read-only
        STATUS  mandatory
        DESCRIPTION ""
    ::= { hwMusaAdlbAturPerfDataEntry 5 }

    adlbAturErrFrames				OBJECT-TYPE
        SYNTAX  INTEGER
        ACCESS  read-only
        STATUS  mandatory
        DESCRIPTION ""
    ::= { hwMusaAdlbAturPerfDataEntry 6 }

    adlbAturBgBENotSES				OBJECT-TYPE
        SYNTAX  INTEGER
        ACCESS  read-only
        STATUS  mandatory
        DESCRIPTION ""
    ::= { hwMusaAdlbAturPerfDataEntry 7 }

    adlbAturErrSecond               OBJECT-TYPE
        SYNTAX  INTEGER
        ACCESS  read-only
        STATUS  mandatory
        DESCRIPTION ""
    ::= { hwMusaAdlbAturPerfDataEntry 8 }

    adlbAturSevereErrSecond         OBJECT-TYPE
        SYNTAX  INTEGER
        ACCESS  read-only
        STATUS  mandatory
        DESCRIPTION ""
    ::= { hwMusaAdlbAturPerfDataEntry 9 }

    adlbAturNonSESFrames            OBJECT-TYPE
        SYNTAX  INTEGER
        ACCESS  read-only
        STATUS  mandatory
        DESCRIPTION ""
    ::= { hwMusaAdlbAturPerfDataEntry 10 }

    adlbAturUnavailableSecond       OBJECT-TYPE
        SYNTAX  INTEGER
        ACCESS  read-only
        STATUS  mandatory
        DESCRIPTION ""
    ::= { hwMusaAdlbAturPerfDataEntry 11 }

    adlbAturLossSecond              OBJECT-TYPE
        SYNTAX  INTEGER
        ACCESS  read-only
        STATUS  mandatory
        DESCRIPTION ""
    ::= { hwMusaAdlbAturPerfDataEntry 12 }

    adlbAturFecSecond               OBJECT-TYPE
        SYNTAX  INTEGER
        ACCESS  read-only
        STATUS  mandatory
        DESCRIPTION ""
    ::= { hwMusaAdlbAturPerfDataEntry 13 }

	adlbAturPerfValidIntervals		OBJECT-TYPE
        SYNTAX  INTEGER
        ACCESS  read-only
        STATUS  mandatory
        DESCRIPTION ""
    ::= { hwMusaAdlbAturPerfDataEntry 14 }
    

    hwMusaAdlbAturPerfPrev15mDataTable    OBJECT-TYPE
        SYNTAX      SEQUENCE OF HwMusaAdlbAturPerfPrev15mDataEntry
        ACCESS      not-accessible
        STATUS      mandatory
    DESCRIPTION
    "Musa adlb port ATUR performance statistic data in previous 15 minutes table."
    ::= { hwMusaAdlbPfm 9 }

    hwMusaAdlbAturPerfPrev15mDataEntry    OBJECT-TYPE
        SYNTAX         HwMusaAdlbAturPerfPrev15mDataEntry
        ACCESS         not-accessible
        STATUS         mandatory
    DESCRIPTION
    "This list contains adlb port ATUR performance statistic data in previous 15 minutes variables."
    INDEX { hwMusaFrameIndex,
            hwMusaSlotIndex,
            adlbPortIndex }
    ::= { hwMusaAdlbAturPerfPrev15mDataTable  1 }

    HwMusaAdlbAturPerfPrev15mDataEntry    ::= SEQUENCE  {
       		adlbAturPrev15MinCrcErrInterleave     	INTEGER,
		    adlbAturPrev15MinCrcErrFast				INTEGER,
		    adlbAturPrev15MinFecErrInterleave		INTEGER,
		    adlbAturPrev15MinFecErrFast				INTEGER,
		    adlbAturPrev15MinTimeCount	           	INTEGER,
		    adlbAturPrev15MinErrFrames				INTEGER,
		    adlbAturPrev15MinBgBENotSES				INTEGER,
		    adlbAturPrev15MinErrSecond              INTEGER,
		    adlbAturPrev15MinSevereErrSecond        INTEGER,
		    adlbAturPrev15MinNonSESFrames           INTEGER,
		    adlbAturPrev15MinUnavailableSecond      INTEGER,
		    adlbAturPrev15MinLossSecond             INTEGER,
		    adlbAturPrev15MinFecSecond              INTEGER
          	}
                                                                                        
    adlbAturPrev15MinCrcErrInterleave			OBJECT-TYPE
        SYNTAX  INTEGER
        ACCESS  read-only
        STATUS  mandatory
        DESCRIPTION ""
    ::= { hwMusaAdlbAturPerfPrev15mDataEntry 1 }

    adlbAturPrev15MinCrcErrFast				OBJECT-TYPE
        SYNTAX  INTEGER
        ACCESS  read-only
        STATUS  mandatory
        DESCRIPTION ""
    ::= { hwMusaAdlbAturPerfPrev15mDataEntry 2 }

    adlbAturPrev15MinFecErrInterleave		OBJECT-TYPE
        SYNTAX  INTEGER
        ACCESS  read-only
        STATUS  mandatory
        DESCRIPTION ""
    ::= { hwMusaAdlbAturPerfPrev15mDataEntry 3 }

    adlbAturPrev15MinFecErrFast				OBJECT-TYPE
        SYNTAX  INTEGER
        ACCESS  read-only
        STATUS  mandatory
        DESCRIPTION ""
    ::= { hwMusaAdlbAturPerfPrev15mDataEntry 4 }

    adlbAturPrev15MinTimeCount	           	OBJECT-TYPE
        SYNTAX  INTEGER
        ACCESS  read-only
        STATUS  mandatory
        DESCRIPTION ""
    ::= { hwMusaAdlbAturPerfPrev15mDataEntry 5 }

    adlbAturPrev15MinErrFrames				OBJECT-TYPE
        SYNTAX  INTEGER
        ACCESS  read-only
        STATUS  mandatory
        DESCRIPTION ""
    ::= { hwMusaAdlbAturPerfPrev15mDataEntry 6 }

    adlbAturPrev15MinBgBENotSES				OBJECT-TYPE
        SYNTAX  INTEGER
        ACCESS  read-only
        STATUS  mandatory
        DESCRIPTION ""
    ::= { hwMusaAdlbAturPerfPrev15mDataEntry 7 }

    adlbAturPrev15MinErrSecond               OBJECT-TYPE
        SYNTAX  INTEGER
        ACCESS  read-only
        STATUS  mandatory
        DESCRIPTION ""
    ::= { hwMusaAdlbAturPerfPrev15mDataEntry 8 }

    adlbAturPrev15MinSevereErrSecond         OBJECT-TYPE
        SYNTAX  INTEGER
        ACCESS  read-only
        STATUS  mandatory
        DESCRIPTION ""
    ::= { hwMusaAdlbAturPerfPrev15mDataEntry 9 }

    adlbAturPrev15MinNonSESFrames            OBJECT-TYPE
        SYNTAX  INTEGER
        ACCESS  read-only
        STATUS  mandatory
        DESCRIPTION ""
    ::= { hwMusaAdlbAturPerfPrev15mDataEntry 10 }

    adlbAturPrev15MinUnavailableSecond       OBJECT-TYPE
        SYNTAX  INTEGER
        ACCESS  read-only
        STATUS  mandatory
        DESCRIPTION ""
    ::= { hwMusaAdlbAturPerfPrev15mDataEntry 11 }

    adlbAturPrev15MinLossSecond              OBJECT-TYPE
        SYNTAX  INTEGER
        ACCESS  read-only
        STATUS  mandatory
        DESCRIPTION ""
    ::= { hwMusaAdlbAturPerfPrev15mDataEntry 12 }

    adlbAturPrev15MinFecSecond               OBJECT-TYPE
        SYNTAX  INTEGER
        ACCESS  read-only
        STATUS  mandatory
        DESCRIPTION ""
    ::= { hwMusaAdlbAturPerfPrev15mDataEntry 13 }


    hwMusaAdlbAturPerfCurr24hDataTable    OBJECT-TYPE
        SYNTAX      SEQUENCE OF HwMusaAdlbAturPerfCurr24hDataEntry
        ACCESS      not-accessible
        STATUS      mandatory
    DESCRIPTION
    "Musa adlb port ATUR performance statistic data in current 24 hours table."
    ::= { hwMusaAdlbPfm 10 }

    hwMusaAdlbAturPerfCurr24hDataEntry    OBJECT-TYPE
        SYNTAX         HwMusaAdlbAturPerfCurr24hDataEntry
        ACCESS         not-accessible
        STATUS         mandatory
    DESCRIPTION
    "This list contains adlb port ATUR performance statistic data in current 24 hours variables."
    INDEX { hwMusaFrameIndex,
            hwMusaSlotIndex,
            adlbPortIndex }
    ::= { hwMusaAdlbAturPerfCurr24hDataTable  1 }

    HwMusaAdlbAturPerfCurr24hDataEntry    ::= SEQUENCE  {
       		adlbAturCurr1DayCrcErrInterleave     	INTEGER,
		    adlbAturCurr1DayCrcErrFast				INTEGER,
		    adlbAturCurr1DayFecErrInterleave		INTEGER,
		    adlbAturCurr1DayFecErrFast				INTEGER,
		    adlbAturCurr1DayTimeCount	           	INTEGER,
		    adlbAturCurr1DayErrFrames				INTEGER,
		    adlbAturCurr1DayBgBENotSES				INTEGER,
		    adlbAturCurr1DayErrSecond               INTEGER,
		    adlbAturCurr1DaySevereErrSecond         INTEGER,
		    adlbAturCurr1DayNonSESFrames            INTEGER,
		    adlbAturCurr1DayUnavailableSecond       INTEGER,
		    adlbAturCurr1DayLossSecond              INTEGER,
		    adlbAturCurr1DayFecSecond               INTEGER
          	}
                                                                                        
    adlbAturCurr1DayCrcErrInterleave		OBJECT-TYPE
        SYNTAX  INTEGER
        ACCESS  read-only
        STATUS  mandatory
        DESCRIPTION ""
    ::= { hwMusaAdlbAturPerfCurr24hDataEntry 1 }

    adlbAturCurr1DayCrcErrFast				OBJECT-TYPE
        SYNTAX  INTEGER
        ACCESS  read-only
        STATUS  mandatory
        DESCRIPTION ""
    ::= { hwMusaAdlbAturPerfCurr24hDataEntry 2 }

    adlbAturCurr1DayFecErrInterleave		OBJECT-TYPE
        SYNTAX  INTEGER
        ACCESS  read-only
        STATUS  mandatory
        DESCRIPTION ""
    ::= { hwMusaAdlbAturPerfCurr24hDataEntry 3 }

    adlbAturCurr1DayFecErrFast				OBJECT-TYPE
        SYNTAX  INTEGER
        ACCESS  read-only
        STATUS  mandatory
        DESCRIPTION ""
    ::= { hwMusaAdlbAturPerfCurr24hDataEntry 4 }

    adlbAturCurr1DayTimeCount	           	OBJECT-TYPE
        SYNTAX  INTEGER
        ACCESS  read-only
        STATUS  mandatory
        DESCRIPTION ""
    ::= { hwMusaAdlbAturPerfCurr24hDataEntry 5 }

    adlbAturCurr1DayErrFrames				OBJECT-TYPE
        SYNTAX  INTEGER
        ACCESS  read-only
        STATUS  mandatory
        DESCRIPTION ""
    ::= { hwMusaAdlbAturPerfCurr24hDataEntry 6 }

    adlbAturCurr1DayBgBENotSES				OBJECT-TYPE
        SYNTAX  INTEGER
        ACCESS  read-only
        STATUS  mandatory
        DESCRIPTION ""
    ::= { hwMusaAdlbAturPerfCurr24hDataEntry 7 }

    adlbAturCurr1DayErrSecond               OBJECT-TYPE
        SYNTAX  INTEGER
        ACCESS  read-only
        STATUS  mandatory
        DESCRIPTION ""
    ::= { hwMusaAdlbAturPerfCurr24hDataEntry 8 }

    adlbAturCurr1DaySevereErrSecond         OBJECT-TYPE
        SYNTAX  INTEGER
        ACCESS  read-only
        STATUS  mandatory
        DESCRIPTION ""
    ::= { hwMusaAdlbAturPerfCurr24hDataEntry 9 }

    adlbAturCurr1DayNonSESFrames            OBJECT-TYPE
        SYNTAX  INTEGER
        ACCESS  read-only
        STATUS  mandatory
        DESCRIPTION ""
    ::= { hwMusaAdlbAturPerfCurr24hDataEntry 10 }

    adlbAturCurr1DayUnavailableSecond       OBJECT-TYPE
        SYNTAX  INTEGER
        ACCESS  read-only
        STATUS  mandatory
        DESCRIPTION ""
    ::= { hwMusaAdlbAturPerfCurr24hDataEntry 11 }

    adlbAturCurr1DayLossSecond              OBJECT-TYPE
        SYNTAX  INTEGER
        ACCESS  read-only
        STATUS  mandatory
        DESCRIPTION ""
    ::= { hwMusaAdlbAturPerfCurr24hDataEntry 12 }

    adlbAturCurr1DayFecSecond               OBJECT-TYPE
        SYNTAX  INTEGER
        ACCESS  read-only
        STATUS  mandatory
        DESCRIPTION ""
    ::= { hwMusaAdlbAturPerfCurr24hDataEntry 13 }


    hwMusaAdlbAturPerfPrev24hDataTable    OBJECT-TYPE
        SYNTAX      SEQUENCE OF HwMusaAdlbAturPerfPrev24hDataEntry
        ACCESS      not-accessible
        STATUS      mandatory
    DESCRIPTION
    "Musa adlb port ATUR performance statistic data in previous 24 hours table."
    ::= { hwMusaAdlbPfm 11}

    hwMusaAdlbAturPerfPrev24hDataEntry    OBJECT-TYPE
        SYNTAX         HwMusaAdlbAturPerfPrev24hDataEntry
        ACCESS         not-accessible
        STATUS         mandatory
    DESCRIPTION
    "This list contains adlb port ATUR performance statistic data in previous 24 hours variables."
    INDEX { hwMusaFrameIndex,
            hwMusaSlotIndex,
            adlbPortIndex }
    ::= { hwMusaAdlbAturPerfPrev24hDataTable  1 }

    HwMusaAdlbAturPerfPrev24hDataEntry    ::= SEQUENCE  {
       		adlbAturPrev1DayCrcErrInterleave     	INTEGER,
		    adlbAturPrev1DayCrcErrFast				INTEGER,
		    adlbAturPrev1DayFecErrInterleave		INTEGER,
		    adlbAturPrev1DayFecErrFast				INTEGER,
		    adlbAturPrev1DayTimeCount	           	INTEGER,
		    adlbAturPrev1DayErrFrames				INTEGER,
		    adlbAturPrev1DayBgBENotSES				INTEGER,
		    adlbAturPrev1DayErrSecond               INTEGER,
		    adlbAturPrev1DaySevereErrSecond         INTEGER,
		    adlbAturPrev1DayNonSESFrames            INTEGER,
		    adlbAturPrev1DayUnavailableSecond       INTEGER,
		    adlbAturPrev1DayLossSecond              INTEGER,
		    adlbAturPrev1DayFecSecond               INTEGER
          	}
                                                                                        
    adlbAturPrev1DayCrcErrInterleave		OBJECT-TYPE
        SYNTAX  INTEGER
        ACCESS  read-only
        STATUS  mandatory
        DESCRIPTION ""
    ::= { hwMusaAdlbAturPerfPrev24hDataEntry 1 }

    adlbAturPrev1DayCrcErrFast				OBJECT-TYPE
        SYNTAX  INTEGER
        ACCESS  read-only
        STATUS  mandatory
        DESCRIPTION ""
    ::= { hwMusaAdlbAturPerfPrev24hDataEntry 2 }

    adlbAturPrev1DayFecErrInterleave		OBJECT-TYPE
        SYNTAX  INTEGER
        ACCESS  read-only
        STATUS  mandatory
        DESCRIPTION ""
    ::= { hwMusaAdlbAturPerfPrev24hDataEntry 3 }

    adlbAturPrev1DayFecErrFast				OBJECT-TYPE
        SYNTAX  INTEGER
        ACCESS  read-only
        STATUS  mandatory
        DESCRIPTION ""
    ::= { hwMusaAdlbAturPerfPrev24hDataEntry 4 }

    adlbAturPrev1DayTimeCount	           	OBJECT-TYPE
        SYNTAX  INTEGER
        ACCESS  read-only
        STATUS  mandatory
        DESCRIPTION ""
    ::= { hwMusaAdlbAturPerfPrev24hDataEntry 5 }

    adlbAturPrev1DayErrFrames				OBJECT-TYPE
        SYNTAX  INTEGER
        ACCESS  read-only
        STATUS  mandatory
        DESCRIPTION ""
    ::= { hwMusaAdlbAturPerfPrev24hDataEntry 6 }

    adlbAturPrev1DayBgBENotSES				OBJECT-TYPE
        SYNTAX  INTEGER
        ACCESS  read-only
        STATUS  mandatory
        DESCRIPTION ""
    ::= { hwMusaAdlbAturPerfPrev24hDataEntry 7 }

    adlbAturPrev1DayErrSecond               OBJECT-TYPE
        SYNTAX  INTEGER
        ACCESS  read-only
        STATUS  mandatory
        DESCRIPTION ""
    ::= { hwMusaAdlbAturPerfPrev24hDataEntry 8 }

    adlbAturPrev1DaySevereErrSecond         OBJECT-TYPE
        SYNTAX  INTEGER
        ACCESS  read-only
        STATUS  mandatory
        DESCRIPTION ""
    ::= { hwMusaAdlbAturPerfPrev24hDataEntry 9 }

    adlbAturPrev1DayNonSESFrames            OBJECT-TYPE
        SYNTAX  INTEGER
        ACCESS  read-only
        STATUS  mandatory
        DESCRIPTION ""
    ::= { hwMusaAdlbAturPerfPrev24hDataEntry 10 }

    adlbAturPrev1DayUnavailableSecond       OBJECT-TYPE
        SYNTAX  INTEGER
        ACCESS  read-only
        STATUS  mandatory
        DESCRIPTION ""
    ::= { hwMusaAdlbAturPerfPrev24hDataEntry 11 }

    adlbAturPrev1DayLossSecond              OBJECT-TYPE
        SYNTAX  INTEGER
        ACCESS  read-only
        STATUS  mandatory
        DESCRIPTION ""
    ::= { hwMusaAdlbAturPerfPrev24hDataEntry 12 }

    adlbAturPrev1DayFecSecond               OBJECT-TYPE
        SYNTAX  INTEGER
        ACCESS  read-only
        STATUS  mandatory
        DESCRIPTION ""
    ::= { hwMusaAdlbAturPerfPrev24hDataEntry 13 }


    hwMusaAdlbAtucLineDefectTable    OBJECT-TYPE
        SYNTAX      SEQUENCE OF HwMusaAdlbAtucLineDefectEntry
        ACCESS      not-accessible
        STATUS      mandatory
    DESCRIPTION
    "Musa adlb port ATUC line defect state table."
    ::= { hwMusaAdlbPfm 12 }

    hwMusaAdlbAtucLineDefectEntry    OBJECT-TYPE
        SYNTAX         HwMusaAdlbAtucLineDefectEntry
        ACCESS         not-accessible
        STATUS         mandatory
    DESCRIPTION
    "This list contains adlb port ATUC line defect state variables."
    INDEX { hwMusaFrameIndex,
            hwMusaSlotIndex,
            adlbPortIndex }
    ::= { hwMusaAdlbAtucLineDefectTable  1 }

    HwMusaAdlbAtucLineDefectEntry    ::= SEQUENCE  {
		    adlbAtucLpsState    			INTEGER,
		    adlbAtucSefState	       		INTEGER,
		    adlbAtucLosState                INTEGER,
		    adlbAtucLofState                INTEGER,
		    adlbAtucFebeInterleaveState     INTEGER,
		    adlbAtucFebeFastState  			INTEGER,
		    adlbAtucFecInterleaveState     	INTEGER,
		    adlbAtucFecFastState  			INTEGER
           	}                              
                                                                                        
    adlbAtucLpsState				OBJECT-TYPE
        SYNTAX  INTEGER
        ACCESS  read-only
        STATUS  mandatory
        DESCRIPTION ""
    ::= { hwMusaAdlbAtucLineDefectEntry 1 }

    adlbAtucSefState	       		OBJECT-TYPE
        SYNTAX  INTEGER
        ACCESS  read-only
        STATUS  mandatory
        DESCRIPTION ""
    ::= { hwMusaAdlbAtucLineDefectEntry 2 }

    adlbAtucLosState           		OBJECT-TYPE
        SYNTAX  INTEGER
        ACCESS  read-only
        STATUS  mandatory
        DESCRIPTION ""
    ::= { hwMusaAdlbAtucLineDefectEntry 3 }

    adlbAtucLofState           		OBJECT-TYPE
        SYNTAX  INTEGER
        ACCESS  read-only
        STATUS  mandatory
        DESCRIPTION ""
    ::= { hwMusaAdlbAtucLineDefectEntry 4 }

    adlbAtucFebeInterleaveState		OBJECT-TYPE
        SYNTAX  INTEGER
        ACCESS  read-only
        STATUS  mandatory
        DESCRIPTION ""
    ::= { hwMusaAdlbAtucLineDefectEntry 5 }

    adlbAtucFebeFastState   		OBJECT-TYPE
        SYNTAX  INTEGER
        ACCESS  read-only
        STATUS  mandatory
        DESCRIPTION ""
    ::= { hwMusaAdlbAtucLineDefectEntry 6 }

    adlbAtucFecInterleaveState 		OBJECT-TYPE
        SYNTAX  INTEGER
        ACCESS  read-only
        STATUS  mandatory
        DESCRIPTION ""
    ::= { hwMusaAdlbAtucLineDefectEntry 7 }

    adlbAtucFecFastState	  		OBJECT-TYPE
        SYNTAX  INTEGER
        ACCESS  read-only
        STATUS  mandatory
        DESCRIPTION ""
    ::= { hwMusaAdlbAtucLineDefectEntry 8 }


    hwMusaAdlbAturLineDefectTable    OBJECT-TYPE
        SYNTAX      SEQUENCE OF HwMusaAdlbAturLineDefectEntry
        ACCESS      not-accessible
        STATUS      mandatory
    DESCRIPTION
    "Musa adlb port ATUR line defect state table."
    ::= { hwMusaAdlbPfm 13 }

    hwMusaAdlbAturLineDefectEntry    OBJECT-TYPE
        SYNTAX         HwMusaAdlbAturLineDefectEntry
        ACCESS         not-accessible
        STATUS         mandatory
    DESCRIPTION
    "This list contains adlb port ATUR line defect state variables."
    INDEX { hwMusaFrameIndex,
            hwMusaSlotIndex,
            adlbPortIndex }
    ::= { hwMusaAdlbAturLineDefectTable  1 }

    HwMusaAdlbAturLineDefectEntry    ::= SEQUENCE  {
		    adlbAturLpsState 				INTEGER,
		    adlbAturRdiState   				INTEGER,
		    adlbAturLosState           		INTEGER,
		    adlbAturFriState           		INTEGER,
		    adlbAturFebeInterleaveState		INTEGER,
		    adlbAturFebeFastState  			INTEGER,
		    adlbAturFecInterleaveState 		INTEGER,
		    adlbAturFecFastState	  		INTEGER
           	}                              
                                                                                        
    adlbAturLpsState				OBJECT-TYPE
        SYNTAX  INTEGER
        ACCESS  read-only
        STATUS  mandatory
        DESCRIPTION ""
    ::= { hwMusaAdlbAturLineDefectEntry 1 }

    adlbAturRdiState	       		OBJECT-TYPE
        SYNTAX  INTEGER
        ACCESS  read-only
        STATUS  mandatory
        DESCRIPTION ""
    ::= { hwMusaAdlbAturLineDefectEntry 2 }

    adlbAturLosState           		OBJECT-TYPE
        SYNTAX  INTEGER
        ACCESS  read-only
        STATUS  mandatory
        DESCRIPTION ""
    ::= { hwMusaAdlbAturLineDefectEntry 3 }

    adlbAturFriState           		OBJECT-TYPE
        SYNTAX  INTEGER
        ACCESS  read-only
        STATUS  mandatory
        DESCRIPTION ""
    ::= { hwMusaAdlbAturLineDefectEntry 4 }

    adlbAturFebeInterleaveState		OBJECT-TYPE
        SYNTAX  INTEGER
        ACCESS  read-only
        STATUS  mandatory
        DESCRIPTION ""
    ::= { hwMusaAdlbAturLineDefectEntry 5 }

    adlbAturFebeFastState	  		OBJECT-TYPE
        SYNTAX  INTEGER
        ACCESS  read-only
        STATUS  mandatory
        DESCRIPTION ""
    ::= { hwMusaAdlbAturLineDefectEntry 6 }

    adlbAturFecInterleaveState 		OBJECT-TYPE
        SYNTAX  INTEGER
        ACCESS  read-only
        STATUS  mandatory
        DESCRIPTION ""
    ::= { hwMusaAdlbAturLineDefectEntry 7 }

    adlbAturFecFastState	  		OBJECT-TYPE
        SYNTAX  INTEGER
        ACCESS  read-only
        STATUS  mandatory
        DESCRIPTION ""
    ::= { hwMusaAdlbAturLineDefectEntry 8 }


    hwMusaAdlbAtucAtmDefectTable    OBJECT-TYPE
        SYNTAX      SEQUENCE OF HwMusaAdlbAtucAtmDefectEntry
        ACCESS      not-accessible
        STATUS      mandatory
    DESCRIPTION
    "Musa adlb port ATUC atm defect state table."
    ::= { hwMusaAdlbPfm 14 }

    hwMusaAdlbAtucAtmDefectEntry    OBJECT-TYPE
        SYNTAX         HwMusaAdlbAtucAtmDefectEntry
        ACCESS         not-accessible
        STATUS         mandatory
    DESCRIPTION
    "This list contains adlb port ATUC atm defect state variables."
    INDEX { hwMusaFrameIndex,
            hwMusaSlotIndex,
            adlbPortIndex }
    ::= { hwMusaAdlbAtucAtmDefectTable  1 }

    HwMusaAdlbAtucAtmDefectEntry    ::= SEQUENCE  {
		    adlbAtucHecInterleave        	INTEGER,
		    adlbAtucHecFast			        INTEGER,
		    adlbAtucNcdInterleave           INTEGER,
		    adlbAtucNcdFast			        INTEGER,
		    adlbAtucOcdInterleave           INTEGER,
		    adlbAtucOcdFast			        INTEGER,
		    adlbAtucLcdInterleave           INTEGER,
		    adlbAtucLcdFast			        INTEGER
           	}                              
                                                                                        
    adlbAtucHecInterleave			OBJECT-TYPE
        SYNTAX  INTEGER
        ACCESS  read-only
        STATUS  mandatory
        DESCRIPTION ""
    ::= { hwMusaAdlbAtucAtmDefectEntry 1 }

    adlbAtucHecFast			        OBJECT-TYPE
        SYNTAX  INTEGER
        ACCESS  read-only
        STATUS  mandatory
        DESCRIPTION ""
    ::= { hwMusaAdlbAtucAtmDefectEntry 2 }

    adlbAtucNcdInterleave           OBJECT-TYPE
        SYNTAX  INTEGER
        ACCESS  read-only
        STATUS  mandatory
        DESCRIPTION ""
    ::= { hwMusaAdlbAtucAtmDefectEntry 3 }

    adlbAtucNcdFast			        OBJECT-TYPE
        SYNTAX  INTEGER
        ACCESS  read-only
        STATUS  mandatory
        DESCRIPTION ""
    ::= { hwMusaAdlbAtucAtmDefectEntry 4 }

    adlbAtucOcdInterleave           OBJECT-TYPE
        SYNTAX  INTEGER
        ACCESS  read-only
        STATUS  mandatory
        DESCRIPTION ""
    ::= { hwMusaAdlbAtucAtmDefectEntry 5 }

    adlbAtucOcdFast			        OBJECT-TYPE
        SYNTAX  INTEGER
        ACCESS  read-only
        STATUS  mandatory
        DESCRIPTION ""
    ::= { hwMusaAdlbAtucAtmDefectEntry 6 }

    adlbAtucLcdInterleave           OBJECT-TYPE
        SYNTAX  INTEGER
        ACCESS  read-only
        STATUS  mandatory
        DESCRIPTION ""
    ::= { hwMusaAdlbAtucAtmDefectEntry 7 }

    adlbAtucLcdFast			        OBJECT-TYPE
        SYNTAX  INTEGER
        ACCESS  read-only
        STATUS  mandatory
        DESCRIPTION ""
    ::= { hwMusaAdlbAtucAtmDefectEntry 8 }


    hwMusaAdlbAturAtmDefectTable    OBJECT-TYPE
        SYNTAX      SEQUENCE OF HwMusaAdlbAturAtmDefectEntry
        ACCESS      not-accessible
        STATUS      mandatory
    DESCRIPTION
    "Musa adlb port ATUR atm defect state table."
    ::= { hwMusaAdlbPfm 15 }

    hwMusaAdlbAturAtmDefectEntry    OBJECT-TYPE
        SYNTAX         HwMusaAdlbAturAtmDefectEntry
        ACCESS         not-accessible
        STATUS         mandatory
    DESCRIPTION
    "This list contains adlb port ATUR atm defect state variables."
    INDEX { hwMusaFrameIndex,
            hwMusaSlotIndex,
            adlbPortIndex }
    ::= { hwMusaAdlbAturAtmDefectTable  1 }

    HwMusaAdlbAturAtmDefectEntry    ::= SEQUENCE  {
		    adlbAturHecInterleave        	INTEGER,
		    adlbAturHecFast        			INTEGER,
		    adlbAturNcdInterleave           INTEGER,
		    adlbAturNcdFast        			INTEGER,
		    adlbAturOcdInterleave           INTEGER,
		    adlbAturOcdFast        			INTEGER,
		    adlbAturLcdInterleave           INTEGER,
		    adlbAturLcdFast        			INTEGER
           	}                              
                                                                                        
    adlbAturHecInterleave			OBJECT-TYPE
        SYNTAX  INTEGER
        ACCESS  read-only
        STATUS  mandatory
        DESCRIPTION ""
    ::= { hwMusaAdlbAturAtmDefectEntry 1 }

    adlbAturHecFast			        OBJECT-TYPE
        SYNTAX  INTEGER
        ACCESS  read-only
        STATUS  mandatory
        DESCRIPTION ""
    ::= { hwMusaAdlbAturAtmDefectEntry 2 }

    adlbAturNcdInterleave           OBJECT-TYPE
        SYNTAX  INTEGER
        ACCESS  read-only
        STATUS  mandatory
        DESCRIPTION ""
    ::= { hwMusaAdlbAturAtmDefectEntry 3 }

    adlbAturNcdFast			        OBJECT-TYPE
        SYNTAX  INTEGER
        ACCESS  read-only
        STATUS  mandatory
        DESCRIPTION ""
    ::= { hwMusaAdlbAturAtmDefectEntry 4 }

    adlbAturOcdInterleave           OBJECT-TYPE
        SYNTAX  INTEGER
        ACCESS  read-only
        STATUS  mandatory
        DESCRIPTION ""
    ::= { hwMusaAdlbAturAtmDefectEntry 5 }

    adlbAturOcdFast			        OBJECT-TYPE
        SYNTAX  INTEGER
        ACCESS  read-only
        STATUS  mandatory
        DESCRIPTION ""
    ::= { hwMusaAdlbAturAtmDefectEntry 6 }

    adlbAturLcdInterleave           OBJECT-TYPE
        SYNTAX  INTEGER
        ACCESS  read-only
        STATUS  mandatory
        DESCRIPTION ""
    ::= { hwMusaAdlbAturAtmDefectEntry 7 }

    adlbAturLcdFast			        OBJECT-TYPE
        SYNTAX  INTEGER
        ACCESS  read-only
        STATUS  mandatory
        DESCRIPTION ""
    ::= { hwMusaAdlbAturAtmDefectEntry 8 }


    hwMusaAdlbPortBitsTable    OBJECT-TYPE
        SYNTAX      SEQUENCE OF HwMusaAdlbPortBitsEntry
        ACCESS      not-accessible
        STATUS      mandatory
    DESCRIPTION
    "Musa adlb port bits distribution table."
    ::= { hwMusaAdlbPfm 16 }

    hwMusaAdlbPortBitsEntry    OBJECT-TYPE
        SYNTAX         HwMusaAdlbPortBitsEntry
        ACCESS         not-accessible
        STATUS         mandatory
    DESCRIPTION
    "This list contains adlb port bits distribution variables."
    INDEX { hwMusaFrameIndex,
            hwMusaSlotIndex,
            adlbPortIndex }
    ::= { hwMusaAdlbPortBitsTable  1 }

    HwMusaAdlbPortBitsEntry    ::= SEQUENCE  {
		    adlbDnBitsPerFrame        INTEGER,
		    adlbUpBitsPerFrame        INTEGER,
		    adlbDnBitAllocate		  DisplayString,
		    adlbUpBitAllocate		  DisplayString
           	}                              
                                                                                        
    adlbDnBitsPerFrame			OBJECT-TYPE
        SYNTAX  INTEGER
        ACCESS  read-only
        STATUS  mandatory
        DESCRIPTION ""
    ::= { hwMusaAdlbPortBitsEntry 1 }
    
    adlbUpBitsPerFrame			OBJECT-TYPE
        SYNTAX  INTEGER
        ACCESS  read-only
        STATUS  mandatory
        DESCRIPTION ""
    ::= { hwMusaAdlbPortBitsEntry 2 }
    
    adlbDnBitAllocate		  OBJECT-TYPE
        SYNTAX  DisplayString
        ACCESS  read-only
        STATUS  mandatory
        DESCRIPTION ""
    ::= { hwMusaAdlbPortBitsEntry 3 }
    
    adlbUpBitAllocate		  OBJECT-TYPE
        SYNTAX  DisplayString
        ACCESS  read-only
        STATUS  mandatory
        DESCRIPTION ""
    ::= { hwMusaAdlbPortBitsEntry 4 }
    


    hwMusaAdlbCarrierSnrTable    OBJECT-TYPE
        SYNTAX      SEQUENCE OF HwMusaAdlbCarrierSnrEntry
        ACCESS      not-accessible
        STATUS      mandatory
    DESCRIPTION
    "Musa adlb port carrier snr distribution table."
    ::= { hwMusaAdlbPfm 17 }

    hwMusaAdlbCarrierSnrEntry    OBJECT-TYPE
        SYNTAX         HwMusaAdlbCarrierSnrEntry
        ACCESS         not-accessible
        STATUS         mandatory
    DESCRIPTION
    "This list contains adlb port carrier snr distribution variables."
    INDEX { hwMusaFrameIndex,
            hwMusaSlotIndex,
            adlbPortIndex }
    ::= { hwMusaAdlbCarrierSnrTable  1 }

    HwMusaAdlbCarrierSnrEntry    ::= SEQUENCE  {    
		    adlbDnSnrAllocate   DisplayString,
		    adlbUpSnrAllocate   DisplayString
           	}                              
                                                                                        
    adlbDnSnrAllocate 		OBJECT-TYPE
        SYNTAX  DisplayString
        ACCESS  read-only
        STATUS  mandatory
        DESCRIPTION ""
    ::= { hwMusaAdlbCarrierSnrEntry 1 }
    
    adlbUpSnrAllocate		OBJECT-TYPE
        SYNTAX  DisplayString
        ACCESS  read-only
        STATUS  mandatory
        DESCRIPTION ""
    ::= { hwMusaAdlbCarrierSnrEntry 2 }


    hwMusaAdlbPortTestTable    OBJECT-TYPE
        SYNTAX      SEQUENCE OF HwMusaAdlbPortTestEntry
        ACCESS      not-accessible
        STATUS      mandatory
    DESCRIPTION
    "Musa adlb port test table."
    ::= { hwMusaAdlbTest 1 }

   hwMusaAdlbPortTestEntry    OBJECT-TYPE
        SYNTAX         HwMusaAdlbPortTestEntry
        ACCESS         not-accessible
        STATUS         mandatory
    DESCRIPTION
    "This list contains Musa adlb port test variables."
    INDEX { hwMusaFrameIndex,
            hwMusaSlotIndex,
            adlbPortIndex }
    ::= { hwMusaAdlbPortTestTable  1 }

   HwMusaAdlbPortTestEntry    ::= SEQUENCE  {
   			adlbPortTestOper		INTEGER
            }            
    
    adlbPortTestOper		OBJECT-TYPE
        SYNTAX  INTEGER {
                            atmLoop			(1), 
                            aturErrCrc		(2),
                            stopAturErrCrc	(3),
                            sendErrCrc		(4),
                            stopSendErrCrc	(5),
                            aturAutoLoop	(6),
                            aturChgLoopParam(7)                            
                       }
        ACCESS  write-only
        STATUS  mandatory
        DESCRIPTION
        " "
    ::= { hwMusaAdlbPortTestEntry 1 }
        
  
END
