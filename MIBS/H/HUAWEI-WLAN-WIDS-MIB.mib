--
-- HUAWEI-WLAN-WIDS-MIB5.mib
-- MIB generated by MG-SOFT Visual MIB Builder Version 4.0 Build 341
-- Tuesday, January 15, 2013 at 19:51:28
--

--  HUAWEI-WLAN-WIDS-MIB.mib
-- MIB generated by MG-SOFT Visual MIB Builder Version 4.0 Build 341
-- Tuesday, May 22, 2012 at 10:38:09
-- 
--   ============================================================================
-- Copyright (C) 2009 by  HUAWEI TECHNOLOGIES. All rights reserved.
-- Description:  The mib include wlan wids device informations.
-- Reference:HUAWEI-WLAN-MIB  
-- Version: V1.03
-- 
-- ============================================================================

	HUAWEI-WLAN-WIDS-MIB DEFINITIONS ::= BEGIN
 
		IMPORTS
			hwApType, hwApIndex, hwApMac			
				FROM HUAWEI-WLAN-DEVICE-MIB			
			hwWlan			
				FROM HUAWEI-WLAN-MIB			
			OBJECT-GROUP, MODULE-COMPLIANCE, NOTIFICATION-GROUP			
				FROM SNMPv2-CONF			
			IpAddress, Integer32, Unsigned32, OBJECT-TYPE, MODULE-IDENTITY, 
			NOTIFICATION-TYPE			
				FROM SNMPv2-SMI			
			MacAddress, RowStatus			
				FROM SNMPv2-TC;

--   June 08, 2010 at 00:00 GMT
-- 1.3.6.1.4.1.2011.6.139.8
-- November 10, 2010 at 00:00 GMT
-- May 08, 2012 at 00:00 GMT
-- May 10, 2012 at 00:00 GMT
		-- 1.3.6.1.4.1.2011.6.139.8
		hwWlanWids MODULE-IDENTITY 
			LAST-UPDATED "201405041600Z"		-- May 4, 2014 at 16:00 GMT
			ORGANIZATION 
				"Huawei Technologies Co.,Ltd."
			CONTACT-INFO 
          "Huawei Industrial Base
				   Bantian, Longgang
				   Shenzhen 518129
				   People's Republic of China
				   Website: http://www.huawei.com
				   Email: support@huawei.com
				  "
			DESCRIPTION 
				"The MIB module include wids informations."
			REVISION "201405041600Z"		-- May 4, 2014 at 16:00 GMT
			DESCRIPTION 
				"V1.03, update for v2r5 change"	
			REVISION "201309041022Z"		-- Sep 4, 2013 at 10:22 GMT
			DESCRIPTION 
				"V1.02, update for v2r3 change"
				
			REVISION "201305211540Z"		-- May 21, 2013 at 15:40 GMT
			DESCRIPTION 
				"V1.01, update for v2r3 change"

			REVISION "201205100000Z"		-- May 10, 2012 at 00:00 GMT
			DESCRIPTION 
				"V1.01, Add wids device"
			REVISION "201205080000Z"		-- May 08, 2012 at 00:00 GMT
			DESCRIPTION 
				"
				V1.00, Inital version.
				"
			::= { hwWlan 8 }

		
	
	
--
-- Node definitions
--
	
--  Node definitions
-- 
-- 1.3.6.1.4.1.2011.6.139.8.1
		-- 1.3.6.1.4.1.2011.6.139.8.1
		hwWlanWidsNotifications OBJECT IDENTIFIER ::= { hwWlanWids 1 }

		
--  1.3.6.1.4.1.2011.6.139.8.1.1
		-- 1.3.6.1.4.1.2011.6.139.8.1.1
		hwWlanWidsNotify OBJECT IDENTIFIER ::= { hwWlanWidsNotifications 1 }

		
--  1.3.6.1.4.1.2011.6.139.8.1.1.1
		-- 1.3.6.1.4.1.2011.6.139.8.1.1.1
		hwWlanWidsRougeDevDetectedNotify NOTIFICATION-TYPE
			OBJECTS { hwWlanObjWidsRogueDevMAC, hwWlanObjWidsRogueDevType, hwWlanObjWidsRogueDevChannel, hwWlanObjWidsRogueDevRSSI, hwWlanObjWidsRogueDevSSID, 
				hwWlanObjWidsDetAPID, hwWlanObjWidsDetAPMAC, hwWlanObjWidsDetRadioId, hwWlanObjWidsDetAPIP, hwWlanObjWidsDetAPChannel
				 }
			STATUS current
			DESCRIPTION 
				"Description."
			::= { hwWlanWidsNotify 1 }

		
--  1.3.6.1.4.1.2011.6.139.8.1.1.2
		-- 1.3.6.1.4.1.2011.6.139.8.1.1.2
		hwWlanWidsRougeDevClearNotify NOTIFICATION-TYPE
			OBJECTS { hwWlanObjWidsRogueDevMAC, hwWlanObjWidsRogueDevType, hwWlanObjWidsRogueDevChannel, hwWlanObjWidsRogueDevRSSI, hwWlanObjWidsRogueDevSSID, 
				hwWlanObjWidsDetAPID, hwWlanObjWidsDetAPMAC, hwWlanObjWidsDetRadioId, hwWlanObjWidsDetAPIP, hwWlanObjWidsDetAPChannel
				 }
			STATUS current
			DESCRIPTION 
				"Description."
			::= { hwWlanWidsNotify 2 }

		
--  1.3.6.1.4.1.2011.6.139.8.1.1.3
		-- 1.3.6.1.4.1.2011.6.139.8.1.1.3
		hwWlanWidsNonWifiDetNotify NOTIFICATION-TYPE
			OBJECTS { hwWlanObjWidsDetAPID, hwWlanObjWidsDetAPMAC, hwWlanObjWidsDetAPName, hwWlanObjWidsDetRadioId, hwWlanObjWidsDetRadioType, 
				hwWlanObjWidsNonWifiDeviceType, hwWlanObjWidsNonWifiRssi, hwWlanObjWidsNonWifiInterChannel }
			STATUS current
			DESCRIPTION 
				"Description."
			::= { hwWlanWidsNotify 3 }

		
		-- 1.3.6.1.4.1.2011.6.139.8.1.1.4
		hwWlanWidsNonWifiClearNotify NOTIFICATION-TYPE
			OBJECTS { hwWlanObjWidsDetAPID, hwWlanObjWidsDetAPMAC, hwWlanObjWidsDetAPName, hwWlanObjWidsDetRadioId, hwWlanObjWidsDetRadioType, 
				hwWlanObjWidsNonWifiDeviceType, hwWlanObjWidsNonWifiRssi, hwWlanObjWidsNonWifiInterChannel }
			STATUS current
			DESCRIPTION 
				"Description."
			::= { hwWlanWidsNotify 4 }
		
		-- 1.3.6.1.4.1.2011.6.139.8.1.1.5
		hwWlanWidsFloodAttackDetectedNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 5 }

		
		-- 1.3.6.1.4.1.2011.6.139.8.1.1.6
		hwWlanWidsFloodAttackClearNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 6 }

		
		-- 1.3.6.1.4.1.2011.6.139.8.1.1.7
		hwWlanWidsSpoofAttackDetectedNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 7 }

		
		-- 1.3.6.1.4.1.2011.6.139.8.1.1.8
		hwWlanWidsSpoofAttackClearNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 8 }

		
		-- 1.3.6.1.4.1.2011.6.139.8.1.1.9
		hwWlanWidsWeakIvAttackDetectedNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 9 }

		
		-- 1.3.6.1.4.1.2011.6.139.8.1.1.10
		hwWlanWidsWeakIvAttackClearNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 10 }

		
		-- 1.3.6.1.4.1.2011.6.139.8.1.1.11
		hwWlanWidsPSKAttackDetectedNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 11 }

		
		-- 1.3.6.1.4.1.2011.6.139.8.1.1.12
		hwWlanWidsPSKAttackClearNotify NOTIFICATION-TYPE
			OBJECTS { hwWlanObjWidsDetAPMAC, hwWlanObjWidsAttackDevMAC, hwWlanObjWidsDetAPChannel, hwWlanObjWidsAttackType, hwWlanObjWidsAttackTypeStr
				 }
			STATUS current
			DESCRIPTION 
				"Description."
			::= { hwWlanWidsNotify 12 }

		
--  1.3.6.1.4.1.2011.6.139.8.1.2
		-- 1.3.6.1.4.1.2011.6.139.8.1.2
		hwWlanWidsNotifyObjects OBJECT IDENTIFIER ::= { hwWlanWidsNotifications 2 }

		
--  1.3.6.1.4.1.2011.6.139.8.1.2.1
		-- 1.3.6.1.4.1.2011.6.139.8.1.2.1
		hwWlanObjWidsRogueDevMAC OBJECT-TYPE
			SYNTAX MacAddress
			MAX-ACCESS read-only
			STATUS current
			DESCRIPTION
				"Description."
			::= { hwWlanWidsNotifyObjects 1 }

		
--  1.3.6.1.4.1.2011.6.139.8.1.2.2
		-- 1.3.6.1.4.1.2011.6.139.8.1.2.2
		hwWlanObjWidsRogueDevType OBJECT-TYPE
			SYNTAX Integer32
			MAX-ACCESS read-only
			STATUS current
			DESCRIPTION
				"Description."
			::= { hwWlanWidsNotifyObjects 2 }

		
--  1.3.6.1.4.1.2011.6.139.8.1.2.3
		-- 1.3.6.1.4.1.2011.6.139.8.1.2.3
		hwWlanObjWidsRogueDevChannel OBJECT-TYPE
			SYNTAX Integer32
			MAX-ACCESS read-only
			STATUS current
			DESCRIPTION
				"Description."
			::= { hwWlanWidsNotifyObjects 3 }

		
--  1.3.6.1.4.1.2011.6.139.8.1.2.4
		-- 1.3.6.1.4.1.2011.6.139.8.1.2.4
		hwWlanObjWidsRogueDevRSSI OBJECT-TYPE
			SYNTAX Integer32
			MAX-ACCESS read-only
			STATUS current
			DESCRIPTION
				"Description."
			::= { hwWlanWidsNotifyObjects 4 }

		
--  1.3.6.1.4.1.2011.6.139.8.1.2.5
		-- 1.3.6.1.4.1.2011.6.139.8.1.2.5
		hwWlanObjWidsRogueDevSSID OBJECT-TYPE
			SYNTAX OCTET STRING
			MAX-ACCESS read-only
			STATUS current
			DESCRIPTION
				"Description."
			::= { hwWlanWidsNotifyObjects 5 }

		
--  1.3.6.1.4.1.2011.6.139.8.1.2.6
		-- 1.3.6.1.4.1.2011.6.139.8.1.2.6
		hwWlanObjWidsDetAPID OBJECT-TYPE
			SYNTAX Integer32
			MAX-ACCESS read-only
			STATUS current
			DESCRIPTION
				"Description."
			::= { hwWlanWidsNotifyObjects 6 }

		
--  1.3.6.1.4.1.2011.6.139.8.1.2.7
		-- 1.3.6.1.4.1.2011.6.139.8.1.2.7
		hwWlanObjWidsDetRadioId OBJECT-TYPE
			SYNTAX Integer32
			MAX-ACCESS read-only
			STATUS current
			DESCRIPTION
				"Description."
			::= { hwWlanWidsNotifyObjects 7 }

		
--  1.3.6.1.4.1.2011.6.139.8.1.2.8
		-- 1.3.6.1.4.1.2011.6.139.8.1.2.8
		hwWlanObjWidsDetAPChannel OBJECT-TYPE
			SYNTAX Integer32
			MAX-ACCESS read-only
			STATUS current
			DESCRIPTION
				"Description."
			::= { hwWlanWidsNotifyObjects 8 }

		
--  1.3.6.1.4.1.2011.6.139.8.1.2.9
		-- 1.3.6.1.4.1.2011.6.139.8.1.2.9
		hwWlanObjWidsDetAPMAC OBJECT-TYPE
			SYNTAX MacAddress
			MAX-ACCESS read-only
			STATUS current
			DESCRIPTION
				"Description."
			::= { hwWlanWidsNotifyObjects 9 }

		
--  1.3.6.1.4.1.2011.6.139.8.1.2.10
		-- 1.3.6.1.4.1.2011.6.139.8.1.2.10
		hwWlanObjWidsDetAPIP OBJECT-TYPE
			SYNTAX IpAddress
			MAX-ACCESS read-only
			STATUS current
			DESCRIPTION
				"Description."
			::= { hwWlanWidsNotifyObjects 10 }

		
--  1.3.6.1.4.1.2011.6.139.8.1.2.11
		-- 1.3.6.1.4.1.2011.6.139.8.1.2.11
		hwWlanObjWidsNonWifiDeviceType OBJECT-TYPE
			SYNTAX Integer32
			MAX-ACCESS read-only
			STATUS current
			DESCRIPTION
				"Description."
			::= { hwWlanWidsNotifyObjects 11 }

		
--  1.3.6.1.4.1.2011.6.139.8.1.2.12
		-- 1.3.6.1.4.1.2011.6.139.8.1.2.12
		hwWlanObjWidsNonWifiInterChannel OBJECT-TYPE
			SYNTAX OCTET STRING
			MAX-ACCESS read-only
			STATUS current
			DESCRIPTION
				"Description."
			::= { hwWlanWidsNotifyObjects 12 }

		
--  1.3.6.1.4.1.2011.6.139.8.1.2.13
		-- 1.3.6.1.4.1.2011.6.139.8.1.2.13
		hwWlanObjWidsNonWifiRssi OBJECT-TYPE
			SYNTAX OCTET STRING
			MAX-ACCESS read-only
			STATUS current
			DESCRIPTION
				"Description."
			::= { hwWlanWidsNotifyObjects 13 }

		
--  1.3.6.1.4.1.2011.6.139.8.1.2.14
		-- 1.3.6.1.4.1.2011.6.139.8.1.2.14
		hwWlanObjWidsDetAPName OBJECT-TYPE
			SYNTAX OCTET STRING
			MAX-ACCESS read-write
			STATUS current
			DESCRIPTION
				"Description."
			::= { hwWlanWidsNotifyObjects 14 }

		
--  1.3.6.1.4.1.2011.6.139.8.1.2.15
		-- 1.3.6.1.4.1.2011.6.139.8.1.2.15
		hwWlanObjWidsDetRadioType OBJECT-TYPE
			SYNTAX Integer32
			MAX-ACCESS read-write
			STATUS current
			DESCRIPTION
				"Description."
			::= { hwWlanWidsNotifyObjects 15 }

		
		-- 1.3.6.1.4.1.2011.6.139.8.1.2.16
		hwWlanObjWidsAttackDevMAC OBJECT-TYPE
			SYNTAX MacAddress
			MAX-ACCESS read-only
			STATUS current
			DESCRIPTION
				"Description."
			::= { hwWlanWidsNotifyObjects 16 }

		
		-- 1.3.6.1.4.1.2011.6.139.8.1.2.17
		hwWlanObjWidsAttackType OBJECT-TYPE
			SYNTAX Integer32
			MAX-ACCESS read-only
			STATUS current
			DESCRIPTION
				"Description."
			::= { hwWlanWidsNotifyObjects 17 }
		
		-- 1.3.6.1.4.1.2011.6.139.8.1.2.18
		hwWlanObjWidsAttackTypeStr OBJECT-TYPE
			SYNTAX OCTET STRING
			MAX-ACCESS read-only
			STATUS current
			DESCRIPTION
				"Description."
			::= { hwWlanWidsNotifyObjects 18 }
--  1.3.6.1.4.1.2011.6.139.8.2
		-- 1.3.6.1.4.1.2011.6.139.8.2
		hwWlanWidsGloablOpt OBJECT IDENTIFIER ::= { hwWlanWids 2 }

		
--  1.3.6.1.4.1.2011.6.139.8.2.1
		-- 1.3.6.1.4.1.2011.6.139.8.2.1
		hwWidsResetDetDevTableAll OBJECT-TYPE
			SYNTAX Integer32
			MAX-ACCESS read-write
			STATUS current
			DESCRIPTION
				"Description."
			::= { hwWlanWidsGloablOpt 1 }

		
--  1.3.6.1.4.1.2011.6.139.8.2.2
		-- 1.3.6.1.4.1.2011.6.139.8.2.2
		hwWidsResetDetDevTableByType OBJECT-TYPE
			SYNTAX Integer32
			MAX-ACCESS read-write
			STATUS current
			DESCRIPTION
				"Description."
			::= { hwWlanWidsGloablOpt 2 }

		
--  1.3.6.1.4.1.2011.6.139.8.2.3
		-- 1.3.6.1.4.1.2011.6.139.8.2.3
		hwWidsResetRogueHistoryAll OBJECT-TYPE
			SYNTAX Integer32
			MAX-ACCESS read-write
			STATUS current
			DESCRIPTION
				"Description."
			::= { hwWlanWidsGloablOpt 3 }

		
--  1.3.6.1.4.1.2011.6.139.8.2.4
		-- 1.3.6.1.4.1.2011.6.139.8.2.4
		hwWidsResetRogueHistoryByDevType OBJECT-TYPE
			SYNTAX Integer32
			MAX-ACCESS read-write
			STATUS current
			DESCRIPTION
				"Description."
			::= { hwWlanWidsGloablOpt 4 }

		
		-- 1.3.6.1.4.1.2011.6.139.8.2.5
		hwWidsResetAttackDev OBJECT-TYPE
			SYNTAX Integer32
			MAX-ACCESS read-write
			STATUS current
			DESCRIPTION
				"Description."
			::= { hwWlanWidsGloablOpt 5 }

		
		-- 1.3.6.1.4.1.2011.6.139.8.2.6
		hwWidsResetAttackStat OBJECT-TYPE
			SYNTAX Integer32
			MAX-ACCESS read-write
			STATUS current
			DESCRIPTION
				"Description."
			::= { hwWlanWidsGloablOpt 6 }

		
		-- 1.3.6.1.4.1.2011.6.139.8.2.7
		hwWidsResetDynamicBlacklist OBJECT-TYPE
			SYNTAX Integer32
			MAX-ACCESS read-write
			STATUS current
			DESCRIPTION
				"Description."
			::= { hwWlanWidsGloablOpt 7 }

		
		-- 1.3.6.1.4.1.2011.6.139.8.2.8
		hwWidsResetDynamicBlacklistMac OBJECT-TYPE
			SYNTAX MacAddress
			MAX-ACCESS read-write
			STATUS current
			DESCRIPTION
				"Description."
			::= { hwWlanWidsGloablOpt 8 }

		
		-- 1.3.6.1.4.1.2011.6.139.8.2.9
		hwWidsResetAttackHistory OBJECT-TYPE
			SYNTAX Integer32
			MAX-ACCESS read-write
			STATUS current
			DESCRIPTION
				"Description."
			::= { hwWlanWidsGloablOpt 9 }
--  1.3.6.1.4.1.2011.6.139.8.3
		-- 1.3.6.1.4.1.2011.6.139.8.3
		hwWidsDetDevTable OBJECT-TYPE
			SYNTAX SEQUENCE OF HwWidsDetDevEntry
			MAX-ACCESS not-accessible
			STATUS current
			DESCRIPTION
				"Detected device table.
				"
			::= { hwWlanWids 3 }

		
--  1.3.6.1.4.1.2011.6.139.8.3.1
		-- 1.3.6.1.4.1.2011.6.139.8.3.1
		hwWidsDetDevEntry OBJECT-TYPE
			SYNTAX HwWidsDetDevEntry
			MAX-ACCESS not-accessible
			STATUS current
			DESCRIPTION
				"Ap UpdateEntry."
			INDEX { hwWidsDetDevMac }
			::= { hwWidsDetDevTable 1 }

		
		HwWidsDetDevEntry ::=
			SEQUENCE { 
				hwWidsDetDevMac
					MacAddress,
				hwWidsDetDevType
					Integer32,
				hwWidsDetDevRssi
					Integer32,
				hwWidsDetDevChannel
					Integer32,
				hwWidsDetDevSSID
					OCTET STRING,
				hwWidsDetDevRogue
					Integer32,
				hwWidsDetDevLastTime
					Unsigned32,
				hwWidsDetDevIsCountermeasuresed
					INTEGER,
				hwWidsDetDevInterference
					Integer32,
				hwWidsDetDevBSSID
					MacAddress,
				hwWidsDetDevFirstDetTime
					Unsigned32
			 }

--  1.3.6.1.4.1.2011.6.139.8.3.1.1
		-- 1.3.6.1.4.1.2011.6.139.8.3.1.1
		hwWidsDetDevMac OBJECT-TYPE
			SYNTAX MacAddress
			MAX-ACCESS not-accessible
			STATUS current
			DESCRIPTION
				"Index. 
				Detected device mac."
			::= { hwWidsDetDevEntry 1 }

		
--  1.3.6.1.4.1.2011.6.139.8.3.1.2
		-- 1.3.6.1.4.1.2011.6.139.8.3.1.2
		hwWidsDetDevType OBJECT-TYPE
			SYNTAX Integer32
			MAX-ACCESS read-only
			STATUS current
			DESCRIPTION
				"Detected device type :"
			::= { hwWidsDetDevEntry 2 }

		
--  1.3.6.1.4.1.2011.6.139.8.3.1.3
		-- 1.3.6.1.4.1.2011.6.139.8.3.1.3
		hwWidsDetDevRssi OBJECT-TYPE
			SYNTAX Integer32
			MAX-ACCESS read-only
			STATUS current
			DESCRIPTION
				"Detected device rssi"
			::= { hwWidsDetDevEntry 3 }

		
--  1.3.6.1.4.1.2011.6.139.8.3.1.4
		-- 1.3.6.1.4.1.2011.6.139.8.3.1.4
		hwWidsDetDevChannel OBJECT-TYPE
			SYNTAX Integer32
			MAX-ACCESS read-only
			STATUS current
			DESCRIPTION
				"Detected device channel"
			::= { hwWidsDetDevEntry 4 }

		
--  1.3.6.1.4.1.2011.6.139.8.3.1.5
		-- 1.3.6.1.4.1.2011.6.139.8.3.1.5
		hwWidsDetDevSSID OBJECT-TYPE
			SYNTAX OCTET STRING
			MAX-ACCESS read-only
			STATUS current
			DESCRIPTION
				"Detected device ssid.
				"
			::= { hwWidsDetDevEntry 5 }

		
--  1.3.6.1.4.1.2011.6.139.8.3.1.6
		-- 1.3.6.1.4.1.2011.6.139.8.3.1.6
		hwWidsDetDevRogue OBJECT-TYPE
			SYNTAX Integer32
			MAX-ACCESS read-only
			STATUS current
			DESCRIPTION
				"Detected device is rouge device"
			::= { hwWidsDetDevEntry 6 }

		
--  1.3.6.1.4.1.2011.6.139.8.3.1.7
		-- 1.3.6.1.4.1.2011.6.139.8.3.1.7
		hwWidsDetDevLastTime OBJECT-TYPE
			SYNTAX Unsigned32
			MAX-ACCESS read-only
			STATUS current
			DESCRIPTION
				"Last Detected time "
			::= { hwWidsDetDevEntry 7 }

		
--  1.3.6.1.4.1.2011.6.139.8.3.1.8
		-- 1.3.6.1.4.1.2011.6.139.8.3.1.8
		hwWidsDetDevIsCountermeasuresed OBJECT-TYPE
			SYNTAX INTEGER
				{
				disbale(1),
				enable(2)
				}
			MAX-ACCESS read-only
			STATUS current
			DESCRIPTION
				"Description."
			::= { hwWidsDetDevEntry 8 }

		
		-- 1.3.6.1.4.1.2011.6.139.8.3.1.9
		hwWidsDetDevInterference OBJECT-TYPE
			SYNTAX Integer32
			MAX-ACCESS read-only
			STATUS current
			DESCRIPTION
				"Description."
			::= { hwWidsDetDevEntry 9 }

		
		-- 1.3.6.1.4.1.2011.6.139.8.3.1.10
		hwWidsDetDevBSSID OBJECT-TYPE
			SYNTAX MacAddress
			MAX-ACCESS read-only
			STATUS current
			DESCRIPTION
				"Description."
			::= { hwWidsDetDevEntry 10 }

		
		-- 1.3.6.1.4.1.2011.6.139.8.3.1.11
		hwWidsDetDevFirstDetTime OBJECT-TYPE
			SYNTAX Unsigned32
			MAX-ACCESS read-only
			STATUS current
			DESCRIPTION
				"Description."
			::= { hwWidsDetDevEntry 11 }

--  1.3.6.1.4.1.2011.6.139.8.4
		-- 1.3.6.1.4.1.2011.6.139.8.4
		hwWidsDetDevMonitorTable OBJECT-TYPE
			SYNTAX SEQUENCE OF HwWidsDetDevMonitorEntry
			MAX-ACCESS not-accessible
			STATUS current
			DESCRIPTION
				"Description."
			::= { hwWlanWids 4 }

		
--  1.3.6.1.4.1.2011.6.139.8.4.1
		-- 1.3.6.1.4.1.2011.6.139.8.4.1
		hwWidsDetDevMonitorEntry OBJECT-TYPE
			SYNTAX HwWidsDetDevMonitorEntry
			MAX-ACCESS not-accessible
			STATUS current
			DESCRIPTION
				"Description."
			INDEX { hwWidsDetDevMac, hwWidsDetDevMonitorApID, hwWidsDetDevMonitorApRadioID }
			::= { hwWidsDetDevMonitorTable 1 }

		
		HwWidsDetDevMonitorEntry ::=
			SEQUENCE { 
				hwWidsDetDevMonitorApID
					Integer32,
				hwWidsDetDevMonitorApRadioID
					Integer32,
				hwWidsDetDevMonitorApMAC
					MacAddress,
				hwWidsDetDevMonitorApIP
					IpAddress,
				hwWidsDetDevMonitorApChannel
					Integer32,
				hwWidsDetDevMonitorApRssi
					Integer32,
				hwWidsDetDevMonitorApLastDetTime
					Unsigned32,
				hwWidsDetDevMonitorApCountermeasuresDev
					INTEGER,
				hwWidsDetDevMonitorDetAtt
					Integer32
			 }

--  1.3.6.1.4.1.2011.6.139.8.4.1.1
		-- 1.3.6.1.4.1.2011.6.139.8.4.1.1
		hwWidsDetDevMonitorApID OBJECT-TYPE
			SYNTAX Integer32
			MAX-ACCESS not-accessible
			STATUS current
			DESCRIPTION
				"Description."
			::= { hwWidsDetDevMonitorEntry 1 }

		
--  1.3.6.1.4.1.2011.6.139.8.4.1.2
		-- 1.3.6.1.4.1.2011.6.139.8.4.1.2
		hwWidsDetDevMonitorApRadioID OBJECT-TYPE
			SYNTAX Integer32
			MAX-ACCESS not-accessible
			STATUS current
			DESCRIPTION
				"Description."
			::= { hwWidsDetDevMonitorEntry 2 }

		
--  1.3.6.1.4.1.2011.6.139.8.4.1.3
		-- 1.3.6.1.4.1.2011.6.139.8.4.1.3
		hwWidsDetDevMonitorApMAC OBJECT-TYPE
			SYNTAX MacAddress
			MAX-ACCESS read-only
			STATUS current
			DESCRIPTION
				"Description."
			::= { hwWidsDetDevMonitorEntry 3 }

		
--  1.3.6.1.4.1.2011.6.139.8.4.1.4
		-- 1.3.6.1.4.1.2011.6.139.8.4.1.4
		hwWidsDetDevMonitorApIP OBJECT-TYPE
			SYNTAX IpAddress
			MAX-ACCESS read-only
			STATUS current
			DESCRIPTION
				"Description."
			::= { hwWidsDetDevMonitorEntry 4 }

		
--  1.3.6.1.4.1.2011.6.139.8.4.1.5
		-- 1.3.6.1.4.1.2011.6.139.8.4.1.5
		hwWidsDetDevMonitorApChannel OBJECT-TYPE
			SYNTAX Integer32
			MAX-ACCESS read-only
			STATUS current
			DESCRIPTION
				"Description."
			::= { hwWidsDetDevMonitorEntry 5 }

		
--  1.3.6.1.4.1.2011.6.139.8.4.1.6
		-- 1.3.6.1.4.1.2011.6.139.8.4.1.6
		hwWidsDetDevMonitorApRssi OBJECT-TYPE
			SYNTAX Integer32
			MAX-ACCESS read-only
			STATUS current
			DESCRIPTION
				"Description."
			::= { hwWidsDetDevMonitorEntry 6 }

		
--  1.3.6.1.4.1.2011.6.139.8.4.1.7
		-- 1.3.6.1.4.1.2011.6.139.8.4.1.7
		hwWidsDetDevMonitorApLastDetTime OBJECT-TYPE
			SYNTAX Unsigned32
			MAX-ACCESS read-only
			STATUS current
			DESCRIPTION
				"Description."
			::= { hwWidsDetDevMonitorEntry 7 }

		
--  1.3.6.1.4.1.2011.6.139.8.4.1.8
		-- 1.3.6.1.4.1.2011.6.139.8.4.1.8
		hwWidsDetDevMonitorApCountermeasuresDev OBJECT-TYPE
			SYNTAX INTEGER
				{
				disable(1),
				enable(2)
				}
			MAX-ACCESS read-only
			STATUS current
			DESCRIPTION
				"Description."
			::= { hwWidsDetDevMonitorEntry 8 }

		
		-- 1.3.6.1.4.1.2011.6.139.8.4.1.9
		hwWidsDetDevMonitorDetAtt OBJECT-TYPE
			SYNTAX Integer32
			MAX-ACCESS read-only
			STATUS current
			DESCRIPTION
				"Description."
			::= { hwWidsDetDevMonitorEntry 9 }
--  1.3.6.1.4.1.2011.6.139.8.5
		-- 1.3.6.1.4.1.2011.6.139.8.5
		hwWidsRogueHistoryTable OBJECT-TYPE
			SYNTAX SEQUENCE OF HwWidsRogueHistoryEntry
			MAX-ACCESS not-accessible
			STATUS current
			DESCRIPTION
				"Description."
			::= { hwWlanWids 5 }

		
--  1.3.6.1.4.1.2011.6.139.8.5.1
		-- 1.3.6.1.4.1.2011.6.139.8.5.1
		hwWidsRogueHistoryEntry OBJECT-TYPE
			SYNTAX HwWidsRogueHistoryEntry
			MAX-ACCESS not-accessible
			STATUS current
			DESCRIPTION
				"Description."
			INDEX { hwWidsRogueDevMac }
			::= { hwWidsRogueHistoryTable 1 }

		
		HwWidsRogueHistoryEntry ::=
			SEQUENCE { 
				hwWidsRogueDevMac
					MacAddress,
				hwWidsRogueDevType
					Integer32,
				hwWidsRogueDevRssi
					Integer32,
				hwWidsRogueDevChannel
					Integer32,
				hwWidsRogueDevSSID
					OCTET STRING,
				hwWidsRogueDevLastTime
					Unsigned32
			 }

--  1.3.6.1.4.1.2011.6.139.8.5.1.1
		-- 1.3.6.1.4.1.2011.6.139.8.5.1.1
		hwWidsRogueDevMac OBJECT-TYPE
			SYNTAX MacAddress
			MAX-ACCESS not-accessible
			STATUS current
			DESCRIPTION
				"Description."
			::= { hwWidsRogueHistoryEntry 1 }

		
--  1.3.6.1.4.1.2011.6.139.8.5.1.2
		-- 1.3.6.1.4.1.2011.6.139.8.5.1.2
		hwWidsRogueDevType OBJECT-TYPE
			SYNTAX Integer32
			MAX-ACCESS read-only
			STATUS current
			DESCRIPTION
				"Description."
			::= { hwWidsRogueHistoryEntry 2 }

		
--  1.3.6.1.4.1.2011.6.139.8.5.1.3
		-- 1.3.6.1.4.1.2011.6.139.8.5.1.3
		hwWidsRogueDevRssi OBJECT-TYPE
			SYNTAX Integer32
			MAX-ACCESS read-only
			STATUS current
			DESCRIPTION
				"Description."
			::= { hwWidsRogueHistoryEntry 3 }

		
--  1.3.6.1.4.1.2011.6.139.8.5.1.4
		-- 1.3.6.1.4.1.2011.6.139.8.5.1.4
		hwWidsRogueDevChannel OBJECT-TYPE
			SYNTAX Integer32
			MAX-ACCESS read-only
			STATUS current
			DESCRIPTION
				"Description."
			::= { hwWidsRogueHistoryEntry 4 }

		
--  1.3.6.1.4.1.2011.6.139.8.5.1.5
		-- 1.3.6.1.4.1.2011.6.139.8.5.1.5
		hwWidsRogueDevSSID OBJECT-TYPE
			SYNTAX OCTET STRING
			MAX-ACCESS read-only
			STATUS current
			DESCRIPTION
				"Description."
			::= { hwWidsRogueHistoryEntry 5 }

		
--  1.3.6.1.4.1.2011.6.139.8.5.1.6
		-- 1.3.6.1.4.1.2011.6.139.8.5.1.6
		hwWidsRogueDevLastTime OBJECT-TYPE
			SYNTAX Unsigned32
			MAX-ACCESS read-only
			STATUS current
			DESCRIPTION
				"Description."
			::= { hwWidsRogueHistoryEntry 6 }

		
--  1.3.6.1.4.1.2011.6.139.8.6
		-- 1.3.6.1.4.1.2011.6.139.8.6
		hwSsidWhitelistTable OBJECT-TYPE
			SYNTAX SEQUENCE OF HwSsidWhitelistEntry
			MAX-ACCESS not-accessible
			STATUS current
			DESCRIPTION
				"Description."
			::= { hwWlanWids 6 }

		
--  1.3.6.1.4.1.2011.6.139.8.6.1
		-- 1.3.6.1.4.1.2011.6.139.8.6.1
		hwSsidWhitelistEntry OBJECT-TYPE
			SYNTAX HwSsidWhitelistEntry
			MAX-ACCESS not-accessible
			STATUS current
			DESCRIPTION
				"Description."
			INDEX { hwSsidWhitelistSsid }
			::= { hwSsidWhitelistTable 1 }

		
		HwSsidWhitelistEntry ::=
			SEQUENCE { 
				hwSsidWhitelistSsid
					OCTET STRING,
				hwSsidWhitelisttRowStatus
					RowStatus
			 }

--  1.3.6.1.4.1.2011.6.139.8.6.1.1
		-- 1.3.6.1.4.1.2011.6.139.8.6.1.1
		hwSsidWhitelistSsid OBJECT-TYPE
			SYNTAX OCTET STRING
			MAX-ACCESS not-accessible
			STATUS current
			DESCRIPTION
				"Description."
			::= { hwSsidWhitelistEntry 1 }

		
--  1.3.6.1.4.1.2011.6.139.8.6.1.2
		-- 1.3.6.1.4.1.2011.6.139.8.6.1.2
		hwSsidWhitelisttRowStatus OBJECT-TYPE
			SYNTAX RowStatus
			MAX-ACCESS read-create
			STATUS current
			DESCRIPTION
				"Description."
			::= { hwSsidWhitelistEntry 2 }

		
--  1.3.6.1.4.1.2011.6.139.8.7
		-- 1.3.6.1.4.1.2011.6.139.8.7
		hwWidsDetNonWifiDevTable OBJECT-TYPE
			SYNTAX SEQUENCE OF HwWidsDetNonWifiDevEntry
			MAX-ACCESS not-accessible
			STATUS current
			DESCRIPTION
				"Description."
			::= { hwWlanWids 7 }

		
--  1.3.6.1.4.1.2011.6.139.8.7.1
		-- 1.3.6.1.4.1.2011.6.139.8.7.1
		hwWidsDetNonWifiDevEntry OBJECT-TYPE
			SYNTAX HwWidsDetNonWifiDevEntry
			MAX-ACCESS not-accessible
			STATUS current
			DESCRIPTION
				"Description."
			INDEX { hwWidsDetNonWifiDevMonitorApMac, hwWidsDetNonWifiDevMonitorRadioId, hwWidsDetNonWifiType }
			::= { hwWidsDetNonWifiDevTable 1 }

		
		HwWidsDetNonWifiDevEntry ::=
			SEQUENCE { 
				hwWidsDetNonWifiDevMonitorApMac
					MacAddress,
				hwWidsDetNonWifiDevMonitorRadioId
					Integer32,
				hwWidsDetNonWifiType
					Integer32,
				hwWidsDetNonWifiRssi
					OCTET STRING,
				hwWidsDetNonWifiFrequencyType
					Integer32,
				hwWidsDetNonWifiChannel
					OCTET STRING,
				hwWidsDetNonWifiDevLastTime
					Integer32,
				hwWidsDetNonWifiCenterFrequency
					Integer32,
				hwWidsDetNonWifiBandwidth
					Integer32,
				hwWidsDetNonWifiDutycycle
					Integer32,
				hwWidsDetNonWifiInterferenceLevel
					Integer32,
				hwWidsDetNonWifiDevMonitorAPName
					OCTET STRING,
				hwWidsDetNonWifiDevMonitorAPID
					Integer32,
				hwWidsDetNonWifiDevRadioType
					Integer32,
				hwWidsDetNonWifiDevMonitorAPChannel
					Integer32,
				hwWidsDetNonWifiDevFirstTime
					Integer32
			 }

--  1.3.6.1.4.1.2011.6.139.8.7.1.1
		-- 1.3.6.1.4.1.2011.6.139.8.7.1.1
		hwWidsDetNonWifiDevMonitorApMac OBJECT-TYPE
			SYNTAX MacAddress
			MAX-ACCESS not-accessible
			STATUS current
			DESCRIPTION
				"Description."
			::= { hwWidsDetNonWifiDevEntry 1 }

		
--  1.3.6.1.4.1.2011.6.139.8.7.1.2
		-- 1.3.6.1.4.1.2011.6.139.8.7.1.2
		hwWidsDetNonWifiDevMonitorRadioId OBJECT-TYPE
			SYNTAX Integer32
			MAX-ACCESS not-accessible
			STATUS current
			DESCRIPTION
				"Description."
			::= { hwWidsDetNonWifiDevEntry 2 }

		
--  1.3.6.1.4.1.2011.6.139.8.7.1.3
		-- 1.3.6.1.4.1.2011.6.139.8.7.1.3
		hwWidsDetNonWifiType OBJECT-TYPE
			SYNTAX Integer32
			MAX-ACCESS not-accessible
			STATUS current
			DESCRIPTION
				"Description."
			::= { hwWidsDetNonWifiDevEntry 3 }

		
--  1.3.6.1.4.1.2011.6.139.8.7.1.4
		-- 1.3.6.1.4.1.2011.6.139.8.7.1.4
		hwWidsDetNonWifiRssi OBJECT-TYPE
			SYNTAX OCTET STRING
			MAX-ACCESS read-only
			STATUS current
			DESCRIPTION
				"Description."
			::= { hwWidsDetNonWifiDevEntry 4 }

		
--  1.3.6.1.4.1.2011.6.139.8.7.1.5
		-- 1.3.6.1.4.1.2011.6.139.8.7.1.5
		hwWidsDetNonWifiFrequencyType OBJECT-TYPE
			SYNTAX Integer32
			MAX-ACCESS read-only
			STATUS current
			DESCRIPTION
				"Description."
			::= { hwWidsDetNonWifiDevEntry 5 }

		
--  1.3.6.1.4.1.2011.6.139.8.7.1.6
		-- 1.3.6.1.4.1.2011.6.139.8.7.1.6
		hwWidsDetNonWifiChannel OBJECT-TYPE
			SYNTAX OCTET STRING
			MAX-ACCESS read-only
			STATUS current
			DESCRIPTION
				"Description."
			::= { hwWidsDetNonWifiDevEntry 6 }

		
--  1.3.6.1.4.1.2011.6.139.8.7.1.7
		-- 1.3.6.1.4.1.2011.6.139.8.7.1.7
		hwWidsDetNonWifiDevLastTime OBJECT-TYPE
			SYNTAX Integer32
			MAX-ACCESS read-only
			STATUS current
			DESCRIPTION
				"Description."
			::= { hwWidsDetNonWifiDevEntry 7 }

		
--  1.3.6.1.4.1.2011.6.139.8.7.1.8
		-- 1.3.6.1.4.1.2011.6.139.8.7.1.8
		hwWidsDetNonWifiCenterFrequency OBJECT-TYPE
			SYNTAX Integer32
			MAX-ACCESS read-only
			STATUS current
			DESCRIPTION
				"Description."
			::= { hwWidsDetNonWifiDevEntry 8 }

		
--  1.3.6.1.4.1.2011.6.139.8.7.1.9
		-- 1.3.6.1.4.1.2011.6.139.8.7.1.9
		hwWidsDetNonWifiBandwidth OBJECT-TYPE
			SYNTAX Integer32
			MAX-ACCESS read-only
			STATUS current
			DESCRIPTION
				"Description."
			::= { hwWidsDetNonWifiDevEntry 9 }

		
--  1.3.6.1.4.1.2011.6.139.8.7.1.10
		-- 1.3.6.1.4.1.2011.6.139.8.7.1.10
		hwWidsDetNonWifiDutycycle OBJECT-TYPE
			SYNTAX Integer32
			MAX-ACCESS read-only
			STATUS current
			DESCRIPTION
				"Description."
			::= { hwWidsDetNonWifiDevEntry 10 }

		
--  1.3.6.1.4.1.2011.6.139.8.7.1.11
		-- 1.3.6.1.4.1.2011.6.139.8.7.1.11
		hwWidsDetNonWifiInterferenceLevel OBJECT-TYPE
			SYNTAX Integer32
			MAX-ACCESS read-only
			STATUS current
			DESCRIPTION
				"Description."
			::= { hwWidsDetNonWifiDevEntry 11 }

		
		-- 1.3.6.1.4.1.2011.6.139.8.7.1.12
		hwWidsDetNonWifiDevMonitorAPName OBJECT-TYPE
			SYNTAX OCTET STRING
			MAX-ACCESS read-only
			STATUS current
			DESCRIPTION
				"Description."
			::= { hwWidsDetNonWifiDevEntry 12 }
		-- 1.3.6.1.4.1.2011.6.139.8.7.1.13
		hwWidsDetNonWifiDevMonitorAPID OBJECT-TYPE
			SYNTAX Integer32
			MAX-ACCESS read-only
			STATUS current
			DESCRIPTION
				"Description."
			::= { hwWidsDetNonWifiDevEntry 13 }
		-- 1.3.6.1.4.1.2011.6.139.8.7.1.14
		hwWidsDetNonWifiDevRadioType OBJECT-TYPE
			SYNTAX Integer32
			MAX-ACCESS read-only
			STATUS current
			DESCRIPTION
				"Description."
			::= { hwWidsDetNonWifiDevEntry 14 }
		-- 1.3.6.1.4.1.2011.6.139.8.7.1.15
		hwWidsDetNonWifiDevMonitorAPChannel OBJECT-TYPE
			SYNTAX Integer32
			MAX-ACCESS read-only
			STATUS current
			DESCRIPTION
				"Description."
			::= { hwWidsDetNonWifiDevEntry 15 }

		-- 1.3.6.1.4.1.2011.6.139.8.7.1.16
		hwWidsDetNonWifiDevFirstTime OBJECT-TYPE
			SYNTAX Integer32
			MAX-ACCESS read-only
			STATUS current
			DESCRIPTION
				"Description."
			::= { hwWidsDetNonWifiDevEntry 16 }


		-- 1.3.6.1.4.1.2011.6.139.8.8
		hwWidsAttackHistoryTable OBJECT-TYPE
			SYNTAX SEQUENCE OF HwWidsAttackHistoryEntry
			MAX-ACCESS not-accessible
			STATUS current
			DESCRIPTION
				"Description."
			::= { hwWlanWids 8 }

		
		-- 1.3.6.1.4.1.2011.6.139.8.8.1
		hwWidsAttackHistoryEntry OBJECT-TYPE
			SYNTAX HwWidsAttackHistoryEntry
			MAX-ACCESS not-accessible
			STATUS current
			DESCRIPTION
				"Description."
			INDEX { hwWidsAttackHistorySeq, hwWidsAttackHistorySubSeq }
			::= { hwWidsAttackHistoryTable 1 }

		
		HwWidsAttackHistoryEntry ::=
			SEQUENCE { 
				hwWidsAttackHistorySeq
					Unsigned32,
				hwWidsAttackHistorySubSeq
					Unsigned32,
				hwWidsAttackHistoryDevMac
					MacAddress,
				hwWidsAttackHistoryDevType
					Integer32,
				hwWidsAttackHistoryRssi
					Integer32,
				hwWidsAttackHistoryChannel
					Integer32,
				hwWidsAttackHistoryAttackType
					Integer32,
				hwWidsAttackHistoryPacketBmp1
					Integer32,
				hwWidsAttackHistoryPacketBmp2
					Integer32,
				hwWidsAttackHistorySSID
					OCTET STRING,
				hwWidsAttackHistoryDetTime
					Unsigned32,
				hwWidsAttackHistoryDetectorApId
					Integer32
			 }

		-- 1.3.6.1.4.1.2011.6.139.8.8.1.1
		hwWidsAttackHistorySeq OBJECT-TYPE
			SYNTAX Unsigned32
			MAX-ACCESS not-accessible
			STATUS current
			DESCRIPTION
				"Description."
			::= { hwWidsAttackHistoryEntry 1 }

		
		-- 1.3.6.1.4.1.2011.6.139.8.8.1.2
		hwWidsAttackHistorySubSeq OBJECT-TYPE
			SYNTAX Unsigned32
			MAX-ACCESS not-accessible
			STATUS current
			DESCRIPTION
				"Description."
			::= { hwWidsAttackHistoryEntry 2 }

		
		-- 1.3.6.1.4.1.2011.6.139.8.8.1.3
		hwWidsAttackHistoryDevMac OBJECT-TYPE
			SYNTAX MacAddress
			MAX-ACCESS read-only
			STATUS current
			DESCRIPTION
				"Description."
			::= { hwWidsAttackHistoryEntry 3 }

		
		-- 1.3.6.1.4.1.2011.6.139.8.8.1.4
		hwWidsAttackHistoryDevType OBJECT-TYPE
			SYNTAX Integer32
			MAX-ACCESS read-only
			STATUS current
			DESCRIPTION
				"Description."
			::= { hwWidsAttackHistoryEntry 4 }

		
		-- 1.3.6.1.4.1.2011.6.139.8.8.1.5
		hwWidsAttackHistoryRssi OBJECT-TYPE
			SYNTAX Integer32
			MAX-ACCESS read-only
			STATUS current
			DESCRIPTION
				"Description."
			::= { hwWidsAttackHistoryEntry 5 }

		
		-- 1.3.6.1.4.1.2011.6.139.8.8.1.6
		hwWidsAttackHistoryChannel OBJECT-TYPE
			SYNTAX Integer32
			MAX-ACCESS read-only
			STATUS current
			DESCRIPTION
				"Description."
			::= { hwWidsAttackHistoryEntry 6 }

		
		-- 1.3.6.1.4.1.2011.6.139.8.8.1.7
		hwWidsAttackHistoryAttackType OBJECT-TYPE
			SYNTAX Integer32
			MAX-ACCESS read-only
			STATUS current
			DESCRIPTION
				"Description."
			::= { hwWidsAttackHistoryEntry 7 }

		
		-- 1.3.6.1.4.1.2011.6.139.8.8.1.8
		hwWidsAttackHistoryPacketBmp1 OBJECT-TYPE
			SYNTAX Integer32
			MAX-ACCESS read-only
			STATUS current
			DESCRIPTION
				"Description."
			::= { hwWidsAttackHistoryEntry 8 }
		
		-- 1.3.6.1.4.1.2011.6.139.8.8.1.9
		hwWidsAttackHistoryPacketBmp2 OBJECT-TYPE
			SYNTAX Integer32
			MAX-ACCESS read-only
			STATUS current
			DESCRIPTION
				"Description."
			::= { hwWidsAttackHistoryEntry 9 }

		-- 1.3.6.1.4.1.2011.6.139.8.8.1.10
		hwWidsAttackHistorySSID OBJECT-TYPE
			SYNTAX OCTET STRING
			MAX-ACCESS read-only
			STATUS current
			DESCRIPTION
				"Description."
			::= { hwWidsAttackHistoryEntry 10 }

		
		-- 1.3.6.1.4.1.2011.6.139.8.8.1.11
		hwWidsAttackHistoryDetTime OBJECT-TYPE
			SYNTAX Unsigned32
			MAX-ACCESS read-only
			STATUS current
			DESCRIPTION
				"Description."
			::= { hwWidsAttackHistoryEntry 11 }

		
		-- 1.3.6.1.4.1.2011.6.139.8.8.1.12
		hwWidsAttackHistoryDetectorApId OBJECT-TYPE
			SYNTAX Integer32
			MAX-ACCESS read-only
			STATUS current
			DESCRIPTION
				"Description."
			::= { hwWidsAttackHistoryEntry 12 }
		-- 1.3.6.1.4.1.2011.6.139.8.9
		hwWidsEnableAPTable OBJECT-TYPE
			SYNTAX SEQUENCE OF HwWidsEnableAPEntry
			MAX-ACCESS not-accessible
			STATUS current
			DESCRIPTION
				"Description."
			::= { hwWlanWids 9 }

		
		-- 1.3.6.1.4.1.2011.6.139.8.9.1
		hwWidsEnableAPEntry OBJECT-TYPE
			SYNTAX HwWidsEnableAPEntry
			MAX-ACCESS not-accessible
			STATUS current
			DESCRIPTION
				"Description."
			INDEX { hwWidsEnableAPID }
			::= { hwWidsEnableAPTable 1 }

		
		HwWidsEnableAPEntry ::=
			SEQUENCE { 
				hwWidsEnableAPID
					Integer32,
				hwWidsEnableDevDetSwitch
					Integer32,
				hwWidsEnableAttackDetSwitch
					Integer32,
				hwWidsEnableAPName
					OCTET STRING
			 }

		-- 1.3.6.1.4.1.2011.6.139.8.9.1.1
		hwWidsEnableAPID OBJECT-TYPE
			SYNTAX Integer32
			MAX-ACCESS not-accessible
			STATUS current
			DESCRIPTION
				"Description."
			::= { hwWidsEnableAPEntry 1 }

		
		-- 1.3.6.1.4.1.2011.6.139.8.9.1.2
		hwWidsEnableDevDetSwitch OBJECT-TYPE
			SYNTAX Integer32
			MAX-ACCESS read-only
			STATUS current
			DESCRIPTION
				"Description."
			::= { hwWidsEnableAPEntry 2 }

		
		-- 1.3.6.1.4.1.2011.6.139.8.9.1.3
		hwWidsEnableAttackDetSwitch OBJECT-TYPE
			SYNTAX Integer32
			MAX-ACCESS read-only
			STATUS current
			DESCRIPTION
				"Description."
			::= { hwWidsEnableAPEntry 3 }

		
		-- 1.3.6.1.4.1.2011.6.139.8.9.1.4
		hwWidsEnableAPName OBJECT-TYPE
			SYNTAX OCTET STRING
			MAX-ACCESS read-only
			STATUS current
			DESCRIPTION
				"Description."
			::= { hwWidsEnableAPEntry 4 }
		-- 1.3.6.1.4.1.2011.6.139.8.10
		hwWidsAttackStatTable OBJECT IDENTIFIER ::= { hwWlanWids 10 }

		
		-- 1.3.6.1.4.1.2011.6.139.8.10.1
		hwWidsAttackStatProbeRequestFloodAttack OBJECT-TYPE
			SYNTAX Unsigned32
			MAX-ACCESS read-only
			STATUS current
			DESCRIPTION
				"Description."
			::= { hwWidsAttackStatTable 1 }

		
		-- 1.3.6.1.4.1.2011.6.139.8.10.2
		hwWidsAttackStatAuthRequestFloodAttack OBJECT-TYPE
			SYNTAX Unsigned32
			MAX-ACCESS read-only
			STATUS current
			DESCRIPTION
				"Description."
			::= { hwWidsAttackStatTable 2 }

		
		-- 1.3.6.1.4.1.2011.6.139.8.10.3
		hwWidsAttackStatDeAuthenFloodAttack OBJECT-TYPE
			SYNTAX Unsigned32
			MAX-ACCESS read-only
			STATUS current
			DESCRIPTION
				"Description."
			::= { hwWidsAttackStatTable 3 }

		
		-- 1.3.6.1.4.1.2011.6.139.8.10.4
		hwWidsAttackStatAssocReqFloodAttack OBJECT-TYPE
			SYNTAX Unsigned32
			MAX-ACCESS read-only
			STATUS current
			DESCRIPTION
				"Description."
			::= { hwWidsAttackStatTable 4 }

		
		-- 1.3.6.1.4.1.2011.6.139.8.10.5
		hwWidsAttackStatDisassocReqFloodAttack OBJECT-TYPE
			SYNTAX Unsigned32
			MAX-ACCESS read-only
			STATUS current
			DESCRIPTION
				"Description."
			::= { hwWidsAttackStatTable 5 }

		
		-- 1.3.6.1.4.1.2011.6.139.8.10.6
		hwWidsAttackStatReassocReqFloodAttack OBJECT-TYPE
			SYNTAX Unsigned32
			MAX-ACCESS read-only
			STATUS current
			DESCRIPTION
				"Description."
			::= { hwWidsAttackStatTable 6 }

		
		-- 1.3.6.1.4.1.2011.6.139.8.10.7
		hwWidsAttackStatActionFloodAttack OBJECT-TYPE
			SYNTAX Unsigned32
			MAX-ACCESS read-only
			STATUS current
			DESCRIPTION
				"Description."
			::= { hwWidsAttackStatTable 7 }

		
		-- 1.3.6.1.4.1.2011.6.139.8.10.8
		hwWidsAttackStatNullDataFloodAttack OBJECT-TYPE
			SYNTAX Unsigned32
			MAX-ACCESS read-only
			STATUS current
			DESCRIPTION
				"Description."
			::= { hwWidsAttackStatTable 8 }

		
		-- 1.3.6.1.4.1.2011.6.139.8.10.9
		hwWidsAttackStatWeakIvAttack OBJECT-TYPE
			SYNTAX Unsigned32
			MAX-ACCESS read-only
			STATUS current
			DESCRIPTION
				"Description."
			::= { hwWidsAttackStatTable 9 }

		
		-- 1.3.6.1.4.1.2011.6.139.8.10.10
		hwWidsAttackStatDeauthSpoofAttack OBJECT-TYPE
			SYNTAX Unsigned32
			MAX-ACCESS read-only
			STATUS current
			DESCRIPTION
				"Description."
			::= { hwWidsAttackStatTable 10 }

		
		-- 1.3.6.1.4.1.2011.6.139.8.10.11
		hwWidsAttackStatDisassocSpoofAttack OBJECT-TYPE
			SYNTAX Unsigned32
			MAX-ACCESS read-only
			STATUS current
			DESCRIPTION
				"Description."
			::= { hwWidsAttackStatTable 11 }

		
		-- 1.3.6.1.4.1.2011.6.139.8.10.12
		hwWidsAttackStatWepShareKeyAttack OBJECT-TYPE
			SYNTAX Unsigned32
			MAX-ACCESS read-only
			STATUS current
			DESCRIPTION
				"Description."
			::= { hwWidsAttackStatTable 12 }

		
		-- 1.3.6.1.4.1.2011.6.139.8.10.13
		hwWidsAttackStatWpaAttack OBJECT-TYPE
			SYNTAX Unsigned32
			MAX-ACCESS read-only
			STATUS current
			DESCRIPTION
				"Description."
			::= { hwWidsAttackStatTable 13 }

		
		-- 1.3.6.1.4.1.2011.6.139.8.10.14
		hwWidsAttackStatWpa2Attack OBJECT-TYPE
			SYNTAX Unsigned32
			MAX-ACCESS read-only
			STATUS current
			DESCRIPTION
				"Description."
			::= { hwWidsAttackStatTable 14 }

		
		-- 1.3.6.1.4.1.2011.6.139.8.10.15
		hwWidsAttackStatWapiAttack OBJECT-TYPE
			SYNTAX Unsigned32
			MAX-ACCESS read-only
			STATUS current
			DESCRIPTION
				"Description."
			::= { hwWidsAttackStatTable 15 }

		
		-- 1.3.6.1.4.1.2011.6.139.8.10.16
		hwWidsAttackStatStartTime OBJECT-TYPE
			SYNTAX Unsigned32
			MAX-ACCESS read-only
			STATUS current
			DESCRIPTION
				"Description."
			::= { hwWidsAttackStatTable 16 }

		
		-- 1.3.6.1.4.1.2011.6.139.8.10.17
		hwWidsAttackStatEAPOLStartFloodAttack OBJECT-TYPE
			SYNTAX Unsigned32
			MAX-ACCESS read-only
			STATUS current
			DESCRIPTION
				"Description."
			::= { hwWidsAttackStatTable 17 }

		
		-- 1.3.6.1.4.1.2011.6.139.8.10.18
		hwWidsAttackStatEAPOLLogoffFloodAttack OBJECT-TYPE
			SYNTAX Unsigned32
			MAX-ACCESS read-only
			STATUS current
			DESCRIPTION
				"Description."
			::= { hwWidsAttackStatTable 18 }   
			
  		-- 1.3.6.1.4.1.2011.6.139.8.10.19
		hwWidsAttackStatNullQosFloodAttack  OBJECT-TYPE
			SYNTAX Unsigned32
			MAX-ACCESS read-only
			STATUS current
			DESCRIPTION
				"Description."
			::= { hwWidsAttackStatTable 19 }

		-- 1.3.6.1.4.1.2011.6.139.8.11
		hwWidsDynamicBlacklistTable OBJECT-TYPE
			SYNTAX SEQUENCE OF HwWidsDynamicBlacklistEntry
			MAX-ACCESS not-accessible
			STATUS current
			DESCRIPTION
				"Description."
			::= { hwWlanWids 11 }

		
		-- 1.3.6.1.4.1.2011.6.139.8.11.1
		hwWidsDynamicBlacklistEntry OBJECT-TYPE
			SYNTAX HwWidsDynamicBlacklistEntry
			MAX-ACCESS not-accessible
			STATUS current
			DESCRIPTION
				"Description."
			INDEX { hwWidsDynamicBlacklistDevMac }
			::= { hwWidsDynamicBlacklistTable 1 }

		
		HwWidsDynamicBlacklistEntry ::=
			SEQUENCE { 
				hwWidsDynamicBlacklistDevMac
					MacAddress,
				hwWidsDynamicBlacklistDevType
					Integer32,
				hwWidsDynamicBlacklistDevAttackType
					Integer32,
				hwWidsDynamicBlacklistAttackPacketBmp1
					Integer32,
				hwWidsDynamicBlacklistAttackPacketBmp2
					Integer32,
				hwWidsDynamicBlacklistLastTime
					Unsigned32
			 }

		-- 1.3.6.1.4.1.2011.6.139.8.11.1.1
		hwWidsDynamicBlacklistDevMac OBJECT-TYPE
			SYNTAX MacAddress
			MAX-ACCESS not-accessible
			STATUS current
			DESCRIPTION
				"Description."
			::= { hwWidsDynamicBlacklistEntry 1 }

		
		-- 1.3.6.1.4.1.2011.6.139.8.11.1.2
		hwWidsDynamicBlacklistDevType OBJECT-TYPE
			SYNTAX Integer32
			MAX-ACCESS read-only
			STATUS current
			DESCRIPTION
				"Description."
			::= { hwWidsDynamicBlacklistEntry 2 }

		
		-- 1.3.6.1.4.1.2011.6.139.8.11.1.3
		hwWidsDynamicBlacklistDevAttackType OBJECT-TYPE
			SYNTAX Integer32
			MAX-ACCESS read-only
			STATUS current
			DESCRIPTION
				"Description."
			::= { hwWidsDynamicBlacklistEntry 3 }

		
		-- 1.3.6.1.4.1.2011.6.139.8.11.1.4
		hwWidsDynamicBlacklistAttackPacketBmp1 OBJECT-TYPE
			SYNTAX Integer32
			MAX-ACCESS read-only
			STATUS current
			DESCRIPTION
				"Description."
			::= { hwWidsDynamicBlacklistEntry 4 }

		
		-- 1.3.6.1.4.1.2011.6.139.8.11.1.5
		hwWidsDynamicBlacklistAttackPacketBmp2 OBJECT-TYPE
			SYNTAX Integer32
			MAX-ACCESS read-only
			STATUS current
			DESCRIPTION
				"Description."
			::= { hwWidsDynamicBlacklistEntry 5 }

		
		-- 1.3.6.1.4.1.2011.6.139.8.11.1.6
		hwWidsDynamicBlacklistLastTime OBJECT-TYPE
			SYNTAX Unsigned32
			MAX-ACCESS read-only
			STATUS current
			DESCRIPTION
				"Description."
			::= { hwWidsDynamicBlacklistEntry 6 }

		-- 1.3.6.1.4.1.2011.6.139.8.12
		hwWidsDynamicBlacklistAPTable OBJECT-TYPE
			SYNTAX SEQUENCE OF HwWidsDynamicBlacklistAPEntry
			MAX-ACCESS not-accessible
			STATUS current
			DESCRIPTION
				"Description."
			::= { hwWlanWids 12 }

		
		-- 1.3.6.1.4.1.2011.6.139.8.12.1
		hwWidsDynamicBlacklistAPEntry OBJECT-TYPE
			SYNTAX HwWidsDynamicBlacklistAPEntry
			MAX-ACCESS not-accessible
			STATUS current
			DESCRIPTION
				"Description."
			INDEX { hwWidsDynamicBlacklistDevMac, hwWidsDynamicBlacklistApID }
			::= { hwWidsDynamicBlacklistAPTable 1 }

		
		HwWidsDynamicBlacklistAPEntry ::=
			SEQUENCE { 
				hwWidsDynamicBlacklistApID
					Integer32,
				hwWidsDynamicBlacklistAPMac
					MacAddress,
				hwWidsDynamicBlacklistApIP
					IpAddress,
				hwWidsDynamicBlacklistAttackType
					Integer32,
				hwWidsDynamicBlacklistAPLastTime
					Unsigned32
			 }

		-- 1.3.6.1.4.1.2011.6.139.8.12.1.1
		hwWidsDynamicBlacklistApID OBJECT-TYPE
			SYNTAX Integer32
			MAX-ACCESS not-accessible
			STATUS current
			DESCRIPTION
				"Description."
			::= { hwWidsDynamicBlacklistAPEntry 1 }

		
		-- 1.3.6.1.4.1.2011.6.139.8.12.1.2
		hwWidsDynamicBlacklistAPMac OBJECT-TYPE
			SYNTAX MacAddress
			MAX-ACCESS read-only
			STATUS current
			DESCRIPTION
				"Description."
			::= { hwWidsDynamicBlacklistAPEntry 2 }

		
		-- 1.3.6.1.4.1.2011.6.139.8.12.1.3
		hwWidsDynamicBlacklistApIP OBJECT-TYPE
			SYNTAX IpAddress
			MAX-ACCESS read-only
			STATUS current
			DESCRIPTION
				"Description."
			::= { hwWidsDynamicBlacklistAPEntry 3 }

		
		-- 1.3.6.1.4.1.2011.6.139.8.12.1.4
		hwWidsDynamicBlacklistAttackType OBJECT-TYPE
			SYNTAX Integer32
			MAX-ACCESS read-only
			STATUS current
			DESCRIPTION
				"Description."
			::= { hwWidsDynamicBlacklistAPEntry 4 }
		
		-- 1.3.6.1.4.1.2011.6.139.8.12.1.5
		hwWidsDynamicBlacklistAPLastTime OBJECT-TYPE
			SYNTAX Unsigned32
			MAX-ACCESS read-only
			STATUS current
			DESCRIPTION
				"Description."
			::= { hwWidsDynamicBlacklistAPEntry 5 }

		-- 1.3.6.1.4.1.2011.6.139.8.13
		hwWlanWidsObjects OBJECT IDENTIFIER ::= { hwWlanWids 13 }

		-- BEGIN: added by lishijun 00209691, 2013/04/20, for spectrum analysis detected non-wifi history table
		-- 1.3.6.1.4.1.2011.6.139.8.13.1
		hwWidsDetNonWifiDevHistTable OBJECT-TYPE
			SYNTAX SEQUENCE OF HwWidsDetNonWifiDevHistEntry
			MAX-ACCESS not-accessible
			STATUS current
			DESCRIPTION
				"Description."
			::= { hwWlanWidsObjects 1 }

		
		-- 1.3.6.1.4.1.2011.6.139.8.13.1.1
		hwWidsDetNonWifiDevHistEntry OBJECT-TYPE
			SYNTAX HwWidsDetNonWifiDevHistEntry
			MAX-ACCESS not-accessible
			STATUS current
			DESCRIPTION
				"Description."
			INDEX { hwWidsDetNonWifiHistIndex }
			::= { hwWidsDetNonWifiDevHistTable 1 }

		
		HwWidsDetNonWifiDevHistEntry ::=
			SEQUENCE { 
				hwWidsDetNonWifiHistIndex
					Integer32,
				hwWidsDetNonWifiHistMonitorApMac
					MacAddress,
				hwWidsDetNonWifiHistMonitorAPName
					OCTET STRING,
				hwWidsDetNonWifiHistMonitorAPID
					Integer32,
				hwWidsDetNonWifiHistMonitorRadioId
					Integer32,
				hwWidsDetNonWifiHistMonitorRadioType
					Integer32,
				hwWidsDetNonWifiHistMonitorAPChannel
					Integer32,					
				hwWidsDetNonWifiHistDevType
					Integer32,
				hwWidsDetNonWifiHistRssi
					OCTET STRING,
				hwWidsDetNonWifiHistFrequencyType
					Integer32,
				hwWidsDetNonWifiHistChannel
					OCTET STRING,
				hwWidsDetNonWifiHistDevLastTime
					Integer32,
				hwWidsDetNonWifiHistCenterFrequency
					Integer32,
				hwWidsDetNonWifiHistBandwidth
					Integer32,
				hwWidsDetNonWifiHistDutycycle
					Integer32,
				hwWidsDetNonWifiHistInterferenceLevel
					Integer32,
				hwWidsDetNonWifiHistDevFirstTime
					Integer32
			 }

		-- 1.3.6.1.4.1.2011.6.139.8.13.1.1.1
		hwWidsDetNonWifiHistIndex OBJECT-TYPE
			SYNTAX Integer32
			MAX-ACCESS not-accessible
			STATUS current
			DESCRIPTION
				"Description."
			::= { hwWidsDetNonWifiDevHistEntry 1 }

		-- 1.3.6.1.4.1.2011.6.139.8.13.1.1.2
		hwWidsDetNonWifiHistMonitorApMac OBJECT-TYPE
			SYNTAX MacAddress
			MAX-ACCESS read-only
			STATUS current
			DESCRIPTION
				"Description."
			::= { hwWidsDetNonWifiDevHistEntry 2 }

		-- 1.3.6.1.4.1.2011.6.139.8.13.1.1.3
		hwWidsDetNonWifiHistMonitorAPName OBJECT-TYPE
			SYNTAX OCTET STRING
			MAX-ACCESS read-only
			STATUS current
			DESCRIPTION
				"Description."
			::= { hwWidsDetNonWifiDevHistEntry 3 }
		
		-- 1.3.6.1.4.1.2011.6.139.8.13.1.1.4
		hwWidsDetNonWifiHistMonitorAPID OBJECT-TYPE
			SYNTAX Integer32
			MAX-ACCESS read-only
			STATUS current
			DESCRIPTION
				"Description."
			::= { hwWidsDetNonWifiDevHistEntry 4 }
		
		-- 1.3.6.1.4.1.2011.6.139.8.13.1.1.5
		hwWidsDetNonWifiHistMonitorRadioId OBJECT-TYPE
			SYNTAX Integer32
			MAX-ACCESS read-only
			STATUS current
			DESCRIPTION
				"Description."
			::= { hwWidsDetNonWifiDevHistEntry 5 }

		-- 1.3.6.1.4.1.2011.6.139.8.13.1.1.6
		hwWidsDetNonWifiHistMonitorRadioType OBJECT-TYPE
			SYNTAX Integer32
			MAX-ACCESS read-only
			STATUS current
			DESCRIPTION
				"Description."
			::= { hwWidsDetNonWifiDevHistEntry 6 }
		
		-- 1.3.6.1.4.1.2011.6.139.8.13.1.1.7
		hwWidsDetNonWifiHistMonitorAPChannel OBJECT-TYPE
			SYNTAX Integer32
			MAX-ACCESS read-only
			STATUS current
			DESCRIPTION
				"Description."
			::= { hwWidsDetNonWifiDevHistEntry 7 }
		
		-- 1.3.6.1.4.1.2011.6.139.8.13.1.1.8
		hwWidsDetNonWifiHistDevType OBJECT-TYPE
			SYNTAX Integer32
			MAX-ACCESS read-only
			STATUS current
			DESCRIPTION
				"Description."
			::= { hwWidsDetNonWifiDevHistEntry 8 }

		-- 1.3.6.1.4.1.2011.6.139.8.13.1.1.9
		hwWidsDetNonWifiHistRssi OBJECT-TYPE
			SYNTAX OCTET STRING
			MAX-ACCESS read-only
			STATUS current
			DESCRIPTION
				"Description."
			::= { hwWidsDetNonWifiDevHistEntry 9 }

		-- 1.3.6.1.4.1.2011.6.139.8.13.1.1.10
		hwWidsDetNonWifiHistFrequencyType OBJECT-TYPE
			SYNTAX Integer32
			MAX-ACCESS read-only
			STATUS current
			DESCRIPTION
				"Description."
			::= { hwWidsDetNonWifiDevHistEntry 10 }

		-- 1.3.6.1.4.1.2011.6.139.8.13.1.1.11
		hwWidsDetNonWifiHistChannel OBJECT-TYPE
			SYNTAX OCTET STRING
			MAX-ACCESS read-only
			STATUS current
			DESCRIPTION
				"Description."
			::= { hwWidsDetNonWifiDevHistEntry 11 }

		-- 1.3.6.1.4.1.2011.6.139.8.13.1.1.12
		hwWidsDetNonWifiHistDevLastTime OBJECT-TYPE
			SYNTAX Integer32
			MAX-ACCESS read-only
			STATUS current
			DESCRIPTION
				"Description."
			::= { hwWidsDetNonWifiDevHistEntry 12 }

		-- 1.3.6.1.4.1.2011.6.139.8.13.1.1.13
		hwWidsDetNonWifiHistCenterFrequency OBJECT-TYPE
			SYNTAX Integer32
			MAX-ACCESS read-only
			STATUS current
			DESCRIPTION
				"Description."
			::= { hwWidsDetNonWifiDevHistEntry 13 }

		-- 1.3.6.1.4.1.2011.6.139.8.13.1.1.14
		hwWidsDetNonWifiHistBandwidth OBJECT-TYPE
			SYNTAX Integer32
			MAX-ACCESS read-only
			STATUS current
			DESCRIPTION
				"Description."
			::= { hwWidsDetNonWifiDevHistEntry 14 }

		-- 1.3.6.1.4.1.2011.6.139.8.13.1.1.15
		hwWidsDetNonWifiHistDutycycle OBJECT-TYPE
			SYNTAX Integer32
			MAX-ACCESS read-only
			STATUS current
			DESCRIPTION
				"Description."
			::= { hwWidsDetNonWifiDevHistEntry 15 }

		-- 1.3.6.1.4.1.2011.6.139.8.13.1.1.16
		hwWidsDetNonWifiHistInterferenceLevel OBJECT-TYPE
			SYNTAX Integer32
			MAX-ACCESS read-only
			STATUS current
			DESCRIPTION
				"Description."
			::= { hwWidsDetNonWifiDevHistEntry 16 }

		-- 1.3.6.1.4.1.2011.6.139.8.13.1.1.17
		hwWidsDetNonWifiHistDevFirstTime OBJECT-TYPE
			SYNTAX Integer32
			MAX-ACCESS read-only
			STATUS current
			DESCRIPTION
				"Description."
			::= { hwWidsDetNonWifiDevHistEntry 17 }


		-- 1.3.6.1.4.1.2011.6.139.8.13.2
		hwWidsAttDevTable OBJECT-TYPE
			SYNTAX SEQUENCE OF HwWidsAttDevEntry
			MAX-ACCESS not-accessible
			STATUS current
			DESCRIPTION
				"Description."
			::= { hwWlanWidsObjects 2 }

		
		-- 1.3.6.1.4.1.2011.6.139.8.13.2.1
		hwWidsAttDevEntry OBJECT-TYPE
			SYNTAX HwWidsAttDevEntry
			MAX-ACCESS not-accessible
			STATUS current
			DESCRIPTION
				"Description."
			INDEX { hwWidsAttackDevMac }
			::= { hwWidsAttDevTable 1 }

		
		HwWidsAttDevEntry ::=
			SEQUENCE { 
				hwWidsAttackDevMac
					MacAddress,
				hwWidsAttackDevChannel
					Integer32,
				hwWidsAttackDevRssi
					Integer32,
				hwWidsAttackDevLastAttType
					Unsigned32,
				hwWidsAttackDevLastPacketBmp
					Unsigned32,
				hwWidsAttackDevLastDetTime
					Unsigned32
			 }

		-- 1.3.6.1.4.1.2011.6.139.8.13.2.1.1
		hwWidsAttackDevMac OBJECT-TYPE
			SYNTAX MacAddress
			MAX-ACCESS not-accessible
			STATUS current
			DESCRIPTION
				"Description."
			::= { hwWidsAttDevEntry 1 }

		
		-- 1.3.6.1.4.1.2011.6.139.8.13.2.1.2
		hwWidsAttackDevChannel OBJECT-TYPE
			SYNTAX Integer32
			MAX-ACCESS read-only
			STATUS current
			DESCRIPTION
				"Description."
			::= { hwWidsAttDevEntry 2 }

		
		-- 1.3.6.1.4.1.2011.6.139.8.13.2.1.3
		hwWidsAttackDevRssi OBJECT-TYPE
			SYNTAX Integer32
			MAX-ACCESS read-only
			STATUS current
			DESCRIPTION
				"Description."
			::= { hwWidsAttDevEntry 3 }

		
		-- 1.3.6.1.4.1.2011.6.139.8.13.2.1.4
		hwWidsAttackDevLastAttType OBJECT-TYPE
			SYNTAX Unsigned32
			MAX-ACCESS read-only
			STATUS current
			DESCRIPTION
				"Description."
			::= { hwWidsAttDevEntry 4 }

		
		-- 1.3.6.1.4.1.2011.6.139.8.13.2.1.5
		hwWidsAttackDevLastPacketBmp OBJECT-TYPE
			SYNTAX Unsigned32
			MAX-ACCESS read-only
			STATUS current
			DESCRIPTION
				"Description."
			::= { hwWidsAttDevEntry 5 }

		
		-- 1.3.6.1.4.1.2011.6.139.8.13.2.1.6
		hwWidsAttackDevLastDetTime OBJECT-TYPE
			SYNTAX Unsigned32
			MAX-ACCESS read-only
			STATUS current
			DESCRIPTION
				"Description."
			::= { hwWidsAttDevEntry 6 }

		
		-- 1.3.6.1.4.1.2011.6.139.8.13.3
		hwWidsAttackDetorTable OBJECT-TYPE
			SYNTAX SEQUENCE OF HwWidsAttackDetorEntry
			MAX-ACCESS not-accessible
			STATUS current
			DESCRIPTION
				"Description."
			::= { hwWlanWidsObjects 3 }

		
		-- 1.3.6.1.4.1.2011.6.139.8.13.3.1
		hwWidsAttackDetorEntry OBJECT-TYPE
			SYNTAX HwWidsAttackDetorEntry
			MAX-ACCESS not-accessible
			STATUS current
			DESCRIPTION
				"Description."
			INDEX { hwWidsAttackDevMac, hwWidsAttackDetorApID }
			::= { hwWidsAttackDetorTable 1 }

		
		HwWidsAttackDetorEntry ::=
			SEQUENCE { 
				hwWidsAttackDetorApID
					Unsigned32,
				hwWidsAttackDetorAttTypeBmp
					Unsigned32,
				hwWidsAttackDetorPacketBmpFlood
					Unsigned32,
				hwWidsAttackDetorPacketBmpSpoof
					Unsigned32,
				hwWidsAttackDetorFirstDetTimeFlood
					Unsigned32,
				hwWidsAttackDetorFirstDetTimeSpoof
					Unsigned32,
				hwWidsAttackDetorFirstDetTimeWeakIv
					Unsigned32,
				hwWidsAttackDetorFirstDetTimeWep
					Unsigned32,
				hwWidsAttackDetorFirstDetTimeWpa
					Unsigned32,
				hwWidsAttackDetorFirstDetTimeWpa2
					Unsigned32,
				hwWidsAttackDetorFirstDetTimeWapi
					Unsigned32
			 }

		-- 1.3.6.1.4.1.2011.6.139.8.13.3.1.1
		hwWidsAttackDetorApID OBJECT-TYPE
			SYNTAX Unsigned32
			MAX-ACCESS not-accessible
			STATUS current
			DESCRIPTION
				"Description."
			::= { hwWidsAttackDetorEntry 1 }

		
		-- 1.3.6.1.4.1.2011.6.139.8.13.3.1.2
		hwWidsAttackDetorAttTypeBmp OBJECT-TYPE
			SYNTAX Unsigned32
			MAX-ACCESS read-only
			STATUS current
			DESCRIPTION
				"Description."
			::= { hwWidsAttackDetorEntry 2 }

		
		-- 1.3.6.1.4.1.2011.6.139.8.13.3.1.3
		hwWidsAttackDetorPacketBmpFlood OBJECT-TYPE
			SYNTAX Unsigned32
			MAX-ACCESS read-only
			STATUS current
			DESCRIPTION
				"Description."
			::= { hwWidsAttackDetorEntry 3 }

		
		-- 1.3.6.1.4.1.2011.6.139.8.13.3.1.4
		hwWidsAttackDetorPacketBmpSpoof OBJECT-TYPE
			SYNTAX Unsigned32
			MAX-ACCESS read-only
			STATUS current
			DESCRIPTION
				"Description."
			::= { hwWidsAttackDetorEntry 4 }

		
		-- 1.3.6.1.4.1.2011.6.139.8.13.3.1.5
		hwWidsAttackDetorFirstDetTimeFlood OBJECT-TYPE
			SYNTAX Unsigned32
			MAX-ACCESS read-only
			STATUS current
			DESCRIPTION
				"Description."
			::= { hwWidsAttackDetorEntry 5 }

		
		-- 1.3.6.1.4.1.2011.6.139.8.13.3.1.6
		hwWidsAttackDetorFirstDetTimeSpoof OBJECT-TYPE
			SYNTAX Unsigned32
			MAX-ACCESS read-only
			STATUS current
			DESCRIPTION
				"Description."
			::= { hwWidsAttackDetorEntry 6 }

		
		-- 1.3.6.1.4.1.2011.6.139.8.13.3.1.7
		hwWidsAttackDetorFirstDetTimeWeakIv OBJECT-TYPE
			SYNTAX Unsigned32
			MAX-ACCESS read-only
			STATUS current
			DESCRIPTION
				"Description."
			::= { hwWidsAttackDetorEntry 7 }

		
		-- 1.3.6.1.4.1.2011.6.139.8.13.3.1.8
		hwWidsAttackDetorFirstDetTimeWep OBJECT-TYPE
			SYNTAX Unsigned32
			MAX-ACCESS read-only
			STATUS current
			DESCRIPTION
				"Description."
			::= { hwWidsAttackDetorEntry 8 }

		
		-- 1.3.6.1.4.1.2011.6.139.8.13.3.1.9
		hwWidsAttackDetorFirstDetTimeWpa OBJECT-TYPE
			SYNTAX Unsigned32
			MAX-ACCESS read-only
			STATUS current
			DESCRIPTION
				"Description."
			::= { hwWidsAttackDetorEntry 9 }

		
		-- 1.3.6.1.4.1.2011.6.139.8.13.3.1.10
		hwWidsAttackDetorFirstDetTimeWpa2 OBJECT-TYPE
			SYNTAX Unsigned32
			MAX-ACCESS read-only
			STATUS current
			DESCRIPTION
				"Description."
			::= { hwWidsAttackDetorEntry 10 }

		
		-- 1.3.6.1.4.1.2011.6.139.8.13.3.1.11
		hwWidsAttackDetorFirstDetTimeWapi OBJECT-TYPE
			SYNTAX Unsigned32
			MAX-ACCESS read-only
			STATUS current
			DESCRIPTION
				"Description."
			::= { hwWidsAttackDetorEntry 11 }
		-- 1.3.6.1.4.1.2011.6.139.8.13.4
		hwOuiWhitelistTable OBJECT-TYPE
			SYNTAX SEQUENCE OF HwOuiWhitelistEntry
			MAX-ACCESS not-accessible
			STATUS current
			DESCRIPTION
				"Description."
			::= { hwWlanWidsObjects 4 }
		
		-- 1.3.6.1.4.1.2011.6.139.8.13.4.1
		hwOuiWhitelistEntry OBJECT-TYPE
			SYNTAX HwOuiWhitelistEntry
			MAX-ACCESS not-accessible
			STATUS current
			DESCRIPTION
				"Description."
			INDEX { hwOuiWhitelistOui }
			::= { hwOuiWhitelistTable 1 }
		
		HwOuiWhitelistEntry ::=
			SEQUENCE { 
				hwOuiWhitelistOui
					OCTET STRING,
				hwOuiWhitelistRowStatus
					RowStatus
			 }

		-- 1.3.6.1.4.1.2011.6.139.8.13.4.1.1
		hwOuiWhitelistOui OBJECT-TYPE
			SYNTAX OCTET STRING
			MAX-ACCESS not-accessible
			STATUS current
			DESCRIPTION
				"Description."
			::= { hwOuiWhitelistEntry 1 }
		
		-- 1.3.6.1.4.1.2011.6.139.8.13.4.1.2
		hwOuiWhitelistRowStatus OBJECT-TYPE
			SYNTAX RowStatus
			MAX-ACCESS read-create
			STATUS current
			DESCRIPTION
				"Description."
			::= { hwOuiWhitelistEntry 2 }
		
		-- 1.3.6.1.4.1.2011.6.139.8.13.5
		hwMacAddressWhitelistTable OBJECT-TYPE
			SYNTAX SEQUENCE OF HwMacAddressWhitelistEntry
			MAX-ACCESS not-accessible
			STATUS current
			DESCRIPTION
				"Description."
			::= { hwWlanWidsObjects 5 }
		
		-- 1.3.6.1.4.1.2011.6.139.8.13.5.1
		hwMacAddressWhitelistEntry OBJECT-TYPE
			SYNTAX HwMacAddressWhitelistEntry
			MAX-ACCESS not-accessible
			STATUS current
			DESCRIPTION
				"Description."
			INDEX { hwMacAddressWhitelistMacAddress }
			::= { hwMacAddressWhitelistTable 1 }
		
		HwMacAddressWhitelistEntry ::=
			SEQUENCE { 
				hwMacAddressWhitelistMacAddress
					MacAddress,
				hwMacAddressWhitelistRowStatus
					RowStatus
			 }

		-- 1.3.6.1.4.1.2011.6.139.8.13.5.1.1
		hwMacAddressWhitelistMacAddress OBJECT-TYPE
			SYNTAX MacAddress
			MAX-ACCESS not-accessible
			STATUS current
			DESCRIPTION
				"Description."
			::= { hwMacAddressWhitelistEntry 1 }
		
		-- 1.3.6.1.4.1.2011.6.139.8.13.5.1.2
		hwMacAddressWhitelistRowStatus OBJECT-TYPE
			SYNTAX RowStatus
			MAX-ACCESS read-create
			STATUS current
			DESCRIPTION
				"Description."
			::= { hwMacAddressWhitelistEntry 2 }
		-- 1.3.6.1.4.1.2011.6.139.8.13.6
		hwWidsSpoofSsidRuleListTable OBJECT-TYPE
			SYNTAX SEQUENCE OF HwWidsSpoofSsidRuleListEntry
			MAX-ACCESS not-accessible
			STATUS current
			DESCRIPTION
				"Description."
			::= { hwWlanWidsObjects 6 }

		
		-- 1.3.6.1.4.1.2011.6.139.8.13.6.1
		hwWidsSpoofSsidRuleListEntry OBJECT-TYPE
			SYNTAX HwWidsSpoofSsidRuleListEntry
			MAX-ACCESS not-accessible
			STATUS current
			DESCRIPTION
				"Description."
			INDEX { hwWidsSpoofSsidRule }
			::= { hwWidsSpoofSsidRuleListTable 1 }

		
		HwWidsSpoofSsidRuleListEntry ::=
			SEQUENCE { 
				hwWidsSpoofSsidRule
					OCTET STRING,
				hwWidsSpoofSsidRuleListRowStatus
					RowStatus
			 }
		-- 1.3.6.1.4.1.2011.6.139.8.13.6.1.1
		hwWidsSpoofSsidRule OBJECT-TYPE
			SYNTAX OCTET STRING
			MAX-ACCESS not-accessible
			STATUS current
			DESCRIPTION
				"Description."
			::= { hwWidsSpoofSsidRuleListEntry 1 }

		
		-- 1.3.6.1.4.1.2011.6.139.8.13.6.1.2
		hwWidsSpoofSsidRuleListRowStatus OBJECT-TYPE
			SYNTAX RowStatus
			MAX-ACCESS read-create
			STATUS current
			DESCRIPTION
				"Description."
			::= { hwWidsSpoofSsidRuleListEntry 2 }
		-- END:   added by lishijun 00209691, 2013/04/20
				
		-- 1.3.6.1.4.1.2011.6.139.8.14
		hwWlanWidsConformance OBJECT IDENTIFIER ::= { hwWlanWids 14 }
		-- 1.3.6.1.4.1.2011.6.139.8.14.1
		hwWlanWidsCompliances OBJECT IDENTIFIER ::= { hwWlanWidsConformance 1 }
		-- 1.3.6.1.4.1.2011.6.139.8.14.1.1
		hwWlanWidsCompliance MODULE-COMPLIANCE
			STATUS current
			DESCRIPTION 
				"Description."
			MODULE -- this module
				MANDATORY-GROUPS { hwWlanWidsMIBNotifyObjectGroup, hwWlanWidsMIBNotifyGroup, hwWlanWidsGlobalOptGroup, hwWidsDetDevGroup, hwWidsDetDevMonitorGroup, 
					hwWidsRogueHistoryGroup, hwSsidWhitelistGroup, hwWidsDetNonWifiDevGroup, hwWidsAttackHistoryGroup, hwWidsEnableAPGroup, 
					hwWidsAttackStatGroup, hwWidsDynamicBlacklistGroup, hwWidsDynamicBlacklistAPGroup, hwWidsDetNonWifiDevHistGroup, hwWidsAttackDevGroup, 
					hwWidsAttackDetorGroup }
			::= { hwWlanWidsCompliances 1 }
		-- 1.3.6.1.4.1.2011.6.139.8.14.2
		hwWlanWidsObjectGroups OBJECT IDENTIFIER ::= { hwWlanWidsConformance 2 }

		-- 1.3.6.1.4.1.2011.6.139.8.14.2.1
		hwWlanWidsMIBNotifyObjectGroup OBJECT-GROUP
			OBJECTS { hwWlanObjWidsRogueDevMAC, hwWlanObjWidsRogueDevType, hwWlanObjWidsRogueDevChannel, hwWlanObjWidsRogueDevRSSI, hwWlanObjWidsRogueDevSSID, 
				hwWlanObjWidsDetAPID, hwWlanObjWidsDetRadioId, hwWlanObjWidsDetAPChannel, hwWlanObjWidsDetAPMAC, hwWlanObjWidsDetAPIP, 
				hwWlanObjWidsNonWifiDeviceType, hwWlanObjWidsNonWifiInterChannel, hwWlanObjWidsNonWifiRssi, hwWlanObjWidsDetAPName, hwWlanObjWidsDetRadioType, 
				hwWlanObjWidsAttackDevMAC, hwWlanObjWidsAttackType, hwWlanObjWidsAttackTypeStr }
			STATUS current
			DESCRIPTION 
				"Description."
			::= { hwWlanWidsObjectGroups 1 }
		-- 1.3.6.1.4.1.2011.6.139.8.14.2.2
		hwWlanWidsMIBNotifyGroup NOTIFICATION-GROUP
			NOTIFICATIONS { hwWlanWidsRougeDevDetectedNotify, hwWlanWidsRougeDevClearNotify, hwWlanWidsNonWifiDetNotify, hwWlanWidsNonWifiClearNotify, 
			    hwWlanWidsFloodAttackDetectedNotify, hwWlanWidsFloodAttackClearNotify, hwWlanWidsSpoofAttackDetectedNotify, hwWlanWidsSpoofAttackClearNotify, 
				hwWlanWidsWeakIvAttackDetectedNotify, hwWlanWidsWeakIvAttackClearNotify, hwWlanWidsPSKAttackDetectedNotify, hwWlanWidsPSKAttackClearNotify }
			STATUS current
			DESCRIPTION 
				"Description."
			::= { hwWlanWidsObjectGroups 2 }

		-- 1.3.6.1.4.1.2011.6.139.8.14.2.3
		hwWlanWidsGlobalOptGroup OBJECT-GROUP
			OBJECTS { hwWidsResetDetDevTableAll, hwWidsResetDetDevTableByType, hwWidsResetRogueHistoryAll, hwWidsResetRogueHistoryByDevType, hwWidsResetAttackDev, 
				hwWidsResetAttackStat, hwWidsResetDynamicBlacklist, hwWidsResetDynamicBlacklistMac, hwWidsResetAttackHistory }
			STATUS current
			DESCRIPTION 
				"Description."
			::= { hwWlanWidsObjectGroups 3 }
		-- 1.3.6.1.4.1.2011.6.139.8.14.2.4
		hwWidsDetDevGroup OBJECT-GROUP
			OBJECTS { hwWidsDetDevType, hwWidsDetDevRssi, hwWidsDetDevChannel, hwWidsDetDevSSID, hwWidsDetDevRogue, 
				hwWidsDetDevLastTime, hwWidsDetDevIsCountermeasuresed, hwWidsDetDevInterference, hwWidsDetDevBSSID, hwWidsDetDevFirstDetTime
				 }
			STATUS current
			DESCRIPTION 
				"Description."
			::= { hwWlanWidsObjectGroups 4 }
		-- 1.3.6.1.4.1.2011.6.139.8.14.2.5
		hwWidsDetDevMonitorGroup OBJECT-GROUP
			OBJECTS { hwWidsDetDevMonitorApMAC, hwWidsDetDevMonitorApIP, hwWidsDetDevMonitorApChannel, hwWidsDetDevMonitorApRssi, hwWidsDetDevMonitorApLastDetTime, 
				hwWidsDetDevMonitorApCountermeasuresDev, hwWidsDetDevMonitorDetAtt }
			STATUS current
			DESCRIPTION 
				"Description."
			::= { hwWlanWidsObjectGroups 5 }
		-- 1.3.6.1.4.1.2011.6.139.8.14.2.6
		hwWidsRogueHistoryGroup OBJECT-GROUP
			OBJECTS { hwWidsRogueDevType, hwWidsRogueDevRssi, hwWidsRogueDevChannel, hwWidsRogueDevSSID, hwWidsRogueDevLastTime
				 }
			STATUS current
			DESCRIPTION 
				"Description."
			::= { hwWlanWidsObjectGroups 6 }
		-- 1.3.6.1.4.1.2011.6.139.8.14.2.7
		hwSsidWhitelistGroup OBJECT-GROUP
			OBJECTS { hwSsidWhitelisttRowStatus }
			STATUS current
			DESCRIPTION 
				"Description."
			::= { hwWlanWidsObjectGroups 7 }
		-- 1.3.6.1.4.1.2011.6.139.8.14.2.8
		hwWidsDetNonWifiDevGroup OBJECT-GROUP
			OBJECTS { hwWidsDetNonWifiRssi, hwWidsDetNonWifiFrequencyType, hwWidsDetNonWifiChannel, hwWidsDetNonWifiDevLastTime, hwWidsDetNonWifiCenterFrequency, 
				hwWidsDetNonWifiBandwidth, hwWidsDetNonWifiDutycycle, hwWidsDetNonWifiInterferenceLevel, hwWidsDetNonWifiDevMonitorAPName
				,hwWidsDetNonWifiDevMonitorAPID ,hwWidsDetNonWifiDevRadioType ,hwWidsDetNonWifiDevMonitorAPChannel, hwWidsDetNonWifiDevFirstTime}
			STATUS current
			DESCRIPTION 
				"Description."
			::= { hwWlanWidsObjectGroups 8 }
		-- 1.3.6.1.4.1.2011.6.139.8.14.2.9
		hwWidsAttackHistoryGroup OBJECT-GROUP
			OBJECTS { hwWidsAttackHistoryDevMac, hwWidsAttackHistoryDevType, hwWidsAttackHistoryRssi, hwWidsAttackHistoryChannel, hwWidsAttackHistoryAttackType, 
				hwWidsAttackHistoryPacketBmp1, hwWidsAttackHistoryPacketBmp2, hwWidsAttackHistorySSID, hwWidsAttackHistoryDetTime, hwWidsAttackHistoryDetectorApId
				 }
			STATUS current
			DESCRIPTION 
				"Description."
			::= { hwWlanWidsObjectGroups 9 }
		-- 1.3.6.1.4.1.2011.6.139.8.14.2.10
		hwWidsEnableAPGroup OBJECT-GROUP
			OBJECTS { hwWidsEnableDevDetSwitch, hwWidsEnableAttackDetSwitch, hwWidsEnableAPName }
			STATUS current
			DESCRIPTION 
				"Description."
			::= { hwWlanWidsObjectGroups 10 }
		-- 1.3.6.1.4.1.2011.6.139.8.14.2.11
		hwWidsAttackStatGroup OBJECT-GROUP
			OBJECTS { hwWidsAttackStatProbeRequestFloodAttack, hwWidsAttackStatAuthRequestFloodAttack, hwWidsAttackStatDeAuthenFloodAttack, hwWidsAttackStatAssocReqFloodAttack, hwWidsAttackStatDisassocReqFloodAttack, 
				hwWidsAttackStatReassocReqFloodAttack, hwWidsAttackStatActionFloodAttack, hwWidsAttackStatNullDataFloodAttack, hwWidsAttackStatWeakIvAttack, hwWidsAttackStatDeauthSpoofAttack, 
				hwWidsAttackStatDisassocSpoofAttack, hwWidsAttackStatWepShareKeyAttack, hwWidsAttackStatWpaAttack, hwWidsAttackStatWpa2Attack, hwWidsAttackStatWapiAttack, 
				hwWidsAttackStatStartTime, hwWidsAttackStatEAPOLStartFloodAttack, hwWidsAttackStatEAPOLLogoffFloodAttack, hwWidsAttackStatNullQosFloodAttack }
			STATUS current
			DESCRIPTION 
				"Description."
			::= { hwWlanWidsObjectGroups 11 }
		-- 1.3.6.1.4.1.2011.6.139.8.14.2.12
		hwWidsDynamicBlacklistGroup OBJECT-GROUP
			OBJECTS { hwWidsDynamicBlacklistDevType, hwWidsDynamicBlacklistDevAttackType, hwWidsDynamicBlacklistAttackPacketBmp1, hwWidsDynamicBlacklistAttackPacketBmp2, hwWidsDynamicBlacklistLastTime
				 }
			STATUS current
			DESCRIPTION 
				"Description."
			::= { hwWlanWidsObjectGroups 12 }
		-- 1.3.6.1.4.1.2011.6.139.8.14.2.13
		hwWidsDynamicBlacklistAPGroup OBJECT-GROUP
			OBJECTS { hwWidsDynamicBlacklistAPMac, hwWidsDynamicBlacklistApIP, hwWidsDynamicBlacklistAttackType, hwWidsDynamicBlacklistAPLastTime }
			STATUS current
			DESCRIPTION 
				"Description."
			::= { hwWlanWidsObjectGroups 13 }

		-- 1.3.6.1.4.1.2011.6.139.8.14.2.14
		hwWidsDetNonWifiDevHistGroup OBJECT-GROUP
			OBJECTS { 
				hwWidsDetNonWifiHistMonitorApMac,
				hwWidsDetNonWifiHistMonitorAPName,
				hwWidsDetNonWifiHistMonitorAPID,
				hwWidsDetNonWifiHistMonitorRadioId,
				hwWidsDetNonWifiHistMonitorRadioType,
				hwWidsDetNonWifiHistMonitorAPChannel,
				hwWidsDetNonWifiHistDevType,
				hwWidsDetNonWifiHistRssi,
				hwWidsDetNonWifiHistFrequencyType,
				hwWidsDetNonWifiHistChannel,
				hwWidsDetNonWifiHistDevLastTime,
				hwWidsDetNonWifiHistCenterFrequency,
				hwWidsDetNonWifiHistBandwidth,
				hwWidsDetNonWifiHistDutycycle,
				hwWidsDetNonWifiHistInterferenceLevel,
				hwWidsDetNonWifiHistDevFirstTime
			}
			STATUS current
			DESCRIPTION 
				"Description."
			::= { hwWlanWidsObjectGroups 14 }

		-- 1.3.6.1.4.1.2011.6.139.8.14.2.15
		hwWidsAttackDevGroup OBJECT-GROUP
			OBJECTS { hwWidsAttackDevChannel, hwWidsAttackDevRssi, hwWidsAttackDevLastAttType, hwWidsAttackDevLastPacketBmp, hwWidsAttackDevLastDetTime
				 }
			STATUS current
			DESCRIPTION 
				"Description."
			::= { hwWlanWidsObjectGroups 15 }

		
		-- 1.3.6.1.4.1.2011.6.139.8.14.2.16
		hwWidsAttackDetorGroup OBJECT-GROUP
			OBJECTS { hwWidsAttackDetorPacketBmpFlood, hwWidsAttackDetorPacketBmpSpoof, hwWidsAttackDetorFirstDetTimeFlood, hwWidsAttackDetorFirstDetTimeSpoof, hwWidsAttackDetorFirstDetTimeWeakIv, 
				hwWidsAttackDetorFirstDetTimeWep, hwWidsAttackDetorFirstDetTimeWpa, hwWidsAttackDetorFirstDetTimeWpa2, hwWidsAttackDetorFirstDetTimeWapi, hwWidsAttackDetorAttTypeBmp
				 }
			STATUS current
			DESCRIPTION 
				"Description."
			::= { hwWlanWidsObjectGroups 16 }
		-- 1.3.6.1.4.1.2011.6.139.8.14.2.17
		hwWidsOuiWhitelistGroup OBJECT-GROUP
			OBJECTS { hwOuiWhitelistRowStatus }
			STATUS current
			DESCRIPTION 
				"Description."
			::= { hwWlanWidsObjectGroups 17 }
		
		-- 1.3.6.1.4.1.2011.6.139.8.14.2.18
		hwWidsMacAddressWhitelistGroup OBJECT-GROUP
			OBJECTS { hwMacAddressWhitelistRowStatus }
			STATUS current
			DESCRIPTION 
				"Description."
			::= { hwWlanWidsObjectGroups 18 }

		
		-- 1.3.6.1.4.1.2011.6.139.8.14.2.19
		hwWidsSpoofSsidRuleGroup OBJECT-GROUP
			OBJECTS { hwWidsSpoofSsidRuleListRowStatus }
			STATUS current
			DESCRIPTION 
				"Description."
			::= { hwWlanWidsObjectGroups 19 }

		
	
	END

--
-- HUAWEI-WLAN-WIDS-MIB.mib
--
