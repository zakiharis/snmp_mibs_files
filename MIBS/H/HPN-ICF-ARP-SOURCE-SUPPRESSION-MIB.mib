-- ============================================================================
-- Copyright (c) 2010-2014 Hewlett-Packard Development Company, L.P.
--
-- Description: Arp source suppression MIB.
-- Reference:
-- Version: V1.0
-- History:
-- V1.0 2013-10-14
--   Initial version, created by yanjun
-- ============================================================================
HPN-ICF-ARP-SOURCE-SUPPRESSION-MIB DEFINITIONS ::= BEGIN

IMPORTS
        hpnicfCommon
    FROM HPN-ICF-OID-MIB
        Unsigned32, OBJECT-TYPE, MODULE-IDENTITY
    FROM SNMPv2-SMI
        TruthValue
    FROM SNMPv2-TC;

-- Node definitions
hpnicfARPSourceSuppression MODULE-IDENTITY
    LAST-UPDATED "201310141800Z"        -- OCT 14, 2013 at 18:00 GMT
    ORGANIZATION
        ""
    CONTACT-INFO
        ""
    DESCRIPTION
        "This MIB file is to provide the definition of the ARP source
        suppression. "
    REVISION "201310141800Z"
    DESCRIPTION
        "The initial version of this MIB file."
    ::= { hpnicfCommon 146 }

hpnicfARPSourceSuppressionObjects OBJECT IDENTIFIER ::= { hpnicfARPSourceSuppression 1 }

hpnicfARPSourceSuppressionGlobal OBJECT IDENTIFIER  ::= { hpnicfARPSourceSuppressionObjects 1 }

hpnicfARPSourceSuppressionEnable OBJECT-TYPE
    SYNTAX      TruthValue
    MAX-ACCESS  read-write
    STATUS      current
    DESCRIPTION
        "Enable or disable ARP source suppression function."
    ::= { hpnicfARPSourceSuppressionGlobal 1 }

hpnicfARPSourceSuppressionLimit OBJECT-TYPE
    SYNTAX      Unsigned32(2..1024)
    MAX-ACCESS  read-write
    STATUS      current
    DESCRIPTION
        "Set the maximum number of unresolvable packets that the device
         can receive from a device in five seconds."
    DEFVAL { 10 }
    ::= { hpnicfARPSourceSuppressionGlobal 2 }
END
