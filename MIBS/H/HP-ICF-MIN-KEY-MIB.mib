HP-ICF-MIN-KEY-MIB DEFINITIONS ::= BEGIN

    IMPORTS
        hpSwitch
            FROM HP-ICF-OID
        OBJECT-GROUP, MODULE-COMPLIANCE
            FROM SNMPv2-CONF 
        OBJECT-TYPE, MODULE-IDENTITY
            FROM SNMPv2-SMI
         RowStatus
            FROM SNMPv2-TC;
 
    hpicfMinKeyMIB MODULE-IDENTITY
 
        LAST-UPDATED "201606220900Z"     --June 22, 2016
        ORGANIZATION "HP Networking"
        CONTACT-INFO "Hewlett-Packard Enterprise Company
                      8000 Foothills Blvd.
                      Roseville, CA 95747"
	DESCRIPTION
	   "This MIB module describes objects for enforcing minimum secure key
           size in the HPE Integrated Communication 
           Facility product line."

	REVISION     "201606220900Z"     -- June 22, 2016 
        DESCRIPTION
           "Initial version of minimum key MIB module."

        ::= { hpSwitch 132 }

 
    ---
    --- Node definitions
    ---

    hpicfMinKeyObjects       OBJECT IDENTIFIER ::= { hpicfMinKeyMIB 0 }
    hpicfMinKeyConformance   OBJECT IDENTIFIER ::= { hpicfMinKeyMIB 1 }
    -- hpicfMinKeyNotifications OBJECT IDENTIFIER ::= { hpicfMinKeyMIB 2 }
   

    hpicfMinKeyConfigObjects OBJECT IDENTIFIER ::= { hpicfMinKeyObjects 1 }
    -- hpicfMinKeyStatsObjects  OBJECT IDENTIFIER ::= { hpicfMinKeyObjects 2 }


    ---
    --- Scalar configuration objects
    ---

    -- hpicfMinKeyScalarConfig OBJECT IDENTIFIER ::= { hpicfMinKeyConfigObjects 0 }

    ---
    --- minimum key table
    ---
    hpicfMinKeyTable OBJECT-TYPE
        SYNTAX          SEQUENCE OF HpicfMinKeyEntry
        MAX-ACCESS      not-accessible
        STATUS          current
        DESCRIPTION 
	    "A table of minimum secure key size objects"
        ::= { hpicfMinKeyConfigObjects 1 }

    hpicfMinKeyEntry OBJECT-TYPE
        SYNTAX          HpicfMinKeyEntry
        MAX-ACCESS      not-accessible
        STATUS          current
        DESCRIPTION 
	    "An entry in the hpicfMinKeyTable."
        INDEX           { hpicfMinKeyType}
        ::= { hpicfMinKeyTable 1 }

    HpicfMinKeyEntry ::= SEQUENCE {
        hpicfMinKeyType          INTEGER,
        hpicfMinKeySize          INTEGER,
        hpicfMinKeyRowStatus     RowStatus
    }

    hpicfMinKeyType OBJECT-TYPE
        SYNTAX          INTEGER {
                            rsa(1)
                        }
        MAX-ACCESS      not-accessible
        STATUS          current
        DESCRIPTION 
            "This object specifies the key type for which the minimum 
             secure key size enforced."
        ::= { hpicfMinKeyEntry 1 }

    hpicfMinKeySize OBJECT-TYPE
        SYNTAX          INTEGER {
                            minBit1024(1),
                            minBit2048(2)
                        }
        MAX-ACCESS      read-create
        STATUS          current
        DESCRIPTION 
            "This object specifies the minimum secure key size enforced. The 
             default value for this attribute will be 1024"
        ::= { hpicfMinKeyEntry 2 }


    hpicfMinKeyRowStatus OBJECT-TYPE
        SYNTAX          RowStatus
        MAX-ACCESS      read-create
        STATUS          current
        DESCRIPTION 
        "Status of this row, by which new entries may be created
         or existing entries deleted from this table."

        ::= { hpicfMinKeyEntry 3 } 


    --- ------------------------------------------------------------
    --- Conformance
    --- ------------------------------------------------------------

    hpicfMinKeyCompliances OBJECT IDENTIFIER ::= { hpicfMinKeyConformance 1 }
    hpicfMinKeyGroups OBJECT IDENTIFIER ::= { hpicfMinKeyConformance 2 }

    hpicfMinKeyCompliance1 MODULE-COMPLIANCE
    STATUS          current
    DESCRIPTION     "The compliance statement"
        MODULE          -- this module
        MANDATORY-GROUPS {
            hpicfMinKeyConfigGroup
        }
        ::= { hpicfMinKeyCompliances 1 }

    --- units of conformance

    hpicfMinKeyConfigGroup OBJECT-GROUP
        OBJECTS    {
            hpicfMinKeySize,
            hpicfMinKeyRowStatus
        }
        STATUS current
        DESCRIPTION
            "A collection of objects providing configuration for
             minimum secure key size."            
        ::= { hpicfMinKeyGroups 1 }

END
