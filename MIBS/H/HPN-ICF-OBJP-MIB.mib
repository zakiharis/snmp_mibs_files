-- ============================================================================
-- Copyright (c) 2010-2014 Hewlett-Packard Development Company, L.P.
--
-- Description: This MIB is used for configuration of OBJP(object policy).
-- Reference:
-- Version: V1.0
-- History:
-- V1.0 created by gaoyu.
-- ============================================================================
HPN-ICF-OBJP-MIB DEFINITIONS ::= BEGIN

IMPORTS
    hpnicfCommon
        FROM  HPN-ICF-OID-MIB
    OBJECT-TYPE, MODULE-IDENTITY,
    Unsigned32, Counter64
        FROM SNMPv2-SMI;

--
-- Node definitions
--

hpnicfObjp MODULE-IDENTITY
    LAST-UPDATED "201403101536Z"        -- Mar 10, 2014 at 15:36 GMT
    ORGANIZATION
        ""
    CONTACT-INFO
        ""
    DESCRIPTION
        "Object-policy management information base for managing devices
        that support object policy.
        "
    REVISION "201403101536Z"            -- Mar 10, 2014 at 15:36 GMT
    DESCRIPTION
        "The initial revision of this MIB module."
    ::= { hpnicfCommon 155 }

--
-- Nodes of hpnicfObjpZonePairObjects
--
hpnicfObjpZonePairObjects OBJECT IDENTIFIER ::= { hpnicfObjp 1 }

--
-- Nodes of hpnicfObjpZonePairRunningInfoTable
--
hpnicfObjpZonePairRunningInfoTable OBJECT-TYPE
    SYNTAX SEQUENCE OF HpnicfObjpZonePairRunningInfoEntry
    MAX-ACCESS not-accessible
    STATUS current
    DESCRIPTION
        "Object policy of zone pair running information base."
    ::= { hpnicfObjpZonePairObjects 1 }

hpnicfObjpZonePairRunningInfoEntry OBJECT-TYPE
    SYNTAX HpnicfObjpZonePairRunningInfoEntry
    MAX-ACCESS not-accessible
    STATUS current
    DESCRIPTION
        "Object policy of zone pair running information entry."
    INDEX
    {
        hpnicfObjpZonePairSrcZone,
        hpnicfObjpZonePairDstZone,
        hpnicfObjpZonePairIPVersion,
        hpnicfObjpZonePairRuleID
    }
    ::= { hpnicfObjpZonePairRunningInfoTable 1 }

HpnicfObjpZonePairRunningInfoEntry ::=
    SEQUENCE
    {
        hpnicfObjpZonePairSrcZone
            OCTET STRING,
        hpnicfObjpZonePairDstZone
            OCTET STRING,
        hpnicfObjpZonePairIPVersion
            INTEGER,
        hpnicfObjpZonePairRuleID
            Unsigned32,
        hpnicfObjpZonePairMatchPacketCount
            Counter64,
        hpnicfObjpZonePairLastMatchTime
            Unsigned32
    }

hpnicfObjpZonePairSrcZone OBJECT-TYPE
    SYNTAX OCTET STRING (SIZE(1..31))
    MAX-ACCESS not-accessible
    STATUS current
    DESCRIPTION
        "Name of the source security zone."
    ::= { hpnicfObjpZonePairRunningInfoEntry 1 }

hpnicfObjpZonePairDstZone OBJECT-TYPE
    SYNTAX OCTET STRING (SIZE(1..31))
    MAX-ACCESS not-accessible
    STATUS current
    DESCRIPTION
        "Name of the destination security zone."
    ::= { hpnicfObjpZonePairRunningInfoEntry 2 }

hpnicfObjpZonePairIPVersion OBJECT-TYPE
    SYNTAX INTEGER
    {
        ipv4(1),
        ipv6(2)
    }
    MAX-ACCESS not-accessible
    STATUS current
    DESCRIPTION
        "IP protocol version."
    ::= { hpnicfObjpZonePairRunningInfoEntry 3 }

hpnicfObjpZonePairRuleID OBJECT-TYPE
    SYNTAX Unsigned32 (0..65534)
    MAX-ACCESS not-accessible
    STATUS current
    DESCRIPTION
        "Rule ID of object policy."
    ::= { hpnicfObjpZonePairRunningInfoEntry 4 }

hpnicfObjpZonePairMatchPacketCount OBJECT-TYPE
    SYNTAX Counter64
    MAX-ACCESS read-only
    STATUS current
    DESCRIPTION
        "Number of packets matching the rule."
    ::= { hpnicfObjpZonePairRunningInfoEntry 5 }

hpnicfObjpZonePairLastMatchTime OBJECT-TYPE
    SYNTAX Unsigned32
    MAX-ACCESS read-only
    STATUS current
    DESCRIPTION
        "Interval in seconds between the last match and 1970/1/1 00:00:00."
    ::= { hpnicfObjpZonePairRunningInfoEntry 6 }

END
