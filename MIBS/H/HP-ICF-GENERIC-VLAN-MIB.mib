HP-ICF-GENERIC-VLAN-MIB DEFINITIONS ::= BEGIN

   IMPORTS
      OBJECT-TYPE, MODULE-IDENTITY
            FROM SNMPv2-SMI
      OBJECT-GROUP, MODULE-COMPLIANCE
            FROM SNMPv2-CONF
      dot1qTpFdbEntry, VlanId
            FROM Q-BRIDGE-MIB
      hpSwitch
            FROM HP-ICF-OID;
   
   hpicfGenericVlanMIB MODULE-IDENTITY
      LAST-UPDATED  "201002080000Z"  -- February 08, 2010
      ORGANIZATION  "HP Networking"
      CONTACT-INFO  "Hewlett Packard Company
                     8000 Foothills Blvd.
                     Roseville, CA 95747"
    
      DESCRIPTION   "The MIB module for generic VLAN features"
            
      REVISION      "201002080000Z"  -- February 08, 2010
      DESCRIPTION   "The initial revision."
    ::= {hpSwitch 67 }           

   hpicfGenericVlanFeaturesObjects       OBJECT IDENTIFIER
           ::= { hpicfGenericVlanMIB 1 }

   hpicfGenericVlanFeaturesConformance   OBJECT IDENTIFIER 
           ::= { hpicfGenericVlanMIB 2 }


   hpicfGenericVlanFeaturesTable OBJECT-TYPE
      SYNTAX      SEQUENCE OF HpicfGenericVlanFeaturesEntry
      MAX-ACCESS  not-accessible
      STATUS      current
      DESCRIPTION "This table contains objects that are generic to
                   multiple VLAN features, using the same indices as
                   dot1qTpFdbEntry"
      ::= { hpicfGenericVlanFeaturesObjects 1 } 

   hpicfGenericVlanFeaturesEntry  OBJECT-TYPE
      SYNTAX      HpicfGenericVlanFeaturesEntry
      MAX-ACCESS  not-accessible
      STATUS      current
      DESCRIPTION "A row in a table, containing the VLAN ID."
      AUGMENTS { dot1qTpFdbEntry }
      ::= { hpicfGenericVlanFeaturesTable 1 }

   HpicfGenericVlanFeaturesEntry ::=
      SEQUENCE
      {
            hpicfMacNotifyClearVlanControl    INTEGER,
            hpicfDot1qTpFdbVlanId             VlanId   
      } 
    
   hpicfMacNotifyClearVlanControl OBJECT-TYPE
      SYNTAX      INTEGER {
         noOperation(1),
         macNotifyClearVlan(2)
      }
      MAX-ACCESS  read-write
      STATUS      current
      DESCRIPTION "This variable uniquely identifies the operation that will be
                   executed on the object this entry applies to.
                   When read, noOperation(1) should be returned."
      ::= { hpicfGenericVlanFeaturesEntry 1 }

   hpicfDot1qTpFdbVlanId OBJECT-TYPE
      SYNTAX      VlanId
      MAX-ACCESS      read-only
      STATUS      current
      DESCRIPTION "The VLAN ID to which this entry belongs."
      ::= { hpicfGenericVlanFeaturesEntry 2 }

--   MAC Notify MIB Conformance

   hpicfGenericVlanFeaturesCompliances 
         OBJECT IDENTIFIER ::= { hpicfGenericVlanFeaturesConformance 1 }
   hpicfGenericVlanFeaturesGroups     
         OBJECT IDENTIFIER ::= { hpicfGenericVlanFeaturesConformance 2 }

-- compliance statements

   hpicfGenericVlanFeaturesCompliance MODULE-COMPLIANCE
        STATUS      current
        DESCRIPTION "The compliance statement for SNMP entities which
                     implement the MAC Notify MIB."
        MODULE  -- this module
           MANDATORY-GROUPS  {
                   hpicfGenericVlanFeaturesConfigGroup
                             }
        ::= { hpicfGenericVlanFeaturesCompliances 1 }

-- ******************
-- Conformance Groups
-- ******************

   hpicfGenericVlanFeaturesConfigGroup  OBJECT-GROUP
        OBJECTS 
           {
              hpicfMacNotifyClearVlanControl,
              hpicfDot1qTpFdbVlanId                          
           }
        STATUS      current
        DESCRIPTION "A collection of objects used for generic
                     VLAN operations."
        ::= { hpicfGenericVlanFeaturesGroups 2 }

END
