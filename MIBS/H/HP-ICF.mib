HP-ICF DEFINITIONS ::= BEGIN

       IMPORTS
           enterprises, IpAddress, Counter,
           TimeTicks, Gauge
               FROM RFC1155-SMI
           OBJECT-TYPE
               FROM RFC-1212
           TRAP-TYPE
               FROM RFC-1215
           DisplayString
               FROM RFC1213-MIB
           rptrAddrTrackLastSourceAddress, rptrPortAdminStatus
               FROM SNMP-REPEATER-MIB; -- 802.3 Repeater MIB

       hp                    OBJECT IDENTIFIER ::= { enterprises 11 }
       nm                    OBJECT IDENTIFIER ::= { hp 2 }
       hpSystem              OBJECT IDENTIFIER ::= { nm 3 }
       netElement            OBJECT IDENTIFIER ::= { hpSystem 7 }

       -- icf MODULE-IDENTITY
       --      LAST-UPDATED "9501180000Z"
       --      ORGANIZATION "Hewlett Packard Company,
       --                   Roseville Networks Division"
       --      CONTACT-INFO
       --             "       John Flick
       --
       --             Postal: Hewlett Packard Company
       --                     8000 Foothills Blvd. M/S 5556
       --                     Roseville, CA 95747-5556
       --
       --             E-mail: johnf@hprnd.rose.hp.com"
       --     DESCRIPTION
       --             "This MIB module describes devices in the HP 
       --             Integrated Communication Facility product 
       --             line."
       --     ::= { nm 14 }

       icf                   OBJECT IDENTIFIER ::= { nm 14 }

       -- The following textual conventions are defined in RFC1443
       -- (Textual Conventions for SNMPv2).  They are used here in
       -- the interest of easing the port to SNMPv2 SMI in future
       -- releases.

       -- Represents an 802 MAC address represented in the
       -- 'canonical' order defined by IEEE 802.1a, i.e., as
       -- if it were transmitted least significant bit
       -- first, even though 802.5 (in contrast to other
       -- 802.x protocols) requires MAC addresses to be
       -- transmitted most significant bit first.
       MacAddress ::= OCTET STRING (SIZE (6))

       -- The value of MIB-II's sysUpTime object at which a specific
       -- occurrence happened.  The specific occurrence must be
       -- defined in the description of any object defined using this
       -- type.
       TimeStamp ::= TimeTicks

       -- Represents a boolean value
       TruthValue ::= INTEGER { true(1), false(2) }

       -- The row status is used to manage the creation and deletion
       -- of conceptual rows, and is used as the value of the SYNTAX
       -- clause for the status column of a conceptual row.  It has
       -- six defined values:
       --
       --    'active', which indicates the row is in use by the
       --       device
       --
       --    'notInService', which indicates the row exists but is
       --       not in use
       --
       --    'notReady', which indicates the row exists, but is
       --       missing information necessary in order to make it
       --       active
       --
       --    'createAndGo', which is supplied by a management station
       --       wishing to create a new instance of a row and to have
       --       it immediately available for use
       --
       --    'createAndWait', which is supplied by a management
       --       station wishing to create a new instance of a row but
       --       not to have it immediately available for use
       --
       --    'destroy', which is supplied by a management station
       --       wishing to delete all of the instances associated
       --       with the conceptual row.
       --
       -- Whereas five of the six values (all except 'notReady') may
       -- be specified in a management protocol set operation, only
       -- three values will be returned in response to a management
       -- protocol retrieval operation: 'notReady', 'notInService',
       -- or 'active'.
       --
       -- Please refer to RFC1443 (Textual Conventions for SNMPv2),
       -- pages 8-19, for a more complete description of this textual
       -- convention, complete with a state diagram.
       RowStatus ::= INTEGER {
                         active(1),
                         notInService(2),
                         notReady(3),
                         createAndGo(4),
                         createAndWait(5),
                         destroy(6)
                     }

       -- The following textual convention is defined in RFC1447
       -- (Party MIB for SNMPv2).  It is used here in the interest of
       -- easing the port to SNMPv2 SMI in future releases.

       -- Denotes a transport service address.  t is formatted
       -- according to the conventions for addresses in the
       -- corresponding transport domain.  For snmpUIDPdomain, a
       -- TAddress is 6 octets long, the initial 4 octets containing
       -- the IP address in network byte order, and the last 2
       -- containing the UDP prot in network byte order.
       TAddress ::= OCTET STRING (SIZE (0..127))

       -- Defined transport domains from RFC1449

       -- snmpV2          OBJECT IDENTIFIER ::= { internet 6 }
       -- snmpDomains     OBJECT IDENTIFIER ::= { snmpV2 1 }
       -- snmpUDPDomain   OBJECT IDENTIFIER ::= { snmpDomains 1 }
       -- snmpCLNSDomain  OBJECT IDENTIFIER ::= { snmpDomains 2 }
       -- snmpCONSDomain  OBJECT IDENTIFIER ::= { snmpDomains 3 }
       -- snmpDDPDomain   OBJECT IDENTIFIER ::= { snmpDomains 4 }
       -- snmpIPXDomain   OBJECT IDENTIFIER ::= { snmpDomains 5 }

       -- Defined textual conventions from RFC1449
       -- SnmpUdpAddress ::= OCTET STRING (SIZE (6))
       -- SnmpIPXAddress ::= OCTET STRING (SIZE (12))
       -- SnmpOSIAddress ::= OCTET STRING (SIZE (1..85))
       -- SnmpNBPAddress ::= OCTET STRING (SIZE (3..99))


       hpicfAdmin            OBJECT IDENTIFIER ::= { icf 10 }
       
       -- HP defined transport domains
       
       hpicfDomains          OBJECT IDENTIFIER ::= { hpicfAdmin 1 }
       hpicfLLCDomain        OBJECT IDENTIFIER ::= { hpicfDomains 1 }


       -- Icf Devices

       bridge                OBJECT IDENTIFIER ::= { netElement 1 }
       router                OBJECT IDENTIFIER ::= { netElement 2 }
       hub                   OBJECT IDENTIFIER ::= { netElement 5 }
       chassis               OBJECT IDENTIFIER ::= { netElement 8 }

       bridge1010            OBJECT IDENTIFIER ::= { bridge 1 }
       bridgeRemote          OBJECT IDENTIFIER ::= { bridge 2 }
       eswitch               OBJECT IDENTIFIER ::= { bridge 3 }

       icfRouterER           OBJECT IDENTIFIER ::= { router 1 }
       icfRouterTR           OBJECT IDENTIFIER ::= { router 2 }
       icfRouterSR           OBJECT IDENTIFIER ::= { router 3 }
       icfRouterFR           OBJECT IDENTIFIER ::= { router 4 }
       icfRouterLR           OBJECT IDENTIFIER ::= { router 5 }
       icfRouterBR           OBJECT IDENTIFIER ::= { router 6 }
       icfRouterPR           OBJECT IDENTIFIER ::= { router 7 }
       icfRouter650          OBJECT IDENTIFIER ::= { router 8 }
       icfRouter230          OBJECT IDENTIFIER ::= { router 9 }
       icfRouter250          OBJECT IDENTIFIER ::= { router 10 }
       icfRouter255          OBJECT IDENTIFIER ::= { router 11 }
       icfRouter210          OBJECT IDENTIFIER ::= { router 12 }

       icfRouter650Engine    OBJECT IDENTIFIER ::= { icfRouter650 2 }
       icfRouter650Port4E    OBJECT IDENTIFIER ::= { icfRouter650 3 }
       icfRouter650Port4S    OBJECT IDENTIFIER ::= { icfRouter650 4 }
       icfRouter650Port4T    OBJECT IDENTIFIER ::= { icfRouter650 5 }

       etherTwist12          OBJECT IDENTIFIER ::= { hub 1 }
       fiberOptic            OBJECT IDENTIFIER ::= { hub 3 }
       etherTwist48          OBJECT IDENTIFIER ::= { hub 4 }
       thinLAN               OBJECT IDENTIFIER ::= { hub 5 }
       etherTwist24S         OBJECT IDENTIFIER ::= { hub 6 }
       advStack12            OBJECT IDENTIFIER ::= { hub 7 }
       advStack24            OBJECT IDENTIFIER ::= { hub 8 }
       advStack48            OBJECT IDENTIFIER ::= { hub 9 }
       advStackVg15          OBJECT IDENTIFIER ::= { hub 10 }
       advStackU8            OBJECT IDENTIFIER ::= { hub 11 }
       advStackU16           OBJECT IDENTIFIER ::= { hub 12 }

       repeaterAgent         OBJECT IDENTIFIER ::= { chassis 1 }
       chassisAgents         OBJECT IDENTIFIER ::= { chassis 2 }
       icfSensors            OBJECT IDENTIFIER ::= { chassis 3 }

       icfVgAgent            OBJECT IDENTIFIER ::= { chassisAgents 1 }
       icfEnetAgent          OBJECT IDENTIFIER ::= { chassisAgents 2 }

       icfPowerSupplySensor  OBJECT IDENTIFIER ::= { icfSensors 1 }
       icfFanSensor          OBJECT IDENTIFIER ::= { icfSensors 2 }
       icfTemperatureSensor  OBJECT IDENTIFIER ::= { icfSensors 3 }




       -- IcfCommon group

       icfCommon             OBJECT IDENTIFIER ::= { icf 1 }

       lastSetError OBJECT-TYPE
           SYNTAX     INTEGER {
                          unexpectedError(100),
                          -- Couldn't get a packet buffer
                          resourceLimitExceeded(101),
                          -- See stpPortState
                          disallowedSTPPortState(102),
                          -- For Super objects
                          incompleteSetlet(103),
                          -- See evtObject
                          invalidEventObject(104),
                          disallowedRemoteDevice(105),
                          -- Local must not equal remote
                          disallowedLAPBAdrsPair(106),
                          -- addressChunk
                          adrsAlreadyPresent(107),
                          -- addressChunk
                          staticSectionFull(108),
                          -- addressChunk
                          cantDeletePermAdrs(109),
                          inconsistentValues(110),
                          downloadInProgress(111)
                      }
           ACCESS     read-only
           STATUS     obsolete
           DESCRIPTION
                   "Provide more detailed, enterprise specific error
                   type. Any error resulting from a SET request will
                   cause this object to be updated, and the previous
                   value overwritten. A management entity may
                   retrieve more detailed error information than that
                   implied by the pdu's ErrorStatus, especially in 
                   the case of a genErr.
 
                   In SNMPv2, there are several more error codes which
                   provide most of the information that is provided
                   by the above codes.  Therefore, this object is now
                   obsolete."
           ::= { icfCommon 1 }

       password OBJECT-TYPE
           SYNTAX     OCTET STRING (SIZE (0..16))
           ACCESS     read-write
           STATUS     obsolete
           DESCRIPTION
               "This is the encrypted password for the device. The 
               algorithm used for the encryption process is HP 
               proprietary. Third party vendor support is provided by
               not setting a password on the device, and using the 
               community name 'public'.  This object is now obsolete,
               and is supported only on 'D' revision EtherTwist hubs
               and bridges and earlier.  It has been superseded by 
               icfSecurPassword."
           ::= { icfCommon 2 }

       reset OBJECT-TYPE
           SYNTAX     INTEGER {
                          warm(1),
                          cold(2)  -- not supported by bridges
                      }
           ACCESS     read-write   -- write-only on EtherTwist 'D' rev
                                   -- and earlier
           STATUS     obsolete
           DESCRIPTION
                   "When the reset object is set to to 'warm' it 
                   results in a 'warm' reset, which does not clear 
                   the parameters in NOVRAM to factory defaults. When
                   set to 'cold', it results in NOVRAM being set to
                   factory defaults. When this object is set, the 
                   agent replies, dallies a short time to allow the 
                   reply to be emitted from the device, then performs
                   the reset.  When read, this object always returns 
                   0.
 
                   This object is now obsolete.  It has been replaced by
                   hpicfReset."
           ::= { icfCommon 3 }

       selfTest OBJECT-TYPE
           SYNTAX     INTEGER --{
                          -- stSuccess(0),
                          -- stExecute(1)
                      --}
           ACCESS     read-write
           STATUS     obsolete
           DESCRIPTION
                   "Self test is invoked by setting this flag to 
                   'stExecute. When the object changes to 
                   'stSuccess', the test has completed successfully.
                   Icf devices will 'hard-fail' if the test does not
                   succeed.
 
                   This object is now obsolete.  It has been replaced by
                   hpicfSelfTest."
           ::= { icfCommon 4 }

       semaphore OBJECT-TYPE
           SYNTAX     IpAddress
           ACCESS     read-write
           STATUS     obsolete
           DESCRIPTION
                   "This object allows a set of objects to be locked.
                   The lock is only assured by the 'cooperation' of 
                   other management entities; they must wait until 
                   the lock is cleared (to value zero) prior to 
                   setting the lock. When this object is set to a 
                   management entity's IP address, if no other 
                   management entity has previously set the lock, the
                   set will succeed.  Otherwise, an error (BadValue) 
                   will be returned. It is the responsibility of the
                   owning management entity to clear the lock when 
                   the transactions complete. To protect against a 
                   management entity failure during a locked 
                   transaction, the agent is NOT responsible for 
                   verifying which management entity is performing 
                   transactions on locked objects; thus, any 
                   management entity can clear this object at any 
                   time. The agent does not do anything with this 
                   object except disallow multiple sets of different
                   IP addresses (unless the object has been cleared 
                   to zero). This means management entities can use 
                   this for locking any valid transactions on defined
                   sets of objects.  This object can also be used on
                   IPX networks by specifying the low 4 bytes of the
                   station address for the IpAddress.
                   
                   This object is now obsolete.  Individual groups of
                   objects now maintain their own locking mechanisms."
           -- INDEX  { INTEGER (1..3)
                      -- pollResponse(1), -  lock pollResponse object
                      -- mapObjects(2),   -  lock mapAddress, 
                                          -- mapState, and mapPort
                      -- eventGroup(3)    -  lock all objects in 
                                          -- event group
                     -- }
           ::= { icfCommon 5 }


       -- Discovery Group.  This group is now deprecated.  It will be
       -- supported for now for the sake of ICM/UX autodiscovery.

       discovery          OBJECT IDENTIFIER ::= { icfCommon 6 }

       pollResponse OBJECT-TYPE
           SYNTAX     INTEGER --{
                          -- false(0),
                          -- true(1)
                      --}
           ACCESS     read-write
           STATUS     obsolete
           DESCRIPTION
                   "Flag indicating whether device should respond to 
                   multicast SNMP PDUs. When set 'true', the device 
                   will respond to multicast SNMP PDU's. Otherwise, 
                   the response is discarded."
           ::= { discovery 1 }

       announceAddress OBJECT-TYPE
           SYNTAX     MacAddress
           ACCESS     read-write
           STATUS     deprecated
           DESCRIPTION
                   "When set to any MAC multicast address, the 
                   device will transmit three identical packets, each
                   with the MAC source set to the device's MAC 
                   address, the MAC destination to the multi-cast 
                   address, the destination SAP is F8, and the 
                   destination HP XSAP is 165D. These packets will 
                   traverse other ICF devices, allowing them to learn
                   the port connectivity of the multicasting 
                   device."
           ::= { discovery 2 }

       mapAddress OBJECT-TYPE
           SYNTAX     OCTET STRING (SIZE (6))
           ACCESS     read-write
           STATUS     deprecated
           DESCRIPTION
                   "When this object is set a map address search 
                   begins. If the address is detected on only one 
                   port, then the mapPort object is set to the port 
                   number on which the address was detected.

                   This object has been deprecated."
           ::= { discovery 3 }

       mapState OBJECT-TYPE
           SYNTAX     INTEGER --{
                          -- psNone(0),
                          -- psSingle(1),
                          -- psMany(2)
                      --}
           ACCESS     read-only
           STATUS     deprecated
           DESCRIPTION
                   "This object will be set to 'psNone' if the 
                   address set in the mapAddress object has not been
                   received on any of the device's interface/ports.
                   It will be set to 'psSingle' if the mapAddress has
                   been detected on only one interface/port. It will
                   be set to 'psMany' if the mapAddress has been 
                   detected on more than one interface/port.
 
                   This object has been deprecated."
           ::= { discovery 4 }

       mapPort OBJECT-TYPE
           SYNTAX     INTEGER (0..65535)
           ACCESS     read-only
           STATUS     deprecated
           DESCRIPTION
                   "The port number on which the map address was 
                   detected. If map state is 'psNone' or 'psMany'
                   then this object is not valid.
 
                   This object has been deprecated."
           ::= { discovery 5 }

       ipSubnetMask OBJECT-TYPE
           SYNTAX     IpAddress
           ACCESS     read-only
           STATUS     obsolete
           DESCRIPTION
                   "This object is the IP subnet mask.
 
                   This object is obsolete.  Management applications
                   should retrieve the ipAddrTable, which contains the
                   ipAdEntNetMask object for each interface on the
                   device."
           ::= { discovery 6 }


       -- Event Group

       icfEvent              OBJECT IDENTIFIER ::= { icfCommon 7 }

       eventNotificationNode OBJECT IDENTIFIER ::= { icfEvent 1 }

       evtIpNotify OBJECT-TYPE
           SYNTAX     IpAddress
           ACCESS     read-write
           STATUS     obsolete
           DESCRIPTION
                   "The network address of the manager node which is
                   to receive the event notification trap.
                   
                   This functionality is currently duplicated in the
                   authorized manager list."
           ::= { eventNotificationNode 1 }

       evtIpxNotify OBJECT-TYPE
           SYNTAX     OCTET STRING (SIZE (10))
           ACCESS     read-write
           STATUS     obsolete
           DESCRIPTION
                   "The IPX address of the manager node which is to
                   receive the event notification trap.
                   
                   This functionality is currently duplicated in the
                   authorized manager list."
           ::= { eventNotificationNode 2 }

       -- NOTE: This table is now obsolete.  It will be replaced in a
       -- later version of this MIB.  It is not implemented on the
       -- 100BaseVG agent, and will not be implemented on the next
       -- release of the AdvanceStack 10Mbit agent.

       evtTable OBJECT-TYPE
           SYNTAX     SEQUENCE OF EvtEntry
           ACCESS     not-accessible
           STATUS     obsolete
           DESCRIPTION
                   "A list of event entries for event processing."
           --INDEX    { evtIndex }
           ::= { icfEvent 2 }

       EvtEntry ::= 
           SEQUENCE {
               evtIndex                        INTEGER,
               evtArm                          INTEGER,
               evtTimeSinceOccurrence          TimeTicks
           }

       evtIndex OBJECT-TYPE
           SYNTAX     INTEGER {
                          warmStartEvent(1),
                          coldStartEvent(2),
                          spanTreeOrLinkBeatEvent(3),
                          temperatureOrSegmentationEvent(4),
                          backupLinkEvent(5),   -- hubs only

                          -- The following are supported only on
                          -- rev 'E' EtherTwist hubs or later and
                          -- AdvanceStack hubs
                          intrusionEvent(6),
                          addressMovedEvent(7),
                          newAddressEvent(8),
                          rptrHealthEvent(9),
                          rptrResetEvent(10)

                          -- spanTreeEvent(3),     -  bridges only
                          -- temperatureEvent(4),  -  bridges only
                          -- linkBeatEvent(3),     -  hubs only
                          -- segmentationEvent(4)  -  hubs only
                      }
           ACCESS     read-only
           STATUS     obsolete
           DESCRIPTION
                   "The index value which uniquely identifies the
                   event to which this entry is applicable."
           ::= { evtTable 1 }

       evtArm OBJECT-TYPE
           SYNTAX     INTEGER --{
                          -- off(0),
                          -- on(1)
                      --}
           ACCESS     read-write
           STATUS     obsolete
           DESCRIPTION
                   "This object arms and disarms events. Events are 
                   implicitly rearmed, that is, once an event occurs,
                   it is rearmed.  Sets to the intrusionEvent 
                   instance of this object are ignored, since 
                   intrusion events are actually armed through the 
                   hubSecPtAlarmEnable object."
           ::= { evtTable 2 }

       evtTimeSinceOccurrence OBJECT-TYPE
           SYNTAX     TimeTicks
           ACCESS     read-only
           STATUS     obsolete
           DESCRIPTION
                   "This object specifies the number of centiseconds
                   since this event last occurred."
           ::= { evtTable 3 }

       -- This table is now obsolete.  We now use the alarm and event
       -- tables of the RMON MIB for this functionality.

       evtThresholdTable OBJECT-TYPE
           SYNTAX     SEQUENCE OF EvtThresholdEntry
           ACCESS     not-accessible
           STATUS     obsolete
           DESCRIPTION
                   "A list of event entries for event processing."
           --INDEX    { evthIndex }
           ::= { icfEvent 3 }

       EvtThresholdEntry ::= 
           SEQUENCE {
               evthIndex                       INTEGER,
               evthArm                         INTEGER,
               evthObject                      OBJECT IDENTIFIER,
               evthThreshold                   INTEGER,
               evthHysteresis                  INTEGER,
               evthTimeInterval                TimeTicks,
               evthTimeSinceOccurrence         TimeTicks
           }

       evthIndex OBJECT-TYPE
           SYNTAX     INTEGER ( 1..5 )
           ACCESS     read-only
           STATUS     obsolete
           DESCRIPTION
                   "The index value which uniquely identifies the
                   event to which this entry is applicable."
           ::= { evtThresholdTable 1 }

       evthArm OBJECT-TYPE
           SYNTAX     INTEGER --{
                          -- off(0),
                          -- on(1)
                       --}
           ACCESS     read-write
           STATUS     obsolete
           DESCRIPTION
                   "This object arms and disarms events. The 
                   notification node, the associated event object,
                   threshold, hysteresis, and time interval should
                   all be set before an event is armed. The objects
                   do not need to be re-set if the existing values
                   are acceptable. The device will refuse to arm an
                   event with uninitialized objects.  Once armed, if
                   the threshold is met or exceeded during the event
                   time interval, a trap PDU is sent to the
                   eventNotificationNode.  Subsequently, the
                   monitored object must fall to or below the
                   hysteresis before another trap can be sent via the
                   threshold mechanism. The hysteresis may equal
                   threshold. Events are implicitly rearmed, that is,
                   once an event occurs, it is rearmed.  Setting this
                   object to 'on' will result in a genErr in any of
                   the following cases: object not set; cannot set an
                   event on this object; time interval not set;
                   threshold not set."
           ::= { evtThresholdTable 2 }

       evthObject OBJECT-TYPE
           SYNTAX     OBJECT IDENTIFIER
           ACCESS     read-write
           STATUS     obsolete
           DESCRIPTION
                   "The data of this object is itself an OBJECT
                   IDENTIFIER which selects the mib object and
                   instance that is to be monitored for the event.
                   Only types INTEGER and Counter are allowed."
           ::= { evtThresholdTable 3 }

       evthThreshold OBJECT-TYPE
           SYNTAX     INTEGER
           ACCESS     read-write
           STATUS     obsolete
           DESCRIPTION
                   "The threshold against which the variable 
                   specified in evthObject is tested over the time
                   interval specified in the evthTimeInterval  When
                   the threshold is met or exceeded, the event is
                   triggered. The event will not trigger again until
                   the variable falls to or below the evthHysteresis
                   value, and then meets or exceeds the threshold."
           ::= { evtThresholdTable 4 }

       evthHysteresis OBJECT-TYPE
           SYNTAX     INTEGER
           ACCESS     read-write
           STATUS     obsolete
           DESCRIPTION
                   "The low value which the variable specified in
                   evthObject must fall to or below after exceeding
                   evthThreshold before the event can re-occur when
                   the threshold is met or exceeded."
           ::= { evtThresholdTable 5 }

       evthTimeInterval OBJECT-TYPE
           SYNTAX     TimeTicks
           ACCESS     read-write
           STATUS     obsolete
           DESCRIPTION
                   "The time interval over which the variable
                   specified in the evthObject is sampled."
           ::= { evtThresholdTable 6 }

       evthTimeSinceOccurrence OBJECT-TYPE
           SYNTAX     TimeTicks
           ACCESS     read-only
           STATUS     obsolete
           DESCRIPTION
                   "This object specifies the number of centiseconds
                   since this event was last triggered."
           ::= { evtThresholdTable 7 }


       -- Link Test Group
       --
       -- The link test objects are part of a super-object. To start
       -- a link the settable objects must be set as a group within a
       -- single SNMP PDU.  There is no requirement on the ordering
       -- of the objects within the group. Only one of
       -- linkTest802MacAddress, linkTestIpxAddress, or
       -- linkTestIpAddress needs to be included in the group.  The
       -- selection of linkTest802MacAddress, linkTestIpxAddress, or
       -- linkTestIpAddress determines if the test is to use IEEE 
       -- 802.2 Test frames, IPX diagnostic frames, or ICMP Echo 
       -- PDUs. The linkTestRepetitions may be set as an individual
       -- object if the value it is set to is zero.  Doing so will
       -- abort any test in progress.
       --
       -- This group is deprecated.  It will be replaced by a new
       -- group in a later version of this MIB.

       linkTest           OBJECT IDENTIFIER ::= { icfCommon 8 }

       linkTestAddress    OBJECT IDENTIFIER ::= { linkTest 1 }

       linkTest802MacAddress OBJECT-TYPE
           SYNTAX     OCTET STRING (SIZE (6))
           ACCESS     read-write
           STATUS     deprecated
           DESCRIPTION
                   "If this object is set to the MAC address of a
                   node to link test in the same PDU that sets
                   linkTestRepetitions to a nonzero value, the link 
                   test performed will use IEEE 802 Test frames.

                   Note that setting more than one of
                   linkTest802MacAddress, linkTestIpAddress, and
                   linkTestIpxAddress to a non-null value in the same
                   PDU will result in a genErr."
           ::= { linkTestAddress 1 }

       linkTestIpAddress OBJECT-TYPE
           SYNTAX     IpAddress
           ACCESS     read-write
           STATUS     deprecated
           DESCRIPTION
                   "If this object is set to the network address of a
                   node to link test in the same PDU that sets
                   linkTestRepetitions to a nonzero value, the link
                   test performed will use ICMP Echo packets.

                   Note that setting more than one of
                   linkTest802MacAddress, linkTestIpAddress, and
                   linkTestIpxAddress to a non-null value in the same
                   PDU will result in a genErr."
           ::= { linkTestAddress 2 }

       linkTestIpxAddress OBJECT-TYPE
           SYNTAX     OCTET STRING (SIZE (10))
           ACCESS     read-write
           STATUS     deprecated
           DESCRIPTION
                   "If this object is set to the IPX address of a
                   node to link test in the same PDU that sets
                   linkTestRepetitions to a nonzero value, the link
                   test performed will use IPX diagnostic packets.

                   Note that setting more than one of
                   linkTest802MacAddress, linkTestIpAddress, and
                   linkTestIpxAddress to a non-null value in the same
                   PDU will result in a genErr."
           ::= { linkTestAddress 3 }

       linkTestRepetitions OBJECT-TYPE
           SYNTAX     INTEGER (0..65535)
           ACCESS     read-write
           STATUS     deprecated
           DESCRIPTION
                   "The number of link tests that the device is to
                   complete.  When this object is set to a non-zero
                   value, the linkTestSuccess object is zeroed and
                   the device begins a link test using IEEE 802.2
                   Test frames, ICMP Echo packets, or IPX diagnostic
                   packets depending on the address selected. Link
                   test results are contained in the link test
                   success object. This object's value decrements
                   (to zero) as the test proceeds. The test may be
                   canceled at any point by setting this object to
                   0."
           ::= { linkTest 2 }

       linkTestSuccess OBJECT-TYPE
           SYNTAX     INTEGER (0..65535)
           ACCESS     read-only
           STATUS     deprecated
           DESCRIPTION
                   "For every successful link test, this counter is
                   incremented.  When link tests are completed, this
                   counter contains the total number of successful
                   tests."
           ::= { linkTest 3 }

       linkTestTimeout OBJECT-TYPE
           SYNTAX     TimeTicks --(10..300000000)
           ACCESS     read-write
           STATUS     deprecated
           DESCRIPTION
                   "The time interval over which a link test response
                   must be received, or the test is counted as
                   failed."
           ::= { linkTest 4 }

       -- Icf 802.3 Mac Group

       icf8023MacTable OBJECT-TYPE
           SYNTAX     SEQUENCE OF Icf8023MacEntry
           ACCESS     not-accessible
           STATUS     obsolete
           DESCRIPTION
                   "A list of icf8023Mac entries."
           --INDEX    { icf8023MacIndex }
           ::= { icfCommon 9 }

       Icf8023MacEntry ::= 
           SEQUENCE {
               icf8023MacIndex                 INTEGER,
               icf8023MacInBroadcastPkts       Counter,
               icf8023MacOutBroadcastPkts      Counter,
               icf8023MacInMulticastPkts       Counter,
               icf8023MacOutMulticastPkts      Counter,
               icf8023MacRunts                 Counter,
               icf8023MacGiants                Counter,
               icf8023MacMissedPktErrors       Counter,
               icf8023MacExcessDeferrals       Counter,
               icf8023MacTotalMediaErrors      Counter,
               icf8023MacSpuriousIntrs         Counter
           }

       icf8023MacIndex OBJECT-TYPE
           SYNTAX     INTEGER
           ACCESS     read-only
           STATUS     obsolete
           DESCRIPTION
                   "The index value which uniquely identifies the
                   port to which this entry is applicable. The port
                   identified by a particular value of this index on
                   a hub is the same port as identified by the same
                   value of rptrPortIndex.  Note that since this hub
                   always has exactly 1 port group, there is no group
                   index for this table.  For a bridge, the port
                   identified by a particular value of this index is
                   the same port identified by the same value of
                   ifIndex."
           ::= { icf8023MacTable 1 }

       icf8023MacInBroadcastPkts OBJECT-TYPE
           SYNTAX     Counter
           ACCESS     read-only
           STATUS     obsolete
           DESCRIPTION
                   "Count of the broadcast packets received."
           ::= { icf8023MacTable 2 }

       icf8023MacOutBroadcastPkts OBJECT-TYPE
           SYNTAX     Counter
           ACCESS     read-only
           STATUS     obsolete
           DESCRIPTION
                   "Count of the broadcast packets transmitted."
           ::= { icf8023MacTable 3 }

       icf8023MacInMulticastPkts OBJECT-TYPE
           SYNTAX     Counter
           ACCESS     read-only
           STATUS     obsolete
           DESCRIPTION
                   "Count of the multicast packets received."
           ::= { icf8023MacTable 4 }

       icf8023MacOutMulticastPkts OBJECT-TYPE
           SYNTAX     Counter
           ACCESS     read-only
           STATUS     obsolete
           DESCRIPTION
                   "Count of the multicast packets transmitted."
           ::= { icf8023MacTable 5 }

       icf8023MacRunts OBJECT-TYPE
           SYNTAX     Counter
           ACCESS     read-only
           STATUS     obsolete
           DESCRIPTION
                   "The number of media frames encountered that were
                   too short (by ethernet/802.3 standards)."
           ::= { icf8023MacTable 6 }

       icf8023MacGiants OBJECT-TYPE
           SYNTAX     Counter
           ACCESS     read-only
           STATUS     obsolete
           DESCRIPTION
                   "The number of media frames encountered that were
                   too long (by ethernet/802.3 standards)."
           ::= { icf8023MacTable 7 }

       icf8023MacMissedPktErrors OBJECT-TYPE
           SYNTAX     Counter
           ACCESS     read-only
           STATUS     obsolete
           DESCRIPTION
                   "The number of frames lost due to lack of
                   resources (e.g. ring buffers, memory buffers,
                   etc)."
           ::= { icf8023MacTable 8 }

       icf8023MacExcessDeferrals OBJECT-TYPE
           SYNTAX     Counter
           ACCESS     read-only
           STATUS     obsolete
           DESCRIPTION
                   "The number of times a frame could not be sent due
                   to excess deferrals because another node was
                   transmitting continually."
           ::= { icf8023MacTable 9 }

       icf8023MacTotalMediaErrors OBJECT-TYPE
           SYNTAX     Counter
           ACCESS     read-only
           STATUS     obsolete
           DESCRIPTION
                   "Count of all possible medium transmit and receive
                   errors, such as crc, alignment, sequence, length,
                   excess etc. The purpose of this object is to
                   support aggregate LAN medium errors for event
                   processing. Collisions and runts are not
                   considered an error."
           ::= { icf8023MacTable 10 }

       icf8023MacSpuriousIntrs OBJECT-TYPE
           SYNTAX     Counter
           ACCESS     read-only
           STATUS     obsolete
           DESCRIPTION
                   "The number of times that the network interface
                   for this port generated a spurious hardware
                   interrupt.  A non-zero value for this object
                   indicates a potential hardware problem."
           ::= { icf8023MacTable 11 }

       -- IcfDownload Group
       --
       -- The icfDownload objects are provided to download a new
       -- version of firmware into the device.  The tftp protocol is
       -- used for the download.  To initiate a download, the
       -- management station must set icfDownloadIp[x]Address to the
       -- address of a tftp server and the management station must
       -- also set icfDownloadFilename to the path name of the file
       -- containing the new revision of firmware.  The address and
       -- filename must both be set in the same PDU.
       --
       -- Note that this group is now obsolete, and has been replaced
       -- by the hpicfDownload group.  It is not supported in any
       -- AdvanceStack products.

       icfDownload        OBJECT IDENTIFIER ::= { icfCommon 10 }

       icfDownloadAddress OBJECT IDENTIFIER ::= { icfDownload 1 }

       icfDownloadIpAddress OBJECT-TYPE
           SYNTAX     IpAddress
           ACCESS     read-write
           STATUS     obsolete
           DESCRIPTION
                   "The IP address of the TFTP server to download
                   firmware from."
           ::= { icfDownloadAddress 1 }

       icfDownloadIpxAddress OBJECT-TYPE
           SYNTAX     OCTET STRING (SIZE (10))
           ACCESS     read-write
           STATUS     obsolete
           DESCRIPTION
                   "The IPX address of the TFTP server to download
                   firmware from."
           ::= { icfDownloadAddress 2 }

       icfDownloadFilename OBJECT-TYPE
           SYNTAX     DisplayString (SIZE (0..63))
           ACCESS     read-write
           STATUS     obsolete
           DESCRIPTION
                   "Filename and path of file to download (maximum
                   length of 63 characters + NULL)."
           ::= { icfDownload 2 }

       --
       -- Icf Hub Group
       --
       -- This group is implemented on both EtherTwist and AdvanceStack
       -- 10Mbit hubs.
       --

       icfHub             OBJECT IDENTIFIER ::= { icf 2 }

       hubThinlanFault OBJECT-TYPE
           SYNTAX     INTEGER --{
                          -- false(0),
                          -- true(1)
                       --}
           ACCESS     read-write
           STATUS     obsolete
           DESCRIPTION
                   "When set to 'true' this object causes the Fault
                   LED to blink if the ThinLan Port is segmented.

                   This object has been deprecated in favor of
                   hpRptrThinlanFault."
           ::= { icfHub 1 }

       -- Note: The hubGlobal counters that are composed of other
       -- objects are provided to allow for event testing on global
       -- error conditions.

       hubGlobal          OBJECT IDENTIFIER ::= { icfHub 2 }

       hubGlobalErrors OBJECT-TYPE
           SYNTAX     Counter
           ACCESS     read-only
           STATUS     obsolete
           DESCRIPTION
                   "This counter is incremented for each packet with
                   an error received on any port. This counter does
                   not include runts, as they are a normal media
                   condition.

                   This object has been deprecated in favor of
                   hpRptrMonGlobalErrors."
           ::= { hubGlobal 1 }

       hubGlobalCollisions OBJECT-TYPE
           SYNTAX     Counter
           ACCESS     read-only
           STATUS     obsolete
           DESCRIPTION
                   "This counter is incremented for each collision
                   between any two or more ports (or AUI) detected by
                   the hub.

                   This object has been deprecated in favor of
                   rptrMonitorTransmitCollisions."
           ::= { hubGlobal 2 }

       hubGlobalPktFragments OBJECT-TYPE
           SYNTAX     Counter
           ACCESS     read-only
           STATUS     obsolete
           DESCRIPTION
                   "This counter is the sum of hubPortPktFragments
                   for all ports.

                   This object has been deprecated in favor of
                   hpRptrMonGlobalFrames."
           ::= { hubGlobal 3 }

       hubGlobalRunts OBJECT-TYPE
           SYNTAX     Counter
           ACCESS     read-only
           STATUS     obsolete
           DESCRIPTION
                   "This counter is incremented for each runt frame
                   received on any port.

                   This object has been deprecated in favor of
                   hpRptrMonGlobalRunts."
           ::= { hubGlobal 4 }

       hubGlobalGiants OBJECT-TYPE
           SYNTAX     Counter
           ACCESS     read-only
           STATUS     obsolete
           DESCRIPTION
                   "This counter is incremented for each giant frame
                   received on any port.

                   This object has been deprecated in favor of
                   hpRptrMonGlobalFrameTooLongs."
           ::= { hubGlobal 5 }

       hubGlobalCrcErrors OBJECT-TYPE
           SYNTAX     Counter
           ACCESS     read-only
           STATUS     obsolete
           DESCRIPTION
                   "This counter is incremented for each frame with a
                   CRC error received on any port.

                   This object has been deprecated in favor of
                   hpRptrMonGlobalFCSErrors."
           ::= { hubGlobal 6 }

       hubGlobalAlignmentErrors OBJECT-TYPE
           SYNTAX     Counter
           ACCESS     read-only
           STATUS     obsolete
           DESCRIPTION
                   "This counter is incremented for each frame with
                   an alignment error received on any port.

                   This object has been deprecated in favor of
                   hpRptrMonGlobalAlignmentErrors."
           ::= { hubGlobal 7 }

       hubGlobalInOctets OBJECT-TYPE
           SYNTAX     Counter
           ACCESS     read-only
           STATUS     obsolete
           DESCRIPTION
                   "This counter is incremented for each octet
                   received on any port.

                   This object has been deprecated in favor of
                   hpRptrMonGlobalOctets."
           ::= { hubGlobal 8 }

       hubGlobalInUcastPkts OBJECT-TYPE
           SYNTAX     Counter
           ACCESS     read-only
           STATUS     obsolete
           DESCRIPTION
                   "This counter is incremented for each unicast
                   packet received on any port.

                   This counter has been deprecated in favor of
                   hpRptrMonGlobalUcastPackets."
           ::= { hubGlobal 9 }

       hubGlobalInNUcastPkts OBJECT-TYPE
           SYNTAX     Counter
           ACCESS     read-only
           STATUS     obsolete
           DESCRIPTION
                   "This counter is incremented for each non-unicast
                   packet received on any port.

                   This object has been deprecated in favor of
                   hpRptrMonGlobalBcastPackets and
                   hpRptrMonGlobalMcastPackets."
           ::= { hubGlobal 10 }

       hubGlobalInBroadcastPkts OBJECT-TYPE
           SYNTAX     Counter
           ACCESS     read-only
           STATUS     obsolete
           DESCRIPTION
                   "This counter is incremented for each broadcast
                   packet received on any port.

                   This object has been deprecated in favor of
                   hpRptrMonGlobalBcastPackets."
           ::= { hubGlobal 11 }

       -- Icf Hub Port Table

       hubPortTable OBJECT-TYPE
           SYNTAX     SEQUENCE OF HubPortEntry
           ACCESS     not-accessible
           STATUS     obsolete
           DESCRIPTION
                   "A list of hubPort entries."
           --INDEX    { hubPortIndex }
           ::= { icfHub 3 }

       HubPortEntry ::= 
           SEQUENCE {
               hubPortIndex                    INTEGER,
               hubPortPktFragments             Counter,
               hubPortCollisions               Counter,
               hubPortSegmentation             INTEGER,
               hubPortLinkBeatStatus           INTEGER,
               hubPortLinkBeatEnable           INTEGER,
               hubPortMacAddress               MacAddress,
               hubPortAddressState             INTEGER,
               hubPortPolarityReversed         INTEGER,
               hubPortLateEventDisable         INTEGER
           }

       hubPortIndex OBJECT-TYPE
           SYNTAX     INTEGER (1..1024)
           ACCESS     read-only
           STATUS     obsolete
           DESCRIPTION
                   "The index value which uniquely identifies the
                   port to which this entry is applicable. The port
                   identified by a particular value of this index is
                   the same port as identified by the same value of
                   rptrPortIndex."
           ::= { hubPortTable 1 }

       hubPortPktFragments OBJECT-TYPE
           SYNTAX     Counter
           ACCESS     read-only
           STATUS     obsolete
           DESCRIPTION
                   "This counter is incremented when a packet or
                   packet fragment is encountered for a port
                   instance.

                   This object has been deprecated in favor of
                   rptrMonitorPortReadableFrames."
           ::= { hubPortTable 2 }

       hubPortCollisions OBJECT-TYPE
           SYNTAX     Counter
           ACCESS     read-only
           STATUS     obsolete
           DESCRIPTION
                   "This counter is incremented when a port is
                   involved in a collision.

                   This object has been deprecated in favor of
                   rptrMonitorPortCollisions."
           ::= { hubPortTable 3 }

       hubPortSegmentation OBJECT-TYPE
           SYNTAX     INTEGER --{
                          -- false(0),
                          -- true(1)
                      --}
           ACCESS     read-only
           STATUS     obsolete
           DESCRIPTION
                   "This is a flag which is 'true' if the port is
                   currently segmented and 'false' otherwise.

                   This object has been deprecated in favor of
                   rptrPortAutoPartitionState."
           ::= { hubPortTable 4 }

       hubPortLinkBeatStatus OBJECT-TYPE
           SYNTAX     INTEGER --{
                          -- false(0),
                          -- true(1)
                      --}
           ACCESS     read-only
           STATUS     obsolete
           DESCRIPTION
                   "This is a flag which is 'true' if link beat is
                   detected on the port and 'false' otherwise.  The
                   value of this variable will always be 'true' when
                   the corresponding instance of
                   hubPortLinkBeatEnable is 'false'.

                   This object has been deprecated in favor of
                   rpMauMediaAvailable."
           ::= { hubPortTable 5 }

       hubPortLinkBeatEnable OBJECT-TYPE
           SYNTAX     INTEGER --{
                          -- false(0),
                          -- true(1)
                       --}
           ACCESS     read-write
           STATUS     obsolete
           DESCRIPTION
                   "When this flag is set to 'true' the port's link
                   beat is enabled and when set to 'false' it is
                   disabled.

                   This object has been deprecated in favor of
                   hpRptrPtLinkbeatEnable."
           ::= { hubPortTable 6 }

       hubPortMacAddress OBJECT-TYPE
           SYNTAX     MacAddress
           ACCESS     read-only
           STATUS     obsolete
           DESCRIPTION
                   "Each port maintains the MAC address of the node
                   currently attached to it. This address is valid
                   only when the port state flag is set to 
                   'psSingle'.

                   This object has been deprecated in favor of
                   rptrAddrTrackNewLastSrcAddress."
           ::= { hubPortTable 7 }

       hubPortAddressState OBJECT-TYPE
           SYNTAX     INTEGER --{
                          -- psNone(0),
                          -- psSingle(1),
                          -- psMany(2)
                       --}
           ACCESS     read-write
           STATUS     obsolete
           DESCRIPTION
                   "The port state object may take on three values.
                   'psNone' means no packets have been received on
                   the port. 'psSingle' means all packets received on
                   the port have originated from a single MAC
                   address. 'psMany' means that packets originating
                   from more than one node have been received on the
                   port. To (re)start a search for a MAC address set
                   the port state to 'psNone'."
           ::= { hubPortTable 8 }

       hubPortPolarityReversed OBJECT-TYPE
           SYNTAX     INTEGER --{
                          -- false(0),
                          -- true(1)
                       --}
           ACCESS     read-only
           STATUS     obsolete
           DESCRIPTION
                   "This object is used to indicate that the hub port
                   was wired with the positive/negative polarity of
                   its transmit and receive pairs reversed.  Note
                   that the port will continue to operate in this
                   state, with the hub inverting the polarity
                   internally.

                   This object has been deprecated in favor of
                   hpRptrPtPolarityReversed."
           ::= { hubPortTable 9 }

       hubPortLateEventDisable OBJECT-TYPE
           SYNTAX     INTEGER {
                          true(1),
                          false(2)
                      }
           ACCESS     read-only
           STATUS     obsolete
           DESCRIPTION
                   "This object indicates that the hub port was
                   disabled as a result of excessive late collisions
                   being caused by the end node attached to this
                   port.  This flag is cleared when the port is
                   reenabled by setting rptrPortAdminStatus to
                   'enabled'."
           ::= { hubPortTable 10 }

       hubBitmaps         OBJECT IDENTIFIER ::= { icfHub 4 }

       hubPortsOperStatus OBJECT-TYPE
           SYNTAX     OCTET STRING (SIZE (1..128))
           ACCESS     read-only
           STATUS     obsolete
           DESCRIPTION
                   "The hubPortsOperStatus is a bit map of the state
                   of all hub ports.  The object has a 1 bit for each
                   port that is enabled, not segmented, and linkbeat
                   is detected.  Ports on which these conditions are
                   not true have a 0 bit.  The bits are placed into
                   the OCTET STRING in the following order:

                       octet     0  octet     1  octet     2  ...
                       bits    7-0  bits    7-0  bits    7-0  ...
                       ports   1-8  ports  9-16  ports 17-24  ...

                   Values of unused bits in the last octet are
                   undefined.

                   This object has been deprecated in favor of
                   hpRptrGrpPortsAdminStatus."
           ::= { hubBitmaps 1 }

       hubAddressTableMaxAge OBJECT-TYPE
           SYNTAX     TimeTicks --(60000..65535000)
           ACCESS     read-write
           STATUS     obsolete
           DESCRIPTION
                   "The hubAddressTableMaxAge is the time beyond
                   which an inactive MAC address will be removed from
                   the hubPortMacAddress table and the
                   hubAddressTable.  Although hubAddressTableMaxAge
                   is specified in units of 10ms time ticks, the
                   actual resolution of this timer is 10 seconds.  A
                   value of 65535000 indicates no aging shall take
                   place."
           ::= { icfHub 5 }

       hubAddressTable OBJECT-TYPE
           SYNTAX     SEQUENCE OF HubAddressEntry
           ACCESS     not-accessible
           STATUS     deprecated
           DESCRIPTION
                   "A list of entries present in the hub address
                   table."
           --INDEX    { hubAddressIndex }
           ::= { icfHub 6 }

       HubAddressEntry ::= 
           SEQUENCE {
               hubAddressIndex                 INTEGER,
               hubAddressChunk                 OCTET STRING
           }

       hubAddressIndex OBJECT-TYPE
           SYNTAX     INTEGER (1..52)
           ACCESS     read-only           
           STATUS     obsolete
           DESCRIPTION
                   "The index value which uniquely identifies the
                   chunk to which this entry is applicable."
           ::= { hubAddressTable 1 }

       hubAddressChunk OBJECT-TYPE
           SYNTAX     OCTET STRING (SIZE (408))
           ACCESS     read-only           
           STATUS     obsolete
           DESCRIPTION
                   "The hubAddressChunk object returns an opaque
                   chunk of the address table. Each chunk can be
                   interpreted as an array of records in the form:

                       mac address [6 bytes], port number [2 bytes],
                       inactivity time [4 bytes]

                   On a Get, the returned chunk can include empty
                   (unused) entries.  Instances are chunk numbers,
                   which start at 1 and go to 52.  Each chunk can
                   hold 34 addresses.

                   A returned chunk might look like:

                       Address       Port      Inactivity Time
            
                       080009001234  1         0
                       080009002345  2         10000
                       080009003456  1         20000
                       000000000000  1         0
                       080009009876  EMPTY     0
                       080009004567  EMPTY     15000
                                     .
                                     .
                                     .
                       080009005678  EOL       959000

                   A value of EMPTY in the Port field indicates an
                   unused (i.e.  aged out) entry in the table.  When
                   the EOL (End Of List) bit is set in the Port 
                   field, that entry is the last entry in the table.
                   It is possible for EOL to be seen in any entry.
                   EOL (0x4000) and EMPTY (0x8000) are bit masks
                   which are ORed with the port number in the port
                   field of the entry.  It is possible for both the
                   EOL and EMPTY bits to be set in the same entry.

                   The remainder of the chunk after the EOL entry
                   will be zeroed.

                   The inactivityTime and Address fields are
                   meaningless if the EMPTY bit is set in the Port
                   field. In this case, inactivityTime and Address
                   are not guaranteed to be zeroed.  The Manager may
                   start with any chunk it likes and request the
                   chunks in any order.  It may perform multiple
                   requests for the same chunk.  The agent does not
                   save state from previous requests.

                   A request of chunk #1 would return the contents of
                   the first 34 address table entries,  whether they
                   are all full, all empty, or some full and the rest
                   empty.  A request of chunk #2 will return entries
                   #35 through #68. And so on.

                   The address table can change between Get requests.
                   An address' location can change, or an address
                   could age out and then be added back in at a
                   different location in the table.  Thus, the
                   Manager could see the address twice in the table."
           ::= { hubAddressTable 2 }

       hubNumBkpLinks OBJECT-TYPE
           SYNTAX     INTEGER
           ACCESS     read-only
           STATUS     obsolete
           DESCRIPTION
                   "The number of backup links configurable on this
                   hub."
           ::= { icfHub 7 }

       hubBkpLinkTable OBJECT-TYPE
           SYNTAX     SEQUENCE OF HubBkpLinkEntry
           ACCESS     not-accessible
           STATUS     obsolete
           DESCRIPTION
                   "A list of backup link configuration entries.  For
                   a given backup link,  the hub will periodically
                   send a test packet to the device at the end of the
                   link.  If there are no responses (the number is
                   configurable), the hub will enable the backup port
                   and disable the primary port.  After the primary
                   link is fixed, the user must turn the primary port
                   on to resume normal operation.

                   At any time, the management station can look at
                   rptrPortAdminStatus for the backup port to
                   determine if it is currently in use.

                   The backup link algorithm enables and disables the
                   backup port by modifying rptrPortAdminStatus for
                   that port.  After the backup port has been enabled
                   by the backup link algorithm, if the primary port
                   is subsequently enabled via the hub console port
                   or by a set of rptrPortAdminStatus, the backup
                   port will be turned off and the periodic test
                   packets will begin again.

                   When the backup link objects are set, the backup
                   port will be turned off, the primary port will be
                   turned on,  and the periodic test packets will be
                   sent.  The time between test packets is
                   configurable by setting hubBackupTestTime.  The
                   number of failures needed to switch to the backup
                   link is configured by setting
                   hubBackupConsecutiveFails.  The backup link
                   function can be turned off by setting
                   hubBackupPort to 0.

                   All five of the backup link objects must be set
                   together in a single PDU except for the case of
                   setting hubBackupPort to 0, in which case, the
                   hubBackupPort can be set without setting the other
                   objects.  Currently, the size of the backup link
                   table is one; future releases may provide the
                   ability to monitor more than one backup link."
           ::= { icfHub 8 }

       HubBkpLinkEntry ::=
           SEQUENCE {
               hubBkpLinkIndex                 INTEGER,
               hubBackupPort                   INTEGER,
               hubPrimaryPort                  INTEGER,
               hubBackupAddress                OCTET STRING,
               hubBackupTestTime               TimeTicks,
               hubBackupConsecutiveFails       INTEGER
           }

       hubBkpLinkIndex OBJECT-TYPE
           SYNTAX     INTEGER
           ACCESS     read-only
           STATUS     obsolete
           DESCRIPTION
                   "The index value which uniquely identifies the
                   backup link configuration entry to which the
                   instance is applicable."
           ::= { hubBkpLinkTable 1 }

       hubBackupPort OBJECT-TYPE
           SYNTAX     INTEGER (0..1024)
           ACCESS     read-write
           STATUS     obsolete
           DESCRIPTION
                   "The port number of the backup link.  Setting this
                   object to zero removes the backup link
                   configuration."
           ::= { hubBkpLinkTable 2 }

       hubPrimaryPort OBJECT-TYPE
           SYNTAX     INTEGER (0..1024)
           ACCESS     read-write
           STATUS     obsolete
           DESCRIPTION
                   "The port number of the primary link.  It can only
                   be set to zero if the hubBackupPort is also zero."
           ::= { hubBkpLinkTable 3 }

       hubBackupAddress OBJECT-TYPE
           SYNTAX     OCTET STRING (SIZE (6))
           ACCESS     read-write
           STATUS     obsolete
           DESCRIPTION
                   "The MAC address of the device at the other end of
                   the primary link which will respond to the
                   periodic test packets sent by this hub."
           ::= { hubBkpLinkTable 4 }

       hubBackupTestTime OBJECT-TYPE
           SYNTAX     TimeTicks --(100..1500)
           ACCESS     read-write
           STATUS     obsolete
           DESCRIPTION
                   "The frequency, in time ticks, between sending the
                   periodic test packets.  The actual resolution of
                   this timer is in seconds.  The test packet
                   response timeout is fixed at 500ms."
           ::= { hubBkpLinkTable 5 }

       hubBackupConsecutiveFails OBJECT-TYPE
           SYNTAX     INTEGER (1..16)
           ACCESS     read-write
           STATUS     obsolete
           DESCRIPTION
                   "The number of test packet failures which will
                   cause the hub to switch to the backup link (i.e.,
                   backup port turned on, primary port turned off).
                   A value of one is generally not recomended and
                   will cause the backup link to be enabled upon the
                   first failure."
           ::= { hubBkpLinkTable 6 }

       hubSqeEnabled OBJECT-TYPE
           SYNTAX     INTEGER --{
                          -- false(0),
                          -- true(1)
                      --}
           ACCESS     read-only
           STATUS     obsolete
           DESCRIPTION
                   "When 'true', this flag indicates that SQE has
                   been detected for the last ten agent transmits and
                   there is a high probability that the SQE switch on
                   the transceiver attached to the AUI port is set to
                   Enabled, when it should be Disabled.

                   This object has been deprecated in favor of
                   hpRptrSqeEnabled."
           ::= { icfHub 9 }


       --
       --  The Hub Security group.  This group is implemented only on
       --  rev 'E' or later EtherTwist hubs, and AdvanceStack 10Mbit
       --  hubs.
       --

       hubSecurity        OBJECT IDENTIFIER ::= { icfHub 10 }

       hubSecurePortTable OBJECT-TYPE
           SYNTAX     SEQUENCE OF HubSecurePortEntry
           ACCESS     not-accessible
           STATUS     mandatory
           DESCRIPTION
                   "Table containing security configuration for each
                   port."
           ::= { hubSecurity 1 }

       hubSecurePortEntry OBJECT-TYPE
           SYNTAX     HubSecurePortEntry
           ACCESS     not-accessible
           STATUS     mandatory
           DESCRIPTION
                   "An entry in the hubSecurePortTable, containing
                   the security configuration for a single port."
           INDEX      { hubSecPtGroupIndex, hubSecPtPortIndex }
           ::= { hubSecurePortTable 1 }

       HubSecurePortEntry ::=
           SEQUENCE {
               hubSecPtGroupIndex              INTEGER,
               hubSecPtPortIndex               INTEGER,
               hubSecPtSecurityAddress         OCTET STRING,
               hubSecPtAuthorizedAddress       OCTET STRING,
               hubSecPtPreventEavesdrop        INTEGER,
               hubSecPtAlarmEnable             INTEGER,
               hubSecPtIntrusionFlag           INTEGER
           }

       hubSecPtGroupIndex OBJECT-TYPE
           SYNTAX     INTEGER (1..1024)
           ACCESS     read-only
           STATUS     mandatory
           DESCRIPTION
                   "This object identifies the group containing the
                   port for which this entry contains security
                   configuration information."
           ::= { hubSecurePortEntry 1 }

       hubSecPtPortIndex  OBJECT-TYPE
           SYNTAX     INTEGER (1..1024)
           ACCESS     read-only
           STATUS     mandatory
           DESCRIPTION
                   "This object identifies the port within the group
                   for which this entry contains security
                   configuration information."
           ::= { hubSecurePortEntry 2 }

       hubSecPtSecurityAddress OBJECT-TYPE
           SYNTAX     OCTET STRING (SIZE (6))
           ACCESS     read-write
           STATUS     mandatory
           DESCRIPTION
                   "The desired authorized MAC address for this port.
                   This can be either a regular station address to
                   configure a specific address, or it can be one of
                   the following special values to specify the
                   address learning method:
                       FFFF-FFFF-FFFE: learnOnce.  First source MAC
                           address heard on this port becomes the
                           authorized address.  Setting this value
                           initiates learning of a new authorized
                           address.  When a new authorized address is
                           learned, it will be stored in nonvolatile
                           memory.  This variable will return
                           learnOnceConditionally to a GET operation
                           after it has been set to this value.
                       FFFF-FFFF-FFFD: learnOnceConditionally.  This
                           option will initiate learning of a new
                           authorized address only if the previous
                           hubSecPtSecurityAddress was set to a
                           specific address or learnContinuous.  No
                           action will be performed if the previous
                           value was already learnOnceConditionally.
                       FFFF-FFFF-FFFC: learnContinuous.  Any address
                           heard becomes the new authorized address.
                           When a new address is learned, it may
                           cause an alarm, but it does not store
                           anything in nonvolatile memory."
           ::= { hubSecurePortEntry 3 }

       hubSecPtAuthorizedAddress OBJECT-TYPE
           SYNTAX     OCTET STRING (SIZE (6))
           ACCESS     read-only
           STATUS     mandatory
           DESCRIPTION
                   "The MAC address of the station authorized to be
                   on this port.  This address could either have been
                   configured by specifying a regular station address
                   for hubSecPtSecurityAddress, or it could have been
                   learned by the agent if hubSecPtSecurityAddress
                   was set to one of the special values listed above.
                   Once the agent has learned an authorized address,
                   it will be saved across powerfails, unless the
                   agent was configured for learnContinuous mode."
           ::= { hubSecurePortEntry 4 }

       hubSecPtPreventEavesdrop OBJECT-TYPE
           SYNTAX     INTEGER {
                          enable(1),
                          disable(2)
                      }
           ACCESS     read-write
           STATUS     mandatory
           DESCRIPTION
                   "If enabled, unicast packets not addressed to the
                   authorized address for this port will be
                   scrambled."
           ::= { hubSecurePortEntry 5 }

       hubSecPtAlarmEnable OBJECT-TYPE
           SYNTAX     INTEGER {
                          enable(1),
                          disable(2)
                      }
           ACCESS     read-write
           STATUS     mandatory
           DESCRIPTION
                   "If enabled, the agent will generate an
                   intrusionTrap if a packet is received on this port
                   with a source MAC address that is different from
                   the hubSecPtAuthorizedAddress for this port."
           ::= { hubSecurePortEntry 6 }

       hubSecPtIntrusionFlag OBJECT-TYPE
           SYNTAX     INTEGER {
                          intrusion(1),
                          noIntrusion(2)
                      }
           ACCESS     read-write
           STATUS     mandatory
           DESCRIPTION
                   "This flag indicates if an intrusion has occurred
                   on this port.  The Security LED on the hub will
                   blink if any instance of this flag has the value
                   intrusion.  Setting this flag to noIntrusion will
                   turn off the Security LED if no other ports have
                   this flag set to intrusion.  An intrusion will
                   only cause an alarm and an intrusion log entry if
                   this flag is equal to noIntrusion."
           ::= { hubSecurePortEntry 7 }

       hubIntruderLogTable OBJECT-TYPE
           SYNTAX     SEQUENCE OF HubIntruderLogEntry
           ACCESS     not-accessible
           STATUS     mandatory
           DESCRIPTION
                   "This table contains a record of the twenty most
                   recent port security violations.  The first entry
                   in the table is the oldest."
           ::= { hubSecurity 2 }

       hubIntruderLogEntry OBJECT-TYPE
           SYNTAX     HubIntruderLogEntry
           ACCESS     not-accessible
           STATUS     mandatory
           DESCRIPTION
                   "A row in the hubIntruderLogTable containing
                   information about a single port security
                   violation."
           INDEX     { hubIntruderIndex }
           ::= { hubIntruderLogTable 1 }

       HubIntruderLogEntry ::=
           SEQUENCE {
               hubIntruderIndex                INTEGER,
               hubIntruderPort                 INTEGER,
               hubIntruderGroup                INTEGER,
               hubIntruderAddress              OCTET STRING,
               hubIntruderTime                 TimeTicks
           }

       hubIntruderIndex OBJECT-TYPE
           SYNTAX     INTEGER (1..20)
           ACCESS     read-only
           STATUS     mandatory
           DESCRIPTION
                   "The index of this entry in the intruder log
                   table.  Index 1 will always contain the oldest
                   entry.  If the table is full when a new intrusion
                   occurs, the new entry becomes index 20, and all
                   earlier entries are shifted down by one entry,
                   removing the old index 1."
           ::= { hubIntruderLogEntry 1 }

       hubIntruderGroup OBJECT-TYPE
           SYNTAX     INTEGER (0..1024)
           ACCESS     read-only
           STATUS     mandatory
           DESCRIPTION
                   "This object identifies the group containing the
                   port on which this intrusion occurred."
           ::= { hubIntruderLogEntry 2 }

       hubIntruderPort  OBJECT-TYPE
           SYNTAX     INTEGER (0..1024)
           ACCESS     read-only
           STATUS     mandatory
           DESCRIPTION
                   "This object identifies the port within the group
                   on which this intrusion occurred.  A port number
                   of zero indicates that this entry is unused and
                   the values for the other variables in this entry
                   are undefined."
           ::= { hubIntruderLogEntry 3 }

       hubIntruderAddress OBJECT-TYPE
           SYNTAX     OCTET STRING (SIZE (6))
           ACCESS     read-only
           STATUS     mandatory
           DESCRIPTION
                   "This object contains the source MAC address of
                   the intruder."
           ::= { hubIntruderLogEntry 4 }

       hubIntruderTime OBJECT-TYPE
           SYNTAX     TimeTicks
           ACCESS     read-only
           STATUS     mandatory
           DESCRIPTION
                   "The value of sysUpTime when the intrusion
                   occurred.  This will be zero if the agent has been
                   reset since the intruder was detected, since
                   sysUpTime could be misinterpreted in that case."
           ::= { hubIntruderLogEntry 5 }


       --
       --  The Hub address movement log.  This table is implemented
       -- only on rev 'E' or later EtherTwist hubs and AdvanceStack
       -- 10Mbit hubs.
       --

       hubAddressMoveLogTable OBJECT-TYPE
           SYNTAX     SEQUENCE OF HubAddressMoveLogEntry
           ACCESS     not-accessible
           STATUS     mandatory
           DESCRIPTION
                   "A log of the 20 most recent times that the agent
                   detected that a source MAC address which had been
                   heard on one port had moved to a different port."
           ::= { icfHub 11 }

       hubAddressMoveLogEntry OBJECT-TYPE
           SYNTAX     HubAddressMoveLogEntry
           ACCESS     not-accessible
           STATUS     mandatory
           DESCRIPTION
                   "A row in the hubAddressMoveLogTable containing
                   information about a single address movement."
           INDEX      { hubAddrMoveIndex }
           ::= { hubAddressMoveLogTable 1 }

       HubAddressMoveLogEntry ::=
           SEQUENCE {
               hubAddrMoveIndex                INTEGER,
               hubAddrMoveAddress              OCTET STRING,
               hubAddrMoveOldGroup             INTEGER,
               hubAddrMoveOldPort              INTEGER,
               hubAddrMoveNewGroup             INTEGER,
               hubAddrMoveNewPort              INTEGER
           }

       hubAddrMoveIndex OBJECT-TYPE
           SYNTAX     INTEGER (1..20)
           ACCESS     read-only
           STATUS     mandatory
           DESCRIPTION
                   "The index of this entry in the address movement
                   log table.  Index 1 will always contain the oldest
                   entry.  If the table is full when a new address
                   movement occurs, the new entry becomes index 20,
                   and all earlier entries are shifted down by one
                   entry, removing the old index 1."
           ::= { hubAddressMoveLogEntry 1 }

       hubAddrMoveAddress OBJECT-TYPE
           SYNTAX     OCTET STRING (SIZE (6))
           ACCESS     read-only
           STATUS     mandatory
           DESCRIPTION
                   "The MAC address of the station that moved to a
                   new port."
           ::= { hubAddressMoveLogEntry 2 }

       hubAddrMoveOldGroup OBJECT-TYPE
           SYNTAX     INTEGER (0..1024)
           ACCESS     read-only
           STATUS     mandatory
           DESCRIPTION
                   "The group containing the port on which this
                   address had been operating before it moved."
           ::= { hubAddressMoveLogEntry 3 }

       hubAddrMoveOldPort OBJECT-TYPE
           SYNTAX     INTEGER (0..1024)
           ACCESS     read-only
           STATUS     mandatory
           DESCRIPTION
                   "The port within the group on which this address
                   had been operating before it moved."
           ::= { hubAddressMoveLogEntry 4 }

       hubAddrMoveNewGroup OBJECT-TYPE
           SYNTAX     INTEGER (0..1024)
           ACCESS     read-only
           STATUS     mandatory
           DESCRIPTION
                   "The group containing the port that the address
                   moved to."
           ::= { hubAddressMoveLogEntry 5 }

       hubAddrMoveNewPort OBJECT-TYPE
           SYNTAX     INTEGER (0..1024)
           ACCESS     read-only
           STATUS     mandatory
           DESCRIPTION
                   "The port within the group that the address moved
                   to."
           ::= { hubAddressMoveLogEntry 6 }

       hubLateEventMonitor OBJECT-TYPE
           SYNTAX     INTEGER {
                          off(1),
                          onSingle(2),
                          onAll(3)
                      }
           ACCESS     read-write
           STATUS     mandatory
           DESCRIPTION
                   "This object configures the late event monitoring
                   functionality for the hub.  This mode periodically
                   samples the rptrMonitorPortLateEvents value for
                   each port.  If the agent detects excessive late
                   events on a port, the port will be disabled by
                   setting the rptrPortAdminStatus for that port to
                   'disabled', and the hubPortLateEventDisable flag
                   for that port will be set to 'true'.  This mode is
                   'off' by default.  Setting it to 'onSingle'
                   enables the mode for all non-cascaded hub ports.
                   Setting it to 'onAll' enables the mode for all hub
                   ports, including cascaded ports."
           ::= { icfHub 12 }

       -- Icf Bridge Group
       -- This entire tree is deprecated.  New bridge products should
       -- use the standard bridge MIB where possible.  HP specific
       -- extensions should be defined under hpicfBridge where
       -- appropriate.

       icfBridge          OBJECT IDENTIFIER ::= { icf 3 }

       operationalState OBJECT-TYPE
           SYNTAX     INTEGER --{
                         -- learning(0),
                         -- secure(1)
                      --}
           ACCESS     read-write
           STATUS     obsolete
           DESCRIPTION
                   "This object controls the forwarding nature of the
                   bridge. In the Learning state the bridge will 
                   learn new MAC addresses, and it ages out older MAC
                   addresses. Statically configured addresses are
                   discarded (they do not age). In the Secure state,
                   the bridge will not learn new MAC addresses.
                   Statically configured addresses are forwarded
                   (they do not age)."
           ::= { icfBridge 1 }

       forwardDbMaxAge OBJECT-TYPE
           SYNTAX     TimeTicks --(1000..100000000)
           ACCESS     read-write
           STATUS     obsolete
           DESCRIPTION
                   "The value of this object controls how long a MAC
                   address stays in the forwarding database. See
                   802.1d, section 3.9.2 'Dynamic Entries'."
           ::= { icfBridge 2 }

       addressTable OBJECT-TYPE
           SYNTAX     SEQUENCE OF AddressEntry
           ACCESS     not-accessible
           STATUS     obsolete
           DESCRIPTION
                   "A list of address entries."
           --INDEX    { addressIndex }
           ::= { icfBridge 3 }

       AddressEntry ::= 
           SEQUENCE {
               addressIndex                    INTEGER,
               addressChunk                    OCTET STRING
           }

       addressIndex OBJECT-TYPE
           SYNTAX     INTEGER
           ACCESS     read-only
           STATUS     obsolete
           DESCRIPTION
                   "The index value which uniquely identifies the
                   chunk to which this entry is applicable."
           ::= { addressTable 1 }

       addressChunk OBJECT-TYPE
           SYNTAX     OCTET STRING (SIZE(410))
           ACCESS     read-write
           STATUS     obsolete
           DESCRIPTION
                   "This object returns an opaque chunk of the
                   address table.  The instance specifies a chunk of
                   the address table.  Each chunk can be interpreted
                   as an array of 41 records of the form:

                       { macAddress[6bytes], port number[2bytes], 
                         permanence[2bytes] }.

                         Address         Port          Perm
 
                   00  080009001234  1              Dynamic(0x0000)
                   01  080009002345  2              Dynamic(0x0000)
                   02  000000000000  EMPTY(0x8000)  Dynamic(0x0000)
                   03  080009003456  1              Dynamic(0x0000)
                   04  000000000000  1              Dynamic(0x0000)
                   05  080009009876  EMPTY(0x8000)  Dynamic(0x0000)
                   06  080009004567  EMPTY(0x8000)  Static(0x0008)
                   07  080009041d08    
                           ...           ...           ...
                   40  080009005678  EOL(0x4000)    Permanent(0x0000)

                   A value of EMPTY in the Port field indicates an
                   aged out table entry.  A value of EOL in the Port
                   field indicates that it is the last entry in the
                   table.  Of course, EOL will only be seen in the
                   last entry.  EOL and EMPTY are AND-able bit
                   fields.  The Disposition and Address are
                   meaningless if Port is EMPTY.

                   When instance=1 is used on a Set, the agent clears
                   the table prior to setting any addresses.  On
                   subsequent Sets, the agent adds the specified
                   addresses.  If a Set starts at instance > 1, the
                   specified addresses will be added to the table
                   without first clearing the table.  Addresses are
                   already in the table are deleted and then
                   readded."
           ::= { addressTable 2 }

       -- Bridge Port Group

       brgPortTable OBJECT-TYPE
           SYNTAX     SEQUENCE OF BrgPortEntry
           ACCESS     not-accessible
           STATUS     obsolete
           DESCRIPTION
                   "A list of brgPort entries."
           --INDEX    { brgPortIndex }
           ::= { icfBridge 4 }

       BrgPortEntry ::= 
           SEQUENCE {
               brgPortIndex                    INTEGER,
               brgPortCacheHits                Counter,
               brgPortCacheMisses              Counter,
               brgPortForwardedPkts            Counter,
               brgPortFilteredPkts             Counter
           }

       brgPortIndex OBJECT-TYPE
           SYNTAX     INTEGER
           ACCESS     read-only
           STATUS     obsolete
           DESCRIPTION
                   "The index value which uniquely identifies the
                   interface/port to which this entry is applicable.
                   The interface/port identified by a particular
                   value of this index is the same interface/port as
                   identified by the same value of ifIndex."
           ::= { brgPortTable 1 }

       brgPortCacheHits OBJECT-TYPE
           SYNTAX     Counter
           ACCESS     read-only
           STATUS     obsolete
           DESCRIPTION
                   "Count of the successful cache matches when
                   looking up a destination MAC address."
           ::= { brgPortTable 2 }

       brgPortCacheMisses OBJECT-TYPE
           SYNTAX     Counter
           ACCESS     read-only
           STATUS     obsolete
           DESCRIPTION
                   "Count of the unsuccessful cache matches when
                   looking up a destination MAC address."
           ::= { brgPortTable 3 }

       brgPortForwardedPkts OBJECT-TYPE
           SYNTAX     Counter
           ACCESS     read-only
           STATUS     obsolete
           DESCRIPTION
                   "Count of the packets received on this port and
                   forwarded to the other port."
           ::= { brgPortTable 4 }

       brgPortFilteredPkts OBJECT-TYPE
           SYNTAX     Counter
           ACCESS     read-only
           STATUS     obsolete
           DESCRIPTION
                   "Count of the frames that were received on this
                   port and filtered."
           ::= { brgPortTable 5 }

       -- Bridge Wildcard Group
       --
       -- The wildcard objects constitute a super-object. 
       -- To arm or redefine a wildcard filter, all 5 wildcard
       -- objects (i.e. Filter, Mask, Offset, UserOffset, and Arm)
       -- must be present and adjacent to each other within an SNMP
       -- PDU.  There is no requirement on the ordering of the
       -- objects within the PDU.
       -- 
       -- To disarm a wildcard filter, only the arm object is needed.
       -- When the Arm object is set to OFF, any other adjacent
       -- wildcard objects are ignored.
       --

       wildcardTable OBJECT-TYPE
           SYNTAX     SEQUENCE OF WildcardEntry
           ACCESS     not-accessible
           STATUS     obsolete
           DESCRIPTION
                   "A list of wildcard entries."
           --INDEX    { wildcardIndex }
           ::= { icfBridge 5 }

       WildcardEntry ::= 
           SEQUENCE {
               wildcardIndex                   INTEGER,
               wildcardFilter                  OCTET STRING,
               wildcardMask                    OCTET STRING,
               wildcardOffset                  INTEGER,
               wildcardUserOffset              INTEGER,
               wildcardArm                     INTEGER
           }

       wildcardIndex OBJECT-TYPE
           SYNTAX     INTEGER
           ACCESS     read-only
           STATUS     obsolete
           DESCRIPTION
                   "The index value which uniquely identifies the
                   interface/port to which this entry is applicable.
                   The interface/port identified by a particular
                   value of this index is the same interface/port as
                   identified by the same value of ifIndex."
           ::= { wildcardTable 1 }

       wildcardFilter OBJECT-TYPE
           SYNTAX     OCTET STRING (SIZE(6))
           ACCESS     read-write
           STATUS     obsolete
           DESCRIPTION
                   "This object contains the binary value used to
                   filter frames. The data in the frame at the offset
                   specified by the Wildcard offsets is XOR'ed with
                   this object after AND'ing with the Wildcard Mask.
                   If zero result occurs, the packet is discarded
                   (filtered).

                   Suppose the user specifies the following values:
                       data:   11001010 10101010 10101010 10101010
                       mask:   11100000 00000000 00000000 00000000
                       filter: 11100000 00000000 00000000 00000000

                       AND'ing data with the mask gives:
                               11000000 00000000 00000000 00000000

                       XOR'ing that value with the filter gives:
                               00100000 00000000 00000000 00000000

                       The non-zero result indicates no match (don't
                       discard).

                   Another example:
                       data:   10011010 10101010 10101010 10101010
                       mask:   10010000 00000000 00000000 00000000
                       filter: 10010000 00000000 00000000 00000000

                       AND'ing data with the mask gives:
                               10010000 00000000 00000000 00000000

                       XOR'ing that value with the filter gives:
                               00000000 00000000 00000000 00000000

                       A zero result indicates a match, so we discard
                       (filter) the packet.

                   The filter AND'ed with the mask must equal the
                   filter. This is an example of a legal filter/mask
                   pair:
                       filter: 00010000 00000000 00000000 00000000
                       mask:   10010000 00000000 00000000 00000000
                       AND'ed: 00010000 00000000 00000000 00000000
                               (equals filter)

                   Another way of saying this: if a mask bit is zero,
                   the corresponding filter bit must be zero.

                   The following would be an illegal pair:
                       filter: 01110000 00000000 00000000 00000000
                       mask:   10010000 00000000 00000000 00000000
                       AND'ed: 00010000 00000000 00000000 00000000  
                               ( != filter)"
           ::= { wildcardTable 2 }

       wildcardMask OBJECT-TYPE
           SYNTAX     OCTET STRING (SIZE(6))
           ACCESS     read-write
           STATUS     obsolete
           DESCRIPTION
                   "This object indicates which portion of the
                   wildcardFilter is to be used in filtering. The
                   data in the frame at the offset specified by
                   Wildcard offsets is AND'ed with this object.  The
                   result is XOR'ed with the Wildcard Filter object.
                   If a zero result is obtained, the packet is
                   discarded.

                   If an all-zeros wildcardMask is specified, a
                   genErr is returned.  Also, see mask/filter
                   constraints in the description of the
                   wildcardFilter object."
           ::= { wildcardTable 3 }

       wildcardOffset OBJECT-TYPE
           SYNTAX     INTEGER
           ACCESS     read-write
           STATUS     obsolete
           DESCRIPTION
                   "Indicates the position in a received frame which
                   is to have the Wildcard Mask/Filter applied. The
                   indicated packet byte is aligned with the 0th byte
                   of the wildcard mask/filter held in network byte
                   order.

                   The MAC destination address starts at byte
                   position (wildcardOffset) zero.

                   The wildcardOffset must fall on a 2-byte boundary,
                   0,2,4,...,1512 (violations of this constraint
                   result in a genErr).  Filters can be aligned on
                   non 2-byte boundaries through use of the
                   wildcardUserOffset."
           ::= { wildcardTable 4 }

       wildcardUserOffset OBJECT-TYPE
           SYNTAX     INTEGER
           ACCESS     read-write
           STATUS     obsolete
           DESCRIPTION
                   "This value is a byte offset from the beginning
                   of the packet. If this offset is such that any
                   portion of the filter extends past the end of the
                   packet (for wildcard filtering purposes, the FCS
                   is part of the packet), then the filter is
                   considered not to match, and the packet is not
                   filtered.

                   For a particular filter, the wildcardUserOffset
                   must be greater than or equal to the
                   wildcardOffset.

                   wildcardUserOffset must be between 0 and 1514,
                   inclusive.

                   The wildcardUserOffset, wildcardOffset pair must
                   conform to one of the following four relationships
                   and also be subject to the range restrictions
                   listed above. For n = 0,..,378

                        Offset         4n   4n      4n      4n+2
                        UserOffset     4n   4n+1    4n+2    4n+3

                   As an example, consider four examples in the
                   following table for locating the filter at or near
                   the beginning of a packet:

                           - 6 filter/mask bytes -      - desired  -
                       0    1    2    3    4    5    6  - position -
                   A|f/m0 f/m1 f/m2 f/m3  00   00   00 |0,4,8,12,...
                   B| 00  f/m0 f/m1 f/m2 f/m3  00   00 |1,5,9,13,...
                   C| 00   00  f/m0 f/m1 f/m2 f/m3  00 |2,6,10,14,...
                   D| 00   00   00  f/m0 f/m1 f/m2 f/m3|3,7,11,15,...

                   Example A corresponds to a UserOffset/Offset pair
                   such as 0/0 (4n/4n).  Example B represents a pair
                   such as 0/1 (4n/4n+1).  Example C is 0/2 
                   (4n/4n+2). Finally, example D is 2/3 (4n+2/4n+3).

                   If any of the above constraints is not honored,
                   the SET Response will indicate genErr."
           ::= { wildcardTable 5 }

       wildcardArm OBJECT-TYPE
           SYNTAX     INTEGER --{
                          -- off(0),
                          -- on(1)
                       --}
           ACCESS     read-write
           STATUS     obsolete
           DESCRIPTION
                   "This object arms (enables) the Wildcard Filter
                   provided all of the other wildcard objects have
                   been set to proper values. To disarm a wildcard,
                   only the wildcardArm object need be set."
           ::= { wildcardTable 6 }

       -- Bridge Spanning Tree Group

       stp                OBJECT IDENTIFIER ::= { icfBridge 6 }

       stpBridgeId OBJECT-TYPE
           SYNTAX     OCTET STRING (SIZE(8))
           ACCESS     read-only
           STATUS     obsolete
           DESCRIPTION
                   "A 64 bit binary bridge id composed of bridge
                   priority and the bridge's mac address fields. see:
                   IEEE 802.1(d) 6.8.1.1.3(1), 4.5.3.7"
           ::= { stp 1 }

       stpTopoChangeTime OBJECT-TYPE
           SYNTAX     TimeTicks
           ACCESS     read-only
           STATUS     obsolete
           DESCRIPTION
                   "The time since the last topology change. see: 
                   IEEE 802.1(d) 6.8.1.1.3(2), 4.5.3.12"
           ::= { stp 2 }

       stpTopoNumChanges OBJECT-TYPE
           SYNTAX     Counter
           ACCESS     read-only
           STATUS     obsolete
           DESCRIPTION
                   "The number of topo changes since initialization
                   of STP. see: IEEE 802.1(d) 6.8.1.1.3(3)"
           ::= { stp 3 }

       stpTopoChange OBJECT-TYPE
           SYNTAX     INTEGER --{
                          -- false(0),
                          -- true(1)
                       --}
           ACCESS     read-only
           STATUS     obsolete
           DESCRIPTION
                   "A 1 bit flag broadcast by the root bridge
                   indicating that a topology change is underway, and
                   Stp bridges should use short term aging. see: IEEE
                   802.1(d) 6.8.1.1.3(4), 4.5.3.12"
           ::= { stp 4 }

       stpDesignatedRoot OBJECT-TYPE
           SYNTAX     OCTET STRING (SIZE(8))
           ACCESS     read-only
           STATUS     obsolete
           DESCRIPTION
                   "The binary bridge id that this bridge believes to
                   be the root bridge for the bridged Lan. see: IEEE
                   802.1(d) 6.8.1.1.3(5), 4.5.3.1"
           ::= { stp 5 }

       stpRootCost OBJECT-TYPE
           SYNTAX     INTEGER (0..4294967295)
           ACCESS     read-only
           STATUS     obsolete
           DESCRIPTION
                   "The cost of the path to the root bridge from this
                   bridge; equal to the sum of the designated cost
                   and the path cost held for the root port. see:
                   IEEE 802.1(d) 6.8.1.1.3(6), 4.5.3.2"
           ::= { stp 6 }

       stpRootPort OBJECT-TYPE
           SYNTAX     INTEGER (1..65535)
           ACCESS     read-only
           STATUS     obsolete
           DESCRIPTION
                   "The port id that this bridge believes to be the
                   root bridge's root port for the bridged Lan. see:
                   IEEE 802.1(d) 6.8.1.1.3(7), 4.5.3.3"
           ::= { stp 7 }

       stpCurrentMaxAge OBJECT-TYPE
           SYNTAX     INTEGER (6..40)
           ACCESS     read-only
           STATUS     obsolete
           DESCRIPTION
                   "The Max Age value received from the Root Bridge
                   (in seconds); the Stp is currently using the
                   value. see: IEEE 802.1(d) 6.8.1.1.3(8), 4.5.3.4"
           ::= { stp 8 }

       stpCurrentHelloTime OBJECT-TYPE
           SYNTAX     INTEGER (1..10)
           ACCESS     read-only
           STATUS     obsolete
           DESCRIPTION
                   "The Hello time value received from the Root
                   Bridge (in seconds); the Stp records the value.
                   see: IEEE 802.1(d) 6.8.1.1.3(9), 4.5.3.5"
           ::= { stp 9 }

       stpCurrentForwardDelay OBJECT-TYPE
           SYNTAX     INTEGER (4..10)
           ACCESS     read-only
           STATUS     obsolete
           DESCRIPTION
                   "The forward delay value received from the Root
                   Bridge (in seconds); the Stp is currently using
                   the value. see: IEEE 802.1(d) 6.8.1.1.3(10),
                   4.5.3.6"
           ::= { stp 10 }

       stpMaxAge OBJECT-TYPE
           SYNTAX     INTEGER (6..40)
           ACCESS     read-write
           STATUS     obsolete
           DESCRIPTION
                   "The maximum age allowed of Config information for
                   a port before a bridge will attempt to become the
                   root (in seconds). Transmitted by this bridge when
                   it is, or is attempting to become the root.  see:
                   IEEE 802.1(d) 6.8.1.1.3(11), 6.8.1.2.2(1),
                   4.5.3.8"
           ::= { stp 11 }

       stpHelloTime OBJECT-TYPE
           SYNTAX     INTEGER (1..10)
           ACCESS     read-write
           STATUS     obsolete
           DESCRIPTION
                   "The time between Config packet transmission when
                   this bridge is, or is attempting to become the
                   root (in seconds). Transmitted by this bridge when
                   it is, or is attempting to become the root. see:
                   IEEE 802.1(d) 6.8.1.1.3(12), 6.8.1.2.2(2),
                   4.5.3.9"
           ::= { stp 12 }

       stpForwardDelay OBJECT-TYPE
           SYNTAX     INTEGER (4..30)
           ACCESS     read-write
           STATUS     obsolete
           DESCRIPTION
                   "The time spent in the Listening and Learning
                   states used when this bridge is, or is attempting
                   to become the root (in seconds).  Transmitted by
                   this bridge when it is, or is attempting to become
                   the root. see: IEEE 802.1(d) 6.8.1.1.3(13),
                   6.8.1.2.2(3), 4.5.3.10"
           ::= { stp 13 }

       stpPriority OBJECT-TYPE
           SYNTAX     INTEGER
           ACCESS     read-write
           STATUS     obsolete
           DESCRIPTION
                   "The upper 16 bits of the 64 bit BridgeId composed
                   of priority and the bridge's mac address fields.
                   see: IEEE 802.1(d) 6.8.1.2.2(4), 4.5.3.7"
           ::= { stp 14 }

       -- Bridge Spanning Tree Port Group

       stpPortTable OBJECT-TYPE
           SYNTAX     SEQUENCE OF StpPortEntry
           ACCESS     not-accessible
           STATUS     obsolete
           DESCRIPTION
                   "A list of stpPort entries."
           --INDEX   { stpPortIndex }
           ::= { stp 15 }

       StpPortEntry ::= 
           SEQUENCE {
               stpPortIndex                    INTEGER,
               stpPortState                    INTEGER,
               stpPortId                       INTEGER,
               stpPortPathCost                 INTEGER,
               stpPortRootId                   OCTET STRING,
               stpPortDesignatedCost           INTEGER,
               stpPortDesignatedBridge         OCTET STRING,
               stpPortDesignatedPort           INTEGER,
               stpPortPriority                 INTEGER
           }

       stpPortIndex OBJECT-TYPE
           SYNTAX     INTEGER
           ACCESS     read-only
           STATUS     obsolete
           DESCRIPTION
                   "The index value which uniquely identifies the
                   port to which this entry is applicable. The port
                   identified by a particular value of this index is
                   the same interface/port as identified by the same
                   value of ifIndex. Not an IEEE 802.1(d) reqmt."
           ::= { stpPortTable 1 }

       stpPortState OBJECT-TYPE
           SYNTAX     INTEGER --{
                          -- stpDisabled(0),    - settable
                          -- stpListening(1),
                          -- stpLearning(2),
                          -- stpForwarding(3),
                          -- stpBlocking(4)     - settable
                       --}
           ACCESS     read-write
           STATUS     obsolete
           DESCRIPTION
                   "The state of a port on a 2 port bridge is really
                   the state of the bridge itself. Management is only
                   allowed to set this object to 'stpDisabled' or
                   'stpBlocking'. Setting the object to 'stpDisabled'
                   will turn off spanning tree only if the state is
                   not 'stpBlocking' (to prevent loops). Setting the
                   object to 'stpBlocking' will turn on spanning tree
                   only if it was previously disabled. see: IEEE
                   802.1(d) 6.8.2.1.3(2), 4.4, 4.5.5.2"
           ::= { stpPortTable 2 }

       stpPortId OBJECT-TYPE
           SYNTAX     INTEGER
           ACCESS     read-only
           STATUS     obsolete
           DESCRIPTION
                   "The 16 bit port id composed of priority and the
                   port's unique id fields. see: IEEE 802.1(d)
                   6.8.2.1.3(3), 4.5.5.1"
           ::= { stpPortTable 3 }

       stpPortPathCost OBJECT-TYPE
           SYNTAX     INTEGER (1..65535)
           ACCESS     read-write
           STATUS     obsolete
           DESCRIPTION
                   "The contribution of the path through this port,
                   when the port is the root port, to the total cost
                   of the path to the root for this bridge. see: IEEE
                   802.1(d) 6.8.2.1.3(4), 6.8.2.3.2(2), 4.5.5.3"
           ::= { stpPortTable 4 }

       stpPortRootId OBJECT-TYPE
           SYNTAX     OCTET STRING (SIZE(6))
           ACCESS     read-only
           STATUS     obsolete
           DESCRIPTION
                   "The bridge id that this port believes to be the
                   root bridge for the bridged Lan. see: IEEE
                   802.1(d) 6.8.2.1.3(5), 4.5.5.4"
           ::= { stpPortTable 5 }

       stpPortDesignatedCost OBJECT-TYPE
           SYNTAX     INTEGER (0..65535)
           ACCESS     read-only
           STATUS     obsolete
           DESCRIPTION
                   "The cost of the path to the root offered by the
                   Designated Port on the LAN to which this Port is
                   attached. see: IEEE 802.1(d) 6.8.2.1.3(6),
                   4.5.5.5"
           ::= { stpPortTable 6 }

       stpPortDesignatedBridge OBJECT-TYPE
           SYNTAX     OCTET STRING (SIZE(6))
           ACCESS     read-only
           STATUS     obsolete
           DESCRIPTION
                   "The Bridge Id of the designated bridge for the
                   LAN associated with the port. see: IEEE 802.1(d)
                   6.8.2.1.3(7), 4.5.5.6"
           ::= { stpPortTable 7 }

       stpPortDesignatedPort OBJECT-TYPE
           SYNTAX     INTEGER (1..65535)
           ACCESS     read-only
           STATUS     obsolete
           DESCRIPTION
                   "The port id of the bridge believed to be the
                   designated port of the LAN associated with the
                   port. see: IEEE 802.1(d) 6.8.2.1.3(8), 4.5.5.7"
           ::= { stpPortTable 8 }

       stpPortPriority OBJECT-TYPE
           SYNTAX     INTEGER (0..255)
           ACCESS     read-write
           STATUS     obsolete
           DESCRIPTION
                   "The upper 8 bits of the 16 bit PortId composed of
                   priority and the port's unique id fields. see:
                   IEEE 802.1(d) 6.8.2.3.2(3), 4.5.5.1"
           ::= { stpPortTable 9 }

       -- Icf HDLC Error Group

       hdlcErrorTable OBJECT-TYPE
           SYNTAX     SEQUENCE OF HdlcErrorEntry
           ACCESS     not-accessible
           STATUS     obsolete
           DESCRIPTION
                   "A list of hdlcError entries."
           --INDEX    { hdlcErrorIndex }
           ::= { icfBridge 7 }

       HdlcErrorEntry ::= 
           SEQUENCE {
               hdlcErrorIndex                  INTEGER,
               hdlcErrorIndications            Counter,
               hdlcT1Timeouts                  Counter,
               hdlcMissedPackets               Counter,
               hdlcRcvOverruns                 Counter,
               hdlcXmtUnderruns                Counter,
               hdlcProviderLostPrimitives      Counter,
               hdlcRuntFrameReceives           Counter,
               hdlcGiantFrameReceives          Counter,
               hdlcBadFrameReceives            Counter,
               hdlcRejectFrameReceives         Counter,
               hdlcRejectFrameSends            Counter,
               hdlcFrameRejectFrameRecs        Counter
           }

       hdlcErrorIndex OBJECT-TYPE
           SYNTAX     INTEGER
           ACCESS     read-only
           STATUS     obsolete
           DESCRIPTION
                   "The index value which uniquely identifies the
                   port to which this entry is applicable. The port
                   identified by a particular value of this index is
                   the same interface/port as identified by the same
                   value of ifIndex. IcfBridge.HP28674: There is only
                   one 'real' instance of this object on port 2."
           ::= { hdlcErrorTable 1 }

       hdlcErrorIndications OBJECT-TYPE
           SYNTAX     Counter
           ACCESS     read-only
           STATUS     obsolete
           DESCRIPTION
                   "Errors occurring during information transfer
                   which required instruction from CPU for recovery.
                   This is a serious link problem. The local node
                   will either reset or disconnect after receiving
                   this message."
           ::= { hdlcErrorTable 2 }

       hdlcT1Timeouts OBJECT-TYPE
           SYNTAX     Counter
           ACCESS     read-only
           STATUS     obsolete
           DESCRIPTION
                   "The number of times the retransmission timer
                   (x25T1Timer) timed out."
           ::= { hdlcErrorTable 3 }

       hdlcMissedPackets OBJECT-TYPE
           SYNTAX     Counter
           ACCESS     read-only
           STATUS     obsolete
           DESCRIPTION
                   "Count of the frames lost by the receiver because
                   there wasn't a receive buffer."
           ::= { hdlcErrorTable 4 }

       hdlcRcvOverruns OBJECT-TYPE
           SYNTAX     Counter
           ACCESS     read-only
           STATUS     obsolete
           DESCRIPTION
                   "Count of the number of times the reciever's FIFO
                   was full when the receiver was ready to put new
                   data into the FIFO."
           ::= { hdlcErrorTable 5 }

       hdlcXmtUnderruns OBJECT-TYPE
           SYNTAX     Counter
           ACCESS     read-only
           STATUS     obsolete
           DESCRIPTION
                   "Count of the number of times the transmitter has
                   aborted a frame transmission because data was
                   late from memory."
           ::= { hdlcErrorTable 6 }

       hdlcProviderLostPrimitives OBJECT-TYPE
           SYNTAX     Counter
           ACCESS     read-only
           STATUS     obsolete
           DESCRIPTION
                   "Count of the number of lost control frames due to
                   802.3 priority processing on receive."
           ::= { hdlcErrorTable 7 }

       hdlcRuntFrameReceives OBJECT-TYPE
           SYNTAX     Counter
           ACCESS     read-only
           STATUS     obsolete
           DESCRIPTION
                   "Count of the HDLC frames received that were less
                   than the minimum legal HDLC size."
           ::= { hdlcErrorTable 8 }

       hdlcGiantFrameReceives OBJECT-TYPE
           SYNTAX     Counter
           ACCESS     read-only
           STATUS     obsolete
           DESCRIPTION
                   "Count of the HDLC frames received that were
                   larger than the maximum legal size that can be
                   sent on the 802.3 LAN link."
           ::= { hdlcErrorTable 9 }

       hdlcBadFrameReceives OBJECT-TYPE
           SYNTAX     Counter
           ACCESS     read-only
           STATUS     obsolete
           DESCRIPTION
                   "Count of the sum of: HDLC frames with bad
                   checksum, and misaligned HDLC frames."
           ::= { hdlcErrorTable 10 }

       hdlcRejectFrameReceives OBJECT-TYPE
           SYNTAX     Counter
           ACCESS     read-only
           STATUS     obsolete
           DESCRIPTION
                   "Count of the HDLC reject frames received."
           ::= { hdlcErrorTable 11 }

       hdlcRejectFrameSends OBJECT-TYPE
           SYNTAX     Counter
           ACCESS     read-only
           STATUS     obsolete
           DESCRIPTION
                   "Count of the HDLC reject frames sent."
           ::= { hdlcErrorTable 12 }

       hdlcFrameRejectFrameRecs OBJECT-TYPE
           SYNTAX     Counter
           ACCESS     read-only
           STATUS     obsolete
           DESCRIPTION
                   "Count of the HDLC frame reject frames (FRMR)
                   received."
           ::= { hdlcErrorTable 13 }

       -- Icf HDLC Local Group

       hdlcLocalTable OBJECT-TYPE
           SYNTAX     SEQUENCE OF HdlcLocalEntry
           ACCESS     not-accessible
           STATUS     obsolete
           DESCRIPTION
                   "A list of hdlcLocal entries."
           --INDEX    { hdlcLocalIndex }
           ::= { icfBridge 8 }

       HdlcLocalEntry ::= 
           SEQUENCE {
               hdlcLocalIndex                  INTEGER,
               hdlcLocalResetRequests          Counter,
               hdlcLocalResetConfirms          Counter,
               hdlcLocalConnectRequests        Counter,
               hdlcLocalConnectConfirms        Counter,
               hdlcLocalDisconnectRequests     Counter,
               hdlcLocalDisconnectConfirms     Counter,
               hdlcLocalState                  INTEGER,
               hdlcLocalAddress                INTEGER,
               hdlcLocalPhase                  INTEGER
           }

       hdlcLocalIndex OBJECT-TYPE
           SYNTAX     INTEGER
           ACCESS     read-only
           STATUS     obsolete
           DESCRIPTION
                   "Index into Hdlc local statistics table on a per
                   port basis.  bridge.HP28674: There is only one
                   'real' instance of this object on port 2."
           ::= { hdlcLocalTable 1 }

       hdlcLocalResetRequests OBJECT-TYPE
           SYNTAX     Counter
           ACCESS     read-only
           STATUS     obsolete
           DESCRIPTION
                   "Count of local HDLC requests to reset current
                   logical link."
           ::= { hdlcLocalTable 2 }

       hdlcLocalResetConfirms OBJECT-TYPE
           SYNTAX     Counter
           ACCESS     read-only
           STATUS     obsolete
           DESCRIPTION
                   "Count of local HDLC node link reset
                   confirmations."
           ::= { hdlcLocalTable 3 }

       hdlcLocalConnectRequests OBJECT-TYPE
           SYNTAX     Counter
           ACCESS     read-only
           STATUS     obsolete
           DESCRIPTION
                   "Count of local HDLC node attempts to establish
                   logical link."
           ::= { hdlcLocalTable 4 }

       hdlcLocalConnectConfirms OBJECT-TYPE
           SYNTAX     Counter
           ACCESS     read-only
           STATUS     obsolete
           DESCRIPTION
                   "Count of local HDLC node connect request
                   acceptances."
           ::= { hdlcLocalTable 5 }

       hdlcLocalDisconnectRequests OBJECT-TYPE
           SYNTAX     Counter
           ACCESS     read-only
           STATUS     obsolete
           DESCRIPTION
                   "Count of local HDLC node disconnect requests."
           ::= { hdlcLocalTable 6 }

       hdlcLocalDisconnectConfirms OBJECT-TYPE
           SYNTAX     Counter
           ACCESS     read-only
           STATUS     obsolete
           DESCRIPTION
                   "Count of local HDLC node disconnects granted."
           ::= { hdlcLocalTable 7 }

       hdlcLocalState OBJECT-TYPE
           SYNTAX     INTEGER --{
                          -- t1HdlcStateNormal(0),
                          -- t1HdlcStateBusy(1),
                          -- t1HdlcStateRejectSent(2),
                          -- t1HdlcStateDiscSent(3),
                          -- t1HdlcStateDisconnect(4),
                          -- t1HdlcStateConnSent(5),
                          -- t1HdlcStateFrameRejectSent(6),
                          -- t1HdlcStateResetSent(7),
                          -- t1HdlcStateErrorIndication(8)
                       --}
           ACCESS     read-only
           STATUS     obsolete
           DESCRIPTION
                   "Current local HDLC operational state."
           ::= { hdlcLocalTable 8 }

       hdlcLocalAddress OBJECT-TYPE
           SYNTAX     INTEGER {
                          hdlcDTEAddress(1),
                          hdlcDCEAddress(3)
                      }
           ACCESS     read-write
           STATUS     obsolete
           DESCRIPTION
                   "The local HDLC address during communication with
                   the remote node.  This object is valid only if a
                   brouter is on the remote end of the HDLC link. It
                   can only be set to one of the two values:
                   'hdlcDTEAddress' or 'hdlcDTEAddress'. Furthermore,
                   the setting of this object must be different from
                   the setting of the hdlcRemoteHdlcAddress object.
                   This object, along with hdlcRemoteAddress and
                   hdlcRemoteNodeId, constitute a superobject.  See
                   hdlcRemoteNodeId for more details."
           ::= { hdlcLocalTable 9 }

       hdlcLocalPhase OBJECT-TYPE
           SYNTAX     INTEGER --{
                          -- t1PhaseStopped(-1),
                          -- t1PhaseInfo(0),
                          -- t1PhaseDisconnect(1),
                          -- t1PhaseReset(2),
                          -- t1PhaseTransparentData(3)
                      --}
           ACCESS     read-only
           STATUS     obsolete
           DESCRIPTION
                   "Current HDLC operational phase."
           ::= { hdlcLocalTable 10 }

       -- Icf HDLC Remote Group

       hdlcRemoteTable OBJECT-TYPE
           SYNTAX     SEQUENCE OF HdlcRemoteEntry
           ACCESS     not-accessible
           STATUS     obsolete
           DESCRIPTION
                   "A list of hdlcRemote entries."
           --INDEX    { hdlcRemoteIndex }
           ::= { icfBridge 9 }

       HdlcRemoteEntry ::= 
           SEQUENCE {
               hdlcRemoteIndex                 INTEGER,
               hdlcRemoteResetRequests         Counter,
               hdlcRemoteResetConfirms         Counter,
               hdlcRemoteConnectRequests       Counter,
               hdlcRemoteConnectConfirms       Counter,
               hdlcRemoteDisconnectRequests    Counter,
               hdlcRemoteState                 INTEGER,
               hdlcRemoteAddress               INTEGER,
               hdlcRemoteXidCommands           Counter,
               hdlcRemoteXidResponses          Counter,
               hdlcRemoteTestCommands          Counter,
               hdlcRemoteTestResponses         Counter,
               hdlcRemoteNodeId                INTEGER
           }

       hdlcRemoteIndex OBJECT-TYPE
           SYNTAX     INTEGER
           ACCESS     read-only
           STATUS     obsolete
           DESCRIPTION
                   "Index into Hdlc remote statistics table on a per
                   port basis.  bridge.HP28674: There is only one
                   'real' instance of this object on port 2."
           ::= { hdlcRemoteTable 1 }

       hdlcRemoteResetRequests OBJECT-TYPE
           SYNTAX     Counter
           ACCESS     read-only
           STATUS     obsolete
           DESCRIPTION
                   "Count of remote HDLC requests to reset current
                   logical link."
           ::= { hdlcRemoteTable 2 }

       hdlcRemoteResetConfirms OBJECT-TYPE
           SYNTAX     Counter
           ACCESS     read-only
           STATUS     obsolete
           DESCRIPTION
                   "Count of remote HDLC node link reset
                   confirmations."
           ::= { hdlcRemoteTable 3 }

       hdlcRemoteConnectRequests OBJECT-TYPE
           SYNTAX     Counter
           ACCESS     read-only
           STATUS     obsolete
           DESCRIPTION
                   "Count of remote HDLC node attempts to establish
                   logical link."
           ::= { hdlcRemoteTable 4 }

       hdlcRemoteConnectConfirms OBJECT-TYPE
           SYNTAX     Counter
           ACCESS     read-only
           STATUS     obsolete
           DESCRIPTION
                   "Count of remote HDLC node connect request
                   acceptances."
           ::= { hdlcRemoteTable 5 }

       hdlcRemoteDisconnectRequests OBJECT-TYPE
           SYNTAX     Counter
           ACCESS     read-only
           STATUS     obsolete
           DESCRIPTION
                   "Count of remote HDLC node disconnect requests."
           ::= { hdlcRemoteTable 6 }

       hdlcRemoteState OBJECT-TYPE
           SYNTAX     INTEGER --{
                          -- t1HdlcStateNormal(0),
                          -- t1HdlcStateBusy(1),
                          -- t1HdlcStateRejectSent(2),
                          -- t1HdlcStateDiscSent(3),
                          -- t1HdlcStateDisconnect(4),
                          -- t1HdlcStateConnSent(5),
                          -- t1HdlcStateFrameRejectSent(6),
                          -- t1HdlcStateResetSent(7),
                          -- t1HdlcStateErrorIndication(8)
                      --}
           ACCESS     read-only
           STATUS     obsolete
           DESCRIPTION
                   "Current remote HDLC operational state."
           ::= { hdlcRemoteTable 7 }

       hdlcRemoteAddress OBJECT-TYPE
           SYNTAX     INTEGER {
                          hdlcDTEAddress(1),
                          hdlcDCEAddress(3)
                      }
           ACCESS     read-write
           STATUS     obsolete
           DESCRIPTION
                   "The remote HDLC address during communication with
                   the local node.  This object is valid only if a
                   brouter is on the remote end of the HDLC link. It
                   can only be set to one of the two values:
                   'hdlcDCEAddress' or 'hdlcDTEAddress'. Furthermore,
                   the setting of this object must be different from
                   the setting of the hdlcLocalAddress object. This
                   object, along with hdlcLocalAddress and
                   hdlcRemoteNodeId, constitute a superobject.  See
                   hdlcRemoteNodeId for more details."
           ::= { hdlcRemoteTable 8 }

       hdlcRemoteXidCommands OBJECT-TYPE
           SYNTAX     Counter
           ACCESS     read-only
           STATUS     obsolete
           DESCRIPTION
                   "Count of XID commands issued by remote node."
           ::= { hdlcRemoteTable 9 }

       hdlcRemoteXidResponses OBJECT-TYPE
           SYNTAX     Counter
           ACCESS     read-only
           STATUS     obsolete
           DESCRIPTION
                   "Count of XID responses issued by remote node."
           ::= { hdlcRemoteTable 10 }

       hdlcRemoteTestCommands OBJECT-TYPE
           SYNTAX     Counter
           ACCESS     read-only
           STATUS     obsolete
           DESCRIPTION
                   "Count of Test commands issued by remote node."
           ::= { hdlcRemoteTable 11 }

       hdlcRemoteTestResponses OBJECT-TYPE
           SYNTAX     Counter
           ACCESS     read-only
           STATUS     obsolete
           DESCRIPTION
                   "Count of Test responses issued by remote node."
           ::= { hdlcRemoteTable 12 }

       hdlcRemoteNodeId OBJECT-TYPE
           SYNTAX     INTEGER --{
                          -- remoteNodeBridge(0),
                          -- remoteNodeRouter(1),   - Settable
                          -- remoteNodeUnknown(2)   - Settable
                      --}
           ACCESS     read-write
           STATUS     obsolete
           DESCRIPTION
                   "Identification of the node at the opposite end of
                   the HDLC link (eg. brouter or bridge).  This
                   object, along with hdlcLocalAddress and
                   hdlcRemoteAddress, constitute a superobject. This
                   object may only be set to one of the two values:
                   'remoteNodeBridge' or 'remoteNodeRouter'.  If this
                   object is set to 'remoteNodeUnknown', then
                   hdlcLocalAddress and hdlcRemoteAddress need not be
                   supplied, and will be ignored if provided. In a
                   get, this object may report 'remoteNodeBridge',
                   but attempts to set this object to
                   'remoteNodeBridge' will result in an error pdu
                   with error type invalidData. If this object is set
                   to 'remoteNodeRouter', then hdlcLocalAddress and
                   hdlcRemoteAddress must be present and contiguous
                   in the pdu in order to properly complete the
                   superobject. The three objects may be in any order
                   within the pdu."
           ::= { hdlcRemoteTable 13 }

       -- Icf X25 Group

       x25Table OBJECT-TYPE
           SYNTAX     SEQUENCE OF X25Entry
           ACCESS     not-accessible
           STATUS     obsolete
           DESCRIPTION
                   "A list of X25 entries."
           --INDEX    { x25Index }
           ::= { icfBridge 10 }

       X25Entry ::= 
           SEQUENCE {
               x25Index                        INTEGER,
               x25T1Timer                      TimeTicks,
               x25N2Count                      INTEGER,
               x25T3Timer                      TimeTicks
           }

       x25Index OBJECT-TYPE
           SYNTAX     INTEGER
           ACCESS     read-only
           STATUS     obsolete
           DESCRIPTION
                   "Index into X25 remote timer table on a per port
                   basis.  bridge.HP28674: There is only one 'real'
                   instance of this object on port 2."
           ::= { x25Table 1 }

       x25T1Timer OBJECT-TYPE
           SYNTAX     TimeTicks --(300..2000)
           ACCESS     read-write
           STATUS     obsolete
           DESCRIPTION
                   "Period of time used to timeout retransmits for
                   X25."
           ::= { x25Table 2 }

       x25N2Count OBJECT-TYPE
           SYNTAX     INTEGER (4..30)
           ACCESS     read-write
           STATUS     obsolete
           DESCRIPTION
                   "Number of retries to be performed during X.25
                   communication."
           ::= { x25Table 3 }

       x25T3Timer OBJECT-TYPE
           SYNTAX     TimeTicks --(1000..3000)
           ACCESS     read-write
           STATUS     obsolete
           DESCRIPTION
                   "Period of idle time before a disconnect is
                   executed for X25."
           ::= { x25Table 4 }


       -- ICF Security group.  This group is only implemented on 
       -- EtherTwist hubs with rev 'E' or later firmware and on
       -- AdvanceStack hubs.

       icfSecurity        OBJECT IDENTIFIER ::= { icf 4 }

       icfSecurPassword OBJECT-TYPE
           SYNTAX     DisplayString (SIZE (0..63))
           ACCESS     read-write
           STATUS     mandatory
           DESCRIPTION
                   "This variable contains a string which is used
                   both as the community name for the password
                   community, and as the login password for the
                   console port.  This community name is needed for
                   most SET operations.  In addition, the variables
                   in the ICF security group are only visible within
                   the password community, and must use the value of
                   this variable as the community name for GET
                   operations.  If the value of this variable is
                   equal to the null string, the community name
                   'public' or the null string will be treated the
                   same as the password community."
           ::= { icfSecurity 1 }

       icfSecurAuthAnyMgr OBJECT-TYPE
           SYNTAX     INTEGER {
                          enabled(1),
                          disabled(2)
                      }
           ACCESS     read-write
           STATUS     mandatory
           DESCRIPTION
                   "When this variable is set to enabled, any manager
                   with a valid community name may perform SET
                   operations on this device.  In this configuration,
                   entries in the icfSecurAuthMgrTable are used only
                   for trap destinations.  If this variable is set to
                   disabled, a manager must be in the
                   icfSecurAuthMgrTable and have a valid community
                   name in order to perform SET operations."
           ::= { icfSecurity 2 }

       icfSecurAuthMgrTable OBJECT-TYPE
           SYNTAX     SEQUENCE OF IcfSecurAuthMgrEntry
           ACCESS     not-accessible
           STATUS     mandatory
           DESCRIPTION
                   "This table contains a list of addresses of
                   managers that are allowed to perform SET
                   operations on this device, and controls the
                   destination addresses for traps.  If
                   icfSecurAuthAnyMgr is set to disabled, a manager
                   must be in this table and use the correct
                   community name for the password community in order
                   to perform a GET operation on this table."
           ::= { icfSecurity 3 }

       icfSecurAuthMgrEntry OBJECT-TYPE
           SYNTAX     IcfSecurAuthMgrEntry
           ACCESS     not-accessible
           STATUS     mandatory
           DESCRIPTION
                   "An entry in the icfSecurAuthMgrTable containing
                   information about a single manager."
           INDEX      { icfAuthMgrIndex }
           ::= { icfSecurAuthMgrTable 1 }

       IcfSecurAuthMgrEntry ::=
           SEQUENCE {
               icfAuthMgrIndex                 INTEGER,
               icfAuthMgrIpAddress             IpAddress,
               icfAuthMgrIpxAddress            OCTET STRING,
               icfAuthMgrRcvTraps              INTEGER
           }

       icfAuthMgrIndex OBJECT-TYPE
           SYNTAX     INTEGER (1..10)
           ACCESS     read-only
           STATUS     mandatory
           DESCRIPTION
                   "This object contains the index which uniquely
                   identifies this entry in the
                   icfSecurAuthMgrTable."
           ::= { icfSecurAuthMgrEntry 1 }

       icfAuthMgrIpAddress OBJECT-TYPE
           SYNTAX     IpAddress
           ACCESS     read-write
           STATUS     mandatory
           DESCRIPTION
                   "The IP address of a manager that is allowed to
                   manage this device.  Setting this variable to a
                   nonzero value will clear the corresponding
                   instance of the icfAuthMgrIpxAddress variable."
           ::= { icfSecurAuthMgrEntry 2 }

       icfAuthMgrIpxAddress OBJECT-TYPE
           SYNTAX     OCTET STRING (SIZE (10))
           ACCESS     read-write
           STATUS     mandatory
           DESCRIPTION
                   "The IPX address of a manager that is allowed to
                   manage this device.  Setting this variable to a
                   valid IPX address will clear the corresponding
                   instance of the icfAuthMgrIpAddress variable."
           ::= { icfSecurAuthMgrEntry 3 }

       icfAuthMgrRcvTraps OBJECT-TYPE
           SYNTAX       INTEGER {
                            enabled(1),
                            disabled(2)
                        }
           ACCESS       read-write
           STATUS       mandatory
           DESCRIPTION
                   "If this variable is set to enabled, any traps
                   generated by this device will be sent to the
                   manager indicated by the corresponding instance of
                   either icfAuthMgrIpAddress or
                   icfAuthMgrIpxAddress, whichever is valid."
           ::= { icfSecurAuthMgrEntry 4 }

       -- icfSecurIntruder objects.  When the agent detects an
       -- authentication failure, it records the violation in the
       -- following objects and in nonvolatile memory.  It uses the
       -- icfSecurIntruderFlag as a throttle to prevent excessive
       -- novram writes.

       icfSecurIntruder   OBJECT IDENTIFIER ::= { icfSecurity 4 }

       icfSecurIntruderFlag OBJECT-TYPE
           SYNTAX     INTEGER {
                          valid(1),
                          invalid(2)
                      }
           ACCESS     read-write
           STATUS     mandatory
           DESCRIPTION
                   "If this object is set to 'valid', the remainder
                   of the intruder objects contain information about
                   an authentication failure.  The Security LED on
                   the device will blink if this flag is set to 
                   'valid'.  The intruder objects will not be
                   overwritten as long as this flag is set to 
                   'valid'.  Setting this flag to 'invalid' will turn
                   off the Security LED if there are no other
                   current violations, and will allow the intruder
                   objects to be overwritten by subsequent
                   authentication failures."
           ::= { icfSecurIntruder 1 }

       icfSecurIntruderIpAddress OBJECT-TYPE
           SYNTAX     IpAddress
           ACCESS     read-only
           STATUS     mandatory
           DESCRIPTION
                   "The IP address of the manager that caused the
                   authentication failure.  Only one of
                   icfSecurIntruderIpAddress and
                   icfSecurIntruderIPXAddress will be valid."
           ::= { icfSecurIntruder 2 }

       icfSecurIntruderIpxAddress OBJECT-TYPE
           SYNTAX     OCTET STRING (SIZE (10))
           ACCESS     read-only
           STATUS     mandatory
           DESCRIPTION
                   "The IPX address of the manager that caused the
                   authentication failure.  Only one of
                   icfSecurIntruderIpAddress and
                   icfSecurIntruderIPXAddress will be valid."
           ::= { icfSecurIntruder 3 }

       icfSecurIntruderTime OBJECT-TYPE
           SYNTAX     TimeTicks
           ACCESS     read-only
           STATUS     mandatory
           DESCRIPTION
                   "The value of sysUpTime when the authentication
                   failure occurred.  A value of 0 indicates that the
                   agent has been reset since this authentication
                   failure occurred."
           ::= { icfSecurIntruder 4 }

       -- ICF Configuration group.  This group is only implemented on
       -- EtherTwist hubs with rev 'E' or later firmware and on
       -- AdvanceStack hubs.

       icfConfig          OBJECT IDENTIFIER ::= { icf 5 }

       icfConfigIfTable OBJECT-TYPE
           SYNTAX     SEQUENCE OF IcfConfigIfEntry
           ACCESS     not-accessible
           STATUS     mandatory
           DESCRIPTION
                   "This table contains per-interface configuration
                   information that will take effect after the next
                   reset of the device."
           ::= { icfConfig 1 }

       icfConfigIfEntry OBJECT-TYPE
           SYNTAX     IcfConfigIfEntry
           ACCESS     not-accessible
           STATUS     mandatory
           DESCRIPTION
                   "An entry in the icfConfigIfTable containing
                   information about a single interface."
           INDEX      { icfConfigIfIndex }
           ::= { icfConfigIfTable 1 }

       IcfConfigIfEntry ::=
           SEQUENCE {
               icfConfigIfIndex                INTEGER,
               icfConfigIfIpAddress            IpAddress,
               icfConfigIfNetMask              IpAddress,
               icfConfigIfDefaultGate          IpAddress
           }

       icfConfigIfIndex OBJECT-TYPE
           SYNTAX     INTEGER
           ACCESS     read-only
           STATUS     mandatory
           DESCRIPTION
                   "The index of the interface which this information
                   contains configuration information for.  The
                   interface identified by a particular value of this
                   index is the same interface identified by the same
                   value of ifIndex."
           ::= { icfConfigIfEntry 1 }

       icfConfigIfIpAddress OBJECT-TYPE
           SYNTAX     IpAddress
           ACCESS     read-write
           STATUS     mandatory
           DESCRIPTION
                   "This variable contains the IP address for this
                   interface which will be used after the next reset
                   of the device."
           ::= { icfConfigIfEntry 2 }

       icfConfigIfNetMask OBJECT-TYPE
           SYNTAX     IpAddress
           ACCESS     read-write
           STATUS     mandatory
           DESCRIPTION
                   "This variable contains the IP subnet mask for
                   this interface which will be used after the next
                   reset of the device."
           ::= { icfConfigIfEntry 3 }

        icfConfigIfDefaultGate OBJECT-TYPE
            SYNTAX     IpAddress
            ACCESS     read-write
            STATUS     mandatory
            DESCRIPTION
                    "This variable contains the IP address of the
                    default router for this interface which will be
                    used after the next reset of the device."
             ::= { icfConfigIfEntry 4 }

       icfConfigIpTTL OBJECT-TYPE
           SYNTAX     INTEGER (1..255)
           ACCESS     read-write
           STATUS     mandatory
           DESCRIPTION
                   "This variable contains the default IP time to
                   live which will be used after the next reset of
                   the device."
           ::= { icfConfig 2 }

       icfConfigBootpEnable OBJECT-TYPE
           SYNTAX     INTEGER {
                          enabled(1),
                          disabled(2)
                      }
           ACCESS     read-write
           STATUS     mandatory
           DESCRIPTION
                   "Setting this flag to 'enabled' (the default) will
                   clear any existing IP address configuration for
                   this device, and will cause the device to use the
                   Bootp protocol to obtain its IP configuration
                   after the next reset.  This flag must be set to
                   'disabled' in order to configure an IP address for
                   the device.  Setting this flag to 'disabled' will
                   prevent the Bootp protocol from running.  Setting
                   this flag to 'disabled' when there is no IP
                   address configured will disable the IP protocol
                   stack on this device."
           ::= { icfConfig 3 }

       -- This group includes objects that we believe will be a part of
       -- the standard 802.12 MIB.  When there is a standard,
       -- the standard MIB will replace the icfDot12Draft group.

       icfDot12Draft      OBJECT IDENTIFIER ::= { icf 8 }

       -- This group includes objects that we believe will be a part of
       -- the standard 802.12 Repeater MIB.

       icfVgRepeater      OBJECT IDENTIFIER ::= { icfDot12Draft 1 }
       icfVgBasic         OBJECT IDENTIFIER ::= { icfVgRepeater 1 }
       icfVgBasicRptr     OBJECT IDENTIFIER ::= { icfVgBasic 1 }

       icfVgMACAddress OBJECT-TYPE
           SYNTAX     MacAddress
           ACCESS     read-only
           STATUS     mandatory
           DESCRIPTION
                   "The MAC address used by the repeater when it
                   initiates training on the uplink port.  Repeaters
                   are allowed to train with an assigned MAC address or
                   a null (all zeroes) MAC address."
           REFERENCE
                   "Reference IEEE Draft Std. 802.12, 31 October, 1994, 
                   13.2.4.2.1, aMACAddress."
           ::= { icfVgBasicRptr 1 }

       icfVgCurrentFramingType OBJECT-TYPE
           SYNTAX     INTEGER {
                          frameType88023(1),
                          frameType88025(2)
                      }
           ACCESS     read-only
           STATUS     mandatory
           DESCRIPTION
                   "The type of framing (802.3 or 802.5) currently in
                   use by the repeater."
           REFERENCE
                   "Reference IEEE Draft Std. 802.12, 31 October, 1994,
                   13.2.4.2.1, aCurrentFramingType."
           ::= { icfVgBasicRptr 2 }

       icfVgDesiredFramingType OBJECT-TYPE
           SYNTAX     INTEGER {
                          frameType88023(1),
                          frameType88025(2)
                      }
           ACCESS     read-write
           STATUS     mandatory
           DESCRIPTION
                   "The type of framing which will be used by the
                   repeater after the next time it is reset.  The value
                   of this object should be preserved across repeater
                   resets and power failures"
           REFERENCE
                   "Reference IEEE Draft Std. 802.12, 31 October, 1994,
                   13.2.4.2.1, aDesiredFramingType."
           ::= { icfVgBasicRptr 3 }

       icfVgFramingCapability OBJECT-TYPE
           SYNTAX     INTEGER {
                          frameType88023(1),
                          frameType88025(2),
                          frameTypeEither(3)
                      }
           ACCESS     read-only
           STATUS     mandatory
           DESCRIPTION
                   "The type of framing this repeater is capable of
                   supporting."
           REFERENCE
                   "Reference IEEE Draft Std. 802.12, 31 October, 1994,
                   13.2.4.2.1, aFramingCapability."
           ::= { icfVgBasicRptr 4 }

       icfVgTrainingVersion OBJECT-TYPE
           SYNTAX     INTEGER (0..7)
           ACCESS     read-only
           STATUS     mandatory
           DESCRIPTION
                   "The highest version bits (vvv bits) supported by the
                   repeater during training."
           REFERENCE
                   "Reference IEEE Draft Std. 802.12, 31 October, 1994,
                   13.2.4.2.1, aRMACVersion."
           ::= { icfVgBasicRptr 5 }


       icfVgRepeaterGroupCapacity OBJECT-TYPE
           SYNTAX     INTEGER (1..1024)
           ACCESS     read-only
           STATUS     mandatory
           DESCRIPTION
                   "The icfVgGroupCapacity is the number of groups that
                   can be contained within the repeater.  Within each
                   managed repeater, the groups are uniquely numbered in
                   the range from 1 to icfVgRepeaterGroupCapacity.

                   Some groups may not be present in the repeater, in
                   which case the actual number of groups present will
                   be less than icfVgRepeaterGroupCapacity.  The number
                   of groups present is never greater than
                   icfVgRepeaterGroupCapacity."
           REFERENCE
                   "Reference IEEE Draft Std. 802.12, 31 October, 1994,
                   13.2.4.2.1, aRepeaterGroupCapacity."
           ::= { icfVgBasicRptr 6 }

       icfVgRepeaterHealthState OBJECT-TYPE
           SYNTAX     INTEGER {
                          other(1),
                          ok(2),
                          rptrFailure(3),
                          groupFailure(4),
                          portFailure(5),
                          generalFailure(6)
                      }
           ACCESS     read-only
           STATUS     mandatory
           DESCRIPTION
                   "The icfVgRepeaterHealthState object indicates the
                   operational state of the repeater.  The
                   icfVgRepeaterHealthText may be consulted for more
                   specific information about the state of the 
                   repeater's health.

                   In the case of multiple kinds of failures (e.g.,
                   repeater failure and port failure), the value of this
                   attribute shall reflect the highest priority failure
                   in the following order, listed highest priority 
                   first:

                       rptrFailure(3)
                       groupFailure(4)
                       portFailure(5)
                       generalFailure(6)."
           REFERENCE
                   "Reference IEEE Draft Std. 802.12, 31 October, 1994,
                   13.2.4.2.1, aRepeaterHealthState."
           ::= { icfVgBasicRptr 7 }

       icfVgRepeaterHealthText OBJECT-TYPE
           SYNTAX     DisplayString (SIZE(0..255))
           ACCESS     read-only
           STATUS     mandatory
           DESCRIPTION
                   "The health text object is a text string that 
                   provides information relevant to the operational 
                   state of the repeater.  Agents may use this string to
                   provide detailed information on current failures,
                   including how they were detected, and/or instructions
                   for problem resolution.  The contents are agent
                   specific."
           REFERENCE
                   "Reference IEEE Draft Std. 802.12, 31 October, 1994,
                   13.2.4.2.1, aRepeaterHealthText."
           ::= { icfVgBasicRptr 8 }

       icfVgRepeaterReset OBJECT-TYPE
           SYNTAX     INTEGER {
                          noReset(1),
                          reset(2)
                      }
           ACCESS     read-write
           STATUS     mandatory
           DESCRIPTION
                   "Setting this object to reset(2) causes the repeater
                   to transition to its initial state as specified in
                   clause 12 [IEEE Draft Std 802.12].

                   Setting this object to noReset(1) has no effect.  The
                   agent will always return the value noReset(1) when
                   this object is read.

                   After receiving a request to set this variable to
                   reset(2), the agent is allowed to delay the reset for
                   a short period.  For example, the implementor may
                   choose to delay the reset long enough to allow the
                   SNMP response to be transmitted.  In any event, the
                   SNMP response must be transmitted.

                   This action does not reset the management counters
                   defined in this document nor does it affect the
                   icfVgPortAdminStatus parameters.  Included in this
                   action is the execution of a disruptive Self-Test
                   with the following characteristics:  a) The nature
                   of the tests is not specified.  b) The test resets
                   the repeater but without affecting management
                   information about the repeater.  c) The test does not
                   inject packets onto any segment.  d) Packets received
                   during the test may or may not be transferred.
                   e) The test does not interfere with management
                   functions.

                   After performing this self-test, the agent will
                   update the repeater health information (including
                   icfVgRepeaterHealthState and 
                   icfVgRepeaterHealthText)."
           REFERENCE
                   "Reference IEEE Draft Std. 802.12, 31 October, 1994,
                   13.2.4.2.2, acResetRepeater."
           ::= { icfVgBasicRptr 9 }

       icfVgRepeaterNonDisruptTest OBJECT-TYPE
           SYNTAX     INTEGER {
                          noSelfTest(1),
                          selfTest(2)
                      }
           ACCESS     read-write
           STATUS     mandatory
           DESCRIPTION
                   "Setting this object to selfTest(2) causes the
                   repeater to perform an agent-specific, non-disruptive
                   self-test that has the following characteristics:
                   a) The nature of the tests is not specified.  b) The
                   test does not change the state of the repeater or
                   management information about the repeater.  c) The
                   test does not inject packets onto any segment. 
                   d) The test does not prevent the relay of any
                   packets.  e) The test does not interfere with
                   management functions.

                   After performing this test, the agent will update the
                   repeater health information (including
                   icfVgRepeaterHealthState and 
                   icfVgRepeaterHealthText).

                   Note that this definition allows returning an 'okay'
                   result after doing a trivial test.

                   Setting this object to noSelfTest(1) has no effect.
                   The agent will always return the value noSelfTest(1)
                   when this object is read."
           REFERENCE
                   "Reference IEEE Draft Std. 802.12, 31 October, 1994,
                   13.2.4.2.2, acExecuteNonDisruptiveSelfTest."
           ::= { icfVgBasicRptr 10 }

       icfVgBasicGroup    OBJECT IDENTIFIER ::= { icfVgBasic 2 }

       icfVgBasicGroupTable OBJECT-TYPE
           SYNTAX     SEQUENCE OF IcfVgBasicGroupEntry
           ACCESS     not-accessible
           STATUS     mandatory
           DESCRIPTION
                   "A table containing information about groups of
                   ports."
           ::= { icfVgBasicGroup 1 }

       icfVgBasicGroupEntry OBJECT-TYPE
           SYNTAX     IcfVgBasicGroupEntry
           ACCESS     not-accessible
           STATUS     mandatory
           DESCRIPTION
                   "An entry in the icfVgBasicGroupTable, containing
                   information about a single group of ports."
           INDEX      { icfVgGroupIndex }
           ::= { icfVgBasicGroupTable 1 }

       IcfVgBasicGroupEntry ::=
           SEQUENCE {
               icfVgGroupIndex                 INTEGER,
               icfVgGroupDescr                 DisplayString,
               icfVgGroupObjectID              OBJECT IDENTIFIER,
               icfVgGroupOperStatus            INTEGER,
               icfVgGroupLastOperStatusChange  TimeStamp,
               icfVgGroupPortCapacity          INTEGER,
               icfVgGroupCablesBundled         INTEGER
           }

       icfVgGroupIndex OBJECT-TYPE
           SYNTAX     INTEGER (1..1024)
           ACCESS     not-accessible
           STATUS     mandatory
           DESCRIPTION
                   "This object identifies the group within the repeater
                   for which this entry contains information.  This
                   value is never greater than
                   icfVgRepeaterGroupCapacity."
           REFERENCE
                   "Reference IEEE Draft Std. 802.12, 31 October, 1994,
                   13.2.4.4.1, aGroupID."
           ::= { icfVgBasicGroupEntry 1 }

       icfVgGroupDescr OBJECT-TYPE
           SYNTAX     DisplayString (SIZE (0..255))
           ACCESS     read-only
           STATUS     mandatory
           DESCRIPTION
                   "A textual description of the group.  This value
                   should include the full name and version
                   identification of the group's hardware type and
                   indicate how the group is differentiated from other
                   types of groups in the repeater.  'Plug-in Module,
                   Rev A' or 'Barney Rubble 100BaseVG 4-port socket
                   Version 2.1' are examples of valid group
                   descriptions.

                   It is mandatory that this only contain printable
                   ASCII characters."
           ::= { icfVgBasicGroupEntry 2 }

       icfVgGroupObjectID OBJECT-TYPE
           SYNTAX     OBJECT IDENTIFIER
           ACCESS     read-only
           STATUS     mandatory
           DESCRIPTION
                   "The vendor's authoritative identification of the
                   group.  This value may be allocated within the SMI
                   enterprises subtree (1.3.6.1.4.1) and provides a
                   straight-forward and unambiguous means for
                   determining what kind of group is being managed.

                   For example, this object could take the value
                   1.3.6.1.4.1.4242.1.2.14 if vendor 'Flintstones, Inc.'
                   was assigned the subtree 1.3.6.1.4.1.4242, and had
                   assigned the identifier 1.3.6.1.4.1.4242.1.2.14 to
                   its 'Wilma Flintstone 6-Port Plug-in Module.'"
           ::= { icfVgBasicGroupEntry 3 }

       icfVgGroupOperStatus OBJECT-TYPE
           SYNTAX     INTEGER {
                          other(1),
                          operational(2),
                          malfunctioning(3),
                          notPresent(4),
                          underTest(5),
                          resetInProgress(6)
                      }
           ACCESS     read-only
           STATUS     mandatory
           DESCRIPTION
                   "An object that indicates the operational status of
                   the group.

                   A status of notPresent(4) indicates that the group is
                   temporarily or permanently physically and/or
                   logically not a part of the repeater.  It is an
                   implementation-specific matter as to whether the
                   agent effectively removes notPresent entries from the
                   table.

                   A status of operational(2) indicates that the group
                   is functioning, and a status of malfunctioning(3)
                   indicates that the group is malfunctioning in some
                   way."
           ::= { icfVgBasicGroupEntry 4 }

       icfVgGroupLastOperStatusChange OBJECT-TYPE
           SYNTAX     TimeStamp
           ACCESS     read-only
           STATUS     mandatory
           DESCRIPTION
                   "An object that contains the value of sysUpTime at
                   the time that the value of the icfVgGroupOperStatus
                   object for this group last changed.

                   A value of zero indicates that the group's
                   operational status has not changed since the agent
                   last restarted."
           ::= { icfVgBasicGroupEntry 5 }

       icfVgGroupPortCapacity OBJECT-TYPE
           SYNTAX     INTEGER (1..1024)
           ACCESS     read-only
           STATUS     mandatory
           DESCRIPTION
                   "The icfVgGroupPortCapacity is the number of ports
                   that can be contained within the group.  Valid range
                   is 1-1024.  Within each group, the ports are uniquely
                   numbered in the range from 1 to
                   icfVgGroupPortCapacity.  Some ports may not be
                   present in a given group instance, in which case the
                   actual number of ports present is less than
                   icfVgGroupPortCapacity.  The number of ports present
                   is never greater than icfVgGroupPortCapacity."
           REFERENCE
                   "Reference IEEE Draft Std. 802.12, 31 October, 1994,
                   13.2.4.4.1, aGroupPortCapacity."
           ::= { icfVgBasicGroupEntry 6 }

       icfVgGroupCablesBundled OBJECT-TYPE
           SYNTAX     INTEGER {
                          someCablesBundled(1),
                          noCablesBundled(2)
                      }
           ACCESS     read-write
           STATUS     mandatory
           DESCRIPTION
                   "This configuration flag is used to select either
                   bundled or unbundled cabling.  When this flag is
                   'someCablesBundled(1)' and the port is not
                   promiscuous or cascaded, frames received from ports
                   on this group and destined to go out multiple ports
                   on this group will be buffered completely before
                   being repeated out ports on this group.  When this
                   flag is 'noCablesBundled(2)' or the port is
                   promiscuous or cascaded, these frames will be
                   repeated out ports on this group as the frame is
                   being received.

                   Note that the value 'someCablesBundled(1)' will work
                   in the vast majority of installations, regardless of
                   whether or not any cables are physically in a bundle,
                   since promiscuous and cascaded ports automatically
                   avoid the store and forward.  The main situation in
                   which 'noCablesBundled(2)' is beneficial is when
                   there is a large amount of multicast traffic and the
                   cables are not in a bundle.  The value of this
                   object should be preserved across repeater resets
                   and power failures."
           REFERENCE
                   "Reference IEEE Draft Std. 802.12, 31 October, 1994,
                   13.2.4.4.1, aGroupCablesBundled."
           ::= { icfVgBasicGroupEntry 7 }

       icfVgBasicPort     OBJECT IDENTIFIER ::= { icfVgBasic 3 }

       icfVgBasicPortTable OBJECT-TYPE
           SYNTAX     SEQUENCE OF IcfVgBasicPortEntry
           ACCESS     not-accessible
           STATUS     mandatory
           DESCRIPTION
                   "A table containing information about ports."
           ::= { icfVgBasicPort 1 }

       icfVgBasicPortEntry OBJECT-TYPE
           SYNTAX     IcfVgBasicPortEntry
           ACCESS     not-accessible
           STATUS     mandatory
           DESCRIPTION
                   "An entry in the icfVgBasicPortTable, containing
                   information about a single port."
           INDEX      { icfVgPortGroupIndex, icfVgPortIndex }
           ::= { icfVgBasicPortTable 1 }

       IcfVgBasicPortEntry ::=
           SEQUENCE {
               icfVgPortGroupIndex             INTEGER,
               icfVgPortIndex                  INTEGER,
               icfVgPortType                   INTEGER,
               icfVgPortAdminStatus            INTEGER,
               icfVgPortStatus                 INTEGER,
               icfVgPortSupportedPromiscMode   INTEGER,
               icfVgPortSupportedCascadeMode   INTEGER,
               icfVgPortAllowedTrainType       INTEGER,
               icfVgPortLastTrainConfig        OCTET STRING,
               icfVgPortTrainingResult         OCTET STRING,
               icfVgPortPriorityEnable         TruthValue,
               icfVgPortMediaType              INTEGER
           }

       icfVgPortGroupIndex OBJECT-TYPE
           SYNTAX     INTEGER (1..1024)
           ACCESS     not-accessible
           STATUS     mandatory
           DESCRIPTION
                   "This object identifies the group containing the port
                   for which this entry contains information."
           ::= { icfVgBasicPortEntry 1 }

       icfVgPortIndex OBJECT-TYPE
           SYNTAX     INTEGER (1..1024)
           ACCESS     not-accessible
           STATUS     mandatory
           DESCRIPTION
                   "This object identifies the port within the group for
                   which this entry contains information.  This value
                   can never be greater than icfVgGroupPortCapacity for
                   the associated group."
           REFERENCE
                   "Reference IEEE Draft Std. 802.12, 31 October, 1994,
                   13.2.4.5.1, aPortID."
           ::= { icfVgBasicPortEntry 2 }

       icfVgPortType OBJECT-TYPE
           SYNTAX     INTEGER {
                          cascadeExternal(1),
                          cascadeInternal(2),
                          localExternal(3),
                          localInternal(4)
                      }
           ACCESS     read-only
           STATUS     mandatory
           DESCRIPTION
                   "Describes the type of port.  One of the following:

                       cascadeExternal - Port is an uplink with physical
                                         connections which are 
                                         externally visible
                       cascadeInternal - Port is an uplink with physical
                                         connections which are not
                                         externally visible, such as a
                                         connection to an internal
                                         backplane in a chassis
                       localExternal   - Port is a downlink or local
                                         port with externally visible
                                         connections
                       localInternal   - Port is a downlink or local
                                         port with connections which are
                                         not externally visible, such as
                                         a connection to an internal
                                         agent

                   'internal' is used to identify ports which place
                   traffic into the repeater, but do not have any
                   external connections.  Note that both DTE and
                   cascaded repeater downlinks are considered 'local'
                   ports."
           REFERENCE
                   "Reference IEEE Draft Std. 802.12, 31 October, 1994,
                   13.2.4.5.1, aPortType."
           ::= { icfVgBasicPortEntry 3 }

       icfVgPortAdminStatus OBJECT-TYPE
           SYNTAX     INTEGER {
                          enabled(1),
                          disabled(2)
                      }
           ACCESS     read-write
           STATUS     mandatory
           DESCRIPTION
                   "Port enable/disable function.  Enabling a disabled
                   port will cause training to be initiated.  Setting
                   this object to disabled(2) disables the port.  A
                   disabled port neither transmits nor receives.  Once
                   disabled, a port must be explicitly enabled to
                   restore operation.  A port which is disabled when
                   power is lost or when a reset is exerted shall remain
                   disabled when normal operation resumes."
           REFERENCE
                   "Reference IEEE Draft Std. 802.12, 31 October, 1994,
                   13.2.4.5.1, aPortAdministrativeState."
           ::= { icfVgBasicPortEntry 4 }

       icfVgPortStatus OBJECT-TYPE
           SYNTAX     INTEGER {
                          active(1),
                          inactive(2),
                          training(3)
                      }
           ACCESS     read-only
           STATUS     mandatory
           DESCRIPTION
                   "Current status for the port as specified by the
                   PORT_META_STATE in the port process module of clause
                   12 [IEEE Draft Std 802.12].

                   During initialization or any link warning conditions,
                   icfVgPortStatus will be 'inactive(2)'.

                   When Training_Up is received by the repeater on a
                   local port (or when Training_Down is received on
                   a cascade port), icfVgPortStatus will change to
                   'training(3)' and icfVgTrainingResult can be
                   monitored to see the detailed status regarding
                   training.

                   When 24 consecutive good FCS packets are received and
                   the configuration bits are OK, icfVgPortStatus will
                   change to 'active(1)'.

                   A disabled port shall have a port status of
                   'inactive(2)'."
           REFERENCE
                   "Reference IEEE Draft Std. 802.12, 31 October, 1994,
                   13.2.4.5.1, aPortStatus."
           ::= { icfVgBasicPortEntry 5 }

       icfVgPortSupportedPromiscMode OBJECT-TYPE
           SYNTAX     INTEGER {
                          singleModeOnly(1),
                          singleOrPromiscMode(2),
                          promiscModeOnly(3)
                      }
           ACCESS     read-only
           STATUS     mandatory
           DESCRIPTION
                   "This object describes whether the port hardware is
                   capable of supporting promiscuous mode, single
                   address mode (i.e., repeater filters unicasts not
                   addressed to the end station attached to this port),
                   or both.  A port for which icfVgPortType is equal to
                   'cascadeInternal' or 'cascadeExternal' will always
                   have a value of 'promiscModeOnly' for this object."
           REFERENCE
                   "Reference IEEE Draft Std. 802.12, 31 October, 1994,
                   13.2.4.5.1, aSupportedPromiscMode."
           ::= { icfVgBasicPortEntry 6 }

       icfVgPortSupportedCascadeMode OBJECT-TYPE
           SYNTAX     INTEGER {
                          endNodesOnly(1),
                          endNodesOrRepeaters(2),
                          cascadePort(3)
                      }
           ACCESS     read-only
           STATUS     mandatory
           DESCRIPTION
                   "This object describes whether the port hardware is
                   capable of supporting cascaded repeaters, end nodes,
                   or both.  A port for which icfVgPortType is equal to
                   'cascadeInternal' or 'cascadeExternal' will always
                   have a value of 'cascadePort' for this object."
           REFERENCE
                   "Reference IEEE Draft Std. 802.12, 31 October, 1994,
                   13.2.4.5.1, aSupportedCascadeMode."
           ::= { icfVgBasicPortEntry 7 }

       icfVgPortAllowedTrainType OBJECT-TYPE
           SYNTAX     INTEGER {
                          allowEndNodesOnly(1),
                          allowPromiscuousEndNodes(2),
                          allowEndNodesOrRepeaters(3),
                          allowAnything(4)
                      }
           ACCESS     read-write
           STATUS     mandatory
           DESCRIPTION
                   "This security object is set by the network manager
                   to configure what type of device is permitted to
                   connect to the port.  One of the following values:

                       allowEndNodesOnly        - only non-promiscuous
                                                  end nodes permitted.
                       allowPromiscuousEndNodes - promiscuous or non-
                                                  promiscuous end nodes
                                                  permitted
                       allowEndNodesOrRepeaters - repeaters or non-
                                                  promiscuous end nodes
                                                  permitted
                       allowAnything            - repeaters, promiscuous
                                                  or non-promiscuous end
                                                  nodes permitted

                   For a port for which icfVgPortType is equal to
                   'cascadeInternal' or 'cascadeExternal', the
                   corresponding instance of this object may not be set
                   to 'allowEndNodesOnly' or 'allowPromiscuousEndNodes'.

                   The agent must reject a SET of this object if the
                   value includes no capabilities that are supported by
                   this port's hardware, as defined by the values of the
                   corresponding instances of
                   icfVgPortSupportedPromiscMode and
                   icfVgPortSupportedCascadeMode."
           REFERENCE
                   "Reference IEEE Draft Std. 802.12, 31 October, 1994,
                   13.2.4.5.1, aAllowableTrainingType."
           ::= { icfVgBasicPortEntry 8 }

       icfVgPortLastTrainConfig OBJECT-TYPE
           SYNTAX     OCTET STRING (SIZE(2))
           ACCESS     read-only
           STATUS     mandatory
           DESCRIPTION
                   "This 16 bit field contains the most recent training
                   configuration in an error-free training frame
                   sent by the end node connected to the port.  For
                   cascade ports, this is the responder's configuration
                   field from the most recent error-free training
                   response frame received in response to training
                   initiated by this repeater.  This object is formatted
                   as follows:

                       First Octet:       Second Octet:

                        7 6 5 4 3 2 1 0    7 6 5 4 3 2 1 0
                       +-+-+-+-+-+-+-+-+  +-+-+-+-+-+-+-+-+
                       |v|v|v|0|0|0|0|0|  |0|0|0|F|F|P|P|R|
                       +-+-+-+-+-+-+-+-+  +-+-+-+-+-+-+-+-+

                       vvv: The version of the 802.12 training protocol
                            with which the training initiator is
                            compliant
                       FF:  00 = frameType88023 is requested
                            01 = frameType88025 is requested
                            10 = reserved
                            11 = either frameType88023 or frameType88025
                                 is acceptable
                       PP:  00 = request singleAddressMode
                            01 = request promiscuousMode
                            10 = reserved
                            11 = reserved
                       R:   0  = request is from an end node
                            1  = request is from a repeater"
           REFERENCE
                   "Reference IEEE Draft Std. 802.12, 31 October, 1994,
                   13.2.4.5.1, aLastTrainingConfig."
           ::= { icfVgBasicPortEntry 9 }

       icfVgPortTrainingResult OBJECT-TYPE
           SYNTAX     OCTET STRING (SIZE(3))
           ACCESS     read-only
           STATUS     mandatory
           DESCRIPTION
                   "This 18 bit field is used to indicate the result of
                   training.  It contains two bits which indicate if
                   error-free training frames have been received, and it
                   also contains the 16 bits of the most recent valid
                   training response frame on the port.

                 First Octet:       Second Octet:      Third Octet:

                  7 6 5 4 3 2 1 0    7 6 5 4 3 2 1 0    7 6 5 4 3 2 1 0
                 +-+-+-+-+-+-+-+-+  +-+-+-+-+-+-+-+-+  +-+-+-+-+-+-+-+-+
                 |0|0|0|0|0|0|V|G|  |v|v|v|D|C|N|0|0|  |0|0|0|F|F|P|P|R|
                 +-+-+-+-+-+-+-+-+  +-+-+-+-+-+-+-+-+  +-+-+-+-+-+-+-+-+

                       V:   Valid: set when at least one error-free
                            training frame has been received.  Indicates
                            the 16 training configuration bits in
                            icfVgPortLastTrainConfig and
                            icfVgPortTrainingResult contain valid
                            information.  This bit is cleared when
                            icfVgPortStatus transitions to the 
                            'inactive' or 'training' state.
                       G:   LinkGood: indicates the link hardware is OK.
                            Set if 24 consecutive error-free training
                            packets have been received.  Cleared when a
                            training packet with errors is received, and
                            when icfVgPortStatus transitions to the
                            'inactive' or 'training' state.
                       vvv: The version of the 802.12 training protocol
                            with which the training responder is
                            compliant
                       D:   0  = no duplicate address has been detected
                            1  = duplicate address has been detected
                       C:   0  = the requested configuration is
                                 compatible with the port
                            1  = the requested configuration is not
                                 compatible with the port.  The FF, PP
                                 and R bits indicate the configuration
                                 which would be allowed (providing 
                                 N = 0).
                       N:   0  = access will be allowed, providing the
                                 configuration is compatible (C = 0).
                            1  = access not allowed because of security
                                 restrictions
                       FF:  00 = frameType88023 will be used
                            01 = frameType88025 will be used
                            10 = reserved
                            11 = reserved
                       PP:  00 = singleAddressMode will be used
                            01 = promiscuousMode will be used
                            10 = reserved
                            11 = reserved
                       R:   0  = requested access as an end node is
                                 allowed
                            1  = requested access as a repeater is
                                 allowed

                   If the port is in training, a management station can
                   examine this object to see if any training packets
                   have been passed successfully.  If there have been
                   any good training packets, the Valid bit will be set
                   and the management station can examine the 16
                   training response bits to see if there is a duplicate
                   address, configuration, or security problem.

                   Note that on a repeater local port, this repeater
                   generates the training response bits, while on the
                   cascade port, the higher level repeater originated
                   the training response bits."
           REFERENCE
                   "Reference IEEE Draft Std. 802.12, 31 October, 1994,
                   13.2.4.5.1, aTrainingResult."
           ::= { icfVgBasicPortEntry 10 }

       icfVgPortPriorityEnable OBJECT-TYPE
           SYNTAX     TruthValue
           ACCESS     read-write
           STATUS     mandatory
           DESCRIPTION
                   "A configuration flag used to determine whether the
                   repeater will service high priority requests received
                   on the port as high priority or normal priority.
                   When 'false', high priority requests on this port
                   will be serviced as normal priority.  The value of
                   this object should be preserved across repeater
                   resets and power failures.  The setting of this
                   object has no effect on a cascade port."
           REFERENCE
                   "Reference IEEE Draft Std. 802.12, 31 October, 1994,
                   13.2.4.5.1, aPriorityEnable."
           ::= { icfVgBasicPortEntry 11 }

       icfVgPortMediaType OBJECT-TYPE
           SYNTAX     INTEGER {
                          other(1),
                          unknown(2),
                          pmdMissing(3),
                          utp4(4),
                          stp2(5),
                          fibre(6)
                      }
           ACCESS     read-only
           STATUS     mandatory
           DESCRIPTION
                   "The type of physical media in use.  One of the
                   following values:

                          other       undefined
                          unknown     true state not known
                          pmdMissing  PMD device not attached
                          utp4        4-pair unshielded twisted pair
                          stp2        2-pair shielded twisted pair
                          fibre       802.12 fibre optic cabling

                   This object may be 'unknown' if the implementation is
                   not capable of identifying the PMD media type, or
                   whether or not the PMD is even present."
           REFERENCE
                   "Reference IEEE Draft Std. 802.12, 31 October, 1994,
                   13.2.4.5.1, aMediaType."
           ::= { icfVgBasicPortEntry 12 }

       icfVgMonitor       OBJECT IDENTIFIER ::= { icfVgRepeater 2 }

       icfVgMonRptr       OBJECT IDENTIFIER ::= { icfVgMonitor 1 }
       -- Currently unused

       icfVgMonGroup      OBJECT IDENTIFIER ::= { icfVgMonitor 2 }
       -- Currently unused

       icfVgMonPort       OBJECT IDENTIFIER ::= { icfVgMonitor 3 }

       icfVgMonPortTable OBJECT-TYPE
           SYNTAX     SEQUENCE OF IcfVgMonPortEntry
           ACCESS     not-accessible
           STATUS     mandatory
           DESCRIPTION
                   "A table of performance and error statistics for the
                   ports."
           ::= { icfVgMonPort 1 }

       icfVgMonPortEntry OBJECT-TYPE
           SYNTAX     IcfVgMonPortEntry
           ACCESS     not-accessible
           STATUS     mandatory
           DESCRIPTION
                   "An entry in the icfVgMonPortTable, containing
                   performance and error statistics for a single port."
           INDEX      { icfVgPortGroupIndex, icfVgPortIndex }
           ::= { icfVgMonPortTable 1 }

       IcfVgMonPortEntry ::=
           SEQUENCE {
               icfVgPortReadableFrames         Counter,
               icfVgPortReadableOctets         Counter,
               icfVgPortUnreadableOctets       Counter,
               icfVgPortHighPriorityFrames     Counter,
               icfVgPortHighPriorityOctets     Counter,
               icfVgPortBroadcastFrames        Counter,
               icfVgPortMulticastFrames        Counter,
               icfVgPortIPMFrames              Counter,
               icfVgPortDataErrorFrames        Counter,
               icfVgPortPriorityPromotions     Counter
           }

       icfVgPortReadableFrames OBJECT-TYPE
           SYNTAX     Counter
           ACCESS     read-only
           STATUS     mandatory
           DESCRIPTION
                   "This object is the number of good frames of valid
                   frame length that have been received on this port.
                   This counter is incremented by one for each frame
                   received on the port which is not counted by
                   icfVgPortIPMFrames or icfVgPortDataErrorFrames."
           REFERENCE
                   "Reference IEEE Draft Std. 802.12, 31 October, 1994,
                   13.2.4.5.1, aReadableFramesReceived."
           ::= { icfVgMonPortEntry 1 }

       icfVgPortReadableOctets OBJECT-TYPE
           SYNTAX     Counter
           ACCESS     read-only
           STATUS     mandatory
           DESCRIPTION
                   "This object is a count of the number of octets
                   contained in good frames that have been received on
                   this port.  This counter is incremented by OctetCount
                   for each frame received on this port which has been
                   determined to be a readable frame (i.e. each frame
                   counted by icfVgPortReadableFrames).

                   Note that this counter may roll over very quickly."
           REFERENCE
                   "Reference IEEE Draft Std. 802.12, 31 October, 1994,
                   13.2.4.5.1, aReadableOctetsReceived."
           ::= { icfVgMonPortEntry 2 }

       icfVgPortUnreadableOctets OBJECT-TYPE
           SYNTAX     Counter
           ACCESS     read-only
           STATUS     mandatory
           DESCRIPTION
                   "This object is a count of the number of octets
                   contained in invalid frames that have been received
                   on this port.  This counter is incremented by
                   OctetCount for each frame received on this port which
                   is counted by icfVgPortIPMFrames or
                   icfVgPortDataErrorFrames.  This counter can be
                   combined with icfVgPortReadableOctets to calculate
                   network utilization.

                   Note that this counter may roll over very quickly."
           REFERENCE
                   "Reference IEEE Draft Std. 802.12, 31 October, 1994,
                   13.2.4.5.1, aOctetsInUnreadableFramesRcvd."
           ::= { icfVgMonPortEntry 3 }

       icfVgPortHighPriorityFrames OBJECT-TYPE
           SYNTAX     Counter
           ACCESS     read-only
           STATUS     mandatory
           DESCRIPTION
                   "This object is a count of high priority frames
                   that have been received on this port.  This counter
                   is incremented by one for each high priority frame
                   received on this port, including readable, invalid,
                   and training frames.  This counter does not include
                   normal priority frames which were priority promoted."
           REFERENCE
                   "Reference IEEE Draft Std. 802.12, 31 October, 1994,
                   13.2.4.5.1, aHighPriorityFramesReceived."
           ::= { icfVgMonPortEntry 4 }

       icfVgPortHighPriorityOctets OBJECT-TYPE
           SYNTAX     Counter
           ACCESS     read-only
           STATUS     mandatory
           DESCRIPTION
                   "This object is a count of the number of octets
                   contained in high priority frames that have been
                   received on this port.  This counter is incremented
                   by OctetCount for each frame received on this port
                   which is counted by icfVgPortHighPriorityFrames.

                   Note that this counter may roll over very quickly."
           REFERENCE
                   "Reference IEEE Draft Std. 802.12, 31 October, 1994,
                   13.2.4.5.1, aHighPriorityOctetsReceived."
           ::= { icfVgMonPortEntry 5 }

       icfVgPortBroadcastFrames OBJECT-TYPE
           SYNTAX     Counter
           ACCESS     read-only
           STATUS     mandatory
           DESCRIPTION
                   "This object is a count of broadcast packets that
                   have been received on this port.  This counter is
                   incremented by one for each readable frame received
                   on this port whose destination MAC address is the
                   broadcast address.  Frames counted by this counter
                   are also counted by icfVgPortReadableFrames."
           REFERENCE
                   "Reference IEEE Draft Std. 802.12, 31 October, 1994,
                   13.2.4.5.1, aBroadcastFramesReceived."
           ::= { icfVgMonPortEntry 6 }

       icfVgPortMulticastFrames OBJECT-TYPE
           SYNTAX     Counter
           ACCESS     read-only
           STATUS     mandatory
           DESCRIPTION
                   "This object is a count of multicast packets that
                   have been received on this port.  This counter is
                   incremented by one for each readable frame received
                   on this port whose destination MAC address has the
                   group address bit set, but is not the broadcast
                   address.  Frames counted by this counter are also
                   counted by icfVgPortReadableFrames, but not by
                   icfVgPortBroadcastFrames"
           REFERENCE
                   "Reference IEEE Draft Std. 802.12, 31 October, 1994,
                   13.2.4.5.1, aMulticastFramesReceived."
           ::= { icfVgMonPortEntry 7 }

       icfVgPortIPMFrames OBJECT-TYPE
           SYNTAX     Counter
           ACCESS     read-only
           STATUS     mandatory
           DESCRIPTION
                   "This object is a count of the number of frames that
                   have been received on this port with an invalid
                   packet marker and no PMI errors.  A repeater will
                   write an invalid packet marker to the end of a frame
                   containing errors as it is forwarded through the
                   repeater to the other ports.  This counter is
                   incremented by one for each frame received on this
                   port which has had an invalid packet marker added to
                   the end of the frame.  This counter indicates
                   problems with remote cable segments, as opposed to
                   problems with cables directly attached to this
                   repeater."
           REFERENCE
                   "Reference IEEE Draft Std. 802.12, 31 October, 1994,
                   13.2.4.5.1, aIPMFramesReceived."
           ::= { icfVgMonPortEntry 8 }

       icfVgPortDataErrorFrames OBJECT-TYPE
           SYNTAX     Counter
           ACCESS     read-only
           STATUS     mandatory
           DESCRIPTION
                   "This object is a count of errored frames received on
                   this port.  This counter is incremented by one for
                   each frame received on this port with any of the
                   following errors: FCS (with no IPM), PMI erorrs 
                   (excluding frames with an IPM error as the only PMI
                   error), oversize (with no IPM), or undersize (with no
                   IPM).  Does not include packets counted by
                   icfVgPortIPMFrames.  This counter indicates problems
                   with the cable directly attached to this repeater,
                   while icfVgPorrtIPMFrames indicates problems with
                   remote cables attached to other repeaters."
           REFERENCE
                   "Reference IEEE Draft Std. 802.12, 31 October, 1994,
                   13.2.4.5.1, aDataErrorFramesReceived."
           ::= { icfVgMonPortEntry 9 }

       icfVgPortPriorityPromotions OBJECT-TYPE
           SYNTAX     Counter
           ACCESS     read-only
           STATUS     mandatory
           DESCRIPTION
                   "This counter is incremented by one each time the
                   priority promotion timer has expired on this port and
                   a normal priority frame was priority promoted."
           REFERENCE
                   "Reference IEEE Draft Std. 802.12, 31 October, 1994,
                   13.2.4.5.1, aPriorityPromotions."
           ::= { icfVgMonPortEntry 10 }

       icfVgAddrTrack      OBJECT IDENTIFIER ::= { icfVgRepeater 3 }

       icfVgAddrTrackRptr  OBJECT IDENTIFIER ::= { icfVgAddrTrack 1 }
       -- Currently unused

       icfVgAddrTrackGroup OBJECT IDENTIFIER ::= { icfVgAddrTrack 2 }
       -- Currently unused

       icfVgAddrTrackPort  OBJECT IDENTIFIER ::= { icfVgAddrTrack 3 }

       icfVgAddrTrackTable OBJECT-TYPE
           SYNTAX     SEQUENCE OF IcfVgAddrTrackEntry
           ACCESS     not-accessible
           STATUS     mandatory
           DESCRIPTION
               "Table of address mapping information about the
               ports."
           ::= { icfVgAddrTrackPort 1 }

       icfVgAddrTrackEntry OBJECT-TYPE
           SYNTAX     IcfVgAddrTrackEntry
           ACCESS     not-accessible
           STATUS     mandatory
           DESCRIPTION
               "An entry in the table, containing address mapping
               information about a single port."
           INDEX      { icfVgPortGroupIndex, icfVgPortIndex }
           ::= { icfVgAddrTrackTable 1 }

       IcfVgAddrTrackEntry ::=
           SEQUENCE {
               icfVgAddrLastTrainedAddress     OCTET STRING,
               icfVgAddrTrainedAddrChanges     Counter
           }


       icfVgAddrLastTrainedAddress OBJECT-TYPE
           SYNTAX     OCTET STRING (SIZE(0 | 6))
           ACCESS     read-only
           STATUS     mandatory
           DESCRIPTION
                   "This object is the MAC address of the last station
                   which succeeded in training on this port.  A
                   cascaded repeater may train using the null address.
                   If no stations have succeeded in training on this
                   port since the agent began monitoring the port
                   activity, the agent shall return a string of length
                   zero."
           REFERENCE
                   "Reference IEEE Draft Std. 802.12, 31 October, 1994,
                   13.2.4.5.1, aLastTrainedAddress."
           ::= { icfVgAddrTrackEntry 1 }

       icfVgAddrTrainedAddrChanges OBJECT-TYPE
           SYNTAX     Counter
           ACCESS     read-only
           STATUS     mandatory
           DESCRIPTION
                   "This counter is incremented by one for each time
                   that the icfVgAddrLastTrainedAddress object for this
                   port has changed."
           REFERENCE
                   "Reference IEEE Draft Std. 802.12, 31 October, 1994,
                   13.2.4.5.1, aTrainedAddressChanges."
           ::= { icfVgAddrTrackEntry 2 }

       -- The new HP ICF tree.  As things in the old tree are
       -- migrated to this tree, the old ones will be deprecated.
       -- Eventually, everything will be here.  This tree is designed
       -- to be simple to convert to the RFC 1442 SMI.
       
       hpicfObjects    OBJECT IDENTIFIER ::= { icf 11 }
       
       -- HP ICF Common Objects
       
       hpicfCommon     OBJECT IDENTIFIER ::= { hpicfObjects 1 }
       
       hpicfChain      OBJECT IDENTIFIER ::= { hpicfCommon 1 }
       
       -- This MIB models a chain of "boxes" attached to an HP 
       -- Distributed Management Chain.  Each box may have one or 
       -- more manageable entities in it, and may contain one or more
       -- SNMP agents, which may each be acting as an SNMP proxy for
       -- one or more of the other boxes on the Distributed 
       -- Management Chain that do not have agents.
       --
       -- All of the agents on the chain will know about the 
       -- hpicfChainTable.  The hpicfChainViewTable will contain 
       -- entries for those boxes on the chain for which the agent 
       -- can act as a proxy.
       
       hpicfChainMaxMembers OBJECT-TYPE 
           SYNTAX     INTEGER (1..16)
           ACCESS     read-only
           STATUS     mandatory
           DESCRIPTION
                   "The maximum number of devices that can be 
                   supported on the Distributed Management Chain from
                   this agent."
           ::= { hpicfChain 1 }
       
       hpicfChainCurMembers OBJECT-TYPE
           SYNTAX     INTEGER (1..16)
           ACCESS     read-only
           STATUS     mandatory
           DESCRIPTION
                   "The number of devices currently on the 
                   Distributed Management Chain connected to this 
                   agent."
           ::= { hpicfChain 2 }
       
       hpicfChainLastChange OBJECT-TYPE
           SYNTAX     TimeStamp
           ACCESS     read-only
           STATUS     mandatory
           DESCRIPTION
                   "The value of sysUpTime on this agent the last 
                   time a device was added to or removed from the 
                   Distributed Management Chain connected to this 
                   agent."
           ::= { hpicfChain 3 }
       
       hpicfChainChanges OBJECT-TYPE
           SYNTAX     Counter
           ACCESS     read-only
           STATUS     mandatory
           DESCRIPTION
                   "A count of the number of times devices have been 
                   added to or removed from the Distributed 
                   Management Chain connected to this agent."
           ::= { hpicfChain 4 }
       
       hpicfChainTable OBJECT-TYPE
           SYNTAX     SEQUENCE OF HpicfChainEntry
           ACCESS     not-accessible
           STATUS     mandatory
           DESCRIPTION
                   "A table of boxes currently connected to the same 
                   Distributed Management Chain as this agent."
           ::= { hpicfChain 5 }
       
       hpicfChainEntry OBJECT-TYPE
           SYNTAX     HpicfChainEntry
           ACCESS     not-accessible
           STATUS     mandatory
           DESCRIPTION
                   "An entry in the table describing a single box on 
                   the Distributed Management Chain connected to this
                   device."
           INDEX      { hpicfChainId }
           ::= { hpicfChainTable 1 }

       HpicfChainEntry ::= 
           SEQUENCE {
               hpicfChainId                    OCTET STRING,
               hpicfChainObjectId              OBJECT IDENTIFIER,
               hpicfChainTimestamp             TimeStamp,
               hpicfChainHasAgent              TruthValue,
               hpicfChainThisBox               TruthValue,
               hpicfChainLocation              INTEGER
           }
       
       hpicfChainId OBJECT-TYPE
           SYNTAX     OCTET STRING (SIZE (6))
           ACCESS     read-only
           STATUS     mandatory
           DESCRIPTION
                   "An identifier which uniquely identifies this 
                   particular box.  In practice, this will be a box
                   serial number or MAC address."
           ::= { hpicfChainEntry 1 }
       
       hpicfChainObjectId OBJECT-TYPE
           SYNTAX      OBJECT IDENTIFIER
           ACCESS      read-only
           STATUS      mandatory
           DESCRIPTION
                   "The authoritative identification of the box which
                   provides an easy and unambiguous means for 
                   determining the type of box."
           ::= { hpicfChainEntry 2 }
       
       hpicfChainTimestamp OBJECT-TYPE
           SYNTAX     TimeStamp
           ACCESS     read-only
           STATUS     mandatory
           DESCRIPTION
                   "The value of the agent's sysUpTime at which this 
                   box was last initialized.  If the box has not been
                   initialized since the last reinitialization of the
                   agent, then this object has a zero value."
           ::= { hpicfChainEntry 3 }
       
       hpicfChainHasAgent OBJECT-TYPE
           SYNTAX     TruthValue
           ACCESS     read-only
           STATUS     mandatory
           DESCRIPTION
                   "This object will contain the value 'true' if this
                   box contains at least one network management agent
                   capable of responding to SNMP requests, and will 
                   contain the value 'false' otherwise."
           ::= { hpicfChainEntry 4 }

       hpicfChainThisBox OBJECT-TYPE
           SYNTAX     TruthValue
           ACCESS     read-only
           STATUS     mandatory
           DESCRIPTION
                   "This object will contain the value 'true' if this
                   entry in the chain table corresponds to the box 
                   which contains the agent which is responding to
                   this SNMP request, and will contain the value
                   'false' otherwise."
           ::= { hpicfChainEntry 5 }

       hpicfChainLocation OBJECT-TYPE
           SYNTAX     INTEGER (0..255)
           ACCESS     read-write
           STATUS     mandatory
           DESCRIPTION
                   "This byte is settable by a management station and
                   is not interpreted by the agent.  The intent is
                   that a management station can use it to assign an
                   ordering to boxes on the chain that can later be
                   used when displaying the chain."
           ::= { hpicfChainEntry 6 }

       hpicfChainViewTable OBJECT-TYPE
           SYNTAX     SEQUENCE OF HpicfChainViewEntry
           ACCESS     not-accessible
           STATUS     mandatory
           DESCRIPTION
                   "This table contains one entry for each box on the
                   Distributed Management Chain for which this agent 
                   is able to act as a proxy."
           ::= { hpicfChain 6 }

       hpicfChainViewEntry OBJECT-TYPE
           SYNTAX     HpicfChainViewEntry
           ACCESS     not-accessible
           STATUS     mandatory
           DESCRIPTION
                   "An entry in the hpicfChainViewTable containing
                   information about how to proxy to a single box."
           INDEX      { hpicfChainViewId }
           ::= { hpicfChainViewTable 1 }

       HpicfChainViewEntry ::=
           SEQUENCE {
               hpicfChainViewId                OCTET STRING,
               hpicfChainViewName              DisplayString
           }

       hpicfChainViewId OBJECT-TYPE
           SYNTAX     OCTET STRING (SIZE (6))
           ACCESS     read-only
           STATUS     mandatory
           DESCRIPTION
                   "An identifier which uniquely identifies this 
                   particular box.  In practice, this will be a box
                   serial number or MAC address."
           ::= { hpicfChainViewEntry 1 }
       
       hpicfChainViewName OBJECT-TYPE
           SYNTAX     DisplayString (SIZE(0..15))
           ACCESS     read-only
           STATUS     mandatory
           DESCRIPTION
                   "The local name of this box.  This is used by the
                   proxy agent for the box to determine which box on
                   the Distributed Management Chain is being 
                   addressed.  If an agent does not use this method 
                   to distinguish proxy destinations, it should 
                   return a zero length octet string for this object.
       
                   For SNMPv1, the destination box is specified by
                   appending this name to the proxy agent's community
                   name.  For example, if this agent has a community
                   with a community name of 'public', and the value
                   of this object is 'repeater1', the community 
                   'public/repeater1' will specify that the agent
                   should proxy to the public community of the
                   'repeater1' box.
       
                   The default value for this object for box-level 
                   repeaters is an ASCII hex representation of the 
                   low-order three bytes of the device MAC address."
           ::= { hpicfChainViewEntry 2 }


       -- The ICF Chassis group

       hpicfChassis    OBJECT IDENTIFIER ::= { hpicfCommon 2 }

       -- The Chassis group contains detailed information about what
       -- is inside a particular chassis.  The intent is that an 
       -- agent can provide information about the box that it is in. 
       
       hpicfChassisId OBJECT-TYPE
           SYNTAX     OCTET STRING (SIZE (6))
           ACCESS     read-only
           STATUS     mandatory
           DESCRIPTION
                   "An identifier that uniquely identifies this 
                   particular chassis.  This will be the same value 
                   as the instance of hpicfChainId for this chassis."
           ::= { hpicfChassis 1 }
       
       hpicfChassisNumSlots OBJECT-TYPE
           SYNTAX     INTEGER (0..16)
           ACCESS     read-only
           STATUS     mandatory
           DESCRIPTION
                   "The number of slots in this chassis."
           ::= { hpicfChassis 2 }
       
       -- The slot table contains one entry for each slot in this
       -- chassis.
       
       hpicfSlotTable OBJECT-TYPE
           SYNTAX     SEQUENCE OF HpicfSlotEntry
           ACCESS     not-accessible
           STATUS     mandatory
           DESCRIPTION
                   "A table that contains information on all the 
                   slots in this chassis."
           ::= { hpicfChassis 3 }
       
       hpicfSlotEntry OBJECT-TYPE
           SYNTAX     HpicfSlotEntry
           ACCESS     not-accessible
           STATUS     mandatory
           DESCRIPTION
                   "Information about a slot in a chassis"
           INDEX      { hpicfSlotIndex }
           ::= { hpicfSlotTable 1 }
       
       HpicfSlotEntry ::=
           SEQUENCE {
               hpicfSlotIndex                  INTEGER,
               hpicfSlotObjectId               OBJECT IDENTIFIER,
               hpicfSlotLastChange             TimeStamp,
               hpicfSlotDescr                  DisplayString
           }
       
       hpicfSlotIndex OBJECT-TYPE
           SYNTAX     INTEGER (1..16)
           ACCESS     read-only
           STATUS     mandatory
           DESCRIPTION
                   "The slot number within the box for which this 
                   entry contains information."
           ::= { hpicfSlotEntry 1 }
       
       hpicfSlotObjectId OBJECT-TYPE
           SYNTAX     OBJECT IDENTIFIER
           ACCESS     read-only
           STATUS     mandatory
           DESCRIPTION
                   "The authoritative identification of the card 
                   plugged into this slot in this chassis.  A value 
                   of { 0 0 } indicates an empty slot."
           ::= { hpicfSlotEntry 2 }
       
       hpicfSlotLastChange OBJECT-TYPE
           SYNTAX     TimeStamp
           ACCESS     read-only
           STATUS     mandatory
           DESCRIPTION
                   "The value of the agent's sysUpTime at which a 
                   card in this slot was last inserted or removed.  
                   If no module has been inserted or removed since 
                   the last reinitialization of the agent, this 
                   object has a zero value."
           ::= { hpicfSlotEntry 3 }
       
       hpicfSlotDescr OBJECT-TYPE
           SYNTAX     DisplayString (SIZE (0..255))
           ACCESS     read-only
           STATUS     mandatory
           DESCRIPTION
                   "A textual description of the card plugged into 
                   this slot in this chassis, including the product 
                   number and version information."
           ::= { hpicfSlotEntry 4 }
       
       -- The entity table contains a list of logical network devices
       -- contained in this chassis, whether or not that agent can 
       -- actually manage the device.  The intent is that any agent 
       -- for a box will have a complete picture of the entities in 
       -- that box.
       
       hpicfEntityTable OBJECT-TYPE
           SYNTAX     SEQUENCE OF HpicfEntityEntry
           ACCESS     not-accessible
           STATUS     mandatory
           DESCRIPTION
                   "A table that contains information about the 
                   (logical) networking devices contained in this
                   chassis."
           ::= { hpicfChassis 4 }
       
       hpicfEntityEntry OBJECT-TYPE
           SYNTAX     HpicfEntityEntry
           ACCESS     not-accessible
           STATUS     mandatory
           DESCRIPTION
                   "Information about a single logical networking 
                   device contained in this chassis."
           INDEX      { hpicfEntityIndex }
           ::= { hpicfEntityTable 1 }
       
       HpicfEntityEntry ::=
           SEQUENCE {
               hpicfEntityIndex                INTEGER,
               hpicfEntityFunction             INTEGER,
               hpicfEntityObjectId             OBJECT IDENTIFIER,
               hpicfEntityDescr                DisplayString,
               hpicfEntityTimestamp            TimeStamp
           }
       
       hpicfEntityIndex OBJECT-TYPE
           SYNTAX     INTEGER (1..16)
           ACCESS     read-only
           STATUS     mandatory
           DESCRIPTION
                   "An index that uniquely identifies the logical 
                   network device for which this entry contains 
                   information."
           ::= { hpicfEntityEntry 1 }
       
       hpicfEntityFunction OBJECT-TYPE
           SYNTAX     INTEGER (0..63)
           ACCESS     read-only
           STATUS     mandatory
           DESCRIPTION
                   "The generic function provided by the logical 
                   network device.  The value is a sum.  Starting 
                   from zero, for each type of generic function that 
                   the entity performs, 2 raised to a power is added 
                   to the sum.  The powers are according to the 
                   following table:
       
                       Function        Power
                       other           0
                       repeater        1
                       bridge          2
                       router          3
                       agent           5
       
                   For example, an entity performing both bridging 
                   and routing functions would have a value of 12 
                   (2^2 + 2^3)."
           ::= { hpicfEntityEntry 2 }
       
       hpicfEntityObjectId OBJECT-TYPE
           SYNTAX     OBJECT IDENTIFIER
           ACCESS     read-only
           STATUS     mandatory
           DESCRIPTION
                   "The authoritative identification of the logical 
                   network device which provides an unambiguous means
                   of determining the type of device.  The value of 
                   this object is analagous to MIB-II's sysObjectId."
           ::= { hpicfEntityEntry 3 }
       
       hpicfEntityDescr OBJECT-TYPE
           SYNTAX     DisplayString (SIZE (0..255))
           ACCESS     read-only
           STATUS     mandatory
           DESCRIPTION
                   "A textual description of this device, including 
                   the product number and version information.  The 
                   value of this object is analogous to MIB-II's 
                   sysDescr."
           ::= { hpicfEntityEntry 4 }
       
       hpicfEntityTimestamp OBJECT-TYPE
           SYNTAX     TimeStamp
           ACCESS     read-only
           STATUS     mandatory
           DESCRIPTION
                   "The value of the agent's sysUpTime at which this 
                   logical network device was last reinitialized.  If
                   the entity has not been reinitialized since the 
                   last reinitialization of the agent, then this 
                   object has a zero value."
           ::= { hpicfEntityEntry 5 }

       -- The hpicfSlotMapTable is used to convey which logical
       -- network devices occupy which slots in the chassis.  For
       -- example, if a chassis contains a repeater entity, with an
       -- hpicfEntityIndex of 2, which is made up of three cards
       -- located in slots 2, 4, and 5 of the chassis, this table
       -- will contain entries indexed by { 2 2 }, { 4 2 } and
       -- { 5 2 }.

       hpicfSlotMapTable OBJECT-TYPE
           SYNTAX     SEQUENCE OF HpicfSlotMapEntry
           ACCESS     not-accessible
           STATUS     mandatory
           DESCRIPTION
                   "A table that contains information about which 
                   entities are in which slots in this chassis."
           ::= { hpicfChassis 5 }
       
       hpicfSlotMapEntry OBJECT-TYPE
           SYNTAX     HpicfSlotMapEntry
           ACCESS     not-accessible
           STATUS     mandatory
           DESCRIPTION
                   "A relationship between a slot and an entity in
                   this chassis.  Such a relationship exists if the 
                   particular slot is occupied by a physical module 
                   performing part of the function of the particular 
                   entity."
           INDEX      { hpicfSlotMapSlot, hpicfSlotMapEntity }
           ::= { hpicfSlotMapTable 1 }
       
       HpicfSlotMapEntry ::=
           SEQUENCE {
               hpicfSlotMapSlot                INTEGER,
               hpicfSlotMapEntity              INTEGER
           }
       
       hpicfSlotMapSlot OBJECT-TYPE
           SYNTAX     INTEGER (1..16)
           ACCESS     read-only
           STATUS     mandatory
           DESCRIPTION
                   "A slot number within the chassis which contains 
                   (part of) this entity."
           ::= { hpicfSlotMapEntry 1 }
       
       hpicfSlotMapEntity OBJECT-TYPE
           SYNTAX     INTEGER (1..16)
           ACCESS     read-only
           STATUS     mandatory
           DESCRIPTION
                   "The entity described in this mapping."
           ::= { hpicfSlotMapEntry 2 }

       -- The sensor table contains one entry for each sensor in this
       -- chassis.  This table is currently only implemented on
       -- AdvanceStack routers.

       hpicfSensorTable OBJECT-TYPE
           SYNTAX     SEQUENCE OF HpicfSensorEntry
           ACCESS     not-accessible
           STATUS     mandatory
           DESCRIPTION
                   "A table that contains information on all the
                   sensors in this chassis"
           ::= { hpicfChassis 6 }

       hpicfSensorEntry OBJECT-TYPE
           SYNTAX     HpicfSensorEntry
           ACCESS     not-accessible
           STATUS     mandatory
           DESCRIPTION
                   "Information about a sensor in a chassis"
           INDEX      { hpicfSensorIndex }
           ::= { hpicfSensorTable 1 }

       HpicfSensorEntry ::=
           SEQUENCE {
               hpicfSensorIndex                INTEGER,
               hpicfSensorObjectId             OBJECT IDENTIFIER,
               hpicfSensorNumber               INTEGER,
               hpicfSensorStatus               INTEGER,
               hpicfSensorWarnings             Counter,
               hpicfSensorFailures             Counter,
               hpicfSensorDescr                DisplayString
           }

       hpicfSensorIndex OBJECT-TYPE
           SYNTAX     INTEGER
           ACCESS     read-only
           STATUS     mandatory
           DESCRIPTION
                   "An index that uniquely identifies the sensor for
                   which this entry contains information."
           ::= { hpicfSensorEntry 1 }

       hpicfSensorObjectId OBJECT-TYPE
           SYNTAX     OBJECT IDENTIFIER
           ACCESS     read-only
           STATUS     mandatory
           DESCRIPTION
                   "The authoritative identification of the kind of
                   sensor this is."
           ::= { hpicfSensorEntry 2 }

       hpicfSensorNumber OBJECT-TYPE
           SYNTAX     INTEGER
           ACCESS     read-only
           STATUS     mandatory
           DESCRIPTION
                   "A number which identifies a particular sensor
                   from other sensors of the same kind.  For
                   instance, if there are many temperature sensors in
                   this chassis, this number whould identify a
                   particular temperature sensor in this chassis."
           ::= { hpicfSensorEntry 3 }

       hpicfSensorStatus OBJECT-TYPE
           SYNTAX     INTEGER {
                          unknown(1),
                          bad(2),
                          warning(3),
                          good(4)
                      }
           ACCESS     read-only
           STATUS     mandatory
           DESCRIPTION
                   "Actual status indicated by the sensor."
           ::= { hpicfSensorEntry 4 }

       hpicfSensorWarnings OBJECT-TYPE
           SYNTAX     Counter
           ACCESS     read-only
           STATUS     mandatory
           DESCRIPTION
                   "The number of times hpicfSensorStatus has entered
                   the 'warning'(3) state."
           ::= { hpicfSensorEntry 5 }

       hpicfSensorFailures OBJECT-TYPE
           SYNTAX     Counter
           ACCESS     read-only
           STATUS     mandatory
           DESCRIPTION
                   "The number of times hpicfSensorStatus has entered
                   the 'bad'(2) state."
           ::= { hpicfSensorEntry 6 }

       hpicfSensorDescr OBJECT-TYPE
           SYNTAX     DisplayString
           ACCESS     read-only
           STATUS     mandatory
           DESCRIPTION
                   "A textual description of the sensor."
           ::= { hpicfSensorEntry 7 }

       hpicfChassisAddrTable OBJECT-TYPE
           SYNTAX     SEQUENCE OF HpicfChassisAddrEntry
           ACCESS     not-accessible
           STATUS     mandatory
           DESCRIPTION
                   "A table of network addresses for entities in this
                   chassis.  The primary use of this table is to map
                   a specific entity address to a specific chassis.
                   Note that this table may not be a complete list of
                   network addresses for this entity."
           ::= { hpicfChassis 7 }

       hpicfChassisAddrEntry OBJECT-TYPE
           SYNTAX     HpicfChassisAddrEntry
           ACCESS     not-accessible
           STATUS     mandatory
           DESCRIPTION
                   "An entry containing a single network address being
                   used by a logical network device in this chassis."
           INDEX      { hpicfChasAddrType, hpicfChasAddrAddress }
           ::= { hpicfChassisAddrTable 1 }

       HpicfChassisAddrEntry ::=
           SEQUENCE {
               hpicfChasAddrType               INTEGER,
               hpicfChasAddrAddress            OCTET STRING,
               hpicfChasAddrEntity             INTEGER
           }

       hpicfChasAddrType OBJECT-TYPE
           SYNTAX     INTEGER {
                          ipAddr(1),
                          ipxAddr(2),
                          macAddr(3)
                      }
           ACCESS     not-accessible
           STATUS     mandatory
           DESCRIPTION
                   "The kind of network address represented in this
                   entry."
           ::= { hpicfChassisAddrEntry 1 }

       hpicfChasAddrAddress OBJECT-TYPE
           SYNTAX     OCTET STRING (SIZE(4..10))
           ACCESS     not-accessible
           STATUS     mandatory
           DESCRIPTION
                   "The network address being used by the logical
                   network device associated with this entry, formatted
                   according to the value of the associated instance of
                   hpicfChasAddrType.

                   For hpicfChasAddrType of ipAddr, this value is four
                   octets long, with each octet representing one byte of
                   the IP address, in network byte order.

                   For hpicfChasAddrType of ipxAddr, this value is ten
                   octets long, with the first four octets representing
                   the IPX network number in network byte order,
                   followed by the six byte host number in network byte
                   order.

                   For hpicfChasAddrType of macAddr, this value is six
                   octets long, representing the MAC address in
                   canonical order."
           ::= { hpicfChassisAddrEntry 2 }

       hpicfChasAddrEntity OBJECT-TYPE
           SYNTAX     INTEGER (1..16)
           ACCESS     read-only
           STATUS     mandatory
           DESCRIPTION
                   "An index that uniquely identifies the logical 
                   network device in this chassis that is using this
                   network address.."
           ::= { hpicfChassisAddrEntry 3 }

       -- The ICF Download group
       
       hpicfDownload   OBJECT IDENTIFIER ::= { hpicfCommon 3 }
       
       hpicfDownloadTable OBJECT-TYPE
           SYNTAX     SEQUENCE OF HpicfDownloadEntry
           ACCESS     not-accessible
           STATUS     mandatory
           DESCRIPTION
                   "A table of firmware downloads to this device.  
                   There will at any time be either 0 or 1 rows in 
                   this table, and the only valid index for this 
                   table is 1.  It is only a table so that we may 
                   take advantage of the RowStatus textual convention
                   for configuring the download parameters."
           ::= { hpicfDownload 1 }
       
       hpicfDownloadEntry OBJECT-TYPE
           SYNTAX     HpicfDownloadEntry
           ACCESS     not-accessible
           STATUS     mandatory
           DESCRIPTION
                   "The row in the hpicfDownloadTable containing the 
                   download parameters."
           INDEX      { hpicfDownloadIndex }
           ::= { hpicfDownloadTable 1 }
       
       HpicfDownloadEntry ::=
           SEQUENCE {
               hpicfDownloadIndex              INTEGER,
               hpicfDownloadOwnerAddress       TAddress,
               hpicfDownloadOwnerDomain        OBJECT IDENTIFIER,
               hpicfDownloadTAddress           TAddress,
               hpicfDownloadTDomain            OBJECT IDENTIFIER,
               hpicfDownloadFilename           DisplayString,
               hpicfDownloadResetType          INTEGER,
               hpicfDownloadErrorStatus        INTEGER,
               hpicfDownloadErrorText          DisplayString,
               hpicfDownloadStatus             RowStatus
           }
       
       hpicfDownloadIndex OBJECT-TYPE
           SYNTAX     INTEGER {
                          dlInstance(1)
                      }
           ACCESS     read-only
           STATUS     mandatory
           DESCRIPTION
                   "The index which uniquely identifies this row.  
                   The only legal value for this object is 1."
           ::= { hpicfDownloadEntry 1 }
       
       hpicfDownloadOwnerAddress OBJECT-TYPE
           SYNTAX     TAddress
           ACCESS     read-only
           STATUS     mandatory
           DESCRIPTION
                   "The transport address of the management station 
                   that initiated this download attempt, formatted 
                   according to the value of the associated instance 
                   of hpicfDownloadOwnerDomain."
           ::= { hpicfDownloadEntry 2 }
       
       hpicfDownloadOwnerDomain  OBJECT-TYPE
           SYNTAX     OBJECT IDENTIFIER
           ACCESS     read-only
           STATUS     mandatory
           DESCRIPTION
                   "The kind of transport service used by the 
                   management station that initiated this download 
                   attempt."
           ::= { hpicfDownloadEntry 3 }
       
       hpicfDownloadTAddress OBJECT-TYPE
           SYNTAX     TAddress
           ACCESS     read-write
           STATUS     mandatory
           DESCRIPTION
                   "The transport address of the node to download 
                   firmware from, formatted according to the value of
                   the associated instance of hpicfDownloadTDomain.
       
                   An attempt to modify this value will fail if the 
                   associated hpicfDownloadStatus object would be 
                   equal to 'active' both before and after the 
                   modification attempt."
           ::= { hpicfDownloadEntry 4 }
       
       hpicfDownloadTDomain OBJECT-TYPE
           SYNTAX     OBJECT IDENTIFIER
           ACCESS     read-write
           STATUS     mandatory
           DESCRIPTION
                   "The kind of transport service to be used for the 
                   download.  Currently supports snmpUDPDomain and 
                   snmpIPXDomain.
       
                   An attempt to modify this value will fail if the 
                   associated hpicfDownloadStatus object would be 
                   equal to 'active' both before and after the 
                   modification attempt."
           ::= { hpicfDownloadEntry 5 }
       
       hpicfDownloadFilename OBJECT-TYPE
           SYNTAX     DisplayString (SIZE(0..63))
           ACCESS     read-write
           STATUS     mandatory
           DESCRIPTION
                   "Filename and path of file to download (maximum 
                   length of 63 characters + NULL).
       
                   An attempt to modify this value will fail if the 
                   associated hpicfDownloadStatus object would be 
                   equal to 'active' both before and after the 
                   modification attempt."
           ::= { hpicfDownloadEntry 6 }
       
       hpicfDownloadResetType OBJECT-TYPE
           SYNTAX     INTEGER {
                          noReset(1),
                          warmReset(2),
                          factoryReset(3)
                      }
           ACCESS     read-write
           STATUS     mandatory
           DESCRIPTION
                   "The type of reset to perform after completion of
                   the firmware download.  Note that not all agents
                   will support all possible values, and there may
                   be other agent-specific values for this object."
           ::= { hpicfDownloadEntry 7 }
       
       hpicfDownloadErrorStatus OBJECT-TYPE
           SYNTAX     INTEGER {
                          fileNotFound(1),
                          accessViolation(2),
                          diskFull(3),
                          illegalOperation(4),
                          unknownTID(5),
                          fileExists(6),
                          noSuchUser(7),
                          notDefined(8),
                          corruptFile(9),
                          noServer(10),
                          tftpTimeout(11),
                          hardwareError(12),
                          success(13),
                          aborted(14),
                          inProgress(15),
                          idle(16),
                          erasingEeprom(17),
                          incompleteFirmware(18),
                          requirePowerCycle(19),
                          cannotUpgrade(20),
                          cannotDowngrade(21)
                      }
           ACCESS     read-only
           STATUS     mandatory
           DESCRIPTION
                   "Status of download.  The first seven codes are 
                   equal to the codes defined by the TFTP protocol.
                   'notDefined' is the same as TFTP protocol error 0.
                   The following are the other possible values for this
                   object:

                     corruptFile        - the agent detected a problem
                                          with the download file format.
                     noServer           - the TFTP server at
                                          hpicfDownloadTAddress did not
                                          respond to the TFTP request.
                     tftpTimeout        - the download was aborted due
                                          to excessive timeouts. 
                     hardwareError      - there was a hardware problem
                                          on the agent that forced an
                                          abort of the download (see
                                          hpicfDownloadErrorText for
                                          more detailed information).
                     success            - the download has completed
                                          successfully.
                     aborted            - the download was aborted by
                                          setting the
                                          hpicfDownloadStatus to
                                          'notInService' or 'delete'.
                     inProgress         - the TFTP transfer is currently
                                          active.
                     idle               - means that the download has
                                          not yet started (i.e. the
                                          value of hpicfDownloadStatus
                                          has not yet been set to
                                          'active').
                     erasingEeprom      - the agent is currently erasing
                                          the EEPROM device.  Currently
                                          only used on JetDirect agents.
                     incompleteFirmware - the agent is running an
                                          incomplete version of firmware
                                          and requires a download.
                                          Currently only used on
                                          JetDirect agents.
                     requirePowerCycle  - the agent must be power cycled
                                          to run the newly downloaded
                                          firmware.  Currently only used
                                          on JetDirect agents.
                     cannotUpgrade      - the agent's current firmware
                                          revision cannot be upgraded to
                                          the revision in the download
                                          file.
                     cannotDowngrade    - the agent's current firmware
                                          revision cannot be downgraded
                                          to the revision in the
                                          download file."
           ::= { hpicfDownloadEntry 8 }
       
       hpicfDownloadErrorText OBJECT-TYPE
           SYNTAX     DisplayString (SIZE (0..255))
           ACCESS     read-only
           STATUS     mandatory
           DESCRIPTION
                   "A textual description of the current error status
                   of the firmware download."
           ::= { hpicfDownloadEntry 9 }

       hpicfDownloadStatus OBJECT-TYPE
           SYNTAX     RowStatus
           ACCESS     read-write
           STATUS     mandatory
           DESCRIPTION
                   "The status of this download entry.  This object
                   may not be set to 'active' unless the following 
                   columnar objects exist in this row: 
                   hpicfDownloadTAddress, hpicfDownloadTDomain,
                   hpicfDownloadFilename, and 
                   hpicfDownloadResetType."
           ::= { hpicfDownloadEntry 10 }

       hpicfDownloadLogMaxSize OBJECT-TYPE
           SYNTAX     INTEGER
           ACCESS     read-only
           STATUS     mandatory
           DESCRIPTION
                   "The maximum number of the download log entries
                   supported by this agent.  Note that 0 is a 
                   legal value for this variable."
           ::= { hpicfDownload 2 }

       hpicfDownloadLogSize OBJECT-TYPE
           SYNTAX     Gauge
           ACCESS     read-only
           STATUS     mandatory
           DESCRIPTION
                   "The number of download log entries currently in
                   the hpicfDownloadLogTable."
           ::= { hpicfDownload 3 }

       hpicfDownloadLogTable OBJECT-TYPE
           SYNTAX     SEQUENCE OF HpicfDownloadLogEntry
           ACCESS     not-accessible
           STATUS     mandatory
           DESCRIPTION
                   "A log of the hpicfDownloadSize most recent 
                   download attempts to this device.  The first entry
                   in the table is the oldest."
           ::= { hpicfDownload 4 }

       hpicfDownloadLogEntry OBJECT-TYPE
           SYNTAX     HpicfDownloadLogEntry
           ACCESS     not-accessible
           STATUS     mandatory
           DESCRIPTION
                   "An entry in the hpicfDownloadLogTable containing
                   information about a single download attempt."
           INDEX      { hpicfDlLogIndex }
           ::= { hpicfDownloadLogTable 1 }
       
       HpicfDownloadLogEntry ::=
           SEQUENCE {
               hpicfDlLogIndex                 INTEGER,
               hpicfDlLogOwnerAddress          TAddress,
               hpicfDlLogOwnerDomain           OBJECT IDENTIFIER,
               hpicfDlLogTAddress              TAddress,
               hpicfDlLogTDomain               OBJECT IDENTIFIER,
               hpicfDlLogFilename              DisplayString,
               hpicfDlLogResetType             INTEGER,
               hpicfDlLogErrorStatus           INTEGER,
               hpicfDlLogErrorText             DisplayString
           }

       hpicfDlLogIndex OBJECT-TYPE
           SYNTAX     INTEGER
           ACCESS     read-only
           STATUS     mandatory
           DESCRIPTION
                   "The index of this entry in the download log 
                   table.  Index 1 will always contain the oldest
                   entry.  If the table is full when a download
                   attempt is made, the new entry becomes the last
                   entry (hpicfDownloadLogMaxSize), and all earlier
                   entries are shifted down by one entry, removing
                   the old index 1."
           ::= { hpicfDownloadLogEntry 1 }
       
       hpicfDlLogOwnerAddress OBJECT-TYPE
           SYNTAX     TAddress
           ACCESS     read-only
           STATUS     mandatory
           DESCRIPTION
                   "The transport address of the management station 
                   that attempted to initiate a download of this
                   device, formatted according to the value of 
                   hpicfDlLastOwnerDomain."
           ::= { hpicfDownloadLogEntry 2 }
       
       hpicfDlLogOwnerDomain OBJECT-TYPE
           SYNTAX     OBJECT IDENTIFIER
           ACCESS     read-only
           STATUS     mandatory
           DESCRIPTION
                   "The kind of transport service used by the 
                   management station that attempted to initiate a 
                   download of this device."
           ::= { hpicfDownloadLogEntry 3 }
       
       hpicfDlLogTAddress OBJECT-TYPE
           SYNTAX     TAddress
           ACCESS     read-only
           STATUS     mandatory
           DESCRIPTION
                   "The transport address of the node from which this
                   device attempted to download firmware, formatted 
                   according to the value of hpicfDlLastTDomain."
           ::= { hpicfDownloadLogEntry 4 }
       
       hpicfDlLogTDomain OBJECT-TYPE
           SYNTAX     OBJECT IDENTIFIER
           ACCESS     read-only
           STATUS     mandatory
           DESCRIPTION
                   "The kind of transport service which was used for 
                   the attempt to download firmware to this device."
           ::= { hpicfDownloadLogEntry 5 }
       
       hpicfDlLogFilename OBJECT-TYPE
           SYNTAX     DisplayString (SIZE(0..63))
           ACCESS     read-only
           STATUS     mandatory
           DESCRIPTION
                   "The filename from which this device attempted to
                   download firmware."
           ::= { hpicfDownloadLogEntry 6 }
       
       hpicfDlLogResetType OBJECT-TYPE
           SYNTAX     INTEGER {
                          noReset(1),
                          warmReset(2),
                          factoryReset(3)
                      }
           ACCESS     read-only
           STATUS     mandatory
           DESCRIPTION
                   "The type of reset requested to be  performed
                   after completion of the firmware download 
                   attempt."
           ::= { hpicfDownloadLogEntry 7 }
       
       hpicfDlLogErrorStatus OBJECT-TYPE
           SYNTAX     INTEGER {
                          fileNotFound(1),
                          accessViolation(2),
                          diskFull(3),
                          illegalOperation(4),
                          unknownTID(5),
                          fileExists(6),
                          noSuchUser(7),
                          notDefined(8),
                          corruptFile(9),
                          noServer(10),
                          tftpTimeout(11),
                          hardwareError(12),
                          success(13),
                          aborted(14)
                      }
           ACCESS     read-only
           STATUS     mandatory
           DESCRIPTION
                   "The result of the attempt to download firmware to
                   this device.  The values are the same as the 
                   corresponding values of hpicfDownloadErrorStatus."
           ::= { hpicfDownloadLogEntry 8 }
       
       hpicfDlLogErrorText OBJECT-TYPE
           SYNTAX     DisplayString (SIZE (0..255))
           ACCESS     read-only
           STATUS     mandatory
           DESCRIPTION
                   "A textual description of the final error status 
                   of the attempt to download firmware to this 
                   device."
           ::= { hpicfDownloadLogEntry 9 }
       
       -- HP ICF Basic group
       
       hpicfBasic   OBJECT IDENTIFIER ::= { hpicfCommon 4 }

       hpicfReset OBJECT-TYPE
           SYNTAX     INTEGER {
                          noReset(1),
                          normalReset(2),
                          factoryReset(3)
                      }
           ACCESS     read-write
           STATUS     mandatory
           DESCRIPTION
                   "When this object is set to to 'normalReset' it 
                   results in a 'warm' reset, which does not clear 
                   the parameters in NOVRAM to factory defaults. When
                   set to 'factoryReset', it results in NOVRAM being set
                   to factory defaults. When this object is set, the 
                   agent replies, dallies a short time to allow the 
                   reply to be emitted from the device, then performs
                   the reset.  When read, this object always returns 
                   'noReset'."
           ::= { hpicfBasic 1 }

       hpicfSelfTest OBJECT-TYPE
           SYNTAX     INTEGER {
                          stSuccess(1),
                          stExecute(2)
                      }
           ACCESS     read-write
           STATUS     mandatory
           DESCRIPTION
                   "Self test is invoked by setting this flag to 
                   'stExecute'. When the object changes to 'stSuccess',
                   the test has completed successfully.  Icf devices
                   will 'hard-fail' if the test does not succeed."
           ::= { hpicfBasic 2 }

       -- HP ICF 802.3 Repeater Objects
       
       hpicfRepeater      OBJECT IDENTIFIER ::= { hpicfObjects 2 }
       hpRptrBasic        OBJECT IDENTIFIER ::= { hpicfRepeater 1 }
       hpRptrBasicGlobal  OBJECT IDENTIFIER ::= { hpRptrBasic 1 }
       
       hpRptrEntityName OBJECT-TYPE
           SYNTAX     DisplayString (SIZE (0..15))
           ACCESS     read-only
           STATUS     mandatory
           DESCRIPTION
                   "The local name of this repeater.  This is the 
                   same value as hpicfEntityName in the case where 
                   there is Distributed Management Protocol to access
                   this device.
       
                   For SNMPv1, this name is appended to the agent 
                   community name to obtain a community name to use
                   to specify that the agent should proxy to this
                   repeater.  For example, if this agent has a 
                   community with a community name of 'public', and
                   the value of this object is 'repeater1', the 
                   community 'public/repeater1' will specify that the
                   agent should proxy to the public community of the
                   repeater1 box to obtain management information
                   about this repeater.
       
                   If an agent receives a management request where 
                   the localEntity is not specified, it will default 
                   to the local repeater on which this agent is 
                   executing."
           ::= { hpRptrBasicGlobal 1 }
       
       hpRptrThinlanFault OBJECT-TYPE
           SYNTAX     TruthValue
           ACCESS     read-write
           STATUS     mandatory
           DESCRIPTION
                   "When set to 'true' this object causes the Fault 
                   Led to blink if the ThinLan Port is segmented."
           ::= { hpRptrBasicGlobal 2 }
       
       hpRptrSqeEnabled OBJECT-TYPE
           SYNTAX     TruthValue
           ACCESS     read-only
           STATUS     mandatory
           DESCRIPTION
                   "When 'true', this flag indicates that SQE has 
                   been detected for the last ten agent transmits and
                   there is a high probability that the SQE switch on
                   the transceiver attached to the AUI port is set to
                   Enabled, when it should be Disabled."
           ::= { hpRptrBasicGlobal 3 }
       
       hpRptrRobustHealing OBJECT-TYPE
           SYNTAX     TruthValue
           ACCESS     read-write
           STATUS     mandatory
           DESCRIPTION
                   "When this flag is set to 'true', it enables 
                   robust port healing mode.  The 802.3 specification
                   states that a segmented port is healed by 
                   successfully transmitting or receiving a packet on
                   the port.  This mode disables port healing on 
                   successful packet reception and requires that a 
                   packet be successfully transmitted on a port in 
                   order for a segmented port to be healed.

                   Note that it is illegal to set this variable to 
                   'true' on a repeater that does not have a local 
                   network management agent."
           ::= { hpRptrBasicGlobal 4 }
       
       hpRptrBasicGroup  OBJECT IDENTIFIER ::= { hpRptrBasic 2 }
       
       hpRptrBasicGroupTable OBJECT-TYPE
           SYNTAX     SEQUENCE OF HpRptrBasicGroupEntry
           ACCESS     not-accessible
           STATUS     mandatory
           DESCRIPTION
                   "HP specific extensions to the rptrGroupTable."
           ::= { hpRptrBasicGroup 1 }
       
       hpRptrBasicGroupEntry OBJECT-TYPE
           SYNTAX     HpRptrBasicGroupEntry
           ACCESS     not-accessible
           STATUS     mandatory
           DESCRIPTION
                   "An entry in the table, containing HP extensions 
                   for a specific group."
           INDEX      { hpRptrGrpGroupIndex }
           ::= { hpRptrBasicGroupTable 1 }
       
       HpRptrBasicGroupEntry ::=
           SEQUENCE {
               hpRptrGrpGroupIndex             INTEGER,
               hpRptrGrpPortsAdminStatus       OCTET STRING,
               hpRptrGrpPortsSegStatus         OCTET STRING,
               hpRptrGrpPortsMediaAvailable    OCTET STRING,
               hpRptrGrpPortsLinkbeatEnabled   OCTET STRING,
               hpRptrGrpPortsOperStatus        OCTET STRING
           }
       
       hpRptrGrpGroupIndex OBJECT-TYPE
           SYNTAX     INTEGER (1..1024)
           ACCESS     read-only
           STATUS     mandatory
           DESCRIPTION
                   "The group within the repeater for which this 
                   entry contains information.  This object has the 
                   same value as the corresponding instance of 
                   rptrGroupIndex."
           ::= {  hpRptrBasicGroupEntry 1 }
       
       hpRptrGrpPortsAdminStatus OBJECT-TYPE
           SYNTAX     OCTET STRING (SIZE (1..128))
           ACCESS     read-only
           STATUS     mandatory
           DESCRIPTION
                   "The hpRptrGrpPortsAdminStatus is a bit map of the
                   state of the rptrPortAdminStatus object for all
                   of the ports in this group.  The object  has a one
                   bit for each port for which the value of
                   rptrPortAdminStatus is equal to 'enabled(1)' and
                   a zero bit for each port for which the value of
                   rptrPortAdminStatus is equal to 'disabled(2)'.

                   The bits are placed into the OCTET STRING in the 
                   following order:
       
                       octet   0  octet    1  octet     2  ...
                       bits  7-0  bits   7-0  bits    7-0  ...
                       ports 1-8  ports 9-16  ports 17-24  ...
       
                   Values of unused bits in the last octet are 
                   undefined."
           ::= { hpRptrBasicGroupEntry 2 }
       
       hpRptrGrpPortsSegStatus OBJECT-TYPE
           SYNTAX     OCTET STRING (SIZE (1..128))
           ACCESS     read-only
           STATUS     mandatory
           DESCRIPTION
                   "The hpRptrGrpPortsSegStatus is a bit map of the 
                   state of the rptrPortAutoPartitionState of all of
                   the ports in this group.  The object  has a one
                   bit for each port for which the value of
                   rptrPortAutoPartitionState is equal to 
                   'notAutoPartitioned(1)' and a zero bit for each
                   port for which the value of 
                   rptrPortAutoPartitionState is equal to 
                   'autoPartitioned(2)'.

                   The bits are placed into the OCTET STRING in the 
                   following order:
       
                       octet   0  octet    1  octet     2  ...
                       bits  7-0  bits   7-0  bits    7-0  ...
                       ports 1-8  ports 9-16  ports 17-24  ...
       
                   Values of unused bits in the last octet are 
                   undefined."
           ::= { hpRptrBasicGroupEntry 3 }
       
       hpRptrGrpPortsMediaAvailable OBJECT-TYPE
           SYNTAX     OCTET STRING (SIZE (1..128))
           ACCESS     read-only
           STATUS     mandatory
           DESCRIPTION
                   "The hpRptrGrpPortsMediaAvailable is a bit map of 
                   the state of the rpMauMediaAvailable object for 
                   all of the ports in this group.  The object has a 
                   one bit for each port for which the value of
                   rpMauMediaAvailable is equal to 'available(3)'
                   and a zero bit for each port for which the value
                   of rpMauMediaAvailable is not equal to
                   'available(3)'.

                   The bits are placed into the OCTET STRING in the 
                   following order:
       
                       octet   0  octet    1  octet     2  ...
                       bits  7-0  bits   7-0  bits    7-0  ...
                       ports 1-8  ports 9-16  ports 17-24  ...
       
                   Values of unused bits in the last octet are 
                   undefined."
           ::= { hpRptrBasicGroupEntry 4 }
       
       hpRptrGrpPortsLinkbeatEnabled OBJECT-TYPE
           SYNTAX     OCTET STRING (SIZE (1..128))
           ACCESS     read-only
           STATUS     mandatory
           DESCRIPTION
                   "The hpRptrGrpPortsLinkbeatEnabled is a bit map of
                   the state of the hpRptrPtLinkbeatEnable object for
                   all of the ports in this group.  The object  has a
                   one bit for each port for which the value of
                   hpRptrPtLinkbeatEnable is equal to 'true(1)' and
                   a zero bit for each port for which the value of
                   hpRptrPtLinkbeatEnable is equal to 'false(2)'.

                   The bits are placed into the OCTET STRING in the 
                   following order:
       
                       octet   0  octet    1  octet     2  ...
                       bits  7-0  bits   7-0  bits    7-0  ...
                       ports 1-8  ports 9-16  ports 17-24  ...
       
                   Values of unused bits in the last octet are 
                   undefined."
           ::= { hpRptrBasicGroupEntry 5 }
       
       hpRptrGrpPortsOperStatus OBJECT-TYPE
           SYNTAX     OCTET STRING (SIZE (1..128))
           ACCESS     read-only
           STATUS     mandatory
           DESCRIPTION
                   "The hpRptrGrpPortsOperStatus is a bit map of the 
                   state of all hub ports in the group.  The object  
                   has a 1 bit for each port that is enabled, not 
                   segmented, and the media is available.  Ports on 
                   which these conditions are not true have a 0 bit.  
                   The bits are placed into the OCTET STRING in the 
                   following order:
       
                       octet   0  octet    1  octet     2  ...
                       bits  7-0  bits   7-0  bits    7-0  ...
                       ports 1-8  ports 9-16  ports 17-24  ...
       
                   Values of unused bits in the last octet are 
                   undefined."
           ::= { hpRptrBasicGroupEntry 6 }
       
       hpRptrBasicPort   OBJECT IDENTIFIER ::= { hpRptrBasic 3 }
       
       hpRptrBasicPtTable OBJECT-TYPE
           SYNTAX     SEQUENCE OF HpRptrBasicPtEntry
           ACCESS     not-accessible
           STATUS     mandatory
           DESCRIPTION
                   "HP specific extensions to the rptrPortTable."
           ::= { hpRptrBasicPort 1 }
       
       hpRptrBasicPtEntry OBJECT-TYPE
           SYNTAX     HpRptrBasicPtEntry
           ACCESS     not-accessible
           STATUS     mandatory
           DESCRIPTION
                   "An entry in the table, containing HP extensions 
                   for a specific port."
           INDEX      { hpRptrPtGroupIndex, hpRptrPtPortIndex }
           ::= { hpRptrBasicPtTable 1 }
       
       HpRptrBasicPtEntry ::=
           SEQUENCE {
               hpRptrPtGroupIndex              INTEGER,
               hpRptrPtPortIndex               INTEGER,
               hpRptrPtLinkbeatEnable          TruthValue,
               hpRptrPtPolarityReversed        TruthValue
           }
       
       hpRptrPtGroupIndex OBJECT-TYPE
           SYNTAX     INTEGER (1..1024)
           ACCESS     read-only
           STATUS     mandatory
           DESCRIPTION
                   "The group containing the port for which this 
                   entry contains information.  This object has the 
                   same value as the corresponding instance of 
                   rptrPortGroupIndex."
           ::= { hpRptrBasicPtEntry 1 }
       
       hpRptrPtPortIndex OBJECT-TYPE
           SYNTAX     INTEGER (1..1024)
           ACCESS     read-only
           STATUS     mandatory
           DESCRIPTION
                   "The port within the group for which this entry 
                   contains information.  This object has the same 
                   value as the corresponding instance of 
                   rptrPortIndex."
           ::= { hpRptrBasicPtEntry 2 }
       
       hpRptrPtLinkbeatEnable OBJECT-TYPE
           SYNTAX     TruthValue
           ACCESS     read-write
           STATUS     mandatory
           DESCRIPTION
                   "When this flag is set to 'true' the port's link 
                   beat is enabled and when set to 'false' it is 
                   disabled."
           ::= { hpRptrBasicPtEntry 3 }
       
       hpRptrPtPolarityReversed OBJECT-TYPE
           SYNTAX     TruthValue
           ACCESS     read-only
           STATUS     mandatory
           DESCRIPTION
                   "This object is used to indicate that the hub port
                   was wired with the positive/negative polarity of 
                   its transmit and receive pairs reversed.  Note 
                   that the port will continue to operate in this 
                   state, with the hub inverting the polarity 
                   internally."
           ::= { hpRptrBasicPtEntry 4 }
       
       hpRptrMonitor   OBJECT IDENTIFIER ::= { hpicfRepeater 2 }
       
       hpRptrMonitorGlobal OBJECT IDENTIFIER ::= { hpRptrMonitor 1 }
       
       -- Note: The hpRptrMonitorGlobal counters that are composed of
       -- other objects are provided to allow for event testing on 
       -- global error conditions.
       
       hpRptrMonCounters
           OBJECT IDENTIFIER ::= { hpRptrMonitorGlobal 1 }
       
       hpRptrMonGlobalFrames OBJECT-TYPE
           SYNTAX     Counter
           ACCESS     read-only
           STATUS     mandatory
           DESCRIPTION
                   "The total number of frames of valid frame length
                   that have been received on all ports in this
                   repeater.  This counter is the summation  of the
                   values of the rptrMonitorPortReadableFrames 
                   counter for all of the ports in this repeater.
                   Equivalently, this counter is the summation of the
                   values of the rptrMonitorGroupTotalFrames counter 
                   for all of the port groups in this repeater."
           REFERENCE
                   "Reference RFC 1516 rptrMonitorPortReadableFrames
                   and rptrMonitorGroupTotalFrames, and IEEE 802.3 
                   Rptr Mgt, 19.2.6.2, aReadableFrames."
           ::= { hpRptrMonCounters 1 }
       
       hpRptrMonGlobalOctets OBJECT-TYPE
           SYNTAX     Counter
           ACCESS     read-only
           STATUS     mandatory
           DESCRIPTION
                   "The total number of octets contained in the valid
                   frames that have been received on the ports in
                   this repeater.  This counter is the summation of
                   the values of the rptrMonitorPortReadableOctets
                   counter for all of the ports in this repeater.
                   Equivalently, this counter is the summation of the
                   values of the rptrMonitorGroupTotalOctets counter
                   for all of the port groups in this repeater."
           REFERENCE
                   "Reference RFC 1516 rptrMonitorPortReadableOctets
                   and rptrMonitorGroupTotalOctets, and IEEE 802.3
                   Rptr Mgt, 19.2.6.2, aReadableOctets."
           ::= { hpRptrMonCounters 2 }
       
       hpRptrMonGlobalFCSErrors OBJECT-TYPE
           SYNTAX     Counter
           ACCESS     read-only
           STATUS     mandatory
           DESCRIPTION
                   "This counter is incremented by one for each frame
                   received on any port with the FCSError signal
                   asserted and the FramingError and CollisionEvent
                   signals deasserted and whose OctetCount is greater
                   than or equal to minFrameSize and less than or
                   equal to maxFrameSize (Ref: 4.4.2.1, IEEE 802.3 
                   Std).  This counter is the summation of the values
                   of the rptrMonitorPortFCSErrors counter for all of
                   the ports in this repeater."
           REFERENCE
                   "Reference RFC 1516 rptrMonitorPortFCSErrors and
                   IEEE 802.3 Rptr Mgt, 19.2.6.2, 
                   aFrameCheckSequenceErrors."
           ::= { hpRptrMonCounters 3 }
       
       hpRptrMonGlobalAlignmentErrors OBJECT-TYPE
           SYNTAX     Counter
           ACCESS     read-only
           STATUS     mandatory
           DESCRIPTION
                   "This counter is incremented by one for each frame
                   received on any port with the FCSError and
                   FramingError signals asserted and CollisonEvent
                   signal deasserted and whose OctetCount is greater
                   than or equal to minFrameSize and less than or
                   equal to maxFrameSize (Ref: 4.4.2.1, IEEE 802.3
                   Std).  If hpRptrMonGlobalAlignmentErrors is
                   incremented, then the hpRptrMonGlobalFCSErorrs
                   counter shall not be incremented for the same
                   frame.  This counter is the summation of the 
                   values of the rptrMonitorPortAlignmentErrors 
                   counter for all of the ports in this repeater."
           REFERENCE
                   "Reference RFC 1516 rptrMonitorPortAlignmentErrors
                   and IEEE 802.3 Rptr Mgt, 19.2.6.2, 
                   aAlignmentErrors."
           ::= { hpRptrMonCounters 4 }
       
       hpRptrMonGlobalFrameTooLongs OBJECT-TYPE
           SYNTAX     Counter
           ACCESS     read-only
           STATUS     mandatory
           DESCRIPTION
                   "This counter is incremented by one for each frame
                   received on any port whose OctetCount is greater
                   than maxFrameSize (Ref: 4.4.2.1, IEEE 802.3 Std).
                   If hpRptrMonGlobalFrameTooLongs is incremented,
                   then neither the hpRptrMonGlobalAlignmentErorrs 
                   nor the hpRptrMonGlobalFCSErrors counter shall be
                   incremented for the frame.  This counter is the
                   summation of the values of the
                   rptrMonitorPortFrameTooLongs counter for all of
                   the ports in this repeater."
           REFERENCE
                   "Reference RFC 1516 rptrMonitorPortFrameTooLongs
                   and IEEE 802.3 Rptr Mgt, 19.2.6.2, 
                   aFramesTooLong"
           ::= { hpRptrMonCounters 5 }
       
       hpRptrMonGlobalShortEvents OBJECT-TYPE
           SYNTAX     Counter
           ACCESS     read-only
           STATUS     mandatory
           DESCRIPTION
                   "This counter is incremented by one for each
                   CarrierEvent on any port with ActivityDuration
                   less than ShortEventMaxTime.  ShortEventMaxTime is
                   greater than 74 bit times and less than 82 bit
                   times.  ShortEventMaxTime has tolerances included
                   to provide for circuit losses between a
                   conformance test point at the AUI and the
                   measurement point within the state machine.  This 
                   counter is the summation of the values of the
                   rptrMonitorPortShortEvents counter for all of the
                   ports in this repeater."
           REFERENCE
                   "Reference RFC 1516 rptrMonitorPortShortEvents and
                   IEEE 802.3 Rptr Mgt, 19.2.6.2, aShortEvents."
           ::= { hpRptrMonCounters 6 }
       
       hpRptrMonGlobalRunts OBJECT-TYPE
           SYNTAX     Counter
           ACCESS     read-only
           STATUS     mandatory
           DESCRIPTION
                   "This counter is incremented by one for each
                   CarrierEvent on any port that meets one of the
                   following two conditions.  Only one test need be
                   made.  a) The ActivityDuration is greater than
                   ShortEventMaxTime and less than ValidPacketMinTime
                   and the CollisionEvent signal is deasserted.  b)
                   The OctetCount is less than 64, the 
                   ActivityDuration is greater than ShortEventMaxTime
                   and the CollisionEvent signal is deasserted.
                   ValidPacketMinTime is greater than or equal to 552
                   bit times but less than 565 bit times.

                   An event whose length is greater than 74 bit times
                   but less than 82 bit times shall increment either
                   the hpRptrMonGlobalShortEvents counter or the
                   hpRptrMonGlobalRunts counter but not both.  A
                   CarrierEvent greater than or equal to 552 bit
                   times but less than 565 bit times may or may not
                   increment the hpRptrMonGlobalRunts counter.
                   ValidPacketMinTime has tolerances included to 
                   provide for circuit losses between a conformance
                   test point at the AUI and the measurement point
                   within the state machine.  
 
                   Runts usually indicate collision fragments, a 
                   normal network event.  This counter is the
                   summation of the values of the 
                   rptrMonitorPortRunts counter for all of the ports
                   in this repeater."
           REFERENCE
                   "Reference RFC 1516 rptrMonitorPortRunts and
                   IEEE 802.3 Rptr Mgt, 19.2.6.2, aRunts."
           ::= { hpRptrMonCounters 7 }

       hpRptrMonGlobalCollisions OBJECT-TYPE
           SYNTAX     Counter
           ACCESS     read-only
           STATUS     mandatory
           DESCRIPTION
                   "This counter is incremented by one for any
                   CarrierEvent signal on any port for which the
                   CollisionEvent signal on any port is asserted.

                   This counter differs from 
                   rptrMonitorTransmitCollisions in that it counts
                   all collisions seen by this repeater, even those
                   involving only a single port on this repeater,
                   whereas rptrMonitorTransmitCollisions counts only
                   collisions involving multiple ports on this
                   repeater."
           REFERENCE
                   "Reference RFC 1516 rptrMonitorPortCollisions and
                   IEEE 802.3 Rptr Mgt, 19.2.6.2, aCollisions."
           ::= { hpRptrMonCounters 8 }

       hpRptrMonGlobalLateEvents OBJECT-TYPE
           SYNTAX     Counter
           ACCESS     read-only
           STATUS     mandatory
           DESCRIPTION
                   "This counter is incremented by one for each
                   CarrierEvent on any port in which the CollIn(X)
                   variable transitions to the value SQE (Ref:
                   9.6.6.2, IEEE 802.3 Std) while the
                   ActivityDuration is greater than the 
                   LateEventThreshold.  Such a CarrierEvent is
                   counted twice, as both hpRptrMonGlobalCollisions
                   and hpRptrMonGlobalLateEvents.  The 
                   LateEventThreshold is greater than 480 bit times
                   and less than 565 bit times.  LateEventThreshold
                   has tolerances included to permit an 
                   implementation to build a single threshold to
                   serve as both the LateEventThreshold and
                   ValidPacketMinTime threshold.  This counter is the
                   summation of the values of the 
                   rptrMonitorPortLateEvents counter for all of the
                   ports in this repeater."
           REFERENCE
                   "Reference RFC 1516 rptrMonitorPortLateEvents and
                   IEEE 802.3 Rptr Mgt, 19.2.6.2, aLateEvents."
           ::= { hpRptrMonCounters 9 }
       
       hpRptrMonGlobalVeryLongEvents OBJECT-TYPE
           SYNTAX     Counter
           ACCESS     read-only
           STATUS     mandatory
           DESCRIPTION
                   "This counter is incremented by one for each 
                   CarrierEvent on any port whose ActivityDuration is
                   greater than the MAU Jabber Lockup Protection 
                   timer TW3 (Ref: 9.6.1 & 9.6.5, IEEE 802.3 Std).
                   Other counters may be incremented as appropriate.
                   This counter is the summation of the values of the
                   rptrMonitorPortVeryLongEvents counter for all of
                   the ports in this repeater."
           REFERENCE
                   "Reference RFC 1516 rptrMonitorPortVeryLongEvents
                   and IEEE 802.3 Rptr Mgt, 19.2.6.2, 
                   aVeryLongEvents."
           ::= { hpRptrMonCounters 10 }
       
       hpRptrMonGlobalDataRateMismatches OBJECT-TYPE
           SYNTAX     Counter
           ACCESS     read-only
           STATUS     mandatory
           DESCRIPTION
                   "This counter is incremented by one for each frame
                   received on any port that meets all of the
                   following conditions:  a) The CollisionEvent
                   signal is not asserted.  b) The ActivityDuration
                   is greater than ValidPacketMinTime.  c) The
                   frequency (data rate) is detectably mismatched 
                   from the local transmit frequency.  The exact
                   degree of mismatch is vendor specific and is to be
                   defined by the vendor for conformance testing.
                   When this event occurs, other counters whose
                   increment conditions were satisfied may or may not
                   also be incremented.  This counter is the 
                   summation of the values of the 
                   rptrMonitorPortDatRateMismatches counter for all
                   of the ports in this repeater."
           REFERENCE
                   "Reference RFC 1516 
                   rptrMonitorPortDataRateMismatches and IEEE 802.3
                   Rptr Mgt, 19.2.6.2, aDataRateMismatches."
           ::= { hpRptrMonCounters 11 }
       
       hpRptrMonGlobalAutoPartitions OBJECT-TYPE
           SYNTAX     Counter
           ACCESS     read-only
           STATUS     mandatory
           DESCRIPTION
                   "This counter is incremented by one for each time
                   the repeater has automatically partitioned any
                   port.  The conditions that cause port partitioning
                   are specified in the partition state machine in
                   Section 9 of the IEEE 802.3 Std.  This counter is
                   the summation of the values of the 
                   rptrMonitorPortAutoPartitions for all of the ports
                   in this repeater."
           REFERENCE
                   "Reference RFC 1516 rptrMonitorPortAutoPartitions
                   and IEEE 802.3 Rptr Mgt, 19.2.6.2, 
                   aAutoPartitions."
           ::= { hpRptrMonCounters 12 }
       
       hpRptrMonGlobalErrors OBJECT-TYPE
           SYNTAX     Counter
           ACCESS     read-only
           STATUS     mandatory
           DESCRIPTION
                   "The total number of errors which have occured
                   on any port in this repeater.  This counter is
                   the summation of the values of other error 
                   counters, namely:

                       hpRptrMonGlobalFCSErrors,
                       hpRptrMonGlobalAlignmentErrors,
                       hpRptrMonGlobalFrameTooLongs,
                       hpRptrMonGlobalShortEvents,
                       hpRptrMonGlobalLateEvents,
                       hpRptrMonGlobalVeryLongEvents, and
                       hpRptrMonGlobalDataRateMismatches.

                   Equivalently, this counter is the summation of
                   the values of the rptrMonitorPortTotalErrors
                   counter for all of the ports in this repeater, or
                   it is the summation of the values of
                   rptrMonitorGroupTotalErrors for all of the port
                   groups in this repeater."
           REFERENCE
                   "RFC 1516, rptrMonitorGroupTotalErrors and
                   hpRptrMonitorPortTotalErrors."
           ::= { hpRptrMonCounters 13 }
       
       hpRptrMonGlobalUcastPackets OBJECT-TYPE
           SYNTAX     Counter
           ACCESS     read-only
           STATUS     mandatory
           DESCRIPTION
                   "This counter is incremented by one for each 
                   unicast packet of valid frame length received on 
                   any port.  This counter is the summation of 
                   hpRptrMonPortUcastPackets for all of the ports
                   in this repeater.  This counter may not be
                   implemented for repeaters which do not have a 
                   local network management agent."
           ::= { hpRptrMonCounters 14 }
       
       hpRptrMonGlobalBcastPackets OBJECT-TYPE
           SYNTAX     Counter
           ACCESS     read-only
           STATUS     mandatory
           DESCRIPTION
                   "This counter is incremented by one for each 
                   broadcast packet of valid frame length received on
                   any port.  This counter is the summation of
                   hpRptrMonPortBcastPackets for all of the ports
                   in this repeater.  This counter may not be
                   implemented for repeaters which do not have a 
                   local network management agent."
           ::= { hpRptrMonCounters 15 }
       
       hpRptrMonGlobalMcastPackets OBJECT-TYPE
           SYNTAX     Counter
           ACCESS     read-only
           STATUS     mandatory
           DESCRIPTION
                   "This counter is incremented by one for each 
                   multicast packet of valid frame length received on
                   any port.  This counter is the summation of
                   hpRptrMonPortMcastPackets for all of the ports in
                   this repeater.  This counter may not be 
                   implemented for repeaters which do not have a 
                   local network management agent."
           ::= { hpRptrMonCounters 16 }
       
       hpRptrMonitorGroup
           OBJECT IDENTIFIER ::= { hpRptrMonitor 2 } -- unused
       
       hpRptrMonitorPort
           OBJECT IDENTIFIER ::= { hpRptrMonitor 3 }
       
       hpRptrMonPtTable OBJECT-TYPE
           SYNTAX     SEQUENCE OF HpRptrMonPtEntry
           ACCESS     not-accessible
           STATUS     mandatory
           DESCRIPTION
                   "Table of HP specific per port monitor objects."
           ::= { hpRptrMonitorPort 1 }
       
       hpRptrMonPtEntry OBJECT-TYPE
           SYNTAX     HpRptrMonPtEntry
           ACCESS     not-accessible
           STATUS     mandatory
           DESCRIPTION
                   "An entry in the table, containing per port 
                   objects for a single port."
           INDEX     { hpRptrMonPtGroupIndex, hpRptrMonPtPortIndex }
           ::= { hpRptrMonPtTable 1 }
       
       HpRptrMonPtEntry ::=
           SEQUENCE {
               hpRptrMonPtGroupIndex           INTEGER,
               hpRptrMonPtPortIndex            INTEGER,
               hpRptrMonPtUcastPackets         Counter,
               hpRptrMonPtBcastPackets         Counter,
               hpRptrMonPtMcastPackets         Counter
           }
       
       hpRptrMonPtGroupIndex OBJECT-TYPE
           SYNTAX     INTEGER (1..1024)
           ACCESS     read-only
           STATUS     mandatory
           DESCRIPTION
                   "The group containing the port for which this 
                   entry contains information.  This object has the 
                   same value as the corresponding instance of 
                   rptrMonitorPortGroupIndex."
           ::= { hpRptrMonPtEntry 1 }
       
       hpRptrMonPtPortIndex OBJECT-TYPE
           SYNTAX     INTEGER (1..1024)
           ACCESS     read-only
           STATUS     mandatory
           DESCRIPTION
                   "The port within the group for which this entry 
                   contains information.  This object has the same 
                   value as the corresponding instance of 
                   rptrMonitorPortIndex."
           ::= { hpRptrMonPtEntry 2 }
       
       hpRptrMonPtUcastPackets OBJECT-TYPE
           SYNTAX     Counter
           ACCESS     read-only
           STATUS     mandatory
           DESCRIPTION
                   "This counter is incremented by one for each 
                   unicast packet of valid frame length received on 
                   this port.  This object may not be implemented for
                   repeaters which do not have a local network 
                   management agent."
           ::= { hpRptrMonPtEntry 3 }
       
       hpRptrMonPtBcastPackets OBJECT-TYPE
           SYNTAX     Counter
           ACCESS     read-only
           STATUS     mandatory
           DESCRIPTION
                   "This counter is incremented by one for each 
                   broadcast packet of valid frame length received on
                   this port.  This object may not be implemented for
                   repeaters which do not have a local network 
                   management agent."
           ::= { hpRptrMonPtEntry 4 }
       
       hpRptrMonPtMcastPackets OBJECT-TYPE
           SYNTAX     Counter
           ACCESS     read-only
           STATUS     mandatory
           DESCRIPTION
                   "This counter is incremented by one for each 
                   multicast packet of valid frame length received on
                   this port.  This object may not be implemented for
                   repeaters which do not have a local network 
                   management agent."
           ::= { hpRptrMonPtEntry 5 }
       
       hpRptrAddrTrack     OBJECT IDENTIFIER ::= { hpicfRepeater 3 }

       hpRptrAddrTrkGlobal OBJECT IDENTIFIER ::= { hpRptrAddrTrack 1 }
       -- currently unused

       hpRptrAddrTrkGroup OBJECT IDENTIFIER ::= { hpRptrAddrTrack 2 }
       -- currently unused

       hpRptrAddrTrkPort  OBJECT IDENTIFIER ::= { hpRptrAddrTrack 3 }
       -- currently unused

       -- HP ICF 100BaseVG Repeater Objects

       hpicfVg            OBJECT IDENTIFIER ::= { hpicfObjects 3 }
       hpVgBasic          OBJECT IDENTIFIER ::= { hpicfVg 1 }
       hpVgBasicGlobal    OBJECT IDENTIFIER ::= { hpVgBasic 1 }

       hpVgEntityName OBJECT-TYPE
           SYNTAX     DisplayString (SIZE (0..15))
           ACCESS     read-only
           STATUS     mandatory
           DESCRIPTION
                   "The local name of this 100BaseVG repeater.  This is
                   the same value as hpicfEntityName in the case where 
                   there is Distributed Management Protocol to access
                   this device.

                   For SNMPv1, this name is appended to the agent 
                   community name to obtain a community name to use
                   to specify that the agent should proxy to this
                   repeater.  For example, if this agent has a 
                   community with a community name of 'public', and
                   the value of this object is 'repeater1', the 
                   community 'public/repeater1' will specify that the
                   agent should proxy to the public community of the
                   repeater1 box to obtain management information
                   about this repeater.

                   If an agent receives a management request where 
                   the localEntity is not specified, it will default 
                   to the local repeater on which this agent is 
                   executing."
           ::= { hpVgBasicGlobal 1 }

       hpVgBasicGroup  OBJECT IDENTIFIER ::= { hpVgBasic 2 }

       hpVgBasicGroupTable OBJECT-TYPE
           SYNTAX     SEQUENCE OF HpVgBasicGroupEntry
           ACCESS     not-accessible
           STATUS     mandatory
           DESCRIPTION
                   "HP specific extensions to the vgBasicGroupTable."
           ::= { hpVgBasicGroup 1 }

       hpVgBasicGroupEntry OBJECT-TYPE
           SYNTAX     HpVgBasicGroupEntry
           ACCESS     not-accessible
           STATUS     mandatory
           DESCRIPTION
                   "An entry in the table, containing HP extensions 
                   for a specific group."
           INDEX      { hpVgGrpGroupIndex }
           ::= { hpVgBasicGroupTable 1 }

       HpVgBasicGroupEntry ::=
           SEQUENCE {
               hpVgGrpGroupIndex               INTEGER,
               hpVgGrpPortsAdminStatus         OCTET STRING,
               hpVgGrpPortsTrained             OCTET STRING,
               hpVgGrpPortsInTraining          OCTET STRING,
               hpVgGrpPortsCascaded            OCTET STRING,
               hpVgGrpPortsPromiscuous         OCTET STRING
           }

       hpVgGrpGroupIndex OBJECT-TYPE
           SYNTAX     INTEGER (1..1024)
           ACCESS     not-accessible
           STATUS     mandatory
           DESCRIPTION
                   "The group within the repeater for which this entry 
                   contains information.  This object has the same value
                   as the corresponding instance of icfVgGroupIndex."
           ::= {  hpVgBasicGroupEntry 1 }

       hpVgGrpPortsAdminStatus OBJECT-TYPE
           SYNTAX     OCTET STRING (SIZE (1..128))
           ACCESS     read-only
           STATUS     mandatory
           DESCRIPTION
                   "The hpVgGrpPortsAdminStatus is a bit map of the
                   state of the icfVgPortAdminStatus object for all
                   of the ports in this group.  The object  has a one
                   bit for each port for which the value of
                   icfVgPortAdminStatus is equal to 'enabled(1)' and
                   a zero bit for each port for which the value of
                   icfVgPortAdminStatus is equal to 'disabled(2)'.

                   The bits are placed into the OCTET STRING in the 
                   following order:

                       octet   0  octet    1  octet     2  ...
                       bits  7-0  bits   7-0  bits    7-0  ...
                       ports 1-8  ports 9-16  ports 17-24  ...

                   Values of unused bits in the last octet are 
                   undefined."
           ::= { hpVgBasicGroupEntry 2 }

       hpVgGrpPortsTrained OBJECT-TYPE
           SYNTAX     OCTET STRING (SIZE (1..128))
           ACCESS     read-only
           STATUS     mandatory
           DESCRIPTION
                   "The hpVgGrpPortsTrained is a bit map which indicates
                   which ports in this group are currently online.  The
                   object  has a one bit for each port for which meets
                   the following conditions:

                     1. The value of the corresponding instance of the
                        ifVgPortAdminStatus object is equal to
                        'enabled(1)'.
                     2. The value of the corresponding instance of the
                        icfVgPortStatus object is equal to 'active(1)'. 

                   The object has a zero bit for each port which does
                   not meet the above conditions.

                   The bits are placed into the OCTET STRING in the 
                   following order:

                       octet   0  octet    1  octet     2  ...
                       bits  7-0  bits   7-0  bits    7-0  ...
                       ports 1-8  ports 9-16  ports 17-24  ...

                   Values of unused bits in the last octet are 
                   undefined."
           ::= { hpVgBasicGroupEntry 3 }

       hpVgGrpPortsInTraining OBJECT-TYPE
           SYNTAX     OCTET STRING (SIZE (1..128))
           ACCESS     read-only
           STATUS     mandatory
           DESCRIPTION
                   "The hpVgGrpPortsInTraining is a bit map which
                   indicates which ports in this group are currently in
                   the training state.  The object has a one bit for
                   each port which meets the following conditions:

                     1. The value of the corresponding instance of the
                        ifVgPortAdminStatus object is equal to
                        'enabled(1)'.
                     2. The value of the corresponding instance of the
                        icfVgPortStatus object is equal to 
                        'training(3)'. 

                   The object has a zero bit for each port which does
                   not meet the above conditions.

                   The bits are placed into the OCTET STRING in the 
                   following order:

                       octet   0  octet    1  octet     2  ...
                       bits  7-0  bits   7-0  bits    7-0  ...
                       ports 1-8  ports 9-16  ports 17-24  ...

                   Values of unused bits in the last octet are 
                   undefined."
           ::= { hpVgBasicGroupEntry 4 }

       hpVgGrpPortsCascaded OBJECT-TYPE
           SYNTAX     OCTET STRING (SIZE (1..128))
           ACCESS     read-only
           STATUS     mandatory
           DESCRIPTION
                   "The hpVgGrpPortsCascaded is a bit map which
                   indicates which ports in this group have trained as
                   cascaded repeater ports.  The object has a one bit
                   for each port which meets the following conditions:

                     1. The value of the corresponding instance of the
                        ifVgPortAdminStatus object is equal to
                        'enabled(1)'.
                     2. The value of the corresponding instance of the
                        icfVgPortStatus object is equal to 
                        'active(1)'.
                     3. The value of the corresponding instance of the
                        icfVgPortType object is equal to either
                        'normalInternal(3)' or 'normalExternal(4)'.
                     4. The value of the 'R' bit in the corresponding
                        instance of the icfVgPortTrainingResult object
                        is equal to one.

                   The object has a zero bit for each port which does
                   not meet the above conditions.

                   The bits are placed into the OCTET STRING in the 
                   following order:

                       octet   0  octet    1  octet     2  ...
                       bits  7-0  bits   7-0  bits    7-0  ...
                       ports 1-8  ports 9-16  ports 17-24  ...

                   Values of unused bits in the last octet are 
                   undefined."
           ::= { hpVgBasicGroupEntry 5 }

       hpVgGrpPortsPromiscuous OBJECT-TYPE
           SYNTAX     OCTET STRING (SIZE (1..128))
           ACCESS     read-only
           STATUS     mandatory
           DESCRIPTION
                   "The hpVgGrpPortsPromiscuous is a bit map which
                   indicates which ports in this group have trained for
                   promiscuous operation.  The object has a one bit for
                   each port which meets the following conditions:

                     1. The value of the corresponding instance of the
                        ifVgPortAdminStatus object is equal to
                        'enabled(1)'.
                     2. The value of the corresponding instance of the
                        icfVgPortStatus object is equal to 
                        'active(1)'.
                     3. The value of the corresponding instance of the
                        icfVgPortType object is equal to either
                        'normalInternal(3)' or 'normalExternal(4)'.
                     4. The value of the 'R' bit in the corresponding
                        instance of the icfVgPortTrainingResult object
                        is equal to zero.
                     5. The value of the 'PP' field in the corresponding
                        instance of the icfVgPortTrainingResult object
                        is equal to 01.

                   The object has a zero bit for each port which does
                   not meet the above conditions.

                   The bits are placed into the OCTET STRING in the 
                   following order:

                       octet   0  octet    1  octet     2  ...
                       bits  7-0  bits   7-0  bits    7-0  ...
                       ports 1-8  ports 9-16  ports 17-24  ...

                   Values of unused bits in the last octet are 
                   undefined."
           ::= { hpVgBasicGroupEntry 6 }

       hpVgBasicPort  OBJECT IDENTIFIER ::= { hpVgBasic 3 }

       hpVgBasicPortTable OBJECT-TYPE
           SYNTAX     SEQUENCE OF HpVgBasicPortEntry
           ACCESS     not-accessible
           STATUS     mandatory
           DESCRIPTION
                   "HP specific extensions to the vg port table."
           ::= { hpVgBasicPort 1 }

       hpVgBasicPortEntry OBJECT-TYPE
           SYNTAX     HpVgBasicPortEntry
           ACCESS     not-accessible
           STATUS     mandatory
           DESCRIPTION
                   "HP extended information about a specific vg port."
           INDEX      { hpVgPortGroupIndex, hpVgPortIndex }
           ::= { hpVgBasicPortTable 1 }

       HpVgBasicPortEntry ::=
           SEQUENCE {
               hpVgPortGroupIndex              INTEGER,
               hpVgPortIndex                   INTEGER,
               hpVgPortPolarityReversed        TruthValue,
               hpVgPortWireSkewError           TruthValue
           }

       hpVgPortGroupIndex OBJECT-TYPE
           SYNTAX     INTEGER (1..1024)
           ACCESS     not-accessible
           STATUS     mandatory
           DESCRIPTION
                   "The group that contains the port for which this
                   entry contains information."
           ::= { hpVgBasicPortEntry 1 }

       hpVgPortIndex OBJECT-TYPE
           SYNTAX     INTEGER (1..1024)
           ACCESS     not-accessible
           STATUS     mandatory
           DESCRIPTION
                   "The port within the group for which this entry
                   contains information."
           ::= { hpVgBasicPortEntry 2 }

       hpVgPortPolarityReversed OBJECT-TYPE
           SYNTAX     TruthValue
           ACCESS     read-only
           STATUS     mandatory
           DESCRIPTION
                   "This object is used to indicate that the hub port
                   was wired with the positive/negative polarity of its
                   wire pairs reversed.  Note that the port will
                   continue to operate in this state, with the hub
                   inverting the polarity internally."
           ::= { hpVgBasicPortEntry 3 }

       hpVgPortWireSkewError OBJECT-TYPE
           SYNTAX     TruthValue
           ACCESS     read-only
           STATUS     mandatory
           DESCRIPTION
                   "This object is used to indicate that a wire skew
                   error has been detected on this port."
           ::= { hpVgBasicPortEntry 4 }

       hpVgMonitor   OBJECT IDENTIFIER ::= { hpicfVg 2 }

       hpVgMonitorGlobal OBJECT IDENTIFIER ::= { hpVgMonitor 1 }

       -- Note: The hpVgMonitorGlobal counters that are composed of
       -- other objects are provided to allow for event testing on 
       -- global error conditions.

       hpVgMonCounters OBJECT IDENTIFIER ::= { hpVgMonitorGlobal 1 }

       hpVgMonGlbReadableFrames OBJECT-TYPE
           SYNTAX     Counter
           ACCESS     read-only
           STATUS     mandatory
           DESCRIPTION
                   "This object is the total number of good frames of
                   valid frame length that have been received on all
                   ports in this repeater.  This counter is the
                   summation of the values of the
                   icfVgPortReadableFrames counter for all of the ports
                   in this repeater."
           REFERENCE
                   "Reference IEEE Draft Std. 802.12, 31 October, 1994,
                   13.2.4.5.1, aReadableFramesReceived."
           ::= { hpVgMonCounters 1 }

       hpVgMonGlbReadableOctets OBJECT-TYPE
           SYNTAX     Counter
           ACCESS     read-only
           STATUS     mandatory
           DESCRIPTION
                   "This object is a count of the total number of octets
                   contained in good frames that have been received on
                   all ports in this repeater.  This counter is the
                   summation of the values of the
                   icfVgPortReadableOctets counter for all of the ports
                   in this repeater.

                   Note that this counter may roll over very quickly."
           REFERENCE
                   "Reference IEEE Draft Std. 802.12, 31 October, 1994,
                   13.2.4.5.1, aReadableOctetsReceived."
           ::= { hpVgMonCounters 2 }

       hpVgMonGlbUnreadableOctets OBJECT-TYPE
           SYNTAX     Counter
           ACCESS     read-only
           STATUS     mandatory
           DESCRIPTION
                   "This object is a count of the total number of octets
                   contained in invalid frames that have been received
                   on all ports in this repeater.  This counter is the
                   summation of the values of icfVgPortUnreadableOctets
                   counter for all of the ports in this repeater.

                   Note that this counter may roll over very quickly."
           REFERENCE
                   "Reference IEEE Draft Std. 802.12, 31 October, 1994,
                   13.2.4.5.1, aOctetsInUnreadableFramesRcvd."
           ::= { hpVgMonCounters 3 }

       hpVgMonGlbHighPriorityFrames OBJECT-TYPE
           SYNTAX     Counter
           ACCESS     read-only
           STATUS     mandatory
           DESCRIPTION
                   "This object is a count of the total number of high
                   priority frames that have been received on all ports
                   in this repeater.  This counter is a summation of the
                   values of the icfVgPortHighPriorityFrames counter for
                   all of the ports in this repeater."
           REFERENCE
                   "Reference IEEE Draft Std. 802.12, 31 October, 1994,
                   13.2.4.5.1, aHighPriorityFramesReceived."
           ::= { hpVgMonCounters 4 }

       hpVgMonGlbHighPriorityOctets OBJECT-TYPE
           SYNTAX     Counter
           ACCESS     read-only
           STATUS     mandatory
           DESCRIPTION
                   "This object is a count of the total number of octets
                   contained in high priority frames that have been
                   received on all ports of this repeater.  This counter
                   is a summation of the values of the
                   icfVgPortHighPriorityOctets counter for all of the
                   ports in this repeater.

                   Note that this counter may roll over very quickly."
           REFERENCE
                   "Reference IEEE Draft Std. 802.12, 31 October, 1994,
                   13.2.4.5.1, aHighPriorityOctetsReceived."
           ::= { hpVgMonCounters 5 }

       hpVgMonGlbBroadcastFrames OBJECT-TYPE
           SYNTAX     Counter
           ACCESS     read-only
           STATUS     mandatory
           DESCRIPTION
                   "This object is a count of the total number of
                   broadcast packets that have been received on all
                   ports in this repeater.  This counter is a summation
                   of the values of the icfVgPortBroadcastFrames counter
                   for all of the ports in this repeater."
           REFERENCE
                   "Reference IEEE Draft Std. 802.12, 31 October, 1994,
                   13.2.4.5.1, aBroadcastFramesReceived."
           ::= { hpVgMonCounters 6 }

       hpVgMonGlbMulticastFrames OBJECT-TYPE
           SYNTAX     Counter
           ACCESS     read-only
           STATUS     mandatory
           DESCRIPTION
                   "This object is a count of the total number of
                   multicast packets that have been received on all
                   ports in this repeater.  This counter is a summation
                   of the values of the icfVgPortMulticastFrames counter
                   for all of the ports in this repeater."
           REFERENCE
                   "Reference IEEE Draft Std. 802.12, 31 October, 1994,
                   13.2.4.5.1, aMulticastFramesReceived."
           ::= { hpVgMonCounters 7 }

       hpVgMonGlbIPMFrames OBJECT-TYPE
           SYNTAX     Counter
           ACCESS     read-only
           STATUS     mandatory
           DESCRIPTION
                   "This object is a count of the total number of frames
                   that have been received on all ports in this repeater
                   with an invalid packet marker.  This counter is a
                   summation of the values of the icfVgPortIPMFrames
                   counter for all of the ports in this repeater."
           REFERENCE
                   "Reference IEEE Draft Std. 802.12, 31 October, 1994,
                   13.2.4.5.1, aIPMFramesReceived."
           ::= { hpVgMonCounters 8 }

       hpVgMonGlbDataErrorFrames OBJECT-TYPE
           SYNTAX     Counter
           ACCESS     read-only
           STATUS     mandatory
           DESCRIPTION
                   "This object is a count of the total number of
                   errored frames received on all ports in this
                   repeater.  This counter is a summation of the values
                   of the icfVgPortDataErrorFrames counter for all of
                   the ports in this repeater."
           REFERENCE
                   "Reference IEEE Draft Std. 802.12, 31 October, 1994,
                   13.2.4.5.1, aDataErrorFramesReceived."
           ::= { hpVgMonCounters 9 }

       hpVgMonGlbPriorityPromotions OBJECT-TYPE
           SYNTAX     Counter
           ACCESS     read-only
           STATUS     mandatory
           DESCRIPTION
                   "This object is a count of the total number of
                   times the priority promotion timer has expired on
                   any port in this repeater.  This counter is a
                   summation of the values of the 
                   icfVgPortPriorityPromotions counter for all of the
                   ports in this repeater."
           REFERENCE
                   "Reference IEEE Draft Std. 802.12, 31 October, 1994,
                   13.2.4.5.1, aPriorityPromotions."
           ::= { hpVgMonCounters 10 }

       hpVgMonitorGroup OBJECT IDENTIFIER ::= { hpVgMonitor 2 }
       -- unused

       hpVgMonitorPort  OBJECT IDENTIFIER ::= { hpVgMonitor 3 }
       -- unused

       -- HP ICF Generic Repeater Objects
       
       hpicfGenericRepeater OBJECT IDENTIFIER ::= { hpicfObjects 4 }

       hpGRpBasic       OBJECT IDENTIFIER ::= { hpicfGenericRepeater 1 }
       hpGRpBasicGlobal OBJECT IDENTIFIER ::= { hpGRpBasic 1 }

       hpGRpSelfHealEnable OBJECT-TYPE
           SYNTAX     INTEGER {
                          enabled(1),
                          disabled(2)
                      }
           ACCESS     read-write
           STATUS     mandatory
           DESCRIPTION
                   "This flag controls whether or not the device will
                   send self healing packets.  Self healing packets are
                   normally sent once per second by the agent when no
                   other traffic is present.  When there is no traffic
                   present on a network, there is no way to detect
                   cabling problems (or the repair of cabling problems)
                   and status LEDs are not always correct.

                   Enabling this flag allows the agent to detect cabling
                   problems on an idle network.  This flag can be
                   disabled if self healing packets are not wanted.

                   On the 100BaseVG-AnyLAN SNMP/Bridge card, these
                   packets are addressed to a unique unused unicast
                   station address which has been reserved by HP for
                   this purpose.  On 802.3 repeaters, these packets are
                   self addressed.

                   On an 802.3 repeater, this flag MUST be enabled when
                   using the Robust Port Healing feature.  Without
                   Robust Port Healing either a good transmit or a good
                   receive will reconnect an autopartitioned port.  With
                   Robust Port Healing the criteria is more restrictive
                   and only a good transmit will heal a segmented port.
                   If all ports are segmented, the repeater will not
                   repeat anything until the agent transmits a self
                   healing packet and reconnects the autopartitioned
                   ports."
           ::= { hpGRpBasicGlobal 1 }
       
       hpGRpBasicGroup  OBJECT IDENTIFIER ::= { hpGRpBasic 2 }
       -- currently unused

       hpGRpBasicPort   OBJECT IDENTIFIER ::= { hpGRpBasic 3 }
       -- currently unused

       hpGRpMonitor     OBJECT IDENTIFIER ::= { hpicfGenericRepeater 2 }
       -- currently unused

       hpGRpAddrTrack   OBJECT IDENTIFIER ::= { hpicfGenericRepeater 3 }
       -- currently unused

       -- Placeholder for registering ICF notifications

       hpicfNotifications OBJECT IDENTIFIER ::= { icf 12 }

       hpicfCommonTraps   OBJECT IDENTIFIER ::= { hpicfNotifications 1 }
       hpicf8023RptrTraps OBJECT IDENTIFIER ::= { hpicfNotifications 2 }
       hpicfVgRptrTraps   OBJECT IDENTIFIER ::= { hpicfNotifications 3 }
       hpicfGenRptrTraps  OBJECT IDENTIFIER ::= { hpicfNotifications 4 }

       hpicfChainAddition TRAP-TYPE
           ENTERPRISE    hpicfCommonTraps
           VARIABLES     { hpicfChainId }
           DESCRIPTION
                   "An hpicfChainAddition trap indicates that a new node
                   has been added to the Distributed Management Chain
                   connected to this agent.  The hpicfChainId returned
                   is the identifier for the new node."
           ::= 1

       hpicfChainRemoval TRAP-TYPE
           ENTERPRISE    hpicfCommonTraps
           VARIABLES     { hpicfChainId }
           DESCRIPTION
                   "An hpicfChainRemoval trap indicates that a node has
                   been removed from the Distributed Management Chain
                   connected to this agent.  The hpicfChainId returned
                   is the identifier for the node that was removed."
           ::= 2



       -- The specific-trap field of the SNMP Trap-PDU is set to the
       -- value of the TRAP-TYPE macro. The generic-trap field is set
       -- to enterpriseSpecific(6).
       --
       -- For traps defined in the icfCommon, icfHub, or icfBridge
       -- enterprise, the ENTERPRISE field contains ths sysObjectId
       -- of the agent sending the trap.

       -- Icf Common traps

       thresholdTrap TRAP-TYPE
           ENTERPRISE    icfCommon
           VARIABLES     { evthObject, evthThreshold, evthHysteresis,
                           evthTimeInterval }
           DESCRIPTION
                   "A thresholdTrap(0) is specific to ICF devices. It
                   signifies that the threshold entity in the device
                   has detected that the object identified by
                   evthObject has exceeded the threshold identified
                   by evthThreshold during the time interval
                   evthTimeInterval. After this condition occurs, it
                   will not reoccur until the the object identified
                   by evthObject falls below evthHysteresis for the
                   duration of evthTimeInterval."
           ::= 0

       -- ICF Bridge Specific traps

       stpTrap TRAP-TYPE
           ENTERPRISE    icfBridge
           VARIABLES     { stpPortState }
           DESCRIPTION
                   "A stpTrap(3) is device type specific to ICF
                   bridges. It signifies that the Spanning Tree
                   entity in the bridge has detected a change of
                   state to either Blocking or Forwarding."
           ::= 3

       temperatureTrap TRAP-TYPE
           ENTERPRISE    icfBridge
           DESCRIPTION
                   "A temperatureTrap(4) is device type specific to
                   ICF bridges. It signifies that the bridge hardware
                   has detected an overheated condition."
           ::= 4

       -- ICF Hub Specific traps

       linkBeatTrap TRAP-TYPE
           ENTERPRISE    icfHub
           VARIABLES     { hubPortLinkBeatStatus }
           DESCRIPTION
                   "A linkBeatTrap(3) is device type specific to ICF
                   hubs. It signifies that the hub hardware has
                   detected a change of state in a port's link beat
                   status. The current value of the port's link beat
                   status is returned in the PDU."
           ::= 3

       segmentationTrap TRAP-TYPE
           ENTERPRISE    icfHub
           VARIABLES     { hubPortSegmentation }
           DESCRIPTION
                   "A segmentationTrap(4) is device type specific to
                   ICF hubs. It signifies that the hub hardware has
                   detected a change of state in a port's
                   segmentation status.  The current value of the
                   port's segmentation status is returned in the
                   PDU."
           ::= 4

       backupLinkTrap TRAP-TYPE
           ENTERPRISE    icfHub
           VARIABLES     { rptrPortAdminStatus }
           DESCRIPTION
                   "A backupLinkTrap(5) is device type specific to
                   most ICF hubs. It signifies that there has been a
                   change in state of rptrPortAdminStatus for a
                   backup port on the hub.  The new value of 
                   rptrPortAdminStatus is returned in the PDU.  

                   Note that in EtherTwist hubs with revision 'D' or
                   earlier firmware, the SNMP-REPEATER-MIB is not
                   supported.  These hubs map hub ports to interfaces
                   in the interfaces group of RFC1213-MIB.  For these
                   hubs, the variable binding list contains
                   ifAdminStatus for the backup port on the hub
                   instead of rptrPortAdminStatus.

                   Backup links are not supported on the HP28688A 
                   hub."
           ::= 5

       intrusionTrap TRAP-TYPE
           ENTERPRISE  icfHub
           VARIABLES   { hubIntruderAddress, hubIntruderPort }
           DESCRIPTION
                   "An intrusionTrap(6) is device type specific to
                   EtherTwist hubs with revision 'E' firmware or 
                   later and AdvanceStack hubs.  It signifies that a
                   port security violation has been detected on a
                   port which has the hubSecPtAlarmEnable flag set
                   to 'enabled'.  The MAC address of the intruder
                   and the port on which the intrusion occurred are
                   returned in the PDU."
           ::= 6

       addressMovedTrap TRAP-TYPE
           ENTERPRISE  icfHub
           VARIABLES   { hubAddrMoveAddress, hubAddrMoveOldGroup,
                         hubAddrMoveOldPort, hubAddrMoveNewGroup,
                         hubAddrMoveNewPort }
           DESCRIPTION
                   "An addressMovedTrap(7) is device type specific
                   to EtherTwist hubs with revision 'E' firmware or
                   later and AdvanceStack hubs.  It signifies that a
                   source MAC address which had been operating at
                   one port has moved to a new port.  The MAC
                   address that moved, the group and port that the
                   address moved from, and the group and port that
                   the address moved to are returned in the PDU."
           ::= 7

       newAddressTrap TRAP-TYPE
           ENTERPRISE  icfHub
           VARIABLES   { rptrAddrTrackLastSourceAddress }
           DESCRIPTION
                   "A newAddressTrap(8) is device type specific to
                   EtherTwist hubs with revision 'E' firmware or 
                   later and AdvanceStack hubs.  It signifies that a
                   new MAC address has been detected on one of the
                   hub's ports.  The instance of
                   rptrAddrTrackLastSourceAddress for the port with
                   the new address is returned in the PDU."
           ::= 8

       END
