HP-ICF-SLOT-STATS-MIB DEFINITIONS ::= BEGIN

    IMPORTS
        Integer32, OBJECT-TYPE, MODULE-IDENTITY
            FROM SNMPv2-SMI
        MODULE-COMPLIANCE, OBJECT-GROUP
            FROM SNMPv2-CONF
        entPhysicalIndex
            FROM ENTITY-MIB
        SnmpAdminString
            FROM SNMP-FRAMEWORK-MIB
        hpSwitchStatistics
            FROM HP-ICF-OID;

    hpicfSlotStatsMIB MODULE-IDENTITY
        LAST-UPDATED "201201050000Z"  -- January 05, 2012
        ORGANIZATION "HP Networking"
        CONTACT-INFO "Hewlett Packard Company
                     8000 Foothills Blvd.
                     Roseville, CA 95747"
        DESCRIPTION  "This MIB module describes objects for 
                     module related statistics in the HP Integrated
                     Communication Facility product line."
        
        REVISION     "201201050000Z"  -- January 05, 2012
        DESCRIPTION  "Initial creation." 
        
        ::= { hpSwitchStatistics 20 }

   -- hpicfSlotStatsMIB - the main groups
   -- -------------------------------------------------------------

   hpicfSlotStatsObjects       OBJECT IDENTIFIER
                         ::= { hpicfSlotStatsMIB 1 }

   hpicfSlotStatsConformance   OBJECT IDENTIFIER
                         ::= { hpicfSlotStatsMIB 2 }

    -- The HP ICF Slot Statistics Group

    hpicfSlotStatsModuleCpuStatTable OBJECT-TYPE 
        SYNTAX      SEQUENCE OF HpicfSlotStatsModuleCpuStatEntry 
        MAX-ACCESS  not-accessible 
        STATUS      current
        DESCRIPTION "A list of CPU load statistics 
                    for the modules in the switch." 
        ::= { hpicfSlotStatsObjects 1 } 

    hpicfSlotStatsModuleCpuStatEntry OBJECT-TYPE
        SYNTAX      HpicfSlotStatsModuleCpuStatEntry
        MAX-ACCESS  not-accessible
        STATUS      current
        DESCRIPTION "An entry for CPU load statistics
                    for the modules in the switch."
        INDEX       { entPhysicalIndex }
        ::= { hpicfSlotStatsModuleCpuStatTable 1 }

    HpicfSlotStatsModuleCpuStatEntry ::=
        SEQUENCE {
            hpicfSlotStatsModuleHwModel                   SnmpAdminString,
            hpicfSlotStatsModuleSerialNum                 SnmpAdminString,
            hpicfSlotStatsModuleCpuStatCurrentPercent     Integer32,
            hpicfSlotStatsModuleCpuStatAveragePercent     Integer32
        }

    hpicfSlotStatsModuleHwModel         OBJECT-TYPE 
        SYNTAX      SnmpAdminString
        MAX-ACCESS  read-only
        STATUS      current
        DESCRIPTION "The model number of the Module."
        ::= { hpicfSlotStatsModuleCpuStatEntry 1 }

    hpicfSlotStatsModuleSerialNum       OBJECT-TYPE 
        SYNTAX      SnmpAdminString
        MAX-ACCESS  read-only
        STATUS      current
        DESCRIPTION "The serial number of the Module."
        ::= { hpicfSlotStatsModuleCpuStatEntry 2 }

    hpicfSlotStatsModuleCpuStatCurrentPercent OBJECT-TYPE 
        SYNTAX      Integer32 (0..100)
        MAX-ACCESS  read-only
        STATUS      current
        DESCRIPTION "CPU utilization in percent(%),
                     over a short time span, updated
                     at the interval 
                     hpicfSlotStatsModuleCpuStatUpdateFrequency.
                     Current time span is 1 second."
        ::= { hpicfSlotStatsModuleCpuStatEntry 3 }

    hpicfSlotStatsModuleCpuStatAveragePercent OBJECT-TYPE 
        SYNTAX      Integer32 (0..100)
        MAX-ACCESS  read-only
        STATUS      current
        DESCRIPTION "The average CPU utilization in percent(%),
                     over a long time span, updated 
                     at the interval 
                     hpicfSlotStatsModuleCpuStatUpdateFrequency.
                     Current time span is 90 seconds."
        ::= { hpicfSlotStatsModuleCpuStatEntry 4 }

    hpicfSlotStatsModuleCpuStatUpdateFrequency OBJECT-TYPE 
        SYNTAX      Integer32 
        MAX-ACCESS  read-only 
        STATUS      current
        DESCRIPTION "The interval in seconds in which the 
                     hpicfSlotStatsModuleCpuStatTable is updated." 
        ::= { hpicfSlotStatsObjects 2 }  

   -- -------------------------------------------------------------
   -- Conformance Information
   -- -------------------------------------------------------------

   hpicfSlotStatsGroups OBJECT IDENTIFIER
                             ::= { hpicfSlotStatsConformance 1 }

   hpicfSlotStatsCompliances OBJECT IDENTIFIER
                             ::= { hpicfSlotStatsConformance 2 }

   -- -------------------------------------------------------------
   -- units of conformance
   -- -------------------------------------------------------------

   hpicfSlotStatsGroup OBJECT-GROUP
         OBJECTS    { hpicfSlotStatsModuleHwModel,
                      hpicfSlotStatsModuleSerialNum,
                      hpicfSlotStatsModuleCpuStatCurrentPercent,
                      hpicfSlotStatsModuleCpuStatAveragePercent,
                      hpicfSlotStatsModuleCpuStatUpdateFrequency }
         STATUS     current
         DESCRIPTION "A collection of objects for SlotStat."
         ::= { hpicfSlotStatsGroups 1}

-- --------------------------------------------------------------
   -- Compliance statements for hpicfSlotStatsMIB Group 
-- --------------------------------------------------------------

   hpicfSlotStatsFullCompliance1 MODULE-COMPLIANCE
       STATUS  current
       DESCRIPTION
           "The compliance statement for SNMP entities which
            implement the HP-ICF-SLOT-STATS-MIB. 
            Such an implementation can be monitored via SNMP.
           "
       MODULE -- this module
       MANDATORY-GROUPS {
           hpicfSlotStatsGroup
       }

       ::= { hpicfSlotStatsCompliances 1 }

   hpicfModuleSlotStatsReadOnlyCompliance1 MODULE-COMPLIANCE
       STATUS  current
       DESCRIPTION
           "The compliance statement for SNMP entities which
            implement the HP-ICF-SLOT-STATS-MIB without support
            for read-write (i.e. in read-only mode). 
           "
       MODULE -- this module
       MANDATORY-GROUPS {
           hpicfSlotStatsGroup
       }
       OBJECT  hpicfSlotStatsModuleHwModel
       MIN-ACCESS  read-only
       DESCRIPTION
           "Write access is not required.
           "
       OBJECT  hpicfSlotStatsModuleSerialNum
       MIN-ACCESS  read-only
       DESCRIPTION
           "Write access is not required.
           "
       OBJECT  hpicfSlotStatsModuleCpuStatCurrentPercent
       MIN-ACCESS  read-only
       DESCRIPTION
           "Write access is not required.
           "
       OBJECT  hpicfSlotStatsModuleCpuStatAveragePercent
       MIN-ACCESS  read-only
       DESCRIPTION
           "Write access is not required.
           "
       ::= { hpicfSlotStatsCompliances 2 }

END
