--**MOD+***********************************************************************
-- * Module:    hpicfiTlsMin.mib
-- *
-- * Copyright (C) 2014 Hewlett Packard Enterprise Development LP
-- * All Rights Reserved.
-- * 
-- * The contents of this software are proprietary and confidential
-- * to the Hewlett Packard Enterprise Development LP.  No part of this
-- * program may be photocopied, reproduced, or translated into another
-- * programming language without prior written consent of the
-- * Hewlett Packard Enterprise Development LP.
-- *
-- * Purpose:   Contains MIB Objects for TLs minimumi version
-- *
-- **MOD-***********************************************************************/

HP-ICF-TLS-MIN-MIB DEFINITIONS ::= BEGIN

    IMPORTS
        hpSwitch
            FROM HP-ICF-OID
        OBJECT-GROUP, MODULE-COMPLIANCE
            FROM SNMPv2-CONF 
        OBJECT-TYPE, MODULE-IDENTITY
            FROM SNMPv2-SMI
        TruthValue, RowStatus
            FROM SNMPv2-TC;
 
    hpicfTlsMinMIB MODULE-IDENTITY
 
        LAST-UPDATED "201606220900Z"     --June 22, 2016
        ORGANIZATION "HP Networking"
        CONTACT-INFO "Hewlett-Packard Company
                      8000 Foothills Blvd.
                      Roseville, CA 95747"
	DESCRIPTION
	   "This MIB module describes objects for enforcing TLS minimum
           version enforcement and ciphersuire enforcement in the HP
           Integrated Communication Facility product line."

	REVISION     "201606220900Z"     -- June 22, 2016 
        DESCRIPTION
           "Added new app type cloud to hpicfTlsMinApp."

	REVISION     "201410010900Z"     -- Oct 1, 2014 
        DESCRIPTION
           "Initial version of TLS Minimum MIB module."

        ::= { hpSwitch 112 }

 
    ---
    --- Node definitions
    ---

    hpicfTlsMinObjects       OBJECT IDENTIFIER ::= { hpicfTlsMinMIB 0 }
    hpicfTlsMinConformance   OBJECT IDENTIFIER ::= { hpicfTlsMinMIB 1 }
   

    hpicfTlsMinConfigObjects OBJECT IDENTIFIER ::= { hpicfTlsMinObjects 1 }


    ---
    --- tls-minimum table
    ---
    hpicfTlsMinTable OBJECT-TYPE
        SYNTAX          SEQUENCE OF HpicfTlsMinEntry
        MAX-ACCESS      not-accessible
        STATUS          current
        DESCRIPTION 
	    "A table of minimum TLS version objects"
        ::= { hpicfTlsMinConfigObjects 1 }

    hpicfTlsMinEntry OBJECT-TYPE
        SYNTAX          HpicfTlsMinEntry
        MAX-ACCESS      not-accessible
        STATUS          current
        DESCRIPTION 
	    "An entry in the hpicfTlsMinTable."
        INDEX           { hpicfTlsMinApp }
        ::= { hpicfTlsMinTable 1 }

    HpicfTlsMinEntry ::= SEQUENCE {
        hpicfTlsMinApp           INTEGER, 
        hpicfTlsMinVersion       INTEGER,
        hpicfTlsMinCloseSSLSess  TruthValue,
        hpicfTlsMinRowStatus     RowStatus
    }

    hpicfTlsMinApp OBJECT-TYPE
        SYNTAX          INTEGER {
                            webSsl(1),
                            openflow(2),
                            syslog(3),
                            tr69(4),
                            cloud(5)
                        }
        MAX-ACCESS      not-accessible
        STATUS          current
        DESCRIPTION 
            "This object specifies the application for which the minimum 
             TLS version and cipher suite is enforced."
        ::= { hpicfTlsMinEntry 1 }

    hpicfTlsMinVersion OBJECT-TYPE
        SYNTAX          INTEGER {
                            tls1dot0(1),
                            tls1dot1(2),
                            tls1dot2(3)
                        }
        MAX-ACCESS      read-create
        STATUS          current
        DESCRIPTION 
            "This object specifies the minimum TLS version enforced. The 
             default value for this attribute will be TLS1.1"
        ::= { hpicfTlsMinEntry 2 }

    hpicfTlsMinCloseSSLSess OBJECT-TYPE
        SYNTAX          TruthValue
        MAX-ACCESS      read-create
        STATUS          current
        DESCRIPTION 
            "This object specifies whether or not to close existing 
             SSL sessions. Setting this attribute to TRUE will close all
             existing SSL sessions. Setting this attribute to FALSE will
             not have any effect."
        ::= { hpicfTlsMinEntry 3 } 

    hpicfTlsMinRowStatus OBJECT-TYPE
        SYNTAX          RowStatus
        MAX-ACCESS      read-create
        STATUS          current
        DESCRIPTION 
        "Status of this row, by which new entries may be created
         or existing entries deleted from this table."

        ::= { hpicfTlsMinEntry 4 } 

    ---
    --- Cipher suites table
    ---

    hpicfTlsMinCipherTable OBJECT-TYPE
        SYNTAX             SEQUENCE OF HpicfTlsMinCipherEntry
        MAX-ACCESS         not-accessible
        STATUS             current
        DESCRIPTION
           "A table that contains a list of cipher suites that
            can be enforced for various applications."

        ::= { hpicfTlsMinConfigObjects 2 }

    hpicfTlsMinCipherEntry OBJECT-TYPE
        SYNTAX          HpicfTlsMinCipherEntry
        MAX-ACCESS      not-accessible
        STATUS          current
        DESCRIPTION
           "An entry in the hpicfTlsMinTable that lists the lowest 
            TLS version and cipher suites enforced for each application."

        INDEX           {hpicfTlsMinApp, hpicfTlsMinCipher }
        ::= { hpicfTlsMinCipherTable 1 }

    HpicfTlsMinCipherEntry ::= SEQUENCE {
        hpicfTlsMinCipher              INTEGER,
        hpicfTlsMinCipherRowStatus     RowStatus
    }

    hpicfTlsMinCipher OBJECT-TYPE
        SYNTAX          INTEGER {
                            aes256Sha256(1),
                            aes256Sha(2),
                            aes128Sha256(3),
                            aes128Sha(4),
                            des3CbcSha(5)
                        }
        MAX-ACCESS      not-accessible
        STATUS          current
        DESCRIPTION
            "This object specifies the cipher suite enforced for applications."
        ::= { hpicfTlsMinCipherEntry 1 }

    hpicfTlsMinCipherRowStatus OBJECT-TYPE
        SYNTAX          RowStatus
        MAX-ACCESS      read-create
        STATUS          current
        DESCRIPTION
        "Status of this row, by which new entries may be created
         or existing entries deleted from this table."
        ::= { hpicfTlsMinCipherEntry 2 }


    --- ------------------------------------------------------------
    --- Conformance
    --- ------------------------------------------------------------

    hpicfTlsMinCompliances OBJECT IDENTIFIER ::= { hpicfTlsMinConformance 1 }
    hpicfTlsMinGroups OBJECT IDENTIFIER ::= { hpicfTlsMinConformance 2 }

    hpicfTlsMinCompliance1 MODULE-COMPLIANCE
    STATUS          current
    DESCRIPTION     "The compliance statement"
        MODULE          -- this module
        MANDATORY-GROUPS {
            hpicfTlsMinConfigGroup
        }
        ::= { hpicfTlsMinCompliances 1 }

    --- units of conformance

    hpicfTlsMinConfigGroup OBJECT-GROUP
        OBJECTS    {
            hpicfTlsMinVersion,
            hpicfTlsMinCloseSSLSess,
            hpicfTlsMinRowStatus,
            hpicfTlsMinCipherRowStatus
        }
        STATUS current
        DESCRIPTION
            "A collection of objects providing configuration for
             TLS minimum version and cipher suite enforcement for an app."            
        ::= { hpicfTlsMinGroups 1 }

END
