--
-- HUAWEI-TFTPC-MIB.my
-- Tuesday, August 18, 2009 at 12:16:34
--

 HUAWEI-TFTPC-MIB DEFINITIONS ::= BEGIN
 
  IMPORTS
   hwDatacomm   
    FROM HUAWEI-MIB
   OBJECT-GROUP, MODULE-COMPLIANCE
    FROM SNMPv2-CONF
   OBJECT-TYPE, MODULE-IDENTITY
    FROM SNMPv2-SMI
   RowStatus, DisplayString   
    FROM SNMPv2-TC;
    
  hwTftpc MODULE-IDENTITY 
      LAST-UPDATED "201012080000Z"
      ORGANIZATION "Huawei Technologies Co.,Ltd."
      CONTACT-INFO 
               "Huawei Industrial Base
                 Bantian, Longgang
                  Shenzhen 518129
                  People's Republic of China
                  Website: http://www.huawei.com
                  Email: support@huawei.com
                "
      DESCRIPTION 
                "The HUAWEI-TFTPC-MIB which contains objects manages the TFTP client configuration. "
      REVISION "201006010000Z"        
      DESCRIPTION "The initial revision of this MIB module."
      REVISION "201012080000Z"        
      DESCRIPTION "Modified by z47250 for fixing SimpleTester compile errors."
      ::= { hwDatacomm 197 }
 
--
-- Node definitions
--
 
     -- 1.3.6.1.4.1.2011.5.25.197.2
     hwTftpClientInfo OBJECT IDENTIFIER ::= { hwTftpc 2 }  
     hwTftpClientConformance OBJECT IDENTIFIER ::= { hwTftpc 3 }
            
     hwTftpClientSourceAddress OBJECT-TYPE
             SYNTAX OCTET STRING (SIZE (0..16))
             MAX-ACCESS read-write
             STATUS current
             DESCRIPTION
                 "Tftp client IP address.
                 "
             ::= { hwTftpClientInfo 1 }       
             
     hwTftpClientSourceInterfaceName OBJECT-TYPE
             SYNTAX OCTET STRING (SIZE (0..63))
             MAX-ACCESS read-write
             STATUS current
             DESCRIPTION
                 "Tftp client source interface name.
                 "
             ::= { hwTftpClientInfo 2 }               
             
     hwTFtpClientGroups OBJECT IDENTIFIER ::= { hwTftpClientConformance 1 }
      
     hwTFtpClientInfoGroup OBJECT-GROUP
            OBJECTS { hwTftpClientSourceAddress, hwTftpClientSourceInterfaceName }
            STATUS current
            DESCRIPTION 
                "A collection of objects on TFtp client information."
            ::= { hwTFtpClientGroups 1 }     
            
      hwTFtpClientCompliances OBJECT IDENTIFIER ::= { hwTftpClientConformance 2 }
       
      hwTFtpClientCompliance MODULE-COMPLIANCE
            STATUS current
            DESCRIPTION 
                "The compliance statement for 
                entities that support the huawei TFtpClient MIB."
            MODULE      -- this module
            ::= { hwTFtpClientCompliances 1 } 
 
 END

--
-- HUAWEI-TFTPC-MIB.my
--
