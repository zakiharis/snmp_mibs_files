-- ============================================================================
-- Copyright (C) by  HUAWEI TECHNOLOGIES. All rights reserved.
-- Description: This mib is used for defining huawei's Easy Opearation MIB objects
-- Reference: None
-- Version:   V1.05
-- ============================================================================

    HUAWEI-EASY-OPERATION-MIB DEFINITIONS ::= BEGIN
 
        IMPORTS
            hwDatacomm            
                FROM HUAWEI-MIB            
            InetAddress, InetAddressType            
                FROM INET-ADDRESS-MIB            
            EnabledStatus            
                FROM P-BRIDGE-MIB            
            OBJECT-GROUP, MODULE-COMPLIANCE, NOTIFICATION-GROUP            
                FROM SNMPv2-CONF            
            Integer32, OBJECT-TYPE, MODULE-IDENTITY, NOTIFICATION-TYPE            
                FROM SNMPv2-SMI            
            DisplayString, RowStatus, MacAddress            
                FROM SNMPv2-TC;
    
    
        hwEasyOperationMIB MODULE-IDENTITY 
            LAST-UPDATED "201409090000Z"       
            ORGANIZATION 
                "Huawei Technologies Co.,Ltd."
                CONTACT-INFO 
               "Huawei Industrial Base
                Bantian, Longgang
                Shenzhen 518129
                People's Republic of China
                Website: http://www.huawei.com
                Email: support@huawei.com
               "
            DESCRIPTION 
                "Huawei Easy Opearation MIB."
            REVISION      "201409090000Z" 
            DESCRIPTION 
               "Revisions made by HUAWEI." 



            REVISION      "201406040000Z" 
            DESCRIPTION 
               "Revisions made by HUAWEI." 

            REVISION      "201312300000Z" 
            DESCRIPTION 
               "Revisions made by HUAWEI." 

            REVISION      "201308050000Z"
            DESCRIPTION
               "Revisions made by HUAWEI."

            REVISION      "201303180000Z"
            DESCRIPTION
               "Revisions made by HUAWEI."

            ::= { hwDatacomm 311 }

        
    
    
--
-- Node definitions
--
    
--  Node definitions
-- 
-- Node definitions
-- 
        hwEasyOperationGlobalObjects OBJECT IDENTIFIER ::= { hwEasyOperationMIB 1 }

        
        hwEasyOperationCommanderEnable OBJECT-TYPE
            SYNTAX EnabledStatus
            MAX-ACCESS read-write
            STATUS current
            DESCRIPTION
                "This object specifies the Easy Operation Commander operation mode."
            ::= { hwEasyOperationGlobalObjects 1 }

        
        hwEasyOperationCommanderIpAddress OBJECT-TYPE
            SYNTAX InetAddress
            MAX-ACCESS read-write
            STATUS current
            DESCRIPTION
                "The IP address of commander."
            ::= { hwEasyOperationGlobalObjects 2 }

        
        hwEasyOperationCommanderIpAddressType OBJECT-TYPE
            SYNTAX InetAddressType
            MAX-ACCESS read-write
            STATUS current
            DESCRIPTION
                "The IP address type of commander."
            ::= { hwEasyOperationGlobalObjects 3 }

        
        hwEasyOperationCommanderUdpPort OBJECT-TYPE
            SYNTAX Integer32
            MAX-ACCESS read-write
            STATUS current
            DESCRIPTION
                "The UDP port of commander."
            ::= { hwEasyOperationGlobalObjects 4 }

        
        hwEasyOperationServerType OBJECT-TYPE
            SYNTAX INTEGER
                {
                tftp(1),
                ftp(2),
                sftp(3)
                }
            MAX-ACCESS read-write
            STATUS current
            DESCRIPTION
                "The type of file server."
            ::= { hwEasyOperationGlobalObjects 5 }

        
        hwEasyOperationServerIpAddress OBJECT-TYPE
            SYNTAX InetAddress
            MAX-ACCESS read-write
            STATUS current
            DESCRIPTION
                "The IP address of file server."
            ::= { hwEasyOperationGlobalObjects 6 }

        
        hwEasyOperationServerIpAddressType OBJECT-TYPE
            SYNTAX InetAddressType
            MAX-ACCESS read-write
            STATUS current
            DESCRIPTION
                "The IP address type of file server."
            ::= { hwEasyOperationGlobalObjects 7 }

        
        hwEasyOperationServerPort OBJECT-TYPE
            SYNTAX Integer32
            MAX-ACCESS read-write
            STATUS current
            DESCRIPTION
                "The port number of file server."
            ::= { hwEasyOperationGlobalObjects 8 }

        
        hwEasyOperationAutoClearEnable OBJECT-TYPE
            SYNTAX EnabledStatus
            MAX-ACCESS read-write
            STATUS current
            DESCRIPTION
                "Whether client would clear the old software file when the free space is not enough."
            ::= { hwEasyOperationGlobalObjects 9 }

        
        hwEasyOperationActivateMode OBJECT-TYPE
            SYNTAX INTEGER
                {
                default(1),
                reload(2)
                }
            MAX-ACCESS read-write
            STATUS current
            DESCRIPTION
                "The mode of activating file."
            ::= { hwEasyOperationGlobalObjects 10 }

        
        hwEasyOperationActivateDelayTime OBJECT-TYPE
            SYNTAX Integer32
            MAX-ACCESS read-write
            STATUS current
            DESCRIPTION
                "The delay time of activating file.The unit is second(s)."
            ::= { hwEasyOperationGlobalObjects 11 }

        
        hwEasyOperationActivateInTime OBJECT-TYPE
            SYNTAX DisplayString
            MAX-ACCESS read-write
            STATUS current
            DESCRIPTION
                "The specific time of activating file."
            ::= { hwEasyOperationGlobalObjects 12 }

        
        hwEasyOperationBackupConfigMode OBJECT-TYPE
            SYNTAX INTEGER
                {
                overwrite(1),
                duplicate(2)
                }
            MAX-ACCESS read-write
            STATUS current
            DESCRIPTION
                "The mode of file created on the server."
            ::= { hwEasyOperationGlobalObjects 13 }

        
        hwEasyOperationBackupConfigInterval OBJECT-TYPE
            SYNTAX Integer32
            MAX-ACCESS read-write
            STATUS current
            DESCRIPTION
                "The interval of configuration backup .The unit is hour(s)"
            ::= { hwEasyOperationGlobalObjects 14 }

        
        hwEasyOperationDefaultSysSoftware OBJECT-TYPE
            SYNTAX DisplayString
            MAX-ACCESS read-write
            STATUS current
            DESCRIPTION
                "The default name of software file."
            ::= { hwEasyOperationGlobalObjects 15 }

        
        hwEasyOperationDefaultSysSoftwareVer OBJECT-TYPE
            SYNTAX DisplayString
            MAX-ACCESS read-write
            STATUS current
            DESCRIPTION
                "The version of default software file."
            ::= { hwEasyOperationGlobalObjects 16 }

        
        hwEasyOperationDefaultConfig OBJECT-TYPE
            SYNTAX DisplayString
            MAX-ACCESS read-write
            STATUS current
            DESCRIPTION
                "The default name of configuration file."
            ::= { hwEasyOperationGlobalObjects 17 }

        
        hwEasyOperationDefaultPatch OBJECT-TYPE
            SYNTAX DisplayString
            MAX-ACCESS read-write
            STATUS current
            DESCRIPTION
                "The default name of patch file."
            ::= { hwEasyOperationGlobalObjects 18 }

        
        hwEasyOperationDefaultWebfile OBJECT-TYPE
            SYNTAX DisplayString
            MAX-ACCESS read-write
            STATUS current
            DESCRIPTION
                "The default name of WEB file."
            ::= { hwEasyOperationGlobalObjects 19 }

        
        hwEasyOperationDefaultLicense OBJECT-TYPE
            SYNTAX DisplayString
            MAX-ACCESS read-write
            STATUS current
            DESCRIPTION
                "The default name of license file."
            ::= { hwEasyOperationGlobalObjects 20 }

        
        hwEasyOperationDefaultCustomfile1 OBJECT-TYPE
            SYNTAX DisplayString
            MAX-ACCESS read-write
            STATUS current
            DESCRIPTION
                "The default name of custom file."
            ::= { hwEasyOperationGlobalObjects 21 }

        
        hwEasyOperationDefaultCustomfile2 OBJECT-TYPE
            SYNTAX DisplayString
            MAX-ACCESS read-write
            STATUS current
            DESCRIPTION
                "The default name of custom file."
            ::= { hwEasyOperationGlobalObjects 22 }

        
        hwEasyOperationDefaultCustomfile3 OBJECT-TYPE
            SYNTAX DisplayString
            MAX-ACCESS read-write
            STATUS current
            DESCRIPTION
                "The default name of custom file."
            ::= { hwEasyOperationGlobalObjects 23 }

        hwEasyOperationClientAutoJoinEnable OBJECT-TYPE
            SYNTAX EnabledStatus
            MAX-ACCESS read-write
            STATUS current
            DESCRIPTION
                "Whether commander can receive the information of new clients."
            ::= { hwEasyOperationGlobalObjects 24 }

        hwEasyOperationTopologyEnable OBJECT-TYPE
            SYNTAX EnabledStatus
            MAX-ACCESS read-write
            STATUS current
            DESCRIPTION
                "Whether commander can collect the topology information of new clients."
            ::= { hwEasyOperationGlobalObjects 25 }

        hwEasyOperationClientAgingTime OBJECT-TYPE
            SYNTAX Integer32
            MAX-ACCESS read-write
            STATUS current
            DESCRIPTION
                "The aging time of client which is lost. The unit is hour(s)."
            ::= { hwEasyOperationGlobalObjects 26 }

        
        hwEasyOperationGroup OBJECT IDENTIFIER ::= { hwEasyOperationMIB 2 }

        
        hwEasyOperationTotalGroupNumber OBJECT-TYPE
            SYNTAX Integer32
            MAX-ACCESS read-only
            STATUS current
            DESCRIPTION
                "The total number of group."
            ::= { hwEasyOperationGroup 1 }

        
        hwEasyOperationBuildInGroupNumber OBJECT-TYPE
            SYNTAX Integer32
            MAX-ACCESS read-only
            STATUS current
            DESCRIPTION
                "The number of build-in group."
            ::= { hwEasyOperationGroup 2 }

        
        hwEasyOperationCustomGroupNumber OBJECT-TYPE
            SYNTAX Integer32
            MAX-ACCESS read-only
            STATUS current
            DESCRIPTION
                "The number of custom group."
            ::= { hwEasyOperationGroup 3 }

        
        hwEasyOperationGroupTable OBJECT-TYPE
            SYNTAX SEQUENCE OF HwEasyOperationGroupEntry
            MAX-ACCESS not-accessible
            STATUS current
            DESCRIPTION
                "Group table."
            ::= { hwEasyOperationGroup 4 }

        
        hwEasyOperationGroupEntry OBJECT-TYPE
            SYNTAX HwEasyOperationGroupEntry
            MAX-ACCESS not-accessible
            STATUS current
            DESCRIPTION
                "The entry of group table."
            INDEX { hwEasyOperationGroupIndex }
            ::= { hwEasyOperationGroupTable 1 }

        
        HwEasyOperationGroupEntry ::=
            SEQUENCE { 
                hwEasyOperationGroupIndex
                    Integer32,
                hwEasyOperationGroupType
                    INTEGER,
                hwEasyOperationGroupName
                    DisplayString,
                hwEasyOperationGroupSysSoftware
                    DisplayString,
                hwEasyOperationGroupSysSoftwareVer
                    DisplayString,
                hwEasyOperationGroupConfig
                    DisplayString,
                hwEasyOperationGroupPatch
                    DisplayString,
                hwEasyOperationGroupWebfile
                    DisplayString,
                hwEasyOperationGroupLicense
                    DisplayString,
                hwEasyOperationGroupCustomfile1
                    DisplayString,
                hwEasyOperationGroupCustomfile2
                    DisplayString,
                hwEasyOperationGroupCustomfile3
                    DisplayString,
                hwEasyOperationGroupActivateMode
                    INTEGER,
                hwEasyOperationGroupActivateDelayTime
                    Integer32,
                hwEasyOperationGroupActivateInTime
                    DisplayString,
                hwEasyOperationGroupRowStatus
                    RowStatus
             }

        hwEasyOperationGroupIndex OBJECT-TYPE
            SYNTAX Integer32 (1..4096)
            MAX-ACCESS not-accessible
            STATUS current
            DESCRIPTION
                "The index of group table."
            ::= { hwEasyOperationGroupEntry 1 }

        
        hwEasyOperationGroupType OBJECT-TYPE
            SYNTAX INTEGER
                {
                buildIn(1),
                macAddress(2),
                esn(3),
                model(4),
                deviceType(5),
                ipAddress(6)
                }
            MAX-ACCESS read-create
            STATUS current
            DESCRIPTION
                "The type of group."
            ::= { hwEasyOperationGroupEntry 2 }

        
        hwEasyOperationGroupName OBJECT-TYPE
            SYNTAX DisplayString
            MAX-ACCESS read-create
            STATUS current
            DESCRIPTION
                "The name of group."
            ::= { hwEasyOperationGroupEntry 3 }

        
        hwEasyOperationGroupSysSoftware OBJECT-TYPE
            SYNTAX DisplayString
            MAX-ACCESS read-create
            STATUS current
            DESCRIPTION
                "The software file name of group."
            ::= { hwEasyOperationGroupEntry 4 }

        
        hwEasyOperationGroupSysSoftwareVer OBJECT-TYPE
            SYNTAX DisplayString
            MAX-ACCESS read-create
            STATUS current
            DESCRIPTION
                "The software version of group."
            ::= { hwEasyOperationGroupEntry 5 }

        
        hwEasyOperationGroupConfig OBJECT-TYPE
            SYNTAX DisplayString
            MAX-ACCESS read-create
            STATUS current
            DESCRIPTION
                "The configuration file name of group."
            ::= { hwEasyOperationGroupEntry 6 }

        
        hwEasyOperationGroupPatch OBJECT-TYPE
            SYNTAX DisplayString
            MAX-ACCESS read-create
            STATUS current
            DESCRIPTION
                "The patch file name of group."
            ::= { hwEasyOperationGroupEntry 7 }

        
        hwEasyOperationGroupWebfile OBJECT-TYPE
            SYNTAX DisplayString
            MAX-ACCESS read-create
            STATUS current
            DESCRIPTION
                "The WEB file name of group."
            ::= { hwEasyOperationGroupEntry 8 }

        
        hwEasyOperationGroupLicense OBJECT-TYPE
            SYNTAX DisplayString
            MAX-ACCESS read-create
            STATUS current
            DESCRIPTION
                "The license file name of group."
            ::= { hwEasyOperationGroupEntry 9 }

        
        hwEasyOperationGroupCustomfile1 OBJECT-TYPE
            SYNTAX DisplayString
            MAX-ACCESS read-create
            STATUS current
            DESCRIPTION
                "The custom file name of group."
            ::= { hwEasyOperationGroupEntry 10 }

        
        hwEasyOperationGroupCustomfile2 OBJECT-TYPE
            SYNTAX DisplayString
            MAX-ACCESS read-create
            STATUS current
            DESCRIPTION
                "The custom file name of group."
            ::= { hwEasyOperationGroupEntry 11 }

        
        hwEasyOperationGroupCustomfile3 OBJECT-TYPE
            SYNTAX DisplayString
            MAX-ACCESS read-create
            STATUS current
            DESCRIPTION
                "The custom file name of group."
            ::= { hwEasyOperationGroupEntry 12 }

        
        hwEasyOperationGroupActivateMode OBJECT-TYPE
            SYNTAX INTEGER
                {
                default(1),
                reload(2)
                }
            MAX-ACCESS read-create
            STATUS current
            DESCRIPTION
                "The mode of activating file of group."
            ::= { hwEasyOperationGroupEntry 13 }

        
        hwEasyOperationGroupActivateDelayTime OBJECT-TYPE
            SYNTAX Integer32
            MAX-ACCESS read-create
            STATUS current
            DESCRIPTION
                "The delay time of activating file of group.The unit is second(s)"
            ::= { hwEasyOperationGroupEntry 14 }

        
        hwEasyOperationGroupActivateInTime OBJECT-TYPE
            SYNTAX DisplayString
            MAX-ACCESS read-create
            STATUS current
            DESCRIPTION
                "The specific time of activating file of group."
            ::= { hwEasyOperationGroupEntry 15 }

        
        hwEasyOperationGroupRowStatus OBJECT-TYPE
            SYNTAX RowStatus
            MAX-ACCESS read-create
            STATUS current
            DESCRIPTION
                "The RowStatus of group table."
            ::= { hwEasyOperationGroupEntry 50 }

        
        hwEasyOperationGroupMatchTable OBJECT-TYPE
            SYNTAX SEQUENCE OF HwEasyOperationGroupMatchEntry
            MAX-ACCESS not-accessible
            STATUS current
            DESCRIPTION
                "The match rule of group."
            ::= { hwEasyOperationGroup 5 }

        
        hwEasyOperationGroupMatchEntry OBJECT-TYPE
            SYNTAX HwEasyOperationGroupMatchEntry
            MAX-ACCESS not-accessible
            STATUS current
            DESCRIPTION
                "The entry of match rule of group."
            INDEX { hwEasyOperationGroupIndex, hwEasyOperationGroupMatchIndex }
            ::= { hwEasyOperationGroupMatchTable 1 }

        
        HwEasyOperationGroupMatchEntry ::=
            SEQUENCE { 
                hwEasyOperationGroupMatchIndex
                    Integer32,
                hwEasyOperationGroupMatchMacAddress
                    MacAddress,
                hwEasyOperationGroupMatchMacMask
                    Integer32,
                hwEasyOperationGroupMatchEsn
                    DisplayString,
                hwEasyOperationGroupMatchModel
                    DisplayString,
                hwEasyOperationGroupMatchDeviceType
                    DisplayString,
                hwEasyOperationGroupMatchIpAddress
                    InetAddress,
                hwEasyOperationGroupMatchIpAddressType
                    InetAddressType,
                hwEasyOperationGroupMatchIpAddressMask
                    Integer32,
                hwEasyOperationGroupMatchRowStatus
                    RowStatus
             }

        hwEasyOperationGroupMatchIndex OBJECT-TYPE
            SYNTAX Integer32 (1..4096)
            MAX-ACCESS not-accessible
            STATUS current
            DESCRIPTION
                "The index of match rule table."
            ::= { hwEasyOperationGroupMatchEntry 1 }

        
        hwEasyOperationGroupMatchMacAddress OBJECT-TYPE
            SYNTAX MacAddress
            MAX-ACCESS read-create
            STATUS current
            DESCRIPTION
                "The match rule of MAC address."
            ::= { hwEasyOperationGroupMatchEntry 2 }

        hwEasyOperationGroupMatchMacMask OBJECT-TYPE
            SYNTAX Integer32
            MAX-ACCESS read-create
            STATUS current
            DESCRIPTION
                "The match rule of mask of MAC address."
            ::= { hwEasyOperationGroupMatchEntry 3 }
        
        hwEasyOperationGroupMatchEsn OBJECT-TYPE
            SYNTAX DisplayString
            MAX-ACCESS read-create
            STATUS current
            DESCRIPTION
                "The match rule of ESN."
            ::= { hwEasyOperationGroupMatchEntry 4 }

        
        hwEasyOperationGroupMatchModel OBJECT-TYPE
            SYNTAX DisplayString
            MAX-ACCESS read-create
            STATUS current
            DESCRIPTION
                "The match rule of model of device."
            ::= { hwEasyOperationGroupMatchEntry 5 }

        
        hwEasyOperationGroupMatchDeviceType OBJECT-TYPE
            SYNTAX DisplayString
            MAX-ACCESS read-create
            STATUS current
            DESCRIPTION
                "The match rule of type of device."
            ::= { hwEasyOperationGroupMatchEntry 6 }

        hwEasyOperationGroupMatchIpAddress OBJECT-TYPE
            SYNTAX InetAddress
            MAX-ACCESS read-create
            STATUS current
            DESCRIPTION
                "The match rule of IP address."
            ::= { hwEasyOperationGroupMatchEntry 7 }

        hwEasyOperationGroupMatchIpAddressType OBJECT-TYPE
            SYNTAX InetAddressType
            MAX-ACCESS read-create
            STATUS current
            DESCRIPTION
              "The match rule of type of IP address."
            ::= { hwEasyOperationGroupMatchEntry 8 }

        hwEasyOperationGroupMatchIpAddressMask OBJECT-TYPE
            SYNTAX Integer32
            MAX-ACCESS read-create
            STATUS current
            DESCRIPTION
                "The match rule of mask of IP address."
            ::= { hwEasyOperationGroupMatchEntry 9 }

        
        hwEasyOperationGroupMatchRowStatus OBJECT-TYPE
            SYNTAX RowStatus
            MAX-ACCESS read-create
            STATUS current
            DESCRIPTION
                "The RowStatus of match rule table."
            ::= { hwEasyOperationGroupMatchEntry 50 }

        
        hwEasyOperationClient OBJECT IDENTIFIER ::= { hwEasyOperationMIB 5 }

        
        hwEasyOperationClientNumber OBJECT-TYPE
            SYNTAX Integer32
            MAX-ACCESS read-only
            STATUS current
            DESCRIPTION
                "The number of client."
            ::= { hwEasyOperationClient 1 }

        
        hwEasyOperationClientInfoTable OBJECT-TYPE
            SYNTAX SEQUENCE OF HwEasyOperationClientInfoEntry
            MAX-ACCESS not-accessible
            STATUS current
            DESCRIPTION
                "The client table."
            ::= { hwEasyOperationClient 2 }

        
        hwEasyOperationClientInfoEntry OBJECT-TYPE
            SYNTAX HwEasyOperationClientInfoEntry
            MAX-ACCESS not-accessible
            STATUS current
            DESCRIPTION
                "The entry of client table."
            INDEX { hwEasyOperationClientInfoClientIndex }
            ::= { hwEasyOperationClientInfoTable 1 }

        
        HwEasyOperationClientInfoEntry ::=
            SEQUENCE { 
                hwEasyOperationClientInfoClientIndex
                    Integer32,
                hwEasyOperationClientInfoClientMacAddress
                    MacAddress,
                hwEasyOperationClientInfoClientEsn
                    DisplayString,
                hwEasyOperationClientInfoClientHostName
                    DisplayString,
                hwEasyOperationClientInfoClientIpAddress
                    InetAddress,
                hwEasyOperationClientInfoClientIpAddressType
                    InetAddressType,
                hwEasyOperationClientInfoClientModel
                    DisplayString,
                hwEasyOperationClientInfoClientDeviceType
                    DisplayString,
                hwEasyOperationClientInfoClientSysSoftware
                    DisplayString,
                hwEasyOperationClientInfoClientSysSoftwareVer
                    DisplayString,
                hwEasyOperationClientInfoClientSysConfig
                    DisplayString,
                hwEasyOperationClientInfoClientSysPatch
                    DisplayString,
                hwEasyOperationClientInfoClientSysWebFile
                    DisplayString,
                hwEasyOperationClientInfoClientSysLicense
                    DisplayString,
                hwEasyOperationClientInfoClientDownloadSoftware
                    DisplayString,
                hwEasyOperationClientInfoClientDownloadSoftwareVer
                    DisplayString,
                hwEasyOperationClientInfoClientDownloadConfig
                    DisplayString,
                hwEasyOperationClientInfoClientDownloadPatch
                    DisplayString,
                hwEasyOperationClientInfoClientDownloadWebFile
                    DisplayString,
                hwEasyOperationClientInfoClientDownloadLicense
                    DisplayString,
                hwEasyOperationClientInfoClientDownloadCustomfile1
                    DisplayString,
                hwEasyOperationClientInfoClientDownloadCustomfile2
                    DisplayString,
                hwEasyOperationClientInfoClientDownloadCustomfile3
                    DisplayString,
                hwEasyOperationClientInfoClientMethod
                    INTEGER,
                hwEasyOperationClientInfoClientPhase
                    INTEGER,
                hwEasyOperationClientInfoClientOperateState
                    INTEGER,
                hwEasyOperationClientInfoClientDownloadPercent
                    Integer32,
                hwEasyOperationClientInfoClientErrorReason
                    Integer32,
                hwEasyOperationClientInfoClientErrorDescr
                    DisplayString,
                hwEasyOperationClientInfoClientBackupErrorReason
                    Integer32,
                hwEasyOperationClientInfoClientBackupErrorDescr
                    DisplayString,
                hwEasyOperationClientInfoClientRunState
                    INTEGER,
                hwEasyOperationClientInfoClientCpuUsage
                    Integer32,
                hwEasyOperationClientInfoClientMemoryUsage
                    Integer32,
                hwEasyOperationClientInfoClientRowStatus
                    RowStatus
             }

        hwEasyOperationClientInfoClientIndex OBJECT-TYPE
            SYNTAX Integer32 (1..4096)
            MAX-ACCESS not-accessible
            STATUS current
            DESCRIPTION
                "The index of client table."
            ::= { hwEasyOperationClientInfoEntry 1 }

        
        hwEasyOperationClientInfoClientMacAddress OBJECT-TYPE
            SYNTAX MacAddress
            MAX-ACCESS read-create
            STATUS current
            DESCRIPTION
                "The MAC address of client."
            ::= { hwEasyOperationClientInfoEntry 2 }

        
        hwEasyOperationClientInfoClientEsn OBJECT-TYPE
            SYNTAX DisplayString
            MAX-ACCESS read-create
            STATUS current
            DESCRIPTION
                "The ESN of client."
            ::= { hwEasyOperationClientInfoEntry 3 }

        
        hwEasyOperationClientInfoClientHostName OBJECT-TYPE
            SYNTAX DisplayString
            MAX-ACCESS read-only
            STATUS current
            DESCRIPTION
                "The host name of client."
            ::= { hwEasyOperationClientInfoEntry 4 }

        
        hwEasyOperationClientInfoClientIpAddress OBJECT-TYPE
            SYNTAX InetAddress
            MAX-ACCESS read-create
            STATUS current
            DESCRIPTION
                "The IP address of client."
            ::= { hwEasyOperationClientInfoEntry 5 }

        
        hwEasyOperationClientInfoClientIpAddressType OBJECT-TYPE
            SYNTAX InetAddressType
            MAX-ACCESS read-create
            STATUS current
            DESCRIPTION
                "The IP address type of client."
            ::= { hwEasyOperationClientInfoEntry 6 }

        
        hwEasyOperationClientInfoClientModel OBJECT-TYPE
            SYNTAX DisplayString
            MAX-ACCESS read-only
            STATUS current
            DESCRIPTION
                "The model of client."
            ::= { hwEasyOperationClientInfoEntry 7 }

        
        hwEasyOperationClientInfoClientDeviceType OBJECT-TYPE
            SYNTAX DisplayString
            MAX-ACCESS read-only
            STATUS current
            DESCRIPTION
                "The device type of client."
            ::= { hwEasyOperationClientInfoEntry 8 }

        
        hwEasyOperationClientInfoClientSysSoftware OBJECT-TYPE
            SYNTAX DisplayString
            MAX-ACCESS read-only
            STATUS current
            DESCRIPTION
                "The startup software file name of client."
            ::= { hwEasyOperationClientInfoEntry 9 }

        
        hwEasyOperationClientInfoClientSysSoftwareVer OBJECT-TYPE
            SYNTAX DisplayString
            MAX-ACCESS read-only
            STATUS current
            DESCRIPTION
                "The startup software version of client."
            ::= { hwEasyOperationClientInfoEntry 10 }

        
        hwEasyOperationClientInfoClientSysConfig OBJECT-TYPE
            SYNTAX DisplayString
            MAX-ACCESS read-only
            STATUS current
            DESCRIPTION
                "The startup configuration file name of client."
            ::= { hwEasyOperationClientInfoEntry 11 }

        
        hwEasyOperationClientInfoClientSysPatch OBJECT-TYPE
            SYNTAX DisplayString
            MAX-ACCESS read-only
            STATUS current
            DESCRIPTION
                "The startup patch file name of client."
            ::= { hwEasyOperationClientInfoEntry 12 }

        
        hwEasyOperationClientInfoClientSysWebFile OBJECT-TYPE
            SYNTAX DisplayString
            MAX-ACCESS read-only
            STATUS current
            DESCRIPTION
                "The startup WEB file name of client."
            ::= { hwEasyOperationClientInfoEntry 13 }

        
        hwEasyOperationClientInfoClientSysLicense OBJECT-TYPE
            SYNTAX DisplayString
            MAX-ACCESS read-only
            STATUS current
            DESCRIPTION
                "The startup license file name of client."
            ::= { hwEasyOperationClientInfoEntry 14 }

        
        hwEasyOperationClientInfoClientDownloadSoftware OBJECT-TYPE
            SYNTAX DisplayString
            MAX-ACCESS read-create
            STATUS current
            DESCRIPTION
                "The software file name of client in downloading status."
            ::= { hwEasyOperationClientInfoEntry 15 }

        
        hwEasyOperationClientInfoClientDownloadSoftwareVer OBJECT-TYPE
            SYNTAX DisplayString
            MAX-ACCESS read-create
            STATUS current
            DESCRIPTION
                "The software version of client in downloading status."
            ::= { hwEasyOperationClientInfoEntry 16 }

        
        hwEasyOperationClientInfoClientDownloadConfig OBJECT-TYPE
            SYNTAX DisplayString
            MAX-ACCESS read-create
            STATUS current
            DESCRIPTION
                "The configuration file name of client in downloading status."
            ::= { hwEasyOperationClientInfoEntry 17 }

        
        hwEasyOperationClientInfoClientDownloadPatch OBJECT-TYPE
            SYNTAX DisplayString
            MAX-ACCESS read-create
            STATUS current
            DESCRIPTION
                "The patch file name of client in downloading status."
            ::= { hwEasyOperationClientInfoEntry 18 }

        
        hwEasyOperationClientInfoClientDownloadWebFile OBJECT-TYPE
            SYNTAX DisplayString
            MAX-ACCESS read-create
            STATUS current
            DESCRIPTION
                "The WEB file name of client in downloading status."
            ::= { hwEasyOperationClientInfoEntry 19 }

        
        hwEasyOperationClientInfoClientDownloadLicense OBJECT-TYPE
            SYNTAX DisplayString
            MAX-ACCESS read-create
            STATUS current
            DESCRIPTION
                "The license file name of client in downloading status."
            ::= { hwEasyOperationClientInfoEntry 20 }

        
        hwEasyOperationClientInfoClientDownloadCustomfile1 OBJECT-TYPE
            SYNTAX DisplayString
            MAX-ACCESS read-create
            STATUS current
            DESCRIPTION
                "The custom file name of client in downloading status."
            ::= { hwEasyOperationClientInfoEntry 21 }

        
        hwEasyOperationClientInfoClientDownloadCustomfile2 OBJECT-TYPE
            SYNTAX DisplayString
            MAX-ACCESS read-create
            STATUS current
            DESCRIPTION
                "The custom file name of client in downloading status."
            ::= { hwEasyOperationClientInfoEntry 22 }

        
        hwEasyOperationClientInfoClientDownloadCustomfile3 OBJECT-TYPE
            SYNTAX DisplayString
            MAX-ACCESS read-create
            STATUS current
            DESCRIPTION
                "The custom file name of client in downloading status."
            ::= { hwEasyOperationClientInfoEntry 23 }

        
        hwEasyOperationClientInfoClientMethod OBJECT-TYPE
            SYNTAX INTEGER
                {
                running(1),
                upgrade(2),
                zeroTouch(3),
                usbDownload(4),
                unknown(255)
                }
            MAX-ACCESS read-only
            STATUS current
            DESCRIPTION
                "The method of upgrading."
            ::= { hwEasyOperationClientInfoEntry 24 }

        
        hwEasyOperationClientInfoClientPhase OBJECT-TYPE
            SYNTAX INTEGER
                {
                initial(1),
                requestIp(2),
                getDownloadInfo(3),
                downloadFile(4),
                activateFile(5),
                normalRunning(6),
                unknown(255)
                }
            MAX-ACCESS read-only
            STATUS current
            DESCRIPTION
                "The downloading phase of client."
            ::= { hwEasyOperationClientInfoEntry 25 }

        
        hwEasyOperationClientInfoClientOperateState OBJECT-TYPE
            SYNTAX INTEGER
                {
                finished(1),
                downloadSoftware(2),
                downloadConfig(3),
                downloadPatch(4),
                downloadWebFile(5),
                downloadLicense(6),
                downloadCustomFile1(7),
                downloadCustomFile2(8),
                downloadCustomFile3(9),
                unknown(255)
                }
            MAX-ACCESS read-only
            STATUS current
            DESCRIPTION
                "The file type in downloading."
            ::= { hwEasyOperationClientInfoEntry 26 }

        
        hwEasyOperationClientInfoClientDownloadPercent OBJECT-TYPE
            SYNTAX Integer32
            MAX-ACCESS read-only
            STATUS current
            DESCRIPTION
                "The percentage of file downloading."
            ::= { hwEasyOperationClientInfoEntry 27 }

        
        hwEasyOperationClientInfoClientErrorReason OBJECT-TYPE
            SYNTAX Integer32
            MAX-ACCESS read-only
            STATUS current
            DESCRIPTION
                "The error reason in processing."
            ::= { hwEasyOperationClientInfoEntry 28 }

        
        hwEasyOperationClientInfoClientErrorDescr OBJECT-TYPE
            SYNTAX DisplayString
            MAX-ACCESS read-only
            STATUS current
            DESCRIPTION
                "The error description in processing."
            ::= { hwEasyOperationClientInfoEntry 29 }

        
        hwEasyOperationClientInfoClientBackupErrorReason OBJECT-TYPE
            SYNTAX Integer32
            MAX-ACCESS read-only
            STATUS current
            DESCRIPTION
                "The error reason in backup configuration."
            ::= { hwEasyOperationClientInfoEntry 30 }

        
        hwEasyOperationClientInfoClientBackupErrorDescr OBJECT-TYPE
            SYNTAX DisplayString
            MAX-ACCESS read-only
            STATUS current
            DESCRIPTION
                "The error description in backup configuration."
            ::= { hwEasyOperationClientInfoEntry 31 }

        hwEasyOperationClientInfoClientRunState OBJECT-TYPE
            SYNTAX INTEGER
                {
                initial(1),
                normalRunning(2),
                upgrading(3),
                lost(4),
                configuring(5),
                unknown(255)
                }
            MAX-ACCESS read-only
            STATUS current
            DESCRIPTION
                "The running state of client."
            ::= { hwEasyOperationClientInfoEntry 32 }

        hwEasyOperationClientInfoClientCpuUsage OBJECT-TYPE
            SYNTAX Integer32
            MAX-ACCESS read-only
            STATUS current
            DESCRIPTION
                "The cpu usage of client."
            ::= { hwEasyOperationClientInfoEntry 33 }
        
        hwEasyOperationClientInfoClientMemoryUsage OBJECT-TYPE
            SYNTAX Integer32
            MAX-ACCESS read-only
            STATUS current
            DESCRIPTION
                "The memory usage of client."
            ::= { hwEasyOperationClientInfoEntry 34 }

        
        hwEasyOperationClientInfoClientRowStatus OBJECT-TYPE
            SYNTAX RowStatus
            MAX-ACCESS read-create
            STATUS current
            DESCRIPTION
                "The RowStatus of client table."
            ::= { hwEasyOperationClientInfoEntry 100 }

        
        hwEasyOperationClientReplaceTable OBJECT-TYPE
            SYNTAX SEQUENCE OF HwEasyOperationClientReplaceEntry
            MAX-ACCESS not-accessible
            STATUS current
            DESCRIPTION
                "The replace client table."
            ::= { hwEasyOperationClient 3 }

        
        hwEasyOperationClientReplaceEntry OBJECT-TYPE
            SYNTAX HwEasyOperationClientReplaceEntry
            MAX-ACCESS not-accessible
            STATUS current
            DESCRIPTION
                "The entry of replace client table."
            INDEX { hwEasyOperationClientReplaceClientIndex }
            ::= { hwEasyOperationClientReplaceTable 1 }

        
        HwEasyOperationClientReplaceEntry ::=
            SEQUENCE { 
                hwEasyOperationClientReplaceClientIndex
                    Integer32,
                hwEasyOperationClientReplaceNewMacAddress
                    MacAddress,
                hwEasyOperationClientReplaceNewEsn
                    DisplayString,
                hwEasyOperationClientReplaceDownloadSoftware
                    DisplayString,
                hwEasyOperationClientReplaceDownloadSoftwareVer
                    DisplayString,
                hwEasyOperationClientReplaceDownloadPatch
                    DisplayString,
                hwEasyOperationClientReplaceDownloadWebFile
                    DisplayString,
                hwEasyOperationClientReplaceDownloadLicense
                    DisplayString,
                hwEasyOperationClientReplaceDownloadCustomfile1
                    DisplayString,
                hwEasyOperationClientReplaceDownloadCustomfile2
                    DisplayString,
                hwEasyOperationClientReplaceDownloadCustomfile3
                    DisplayString,
                hwEasyOperationClientReplaceRowStatus
                    RowStatus
             }

        hwEasyOperationClientReplaceClientIndex OBJECT-TYPE
            SYNTAX Integer32 (1..4096)
            MAX-ACCESS not-accessible
            STATUS current
            DESCRIPTION
                "The index of replace client table."
            ::= { hwEasyOperationClientReplaceEntry 1 }

        
        hwEasyOperationClientReplaceNewMacAddress OBJECT-TYPE
            SYNTAX MacAddress
            MAX-ACCESS read-create
            STATUS current
            DESCRIPTION
                "The MAC address of new device."
            ::= { hwEasyOperationClientReplaceEntry 2 }

        
        hwEasyOperationClientReplaceNewEsn OBJECT-TYPE
            SYNTAX DisplayString
            MAX-ACCESS read-create
            STATUS current
            DESCRIPTION
                "The ESN of new device."
            ::= { hwEasyOperationClientReplaceEntry 3 }

        
        hwEasyOperationClientReplaceDownloadSoftware OBJECT-TYPE
            SYNTAX DisplayString
            MAX-ACCESS read-create
            STATUS current
            DESCRIPTION
                "The software file name needs to be downloaded."
            ::= { hwEasyOperationClientReplaceEntry 4 }

        
        hwEasyOperationClientReplaceDownloadSoftwareVer OBJECT-TYPE
            SYNTAX DisplayString
            MAX-ACCESS read-create
            STATUS current
            DESCRIPTION
                "The software version needs to be downloaded."
            ::= { hwEasyOperationClientReplaceEntry 5 }

        
        hwEasyOperationClientReplaceDownloadPatch OBJECT-TYPE
            SYNTAX DisplayString
            MAX-ACCESS read-create
            STATUS current
            DESCRIPTION
                "The patch file name needs to be downloaded."
            ::= { hwEasyOperationClientReplaceEntry 6 }

        
        hwEasyOperationClientReplaceDownloadWebFile OBJECT-TYPE
            SYNTAX DisplayString
            MAX-ACCESS read-create
            STATUS current
            DESCRIPTION
                "The WEB file name needs to be downloaded."
            ::= { hwEasyOperationClientReplaceEntry 7 }

        
        hwEasyOperationClientReplaceDownloadLicense OBJECT-TYPE
            SYNTAX DisplayString
            MAX-ACCESS read-create
            STATUS current
            DESCRIPTION
                "The license file name needs to be downloaded."
            ::= { hwEasyOperationClientReplaceEntry 8 }

        
        hwEasyOperationClientReplaceDownloadCustomfile1 OBJECT-TYPE
            SYNTAX DisplayString
            MAX-ACCESS read-create
            STATUS current
            DESCRIPTION
                "The custom file name needs to be downloaded."
            ::= { hwEasyOperationClientReplaceEntry 9 }

        
        hwEasyOperationClientReplaceDownloadCustomfile2 OBJECT-TYPE
            SYNTAX DisplayString
            MAX-ACCESS read-create
            STATUS current
            DESCRIPTION
                "The custom file name needs to be downloaded."
            ::= { hwEasyOperationClientReplaceEntry 10 }

        
        hwEasyOperationClientReplaceDownloadCustomfile3 OBJECT-TYPE
            SYNTAX DisplayString
            MAX-ACCESS read-create
            STATUS current
            DESCRIPTION
                "The custom file name needs to be downloaded."
            ::= { hwEasyOperationClientReplaceEntry 11 }

        
        hwEasyOperationClientReplaceRowStatus OBJECT-TYPE
            SYNTAX RowStatus
            MAX-ACCESS read-create
            STATUS current
            DESCRIPTION
                "The RowStatus of table."
            ::= { hwEasyOperationClientReplaceEntry 50 }

        
        hwEasyOperationNotification OBJECT IDENTIFIER ::= { hwEasyOperationMIB 6 }

        
        hwEasyOperationTrapVar OBJECT IDENTIFIER ::= { hwEasyOperationNotification 1 }

        
        hwEasyOperationTrap OBJECT IDENTIFIER ::= { hwEasyOperationNotification 2 }

        
        hwEasyOperationClientAdded NOTIFICATION-TYPE
            OBJECTS { hwEasyOperationClientInfoClientHostName, hwEasyOperationClientInfoClientIpAddress, hwEasyOperationClientInfoClientMacAddress, hwEasyOperationClientInfoClientEsn }
            STATUS current
            DESCRIPTION 
                "The notification of client added."
            ::= { hwEasyOperationTrap 1 }

        
        hwEasyOperationClientLost NOTIFICATION-TYPE
            OBJECTS { hwEasyOperationClientInfoClientHostName, hwEasyOperationClientInfoClientIpAddress, hwEasyOperationClientInfoClientMacAddress, hwEasyOperationClientInfoClientEsn }
            STATUS current
            DESCRIPTION 
                "The notification of client lost."
            ::= { hwEasyOperationTrap 2 }

        hwEasyOperationClientJoinNotPermit NOTIFICATION-TYPE
            OBJECTS { hwEasyOperationClientInfoClientHostName, hwEasyOperationClientInfoClientIpAddress, hwEasyOperationClientInfoClientMacAddress, hwEasyOperationClientInfoClientEsn }
            STATUS current
            DESCRIPTION 
                "The notification of not permit client to join."
            ::= { hwEasyOperationTrap 3 }

		hwEasyOperationMonitor OBJECT IDENTIFIER ::= { hwEasyOperationMIB 7 }

		
		hwEasyOperationPowerInfo OBJECT IDENTIFIER ::= { hwEasyOperationMonitor 1 }

		
		hwEasyOperationDevicePowerInfoTable OBJECT-TYPE
			SYNTAX SEQUENCE OF HwEasyOperationDevicePowerInfoEntry
			MAX-ACCESS not-accessible
			STATUS current
			DESCRIPTION
				"The device power information table."
			::= { hwEasyOperationPowerInfo 1 }

		
		hwEasyOperationDevicePowerInfoEntry OBJECT-TYPE
			SYNTAX HwEasyOperationDevicePowerInfoEntry
			MAX-ACCESS not-accessible
			STATUS current
			DESCRIPTION
				"The entry of device power infomation table."
			INDEX { hwEasyOperationDevicePowerInfoIndex }
			::= { hwEasyOperationDevicePowerInfoTable 1 }

		
		HwEasyOperationDevicePowerInfoEntry ::=
			SEQUENCE { 
				hwEasyOperationDevicePowerInfoIndex
					Integer32,
				hwEasyOperationDevicePowerInfoCurrentPower
					Integer32,
				hwEasyOperationDevicePowerInfoGauge
					INTEGER,
				hwEasyOperationDevicePowerInfoRatedPower
					Integer32,
				hwEasyOperationDevicePowerInfoPowerManageMode
					INTEGER
			 }

		hwEasyOperationDevicePowerInfoIndex OBJECT-TYPE
			SYNTAX Integer32
			MAX-ACCESS not-accessible
			STATUS current
			DESCRIPTION
				"The index of device power table."
			::= { hwEasyOperationDevicePowerInfoEntry 1 }

		
		hwEasyOperationDevicePowerInfoCurrentPower OBJECT-TYPE
			SYNTAX Integer32
			MAX-ACCESS read-only
			STATUS current
			DESCRIPTION
				"The current power of device."
			::= { hwEasyOperationDevicePowerInfoEntry 2 }

		
		hwEasyOperationDevicePowerInfoGauge OBJECT-TYPE
			SYNTAX INTEGER
				{
				actual(1),
				rated(2)
				}
			MAX-ACCESS read-only
			STATUS current
			DESCRIPTION
				"The gauge of device power."
			::= { hwEasyOperationDevicePowerInfoEntry 3 }

		
		hwEasyOperationDevicePowerInfoRatedPower OBJECT-TYPE
			SYNTAX Integer32
			MAX-ACCESS read-only
			STATUS current
			DESCRIPTION
				"The rated power of device."
			::= { hwEasyOperationDevicePowerInfoEntry 4 }

		
		hwEasyOperationDevicePowerInfoPowerManageMode OBJECT-TYPE
			SYNTAX INTEGER
				{
				userDefined(1),
				standard(2),
				basic(3),
				deep(4)
				}
			MAX-ACCESS read-only
			STATUS current
			DESCRIPTION
				"The power manage mode of device."
			::= { hwEasyOperationDevicePowerInfoEntry 5 }

		
		hwEasyOperationPortPowerInfoTable OBJECT-TYPE
			SYNTAX SEQUENCE OF HwEasyOperationPortPowerInfoEntry
			MAX-ACCESS not-accessible
			STATUS current
			DESCRIPTION
				"The port power information table."
			::= { hwEasyOperationPowerInfo 2 }

		
		hwEasyOperationPortPowerInfoEntry OBJECT-TYPE
			SYNTAX HwEasyOperationPortPowerInfoEntry
			MAX-ACCESS not-accessible
			STATUS current
			DESCRIPTION
				"The entry of port power table."
			INDEX { hwEasyOperationPortPowerInfoDeviceIndex, hwEasyOperationPortPowerInfoPortIndex }
			::= { hwEasyOperationPortPowerInfoTable 1 }

		
		HwEasyOperationPortPowerInfoEntry ::=
			SEQUENCE { 
				hwEasyOperationPortPowerInfoDeviceIndex
					Integer32,
				hwEasyOperationPortPowerInfoPortIndex
					Integer32,
				hwEasyOperationPortPowerInfoPortName
					OCTET STRING,
				hwEasyOperationPortPowerInfoCurrentPower
					Integer32,
				hwEasyOperationPortPowerInfoGauge
					INTEGER
			 }

		hwEasyOperationPortPowerInfoDeviceIndex OBJECT-TYPE
			SYNTAX Integer32
			MAX-ACCESS not-accessible
			STATUS current
			DESCRIPTION
				"The index of device."
			::= { hwEasyOperationPortPowerInfoEntry 1 }

		
		hwEasyOperationPortPowerInfoPortIndex OBJECT-TYPE
			SYNTAX Integer32
			MAX-ACCESS not-accessible
			STATUS current
			DESCRIPTION
				"The index of port."
			::= { hwEasyOperationPortPowerInfoEntry 2 }

		
		hwEasyOperationPortPowerInfoPortName OBJECT-TYPE
			SYNTAX OCTET STRING
			MAX-ACCESS read-only
			STATUS current
			DESCRIPTION
				"The port name."
			::= { hwEasyOperationPortPowerInfoEntry 3 }

		
		hwEasyOperationPortPowerInfoCurrentPower OBJECT-TYPE
			SYNTAX Integer32
			MAX-ACCESS read-only
			STATUS current
			DESCRIPTION
				"The current power of port."
			::= { hwEasyOperationPortPowerInfoEntry 4 }

		
		hwEasyOperationPortPowerInfoGauge OBJECT-TYPE
			SYNTAX INTEGER
				{
				actual(1),
				presumed(2)
				}
			MAX-ACCESS read-write
			STATUS current
			DESCRIPTION
				"The gauge of port power."
			::= { hwEasyOperationPortPowerInfoEntry 5 }

		hwEasyOperationNetPowerHistoryInfoTable OBJECT-TYPE
			SYNTAX SEQUENCE OF HwEasyOperationNetPowerHistoryInfoEntry
			MAX-ACCESS not-accessible
			STATUS current
			DESCRIPTION
				"The net power history information table."
			::= { hwEasyOperationPowerInfo 3 }

		
		hwEasyOperationNetPowerHistoryInfoEntry OBJECT-TYPE
			SYNTAX HwEasyOperationNetPowerHistoryInfoEntry
			MAX-ACCESS not-accessible
			STATUS current
			DESCRIPTION
				"The entry of net power history table."
			INDEX { hwEasyOperationNetPowerHistoryInfoIndex }
			::= { hwEasyOperationNetPowerHistoryInfoTable 1 }

		
		HwEasyOperationNetPowerHistoryInfoEntry ::=
			SEQUENCE { 
				hwEasyOperationNetPowerHistoryInfoIndex
					Integer32,
				hwEasyOperationNetPowerHistoryInfoWholePower
					Integer32
			 }

		hwEasyOperationNetPowerHistoryInfoIndex OBJECT-TYPE
			SYNTAX Integer32
			MAX-ACCESS not-accessible
			STATUS current
			DESCRIPTION
				"The index of the table."
			::= { hwEasyOperationNetPowerHistoryInfoEntry 1 }

		hwEasyOperationNetPowerHistoryInfoWholePower OBJECT-TYPE
			SYNTAX Integer32
			MAX-ACCESS read-only
			STATUS current
			DESCRIPTION
				"The total power of the whole network."
			::= { hwEasyOperationNetPowerHistoryInfoEntry 2 }

		
		hwEasyOperationTopologyTable OBJECT-TYPE
			SYNTAX SEQUENCE OF HwEasyOperationTopologyEntry
			MAX-ACCESS not-accessible
			STATUS current
			DESCRIPTION
				"The topology table."
			::= { hwEasyOperationMonitor 3 }

		
		hwEasyOperationTopologyEntry OBJECT-TYPE
			SYNTAX HwEasyOperationTopologyEntry
			MAX-ACCESS not-accessible
			STATUS current
			DESCRIPTION
				"The entry of topology table."
			INDEX { hwEasyOperationTopologyHopIndex, hwEasyOperationTopologyDeviceIndex }
			::= { hwEasyOperationTopologyTable 1 }

		
		HwEasyOperationTopologyEntry ::=
			SEQUENCE { 
				hwEasyOperationTopologyHopIndex
					Integer32,
				hwEasyOperationTopologyDeviceIndex
					Integer32,
				hwEasyOperationTopologyLocalMac
					MacAddress,
				hwEasyOperationTopologyFatherMac
					MacAddress,
				hwEasyOperationTopologyLocalPortName
					OCTET STRING,
				hwEasyOperationTopologyFatherPortName
					OCTET STRING,
				hwEasyOperationTopologyLocalDeviceId
					Integer32,
				hwEasyOperationTopologyFatherDeviceId
					Integer32
			 }

		hwEasyOperationTopologyHopIndex OBJECT-TYPE
			SYNTAX Integer32
			MAX-ACCESS not-accessible
			STATUS current
			DESCRIPTION
				"The topoloy hop."
			::= { hwEasyOperationTopologyEntry 1 }

		
		hwEasyOperationTopologyDeviceIndex OBJECT-TYPE
			SYNTAX Integer32
			MAX-ACCESS not-accessible
			STATUS current
			DESCRIPTION
				"The index of topology device."
			::= { hwEasyOperationTopologyEntry 2 }

		
		hwEasyOperationTopologyLocalMac OBJECT-TYPE
			SYNTAX MacAddress
			MAX-ACCESS read-only
			STATUS current
			DESCRIPTION
				"The mac address of local topology node."
			::= { hwEasyOperationTopologyEntry 3 }

		
		hwEasyOperationTopologyFatherMac OBJECT-TYPE
			SYNTAX MacAddress
			MAX-ACCESS read-only
			STATUS current
			DESCRIPTION
				"The mac address of father topology node."
			::= { hwEasyOperationTopologyEntry 4 }

		
		hwEasyOperationTopologyLocalPortName OBJECT-TYPE
			SYNTAX OCTET STRING
			MAX-ACCESS read-only
			STATUS current
			DESCRIPTION
				"The port name of local topology node."
			::= { hwEasyOperationTopologyEntry 5 }

		
		hwEasyOperationTopologyFatherPortName OBJECT-TYPE
			SYNTAX OCTET STRING
			MAX-ACCESS read-only
			STATUS current
			DESCRIPTION
				"The port name of father topology node."
			::= { hwEasyOperationTopologyEntry 6 }

		
		hwEasyOperationTopologyLocalDeviceId OBJECT-TYPE
			SYNTAX Integer32
			MAX-ACCESS read-only
			STATUS current
			DESCRIPTION
				"The device id of local topology node."
			::= { hwEasyOperationTopologyEntry 7 }

		hwEasyOperationTopologyFatherDeviceId OBJECT-TYPE
			SYNTAX Integer32
			MAX-ACCESS read-only
			STATUS current
			DESCRIPTION
				"The device id of father topology node."
			::= { hwEasyOperationTopologyEntry 8 }

		hwEasyOperationSavedTopologyTable OBJECT-TYPE
			SYNTAX SEQUENCE OF HwEasyOperationSavedTopologyEntry
			MAX-ACCESS not-accessible
			STATUS current
			DESCRIPTION
				"The saved topology table."
			::= { hwEasyOperationMonitor 4 }

		
		hwEasyOperationSavedTopologyEntry OBJECT-TYPE
			SYNTAX HwEasyOperationSavedTopologyEntry
			MAX-ACCESS not-accessible
			STATUS current
			DESCRIPTION
				"The entry of saved topology table."
			INDEX { hwEasyOperationSavedTopologyHopIndex, hwEasyOperationSavedTopologyDeviceIndex }
			::= { hwEasyOperationSavedTopologyTable 1 }

		
		HwEasyOperationSavedTopologyEntry ::=
			SEQUENCE { 
				hwEasyOperationSavedTopologyHopIndex
					Integer32,
				hwEasyOperationSavedTopologyDeviceIndex
					Integer32,
				hwEasyOperationSavedTopologyLocalMac
					MacAddress,
				hwEasyOperationSavedTopologyFatherMac
					MacAddress,
				hwEasyOperationSavedTopologyLocalPortName
					OCTET STRING,
				hwEasyOperationSavedTopologyFatherPortName
					OCTET STRING

			 }

		hwEasyOperationSavedTopologyHopIndex OBJECT-TYPE
			SYNTAX Integer32
			MAX-ACCESS not-accessible
			STATUS current
			DESCRIPTION
				"The index of saved topology hop."
			::= { hwEasyOperationSavedTopologyEntry 1 }

		
		hwEasyOperationSavedTopologyDeviceIndex OBJECT-TYPE
			SYNTAX Integer32
			MAX-ACCESS not-accessible
			STATUS current
			DESCRIPTION
				"The index of saved topology device."
			::= { hwEasyOperationSavedTopologyEntry 2 }

		
		hwEasyOperationSavedTopologyLocalMac OBJECT-TYPE
			SYNTAX MacAddress
			MAX-ACCESS read-only
			STATUS current
			DESCRIPTION
				"The mac address of saved local topology node."
			::= { hwEasyOperationSavedTopologyEntry 3 }

		
		hwEasyOperationSavedTopologyFatherMac OBJECT-TYPE
			SYNTAX MacAddress
			MAX-ACCESS read-only
			STATUS current
			DESCRIPTION
				"The mac address of saved father topology node."
			::= { hwEasyOperationSavedTopologyEntry 4 }

		
		hwEasyOperationSavedTopologyLocalPortName OBJECT-TYPE
			SYNTAX OCTET STRING
			MAX-ACCESS read-only
			STATUS current
			DESCRIPTION
				"The port name of saved local topology node."
			::= { hwEasyOperationSavedTopologyEntry 5 }

		
		hwEasyOperationSavedTopologyFatherPortName OBJECT-TYPE
			SYNTAX OCTET STRING
			MAX-ACCESS read-only
			STATUS current
			DESCRIPTION
				"The port name of saved father topology node."
			::= { hwEasyOperationSavedTopologyEntry 6 }





--  this module
        hwEasyOperationCompliance MODULE-COMPLIANCE
            STATUS current
            DESCRIPTION 
                "The compliance."
            MODULE -- this module
                MANDATORY-GROUPS { hwEasyOperationGlobalObjectsGroup, hwEasyOperationGroupObjectsGroup, hwEasyOperationGroupTableGroup, hwEasyOperationGroupMatchTableGroup, hwEasyOperationClientObjectsGroup, 
					hwEasyOperationClientInfoGroup, hwEasyOperationTopologyGroup, hwEasyOperationPortPowerInfoGroup, hwEasyOperationDevicePowerInfoGroup, hwEasyOperationNotificationGroup, 
					hwEasyOperationClientReplaceGroup, hwEasyOperationSavedTopologyGroup,hwEasyOperationNetPowerHistoryInfoGroup }
            ::= { hwEasyOperationMIB 100 }

        
        hwEasyOperationGlobalObjectsGroup OBJECT-GROUP
            OBJECTS { hwEasyOperationCommanderIpAddressType, hwEasyOperationBackupConfigMode, hwEasyOperationActivateInTime, hwEasyOperationActivateDelayTime, hwEasyOperationActivateMode, 
                hwEasyOperationAutoClearEnable, hwEasyOperationServerIpAddressType, hwEasyOperationServerIpAddress, hwEasyOperationServerType, hwEasyOperationDefaultSysSoftwareVer, 
                hwEasyOperationDefaultConfig, hwEasyOperationDefaultPatch, hwEasyOperationDefaultWebfile, hwEasyOperationDefaultLicense, hwEasyOperationDefaultCustomfile1, 
                hwEasyOperationDefaultCustomfile2, hwEasyOperationDefaultCustomfile3, hwEasyOperationDefaultSysSoftware, hwEasyOperationBackupConfigInterval, hwEasyOperationCommanderUdpPort, 
				hwEasyOperationServerPort, hwEasyOperationClientAgingTime, hwEasyOperationTopologyEnable, hwEasyOperationCommanderIpAddress, hwEasyOperationCommanderEnable, 
				hwEasyOperationClientAutoJoinEnable }
            STATUS current
            DESCRIPTION 
                "The global objects group."
            ::= { hwEasyOperationCompliance 1 }

        
        hwEasyOperationGroupObjectsGroup OBJECT-GROUP
            OBJECTS { hwEasyOperationTotalGroupNumber, hwEasyOperationBuildInGroupNumber, hwEasyOperationCustomGroupNumber }
            STATUS current
            DESCRIPTION 
                "The group objects group."
            ::= { hwEasyOperationCompliance 2 }

        
        hwEasyOperationGroupTableGroup OBJECT-GROUP
            OBJECTS { hwEasyOperationGroupType, hwEasyOperationGroupName, hwEasyOperationGroupSysSoftware, hwEasyOperationGroupSysSoftwareVer, hwEasyOperationGroupConfig, 
                hwEasyOperationGroupPatch, hwEasyOperationGroupWebfile, hwEasyOperationGroupLicense, hwEasyOperationGroupCustomfile1, hwEasyOperationGroupCustomfile2, 
                hwEasyOperationGroupCustomfile3, hwEasyOperationGroupActivateMode, hwEasyOperationGroupActivateDelayTime, hwEasyOperationGroupActivateInTime, hwEasyOperationGroupRowStatus                
                 }
            STATUS current
            DESCRIPTION 
                "The group table group."
            ::= { hwEasyOperationCompliance 3 }

        
        hwEasyOperationGroupMatchTableGroup OBJECT-GROUP
			      OBJECTS { hwEasyOperationGroupMatchMacAddress, hwEasyOperationGroupMatchEsn, hwEasyOperationGroupMatchModel, 
			                hwEasyOperationGroupMatchDeviceType, hwEasyOperationGroupMatchRowStatus, hwEasyOperationGroupMatchMacMask,
                      hwEasyOperationGroupMatchIpAddress, hwEasyOperationGroupMatchIpAddressType, hwEasyOperationGroupMatchIpAddressMask			                
			               }
            STATUS current
            DESCRIPTION 
                "The match rule table objects group."
            ::= { hwEasyOperationCompliance 4 }

        
        hwEasyOperationClientObjectsGroup OBJECT-GROUP
            OBJECTS { hwEasyOperationClientNumber }
            STATUS current
            DESCRIPTION 
                "The client objects group."
            ::= { hwEasyOperationCompliance 5 }

        
        hwEasyOperationClientInfoGroup OBJECT-GROUP
            OBJECTS { hwEasyOperationClientInfoClientMacAddress, hwEasyOperationClientInfoClientEsn, hwEasyOperationClientInfoClientModel, hwEasyOperationClientInfoClientDeviceType, hwEasyOperationClientInfoClientSysSoftware, 
                hwEasyOperationClientInfoClientSysSoftwareVer, hwEasyOperationClientInfoClientSysConfig, hwEasyOperationClientInfoClientSysPatch, hwEasyOperationClientInfoClientSysWebFile, hwEasyOperationClientInfoClientSysLicense, 
                hwEasyOperationClientInfoClientDownloadSoftware, hwEasyOperationClientInfoClientDownloadSoftwareVer, hwEasyOperationClientInfoClientDownloadConfig, hwEasyOperationClientInfoClientDownloadPatch, hwEasyOperationClientInfoClientDownloadWebFile, 
                hwEasyOperationClientInfoClientDownloadLicense, hwEasyOperationClientInfoClientDownloadCustomfile1, hwEasyOperationClientInfoClientDownloadCustomfile2, hwEasyOperationClientInfoClientDownloadCustomfile3, hwEasyOperationClientInfoClientErrorDescr, 
                hwEasyOperationClientInfoClientIpAddress, hwEasyOperationClientInfoClientRowStatus, hwEasyOperationClientInfoClientHostName, hwEasyOperationClientInfoClientBackupErrorDescr, hwEasyOperationClientInfoClientBackupErrorReason, 
                hwEasyOperationClientInfoClientErrorReason, hwEasyOperationClientInfoClientDownloadPercent, hwEasyOperationClientInfoClientIpAddressType, hwEasyOperationClientInfoClientMethod, hwEasyOperationClientInfoClientPhase, 
                hwEasyOperationClientInfoClientOperateState, hwEasyOperationClientInfoClientRunState, hwEasyOperationClientInfoClientCpuUsage,hwEasyOperationClientInfoClientMemoryUsage }
            STATUS current
            DESCRIPTION 
                "The client table group."
            ::= { hwEasyOperationCompliance 6 }

        
        hwEasyOperationClientReplaceGroup OBJECT-GROUP
            OBJECTS { hwEasyOperationClientReplaceRowStatus, hwEasyOperationClientReplaceDownloadCustomfile3, hwEasyOperationClientReplaceDownloadCustomfile2, hwEasyOperationClientReplaceDownloadCustomfile1, hwEasyOperationClientReplaceDownloadLicense, 
                hwEasyOperationClientReplaceDownloadWebFile, hwEasyOperationClientReplaceDownloadPatch, hwEasyOperationClientReplaceDownloadSoftwareVer, hwEasyOperationClientReplaceDownloadSoftware, hwEasyOperationClientReplaceNewEsn, 
                hwEasyOperationClientReplaceNewMacAddress }
            STATUS current
            DESCRIPTION 
                "The replace client table group."
            ::= { hwEasyOperationCompliance 7 }

        
        hwEasyOperationNotificationGroup NOTIFICATION-GROUP
            NOTIFICATIONS { hwEasyOperationClientAdded, hwEasyOperationClientLost }
            STATUS current
            DESCRIPTION 
                "The notification objects group."
            ::= { hwEasyOperationCompliance 8 }

		
		hwEasyOperationDevicePowerInfoGroup OBJECT-GROUP
			OBJECTS { hwEasyOperationDevicePowerInfoCurrentPower, hwEasyOperationDevicePowerInfoGauge, hwEasyOperationDevicePowerInfoRatedPower, hwEasyOperationDevicePowerInfoPowerManageMode }
			STATUS current
			DESCRIPTION 
				"The device power information table group."
			::= { hwEasyOperationCompliance 9 }

		
		hwEasyOperationPortPowerInfoGroup OBJECT-GROUP
			OBJECTS { hwEasyOperationPortPowerInfoPortName, hwEasyOperationPortPowerInfoCurrentPower, hwEasyOperationPortPowerInfoGauge }
			STATUS current
			DESCRIPTION 
				"The port power information table group."
			::= { hwEasyOperationCompliance 10 }

		
		hwEasyOperationTopologyGroup OBJECT-GROUP
			OBJECTS { hwEasyOperationTopologyLocalMac, hwEasyOperationTopologyFatherMac, hwEasyOperationTopologyLocalPortName, hwEasyOperationTopologyFatherPortName,
			          hwEasyOperationTopologyLocalDeviceId, hwEasyOperationTopologyFatherDeviceId}
			STATUS current
			DESCRIPTION 
				"The topology table group."
			::= { hwEasyOperationCompliance 11 }

		hwEasyOperationSavedTopologyGroup OBJECT-GROUP
			OBJECTS { hwEasyOperationSavedTopologyLocalMac, hwEasyOperationSavedTopologyFatherMac, hwEasyOperationSavedTopologyLocalPortName, hwEasyOperationSavedTopologyFatherPortName
				        }
			STATUS current
			DESCRIPTION 
				"The saved topology table group."
			::= { hwEasyOperationCompliance 12 }

		hwEasyOperationNetPowerHistoryInfoGroup OBJECT-GROUP
			OBJECTS { hwEasyOperationNetPowerHistoryInfoWholePower  }
			STATUS current
			DESCRIPTION 
				"The power history of whole network table group."
			::= { hwEasyOperationCompliance 13 }


    END

--
-- 
--
