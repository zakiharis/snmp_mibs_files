-- Title:         Fibronics' MIB  
-- MIB Module :   Private MIB for  NM349
-- Version    :   V1.0
-- Date       :   Jan 1, 1995
-- By         :   Gadi K.
-- Contact    :   Edna Ganon
-- Email:     :   edna@fibronics.co.il 
-- 
-- Description:   NM349 Private Ethernet Repeater Mib
-- Copyright (c) 1994 Fibronics International

           Hub-rptr-prvt DEFINITIONS ::= BEGIN
			  
			  IMPORTS OBJECT-TYPE, internet FROM SNMPv2-SMI
			  DisplayString FROM SNMPv2-TC
			  Counter FROM RFC1155-SMI;

           private               OBJECT IDENTIFIER ::= { internet 4 }
           enterprises           OBJECT IDENTIFIER ::= { private 1 }
           fibronics             OBJECT IDENTIFIER ::= { enterprises 22 }
           mibs                  OBJECT IDENTIFIER ::= { fibronics 101 }
           mibseth-rptrs         OBJECT IDENTIFIER ::= { mibs 8 }
           xrptrinfo             OBJECT IDENTIFIER ::= { mibseth-rptrs 1 }
           xrptrgroup            OBJECT IDENTIFIER ::= { mibseth-rptrs 2 }
           xrptrgroupport        OBJECT IDENTIFIER ::= { mibseth-rptrs 3 }
           xrptrgroupmodule      OBJECT IDENTIFIER ::= { mibseth-rptrs 4 }

-- ------------------------------------------------
--         Repeater Level
-- ------------------------------------------------

xrptrRxDscrptrOverFlows        OBJECT-TYPE
        SYNTAX  Counter
        ACCESS  read-only
        STATUS  mandatory
        DESCRIPTION "This counter reflects the number of the
                     missed received packets due to lack of resources
                     such as descriptors or memory buffers"
        ::= { xrptrinfo 1 }

xrptrTxDscrptrOverFlows        OBJECT-TYPE
        SYNTAX  Counter
        ACCESS  read-only
        STATUS  mandatory
        DESCRIPTION "This counter is incremented every time
                     there is a transmit overflow"
        ::= { xrptrinfo 2 }


xrptrMemoryErrors        OBJECT-TYPE
        SYNTAX  Counter
        ACCESS  read-only
        STATUS  mandatory
        DESCRIPTION "This counter is incremented every time
                     there is a memory error"
        ::= { xrptrinfo 3 }

xrptrJabbers        OBJECT-TYPE
        SYNTAX  Counter
        ACCESS  read-only
        STATUS  mandatory
        DESCRIPTION "This counter is incremented every time
                     there is a jabber in one of the ports."
        ::= { xrptrinfo 4 }



xrptrNMSPort      OBJECT-TYPE
        SYNTAX  INTEGER
        ACCESS  read-only
        STATUS  mandatory
        DESCRIPTION "Returns the port number which the
                     NMS is connected to. If an NMS
                     is not connected to the card
                     the value returned will be 99."
        ::= { xrptrinfo 5 }

xrptrNMSGroup      OBJECT-TYPE
        SYNTAX  INTEGER
        ACCESS  read-only
        STATUS  mandatory
        DESCRIPTION "Returns the group number which the
                     NMS is connected to. If the NMS
                     is not connected to a card
                     the value returned will be 99."
        ::= { xrptrinfo 6 }


xrptrESMPort      OBJECT-TYPE
        SYNTAX  INTEGER
        ACCESS  read-only
        STATUS  mandatory
        DESCRIPTION "Returns the port number which the
                     GigaHub (ESM) is connected to. If the
                     GigaHub is not connected to the card
                     the value returned will be 99."
        ::= { xrptrinfo 7 }

xrptrESMGroup      OBJECT-TYPE
        SYNTAX  INTEGER
        ACCESS  read-only
        STATUS  mandatory
        DESCRIPTION "Returns the group number which the
                     GigaHub (ESM) is connected to. If the
                     GigaHub is not connected to a card
                     the value returned will be 99."
        ::= { xrptrinfo 8 }


xrptrSmCpuError      OBJECT-TYPE
        SYNTAX  INTEGER {
                fault-exist(1),
                no-fault-exist(2)
                }
        ACCESS  read-only
        STATUS  mandatory
        DESCRIPTION "CPU Fault status. If
                     the value is fault-exist(1) - there is a
                     CPU fault in the repeater manager card."
        ::= {xrptrinfo 9  }


xrptrSmControllerError      OBJECT-TYPE
        SYNTAX  INTEGER {
                fault-exist(1),
                no-fault-exist(2)
                }
        ACCESS  read-only
        STATUS  mandatory
        DESCRIPTION "Controller Fault status. If
                     the value is fault-exist(1) - there is a
                     fault in the Ethernet control block
                     of the repeater manager card."
        ::= {xrptrinfo 10  }

-- ------------------------------------------------
--         Group Level
-- ------------------------------------------------

xrptrGroupTable     OBJECT-TYPE
        SYNTAX  SEQUENCE OF XrptrGroupEntry
        ACCESS  not-accessible
        STATUS  mandatory
        DESCRIPTION "Table of entries with global information on each group.
                     Information or error may stem from one single port in
                     group, but is displayed as group info/error. "
        ::= { xrptrgroup 1 }


xrptrGroupEntry     OBJECT-TYPE
        SYNTAX  XrptrGroupEntry
        ACCESS  not-accessible
        STATUS  mandatory
        DESCRIPTION "Entry per group containing info/errors on the group."
        INDEX   { xrptrGroupIndex }
        ::= { xrptrGroupTable 1 }

XrptrGroupEntry ::= SEQUENCE {
        xrptrGroupIndex
                INTEGER,
        xrptrGroupGlobalStatus
                OCTET STRING,
        xrptrGroupPrevStatus
                OCTET STRING,
        xrptrGroupGlobalError
                INTEGER,
        xrptrGroupJabberError
                INTEGER,
        xrptrGroupRepeaterCpuBlockError
                INTEGER,
        xrptrGroupAutoPartition
                INTEGER,
        xrptrGroupDetachStatus
                INTEGER,
        xrptrGroupGlobalCommandCode
                INTEGER,
        xrptrGroupTrapMask
                INTEGER,
        xrptrGroupLinkSelectHead1
                INTEGER,
        xrptrGroupBackupHead1State
                INTEGER,
        xrptrGroupMaxModuleNumber
                INTEGER,
        xrptrGroupSlotNumber
                INTEGER,
        xrptrGroupSlotInternalIndex
                INTEGER
}


xrptrGroupIndex     OBJECT-TYPE
        SYNTAX  INTEGER
        ACCESS  read-only
        STATUS  mandatory
        DESCRIPTION "Group Number"
        ::= { xrptrGroupEntry 1 }

xrptrGroupGlobalStatus      OBJECT-TYPE
        SYNTAX  OCTET STRING
        ACCESS  read-only
        STATUS  mandatory
        DESCRIPTION "8 bytes. 60 status bits of
                the card. For more information about
                the meaning of the status, read the
                specific user manual of each card.
                The channel leds are encoded into
                2 bytes."
        ::= { xrptrGroupEntry 2 }

xrptrGroupPrevStatus      OBJECT-TYPE
        SYNTAX  OCTET STRING
        ACCESS  read-only
        STATUS  mandatory
        DESCRIPTION "8 bytes. Previous 60 status
                   bits of the card. This
                   object id is used mainly
                   for traps (see Card Trap)"
        ::= { xrptrGroupEntry 3 }


xrptrGroupGlobalError      OBJECT-TYPE
        SYNTAX  INTEGER {
                fault-exist(1),
                no-fault-exist(2)
                }
        ACCESS  read-only
        STATUS  mandatory
        DESCRIPTION "Group Global Fault status. If
                     the value is fault-exist(1) - there
                     is a fault in the card."
        ::= { xrptrGroupEntry 4 }

xrptrGroupJabberError      OBJECT-TYPE
        SYNTAX  INTEGER {
                fault-exist(1),
                no-fault-exist(2)
                }
        ACCESS  read-only
        STATUS  mandatory
        DESCRIPTION "Jabber Fault status. If
                     the value is fault-exist(1) - there is a
                     jabber event."
        ::= { xrptrGroupEntry 5 }



xrptrGroupRepeaterCpuBlockError      OBJECT-TYPE
        SYNTAX  INTEGER {
                fault-exist(1),
                no-fault-exist(2)
                }
        ACCESS  read-only
        STATUS  mandatory
        DESCRIPTION "Repeater Block Fault status. If
                     the value is fault-exist(1) - there is a
                     fault in the repeater block or cpu
                     block of the repeater card."
        ::= { xrptrGroupEntry 8 }


xrptrGroupAutoPartition      OBJECT-TYPE
        SYNTAX  INTEGER {
                fault-exist(1),
                no-fault-exist(2)
                }
        ACCESS  read-only
        STATUS  mandatory
        DESCRIPTION "Group Auto partition Fault status. If
                     the value is fault-exist(1) - at least one of
                     the ports is in auto-partition."
        ::= { xrptrGroupEntry 9 }


xrptrGroupDetachStatus      OBJECT-TYPE
        SYNTAX  INTEGER {
                detach-exist(1),
                no-detach-exist(2)
                }
        ACCESS  read-only
        STATUS  mandatory
        DESCRIPTION "Global Detach status. If
                     the value is fault-exist(1) -
                     at least one of the ports is detached."
        ::= { xrptrGroupEntry 10 }


xrptrGroupGlobalCommandCode   OBJECT-TYPE
        SYNTAX  INTEGER {
                attach-all-ports(1),
                detach-all-ports(2)
                }
        ACCESS  read-write
        STATUS  mandatory
        DESCRIPTION "Enable the user to attach/detach all repeater
                     ports. Note: in case of detach command - all ports
                     will detach except the port on which the
                     last NMS message was received.
                     When reading this object the value returned
                     is always attach-all-ports(1)"
        ::= { xrptrGroupEntry 11 }


xrptrGroupTrapMask  OBJECT-TYPE
        SYNTAX  INTEGER {
                mask-all(1),
                mask-fatal(2),
                mask-warn(3),
                mask-info(4)
                }
        ACCESS  read-write
        STATUS  mandatory
        DESCRIPTION "If this variable is set to mask-info(4)
                     all traps will be sent.
                     If this variable is set to mask-warn(3)
                     only traps with severity WARN or FATAL
                     will be sent.
                     If this variable is set to mask-fatal(2)
                     only traps with severity FATAL will be sent.
                     If this variable is set to mask-all(1)
                     then no traps will be sent."
        ::= { xrptrGroupEntry 12 }

xrptrGroupLinkSelectHead1   OBJECT-TYPE
        SYNTAX  INTEGER {
                toggle-link-select(1)
                }
        ACCESS  read-write
        STATUS  mandatory
        DESCRIPTION  "Enable the user to switch between MAIN
                     and SECOND link only in Head module in
                     the 342 type cards."
        ::= { xrptrGroupEntry 13 }

xrptrGroupBackupHead1State   OBJECT-TYPE
        SYNTAX  INTEGER {
                primary(1),
                secondary(2),
                normal(3),
                not-applicable(4)
                }
        ACCESS  read-write
        STATUS  mandatory
        DESCRIPTION "Allow the user to enable or disable
                     the backup port for Head module only
                     in 342 cards. When set to primary(1)
                     the active port will be the primary port,
                     when set to secondary(2) the active port
                     will be the secondary port and when set
                     to normal(3) the active port will be set
                     by the backup algorithm."
        ::= { xrptrGroupEntry 14 }


xrptrGroupMaxModuleNumber     OBJECT-TYPE
        SYNTAX  INTEGER
        ACCESS  read-only
        STATUS  mandatory
        DESCRIPTION "Maximum Number of modules in a group."
        ::= { xrptrGroupEntry 15 }



xrptrGroupSlotNumber        OBJECT-TYPE
        SYNTAX  INTEGER
        ACCESS  read-only
        STATUS  mandatory
        DESCRIPTION "Physical slot index of the group"
        ::= { xrptrGroupEntry 16 }


xrptrGroupSlotInternalIndex   OBJECT-TYPE
        SYNTAX  INTEGER
        ACCESS  read-only
        STATUS  mandatory
        DESCRIPTION "Internal index of the group within its slot"
        ::= { xrptrGroupEntry 17 }


------------------------------------------------------
-- group fault table
------------------------------------------------------

xrptrGroupFaultTable  OBJECT-TYPE
        SYNTAX  SEQUENCE OF XrptrGroupFaultEntry
        ACCESS  not-accessible
        STATUS  mandatory
        DESCRIPTION "Table of fault reports per group."
         ::= { xrptrgroup 2 }


xrptrGroupFaultEntry  OBJECT-TYPE
        SYNTAX  XrptrGroupFaultEntry
        ACCESS  not-accessible
        STATUS  mandatory
        DESCRIPTION "Entry of fault information."
        INDEX   { xrptrGroupGroupIndex, xrptrGroupFaultIndex}
        ::=     { xrptrGroupFaultTable 1 }


XrptrGroupFaultEntry ::= SEQUENCE {
         xrptrGroupGroupIndex
                INTEGER,
        xrptrGroupFaultIndex
                INTEGER,
        xrptrGroupFaultReport
                DisplayString
        }

xrptrGroupGroupIndex     OBJECT-TYPE
        SYNTAX  INTEGER
        ACCESS  read-only
        STATUS  mandatory
        DESCRIPTION "Group Number"
        ::= { xrptrGroupFaultEntry 1 }


xrptrGroupFaultIndex OBJECT-TYPE
        SYNTAX  INTEGER
        ACCESS  read-only
        STATUS  mandatory
        DESCRIPTION "The fault index in the fault table"
        ::= { xrptrGroupFaultEntry 2 }

xrptrGroupFaultReport   OBJECT-TYPE
        SYNTAX  DisplayString  (SIZE (0..255))
        ACCESS  read-only
        STATUS  mandatory
        DESCRIPTION "Get the faults detected by the agent"
        ::= { xrptrGroupFaultEntry 3 }

----------------------------------------------------
--         Port Level
----------------------------------------------------

xrptrGroupPortTable     OBJECT-TYPE
        SYNTAX  SEQUENCE OF XrptrGroupPortEntry
        ACCESS  not-accessible
        STATUS  mandatory
        DESCRIPTION "Table of entries with information/errors per port in group."
        ::= { xrptrgroupport 1 }


xrptrGroupPortEntry     OBJECT-TYPE
        SYNTAX  XrptrGroupPortEntry
        ACCESS  read-write
        STATUS  mandatory
        DESCRIPTION "Entry per port with info/errors."
        INDEX   { xrptrGroupPIndex , xrptrGroupPortIndex }
        ::= { xrptrGroupPortTable 1 }

XrptrGroupPortEntry ::= SEQUENCE {
        xrptrGroupPIndex
                INTEGER,
        xrptrGroupPortIndex
                INTEGER,
        xrptrGroupPortLinkStatus
                INTEGER,
        xrptrGroupPortRcvStatus
                INTEGER,
        xrptrGroupPortLinkFaults
                Counter,
        xrptrGroupPortAutoPartitions
                Counter,
        xrptrGroupPortAutoPartitionType
                INTEGER
}


xrptrGroupPIndex     OBJECT-TYPE
        SYNTAX  INTEGER
        ACCESS  read-only
        STATUS  mandatory
        DESCRIPTION "Group Number"
        ::= { xrptrGroupPortEntry 1 }

xrptrGroupPortIndex     OBJECT-TYPE
        SYNTAX  INTEGER
        ACCESS  read-only
        STATUS  mandatory
        DESCRIPTION "Port Number"
        ::= { xrptrGroupPortEntry 2 }

xrptrGroupPortLinkStatus      OBJECT-TYPE
        SYNTAX  INTEGER {
                link-ok(1),
                link-not-ok(2),
                link-not-applicable(3)
                }
        ACCESS  read-only
        STATUS  mandatory
        DESCRIPTION "When the value is 1, link status is O.K."
        ::= { xrptrGroupPortEntry 3 }

xrptrGroupPortRcvStatus      OBJECT-TYPE
        SYNTAX  INTEGER {
                receive(1),
                no-receive(2)
                }
        ACCESS  read-only
        STATUS  mandatory
        DESCRIPTION "This object describes the receive status of the port,
                     When a port is receiving data the object's
                     value is receive(1); when the port does not
                     receive any data the object's value is no-receive(2)"
        ::= { xrptrGroupPortEntry 4 }


xrptrGroupPortLinkFaults      OBJECT-TYPE
        SYNTAX  Counter
        ACCESS  read-only
        STATUS  mandatory
        DESCRIPTION "This counter is incremented every time
                     a link change is detected in the port.
                     A link change occurs whenever the link
                     either goes down or comes up on the port"
        ::= { xrptrGroupPortEntry 5 }


xrptrGroupPortAutoPartitions      OBJECT-TYPE
        SYNTAX  Counter
        ACCESS  read-only
        STATUS  mandatory
        DESCRIPTION "This counter is incremented every time
                     the port enters the Auto Partition state."
        ::= { xrptrGroupPortEntry 6 }


xrptrGroupPortAutoPartitionType      OBJECT-TYPE
        SYNTAX  INTEGER {
                collision-limit(1),
                collision-length-limit(2),
                loopback-failure(3),
                cpu-forced-reconnection(4),
                none(5)
                }
        ACCESS  read-only
        STATUS  mandatory
        DESCRIPTION "Auto Partition type."
        ::= { xrptrGroupPortEntry 7 }



------------------------------------------------------
-- group port protect table - runtine
------------------------------------------------------

xrptrGroupRPortProtectTable     OBJECT-TYPE
        SYNTAX  SEQUENCE OF XrptrGroupRPortProtectEntry
        ACCESS  not-accessible
        STATUS  mandatory
        DESCRIPTION "Table of entries regarding status of port protect.
                     One entry per port, with runtime status.
                     Setting these objects will prevent detach of port."
        ::= { xrptrgroupport 2 }


xrptrGroupRPortProtectEntry     OBJECT-TYPE
        SYNTAX  XrptrGroupRPortProtectEntry
        ACCESS  read-write
        STATUS  mandatory
        DESCRIPTION "Entry regarding port runtime protect status."
        INDEX   {xrptrGroupRPortProtectGrIndex ,
                 xrptrGroupRPortProtectPortIndex }
        ::= { xrptrGroupRPortProtectTable 1 }

XrptrGroupRPortProtectEntry ::= SEQUENCE {
        xrptrGroupRPortProtectGrIndex
                INTEGER,
        xrptrGroupRPortProtectPortIndex
                INTEGER,
        xrptrGroupRPortProtectPortState
                INTEGER
}


xrptrGroupRPortProtectGrIndex     OBJECT-TYPE
        SYNTAX  INTEGER
        ACCESS  read-write
        STATUS  mandatory
        DESCRIPTION "Group Number"
        ::= { xrptrGroupRPortProtectEntry 1 }

xrptrGroupRPortProtectPortIndex     OBJECT-TYPE
        SYNTAX  INTEGER
        ACCESS  read-write
        STATUS  mandatory
        DESCRIPTION "Port Number"
        ::= { xrptrGroupRPortProtectEntry 2 }

xrptrGroupRPortProtectPortState          OBJECT-TYPE
        SYNTAX  INTEGER {
                protected (1),
                not-protected (2)
                }
        ACCESS  read-write
        STATUS  mandatory
        DESCRIPTION "State of port protection.
                     If port is protected, a detach
                     command to this port is rejected."
        ::= { xrptrGroupRPortProtectEntry 3 }


----------------------------------------------------
-- group port permanent protect table
----------------------------------------------------



xrptrGroupPPortProtectTable     OBJECT-TYPE
        SYNTAX  SEQUENCE OF XrptrGroupPPortProtectEntry
        ACCESS  not-accessible
        STATUS  mandatory
        DESCRIPTION "Table of entries regarding status of port protect.
                     One entry per port, with permanent status.
                     Set on these objects will prevent detach of port.
                     Value is saved permanently."
        ::= { xrptrgroupport 3 }


xrptrGroupPPortProtectEntry     OBJECT-TYPE
        SYNTAX  XrptrGroupPPortProtectEntry
        ACCESS  read-write
        STATUS  mandatory
        DESCRIPTION "Entry regarding port permanent protect status."
        INDEX   {xrptrGroupPPortProtectGrIndex ,
                 xrptrGroupPPortProtectPortIndex }
        ::= { xrptrGroupPPortProtectTable 1 }

XrptrGroupPPortProtectEntry ::= SEQUENCE {
        xrptrGroupPPortProtectGrIndex
                INTEGER,
        xrptrGroupPPortProtectPortIndex
                INTEGER,
        xrptrGroupPPortProtectPortState
                INTEGER
}


xrptrGroupPPortProtectGrIndex     OBJECT-TYPE
        SYNTAX  INTEGER
        ACCESS  read-write
        STATUS  mandatory
        DESCRIPTION "Group Number"
        ::= { xrptrGroupPPortProtectEntry 1 }

xrptrGroupPPortProtectPortIndex     OBJECT-TYPE
        SYNTAX  INTEGER
        ACCESS  read-write
        STATUS  mandatory
        DESCRIPTION "Port Number"
        ::= { xrptrGroupPPortProtectEntry 2 }

xrptrGroupPPortProtectPortState          OBJECT-TYPE
        SYNTAX  INTEGER {
                protected (1),
                not-protected (2)
                }
        ACCESS  read-write
        STATUS  mandatory
        DESCRIPTION "State of port protection.
                     If port is protected, a detach
                     command to this port is rejected."
        ::= { xrptrGroupPPortProtectEntry 3 }


----------------------------------------------------
-- module table
----------------------------------------------------


xrptrGroupModuleTable     OBJECT-TYPE
        SYNTAX  SEQUENCE OF XrptrGroupModuleEntry
        ACCESS  not-accessible
        STATUS  mandatory
        DESCRIPTION "Table of entries regarding port modules in group."
        ::= { xrptrgroupmodule 1 }


xrptrGroupModuleEntry     OBJECT-TYPE
        SYNTAX  XrptrGroupModuleEntry
        ACCESS  read-write
        STATUS  mandatory
        DESCRIPTION "Entry per group, per module, describing module."
        INDEX   { xrptrGroupMIndex , xrptrGroupModuleIndex }
        ::= { xrptrGroupModuleTable 1 }

XrptrGroupModuleEntry ::= SEQUENCE {
        xrptrGroupMIndex
                INTEGER,
        xrptrGroupModuleIndex
                INTEGER,
        xrptrGroupModuleStructInfo
                INTEGER,
        xrptrGroupModuleBackupState
                INTEGER
}


xrptrGroupMIndex     OBJECT-TYPE
        SYNTAX  INTEGER
        ACCESS  read-only
        STATUS  mandatory
        DESCRIPTION "Group Number"
        ::= { xrptrGroupModuleEntry 1 }

xrptrGroupModuleIndex     OBJECT-TYPE
        SYNTAX  INTEGER
        ACCESS  read-only
        STATUS  mandatory
        DESCRIPTION "Module Number"
        ::= { xrptrGroupModuleEntry 2 }

xrptrGroupModuleStructInfo    OBJECT-TYPE
        SYNTAX  INTEGER {
                em350-Blank(1),
                em351-FO1(2),
                em352-FO2(3),
                em353-CX1(4),
                em354-CX2(5),
                em357-DTE(8),
                em356-TP2(9),
                em359-AUI(10),
                other(11),
                em355-EB2(12)
                }
        ACCESS  read-only
        STATUS  mandatory
        DESCRIPTION "
                List of module numbers:
                em350    /* BLANK */
                em351    /* FO single port  */
                em352    /* FO dual port */
                em353    /* COAX single port  */
                em354    /* COAX dual port */
                em357    /* DTE */
                em356    /* 10BASET dual port */
                em359    /* AUI */
                em355    /* EB2 */"
        ::= { xrptrGroupModuleEntry 3 }

xrptrGroupModuleBackupState   OBJECT-TYPE
        SYNTAX  INTEGER {
                enable(1),
                disable(2)
                }
        ACCESS  read-write
        STATUS  mandatory
        DESCRIPTION "Enable the user to specify the
                     backup state (enable/disable) for appropriate
                     EM modules (e.g., em352 FO dual port) installed
                     in an LC348 card.
                     This object applies only to the 348 card.
                     Setting this object will take effect only after
                     the next reset or power up of the card."
        ::= { xrptrGroupModuleEntry 4 }


----------------------------------------------------
--                TRAPS
----------------------------------------------------

xrptrGroupPortStatus        TRAP-TYPE
        ENTERPRISE mibseth-rptrs
        VARIABLES { rptrPortGroupIndex,
                    rptrPortIndex,
                    rptrPortAdminStatus
                  }
        DESCRIPTION "Issued when a port changes its status"
        ::= 1

xrptrGroupJabberFaultStatus        TRAP-TYPE
        ENTERPRISE mibseth-rptrs
        VARIABLES { xrptrGroupIndex,
                    xrptrGroupPortIndex,
                    xrptrGroupJabberError
                  }
        DESCRIPTION "Issued when a port enters the jabber lock state"
        ::= 2

xrptrGroupCPUBlockFaultStatus        TRAP-TYPE
        ENTERPRISE mibseth-rptrs
        VARIABLES {xrptrGroupIndex,
                   xrptrGroupRepeaterCpuBlockError }
        DESCRIPTION "Issued when a CPU or block error is detected"
        ::= 3

xrptrGrpPortAutoPartitionStatus        TRAP-TYPE
        ENTERPRISE mibseth-rptrs
        VARIABLES { xrptrGroupPIndex,
                    xrptrGroupPortIndex,
                    xrptrGroupPortAutoPartitionType
                  }
        DESCRIPTION "Issued when a port is auto partitioned"
        ::= 4


xrptrGroupPortLinkStatus        TRAP-TYPE
        ENTERPRISE mibseth-rptrs
        VARIABLES { xrptrGroupPIndex,
                    xrptrGroupPortIndex,
                    xrptrGroupPortLinkStatus
                  }
        DESCRIPTION "Issued when the link status of a port
                     changes"
        ::= 6

xrptrDetachNmsPort        TRAP-TYPE
        ENTERPRISE mibseth-rptrs
        VARIABLES {xrptrNMSGroup,
                   xrptrNMSPort }
        DESCRIPTION "Issued when the port connected to the NMS
                     is not detached by a detach command received
                     from the NMS"
        ::= 7

xrptrGrpHead1BackupMainActive        TRAP-TYPE
        ENTERPRISE mibseth-rptrs
        VARIABLES { xrptrGroupIndex }
        DESCRIPTION "Indicates that the MAIN link is active"
        ::= 8

xrptrGrpHead1BackupSecondActive        TRAP-TYPE
        ENTERPRISE mibseth-rptrs
        VARIABLES { xrptrGroupIndex }
        DESCRIPTION "Indicates that the SECOND link is active"
        ::= 9

xrptrDetachEsm        TRAP-TYPE
        ENTERPRISE mibseth-rptrs
        VARIABLES {xrptrESMGroup,
                   xrptrESMPort  }
        DESCRIPTION "Issued when the port connected to the ESM
                     is not detached by a detach command received
                     from the NMS"
        ::= 10

xrptrDetachProtectPort     TRAP-TYPE
        ENTERPRISE mibseth-rptrs
        VARIABLES {xrptrGroupRPortProtectGrIndex,
                   xrptrGroupRPortProtectPortIndex }
        DESCRIPTION "Issued when a protected port is not
                     detached by a detach command received
                     from the NMS"
        ::= 11

xrptrSmCpufaultStatus        TRAP-TYPE
        ENTERPRISE mibseth-rptrs
        VARIABLES {xrptrSmCpuError}

        DESCRIPTION "Issued when a CPU fault is detected
                     in manager card. For factory use only."
        ::= 12

xrptrSmControllerFaultStatus        TRAP-TYPE
        ENTERPRISE mibseth-rptrs
        VARIABLES {xrptrSmControllerError}

        DESCRIPTION "Issued when a Controller fault is detected
                     in manager card. For factory use only"
        ::= 13


        END
