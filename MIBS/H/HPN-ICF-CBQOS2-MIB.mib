-- =========================================================================
-- Copyright (c) 2010-2014 Hewlett-Packard Development Company, L.P.
--
-- Description: This MIB file is used for management of hpnicf Class Based
--             QoS information.
-- Reference:
-- Version: V2.1
-- History:
-- V1.0 created by tangshun.
-- V1.1 2006/01/17 modified by wangjinwang
--   add enum value 22 and 23 in MatchRuleType
--   add comment for hpnicfCBQoSMatchRuleIntValue1
-- V1.2 2006/02/24 modified by changhuifeng
--   Add an enumeration Bittorrent(24) to object hpnicfCBQoSMatchRuleType.
--   Add hpnicfCBQoSMirrorCfgInfoTable for flow mirror.
--   Add hpnicfCBQoSRedirectIpv6Interface1 and hpnicfCBQoSRedirectIpv6Interface2
--   object for hpnicfCBQoSRedirectCfgInfoTable.
--   Modify the value range of hpnicfCBQoSRemarkValue from "1~4094" to "1~4095"
--   in hpnicfIfQoSPQClassRuleTable.
-- V1.3 2006/03/29 modified by xialei
--   Modify the MAX-ACCESS clause of hpnicfCBQoSQueueDropType.
--   Modify the description for object hpnicfCBQoSQueueCbs.
--   Modify the enumeration name of object hpnicfCBQoSRedirectType.
-- V1.4 2007/10/15 modified by wangjinwang
--   Add hpnicfCBQoSGlobalApplyTable to global policy apply.
--   Add hpnicfCBQoSPolicyClassMode and hpnicfCBQoSPolicyClassCfgOrder to
--   hpnicfCBQoSPolicyClassCfgInfoTable.
--   Add hpnicfCBQoSNestCfgInfoTable to traffic behavior.
--   Add enumeration matchRuleServiceDot1p
--   to object hpnicfCBQoSMatchRuleType.
--   Add enumeration typeTopMostVlanID to object hpnicfCBQoSRemarkType.
-- V1.5 2007/12/12 modified by Xu Hang/ChenWei
--   Delete the default value of hpnicfCBQoSGlobalApplyDirection
--   in hpnicfCBQoSGlobalApplyTable
--   Add hpnicfCBQoSApplyPolicyIndexObjects to hpnicfCBQoSApplyPolicyStaticsObjects
--   Add hpnicfCBQoSStaticsObjects to hpnicfCBQoSApplyPolicyStaticsObjects
--   Modify the MAX-ACCESS clause of hpnicfCBQoSQueueDropType.
--   Modify the MAX-ACCESS clause of hpnicfCBQoSIfApplyPolicyIfIndex,
--   hpnicfCBQoSIfApplyPolicyDirection, hpnicfCBQoSVlanApplyPolicyVlanid
--   and hpnicfCBQoSVlanApplyPolicyDirection.
--   Add hpnicfCBQoSApplyingStatusObjects to hpnicfCBQoSObjects.
--   Add hpnicfCBQoSApplyingStatus to hpnicfCBQoSApplyPolicyObjects.
--   Add hpnicfCBQoSNotifications to hpnicfCBQoSObjects.
--   Add hpnicfCBQoSNotificationsPrefix to hpnicfCBQoSNotifications.
--   Add hpnicfCBQoSIfPolicyChanged and hpnicfCBQoSVlanPolicyChanged
--   to hpnicfCBQoSNotificationsPrefix.
--   Add remark-local-pre-pass and remark-drop-pre-pass to CarAction.
--   Delete the default value of hpnicfCBQoSVlanApplyPolicyDirection and
--   hpnicfCBQoSGlobalApplyDirection.
-- V1.6 2008/05/28 modified by ChenWei
--   Add hpnicfCBQoSNestPolicyCfgInfoTable to hpnicfCBQoSBehaviorObjects.
--   Add hpnicfCBQoSNestPolicyApplyObjectTable to hpnicfCBQoSApplyPolicyIndexObjects.
-- V1.7 2011/01/25 modified by XuGuoFang/zhaixiaoxiang
--   Modify the range of hpnicfCBQoSQueueBandwidthValue.
--   Modify the range of hpnicfCBQoSQueueCbs.
--   Modify the description of hpnicfCBQoSQueueCbsRatio.
--   Modify the description of hpnicfCBQoSBehaviorIndexNext.
-- V1.8 2012/07/02 modified by XuJunjie/XunZhi
--   Modify MatchRuleType add matchRuleMplsLabel to matchRuleForwardingLayer.
--   Modify the description for hpnicfCBQoSClassifierIndexNext.
--   Modify the description for hpnicfCBQosClassifierMatchRuleNextIndex.
--   Modify the description for hpnicfCBQoSMatchRuleStringValue.
--   Modify the description for hpnicfCBQoSMatchRuleIntValue1.
--   Modify the description for hpnicfCBQoSMatchRuleIntValue2.
--   Add table hpnicfCBQoSMatchCpProtoCfgTable.
--   Add table hpnicfCBQoSMatchCpGroupCfgTable.
--   Add hpnicfCBQoSAccountingMode in hpnicfCBQoSAccountCfgInfoTable.
--   Add hpnicfCBQoSRedirectIfVlanID in hpnicfCBQoSRedirectCfgInfoTable.
--   Add table hpnicfCBQoSMirrorIfCfgInfoTable.
--   Add table hpnicfCBQoSColoredRemarkCfgTable.
--   Add table hpnicfCBQoSPrimapCfgInfoTable.
--   Add table hpnicfCBQoSColorMapDpCfgInfoTable.
--   Modify the description for hpnicfCBQoSPolicyIndexNext
--   Modify the description for hpnicfCBQoSPolicyClassNextIndex
--   Add table hpnicfCBQoSCpApplyPolicyTable
--   Modify ApplyObjectType add controlPlane
--   Modify the description for hpnicfCBQoSApplyObjectMainSite
--   Modify the description for hpnicfCBQoSApplyObjectSubChannel
--   Add table hpnicfCBQoSCpApplyObjectTable
--   Modify SYNTAX add partialSuccess(3) for hpnicfCBQoSClassBehaviorStatus
--   Modify hpnicfCBQoSQueueBandwidthUnit add a value RemainPercent.
--   Modify hpnicfCBQoSPolicyClassMode, add modeQppb, modeIpSourceGuard, modeVoiceVlan,
--   modeDCBX to value list.
--   Add node ApplyPolicyStatus for table hpnicfCBQoSIfApplyPolicyTable,
--   hpnicfCBQoSVlanApplyPolicyTable, and hpnicfCBQoSGlobalApplyTable.
-- V1.9 2013/03/13 modified by MouXuanli
--   Add typeSecondMplsExp to RemarkType.
--   Modify the description of hpnicfCBQoSRemarkValue and hpnicfCBQoSColoredRemarkValue.
-- V2.0 2014/02/24 modified by MouXuanli
--   Modify the range of hpnicfCBQoSQueueLength.
-- V2.1 2014/04/17 modified by GaoYu/XunZhi
--   Add enumeration matchRuleMacAcl and matchRuleUserAcl to MatchRuleType.
--   Modify the description of hpnicfCBQoSMatchRuleStringValue.
--   Modify the description of hpnicfCBQoSMatchRuleIntValue1.
-- ==========================================================================
HPN-ICF-CBQOS2-MIB DEFINITIONS ::= BEGIN

IMPORTS
    hpnicfCommon
        FROM HPN-ICF-OID-MIB
    Integer32, Counter64, Unsigned32, OBJECT-TYPE, MODULE-IDENTITY, NOTIFICATION-TYPE
        FROM SNMPv2-SMI
    InetAddressType, InetAddress
        FROM INET-ADDRESS-MIB           -- [RFC3291]
    TEXTUAL-CONVENTION, RowStatus, TruthValue
        FROM SNMPv2-TC;

hpnicfCBQos2 MODULE-IDENTITY
    LAST-UPDATED "201207020000Z"            -- July 02, 2012 at 00:00 GMT
    ORGANIZATION
        ""
    CONTACT-INFO
        ""
    DESCRIPTION
        "This MIB contains objects to manage configuration and
         monitor running state for Class Based QoS feature.

            *********************************
                    MIB Tables
            **********************************
         This MIB consists of the following tables:
            1 :  hpnicfCBQoSClassifierCfgInfoTable
            2 :  hpnicfCBQoSMatchRuleCfgInfoTable
            3 :  hpnicfCBQoSMatchCpProtoCfgTable
            4 :  hpnicfCBQoSMatchCpGroupCfgTable
            5 :  hpnicfCBQoSBehaviorCfgInfoTable
            6 :  hpnicfCBQoSCarCfgInfoTable
            7 :  hpnicfCBQoSAggregativeCarCfgInfoTable
            8 :  hpnicfCBQoSGtsCfgInfoTable
            9 :  hpnicfCBQoSRemarkCfgInfoTable
            10:  hpnicfCBQoSQueueCfgInfoTable
            11:  hpnicfCBQoSWredCfgInfoTable
            12:  hpnicfCBQoSWredClassCfgInfoTable
            13:  hpnicfCBQoSPolicyRouteCfgInfoTable
            14:  hpnicfCBQoSNatCfgInfoTable
            15:  hpnicfCBQoSFirewallCfgInfoTable
            16:  hpnicfCBQoSSamplingCfgInfoTable
            17:  hpnicfCBQoSAccountCfgInfoTable
            18:  hpnicfCBQoSRedirectCfgInfoTable
            19:  hpnicfCBQoSPriorityMapCfgInfoTable
            20:  hpnicfCBQoSPolicyCfgInfoTable
            21:  hpnicfCBQoSPolicyClassCfgInfoTable
            22:  hpnicfCBQoSIfApplyPolicyTable
            23:  hpnicfCBQoSAtmPvcApplyPolicyTable
            24:  hpnicfCBQoSVlanApplyPolicyTable
            25:  hpnicfCBQoSFrClassApplyPolicyTable
            26:  hpnicfCBQoSFrPvcApplyPolicyTable
            27:  hpnicfCBQoSIfCbqRunInfoTable
            28:  hpnicfCBQoSIfClassMatchRunInfoTable
            29:  hpnicfCBQoSIfCarRunInfoTable
            30:  hpnicfCBQoSIfGtsRunInfoTable
            31:  hpnicfCBQoSIfRemarkRunInfoTable
            32:  hpnicfCBQoSIfQueueRunInfoTable
            33:  hpnicfCBQoSIfWredRunInfoTable
            34:  hpnicfCBQoSIfAccountingRunInfoTable
            35:  hpnicfCBQoSAtmPvcCbqRunInfoTable
            36:  hpnicfCBQoSAtmPvcClassMatchRunInfoTable
            37:  hpnicfCBQoSAtmPvcCarRunInfoTable
            38:  hpnicfCBQoSAtmPvcGtsRunInfoTable
            39:  hpnicfCBQoSAtmPvcRemarkRunInfoTable
            40:  hpnicfCBQoSAtmPvcQueueRunInfoTable
            41:  hpnicfCBQoSAtmPvcWredRunInfoTable
            42:  hpnicfCBQoSAtmPvcAccountingRunInfoTable
            43:  hpnicfCBQoSFrPvcCbqRunInfoTable
            44:  hpnicfCBQoSFrPvcClassMatchRunInfoTable
            45:  hpnicfCBQoSFrPvcCarRunInfoTable
            46:  hpnicfCBQoSFrPvcGtsRunInfoTable
            47:  hpnicfCBQoSFrPvcRemarkRunInfoTable
            48:  hpnicfCBQoSFrPvcQueueRunInfoTable
            49:  hpnicfCBQoSFrPvcWredRunInfoTable
            50:  hpnicfCBQoSFrPvcAccountingRunInfoTable
            51:  hpnicfCBQoSIfVlanClassMatchRunInfoTable
            52:  hpnicfCBQoSIfVlanAccountingRunInfoTable
            53:  hpnicfCBQoSMirrorCfgInfoTable
            54:  hpnicfCBQoSGlobalApplyTable
            55:  hpnicfCBQoSCpApplyPolicyTable
            56:  hpnicfCBQoSNestCfgInfoTable
            57:  hpnicfCBQoSNestPolicyCfgInfoTable
            58:  hpnicfCBQoSMirrorIfCfgInfoTable
            59:  hpnicfCBQoSColoredRemarkCfgTable
            60:  hpnicfCBQoSPrimapCfgInfoTable
            61:  hpnicfCBQoSColorMapDpCfgInfoTable
            62:  hpnicfCBQoSApplyObjectTable
            63:  hpnicfCBQoSIntApplyObjectTable
            64:  hpnicfCBQoSVlanApplyObjectTable
            65:  hpnicfCBQoSPvcApplyObjectTable
            66:  hpnicfCBQoSNestPolicyApplyObjectTable
            67:  hpnicfCBQoSCpApplyObjectTable
            68:  hpnicfCBQoSCbqRunInfoTable
            69:  hpnicfCBQoSClassMatchRunInfoTable
            70:  hpnicfCBQoSCarRunInfoTable
            71:  hpnicfCBQoSGtsRunInfoTable
            72:  hpnicfCBQoSRemarkRunInfoTable
            73:  hpnicfCBQoSQueueRunInfoTable
            74:  hpnicfCBQoSWredRunInfoTable
            75:  hpnicfCBQoSAccountingRunInfoTable
            76:  hpnicfCBQoSApplyingStatusObjects
            77:  hpnicfCBQoSNotifications
        "
    REVISION "201207020000Z"        -- July 02, 2012 at 00:00 GMT
    DESCRIPTION
        "Modified to add new tables and new nodes."
    REVISION "200507300000Z"        -- July 30, 2005 at 00:00 GMT
    DESCRIPTION
        "The initial revision of this MIB module."
    ::= { hpnicfQos2 2 }

hpnicfQos2 OBJECT IDENTIFIER ::= { hpnicfCommon 65 }

--
-- type definitions in the traffic classifier
--

-- MatchRuleType
MatchRuleType ::= TEXTUAL-CONVENTION
    STATUS current
    DESCRIPTION
        "Type of Match Rule."
    SYNTAX INTEGER
    {
        matchRuleAny(1),
        matchRuleIpv4Acl(2),
        matchRuleIPv6Acl(3) ,
        matchRuleIPv4Protocol(4),
        matchRuleIPv6Protocol(5),
        matchRuleIPXProtocol(6),
        matchRuleDscp(7),
        matchRuleIpPre(8),
        matchRuleVlan8021p(9),
        matchRuleMplsExp(10),
        matchRuleAtmClp(11),
        matchRuleFrDe(12),
        matchRuleSourceMac(13),
        matchRuleDestinationMac(14),
        matchRuleQosLocalID(15),
        matchRuleClassifier(16),
        matchRuleInboundInterface(17),
        matchRuleRtpPort(18),
        matchRuleSourceIp(19),
        matchRuleVlanID(20),
        matchRuleTopMostVlanID(21),
        matchRuleLocalPrecedence(22),
        matchRuleDropPriority(23),
        matchRuleBittorrent(24),
        matchRuleServiceDot1p(25),
        matchRuleMplsLabel(26),
        matchRuleSecondMplsLabel(27),
        matchRuleSecondMplsExp(28),
        matchRulePacketLength(29),
        matchRuleArpProtocol(30),
        matchRuleForwardingLayer(31),
        matchRuleMacAcl(32),
        matchRuleUserAcl(33)
    }
--
-- end of type definitions in the traffic classifier
--

--
-- type definitions in the traffic behavior
--

-- CarAction
CarAction ::= TEXTUAL-CONVENTION
    STATUS current
    DESCRIPTION
        "The actions taken when packets conforming or exceeding
         the configured committed information rate(CIR)."
    SYNTAX INTEGER
    {
        invalid(0),
        pass(1),
        continue(2),
        discard(3),
        remark(4),
        remark-ip-continue(5),
        remark-ip-pass(6),
        remark-mplsexp-continue(7),
        remark-mplsexp-pass(8),
        remark-dscp-continue(9),
        remark-dscp-pass(10),
        remark-dot1p-continue(11),
        remark-dot1p-pass(12),
        remark-atm-clp-continue(13),
        remark-atm-clp-pass(14),
        remark-fr-de-continue(15),
        remark-fr-de-pass(16),
        remark-local-pre-pass(17),
        remark-drop-pre-pass(18)
    }

-- RemarkType
RemarkType ::= TEXTUAL-CONVENTION
    STATUS  current
    DESCRIPTION
        "Type of remark."
    SYNTAX INTEGER
    {
        typeIpPrecedence(1),
        typeDscp(2),
        typeMplsExp(3),
        typeVlan8021p(4),
        typeAtmClp(5),
        typeFrDe(6),
        typeVlanID(7),
        typeQosLocalID(8),
        typeDropPrecedence(9),
        typeLocalPrecedence(10),
        typeTopMostVlanID(11),
        typeSecondMplsExp(12)
    }

-- WredType
WredType ::= TEXTUAL-CONVENTION
    STATUS current
    DESCRIPTION
        "WRED type."
    SYNTAX INTEGER
    {
        typeIpPrecBased(1),
        typeDscpBased(2),
        typeDropLevelBased(3),
        typeAtmClpBased(4),
        typeVlan8021pBased(5),
        typeMplsExpBased(6)
    }

-- QueueType
QueueType ::= TEXTUAL-CONVENTION
    STATUS  current
    DESCRIPTION
        "Queueing Type:
         EF:(1)
         AF:(2)
         WFQ:(3)
        "
    SYNTAX INTEGER
    {
        ef(1),
        af(2),
        wfq(3)
    }

-- QueueBandwidthUnit
QueueBandwidthUnit ::= TEXTUAL-CONVENTION
    STATUS current
    DESCRIPTION
        "Bandwidth Unit:
         Absolute, Unit : Kbps(1)
         Percent, Unit : %(2)
         RemainPercent, Unit : %(3)
        "
    SYNTAX INTEGER
    {
        unitUnavailable(0),
        unitAbsolute(1),
        unitPercent(2),
        unitRemainPercent(3)
    }

--
-- end of type definitions in the traffic behavior
--

--
-- type definitions in the policy
--

-- Direction
DirectionType ::= TEXTUAL-CONVENTION
    STATUS  current
    DESCRIPTION
        "The direction of policy apply on at interface."
    SYNTAX  INTEGER
    {
        inbound(1),
        outbound(2)
    }

-- ApplyObjectType
ApplyObjectType ::= TEXTUAL-CONVENTION
    STATUS  current
    DESCRIPTION
        "Type of QoS apply object."
    SYNTAX  INTEGER
    {
        interface(1),
        vlan(2),
        atmPvc(3),
        frDlci(4),
        controlPlane(5)
    }

--
-- end of type definitions in policy
--

--
-- Node definitions
--
hpnicfCBQoSObjects OBJECT IDENTIFIER ::= { hpnicfCBQos2 1 }

-- hpnicfCBQoSClassifierObjects

hpnicfCBQoSClassifierObjects OBJECT IDENTIFIER ::= { hpnicfCBQoSObjects 1 }

-- Traffic Classifier Next Index
hpnicfCBQoSClassifierIndexNext OBJECT-TYPE
    SYNTAX Integer32
    MAX-ACCESS read-only
    STATUS current
    DESCRIPTION
        "This object contains an appropriate value to be used for
         hpnicfCBQoSClassifierIndex when creating rows in the
         hpnicfCBQoSClassifierCfgInfoTable.
        "
    ::= { hpnicfCBQoSClassifierObjects 1 }

-- Traffic Classifier

hpnicfCBQoSClassifierCfgInfoTable OBJECT-TYPE
    SYNTAX SEQUENCE OF HpnicfCBQoSClassifierCfgInfoEntry
    MAX-ACCESS not-accessible
    STATUS current
    DESCRIPTION
        "A table of Traffic Classifier configuration information."
    ::= { hpnicfCBQoSClassifierObjects 2 }

hpnicfCBQoSClassifierCfgInfoEntry OBJECT-TYPE
    SYNTAX HpnicfCBQoSClassifierCfgInfoEntry
    MAX-ACCESS not-accessible
    STATUS current
    DESCRIPTION
        "Traffic Classifier Configuration Information Entry."
    INDEX { hpnicfCBQoSClassifierIndex }
    ::= { hpnicfCBQoSClassifierCfgInfoTable 1 }

HpnicfCBQoSClassifierCfgInfoEntry ::=
    SEQUENCE
    {
        hpnicfCBQoSClassifierIndex
            Integer32,
        hpnicfCBQoSClassifierName
            OCTET STRING,
        hpnicfCBQoSClassifierRuleCount
            Integer32,
        hpnicfCBQoSClassifierOperator
            INTEGER,
        hpnicfCBQoSClassifierLayer
            INTEGER,
        hpnicfCBQoSClassifierType
            INTEGER,
        hpnicfCBQosClassifierMatchRuleNextIndex
            Integer32,
        hpnicfCBQoSClassifierRowStatus
            RowStatus
    }

hpnicfCBQoSClassifierIndex OBJECT-TYPE
    SYNTAX Integer32
    MAX-ACCESS not-accessible
    STATUS current
    DESCRIPTION
        "Index of Traffic Classifier.  Begin with 0."
    ::= { hpnicfCBQoSClassifierCfgInfoEntry 1 }

hpnicfCBQoSClassifierName OBJECT-TYPE
    SYNTAX OCTET STRING (SIZE (1..31))
    MAX-ACCESS read-create
    STATUS current
    DESCRIPTION
        "Name of Traffic Classifier."
    ::= { hpnicfCBQoSClassifierCfgInfoEntry 2 }

hpnicfCBQoSClassifierRuleCount OBJECT-TYPE
    SYNTAX Integer32
    MAX-ACCESS read-only
    STATUS current
    DESCRIPTION
        "The counter of match rules of Traffic classifier."
    ::= { hpnicfCBQoSClassifierCfgInfoEntry 3 }

hpnicfCBQoSClassifierOperator OBJECT-TYPE
    SYNTAX INTEGER
    {
        and(1),
        or(2)
    }
    MAX-ACCESS read-create
    STATUS current
    DESCRIPTION
        "Operator of the match rules of traffic classifier.
         Software QoS supports and, or.
         Hardware QoS supports and.
        "
    DEFVAL { and }
    ::= { hpnicfCBQoSClassifierCfgInfoEntry 4 }

hpnicfCBQoSClassifierLayer OBJECT-TYPE
    SYNTAX INTEGER
    {
        unavailable(1),
        l2(2),
        l3(3),
        both(4)
    }
    MAX-ACCESS read-create
    STATUS current
    DESCRIPTION
        "Configuration layer of traffic classifier.
         Only hardware QoS support it.
         1(unavailable) is returned only when getting value from software QoS.
         1(unavailable) can't be set.
        "
    DEFVAL { l3 }
    ::= { hpnicfCBQoSClassifierCfgInfoEntry 5 }

hpnicfCBQoSClassifierType OBJECT-TYPE
    SYNTAX INTEGER
    {
        systemDefined(1),
        userDefined(2)
    }
    MAX-ACCESS read-only
    STATUS current
    DESCRIPTION
        "The type of classifier."
    ::= { hpnicfCBQoSClassifierCfgInfoEntry 6 }

hpnicfCBQosClassifierMatchRuleNextIndex OBJECT-TYPE
    SYNTAX Integer32
    MAX-ACCESS read-only
    STATUS current
    DESCRIPTION
        "This object contains an appropriate value to be used for
         hpnicfCBQoSMatchRuleIndex when creating rows in the
         hpnicfCBQoSMatchRuleCfgInfoTable.
        "
    ::= { hpnicfCBQoSClassifierCfgInfoEntry 7 }

hpnicfCBQoSClassifierRowStatus OBJECT-TYPE
    SYNTAX RowStatus
    MAX-ACCESS read-create
    STATUS current
    DESCRIPTION
        "RowStatus."
    ::= { hpnicfCBQoSClassifierCfgInfoEntry 8 }

-- Match rule

hpnicfCBQoSMatchRuleCfgInfoTable OBJECT-TYPE
    SYNTAX SEQUENCE OF HpnicfCBQoSMatchRuleCfgInfoEntry
    MAX-ACCESS not-accessible
    STATUS current
    DESCRIPTION
        "A table of Match Rule configuration information."
    ::= { hpnicfCBQoSClassifierObjects 3 }

hpnicfCBQoSMatchRuleCfgInfoEntry OBJECT-TYPE
    SYNTAX HpnicfCBQoSMatchRuleCfgInfoEntry
    MAX-ACCESS not-accessible
    STATUS current
    DESCRIPTION
        "Match Rule Configuration Information Entry."
    INDEX { hpnicfCBQoSClassifierIndex, hpnicfCBQoSMatchRuleIndex }
    ::= { hpnicfCBQoSMatchRuleCfgInfoTable 1 }

HpnicfCBQoSMatchRuleCfgInfoEntry ::=
    SEQUENCE
    {
        hpnicfCBQoSMatchRuleIndex
            Integer32,
        hpnicfCBQoSMatchRuleIfNot
            INTEGER,
        hpnicfCBQoSMatchRuleType
            MatchRuleType,
        hpnicfCBQoSMatchRuleStringValue
            OCTET STRING,
        hpnicfCBQoSMatchRuleIntValue1
            Unsigned32,
        hpnicfCBQoSMatchRuleIntValue2
            Unsigned32,
        hpnicfCBQoSMatchIpAddressType
            InetAddressType,
        hpnicfCBQoSMatchIpAddress
            InetAddress,
        hpnicfCBQoSMatchRuleRowStatus
            RowStatus
    }

hpnicfCBQoSMatchRuleIndex OBJECT-TYPE
    SYNTAX Integer32
    MAX-ACCESS not-accessible
    STATUS current
    DESCRIPTION
        "Index of Match Rule."
    ::= { hpnicfCBQoSMatchRuleCfgInfoEntry 1 }

hpnicfCBQoSMatchRuleIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { hpnicfCBQoSMatchRuleCfgInfoEntry 2 }

hpnicfCBQoSMatchRuleType OBJECT-TYPE
    SYNTAX MatchRuleType
    MAX-ACCESS read-create
    STATUS current
    DESCRIPTION
        "Type of Match Rule."
    ::= { hpnicfCBQoSMatchRuleCfgInfoEntry 3 }

hpnicfCBQoSMatchRuleStringValue OBJECT-TYPE
    SYNTAX OCTET STRING (SIZE (0..255))
    MAX-ACCESS read-create
    STATUS current
    DESCRIPTION
        "Value of Match Rule.
         IPv4 ACL: SIZE (1..63) ACL name
         MAC ACL: SIZE (1..63) MAC ACL name
         User ACL: SIZE (1..63) User ACL name
         IPv6 ACL: SIZE (1..63) IPv6 ACL name
         SourceMAC: SIZE (12) HHHHHHHHHHHH
           for example: 010102020303 means the match rule is
                        'if-match source-mac 0101-0202-0303'
         DestinationMAC: SIZE (12) HHHHHHHHHHHH
           for example: 010102020303 means the match rule is
                        'if-match destination-mac 0101-0202-0303'
         Classifier: SIZE (1..31) classifier name
         InboundInterface: SIZE (1..47) interface description
         TopMostVlanID, VlanID: SIZE(1..109), up to 10 values can be input;
           for example: 1##5#11#111##114#1111 means the match rule is
                        'if-match vlanid 1 to 5 11 111 to 114 1111'
         SourceIp: SIZE (12) HHHHHHHHHHHH
           for example: 010102020303 means the match rule is
                        'if-match source-ip mac-address 0101-0202-0303'
         MplsLabel: SIZE (1..63), up to 8 values can be input;
           for example: 1#11#111#1111 means the match rule is
                        'if-match mpls-label 1 11 111 1111';
                        1##1111 means the match rule is
                        'if-match mpls-label 1 to 1111';
         SecondMplsLabel: SIZE (1..63), up to 8 values can be input;
           for example: 1#11#111#1111 means the match rule is
                        'if-match mpls-label 1 11 111 1111';
                        1##1111 means the match rule is
                        'if-match mpls-label 1 to 1111';
         other types: Set is not permitted.  Zero-length string will
                      be returned when getting.
        "
    ::= { hpnicfCBQoSMatchRuleCfgInfoEntry 4 }

hpnicfCBQoSMatchRuleIntValue1 OBJECT-TYPE
    SYNTAX Unsigned32
    MAX-ACCESS read-create
    STATUS current
    DESCRIPTION
        "Value of Match Rule.
         IPv4 ACL: 2000~3999
         MAC ACL: 4000~4999
         User ACL: 5000~5999
         IPv6 ACL: 2000~3999; 10000~42767
         Software QoS: 2000~3999
         Hardware Qos: 10000~42767
         RtpPort: start-port: 2000~65535
         IpPrec: value: 0~7, up to 8 values can be input.  The bit set to
                 1 of the last 8 bits of hpnicfCBQoSMatchRuleIntValue1 is
                 used to indicate the value 0~7.
           for example: 0x53(Binary format is 01010011)
                        means the match rule is 'if-match ip-prec 0 1 4 6'
         Dscp: value:0~63, up to 8 values can be input.
               The bit set to 1 of hpnicfCBQoSMatchRuleIntValue1 is used
               to indicate the value 32~63.
               The bit set to 1 of hpnicfCBQoSMatchRuleIntValue2 is used to
               indicate the value 0~31.
           for example: 0x80000003 means the match rule is 'if-match
                        dscp 32 33 63'
         Vlan8021p: value:0~7, up to 8 values can be input.  The bit set
                    to 1 of the last 8 bits of hpnicfCBQoSMatchRuleIntValue1
                    is used to indicate the value 0~7.
           for example: 0x53(Binary format is 01010011) means the
                        match rule is 'if-match customer-dot1p 0 1 4 6'
         MplsExp: value:0~7, up to 8 values can be input.  The bit set to 1
                  of the last 8 bits of hpnicfCBQoSMatchRuleIntValue1 is used
                  to indicate the 8 value 0~7.
           for example: 0x53(Binary format is 01010011) means the
                        match rule is 'if-match mpls 0 1 4 6'
         SourceIp: 1~4095
         QosLocalID: 1~4095
         AtmClp: 0~1
         FrDe: 0~1
         LocalPrecedence: 0~7, up to 8 values can be input.  The bit set to
                          1 of the last 8 bits of hpnicfCBQoSMatchRuleIntValue1
                          is used to indicate the value 0~7.
           for example: 0x53(Binary format is 01010011) means the match
                        rule is 'if-match localprecedence 0 1 4 6'
         DropPriority: 0~2, up to 3 values can be input.  The bit set to 1
                       of the last 3 bits of hpnicfCBQoSMatchRuleIntValue1 is
                       used to indicate the value 0~2.
         ServiceDot1p: 0~7, up to 8 values can be input.
                       The bit set to 1 of the last 8 bits of
                       hpnicfCBQoSMatchRuleIntValue1 is used to indicate
                       the value 0~7.
           for example: 0x53(Binary format is 01010011) means the match
                        rule is 'if-match service-dot1p 0 1 4 6'
         SecondMplsExp: value:0~7, up to 8 values can be input.  The bit
                        set to 1 of the last 8 bits of hpnicfCBQoSMatchRuleIntValue1
                        is used to indicate the 8 value 0~7.
           for example: 0x53(Binary format is 01010011) means the
                        match rule is 'if-match mpls 0 1 4 6'
         PacketLength: 1~2000.  hpnicfCBQoSMatchRuleIntValue1 is used to
                       indicate the minimum value, hpnicfCBQoSMatchRuleIntValue2
                       is used to indicate the maximum value.
         ForwardingLayer: {bridge(1), route(2)}
         other types: Set is not permitted.  0xffffffff will be returned
                      when getting.
        "
    ::= { hpnicfCBQoSMatchRuleCfgInfoEntry 5 }

hpnicfCBQoSMatchRuleIntValue2 OBJECT-TYPE
    SYNTAX Unsigned32
    MAX-ACCESS read-create
    STATUS current
    DESCRIPTION
        "Value of Match Rule.
         RtpPort: end-port: 2000~65535
         Dscp: value:0~63, up to 8 values can be input.
               The bit set to 1 of hpnicfCBQoSMatchRuleIntValue1 is used to indicate the value 32~63.
               The bit set to 1 of hpnicfCBQoSMatchRuleIntValue2 is used to indicate the value 0~31.
               for example: 0x80000003 means the match rule is 'if-match dscp 0 1 31'
         PacketLength: 1~2000.  hpnicfCBQoSMatchRuleIntValue1 is used to
                       indicate the minimum value, hpnicfCBQoSMatchRuleIntValue2
                       is used to indicate the maximum value.
         other types: Set is not permitted.  0xffffffff will be returned when getting.
        "
    ::= { hpnicfCBQoSMatchRuleCfgInfoEntry 6 }

hpnicfCBQoSMatchIpAddressType OBJECT-TYPE
    SYNTAX InetAddressType
    MAX-ACCESS read-create
    STATUS current
    DESCRIPTION
        "A value that represents a type of Internet address.
          unknown(0)  An unknown address type.  This value MUST
            be used if the value of the corresponding
            InetAddress object is a zero-length string.
            It may also be used to indicate an IP address
            which is not in one of the formats defined below.

         ipv4(1)     An IPv4 address as defined by the
                InetAddressIPv4 textual convention.

         ipv6(2)     A global IPv6 address as defined by the
                InetAddressIPv6 textual convention.

         ipv4z(3)    A non-global IPv4 address including a zone
                index as defined by the InetAddressIPv4z textual convention.

         ipv6z(4)    A non-global IPv6 address including a zone
                index as defined by the InetAddressIPv6z textual convention.

         dns(16)     A DNS domain name as defined by the
                InetAddressDNS textual convention.

         Value of match rule.
         SourceIp support this node.
         other types: Set is not permitted.  Unknown will be returned when getting.
        "
    ::= { hpnicfCBQoSMatchRuleCfgInfoEntry 7 }

hpnicfCBQoSMatchIpAddress OBJECT-TYPE
    SYNTAX InetAddress
    MAX-ACCESS read-create
    STATUS current
    DESCRIPTION
        "Denotes a generic Internet address.
         SourceIP support this node.
         other types: Set is not permitted.  NULL will be returned when getting.
        "
    ::= { hpnicfCBQoSMatchRuleCfgInfoEntry 8 }

hpnicfCBQoSMatchRuleRowStatus OBJECT-TYPE
    SYNTAX RowStatus
    MAX-ACCESS read-create
    STATUS current
    DESCRIPTION
        "RowStatus."
    ::= { hpnicfCBQoSMatchRuleCfgInfoEntry 9 }

-- hpnicfCBQoSMatchCpProtoCfgTable

hpnicfCBQoSMatchCpProtoCfgTable OBJECT-TYPE
    SYNTAX SEQUENCE OF HpnicfCBQoSMatchCpProtoCfgEntry
    MAX-ACCESS not-accessible
    STATUS current
    DESCRIPTION
        "A table of Matching CpProtocol Rule configuration information."
    ::= { hpnicfCBQoSClassifierObjects 4 }

hpnicfCBQoSMatchCpProtoCfgEntry OBJECT-TYPE
    SYNTAX HpnicfCBQoSMatchCpProtoCfgEntry
    MAX-ACCESS not-accessible
    STATUS current
    DESCRIPTION
        "Matching CpProtocol Rule Configuration Information Entry."
    INDEX { hpnicfCBQoSClassifierIndex, hpnicfCBQoSMatchRuleIndex }
    ::= { hpnicfCBQoSMatchCpProtoCfgTable 1 }

HpnicfCBQoSMatchCpProtoCfgEntry ::=
    SEQUENCE
    {
        hpnicfCBQoSMatchCpProtoIfNot
            INTEGER,
        hpnicfCBQoSMatchCpProtoValue
            OCTET STRING,
        hpnicfCBQoSMatchCpProtoRowStatus
            RowStatus
    }

hpnicfCBQoSMatchCpProtoIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { hpnicfCBQoSMatchCpProtoCfgEntry 1 }

hpnicfCBQoSMatchCpProtoValue OBJECT-TYPE
    SYNTAX OCTET STRING (SIZE (0..255))
    MAX-ACCESS read-create
    STATUS current
    DESCRIPTION
        "Value of Cp Protocol, SIZE (1..23).  Up to 8 values can be input.
           for example: 1#2#3#4#5 means the match rule is
                        'if-match control-plane protocol arp arp-snooping
                        bgp bgp4+ bpdu-tunnel';
        arp: 1
        arp-snooping: 2
        bgp: 3
        bgp4+: 4
        bpdu-tunnel: 5
        cdp: 6
        cfd: 7
        dhcp: 8
        dhcp-snooping: 9
        dhcp6: 10
        dldp: 11
        dot1x: 12
        gmrp: 13
        gvrp: 14
        http: 15
        https: 16
        icmp: 17
        icmp6: 18
        igmp: 19
        igmp-snooping: 20
        irdp: 21
        isis: 22
        lacp: 23
        ldp: 24
        ldp6: 25
        lldp: 26
        mld: 27
        msdp: 28
        ntp: 29
        oam: 30
        ospf-multicast: 31
        ospf-unicast: 32
        ospf3-multicast: 33
        ospf3-unicast: 34
        pagp: 35
        pim-multicast: 36
        pim-unicast: 37
        pim6-multicast: 38
        pim6-unicast: 39
        portal: 40
        pppoe-negotiation: 41
        pvst: 42
        radius: 43
        rip: 44
        ripng: 45
        rrpp: 46
        rsvp: 47
        smart-link: 48
        snmp: 49
        stp: 50
        tacas: 51
        udld: 52
        udp-helper: 53
        vrrp: 54
        vrrp6: 55
        vtp: 56
        ip-option: 57
        ipv6-option: 58
        ssh: 59
        telnet: 60"
    ::= { hpnicfCBQoSMatchCpProtoCfgEntry 2 }

hpnicfCBQoSMatchCpProtoRowStatus OBJECT-TYPE
    SYNTAX RowStatus
    MAX-ACCESS read-create
    STATUS current
    DESCRIPTION
        "RowStatus."
    ::= { hpnicfCBQoSMatchCpProtoCfgEntry 3 }

-- hpnicfCBQoSMatchCpGroupCfgTable

hpnicfCBQoSMatchCpGroupCfgTable OBJECT-TYPE
    SYNTAX SEQUENCE OF HpnicfCBQoSMatchCpGroupCfgEntry
    MAX-ACCESS not-accessible
    STATUS current
    DESCRIPTION
        "A table of matching Cp protocol group rule configuration information."
    ::= { hpnicfCBQoSClassifierObjects 5 }

hpnicfCBQoSMatchCpGroupCfgEntry OBJECT-TYPE
    SYNTAX HpnicfCBQoSMatchCpGroupCfgEntry
    MAX-ACCESS not-accessible
    STATUS current
    DESCRIPTION
        "Matching Cp protocol group Rule Configuration Information Entry."
    INDEX { hpnicfCBQoSClassifierIndex, hpnicfCBQoSMatchRuleIndex }
    ::= { hpnicfCBQoSMatchCpGroupCfgTable 1 }

HpnicfCBQoSMatchCpGroupCfgEntry ::=
    SEQUENCE
    {
        hpnicfCBQoSMatchCpGroupIfNot
            INTEGER,
        hpnicfCBQoSMatchCpGroupValue
            INTEGER,
        hpnicfCBQoSMatchCpGroupRowStatus
            RowStatus
    }

hpnicfCBQoSMatchCpGroupIfNot OBJECT-TYPE
    SYNTAX INTEGER
    {
        match(1),
        matchNot(2)
    }
    MAX-ACCESS read-create
    STATUS current
    DESCRIPTION
        "Whether the if-match rule is a match or matchNot statement.
         Software QoS supports match, matchNot.
         Hardware QoS supports match.
        "
    DEFVAL { match }
    ::= { hpnicfCBQoSMatchCpGroupCfgEntry 1 }

hpnicfCBQoSMatchCpGroupValue OBJECT-TYPE
    SYNTAX INTEGER
    {
        critical(1),
        important(2),
        management(3),
        normal(4),
        redirect(5),
        monitor(6),
        exception(7)
    }
    MAX-ACCESS read-create
    STATUS current
    DESCRIPTION
        "Type of Cp protocol group.
        "
    ::= { hpnicfCBQoSMatchCpGroupCfgEntry 2 }

hpnicfCBQoSMatchCpGroupRowStatus OBJECT-TYPE
    SYNTAX RowStatus
    MAX-ACCESS read-create
    STATUS current
    DESCRIPTION
        "RowStatus."
    ::= { hpnicfCBQoSMatchCpGroupCfgEntry 3 }

-- hpnicfCBQoSBehaviorObjects

hpnicfCBQoSBehaviorObjects OBJECT IDENTIFIER ::= { hpnicfCBQoSObjects 2 }

-- Traffic Behavior Next Index

hpnicfCBQoSBehaviorIndexNext OBJECT-TYPE
    SYNTAX Integer32
    MAX-ACCESS read-only
    STATUS current
    DESCRIPTION
        "This object contains an appropriate value to be used for
         hpnicfCBQoSBehaviorIndex when creating rows in the
         hpnicfCBQoSBehaviorCfgInfoTable."
    ::= { hpnicfCBQoSBehaviorObjects 1 }

-- Traffic Behavior

hpnicfCBQoSBehaviorCfgInfoTable OBJECT-TYPE
    SYNTAX SEQUENCE OF HpnicfCBQoSBehaviorCfgInfoEntry
    MAX-ACCESS not-accessible
    STATUS current
    DESCRIPTION
        "A table of Traffic Behavior configuration information."
    ::= { hpnicfCBQoSBehaviorObjects 2 }

hpnicfCBQoSBehaviorCfgInfoEntry OBJECT-TYPE
    SYNTAX HpnicfCBQoSBehaviorCfgInfoEntry
    MAX-ACCESS not-accessible
    STATUS current
    DESCRIPTION
        "Traffic Behavior Configuration Information Entry."
    INDEX { hpnicfCBQoSBehaviorIndex }
    ::= { hpnicfCBQoSBehaviorCfgInfoTable 1 }

HpnicfCBQoSBehaviorCfgInfoEntry ::=
    SEQUENCE
    {
        hpnicfCBQoSBehaviorIndex
            Integer32,
        hpnicfCBQoSBehaviorName
            OCTET STRING,
        hpnicfCBQoSBehaviorType
            INTEGER,
        hpnicfCBQoSBehaviorRowStatus
            RowStatus
    }

hpnicfCBQoSBehaviorIndex OBJECT-TYPE
    SYNTAX Integer32
    MAX-ACCESS not-accessible
    STATUS current
    DESCRIPTION
        "Index of Traffic Behavior."
    ::= { hpnicfCBQoSBehaviorCfgInfoEntry 1 }

hpnicfCBQoSBehaviorName OBJECT-TYPE
    SYNTAX OCTET STRING (SIZE (1..31))
    MAX-ACCESS read-create
    STATUS current
    DESCRIPTION
        "Name of Traffic Behavior."
    ::= { hpnicfCBQoSBehaviorCfgInfoEntry 2 }

hpnicfCBQoSBehaviorType OBJECT-TYPE
    SYNTAX INTEGER
    {
        systemDefined(1),
        userDefined(2)
    }
    MAX-ACCESS read-only
    STATUS current
    DESCRIPTION
        "Type of behavior."
    ::= { hpnicfCBQoSBehaviorCfgInfoEntry 3 }

hpnicfCBQoSBehaviorRowStatus OBJECT-TYPE
    SYNTAX RowStatus
    MAX-ACCESS read-create
    STATUS current
    DESCRIPTION
        "RowStatus."
    ::= { hpnicfCBQoSBehaviorCfgInfoEntry 4 }

-- CAR

hpnicfCBQoSCarCfgInfoTable OBJECT-TYPE
    SYNTAX SEQUENCE OF HpnicfCBQoSCarCfgInfoEntry
    MAX-ACCESS not-accessible
    STATUS current
    DESCRIPTION
        "A table of CAR feature configuration information."
    ::= { hpnicfCBQoSBehaviorObjects 3 }

hpnicfCBQoSCarCfgInfoEntry OBJECT-TYPE
    SYNTAX HpnicfCBQoSCarCfgInfoEntry
    MAX-ACCESS not-accessible
    STATUS current
    DESCRIPTION
        "CAR Configuration Information Entry."
    INDEX { hpnicfCBQoSBehaviorIndex }
    ::= { hpnicfCBQoSCarCfgInfoTable 1 }

HpnicfCBQoSCarCfgInfoEntry ::=
    SEQUENCE
    {
        hpnicfCBQoSCarCir
            Unsigned32,
        hpnicfCBQoSCarCbs
            Unsigned32,
        hpnicfCBQoSCarEbs
            Unsigned32,
        hpnicfCBQoSCarPir
            Unsigned32,
        hpnicfCBQoSCarPbs
            Unsigned32,
        hpnicfCBQoSCarGreenAction
            CarAction,
        hpnicfCBQoSCarGreenRemarkValue
            Integer32,
        hpnicfCBQoSCarYellowAction
            CarAction,
        hpnicfCBQoSCarYellowRemarkValue
            Integer32,
        hpnicfCBQoSCarRedAction
            CarAction,
        hpnicfCBQoSCarRedRemarkValue
            Integer32,
        hpnicfCBQoSCarPolicedPriorityMapType
            INTEGER,
        hpnicfCBQoSCarRowStatus
            RowStatus
    }

hpnicfCBQoSCarCir OBJECT-TYPE
    SYNTAX Unsigned32
    MAX-ACCESS read-create
    STATUS current
    DESCRIPTION
        "Committed Information Rate.  Unit: kbps."
    ::= { hpnicfCBQoSCarCfgInfoEntry 1 }

hpnicfCBQoSCarCbs OBJECT-TYPE
    SYNTAX Unsigned32
    MAX-ACCESS read-create
    STATUS current
    DESCRIPTION
        "Committed Burst Size.  Unit: byte."
    ::= { hpnicfCBQoSCarCfgInfoEntry 2 }

hpnicfCBQoSCarEbs OBJECT-TYPE
    SYNTAX Unsigned32
    MAX-ACCESS read-create
    STATUS current
    DESCRIPTION
        "Excess Burst Size.  Unit: byte.
         Only software QoS support this node.
         4294967295 is returned only when getting value from hardware QoS.
         4294967295 can't be set."
    DEFVAL {0}
    ::= { hpnicfCBQoSCarCfgInfoEntry 3 }

hpnicfCBQoSCarPir OBJECT-TYPE
    SYNTAX Unsigned32
    MAX-ACCESS read-create
    STATUS current
    DESCRIPTION
        "Peak Information Rate.  Unit: kbps.
         Only hardware QoS support this node.
         4294967295 is returned only when getting value from software QoS.
         4294967295 can't be set."
    ::= { hpnicfCBQoSCarCfgInfoEntry 4 }

hpnicfCBQoSCarPbs OBJECT-TYPE
    SYNTAX Unsigned32
    MAX-ACCESS read-create
    STATUS current
    DESCRIPTION
        "Peak Burst Size.  Unit: byte.
         Only hardware QoS support this node.
         4294967295 is returned only when getting value from software QoS.
         4294967295 can't be set."
    ::= { hpnicfCBQoSCarCfgInfoEntry 5 }

hpnicfCBQoSCarGreenAction OBJECT-TYPE
    SYNTAX CarAction
    MAX-ACCESS read-create
    STATUS current
    DESCRIPTION
        "Green Action
         Hardware QoS : pass, discard, remark.
         Software QoS : pass, discard, remark IP Precedence, remark DSCP, remark MPLS EXP.
        "
    DEFVAL {pass}
    ::= { hpnicfCBQoSCarCfgInfoEntry 6 }

hpnicfCBQoSCarGreenRemarkValue OBJECT-TYPE
    SYNTAX Integer32 (0..63|255)
    MAX-ACCESS read-create
    STATUS current
    DESCRIPTION
        "The value is to remark When green action is remarking.
         For remarking DSCP, the range is 0~63;
         For remarking IP Precedence and MPLS EXP, the range is 0~7;
         Only software QoS support this node.
         255 is returned only when getting value from hardware QoS or
         when action being pass, discard of software QoS.
         255 can't be set.
        "
    ::= { hpnicfCBQoSCarCfgInfoEntry 7 }

hpnicfCBQoSCarYellowAction OBJECT-TYPE
    SYNTAX CarAction
    MAX-ACCESS read-create
    STATUS current
    DESCRIPTION
        "Yellow Action:
         Only hardware QoS support this node.  Hardware QoS support pass, discard, remark.
         invalid is returned only when getting value from software QoS.
         invalid can't be set.
        "
    DEFVAL {remark}
    ::= { hpnicfCBQoSCarCfgInfoEntry 8 }

hpnicfCBQoSCarYellowRemarkValue OBJECT-TYPE
    SYNTAX Integer32 (0..63|255)
    MAX-ACCESS read-create
    STATUS current
    DESCRIPTION
        "The value is to remark When red action is remarking.
         For remarking DSCP, the range is 0~63;
         For remarking IP Precedence and MPLS EXP, the range is 0~7;
         Only software QoS support this node.
         255 is returned only when getting value from hardware QoS or
         when action being pass, discard of software QoS.
         255 can't be set."
    ::= { hpnicfCBQoSCarCfgInfoEntry 9 }

hpnicfCBQoSCarRedAction OBJECT-TYPE
    SYNTAX CarAction
    MAX-ACCESS read-create
    STATUS current
    DESCRIPTION
        "Red Action:
         Hardware QoS : pass, discard, remark.
         Software QoS : pass, discard, remark IP Precedence, remark DSCP, remark MPLS EXP.
        "
    DEFVAL {discard}
    ::= { hpnicfCBQoSCarCfgInfoEntry 10 }

hpnicfCBQoSCarRedRemarkValue OBJECT-TYPE
    SYNTAX Integer32 (0..63|255)
    MAX-ACCESS read-create
    STATUS current
    DESCRIPTION
        "The value is to remark When red action is remarking.
         For remarking DSCP, the range is 0~63;
         For remarking IP Precedence and MPLS EXP, the range is 0~7;
         Only software QoS support this node.
         255 is returned only when getting value from hardware QoS or
         when action being pass, discard of software QoS.
         255 can't be set."
    ::= { hpnicfCBQoSCarCfgInfoEntry 11 }

hpnicfCBQoSCarPolicedPriorityMapType OBJECT-TYPE
    SYNTAX INTEGER
    {
        none(0),
        policed-service-map(1),
        local-precedence-dot1p-map(2),
        drop-precedence-map(3)
    }
    MAX-ACCESS read-create
    STATUS current
    DESCRIPTION
        "Type of priority map."
    DEFVAL { none }
    ::= { hpnicfCBQoSCarCfgInfoEntry 12 }

hpnicfCBQoSCarRowStatus OBJECT-TYPE
    SYNTAX RowStatus
    MAX-ACCESS read-create
    STATUS current
    DESCRIPTION
        "RowStatus."
    ::= { hpnicfCBQoSCarCfgInfoEntry 13 }

--
-- nodes of aggregative CAR applyed behavior
--
hpnicfCBQoSAggregativeCarCfgInfoTable OBJECT-TYPE
    SYNTAX SEQUENCE OF HpnicfCBQoSAggregativeCarCfgInfoEntry
    MAX-ACCESS not-accessible
    STATUS current
    DESCRIPTION
        "A table of aggregative CAR applied CBQ feature configuration information.
         Aggregative CAR is managed by HPN-ICF-IFQOS2-MIB.  So, you can use HPN-ICF-IFQOS2-MIB
         to get some details information about aggregative CAR.
        "
    ::= { hpnicfCBQoSBehaviorObjects 4 }

hpnicfCBQoSAggregativeCarCfgInfoEntry OBJECT-TYPE
    SYNTAX HpnicfCBQoSAggregativeCarCfgInfoEntry
    MAX-ACCESS not-accessible
    STATUS current
    DESCRIPTION
        "Aggregative CAR feature applied CBQ configuration information entry."
    INDEX { hpnicfCBQoSBehaviorIndex,
            hpnicfCBQoSCarAggregativeCarIndex }
    ::= { hpnicfCBQoSAggregativeCarCfgInfoTable 1 }

HpnicfCBQoSAggregativeCarCfgInfoEntry ::=
    SEQUENCE
    {
        hpnicfCBQoSCarAggregativeCarIndex
            Integer32,
        hpnicfCBQoSCarAggregativeCarName
            OCTET STRING,
        hpnicfCBQoSAggregativeCarRowStatus
            RowStatus
    }

hpnicfCBQoSCarAggregativeCarIndex OBJECT-TYPE
    SYNTAX Integer32
    MAX-ACCESS not-accessible
    STATUS current
    DESCRIPTION
        "Index of aggregative CAR.
         It is equal to hpnicfIfQoSAggregativeCarIndex at HPN-ICF-IFQOS2-MIB.
        "
    ::= { hpnicfCBQoSAggregativeCarCfgInfoEntry 1 }

hpnicfCBQoSCarAggregativeCarName OBJECT-TYPE
    SYNTAX OCTET STRING (SIZE(1..31))
    MAX-ACCESS read-only
    STATUS current
    DESCRIPTION
        "Name of aggregative CAR.
         It is equal to hpnicfIfQoSAggregativeCarName at HPN-ICF-IFQOS2-MIB.
        "
    ::= { hpnicfCBQoSAggregativeCarCfgInfoEntry 2 }

hpnicfCBQoSAggregativeCarRowStatus OBJECT-TYPE
    SYNTAX RowStatus
    MAX-ACCESS read-create
    STATUS current
    DESCRIPTION
        "RowStatus."
    ::= { hpnicfCBQoSAggregativeCarCfgInfoEntry 3 }

-- GTS

hpnicfCBQoSGtsCfgInfoTable OBJECT-TYPE
    SYNTAX SEQUENCE OF HpnicfCBQoSGtsCfgInfoEntry
    MAX-ACCESS not-accessible
    STATUS current
    DESCRIPTION
        "A table of GTS feature configuration information."
    ::= { hpnicfCBQoSBehaviorObjects 5 }

hpnicfCBQoSGtsCfgInfoEntry OBJECT-TYPE
    SYNTAX HpnicfCBQoSGtsCfgInfoEntry
    MAX-ACCESS not-accessible
    STATUS current
    DESCRIPTION
        "GTS Configuration Information Entry."
    INDEX { hpnicfCBQoSBehaviorIndex }
    ::= { hpnicfCBQoSGtsCfgInfoTable 1 }

HpnicfCBQoSGtsCfgInfoEntry ::=
    SEQUENCE
    {
        hpnicfCBQoSGtsCir
            Unsigned32,
        hpnicfCBQoSGtsCbs
            Unsigned32,
        hpnicfCBQoSGtsEbs
            Unsigned32,
        hpnicfCBQoSGtsQueueLength
            Integer32,
        hpnicfCBQoSGtsRowStatus
            RowStatus,
        hpnicfCBQoSGtsPir
            Unsigned32
    }

hpnicfCBQoSGtsCir OBJECT-TYPE
    SYNTAX Unsigned32
    MAX-ACCESS read-create
    STATUS current
    DESCRIPTION
        "Committed Information Rate.  Unit: kbps"
    ::= { hpnicfCBQoSGtsCfgInfoEntry 1 }

hpnicfCBQoSGtsCbs OBJECT-TYPE
    SYNTAX Unsigned32
    MAX-ACCESS read-create
    STATUS current
    DESCRIPTION
        "Committed Burst Size.  Unit: byte
         default: max(cir*1/2,15000)"
    ::= { hpnicfCBQoSGtsCfgInfoEntry 2 }

hpnicfCBQoSGtsEbs OBJECT-TYPE
    SYNTAX Unsigned32
    MAX-ACCESS read-create
    STATUS current
    DESCRIPTION
        "Excess Burst Size.  Unit: byte"
    ::= { hpnicfCBQoSGtsCfgInfoEntry 3 }

hpnicfCBQoSGtsQueueLength OBJECT-TYPE
    SYNTAX Integer32 (1..1024)
    MAX-ACCESS read-create
    STATUS current
    DESCRIPTION
        "The length of GTS buffer."
    DEFVAL { 50 }
    ::= { hpnicfCBQoSGtsCfgInfoEntry 4 }

hpnicfCBQoSGtsRowStatus OBJECT-TYPE
    SYNTAX RowStatus
    MAX-ACCESS read-create
    STATUS current
    DESCRIPTION
        "RowStatus."
    ::= { hpnicfCBQoSGtsCfgInfoEntry 5 }

hpnicfCBQoSGtsPir OBJECT-TYPE
    SYNTAX Unsigned32
    UNITS  "kbps"
    MAX-ACCESS read-create
    STATUS current
    DESCRIPTION
        "Peak Information Rate."
    ::= { hpnicfCBQoSGtsCfgInfoEntry 6 }

-- REMARK

hpnicfCBQoSRemarkCfgInfoTable OBJECT-TYPE
    SYNTAX SEQUENCE OF HpnicfCBQoSRemarkCfgInfoEntry
    MAX-ACCESS not-accessible
    STATUS current
    DESCRIPTION
        "A table of Remarking feature configuration information."
    ::= { hpnicfCBQoSBehaviorObjects 6 }

hpnicfCBQoSRemarkCfgInfoEntry OBJECT-TYPE
    SYNTAX HpnicfCBQoSRemarkCfgInfoEntry
    MAX-ACCESS not-accessible
    STATUS current
    DESCRIPTION
        "Remarking Configuration Information Entry."
    INDEX { hpnicfCBQoSBehaviorIndex, hpnicfCBQoSRemarkType }
    ::= { hpnicfCBQoSRemarkCfgInfoTable 1 }

HpnicfCBQoSRemarkCfgInfoEntry ::=
    SEQUENCE
    {
        hpnicfCBQoSRemarkType
            RemarkType,
        hpnicfCBQoSRemarkValue
            Integer32,
        hpnicfCBQoSRemarkRowStatus
            RowStatus
    }

hpnicfCBQoSRemarkType OBJECT-TYPE
    SYNTAX RemarkType
    MAX-ACCESS not-accessible
    STATUS current
    DESCRIPTION
        "Remark type."
    ::= { hpnicfCBQoSRemarkCfgInfoEntry 1 }

hpnicfCBQoSRemarkValue OBJECT-TYPE
    SYNTAX Integer32 (0..4095)
    MAX-ACCESS read-create
    STATUS current
    DESCRIPTION
        "Value to remark:
         for IpPrecedence: 0~7
         for Dscp: 0~63
         for MplsExp: 0~7
         for Vlan8021p: 0~7
         for AtmClp: 0~1
         for FrDe: 0~1
         for VlanID: 1~4094
         for QosLocalID: 1~4095
         for DropPrecedence: 0~2
         for LocalPrecedence: 0~7
         for TopMostVlanID: 1~4094
         for SecondMplsExp: 0~7
        "
    ::= { hpnicfCBQoSRemarkCfgInfoEntry 2 }

hpnicfCBQoSRemarkRowStatus OBJECT-TYPE
    SYNTAX RowStatus
    MAX-ACCESS read-create
    STATUS current
    DESCRIPTION
        "RowStatus"
    ::= { hpnicfCBQoSRemarkCfgInfoEntry 3 }

-- Queue

hpnicfCBQoSQueueCfgInfoTable OBJECT-TYPE
    SYNTAX SEQUENCE OF HpnicfCBQoSQueueCfgInfoEntry
    MAX-ACCESS not-accessible
    STATUS current
    DESCRIPTION
        "A table of queue feature configuration information."
    ::= { hpnicfCBQoSBehaviorObjects 7 }

hpnicfCBQoSQueueCfgInfoEntry OBJECT-TYPE
    SYNTAX HpnicfCBQoSQueueCfgInfoEntry
    MAX-ACCESS not-accessible
    STATUS current
    DESCRIPTION
        "Queue Configuration Information Entry."
    INDEX { hpnicfCBQoSBehaviorIndex }
    ::= { hpnicfCBQoSQueueCfgInfoTable 1 }

HpnicfCBQoSQueueCfgInfoEntry ::=
    SEQUENCE
    {
        hpnicfCBQoSQueueType
            QueueType,
        hpnicfCBQoSQueueDropType
            INTEGER,
        hpnicfCBQoSQueueLength
            Integer32,
        hpnicfCBQoSQueueBandwidthUnit
            QueueBandwidthUnit,
        hpnicfCBQoSQueueBandwidthValue
            Integer32,
        hpnicfCBQoSQueueCbs
            Integer32,
        hpnicfCBQoSQueueQueueNumber
            INTEGER,
        hpnicfCBQoSQueueCbsRatio
            Integer32,
        hpnicfCBQoSQueueRowStatus
            RowStatus
    }

hpnicfCBQoSQueueType OBJECT-TYPE
    SYNTAX QueueType
    MAX-ACCESS read-create
    STATUS current
    DESCRIPTION
        "Queueing Type:
         EF:(1)
         AF:(2)
         WFQ:(3)"
    ::= { hpnicfCBQoSQueueCfgInfoEntry 1 }

hpnicfCBQoSQueueDropType OBJECT-TYPE
    SYNTAX INTEGER
    {
        typeUnavailable(0),
        typeTailDrop(1),
        typeWred(2)
    }
    MAX-ACCESS read-create
    STATUS current
    DESCRIPTION
        "The drop type of queue.  Only valid for AF and WFQ queue.
         typeUnavailable is returned only when getting value about EF queue.
         typeUnavailable can't be set."
    DEFVAL {typeTailDrop}
    ::= { hpnicfCBQoSQueueCfgInfoEntry 2 }

hpnicfCBQoSQueueLength OBJECT-TYPE
    SYNTAX Integer32 (1..2147483647)
    MAX-ACCESS read-create
    STATUS current
    DESCRIPTION
        "The length of QueueLength.  Only valid for tail-drop type
         of AF and WFQ queue.
         2147483647 is returned only when getting value about EF queue
         or WRED type of AF and WFQ queue.
         2147483647 can't be set."
    DEFVAL { 64 }
    ::= { hpnicfCBQoSQueueCfgInfoEntry 3 }

hpnicfCBQoSQueueBandwidthUnit OBJECT-TYPE
    SYNTAX QueueBandwidthUnit
    MAX-ACCESS read-create
    STATUS current
    DESCRIPTION
        "Bandwidth Unit:
         Absolute, Unit Kbps (1)
         Percent, Unit % (2)
         RemainPercent, Unit % of remained bandwidth (3)
         Only valid for EF and AF queue.
         0 is returned only when getting value about WFQ queue.
         0 can't be set.
        "
    ::= { hpnicfCBQoSQueueCfgInfoEntry 4 }

hpnicfCBQoSQueueBandwidthValue OBJECT-TYPE
    SYNTAX Integer32 (1..10000000|2147483647)
    MAX-ACCESS read-create
    STATUS current
    DESCRIPTION
        "Bandwidth value:
         Absolute value: 8~10000000.  Unit: Kbps
         Percent value: 1~100.
         Only valid for EF and AF queue.
         2147483647 is returned only when getting value about WFQ queue.
         2147483647 can't be set."
    ::= { hpnicfCBQoSQueueCfgInfoEntry 5 }

hpnicfCBQoSQueueCbs OBJECT-TYPE
    SYNTAX Integer32 (32..1000000000|2147483647)
    MAX-ACCESS read-create
    STATUS current
    DESCRIPTION
        "Committed Burst Size.  Unit: byte.
         Only valid for EF queue.
         Default: If the value of 'hpnicfCBQoSQueueBandwidthValue * 25' is
                  between 1500 and 2000000, the default value of this
                  object is 'hpnicfCBQoSQueueBandwidthValue * 25';If the value of
                  'hpnicfCBQoSQueueBandwidthValue * 25' is larger than or equal to
                  2000000, the default value of this object is 2000000;
                  If the value of 'hpnicfCBQoSQueueBandwidthValue * 25' is
                  less than or equal to 1500, the default value of this object is 1500.
         2147483647 is returned only when getting value about AF or WFQ queue.
         2147483647 can't be set."
    ::= { hpnicfCBQoSQueueCfgInfoEntry 6 }

hpnicfCBQoSQueueQueueNumber OBJECT-TYPE
    SYNTAX INTEGER
    {
        unavailable(0),
        a16(16),
        a32(32),
        a64(64),
        a128(128),
        a256(256),
        a512(512),
        a1024(1024),
        a2048(2048),
        a4096(4096)
    }
    MAX-ACCESS read-create
    STATUS current
    DESCRIPTION
        "Max number of hashed queues (a power of 2).
         Only valid for WFQ.
         'unavailable' is returned only when getting value about AF or EF queue.
         'unavailable' can't be set."
    DEFVAL {a256}
    ::= { hpnicfCBQoSQueueCfgInfoEntry 7 }

hpnicfCBQoSQueueCbsRatio OBJECT-TYPE
    SYNTAX Integer32(25..500|2147483647)
    MAX-ACCESS read-create
    STATUS current
    DESCRIPTION
        "Committed Burst Size Ratio.
         CBS = CBS_Ratio * Bandwidth(k bps)
         Only valid for EF queue.
         2147483647 is returned only when getting value about AF or WFQ queue.
         2147483647 can't be set.
        "
    DEFVAL { 25 }
    ::= { hpnicfCBQoSQueueCfgInfoEntry 8 }

hpnicfCBQoSQueueRowStatus OBJECT-TYPE
    SYNTAX RowStatus
    MAX-ACCESS read-create
    STATUS current
    DESCRIPTION
        "RowStatus."
    ::= { hpnicfCBQoSQueueCfgInfoEntry 9 }

-- WRED

hpnicfCBQoSWredCfgInfoTable OBJECT-TYPE
    SYNTAX SEQUENCE OF HpnicfCBQoSWredCfgInfoEntry
    MAX-ACCESS not-accessible
    STATUS current
    DESCRIPTION
        "A table of WRED configuration information."
    ::= { hpnicfCBQoSBehaviorObjects 8 }

hpnicfCBQoSWredCfgInfoEntry OBJECT-TYPE
    SYNTAX HpnicfCBQoSWredCfgInfoEntry
    MAX-ACCESS not-accessible
    STATUS current
    DESCRIPTION
        "WRED Configuration Information Entry."
    INDEX { hpnicfCBQoSBehaviorIndex }
    ::= { hpnicfCBQoSWredCfgInfoTable 1 }

HpnicfCBQoSWredCfgInfoEntry ::=
    SEQUENCE
    {
        hpnicfCBQoSWredType
            WredType,
        hpnicfCBQoSWredWeightConst
            Integer32
    }

hpnicfCBQoSWredType OBJECT-TYPE
    SYNTAX WredType
    MAX-ACCESS read-write
    STATUS current
    DESCRIPTION
        "WRED type."
    DEFVAL { 1 }
    ::= { hpnicfCBQoSWredCfgInfoEntry 1 }

hpnicfCBQoSWredWeightConst OBJECT-TYPE
    SYNTAX Integer32 (1..16)
    MAX-ACCESS read-write
    STATUS current
    DESCRIPTION
        "Specify weight for calculating mean queue depth."
    DEFVAL { 9 }
    ::= { hpnicfCBQoSWredCfgInfoEntry 2 }

-- WRED Class

hpnicfCBQoSWredClassCfgInfoTable OBJECT-TYPE
    SYNTAX SEQUENCE OF HpnicfCBQoSWredClassCfgInfoEntry
    MAX-ACCESS not-accessible
    STATUS current
    DESCRIPTION
        "A table of WRED configuration information."
    ::= { hpnicfCBQoSBehaviorObjects 9 }

hpnicfCBQoSWredClassCfgInfoEntry OBJECT-TYPE
    SYNTAX HpnicfCBQoSWredClassCfgInfoEntry
    MAX-ACCESS not-accessible
    STATUS current
    DESCRIPTION
        "WRED Class Configuration Information Entry."
    INDEX { hpnicfCBQoSBehaviorIndex, hpnicfCBQoSWredClassValue }
    ::= { hpnicfCBQoSWredClassCfgInfoTable 1 }

HpnicfCBQoSWredClassCfgInfoEntry ::=
    SEQUENCE
    {
        hpnicfCBQoSWredClassValue
            Integer32,
        hpnicfCBQoSWredClassLowLimit
            Integer32,
        hpnicfCBQoSWredClassHighLimit
            Integer32,
        hpnicfCBQoSWredClassDiscardProb
            Integer32
    }

hpnicfCBQoSWredClassValue OBJECT-TYPE
    SYNTAX Integer32 (0..63)
    MAX-ACCESS not-accessible
    STATUS current
    DESCRIPTION
        "The class value.
         For IP precedence based WRED, the class is IP precedence,
         and range is 0~7.
         For DSCP based WRED, the class is DSCP, and range is 0~63.
        "
    ::= { hpnicfCBQoSWredClassCfgInfoEntry 1 }

hpnicfCBQoSWredClassLowLimit OBJECT-TYPE
    SYNTAX Integer32 (1..1024)
    MAX-ACCESS read-write
    STATUS current
    DESCRIPTION
        "The low limit of queue depth."
    DEFVAL {10}
    ::= { hpnicfCBQoSWredClassCfgInfoEntry 2 }

hpnicfCBQoSWredClassHighLimit OBJECT-TYPE
    SYNTAX Integer32 (1..1024)
    MAX-ACCESS read-write
    STATUS current
    DESCRIPTION
        "The high limit of queue depth."
    DEFVAL { 30 }
    ::= { hpnicfCBQoSWredClassCfgInfoEntry 3 }

hpnicfCBQoSWredClassDiscardProb OBJECT-TYPE
    SYNTAX Integer32 (1..255)
    MAX-ACCESS read-write
    STATUS current
    DESCRIPTION
        "The discard probability denominator."
    DEFVAL { 10 }
    ::= { hpnicfCBQoSWredClassCfgInfoEntry 4 }

-- Policy Route

hpnicfCBQoSPolicyRouteCfgInfoTable OBJECT-TYPE
    SYNTAX SEQUENCE OF HpnicfCBQoSPolicyRouteCfgInfoEntry
    MAX-ACCESS not-accessible
    STATUS current
    DESCRIPTION
        "A table of Policy Routing configuration information."
    ::= { hpnicfCBQoSBehaviorObjects 10 }

hpnicfCBQoSPolicyRouteCfgInfoEntry OBJECT-TYPE
    SYNTAX HpnicfCBQoSPolicyRouteCfgInfoEntry
    MAX-ACCESS not-accessible
    STATUS current
    DESCRIPTION
        "Policy Routeing Configuration Information Entry."
    INDEX { hpnicfCBQoSBehaviorIndex }
    ::= { hpnicfCBQoSPolicyRouteCfgInfoTable 1 }

HpnicfCBQoSPolicyRouteCfgInfoEntry ::=
    SEQUENCE
    {
        hpnicfCBQoSPolicyRouteIpAddrType
            InetAddressType,
        hpnicfCBQoSPolicyRouteNexthop
            InetAddress,
        hpnicfCBQoSPolicyRouteBackup
            INTEGER,
        hpnicfCBQoSPolicyRouteRowStatus
            RowStatus
    }

hpnicfCBQoSPolicyRouteIpAddrType OBJECT-TYPE
    SYNTAX InetAddressType
    MAX-ACCESS read-create
    STATUS current
    DESCRIPTION
        "Type of InetAddress."
    ::= { hpnicfCBQoSPolicyRouteCfgInfoEntry 1 }

hpnicfCBQoSPolicyRouteNexthop OBJECT-TYPE
    SYNTAX InetAddress
    MAX-ACCESS read-create
    STATUS current
    DESCRIPTION
        "The next-hop ip address for redirection."
    ::= { hpnicfCBQoSPolicyRouteCfgInfoEntry 2 }

hpnicfCBQoSPolicyRouteBackup OBJECT-TYPE
    SYNTAX INTEGER
    {
        backup(1),
        notbackup(2)
    }
    MAX-ACCESS read-create
    STATUS current
    DESCRIPTION
        "Whether forward the packet according to the routing table
         When the next-hop IP address for redirection is not valid.
         Backup means forwarding.  NoBackup means not forwarding.
        "
    ::= { hpnicfCBQoSPolicyRouteCfgInfoEntry 3 }

hpnicfCBQoSPolicyRouteRowStatus OBJECT-TYPE
    SYNTAX RowStatus
    MAX-ACCESS read-create
    STATUS current
    DESCRIPTION
        "RowStatus."
    ::= { hpnicfCBQoSPolicyRouteCfgInfoEntry 4 }

-- NAT

hpnicfCBQoSNatCfgInfoTable OBJECT-TYPE
    SYNTAX SEQUENCE OF HpnicfCBQoSNatCfgInfoEntry
    MAX-ACCESS not-accessible
    STATUS current
    DESCRIPTION
        "A table of Nat configuration information."
    ::= { hpnicfCBQoSBehaviorObjects 11 }

hpnicfCBQoSNatCfgInfoEntry OBJECT-TYPE
    SYNTAX HpnicfCBQoSNatCfgInfoEntry
    MAX-ACCESS not-accessible
    STATUS current
    DESCRIPTION
        "Nat Configuration Information Entry."
    INDEX { hpnicfCBQoSBehaviorIndex }
    ::= { hpnicfCBQoSNatCfgInfoTable 1 }

HpnicfCBQoSNatCfgInfoEntry ::=
    SEQUENCE
    {
        hpnicfCBQoSNatMainNumber
            Integer32,
        hpnicfCBQoSNatBackupNumber
            Integer32,
        hpnicfCBQoSNatServiceClass
            Integer32,
        hpnicfCBQoSNatRowStatus
            RowStatus
    }

hpnicfCBQoSNatMainNumber OBJECT-TYPE
    SYNTAX Integer32 (1..255)
    MAX-ACCESS read-create
    STATUS current
    DESCRIPTION
        "The main ISP number."
    ::= { hpnicfCBQoSNatCfgInfoEntry 1 }

hpnicfCBQoSNatBackupNumber OBJECT-TYPE
    SYNTAX Integer32 (1..255)
    MAX-ACCESS read-create
    STATUS current
    DESCRIPTION
        "The backup ISP number"
    ::= { hpnicfCBQoSNatCfgInfoEntry 2 }

hpnicfCBQoSNatServiceClass OBJECT-TYPE
    SYNTAX Integer32 (1..4)
    MAX-ACCESS read-create
    STATUS current
    DESCRIPTION
        "The service class."
    DEFVAL { 2 }
    ::= { hpnicfCBQoSNatCfgInfoEntry 3 }

hpnicfCBQoSNatRowStatus OBJECT-TYPE
    SYNTAX RowStatus
    MAX-ACCESS read-create
    STATUS current
    DESCRIPTION
        "RowStatus."
    ::= { hpnicfCBQoSNatCfgInfoEntry 4 }

-- Firewall

hpnicfCBQoSFirewallCfgInfoTable OBJECT-TYPE
    SYNTAX SEQUENCE OF HpnicfCBQoSFirewallCfgInfoEntry
    MAX-ACCESS not-accessible
    STATUS current
    DESCRIPTION
        "A table of firewall configuration information."
    ::= { hpnicfCBQoSBehaviorObjects 12 }

hpnicfCBQoSFirewallCfgInfoEntry OBJECT-TYPE
    SYNTAX HpnicfCBQoSFirewallCfgInfoEntry
    MAX-ACCESS not-accessible
    STATUS current
    DESCRIPTION
        "Firewall configuration information entry."
    INDEX { hpnicfCBQoSBehaviorIndex }
    ::= { hpnicfCBQoSFirewallCfgInfoTable 1 }

HpnicfCBQoSFirewallCfgInfoEntry ::=
    SEQUENCE
    {
        hpnicfCBQoSFirewallAction
            INTEGER,
        hpnicfCBQoSFirewallRowStatus
            RowStatus
    }

hpnicfCBQoSFirewallAction OBJECT-TYPE
    SYNTAX INTEGER
    {
        permit(1),
        deny(2)
    }
    MAX-ACCESS read-create
    STATUS current
    DESCRIPTION
        "The firewall action "
    DEFVAL {permit}
    ::= { hpnicfCBQoSFirewallCfgInfoEntry 1 }

hpnicfCBQoSFirewallRowStatus OBJECT-TYPE
    SYNTAX RowStatus
    MAX-ACCESS read-create
    STATUS current
    DESCRIPTION
        "RowStatus."
    ::= { hpnicfCBQoSFirewallCfgInfoEntry 2 }

-- Sampling behavior

hpnicfCBQoSSamplingCfgInfoTable OBJECT-TYPE
    SYNTAX SEQUENCE OF HpnicfCBQoSSamplingCfgInfoEntry
    MAX-ACCESS not-accessible
    STATUS current
    DESCRIPTION
        "A table of sampling configuration information."
    ::= { hpnicfCBQoSBehaviorObjects 13 }

hpnicfCBQoSSamplingCfgInfoEntry OBJECT-TYPE
    SYNTAX HpnicfCBQoSSamplingCfgInfoEntry
    MAX-ACCESS not-accessible
    STATUS current
    DESCRIPTION
        "Sampling configuration information entry."
    INDEX { hpnicfCBQoSBehaviorIndex }
    ::= { hpnicfCBQoSSamplingCfgInfoTable 1 }

HpnicfCBQoSSamplingCfgInfoEntry ::=
    SEQUENCE
    {
        hpnicfCBQoSSamplingNum
            Integer32,
        hpnicfCBQoSSamplingRowStatus
            RowStatus
    }

hpnicfCBQoSSamplingNum OBJECT-TYPE
    SYNTAX Integer32 (1..16)
    MAX-ACCESS read-create
    STATUS current
    DESCRIPTION
        "The sampling number."
    ::= { hpnicfCBQoSSamplingCfgInfoEntry 1 }

hpnicfCBQoSSamplingRowStatus OBJECT-TYPE
    SYNTAX RowStatus
    MAX-ACCESS read-create
    STATUS current
    DESCRIPTION
        "RowStatus."
    ::= { hpnicfCBQoSSamplingCfgInfoEntry 2 }

hpnicfCBQoSAccountCfgInfoTable OBJECT-TYPE
    SYNTAX SEQUENCE OF HpnicfCBQoSAccountCfgInfoEntry
    MAX-ACCESS not-accessible
    STATUS current
    DESCRIPTION
        "A table of account configuration information."
    ::= { hpnicfCBQoSBehaviorObjects 14 }

hpnicfCBQoSAccountCfgInfoEntry OBJECT-TYPE
    SYNTAX HpnicfCBQoSAccountCfgInfoEntry
    MAX-ACCESS not-accessible
    STATUS current
    DESCRIPTION
        "Account configuration information entry."
    INDEX { hpnicfCBQoSBehaviorIndex }
    ::= { hpnicfCBQoSAccountCfgInfoTable 1 }

HpnicfCBQoSAccountCfgInfoEntry ::=
    SEQUENCE
    {
        hpnicfCBQoSAccounting
            TruthValue,
        hpnicfCBQoSAccountRowStatus
            RowStatus,
        hpnicfCBQoSAccountingMode
            INTEGER
    }

hpnicfCBQoSAccounting OBJECT-TYPE
    SYNTAX TruthValue
    MAX-ACCESS read-create
    STATUS current
    DESCRIPTION
        "Account action."
    ::= { hpnicfCBQoSAccountCfgInfoEntry 1 }

hpnicfCBQoSAccountRowStatus OBJECT-TYPE
    SYNTAX RowStatus
    MAX-ACCESS read-create
    STATUS current
    DESCRIPTION
        "RowStatus."
    ::= { hpnicfCBQoSAccountCfgInfoEntry 2 }

hpnicfCBQoSAccountingMode OBJECT-TYPE
    SYNTAX INTEGER
    {
        auto(1),
        packet(2),
        byte(3),
        both(4)
    }
    MAX-ACCESS read-create
    STATUS current
    DESCRIPTION
        "Account mode."
    DEFVAL { auto }
    ::= { hpnicfCBQoSAccountCfgInfoEntry 3 }

--
-- nodes of hpnicfCBQoSRedirectCfgInfoTable
--
hpnicfCBQoSRedirectCfgInfoTable OBJECT-TYPE
    SYNTAX SEQUENCE OF HpnicfCBQoSRedirectCfgInfoEntry
    MAX-ACCESS not-accessible
    STATUS current
    DESCRIPTION
        "A table of redirect configuration information."
    ::= { hpnicfCBQoSBehaviorObjects 15 }

hpnicfCBQoSRedirectCfgInfoEntry OBJECT-TYPE
    SYNTAX HpnicfCBQoSRedirectCfgInfoEntry
    MAX-ACCESS not-accessible
    STATUS current
    DESCRIPTION
        "Redirect configuration information entry."
    INDEX { hpnicfCBQoSBehaviorIndex }
    ::= { hpnicfCBQoSRedirectCfgInfoTable 1 }

HpnicfCBQoSRedirectCfgInfoEntry ::=
    SEQUENCE
    {
        hpnicfCBQoSRedirectType
            INTEGER,
        hpnicfCBQoSRedirectIfIndex
            Integer32,
        hpnicfCBQoSRedirectIpAddressType
            InetAddressType,
        hpnicfCBQoSRedirectIpAddress1
            InetAddress,
        hpnicfCBQoSRedirectIpAddress2
            InetAddress,
        hpnicfCBQoSRedirectRowStatus
            RowStatus,
        hpnicfCBQoSRedirectIpv6Interface1
            Integer32,
        hpnicfCBQoSRedirectIpv6Interface2
            Integer32,
        hpnicfCBQoSRedirectIfVlanID
            Integer32
    }

hpnicfCBQoSRedirectType OBJECT-TYPE
    SYNTAX INTEGER
    {
        cpu(1),
        interface(2),
        nextHop(3)
    }
    MAX-ACCESS read-create
    STATUS current
    DESCRIPTION
        "The type of redirect."
    ::= { hpnicfCBQoSRedirectCfgInfoEntry 1 }

hpnicfCBQoSRedirectIfIndex OBJECT-TYPE
    SYNTAX Integer32
    MAX-ACCESS read-create
    STATUS current
    DESCRIPTION
        "ifIndex.
         Only the value of hpnicfCBQoSRedirectType is interface,
         can be set this node.
        "
    DEFVAL { 0 }
    ::= { hpnicfCBQoSRedirectCfgInfoEntry 2 }

hpnicfCBQoSRedirectIpAddressType OBJECT-TYPE
    SYNTAX InetAddressType
    MAX-ACCESS read-create
    STATUS current
    DESCRIPTION
        "A value that represents a type of Internet address.
          unknown(0)  An unknown address type.  This value MUST
             be used if the value of the corresponding
             InetAddress object is a zero-length string.
             It may also be used to indicate an IP address
             which is not in one of the formats defined
             below.

          ipv4(1)     An IPv4 address as defined by the
             InetAddressIPv4 textual convention.

          ipv6(2)     A global IPv6 address as defined by the
             InetAddressIPv6 textual convention.

          ipv4z(3)    A non-global IPv4 address including a zone
             index as defined by the InetAddressIPv4z
             textual convention.

          ipv6z(4)    A non-global IPv6 address including a zone
             index as defined by the InetAddressIPv6z
             textual convention.

          dns(16)     A DNS domain name as defined by the
             InetAddressDNS textual convention.
          Now supports ipv4 and ipv6.
          Only the value of hpnicfCBQoSRedirectType is next-hop,
          can be set this node and hpnicfCBQoSRedirectIpAddress1 or hpnicfCBQoSRedirectIpAddress2.
        "
    DEFVAL { unknown }
    ::= { hpnicfCBQoSRedirectCfgInfoEntry 3 }

hpnicfCBQoSRedirectIpAddress1 OBJECT-TYPE
    SYNTAX InetAddress
    MAX-ACCESS read-create
    STATUS current
    DESCRIPTION
        "IP Address.
         If the value of hpnicfCBQoSRedirectType is not next-hop,
         zero-length string will be returned when getting.
         If the value of hpnicfCBQoSRedirectIpAddressType is ipv6,
         this node is set necessarily.
        "
    ::= { hpnicfCBQoSRedirectCfgInfoEntry 4 }

hpnicfCBQoSRedirectIpAddress2 OBJECT-TYPE
    SYNTAX InetAddress
    MAX-ACCESS read-create
    STATUS current
    DESCRIPTION
        "IP Address.
         If the value of hpnicfCBQoSRedirectType is not next-hop,
         zero-length string will be returned when getting.
         If the value of hpnicfCBQoSRedirectIpAddressType is ipv6,
         this node is set optionally.
        "
    ::= { hpnicfCBQoSRedirectCfgInfoEntry 5 }

hpnicfCBQoSRedirectRowStatus OBJECT-TYPE
    SYNTAX RowStatus
    MAX-ACCESS read-create
    STATUS current
    DESCRIPTION
        "RowStatus."
    ::= { hpnicfCBQoSRedirectCfgInfoEntry 6 }

hpnicfCBQoSRedirectIpv6Interface1 OBJECT-TYPE
    SYNTAX Integer32
    MAX-ACCESS read-create
    STATUS current
    DESCRIPTION
        "IfIndex for ipv6 next hop .
         If and only if the value of hpnicfCBQoSRedirectIpAddressType is ipv6
         and hpnicfCBQoSRedirectIpAddress1 is set,
         this node can be set.
        "
    DEFVAL { 0 }
    ::= { hpnicfCBQoSRedirectCfgInfoEntry 7 }

hpnicfCBQoSRedirectIpv6Interface2 OBJECT-TYPE
    SYNTAX Integer32
    MAX-ACCESS read-create
    STATUS current
    DESCRIPTION
        "IfIndex for ipv6 next hop .
         If and only if the value of hpnicfCBQoSRedirectIpAddressType is ipv6
         and hpnicfCBQoSRedirectIpAddress2 is set,
         this node can be set.
        "
    DEFVAL { 0 }
    ::= { hpnicfCBQoSRedirectCfgInfoEntry 8 }

hpnicfCBQoSRedirectIfVlanID OBJECT-TYPE
    SYNTAX Integer32 (0..4094 |65535)
    MAX-ACCESS read-create
    STATUS current
    DESCRIPTION
        "VLAN-ID to tag.
         If and only if the value of hpnicfCBQoSRedirectType is interface,
         this node can be set.
        "
    DEFVAL { 65535 }
    ::= { hpnicfCBQoSRedirectCfgInfoEntry 9 }

--
-- nodes of hpnicfCBQoSPriorityMapCfgInfoTable
--
hpnicfCBQoSPriorityMapCfgInfoTable OBJECT-TYPE
    SYNTAX SEQUENCE OF HpnicfCBQoSPriorityMapCfgInfoEntry
    MAX-ACCESS not-accessible
    STATUS current
    DESCRIPTION
        "A table of priority map configuration information."
    ::= { hpnicfCBQoSBehaviorObjects 16 }

hpnicfCBQoSPriorityMapCfgInfoEntry OBJECT-TYPE
    SYNTAX HpnicfCBQoSPriorityMapCfgInfoEntry
    MAX-ACCESS not-accessible
    STATUS current
    DESCRIPTION
        "priority map configuration information entry."
    INDEX { hpnicfCBQoSBehaviorIndex }
    ::= { hpnicfCBQoSPriorityMapCfgInfoTable 1 }

HpnicfCBQoSPriorityMapCfgInfoEntry ::=
    SEQUENCE
    {
        hpnicfCBQoSPriorityMapImportType
            INTEGER,
        hpnicfCBQoSPriorityMapExportType
            INTEGER,
        hpnicfCBQoSPriorityMapGroupIndex
            Integer32,
        hpnicfCBQoSPriorityMapGroupName
            OCTET STRING,
        hpnicfCBQoSPriorityMapAuto
            INTEGER,
        hpnicfCBQoSPriorityMapRowStatus
            RowStatus
    }

hpnicfCBQoSPriorityMapImportType OBJECT-TYPE
    SYNTAX INTEGER
    {
        invalid(1),
        dscp(2),
        dot1p(3),
        exp(4),
        ipPrecedence(5),
        localPrecedence(6),
        dropPrecedence(7)
    }
    MAX-ACCESS read-create
    STATUS current
    DESCRIPTION
        "Import type of map."
    DEFVAL { invalid }
    ::= { hpnicfCBQoSPriorityMapCfgInfoEntry 1 }

hpnicfCBQoSPriorityMapExportType OBJECT-TYPE
    SYNTAX INTEGER
    {
        invalid(1),
        dscp(2),
        dot1p(3),
        exp(4),
        ipPrecedence(5),
        localPrecedence(6),
        dropPrecedence(7)
    }
    MAX-ACCESS read-create
    STATUS current
    DESCRIPTION
        "Export type of map."
    DEFVAL { invalid }
    ::= { hpnicfCBQoSPriorityMapCfgInfoEntry 2 }

hpnicfCBQoSPriorityMapGroupIndex OBJECT-TYPE
    SYNTAX Integer32
    MAX-ACCESS read-create
    STATUS current
    DESCRIPTION
        "Index of map group.
         Map group is managed by HPN-ICF-IFQOS2-MIB.
        "
    ::= { hpnicfCBQoSPriorityMapCfgInfoEntry 3 }

hpnicfCBQoSPriorityMapGroupName OBJECT-TYPE
    SYNTAX OCTET STRING (SIZE(0..31))
    MAX-ACCESS read-only
    STATUS current
    DESCRIPTION
        "Name of map group.
         Map group is managed by HPN-ICF-IFQOS2-MIB.
        "
    ::= { hpnicfCBQoSPriorityMapCfgInfoEntry 4 }

hpnicfCBQoSPriorityMapAuto OBJECT-TYPE
    SYNTAX INTEGER
    {
        invalid(1),
        autoDscp(2),
        autoDot1p(3),
        autoMplsExp(4),
        autoIp(5)
    }
    MAX-ACCESS read-create
    STATUS current
    DESCRIPTION
        "Type of priority MAP."
    DEFVAL { invalid }
    ::= { hpnicfCBQoSPriorityMapCfgInfoEntry 5 }

hpnicfCBQoSPriorityMapRowStatus OBJECT-TYPE
    SYNTAX RowStatus
    MAX-ACCESS read-create
    STATUS current
    DESCRIPTION
        "RowStatus."
    ::= { hpnicfCBQoSPriorityMapCfgInfoEntry 6 }

--
-- nodes of hpnicfCBQoSMirrorCfgInfoTable
--
hpnicfCBQoSMirrorCfgInfoTable OBJECT-TYPE
    SYNTAX SEQUENCE OF HpnicfCBQoSMirrorCfgInfoEntry
    MAX-ACCESS not-accessible
    STATUS current
    DESCRIPTION
        "A table of flow mirror configuration information."
    ::= { hpnicfCBQoSBehaviorObjects 17 }

hpnicfCBQoSMirrorCfgInfoEntry OBJECT-TYPE
    SYNTAX HpnicfCBQoSMirrorCfgInfoEntry
    MAX-ACCESS not-accessible
    STATUS current
    DESCRIPTION
        "Flow mirror configuration information entry."
    INDEX { hpnicfCBQoSBehaviorIndex }
    ::= { hpnicfCBQoSMirrorCfgInfoTable 1 }

HpnicfCBQoSMirrorCfgInfoEntry ::=
    SEQUENCE
    {
        hpnicfCBQoSMirrorType
            INTEGER,
        hpnicfCBQoSMirrorIfIndex
            OCTET STRING,
        hpnicfCBQoSMirrorVlanID
            Integer32,
        hpnicfCBQoSMirrorRowStatus
            RowStatus
    }

hpnicfCBQoSMirrorType OBJECT-TYPE
    SYNTAX INTEGER
    {
        interface(1),
        cpu(2),
        vlan(3)
    }
    MAX-ACCESS read-create
    STATUS current
    DESCRIPTION
        "Type of flow mirror."
    ::= { hpnicfCBQoSMirrorCfgInfoEntry 1 }

hpnicfCBQoSMirrorIfIndex OBJECT-TYPE
    SYNTAX OCTET STRING (SIZE (0..255))
    MAX-ACCESS read-create
    STATUS current
    DESCRIPTION
        "IfIndex of destination interface.
         Only the value of hpnicfCBQoSMirrorType is interface,
         can be set this node.
         For example: 1#11#111#1111 means the flow mirror
         destination ifindex is 1,11,111 and 1111.
         '#' is list separator for all IfIndex value.
        "
    ::= { hpnicfCBQoSMirrorCfgInfoEntry 2 }

hpnicfCBQoSMirrorVlanID OBJECT-TYPE
    SYNTAX Integer32 (0..4094)
    MAX-ACCESS read-create
    STATUS current
    DESCRIPTION
        "Destination vlan of flow mirror,
         Only the value of hpnicfCBQoSMirrorType is vlan,
         can be set this node.
        "
    ::= { hpnicfCBQoSMirrorCfgInfoEntry 3 }

hpnicfCBQoSMirrorRowStatus OBJECT-TYPE
    SYNTAX RowStatus
    MAX-ACCESS read-create
    STATUS current
    DESCRIPTION
        "RowStatus."
    ::= { hpnicfCBQoSMirrorCfgInfoEntry 4 }

--
-- nodes of hpnicfCBQoSNestCfgInfoTable
--
hpnicfCBQoSNestCfgInfoTable OBJECT-TYPE
    SYNTAX SEQUENCE OF HpnicfCBQoSNestCfgInfoEntry
    MAX-ACCESS not-accessible
    STATUS current
    DESCRIPTION
        "Insert a service VLAN tag or customer VLAN tag into a packet.
        A VLAN tag contains the VLAN ID field and the 802.1p priority
        field.  Both the service VLAN ID and the customer VLAN ID can
        not be set at the same time.  One of them must be set.  The
        802.1p priority of the service VLAN tag and that of the
        customer VLAN tag can be set optionally.  However, both of
        them can not be set at the same time.  The new setting
        overwrites the previous one."
    ::= { hpnicfCBQoSBehaviorObjects 18 }

hpnicfCBQoSNestCfgInfoEntry OBJECT-TYPE
    SYNTAX HpnicfCBQoSNestCfgInfoEntry
    MAX-ACCESS not-accessible
    STATUS current
    DESCRIPTION
        "VLAN nesting table entry."
    INDEX { hpnicfCBQoSBehaviorIndex }
    ::= { hpnicfCBQoSNestCfgInfoTable 1 }

HpnicfCBQoSNestCfgInfoEntry ::=
    SEQUENCE
    {
        hpnicfCBQoSNestServiceVlanID
            Integer32,
        hpnicfCBQoSNestServiceDot1pValue
            Integer32,
        hpnicfCBQoSNestCustomerVlanID
            Integer32,
        hpnicfCBQoSNestCustomerDot1pValue
            Integer32,
        hpnicfCBQoSNestRowStatus
            RowStatus
    }

hpnicfCBQoSNestServiceVlanID OBJECT-TYPE
    SYNTAX Integer32 (1..4094|65535)
    MAX-ACCESS read-create
    STATUS current
    DESCRIPTION
        "VLAN ID of the service VLAN tag to be inserted.  If the
        customer VLAN tag has been configured, 65535 is returned
        for the service VLAN ID.  The service VLAN ID can not be
        set to 65535."
    ::= { hpnicfCBQoSNestCfgInfoEntry 1 }

hpnicfCBQoSNestServiceDot1pValue OBJECT-TYPE
    SYNTAX Integer32 (0..7|65535)
    MAX-ACCESS read-create
    STATUS current
    DESCRIPTION
        "802.1p priority value in the service VLAN tag to be inserted.
        If the 802.1p priority is not set, 65535 is returned.  The
        802.1p priority value can not be set to 65535."
    ::= { hpnicfCBQoSNestCfgInfoEntry 2 }

hpnicfCBQoSNestCustomerVlanID OBJECT-TYPE
    SYNTAX Integer32 (1..4094|65535)
    MAX-ACCESS read-create
    STATUS current
    DESCRIPTION
        "VLAN ID of the customer VLAN tag to be inserted.  If the
        service VLAN tag has been configured, 65535 is returned for
        the customer VLAN ID.  The customer VLAN ID can not be set
        to 65535."
    ::= { hpnicfCBQoSNestCfgInfoEntry 3 }

hpnicfCBQoSNestCustomerDot1pValue OBJECT-TYPE
    SYNTAX Integer32 (0..7|65535)
    MAX-ACCESS read-create
    STATUS current
    DESCRIPTION
        "802.1p priority value in the customer VLAN tag to be inserted.
        If the 802.1p priority is not set, 65535 is returned.  The
        802.1p priority value can not be set to 65535."
    ::= { hpnicfCBQoSNestCfgInfoEntry 4 }

hpnicfCBQoSNestRowStatus OBJECT-TYPE
    SYNTAX RowStatus
    MAX-ACCESS read-create
    STATUS current
    DESCRIPTION
        "RowStatus"
    ::= { hpnicfCBQoSNestCfgInfoEntry 5 }

-- Nest Policy

hpnicfCBQoSNestPolicyCfgInfoTable OBJECT-TYPE
    SYNTAX SEQUENCE OF HpnicfCBQoSNestPolicyCfgInfoEntry
    MAX-ACCESS not-accessible
    STATUS current
    DESCRIPTION
        "This table is used for configuring nest policy."
    ::= { hpnicfCBQoSBehaviorObjects 19 }

hpnicfCBQoSNestPolicyCfgInfoEntry OBJECT-TYPE
    SYNTAX HpnicfCBQoSNestPolicyCfgInfoEntry
    MAX-ACCESS not-accessible
    STATUS current
    DESCRIPTION
        "Nest policy configuration entry."
    INDEX { hpnicfCBQoSBehaviorIndex }
    ::= { hpnicfCBQoSNestPolicyCfgInfoTable 1 }

HpnicfCBQoSNestPolicyCfgInfoEntry ::=
    SEQUENCE
    {
        hpnicfCBQoSNestPolicyName
            OCTET STRING,
        hpnicfCBQoSNestPolicyRowStatus
            RowStatus
    }

hpnicfCBQoSNestPolicyName OBJECT-TYPE
    SYNTAX OCTET STRING (SIZE(1..31))
    MAX-ACCESS read-create
    STATUS current
    DESCRIPTION
        "Name of the nested policy."
    ::= { hpnicfCBQoSNestPolicyCfgInfoEntry 1 }

hpnicfCBQoSNestPolicyRowStatus OBJECT-TYPE
    SYNTAX RowStatus
    MAX-ACCESS read-create
    STATUS current
    DESCRIPTION
        "RowStatus"
    ::= { hpnicfCBQoSNestPolicyCfgInfoEntry 2 }

--
-- nodes of hpnicfCBQoSMirrorIfCfgInfoTable
--
hpnicfCBQoSMirrorIfCfgInfoTable OBJECT-TYPE
    SYNTAX SEQUENCE OF HpnicfCBQoSMirrorIfCfgInfoEntry
    MAX-ACCESS not-accessible
    STATUS current
    DESCRIPTION
        "A table of flow mirroring to interface configuration information."
    ::= { hpnicfCBQoSBehaviorObjects 20 }

hpnicfCBQoSMirrorIfCfgInfoEntry OBJECT-TYPE
    SYNTAX HpnicfCBQoSMirrorIfCfgInfoEntry
    MAX-ACCESS not-accessible
    STATUS current
    DESCRIPTION
        "Flow mirroring to interface configuration information entry."
    INDEX { hpnicfCBQoSBehaviorIndex, hpnicfCBQoSMirrorIfMainIfIndex }
    ::= { hpnicfCBQoSMirrorIfCfgInfoTable 1 }

HpnicfCBQoSMirrorIfCfgInfoEntry ::=
    SEQUENCE
    {
        hpnicfCBQoSMirrorIfMainIfIndex
            Integer32,
        hpnicfCBQoSMirrorIfMainIfStatus
            INTEGER,
        hpnicfCBQoSMirrorIfBackupIfIndex
            Integer32,
        hpnicfCBQoSMirrorIfBackupIfStatus
            INTEGER,
        hpnicfCBQoSMirrorIfRowStatus
            RowStatus
    }

hpnicfCBQoSMirrorIfMainIfIndex OBJECT-TYPE
    SYNTAX Integer32
    MAX-ACCESS not-accessible
    STATUS current
    DESCRIPTION
        "IfIndex of mirror interface."
    ::= { hpnicfCBQoSMirrorIfCfgInfoEntry 1 }

hpnicfCBQoSMirrorIfMainIfStatus OBJECT-TYPE
    SYNTAX INTEGER
    {
        inactive(1),
        active(2)
    }
    MAX-ACCESS read-only
    STATUS current
    DESCRIPTION
        "Status of main interface."
    DEFVAL {active}
    ::= { hpnicfCBQoSMirrorIfCfgInfoEntry 2 }

hpnicfCBQoSMirrorIfBackupIfIndex OBJECT-TYPE
    SYNTAX Integer32
    MAX-ACCESS read-create
    STATUS current
    DESCRIPTION
        "IfIndex of backup mirror interface."
    ::= { hpnicfCBQoSMirrorIfCfgInfoEntry 3 }

hpnicfCBQoSMirrorIfBackupIfStatus OBJECT-TYPE
    SYNTAX INTEGER
    {
        inactive(1),
        active(2)
    }
    MAX-ACCESS read-only
    STATUS current
    DESCRIPTION
        "Status of backup interface."
    DEFVAL {active}
    ::= { hpnicfCBQoSMirrorIfCfgInfoEntry 4 }

hpnicfCBQoSMirrorIfRowStatus OBJECT-TYPE
    SYNTAX RowStatus
    MAX-ACCESS read-create
    STATUS current
    DESCRIPTION
        "RowStatus."
    ::= { hpnicfCBQoSMirrorIfCfgInfoEntry 5 }

--
-- nodes of hpnicfCBQoSColoredRemarkCfgTable
--
hpnicfCBQoSColoredRemarkCfgTable OBJECT-TYPE
    SYNTAX SEQUENCE OF HpnicfCBQoSColoredRemarkCfgEntry
    MAX-ACCESS not-accessible
    STATUS current
    DESCRIPTION
        "A table of colored remarking feature configuration information."
    ::= { hpnicfCBQoSBehaviorObjects 21 }

hpnicfCBQoSColoredRemarkCfgEntry OBJECT-TYPE
    SYNTAX HpnicfCBQoSColoredRemarkCfgEntry
    MAX-ACCESS not-accessible
    STATUS current
    DESCRIPTION
        "Colored remarking configuration information entry."
    INDEX { hpnicfCBQoSBehaviorIndex, hpnicfCBQoSColoredRemarkType, hpnicfCBQoSColoredRemarkColor }
    ::= { hpnicfCBQoSColoredRemarkCfgTable 1 }

HpnicfCBQoSColoredRemarkCfgEntry ::=
    SEQUENCE
    {
        hpnicfCBQoSColoredRemarkType
            RemarkType,
        hpnicfCBQoSColoredRemarkColor
            INTEGER,
        hpnicfCBQoSColoredRemarkValue
            Integer32,
        hpnicfCBQoSColoredRemarkRowStatus
            RowStatus
    }

hpnicfCBQoSColoredRemarkType OBJECT-TYPE
    SYNTAX RemarkType
    MAX-ACCESS not-accessible
    STATUS current
    DESCRIPTION
        "Remark type."
    ::= { hpnicfCBQoSColoredRemarkCfgEntry 1 }

hpnicfCBQoSColoredRemarkColor OBJECT-TYPE
    SYNTAX INTEGER
    {
        green(1),
        yellow(2),
        red(3)
    }
    MAX-ACCESS not-accessible
    STATUS current
    DESCRIPTION
        "Remark color."
    ::= { hpnicfCBQoSColoredRemarkCfgEntry 2 }

hpnicfCBQoSColoredRemarkValue OBJECT-TYPE
    SYNTAX Integer32 (0..4095)
    MAX-ACCESS read-create
    STATUS current
    DESCRIPTION
        "Value to remark:
         for IpPrecedence: 0~7
         for Dscp: 0~63
         for MplsExp: 0~7
         for Vlan8021p: 0~7
         for AtmClp: 0~1
         for FrDe: 0~1
         for VlanID: 1~4094
         for QosLocalID: 1~4095
         for DropPrecedence: 0~2
         for LocalPrecedence: 0~7
         for TopMostVlanID: 1~4094
         for SecondMplsExp: 0~7
        "
    ::= { hpnicfCBQoSColoredRemarkCfgEntry 3 }

hpnicfCBQoSColoredRemarkRowStatus OBJECT-TYPE
    SYNTAX RowStatus
    MAX-ACCESS read-create
    STATUS current
    DESCRIPTION
        "RowStatus"
    ::= { hpnicfCBQoSColoredRemarkCfgEntry 4 }

--
-- nodes of hpnicfCBQoSPrimapCfgInfoTable
--
hpnicfCBQoSPrimapCfgInfoTable OBJECT-TYPE
    SYNTAX SEQUENCE OF HpnicfCBQoSPrimapCfgInfoEntry
    MAX-ACCESS not-accessible
    STATUS current
    DESCRIPTION
        "A table of referencing priority map configuration information."
    ::= { hpnicfCBQoSBehaviorObjects 22 }

hpnicfCBQoSPrimapCfgInfoEntry OBJECT-TYPE
    SYNTAX HpnicfCBQoSPrimapCfgInfoEntry
    MAX-ACCESS not-accessible
    STATUS current
    DESCRIPTION
        "Referencing priority map configuration information entry."
    INDEX { hpnicfCBQoSBehaviorIndex, hpnicfCBQoSPrimapColorType, hpnicfCBQoSPrePriMapTableType }
    ::= { hpnicfCBQoSPrimapCfgInfoTable 1 }

HpnicfCBQoSPrimapCfgInfoEntry ::=
    SEQUENCE
    {
        hpnicfCBQoSPrimapColorType
            INTEGER,
        hpnicfCBQoSPrePriMapTableType
            INTEGER,
        hpnicfCBQoSPrimapRowStatus
            RowStatus
    }

hpnicfCBQoSPrimapColorType OBJECT-TYPE
    SYNTAX INTEGER
    {
        noColorMap(1),
        colorMap(2)
    }
    MAX-ACCESS not-accessible
    STATUS current
    DESCRIPTION
        "Color type of priority map."
    ::= { hpnicfCBQoSPrimapCfgInfoEntry 1 }

hpnicfCBQoSPrePriMapTableType OBJECT-TYPE
    SYNTAX INTEGER
    {
        dot1pToLp(1),
        dot1pToDp(2),
        expToLp(3),
        dscpToLp(4),
        expToDp(5),
        dscpToDp(6),
        dscpToDot1p(7),
        dot1pToDscp(8),
        dscpToDscp(9),
        dscpToExp(10),
        expToDscp(11),
        expToDot1p(12),
        expToExp(13),
        lpToDot1p(14),
        dot1pToRpr(15),
        dscpToRpr(16),
        expToRpr(17),
        ippreToRpr(18),
        upToDot1p(19),
        upToDscp(20),
        upToExp(21),
        upToDp(22),
        upToLp(23),
        upToRpr(24),
        upToFc(25),
        lpTodscp(26),
        dot11eToLp(27),
        lpToDot11e(28),
        lpToLp(29),
        dot1pToExp(30),
        lpToExp(31),
        lpToDp(32),
        upToUp(33),
        dot1pToDot1p(34)
    }
    MAX-ACCESS not-accessible
    STATUS current
    DESCRIPTION
        "The type of pre-defined priority mapping table."
    ::= { hpnicfCBQoSPrimapCfgInfoEntry 2 }

hpnicfCBQoSPrimapRowStatus OBJECT-TYPE
    SYNTAX RowStatus
    MAX-ACCESS read-create
    STATUS current
    DESCRIPTION
        "RowStatus"
    ::= { hpnicfCBQoSPrimapCfgInfoEntry 3 }

--
-- nodes of hpnicfCBQoSColorMapDpCfgInfoTable
--
hpnicfCBQoSColorMapDpCfgInfoTable OBJECT-TYPE
    SYNTAX SEQUENCE OF HpnicfCBQoSColorMapDpCfgInfoEntry
    MAX-ACCESS not-accessible
    STATUS current
    DESCRIPTION
        "A table of referencing color-map-DP action configuration information."
    ::= { hpnicfCBQoSBehaviorObjects 23 }

hpnicfCBQoSColorMapDpCfgInfoEntry OBJECT-TYPE
    SYNTAX HpnicfCBQoSColorMapDpCfgInfoEntry
    MAX-ACCESS not-accessible
    STATUS current
    DESCRIPTION
        "Referencing color-map-DP action configuration information entry."
    INDEX { hpnicfCBQoSBehaviorIndex }
    ::= { hpnicfCBQoSColorMapDpCfgInfoTable 1 }

HpnicfCBQoSColorMapDpCfgInfoEntry ::=
    SEQUENCE
    {
        hpnicfCBQoSColorMapDpEnable
            TruthValue,
        hpnicfCBQoSColorMapDpRowStatus
            RowStatus
    }

hpnicfCBQoSColorMapDpEnable OBJECT-TYPE
    SYNTAX TruthValue
    MAX-ACCESS read-create
    STATUS current
    DESCRIPTION
        "Color-map-DP enable status."
    ::= { hpnicfCBQoSColorMapDpCfgInfoEntry 1 }

hpnicfCBQoSColorMapDpRowStatus OBJECT-TYPE
    SYNTAX RowStatus
    MAX-ACCESS read-create
    STATUS current
    DESCRIPTION
        "RowStatus"
    ::= { hpnicfCBQoSColorMapDpCfgInfoEntry 2 }

-- hpnicfCBQoSPolicyObjects

hpnicfCBQoSPolicyObjects OBJECT IDENTIFIER ::= { hpnicfCBQoSObjects 3 }

-- Traffic Policy Next Index

hpnicfCBQoSPolicyIndexNext OBJECT-TYPE
    SYNTAX Integer32
    MAX-ACCESS read-only
    STATUS current
    DESCRIPTION
        "This object contains an appropriate value to be used for
         hpnicfCBQoSPolicyIndex when creating rows in the
         hpnicfCBQoSPolicyCfgInfoTable."
    ::= { hpnicfCBQoSPolicyObjects 1 }

-- Traffic Policy

hpnicfCBQoSPolicyCfgInfoTable OBJECT-TYPE
    SYNTAX SEQUENCE OF HpnicfCBQoSPolicyCfgInfoEntry
    MAX-ACCESS not-accessible
    STATUS current
    DESCRIPTION
        "A table of QoS policy configuration information."
    ::= { hpnicfCBQoSPolicyObjects 2 }

hpnicfCBQoSPolicyCfgInfoEntry OBJECT-TYPE
    SYNTAX HpnicfCBQoSPolicyCfgInfoEntry
    MAX-ACCESS not-accessible
    STATUS current
    DESCRIPTION
        "Traffic policy configuration information entry."
    INDEX { hpnicfCBQoSPolicyIndex }
    ::= { hpnicfCBQoSPolicyCfgInfoTable 1 }

HpnicfCBQoSPolicyCfgInfoEntry ::=
    SEQUENCE
    {
        hpnicfCBQoSPolicyIndex
            Integer32,
        hpnicfCBQoSPolicyName
            OCTET STRING,
        hpnicfCBQoSPolicyClassCount
            Integer32,
        hpnicfCBQoSPolicyConfigMode
            INTEGER,
        hpnicfCBQoSPolicyType
            INTEGER,
        hpnicfCBQoSPolicyClassNextIndex
            Integer32,
        hpnicfCBQoSPolicyRowStatus
            RowStatus
    }

hpnicfCBQoSPolicyIndex OBJECT-TYPE
    SYNTAX Integer32
    MAX-ACCESS not-accessible
    STATUS current
    DESCRIPTION
        "Index of Traffic Policy."
    ::= { hpnicfCBQoSPolicyCfgInfoEntry 1 }

hpnicfCBQoSPolicyName OBJECT-TYPE
    SYNTAX OCTET STRING (SIZE (1..31))
    MAX-ACCESS read-create
    STATUS current
    DESCRIPTION
        "Name of Traffic Policy."
    ::= { hpnicfCBQoSPolicyCfgInfoEntry 2 }

hpnicfCBQoSPolicyClassCount OBJECT-TYPE
    SYNTAX Integer32
    MAX-ACCESS read-only
    STATUS current
    DESCRIPTION
        "The counter of policy classes of policy."
    ::= { hpnicfCBQoSPolicyCfgInfoEntry 3 }

hpnicfCBQoSPolicyConfigMode OBJECT-TYPE
    SYNTAX INTEGER
    {
        unavailable(0),
        config(1),
        auto(2)
    }
    MAX-ACCESS read-create
    STATUS current
    DESCRIPTION
        "Configuration mode of Traffic Policy.
         Only hardware QoS support this node.
         'unavailable' is returned only when getting value from software QoS.
         'unavailable' can't be set."
    DEFVAL {config}
    ::= { hpnicfCBQoSPolicyCfgInfoEntry 4 }

hpnicfCBQoSPolicyType OBJECT-TYPE
    SYNTAX INTEGER
    {
        systemDefined(1),
        userDefined(2)
    }
    MAX-ACCESS read-only
    STATUS current
    DESCRIPTION
        "Type of policy."
    ::= { hpnicfCBQoSPolicyCfgInfoEntry 5 }

hpnicfCBQoSPolicyClassNextIndex OBJECT-TYPE
    SYNTAX Integer32
    MAX-ACCESS read-only
    STATUS current
    DESCRIPTION
        "This object contains an appropriate value to be used for
         hpnicfCBQoSPolicyClassIndex when creating rows in the
         hpnicfCBQoSPolicyClassCfgInfoTable.
        "
    ::= { hpnicfCBQoSPolicyCfgInfoEntry 6 }

hpnicfCBQoSPolicyRowStatus OBJECT-TYPE
    SYNTAX RowStatus
    MAX-ACCESS read-create
    STATUS current
    DESCRIPTION
        "RowStatus."
    ::= { hpnicfCBQoSPolicyCfgInfoEntry 7 }

-- Classifier-Behavior in QoS policy

hpnicfCBQoSPolicyClassCfgInfoTable OBJECT-TYPE
    SYNTAX SEQUENCE OF HpnicfCBQoSPolicyClassCfgInfoEntry
    MAX-ACCESS not-accessible
    STATUS current
    DESCRIPTION
        "A table of QoS Policy classifier-behavior configuration information."
    ::= { hpnicfCBQoSPolicyObjects 3 }

hpnicfCBQoSPolicyClassCfgInfoEntry OBJECT-TYPE
    SYNTAX HpnicfCBQoSPolicyClassCfgInfoEntry
    MAX-ACCESS not-accessible
    STATUS current
    DESCRIPTION
        "Traffic policy classifier-behavior configuration information entry."
    INDEX { hpnicfCBQoSPolicyIndex, hpnicfCBQoSPolicyClassIndex }
    ::= { hpnicfCBQoSPolicyClassCfgInfoTable 1 }

HpnicfCBQoSPolicyClassCfgInfoEntry ::=
    SEQUENCE
    {
        hpnicfCBQoSPolicyClassIndex
            Integer32,
        hpnicfCBQoSPolicyClassClassifierIndex
            Integer32,
        hpnicfCBQoSPolicyClassClassifierName
            OCTET STRING,
        hpnicfCBQoSPolicyClassBehaviorIndex
            Integer32,
        hpnicfCBQoSPolicyClassBehaviorName
            OCTET STRING,
        hpnicfCBQoSPolicyClassPrecedence
            Integer32,
        hpnicfCBQoSPolicyClassRowStatus
            RowStatus,
        hpnicfCBQoSPolicyClassMode
            INTEGER,
        hpnicfCBQoSPolicyClassCfgOrder
            Integer32
    }

hpnicfCBQoSPolicyClassIndex OBJECT-TYPE
    SYNTAX Integer32
    MAX-ACCESS not-accessible
    STATUS current
    DESCRIPTION
        "PolicyClass Index in a QoS policy."
    ::= { hpnicfCBQoSPolicyClassCfgInfoEntry 1 }

hpnicfCBQoSPolicyClassClassifierIndex OBJECT-TYPE
    SYNTAX Integer32
    MAX-ACCESS read-create
    STATUS current
    DESCRIPTION
        "Index of classifier applied by a policy.
         It should exist in hpnicfCBQoSClassifierCfgInfoTable."
    ::= { hpnicfCBQoSPolicyClassCfgInfoEntry 2 }

hpnicfCBQoSPolicyClassClassifierName OBJECT-TYPE
    SYNTAX OCTET STRING (SIZE (1..31))
    MAX-ACCESS read-only
    STATUS current
    DESCRIPTION
        "Name of classifier applied by a policy.
         It is corresponding to hpnicfCBQoSPolicyClassClassifierIndex."
    ::= { hpnicfCBQoSPolicyClassCfgInfoEntry 3 }

hpnicfCBQoSPolicyClassBehaviorIndex OBJECT-TYPE
    SYNTAX Integer32
    MAX-ACCESS read-create
    STATUS current
    DESCRIPTION
        "Index of Behavior applied by a policy.
         It should exist in hpnicfCBQoSBehaviorCfgInfoTable."
    ::= { hpnicfCBQoSPolicyClassCfgInfoEntry 4 }

hpnicfCBQoSPolicyClassBehaviorName OBJECT-TYPE
    SYNTAX OCTET STRING (SIZE (1..31))
    MAX-ACCESS read-only
    STATUS current
    DESCRIPTION
        "Name of Behavior applied by a policy.
         It is corresponding to hpnicfCBQoSPolicyClassBehaviorIndex."
    ::= { hpnicfCBQoSPolicyClassCfgInfoEntry 5 }

hpnicfCBQoSPolicyClassPrecedence OBJECT-TYPE
    SYNTAX Integer32 (0..16383|2147483647)
    MAX-ACCESS read-create
    STATUS current
    DESCRIPTION
        "The Precedence of the class in the policy.
         Only hardware QoS support this node.
         2147483647 is returned only when getting value from software QoS.
         2147483647 can't be set."
    ::= { hpnicfCBQoSPolicyClassCfgInfoEntry 6 }

hpnicfCBQoSPolicyClassRowStatus OBJECT-TYPE
    SYNTAX RowStatus
    MAX-ACCESS read-create
    STATUS current
    DESCRIPTION
        "RowStatus."
    ::= { hpnicfCBQoSPolicyClassCfgInfoEntry 7 }

hpnicfCBQoSPolicyClassMode OBJECT-TYPE
    SYNTAX INTEGER
    {
        modeNo(1),
        modeDot1q(2),
        modeQppb(3),
        modeIpSourceGuard(4),
        modeVoiceVlan(5),
        modeDCBX(6)
    }
    MAX-ACCESS read-create
    STATUS current
    DESCRIPTION
        "Set the mode of the classifier-behavior association.  The
        default mode modeNo is a normal mode.
        modeDot1q indicates that the association is used for VLAN mapping.
        modeQppb indicates that the association is used for BGP routing policy.
        modeIpSourceGuard indicates that the association is used for packets
        undergo IP source guard.
        modeVoiceVlan indicates that the association is used for voice data
        packets.
        modeDCBX indicates that the association is used for DCBX.
        "
    DEFVAL {modeNo}
    ::= { hpnicfCBQoSPolicyClassCfgInfoEntry 8 }

hpnicfCBQoSPolicyClassCfgOrder OBJECT-TYPE
    SYNTAX Integer32
    MAX-ACCESS read-only
    STATUS current
    DESCRIPTION
        "A QoS policy contains multiple classifier-behavior
        associations.  A node indicates the configuration order of
        the corresponding classifier-behavior association."
    ::= { hpnicfCBQoSPolicyClassCfgInfoEntry 9 }

-- hpnicfCBQoSApplyPolicyObjects

hpnicfCBQoSApplyPolicyObjects OBJECT IDENTIFIER ::= { hpnicfCBQoSObjects 4 }

-- Policy Instance on interface Table

hpnicfCBQoSIfApplyPolicyTable OBJECT-TYPE
    SYNTAX SEQUENCE OF HpnicfCBQoSIfApplyPolicyEntry
    MAX-ACCESS not-accessible
    STATUS current
    DESCRIPTION
        "A table of QoS policy instance."
    ::= { hpnicfCBQoSApplyPolicyObjects 1 }

hpnicfCBQoSIfApplyPolicyEntry OBJECT-TYPE
    SYNTAX HpnicfCBQoSIfApplyPolicyEntry
    MAX-ACCESS not-accessible
    STATUS current
    DESCRIPTION
        "Policy applied on interface Configuration Information Entry."
    INDEX { hpnicfCBQoSIfApplyPolicyIfIndex, hpnicfCBQoSIfApplyPolicyDirection }
    ::= { hpnicfCBQoSIfApplyPolicyTable 1 }

HpnicfCBQoSIfApplyPolicyEntry ::=
    SEQUENCE
    {
        hpnicfCBQoSIfApplyPolicyIfIndex
            Integer32,
        hpnicfCBQoSIfApplyPolicyDirection
            DirectionType,
        hpnicfCBQoSIfApplyPolicyName
            OCTET STRING,
        hpnicfCBQoSIfApplyPolicyEnableDynamic
            INTEGER,
        hpnicfCBQoSIfApplyPolicyRowStatus
            RowStatus,
        hpnicfCBQoSIfApplyPolicyStatus
            INTEGER
    }

hpnicfCBQoSIfApplyPolicyIfIndex OBJECT-TYPE
    SYNTAX Integer32
    MAX-ACCESS accessible-for-notify
    STATUS current
    DESCRIPTION
        "Interface Index, equal to ifIndex."
    ::= { hpnicfCBQoSIfApplyPolicyEntry 1 }

hpnicfCBQoSIfApplyPolicyDirection OBJECT-TYPE
    SYNTAX DirectionType
    MAX-ACCESS accessible-for-notify
    STATUS current
    DESCRIPTION
        "Policy direction:
         inbound (1)
         outbound (2)
        "
    ::= { hpnicfCBQoSIfApplyPolicyEntry 2 }

hpnicfCBQoSIfApplyPolicyName OBJECT-TYPE
    SYNTAX OCTET STRING (SIZE (1..31))
    MAX-ACCESS read-create
    STATUS current
    DESCRIPTION
        "Name of Traffic Policy."
    ::= { hpnicfCBQoSIfApplyPolicyEntry 3 }

hpnicfCBQoSIfApplyPolicyEnableDynamic OBJECT-TYPE
    SYNTAX INTEGER
    {
        unavailable(1),
        true(2),
        false(3)
    }
    MAX-ACCESS read-create
    STATUS current
    DESCRIPTION
        "If the value of it is specified 'true',Enable dynamic qos policy.
         'unavailable' is returned if device don't support dynamic QoS.
         'unavailable' can't be set.
        "
    ::= { hpnicfCBQoSIfApplyPolicyEntry 4 }

hpnicfCBQoSIfApplyPolicyRowStatus OBJECT-TYPE
    SYNTAX RowStatus
    MAX-ACCESS read-create
    STATUS current
    DESCRIPTION
        "RowStatus."
    ::= { hpnicfCBQoSIfApplyPolicyEntry 5 }

hpnicfCBQoSIfApplyPolicyStatus OBJECT-TYPE
    SYNTAX INTEGER
    {
        proccessing(1),
        success(2),
        partialItemFailed(3)
    }
    MAX-ACCESS read-only
    STATUS current
    DESCRIPTION
        "Status of policy applied on interface."
    ::= { hpnicfCBQoSIfApplyPolicyEntry 6 }

-- Policy Instance on ATM PVC Table

hpnicfCBQoSAtmPvcApplyPolicyTable OBJECT-TYPE
    SYNTAX SEQUENCE OF HpnicfCBQoSAtmPvcApplyPolicyEntry
    MAX-ACCESS not-accessible
    STATUS current
    DESCRIPTION
        "A table of QoS policy instance."
    ::= { hpnicfCBQoSApplyPolicyObjects 2 }

hpnicfCBQoSAtmPvcApplyPolicyEntry OBJECT-TYPE
    SYNTAX HpnicfCBQoSAtmPvcApplyPolicyEntry
    MAX-ACCESS not-accessible
    STATUS current
    DESCRIPTION
        "Policy applied on ATM PVC Configuration Information Entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection }
    ::= { hpnicfCBQoSAtmPvcApplyPolicyTable 1 }

HpnicfCBQoSAtmPvcApplyPolicyEntry ::=
    SEQUENCE
    {
        hpnicfCBQoSAtmPvcApplyPolicyIfIndex
            Integer32,
        hpnicfCBQoSAtmPvcApplyPolicyVPI
            Integer32,
        hpnicfCBQoSAtmPvcApplyPolicyVCI
            Integer32,
        hpnicfCBQoSAtmPvcApplyPolicyDirection
            DirectionType,
        hpnicfCBQoSAtmPvcApplyPolicyName
            OCTET STRING,
        hpnicfCBQoSAtmPvcApplyPolicyRowStatus
            RowStatus
    }

hpnicfCBQoSAtmPvcApplyPolicyIfIndex OBJECT-TYPE
    SYNTAX Integer32
    MAX-ACCESS not-accessible
    STATUS current
    DESCRIPTION
        "ATM Interface Index, equal to ifIndex."
    ::= { hpnicfCBQoSAtmPvcApplyPolicyEntry 1 }

hpnicfCBQoSAtmPvcApplyPolicyVPI OBJECT-TYPE
    SYNTAX Integer32
    MAX-ACCESS not-accessible
    STATUS current
    DESCRIPTION
        "VPI value of ATM Interface."
    ::= { hpnicfCBQoSAtmPvcApplyPolicyEntry 2 }

hpnicfCBQoSAtmPvcApplyPolicyVCI OBJECT-TYPE
    SYNTAX Integer32
    MAX-ACCESS not-accessible
    STATUS current
    DESCRIPTION
        "VCI value of ATM Interface."
    ::= { hpnicfCBQoSAtmPvcApplyPolicyEntry 3 }

hpnicfCBQoSAtmPvcApplyPolicyDirection OBJECT-TYPE
    SYNTAX DirectionType
    MAX-ACCESS not-accessible
    STATUS current
    DESCRIPTION
        "Policy direction:
         inbound (1)
         outbound (2)"
    ::= { hpnicfCBQoSAtmPvcApplyPolicyEntry 4 }

hpnicfCBQoSAtmPvcApplyPolicyName OBJECT-TYPE
    SYNTAX OCTET STRING (SIZE (1..31))
    MAX-ACCESS read-create
    STATUS current
    DESCRIPTION
        "Name of Traffic Policy."
    ::= { hpnicfCBQoSAtmPvcApplyPolicyEntry 5 }

hpnicfCBQoSAtmPvcApplyPolicyRowStatus OBJECT-TYPE
    SYNTAX RowStatus
    MAX-ACCESS read-create
    STATUS current
    DESCRIPTION
        "RowStatus"
    ::= { hpnicfCBQoSAtmPvcApplyPolicyEntry 6 }

-- Policy Instance on VLAN Table

hpnicfCBQoSVlanApplyPolicyTable OBJECT-TYPE
    SYNTAX SEQUENCE OF HpnicfCBQoSVlanApplyPolicyEntry
    MAX-ACCESS not-accessible
    STATUS current
    DESCRIPTION
        "A table of QoS policy instance."
    ::= { hpnicfCBQoSApplyPolicyObjects 3 }

hpnicfCBQoSVlanApplyPolicyEntry OBJECT-TYPE
    SYNTAX HpnicfCBQoSVlanApplyPolicyEntry
    MAX-ACCESS not-accessible
    STATUS current
    DESCRIPTION
        "Policy applied on Ethernet VLAN Configuration Information Entry."
    INDEX { hpnicfCBQoSVlanApplyPolicyVlanid,
            hpnicfCBQoSVlanApplyPolicyDirection }
    ::= { hpnicfCBQoSVlanApplyPolicyTable 1 }

HpnicfCBQoSVlanApplyPolicyEntry ::=
    SEQUENCE
    {
        hpnicfCBQoSVlanApplyPolicyVlanid
            Integer32,
        hpnicfCBQoSVlanApplyPolicyDirection
            DirectionType,
        hpnicfCBQoSVlanApplyPolicyName
            OCTET STRING,
        hpnicfCBQoSVlanApplyPriority
            Integer32,
        hpnicfCBQoSVlanApplyPolicyRowStatus
            RowStatus,
        hpnicfCBQoSVlanApplyPolicyStatus
            INTEGER
    }

hpnicfCBQoSVlanApplyPolicyVlanid OBJECT-TYPE
    SYNTAX Integer32
    MAX-ACCESS accessible-for-notify
    STATUS current
    DESCRIPTION
        "Vlan of Ethernet Interface."
    ::= { hpnicfCBQoSVlanApplyPolicyEntry 1 }

hpnicfCBQoSVlanApplyPolicyDirection OBJECT-TYPE
    SYNTAX DirectionType
    MAX-ACCESS accessible-for-notify
    STATUS current
    DESCRIPTION
        "Policy direction:
         inbound (1)
         outbound (2)"
    ::= { hpnicfCBQoSVlanApplyPolicyEntry 2 }

hpnicfCBQoSVlanApplyPolicyName OBJECT-TYPE
    SYNTAX OCTET STRING (SIZE (0..31))
    MAX-ACCESS read-create
    STATUS current
    DESCRIPTION
        "Name of Traffic Policy."
    ::= { hpnicfCBQoSVlanApplyPolicyEntry 3 }

hpnicfCBQoSVlanApplyPriority OBJECT-TYPE
    SYNTAX Integer32 (0..4095)
    MAX-ACCESS read-create
    STATUS current
    DESCRIPTION
        "The priority of policy."
    ::= { hpnicfCBQoSVlanApplyPolicyEntry 4 }

hpnicfCBQoSVlanApplyPolicyRowStatus OBJECT-TYPE
    SYNTAX RowStatus
    MAX-ACCESS read-create
    STATUS current
    DESCRIPTION
        "RowStatus."
    ::= { hpnicfCBQoSVlanApplyPolicyEntry 5 }

hpnicfCBQoSVlanApplyPolicyStatus OBJECT-TYPE
    SYNTAX INTEGER
    {
        proccessing(1),
        success(2),
        partialItemFailed(3)
    }
    MAX-ACCESS read-only
    STATUS current
    DESCRIPTION
        "Status of policy applied on VLAN."
    ::= { hpnicfCBQoSVlanApplyPolicyEntry 6 }

-- Policy Instance on FR class Table

hpnicfCBQoSFrClassApplyPolicyTable OBJECT-TYPE
    SYNTAX SEQUENCE OF HpnicfCBQoSFrClassApplyPolicyEntry
    MAX-ACCESS not-accessible
    STATUS current
    DESCRIPTION
        "A table of QoS policy instance."
    ::= { hpnicfCBQoSApplyPolicyObjects 4 }

hpnicfCBQoSFrClassApplyPolicyEntry OBJECT-TYPE
    SYNTAX HpnicfCBQoSFrClassApplyPolicyEntry
    MAX-ACCESS not-accessible
    STATUS current
    DESCRIPTION
        "Policy applied on FR class Configuration Information Entry."
    INDEX { hpnicfCBQoSFrClassApplyPolicyFrClassName,
            hpnicfCBQoSFrClassApplyPolicyDirection }
    ::= { hpnicfCBQoSFrClassApplyPolicyTable 1 }

HpnicfCBQoSFrClassApplyPolicyEntry ::=
    SEQUENCE
    {
        hpnicfCBQoSFrClassApplyPolicyFrClassName
            OCTET STRING,
        hpnicfCBQoSFrClassApplyPolicyDirection
            DirectionType,
        hpnicfCBQoSFrClassApplyPolicyName
            OCTET STRING,
        hpnicfCBQoSFrClassApplyPolicyRowStatus
            RowStatus
    }

hpnicfCBQoSFrClassApplyPolicyFrClassName OBJECT-TYPE
    SYNTAX OCTET STRING (SIZE (1..31))
    MAX-ACCESS not-accessible
    STATUS current
    DESCRIPTION
        "The name of FR class."
    ::= { hpnicfCBQoSFrClassApplyPolicyEntry 1 }

hpnicfCBQoSFrClassApplyPolicyDirection OBJECT-TYPE
    SYNTAX DirectionType
    MAX-ACCESS not-accessible
    STATUS current
    DESCRIPTION
        "Policy direction:
         inbound (1)
         outbound (2)"
    ::= { hpnicfCBQoSFrClassApplyPolicyEntry 2 }

hpnicfCBQoSFrClassApplyPolicyName OBJECT-TYPE
    SYNTAX OCTET STRING (SIZE (1..31))
    MAX-ACCESS read-create
    STATUS current
    DESCRIPTION
        "Name of Traffic Policy."
    ::= { hpnicfCBQoSFrClassApplyPolicyEntry 3 }

hpnicfCBQoSFrClassApplyPolicyRowStatus OBJECT-TYPE
    SYNTAX RowStatus
    MAX-ACCESS read-create
    STATUS current
    DESCRIPTION
        "RowStatus."
    ::= { hpnicfCBQoSFrClassApplyPolicyEntry 4 }

-- Policy Instance on FR PVC Table

hpnicfCBQoSFrPvcApplyPolicyTable OBJECT-TYPE
    SYNTAX SEQUENCE OF HpnicfCBQoSFrPvcApplyPolicyEntry
    MAX-ACCESS not-accessible
    STATUS current
    DESCRIPTION
        "A table of QoS policy instance."
    ::= { hpnicfCBQoSApplyPolicyObjects 5 }

hpnicfCBQoSFrPvcApplyPolicyEntry OBJECT-TYPE
    SYNTAX HpnicfCBQoSFrPvcApplyPolicyEntry
    MAX-ACCESS not-accessible
    STATUS current
    DESCRIPTION
        "Policy applied on FR PVC Configuration Information Entry."
    INDEX { hpnicfCBQoSFrPvcApplyPolicyIfIndex,
            hpnicfCBQoSFrPvcApplyPolicyDlciNum,
            hpnicfCBQoSFrPvcApplyPolicyDirection }
    ::= { hpnicfCBQoSFrPvcApplyPolicyTable 1 }

HpnicfCBQoSFrPvcApplyPolicyEntry ::=
    SEQUENCE
    {
        hpnicfCBQoSFrPvcApplyPolicyIfIndex
            Integer32,
        hpnicfCBQoSFrPvcApplyPolicyDlciNum
            Integer32,
        hpnicfCBQoSFrPvcApplyPolicyDirection
            DirectionType,
        hpnicfCBQoSFrPvcApplyPolicyName
            OCTET STRING,
        hpnicfCBQoSFrPvcApplyPolicyRowStatus
            RowStatus
    }

hpnicfCBQoSFrPvcApplyPolicyIfIndex OBJECT-TYPE
    SYNTAX Integer32
    MAX-ACCESS not-accessible
    STATUS current
    DESCRIPTION
        "Fr Interface Index, equal to ifIndex."
    ::= { hpnicfCBQoSFrPvcApplyPolicyEntry 1 }

hpnicfCBQoSFrPvcApplyPolicyDlciNum OBJECT-TYPE
    SYNTAX Integer32 (16..1007)
    MAX-ACCESS not-accessible
    STATUS current
    DESCRIPTION
        "Fr DLCI number."
    ::= { hpnicfCBQoSFrPvcApplyPolicyEntry 2 }

hpnicfCBQoSFrPvcApplyPolicyDirection OBJECT-TYPE
    SYNTAX DirectionType
    MAX-ACCESS not-accessible
    STATUS current
    DESCRIPTION
        "Policy direction:
         inbound (1)
         outbound (2)"
    ::= { hpnicfCBQoSFrPvcApplyPolicyEntry 3 }

hpnicfCBQoSFrPvcApplyPolicyName OBJECT-TYPE
    SYNTAX OCTET STRING (SIZE (1..31))
    MAX-ACCESS read-only
    STATUS current
    DESCRIPTION
        "Name of Traffic Policy."
    ::= { hpnicfCBQoSFrPvcApplyPolicyEntry 4 }

hpnicfCBQoSFrPvcApplyPolicyRowStatus OBJECT-TYPE
    SYNTAX RowStatus
    MAX-ACCESS read-only
    STATUS current
    DESCRIPTION
        "RowStatus."
    ::= { hpnicfCBQoSFrPvcApplyPolicyEntry 5 }

-- Policy Instance on Global

hpnicfCBQoSGlobalApplyTable OBJECT-TYPE
    SYNTAX SEQUENCE OF HpnicfCBQoSGlobalApplyEntry
    MAX-ACCESS not-accessible
    STATUS current
    DESCRIPTION
        "A table of QoS policies applied globally.  A QoS policy
        applied globally takes effect on all ports of the device."
    ::= { hpnicfCBQoSApplyPolicyObjects 6 }

hpnicfCBQoSGlobalApplyEntry OBJECT-TYPE
    SYNTAX HpnicfCBQoSGlobalApplyEntry
    MAX-ACCESS not-accessible
    STATUS current
    DESCRIPTION
        "A global policy entry."
    INDEX { hpnicfCBQoSGlobalApplyDirection }
    ::= { hpnicfCBQoSGlobalApplyTable 1 }

HpnicfCBQoSGlobalApplyEntry ::=
    SEQUENCE
    {
        hpnicfCBQoSGlobalApplyDirection
            DirectionType,
        hpnicfCBQoSGlobalApplyName
            OCTET STRING,
        hpnicfCBQoSGlobalApplyRowStatus
            RowStatus,
        hpnicfCBQoSGlobalApplyStatus
            INTEGER
    }

hpnicfCBQoSGlobalApplyDirection OBJECT-TYPE
    SYNTAX DirectionType
    MAX-ACCESS not-accessible
    STATUS current
    DESCRIPTION
        "Policy direction:
         inbound (1)
         outbound (2)"
    ::= { hpnicfCBQoSGlobalApplyEntry 1 }

hpnicfCBQoSGlobalApplyName OBJECT-TYPE
    SYNTAX OCTET STRING (SIZE (1..31))
    MAX-ACCESS read-create
    STATUS current
    DESCRIPTION
        "Name of a global policy."
    ::= { hpnicfCBQoSGlobalApplyEntry 2 }

hpnicfCBQoSGlobalApplyRowStatus OBJECT-TYPE
    SYNTAX RowStatus
    MAX-ACCESS read-create
    STATUS current
    DESCRIPTION
        "RowStatus."
    ::= { hpnicfCBQoSGlobalApplyEntry 3 }

hpnicfCBQoSGlobalApplyStatus OBJECT-TYPE
    SYNTAX INTEGER
    {
        proccessing(1),
        success(2),
        partialItemFailed(3)
    }
    MAX-ACCESS read-only
    STATUS current
    DESCRIPTION
        "Status of policy applied globally."
    ::= { hpnicfCBQoSGlobalApplyEntry 4 }

-- Policy Instance on controlPlane

hpnicfCBQoSCpApplyPolicyTable OBJECT-TYPE
    SYNTAX SEQUENCE OF HpnicfCBQoSCpApplyPolicyEntry
    MAX-ACCESS not-accessible
    STATUS current
    DESCRIPTION
        "A table of QoS policies applied on control plane."
    ::= { hpnicfCBQoSApplyPolicyObjects 7 }

hpnicfCBQoSCpApplyPolicyEntry OBJECT-TYPE
    SYNTAX HpnicfCBQoSCpApplyPolicyEntry
    MAX-ACCESS not-accessible
    STATUS current
    DESCRIPTION
        "Policy applied on control plane configuration information entry."
    INDEX { hpnicfCBQoSCpApplyPolicyChassis,
            hpnicfCBQoSCpApplyPolicySlot,
            hpnicfCBQoSCpApplyPolicyDirection }
    ::= { hpnicfCBQoSCpApplyPolicyTable 1 }

HpnicfCBQoSCpApplyPolicyEntry ::=
    SEQUENCE
    {
        hpnicfCBQoSCpApplyPolicyChassis
            Unsigned32,
        hpnicfCBQoSCpApplyPolicySlot
            Unsigned32,
        hpnicfCBQoSCpApplyPolicyDirection
            DirectionType,
        hpnicfCBQoSCpApplyPolicyName
            OCTET STRING,
        hpnicfCBQoSCpApplyPolicyStatus
            INTEGER,
        hpnicfCBQoSCpApplyRowStatus
            RowStatus
    }

hpnicfCBQoSCpApplyPolicyChassis OBJECT-TYPE
    SYNTAX Unsigned32
    MAX-ACCESS not-accessible
    STATUS current
    DESCRIPTION
        "Chassis number."
    ::= { hpnicfCBQoSCpApplyPolicyEntry 1 }

hpnicfCBQoSCpApplyPolicySlot OBJECT-TYPE
    SYNTAX Unsigned32
    MAX-ACCESS not-accessible
    STATUS current
    DESCRIPTION
        "Slot number."
    ::= { hpnicfCBQoSCpApplyPolicyEntry 2 }

hpnicfCBQoSCpApplyPolicyDirection OBJECT-TYPE
    SYNTAX DirectionType
    MAX-ACCESS not-accessible
    STATUS current
    DESCRIPTION
        "Policy direction:
         inbound (1)
         outbound (2)"
    ::= { hpnicfCBQoSCpApplyPolicyEntry 3 }

hpnicfCBQoSCpApplyPolicyName OBJECT-TYPE
    SYNTAX OCTET STRING (SIZE (1..31))
    MAX-ACCESS read-create
    STATUS current
    DESCRIPTION
        "Name of traffic policy."
    ::= { hpnicfCBQoSCpApplyPolicyEntry 4 }

hpnicfCBQoSCpApplyPolicyStatus OBJECT-TYPE
    SYNTAX INTEGER
    {
        proccessing(1),
        success(2),
        partialItemFailed(3)
    }
    MAX-ACCESS read-only
    STATUS current
    DESCRIPTION
        "Status of policy applied on control plane."
    ::= { hpnicfCBQoSCpApplyPolicyEntry 5 }

hpnicfCBQoSCpApplyRowStatus OBJECT-TYPE
    SYNTAX RowStatus
    MAX-ACCESS read-create
    STATUS current
    DESCRIPTION
        "RowStatus."
    ::= { hpnicfCBQoSCpApplyPolicyEntry 6 }

-- Running statistics information

hpnicfCBQoSApplyPolicyStaticsObjects OBJECT IDENTIFIER ::= { hpnicfCBQoSObjects 5 }

-- Interface: policy Running statistics information

hpnicfCBQoSIfStaticsObjects OBJECT IDENTIFIER ::= { hpnicfCBQoSApplyPolicyStaticsObjects 1 }

-- Interface CBQ statistics

hpnicfCBQoSIfCbqRunInfoTable OBJECT-TYPE
    SYNTAX SEQUENCE OF HpnicfCBQoSIfCbqRunInfoEntry
    MAX-ACCESS not-accessible
    STATUS current
    DESCRIPTION
        "A table of interface CBQ Running statistics.
         When policy using queue behavior is applied on
         interface the interface will using Class Based Queuing."
    ::= { hpnicfCBQoSIfStaticsObjects 1 }

hpnicfCBQoSIfCbqRunInfoEntry OBJECT-TYPE
    SYNTAX HpnicfCBQoSIfCbqRunInfoEntry
    MAX-ACCESS not-accessible
    STATUS current
    DESCRIPTION
        "Interface CBQ statistics entry."
    INDEX { hpnicfCBQoSIfApplyPolicyIfIndex }
    ::= { hpnicfCBQoSIfCbqRunInfoTable 1 }

HpnicfCBQoSIfCbqRunInfoEntry ::=
    SEQUENCE
    {
        hpnicfCBQoSIfCbqQueueSize
            Integer32,
        hpnicfCBQoSIfCbqDiscard
            Counter64,
        hpnicfCBQoSIfCbqEfQueueSize
            Integer32,
        hpnicfCBQoSIfCbqAfQueueSize
            Integer32,
        hpnicfCBQoSIfCbqBeQueueSize
            Integer32,
        hpnicfCBQoSIfCbqBeActiveQueueNum
            Integer32,
        hpnicfCBQoSIfCbqBeMaxActiveQueueNum
            Integer32,
        hpnicfCBQoSIfCbqBeTotalQueueNum
            Integer32,
        hpnicfCBQoSIfCbqAfAllocatedQueueNum
            Integer32
    }

hpnicfCBQoSIfCbqQueueSize OBJECT-TYPE
    SYNTAX Integer32
    MAX-ACCESS read-only
    STATUS current
    DESCRIPTION
        "Packet number of CBQ queue"
    ::= { hpnicfCBQoSIfCbqRunInfoEntry 1 }

hpnicfCBQoSIfCbqDiscard OBJECT-TYPE
    SYNTAX Counter64
    MAX-ACCESS read-only
    STATUS current
    DESCRIPTION
        "The number of discarded packets which couldn't be enqueued."
    ::= { hpnicfCBQoSIfCbqRunInfoEntry 2 }

hpnicfCBQoSIfCbqEfQueueSize OBJECT-TYPE
    SYNTAX Integer32
    MAX-ACCESS read-only
    STATUS current
    DESCRIPTION
        "Packet number of EF queue."
    ::= { hpnicfCBQoSIfCbqRunInfoEntry 3 }

hpnicfCBQoSIfCbqAfQueueSize OBJECT-TYPE
    SYNTAX Integer32
    MAX-ACCESS read-only
    STATUS current
    DESCRIPTION
        "Packet number of AF queue."
    ::= { hpnicfCBQoSIfCbqRunInfoEntry 4 }

hpnicfCBQoSIfCbqBeQueueSize OBJECT-TYPE
    SYNTAX Integer32
    MAX-ACCESS read-only
    STATUS current
    DESCRIPTION
        "Packet number of BE queue."
    ::= { hpnicfCBQoSIfCbqRunInfoEntry 5 }

hpnicfCBQoSIfCbqBeActiveQueueNum OBJECT-TYPE
    SYNTAX Integer32
    MAX-ACCESS read-only
    STATUS current
    DESCRIPTION
        "The Packet number of Active BE Queue."
    ::= { hpnicfCBQoSIfCbqRunInfoEntry 6 }

hpnicfCBQoSIfCbqBeMaxActiveQueueNum OBJECT-TYPE
    SYNTAX Integer32
    MAX-ACCESS read-only
    STATUS current
    DESCRIPTION
        "The max Packet number of Active BE Queue."
    ::= { hpnicfCBQoSIfCbqRunInfoEntry 7 }

hpnicfCBQoSIfCbqBeTotalQueueNum OBJECT-TYPE
    SYNTAX Integer32
    MAX-ACCESS read-only
    STATUS current
    DESCRIPTION
        "The total Packet number of BE Queue."
    ::= { hpnicfCBQoSIfCbqRunInfoEntry 8 }

hpnicfCBQoSIfCbqAfAllocatedQueueNum OBJECT-TYPE
    SYNTAX Integer32
    MAX-ACCESS read-only
    STATUS current
    DESCRIPTION
        "The Allocated Packet number of AF Queue."
    ::= { hpnicfCBQoSIfCbqRunInfoEntry 9 }

-- Class match statistics

hpnicfCBQoSIfClassMatchRunInfoTable OBJECT-TYPE
    SYNTAX SEQUENCE OF HpnicfCBQoSIfClassMatchRunInfoEntry
    MAX-ACCESS not-accessible
    STATUS current
    DESCRIPTION
        "A table of Running statistics for matching a classifier
         in a QoS policy applied on the interface."
    ::= { hpnicfCBQoSIfStaticsObjects 2 }

hpnicfCBQoSIfClassMatchRunInfoEntry OBJECT-TYPE
    SYNTAX HpnicfCBQoSIfClassMatchRunInfoEntry
    MAX-ACCESS not-accessible
    STATUS current
    DESCRIPTION
        "Classifier's matching statistics information entry."
    INDEX { hpnicfCBQoSIfApplyPolicyIfIndex,
            hpnicfCBQoSIfApplyPolicyDirection,
            hpnicfCBQoSPolicyClassIndex }
    ::= { hpnicfCBQoSIfClassMatchRunInfoTable 1 }

HpnicfCBQoSIfClassMatchRunInfoEntry ::=
    SEQUENCE
    {
        hpnicfCBQoSIfClassMatchedPackets
            Counter64,
        hpnicfCBQoSIfClassMatchedBytes
            Counter64,
        hpnicfCBQoSIfClassAverageRate
            Counter64
    }

hpnicfCBQoSIfClassMatchedPackets OBJECT-TYPE
    SYNTAX Counter64
    MAX-ACCESS read-only
    STATUS current
    DESCRIPTION
        "Number of packets matching a class in a QoS policy."
    ::= { hpnicfCBQoSIfClassMatchRunInfoEntry 1 }

hpnicfCBQoSIfClassMatchedBytes OBJECT-TYPE
    SYNTAX Counter64
    MAX-ACCESS read-only
    STATUS current
    DESCRIPTION
        "Number of bytes matching a class in a QoS policy.
         Only software QoS support this node."
    ::= { hpnicfCBQoSIfClassMatchRunInfoEntry 2 }

hpnicfCBQoSIfClassAverageRate OBJECT-TYPE
    SYNTAX Counter64
    MAX-ACCESS read-only
    STATUS current
    DESCRIPTION
        "Average rate matching a class of the last 5 minutes."
    ::= { hpnicfCBQoSIfClassMatchRunInfoEntry 3 }

-- CAR statistics

hpnicfCBQoSIfCarRunInfoTable OBJECT-TYPE
    SYNTAX SEQUENCE OF HpnicfCBQoSIfCarRunInfoEntry
    MAX-ACCESS not-accessible
    STATUS current
    DESCRIPTION
        "A table of Running statistics for CAR
         in a QoS policy applied on the interface."
    ::= { hpnicfCBQoSIfStaticsObjects 3 }

hpnicfCBQoSIfCarRunInfoEntry OBJECT-TYPE
    SYNTAX HpnicfCBQoSIfCarRunInfoEntry
    MAX-ACCESS not-accessible
    STATUS current
    DESCRIPTION
        "CAR statistics information entry."
    INDEX { hpnicfCBQoSIfApplyPolicyIfIndex,
            hpnicfCBQoSIfApplyPolicyDirection,
            hpnicfCBQoSPolicyClassIndex }
    ::= { hpnicfCBQoSIfCarRunInfoTable 1 }

HpnicfCBQoSIfCarRunInfoEntry ::=
    SEQUENCE
    {
        hpnicfCBQoSIfCarGreenPackets
            Counter64,
        hpnicfCBQoSIfCarGreenBytes
            Counter64,
        hpnicfCBQoSIfCarRedPackets
            Counter64,
        hpnicfCBQoSIfCarRedBytes
            Counter64,
        hpnicfCBQoSIfCarYellowPackets
            Counter64,
        hpnicfCBQoSIfCarYellowBytes
            Counter64
    }

hpnicfCBQoSIfCarGreenPackets OBJECT-TYPE
    SYNTAX Counter64
    MAX-ACCESS read-only
    STATUS current
    DESCRIPTION
        "Number of green packets."
    ::= { hpnicfCBQoSIfCarRunInfoEntry 1 }

hpnicfCBQoSIfCarGreenBytes OBJECT-TYPE
    SYNTAX Counter64
    MAX-ACCESS read-only
    STATUS current
    DESCRIPTION
        "Number of green bytes."
    ::= { hpnicfCBQoSIfCarRunInfoEntry 2 }

hpnicfCBQoSIfCarRedPackets OBJECT-TYPE
    SYNTAX Counter64
    MAX-ACCESS read-only
    STATUS current
    DESCRIPTION
        "Number of red packets."
    ::= { hpnicfCBQoSIfCarRunInfoEntry 3 }

hpnicfCBQoSIfCarRedBytes OBJECT-TYPE
    SYNTAX Counter64
    MAX-ACCESS read-only
    STATUS current
    DESCRIPTION
        "Number of red bytes."
    ::= { hpnicfCBQoSIfCarRunInfoEntry 4 }

hpnicfCBQoSIfCarYellowPackets OBJECT-TYPE
    SYNTAX Counter64
    MAX-ACCESS read-only
    STATUS current
    DESCRIPTION
        "Number of yellow packets."
    ::= { hpnicfCBQoSIfCarRunInfoEntry 5 }

hpnicfCBQoSIfCarYellowBytes OBJECT-TYPE
    SYNTAX Counter64
    MAX-ACCESS read-only
    STATUS current
    DESCRIPTION
        "Number of yellow bytes."
    ::= { hpnicfCBQoSIfCarRunInfoEntry 6 }

-- GTS statistics

hpnicfCBQoSIfGtsRunInfoTable OBJECT-TYPE
    SYNTAX SEQUENCE OF HpnicfCBQoSIfGtsRunInfoEntry
    MAX-ACCESS not-accessible
    STATUS current
    DESCRIPTION
        "A table of Running statistics for GTS
         in a QoS policy applied on the interface."
    ::= { hpnicfCBQoSIfStaticsObjects 4 }

hpnicfCBQoSIfGtsRunInfoEntry OBJECT-TYPE
    SYNTAX HpnicfCBQoSIfGtsRunInfoEntry
    MAX-ACCESS not-accessible
    STATUS current
    DESCRIPTION
        "GTS statistics entry."
    INDEX { hpnicfCBQoSIfApplyPolicyIfIndex,
            hpnicfCBQoSIfApplyPolicyDirection,
            hpnicfCBQoSPolicyClassIndex }
    ::= { hpnicfCBQoSIfGtsRunInfoTable 1 }

HpnicfCBQoSIfGtsRunInfoEntry ::=
    SEQUENCE
    {
        hpnicfCBQoSIfGtsPassedPackets
            Counter64,
        hpnicfCBQoSIfGtsPassedBytes
            Counter64,
        hpnicfCBQoSIfGtsDiscardedPackets
            Counter64,
        hpnicfCBQoSIfGtsDiscardedBytes
            Counter64,
        hpnicfCBQoSIfGtsDelayedPackets
            Counter64,
        hpnicfCBQoSIfGtsDelayedBytes
            Counter64,
        hpnicfCBQoSIfGtsQueueSize
            Integer32
    }

hpnicfCBQoSIfGtsPassedPackets OBJECT-TYPE
    SYNTAX Counter64
    MAX-ACCESS read-only
    STATUS current
    DESCRIPTION
        "Number of packets passed by GTS."
    ::= { hpnicfCBQoSIfGtsRunInfoEntry 1 }

hpnicfCBQoSIfGtsPassedBytes OBJECT-TYPE
    SYNTAX Counter64
    MAX-ACCESS read-only
    STATUS current
    DESCRIPTION
        "Number of bytes passed by GTS."
    ::= { hpnicfCBQoSIfGtsRunInfoEntry 2 }

hpnicfCBQoSIfGtsDiscardedPackets OBJECT-TYPE
    SYNTAX Counter64
    MAX-ACCESS read-only
    STATUS current
    DESCRIPTION
        "Number of packets discarded by GTS."
    ::= { hpnicfCBQoSIfGtsRunInfoEntry 3 }

hpnicfCBQoSIfGtsDiscardedBytes OBJECT-TYPE
    SYNTAX Counter64
    MAX-ACCESS read-only
    STATUS current
    DESCRIPTION
        "Number of bytes discarded by GTS."
    ::= { hpnicfCBQoSIfGtsRunInfoEntry 4 }

hpnicfCBQoSIfGtsDelayedPackets OBJECT-TYPE
    SYNTAX Counter64
    MAX-ACCESS read-only
    STATUS current
    DESCRIPTION
        "Number of packets delayed by GTS."
    ::= { hpnicfCBQoSIfGtsRunInfoEntry 5 }

hpnicfCBQoSIfGtsDelayedBytes OBJECT-TYPE
    SYNTAX Counter64
    MAX-ACCESS read-only
    STATUS current
    DESCRIPTION
        "Number of bytes delayed by GTS."
    ::= { hpnicfCBQoSIfGtsRunInfoEntry 6 }

hpnicfCBQoSIfGtsQueueSize OBJECT-TYPE
    SYNTAX Integer32
    MAX-ACCESS read-only
    STATUS current
    DESCRIPTION
        "Packet number of GTS queue."
    ::= { hpnicfCBQoSIfGtsRunInfoEntry 7 }

-- Remark statistics

hpnicfCBQoSIfRemarkRunInfoTable OBJECT-TYPE
    SYNTAX SEQUENCE OF HpnicfCBQoSIfRemarkRunInfoEntry
    MAX-ACCESS not-accessible
    STATUS current
    DESCRIPTION
        "A table of Running statistics for remarking
         in a QoS policy applied on the interface."
    ::= { hpnicfCBQoSIfStaticsObjects 5 }

hpnicfCBQoSIfRemarkRunInfoEntry OBJECT-TYPE
    SYNTAX HpnicfCBQoSIfRemarkRunInfoEntry
    MAX-ACCESS not-accessible
    STATUS current
    DESCRIPTION
        "Remarking statistics entry."
    INDEX { hpnicfCBQoSIfApplyPolicyIfIndex,
            hpnicfCBQoSIfApplyPolicyDirection,
            hpnicfCBQoSPolicyClassIndex }
    ::= { hpnicfCBQoSIfRemarkRunInfoTable 1 }

HpnicfCBQoSIfRemarkRunInfoEntry ::=
    SEQUENCE
    {
        hpnicfCBQoSIfRemarkedPackets
            Counter64
    }

hpnicfCBQoSIfRemarkedPackets OBJECT-TYPE
    SYNTAX Counter64
    MAX-ACCESS read-only
    STATUS current
    DESCRIPTION
        "Number of packets remarked."
    ::= { hpnicfCBQoSIfRemarkRunInfoEntry 1 }

-- Queue statistics

hpnicfCBQoSIfQueueRunInfoTable OBJECT-TYPE
    SYNTAX SEQUENCE OF HpnicfCBQoSIfQueueRunInfoEntry
    MAX-ACCESS not-accessible
    STATUS current
    DESCRIPTION
        "A table of Running statistics for queue
         in a QoS policy applied on the interface."
    ::= { hpnicfCBQoSIfStaticsObjects 6 }

hpnicfCBQoSIfQueueRunInfoEntry OBJECT-TYPE
    SYNTAX HpnicfCBQoSIfQueueRunInfoEntry
    MAX-ACCESS not-accessible
    STATUS current
    DESCRIPTION
        "Queue statistics entry."
    INDEX { hpnicfCBQoSIfApplyPolicyIfIndex,
            hpnicfCBQoSIfApplyPolicyDirection,
            hpnicfCBQoSPolicyClassIndex }
    ::= { hpnicfCBQoSIfQueueRunInfoTable 1 }

HpnicfCBQoSIfQueueRunInfoEntry ::=
    SEQUENCE
    {
        hpnicfCBQoSIfQueueMatchedPackets
            Counter64,
        hpnicfCBQoSIfQueueMatchedBytes
            Counter64,
        hpnicfCBQoSIfQueueEnqueuedPackets
            Counter64,
        hpnicfCBQoSIfQueueEnqueuedBytes
            Counter64,
        hpnicfCBQoSIfQueueDiscardedPackets
            Counter64,
        hpnicfCBQoSIfQueueDiscardedBytes
            Counter64
    }

hpnicfCBQoSIfQueueMatchedPackets OBJECT-TYPE
    SYNTAX Counter64
    MAX-ACCESS read-only
    STATUS current
    DESCRIPTION
        "Number of packets matched to enqueue."
    ::= { hpnicfCBQoSIfQueueRunInfoEntry 1 }

hpnicfCBQoSIfQueueMatchedBytes OBJECT-TYPE
    SYNTAX Counter64
    MAX-ACCESS read-only
    STATUS current
    DESCRIPTION
        "Number of bytes matched to enqueue."
    ::= { hpnicfCBQoSIfQueueRunInfoEntry 2 }

hpnicfCBQoSIfQueueEnqueuedPackets OBJECT-TYPE
    SYNTAX Counter64
    MAX-ACCESS read-only
    STATUS current
    DESCRIPTION
        "Number of packets enqueued."
    ::= { hpnicfCBQoSIfQueueRunInfoEntry 3 }

hpnicfCBQoSIfQueueEnqueuedBytes OBJECT-TYPE
    SYNTAX Counter64
    MAX-ACCESS read-only
    STATUS current
    DESCRIPTION
        "Number of bytes enqueued."
    ::= { hpnicfCBQoSIfQueueRunInfoEntry 4 }

hpnicfCBQoSIfQueueDiscardedPackets OBJECT-TYPE
    SYNTAX Counter64
    MAX-ACCESS read-only
    STATUS current
    DESCRIPTION
        "Number of packets discarded when enqueued by discard method."
    ::= { hpnicfCBQoSIfQueueRunInfoEntry 5 }

hpnicfCBQoSIfQueueDiscardedBytes OBJECT-TYPE
    SYNTAX Counter64
    MAX-ACCESS read-only
    STATUS current
    DESCRIPTION
        "Number of bytes discarded when enqueued by discard method."
    ::= { hpnicfCBQoSIfQueueRunInfoEntry 6 }

-- WRED statistics

hpnicfCBQoSIfWredRunInfoTable OBJECT-TYPE
    SYNTAX SEQUENCE OF HpnicfCBQoSIfWredRunInfoEntry
    MAX-ACCESS not-accessible
    STATUS current
    DESCRIPTION
        "A table of Running statistics for WRED
         in a QoS policy applied on the interface."
    ::= { hpnicfCBQoSIfStaticsObjects 7 }

hpnicfCBQoSIfWredRunInfoEntry OBJECT-TYPE
    SYNTAX HpnicfCBQoSIfWredRunInfoEntry
    MAX-ACCESS not-accessible
    STATUS current
    DESCRIPTION
        "WRED statistics entry."
    INDEX { hpnicfCBQoSIfApplyPolicyIfIndex,
            hpnicfCBQoSIfApplyPolicyDirection,
            hpnicfCBQoSPolicyClassIndex,
            hpnicfCBQoSWredClassValue }
    ::= { hpnicfCBQoSIfWredRunInfoTable 1 }

HpnicfCBQoSIfWredRunInfoEntry ::=
    SEQUENCE
    {
        hpnicfCBQoSIfWredRandomDiscardedPackets
            Counter64,
        hpnicfCBQoSIfWredTailDiscardedPackets
            Counter64
    }

hpnicfCBQoSIfWredRandomDiscardedPackets OBJECT-TYPE
    SYNTAX Counter64
    MAX-ACCESS read-only
    STATUS current
    DESCRIPTION
        "Number of packets that random-discarded by WRED."
    ::= { hpnicfCBQoSIfWredRunInfoEntry 1 }

hpnicfCBQoSIfWredTailDiscardedPackets OBJECT-TYPE
    SYNTAX Counter64
    MAX-ACCESS read-only
    STATUS current
    DESCRIPTION
        "Number of packets that tail-discarded by WRED."
    ::= { hpnicfCBQoSIfWredRunInfoEntry 2 }

--
-- nodes of hpnicfCBQoSIfAccountingRunInfoTable
--
hpnicfCBQoSIfAccountingRunInfoTable OBJECT-TYPE
    SYNTAX SEQUENCE OF HpnicfCBQoSIfAccountingRunInfoEntry
    MAX-ACCESS not-accessible
    STATUS current
    DESCRIPTION
        "A table of Running statistics for account
         in a QoS policy applied on the interface."
    ::= { hpnicfCBQoSIfStaticsObjects 8 }

hpnicfCBQoSIfAccountingRunInfoEntry OBJECT-TYPE
    SYNTAX HpnicfCBQoSIfAccountingRunInfoEntry
    MAX-ACCESS not-accessible
    STATUS current
    DESCRIPTION
        "Account statistics entry."
    INDEX { hpnicfCBQoSIfApplyPolicyIfIndex,
            hpnicfCBQoSIfApplyPolicyDirection,
            hpnicfCBQoSPolicyClassIndex
          }
    ::= { hpnicfCBQoSIfAccountingRunInfoTable 1 }

HpnicfCBQoSIfAccountingRunInfoEntry ::=
    SEQUENCE
    {
        hpnicfCBQoSIfAccountingPackets
            Counter64,
        hpnicfCBQoSIfAccountingBytes
            Counter64
    }

hpnicfCBQoSIfAccountingPackets OBJECT-TYPE
    SYNTAX Counter64
    MAX-ACCESS read-only
    STATUS current
    DESCRIPTION
        "Number of packets."
    ::= { hpnicfCBQoSIfAccountingRunInfoEntry 1 }

hpnicfCBQoSIfAccountingBytes OBJECT-TYPE
    SYNTAX Counter64
    MAX-ACCESS read-only
    STATUS current
    DESCRIPTION
        "Number of bytes."
    ::= { hpnicfCBQoSIfAccountingRunInfoEntry 2 }

-- ATM Interface PVC: policy Running statistics information

hpnicfCBQoSAtmPvcStaticsObjects OBJECT IDENTIFIER ::= { hpnicfCBQoSApplyPolicyStaticsObjects 2 }

-- ATM PVC CBQ statistics

hpnicfCBQoSAtmPvcCbqRunInfoTable OBJECT-TYPE
    SYNTAX SEQUENCE OF HpnicfCBQoSAtmPvcCbqRunInfoEntry
    MAX-ACCESS not-accessible
    STATUS current
    DESCRIPTION
        "A table of ATM PVC CBQ Running statistics.
         When policy using queue behavior is applied on
         ATM PVC.  ATM PVC will using Class Based Queuing."
    ::= { hpnicfCBQoSAtmPvcStaticsObjects 1 }

hpnicfCBQoSAtmPvcCbqRunInfoEntry OBJECT-TYPE
    SYNTAX HpnicfCBQoSAtmPvcCbqRunInfoEntry
    MAX-ACCESS not-accessible
    STATUS current
    DESCRIPTION
        "FR PVC CBQ statistics entry."
    INDEX { hpnicfCBQoSAtmPvcApplyPolicyIfIndex,
            hpnicfCBQoSAtmPvcApplyPolicyVPI,
            hpnicfCBQoSAtmPvcApplyPolicyVCI }
    ::= { hpnicfCBQoSAtmPvcCbqRunInfoTable 1 }

HpnicfCBQoSAtmPvcCbqRunInfoEntry ::=
    SEQUENCE
    {
        hpnicfCBQoSAtmPvcCbqQueueSize
            Integer32,
        hpnicfCBQoSAtmPvcCbqDiscard
            Counter64,
        hpnicfCBQoSAtmPvcCbqEfQueueSize
            Integer32,
        hpnicfCBQoSAtmPvcCbqAfQueueSize
            Integer32,
        hpnicfCBQoSAtmPvcCbqBeQueueSize
            Integer32,
        hpnicfCBQoSAtmPvcCbqBeActiveQueueNum
            Integer32,
        hpnicfCBQoSAtmPvcCbqBeMaxActiveQueueNum
            Integer32,
        hpnicfCBQoSAtmPvcCbqBeTotalQueueNum
            Integer32,
        hpnicfCBQoSAtmPvcCbqAfAllocatedQueueNum
            Integer32
    }

hpnicfCBQoSAtmPvcCbqQueueSize OBJECT-TYPE
    SYNTAX Integer32
    MAX-ACCESS read-only
    STATUS current
    DESCRIPTION
        "Packet number of CBQ queue."
    ::= { hpnicfCBQoSAtmPvcCbqRunInfoEntry 1 }

hpnicfCBQoSAtmPvcCbqDiscard OBJECT-TYPE
    SYNTAX Counter64
    MAX-ACCESS read-only
    STATUS current
    DESCRIPTION
        "The number of discarded packets which couldn't be enqueued."
    ::= { hpnicfCBQoSAtmPvcCbqRunInfoEntry 2 }

hpnicfCBQoSAtmPvcCbqEfQueueSize OBJECT-TYPE
    SYNTAX Integer32
    MAX-ACCESS read-only
    STATUS current
    DESCRIPTION
        "Packet number of EF queue."
    ::= { hpnicfCBQoSAtmPvcCbqRunInfoEntry 3 }

hpnicfCBQoSAtmPvcCbqAfQueueSize OBJECT-TYPE
    SYNTAX Integer32
    MAX-ACCESS read-only
    STATUS current
    DESCRIPTION
        "Packet number of AF queue."
    ::= { hpnicfCBQoSAtmPvcCbqRunInfoEntry 4 }

hpnicfCBQoSAtmPvcCbqBeQueueSize OBJECT-TYPE
    SYNTAX Integer32
    MAX-ACCESS read-only
    STATUS current
    DESCRIPTION
        "Packet number of BE queue."
    ::= { hpnicfCBQoSAtmPvcCbqRunInfoEntry 5 }

hpnicfCBQoSAtmPvcCbqBeActiveQueueNum OBJECT-TYPE
    SYNTAX Integer32
    MAX-ACCESS read-only
    STATUS current
    DESCRIPTION
        "The packet number of Active Be Queue."
    ::= { hpnicfCBQoSAtmPvcCbqRunInfoEntry 6 }

hpnicfCBQoSAtmPvcCbqBeMaxActiveQueueNum OBJECT-TYPE
    SYNTAX Integer32
    MAX-ACCESS read-only
    STATUS current
    DESCRIPTION
        "The max packet number of Active Be Queue."
    ::= { hpnicfCBQoSAtmPvcCbqRunInfoEntry 7 }

hpnicfCBQoSAtmPvcCbqBeTotalQueueNum OBJECT-TYPE
    SYNTAX Integer32
    MAX-ACCESS read-only
    STATUS current
    DESCRIPTION
        "The total packet number of Be Queue."
    ::= { hpnicfCBQoSAtmPvcCbqRunInfoEntry 8 }

hpnicfCBQoSAtmPvcCbqAfAllocatedQueueNum OBJECT-TYPE
    SYNTAX Integer32
    MAX-ACCESS read-only
    STATUS current
    DESCRIPTION
        "The Allocated packet number of AF Queue."
    ::= { hpnicfCBQoSAtmPvcCbqRunInfoEntry 9 }

-- Class match statistics

hpnicfCBQoSAtmPvcClassMatchRunInfoTable OBJECT-TYPE
    SYNTAX SEQUENCE OF HpnicfCBQoSAtmPvcClassMatchRunInfoEntry
    MAX-ACCESS not-accessible
    STATUS current
    DESCRIPTION
        "A table of Running statistics for matching a classifier
         in a QoS policy applied on ATM PVC."
    ::= { hpnicfCBQoSAtmPvcStaticsObjects 2 }

hpnicfCBQoSAtmPvcClassMatchRunInfoEntry OBJECT-TYPE
    SYNTAX HpnicfCBQoSAtmPvcClassMatchRunInfoEntry
    MAX-ACCESS not-accessible
    STATUS current
    DESCRIPTION
        "Classifier matching statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex }
    ::= { hpnicfCBQoSAtmPvcClassMatchRunInfoTable 1 }

HpnicfCBQoSAtmPvcClassMatchRunInfoEntry ::=
    SEQUENCE
    {
        hpnicfCBQoSAtmPvcClassMatchPackets
            Counter64,
        hpnicfCBQoSAtmPvcClassMatchBytes
            Counter64,
        hpnicfCBQoSAtmPvcClassAverageRate
            Integer32
    }

hpnicfCBQoSAtmPvcClassMatchPackets OBJECT-TYPE
    SYNTAX Counter64
    MAX-ACCESS read-only
    STATUS current
    DESCRIPTION
        "Number of packets matching a class in a QoS policy."
    ::= { hpnicfCBQoSAtmPvcClassMatchRunInfoEntry 1 }

hpnicfCBQoSAtmPvcClassMatchBytes OBJECT-TYPE
    SYNTAX Counter64
    MAX-ACCESS read-only
    STATUS current
    DESCRIPTION
        "Number of bytes matching a class in a QoS policy."
    ::= { hpnicfCBQoSAtmPvcClassMatchRunInfoEntry 2 }

hpnicfCBQoSAtmPvcClassAverageRate OBJECT-TYPE
    SYNTAX Integer32
    MAX-ACCESS read-only
    STATUS current
    DESCRIPTION
        "Average rate matching a class in the last 5 minutes."
    ::= { hpnicfCBQoSAtmPvcClassMatchRunInfoEntry 3 }

-- CAR statistics

hpnicfCBQoSAtmPvcCarRunInfoTable OBJECT-TYPE
    SYNTAX SEQUENCE OF HpnicfCBQoSAtmPvcCarRunInfoEntry
    MAX-ACCESS not-accessible
    STATUS current
    DESCRIPTION
        "A table of Running statistics for CAR
         in a QoS policy applied on ATM PVC."
    ::= { hpnicfCBQoSAtmPvcStaticsObjects 3 }

hpnicfCBQoSAtmPvcCarRunInfoEntry OBJECT-TYPE
    SYNTAX HpnicfCBQoSAtmPvcCarRunInfoEntry
    MAX-ACCESS not-accessible
    STATUS current
    DESCRIPTION
        "CAR statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex }
    ::= { hpnicfCBQoSAtmPvcCarRunInfoTable 1 }

HpnicfCBQoSAtmPvcCarRunInfoEntry ::=
    SEQUENCE
    {
        hpnicfCBQoSAtmPvcCarConformPackets
            Counter64,
        hpnicfCBQoSAtmPvcCarConformBytes
            Counter64,
        hpnicfCBQoSAtmPvcCarExceedPackets
            Counter64,
        hpnicfCBQoSAtmPvcCarExceedBytes
            Counter64
    }

hpnicfCBQoSAtmPvcCarConformPackets OBJECT-TYPE
    SYNTAX Counter64
    MAX-ACCESS read-only
    STATUS current
    DESCRIPTION
        "Number of packets that conforming specified CIR."
    ::= { hpnicfCBQoSAtmPvcCarRunInfoEntry 1 }

hpnicfCBQoSAtmPvcCarConformBytes OBJECT-TYPE
    SYNTAX Counter64
    MAX-ACCESS read-only
    STATUS current
    DESCRIPTION
        "Number of bytes that conforming specified CIR."
    ::= { hpnicfCBQoSAtmPvcCarRunInfoEntry 2 }

hpnicfCBQoSAtmPvcCarExceedPackets OBJECT-TYPE
    SYNTAX Counter64
    MAX-ACCESS read-only
    STATUS current
    DESCRIPTION
        "Number of packets exceeded CIR."
    ::= { hpnicfCBQoSAtmPvcCarRunInfoEntry 3 }

hpnicfCBQoSAtmPvcCarExceedBytes OBJECT-TYPE
    SYNTAX Counter64
    MAX-ACCESS read-only
    STATUS current
    DESCRIPTION
        "Number of bytes exceeded CIR."
    ::= { hpnicfCBQoSAtmPvcCarRunInfoEntry 4 }

-- GTS statistics

hpnicfCBQoSAtmPvcGtsRunInfoTable OBJECT-TYPE
    SYNTAX SEQUENCE OF HpnicfCBQoSAtmPvcGtsRunInfoEntry
    MAX-ACCESS not-accessible
    STATUS current
    DESCRIPTION
        "A table of Running statistics for GTS
         in a QoS policy applied on ATM PVC."
    ::= { hpnicfCBQoSAtmPvcStaticsObjects 4 }

hpnicfCBQoSAtmPvcGtsRunInfoEntry OBJECT-TYPE
    SYNTAX HpnicfCBQoSAtmPvcGtsRunInfoEntry
    MAX-ACCESS not-accessible
    STATUS current
    DESCRIPTION
        "GTS statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex }
    ::= { hpnicfCBQoSAtmPvcGtsRunInfoTable 1 }

HpnicfCBQoSAtmPvcGtsRunInfoEntry ::=
    SEQUENCE
    {
        hpnicfCBQoSAtmPvcGtsPassedPackets
            Counter64,
        hpnicfCBQoSAtmPvcGtsPassedBytes
            Counter64,
        hpnicfCBQoSAtmPvcGtsDiscardedPackets
            Counter64,
        hpnicfCBQoSAtmPvcGtsDiscardedBytes
            Counter64,
        hpnicfCBQoSAtmPvcGtsDelayedPackets
            Counter64,
        hpnicfCBQoSAtmPvcGtsDelayedBytes
            Counter64,
        hpnicfCBQoSAtmPvcGtsQueueSize
            Integer32
    }

hpnicfCBQoSAtmPvcGtsPassedPackets OBJECT-TYPE
    SYNTAX Counter64
    MAX-ACCESS read-only
    STATUS current
    DESCRIPTION
        "Number of packets passed by GTS."
    ::= { hpnicfCBQoSAtmPvcGtsRunInfoEntry 1 }

hpnicfCBQoSAtmPvcGtsPassedBytes OBJECT-TYPE
    SYNTAX Counter64
    MAX-ACCESS read-only
    STATUS current
    DESCRIPTION
        "Number of bytes passed by GTS."
    ::= { hpnicfCBQoSAtmPvcGtsRunInfoEntry 2 }

hpnicfCBQoSAtmPvcGtsDiscardedPackets OBJECT-TYPE
    SYNTAX Counter64
    MAX-ACCESS read-only
    STATUS current
    DESCRIPTION
        "Number of packets discarded by GTS."
    ::= { hpnicfCBQoSAtmPvcGtsRunInfoEntry 3 }

hpnicfCBQoSAtmPvcGtsDiscardedBytes OBJECT-TYPE
    SYNTAX Counter64
    MAX-ACCESS read-only
    STATUS current
    DESCRIPTION
        "Number of bytes discarded by GTS."
    ::= { hpnicfCBQoSAtmPvcGtsRunInfoEntry 4 }

hpnicfCBQoSAtmPvcGtsDelayedPackets OBJECT-TYPE
    SYNTAX Counter64
    MAX-ACCESS read-only
    STATUS current
    DESCRIPTION
        "Number of packets delayed by GTS."
    ::= { hpnicfCBQoSAtmPvcGtsRunInfoEntry 5 }

hpnicfCBQoSAtmPvcGtsDelayedBytes OBJECT-TYPE
    SYNTAX Counter64
    MAX-ACCESS read-only
    STATUS current
    DESCRIPTION
        "Number of bytes delayed by GTS."
    ::= { hpnicfCBQoSAtmPvcGtsRunInfoEntry 6 }

hpnicfCBQoSAtmPvcGtsQueueSize OBJECT-TYPE
    SYNTAX Integer32
    MAX-ACCESS read-only
    STATUS current
    DESCRIPTION
        "packet number of GTS queue."
    ::= { hpnicfCBQoSAtmPvcGtsRunInfoEntry 7 }

-- Remark statistics

hpnicfCBQoSAtmPvcRemarkRunInfoTable OBJECT-TYPE
    SYNTAX SEQUENCE OF HpnicfCBQoSAtmPvcRemarkRunInfoEntry
    MAX-ACCESS not-accessible
    STATUS current
    DESCRIPTION
        "A table of Running statistics for remarking
         in a QoS policy applied on ATM PVC."
    ::= { hpnicfCBQoSAtmPvcStaticsObjects 5 }

hpnicfCBQoSAtmPvcRemarkRunInfoEntry OBJECT-TYPE
    SYNTAX HpnicfCBQoSAtmPvcRemarkRunInfoEntry
    MAX-ACCESS not-accessible
    STATUS current
    DESCRIPTION
        "Remarking statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex }
    ::= { hpnicfCBQoSAtmPvcRemarkRunInfoTable 1 }

HpnicfCBQoSAtmPvcRemarkRunInfoEntry ::=
    SEQUENCE
    {
        hpnicfCBQoSAtmPvcRemarkedPackets
            Counter64
    }

hpnicfCBQoSAtmPvcRemarkedPackets OBJECT-TYPE
    SYNTAX Counter64
    MAX-ACCESS read-only
    STATUS current
    DESCRIPTION
        "Number of packets remarked."
    ::= { hpnicfCBQoSAtmPvcRemarkRunInfoEntry 1 }

-- Queue statistics

hpnicfCBQoSAtmPvcQueueRunInfoTable OBJECT-TYPE
    SYNTAX SEQUENCE OF HpnicfCBQoSAtmPvcQueueRunInfoEntry
    MAX-ACCESS not-accessible
    STATUS current
    DESCRIPTION
        "A table of Running statistics for queue
         in a QoS policy applied on ATM PVC."
    ::= { hpnicfCBQoSAtmPvcStaticsObjects 6 }

hpnicfCBQoSAtmPvcQueueRunInfoEntry OBJECT-TYPE
    SYNTAX HpnicfCBQoSAtmPvcQueueRunInfoEntry
    MAX-ACCESS not-accessible
    STATUS current
    DESCRIPTION
        "Queue statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex }
    ::= { hpnicfCBQoSAtmPvcQueueRunInfoTable 1}

HpnicfCBQoSAtmPvcQueueRunInfoEntry ::=
    SEQUENCE
    {
        hpnicfCBQoSAtmPvcQueueMatchedPackets
            Counter64,
        hpnicfCBQoSAtmPvcQueueMatchedBytes
            Counter64,
        hpnicfCBQoSAtmPvcQueueEnqueuedPackets
            Counter64,
        hpnicfCBQoSAtmPvcQueueEnqueuedBytes
            Counter64,
        hpnicfCBQoSAtmPvcQueueDiscardedPackets
            Counter64,
        hpnicfCBQoSAtmPvcQueueDiscardedBytes
            Counter64
    }

hpnicfCBQoSAtmPvcQueueMatchedPackets OBJECT-TYPE
    SYNTAX Counter64
    MAX-ACCESS read-only
    STATUS current
    DESCRIPTION
        "Number of packets matched to enqueue."
    ::= { hpnicfCBQoSAtmPvcQueueRunInfoEntry 1 }

hpnicfCBQoSAtmPvcQueueMatchedBytes OBJECT-TYPE
    SYNTAX Counter64
    MAX-ACCESS read-only
    STATUS current
    DESCRIPTION
        "Number of bytes matched to enqueue."
    ::= { hpnicfCBQoSAtmPvcQueueRunInfoEntry 2 }

hpnicfCBQoSAtmPvcQueueEnqueuedPackets OBJECT-TYPE
    SYNTAX Counter64
    MAX-ACCESS read-only
    STATUS current
    DESCRIPTION
        "Number of packets enqueued."
    ::= { hpnicfCBQoSAtmPvcQueueRunInfoEntry 3 }

hpnicfCBQoSAtmPvcQueueEnqueuedBytes OBJECT-TYPE
    SYNTAX Counter64
    MAX-ACCESS read-only
    STATUS current
    DESCRIPTION
        "Number of bytes enqueued."
    ::= { hpnicfCBQoSAtmPvcQueueRunInfoEntry 4 }

hpnicfCBQoSAtmPvcQueueDiscardedPackets OBJECT-TYPE
    SYNTAX Counter64
    MAX-ACCESS read-only
    STATUS current
    DESCRIPTION
        "Number of packets discard when enqueued by discard method."
    ::= { hpnicfCBQoSAtmPvcQueueRunInfoEntry 5 }

hpnicfCBQoSAtmPvcQueueDiscardedBytes OBJECT-TYPE
    SYNTAX Counter64
    MAX-ACCESS read-only
    STATUS current
    DESCRIPTION
        "Number of bytes discard when enqueued by discard method."
    ::= { hpnicfCBQoSAtmPvcQueueRunInfoEntry 6 }

-- WRED statistics

hpnicfCBQoSAtmPvcWredRunInfoTable OBJECT-TYPE
    SYNTAX SEQUENCE OF HpnicfCBQoSAtmPvcWredRunInfoEntry
    MAX-ACCESS not-accessible
    STATUS current
    DESCRIPTION
        "A table of Running statistics for WRED
         in a QoS policy applied on ATM PVC."
    ::= { hpnicfCBQoSAtmPvcStaticsObjects 7 }

hpnicfCBQoSAtmPvcWredRunInfoEntry OBJECT-TYPE
    SYNTAX HpnicfCBQoSAtmPvcWredRunInfoEntry
    MAX-ACCESS not-accessible
    STATUS current
    DESCRIPTION
        "WRED statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex,
            hpnicfCBQoSWredClassValue }
    ::= { hpnicfCBQoSAtmPvcWredRunInfoTable 1 }

HpnicfCBQoSAtmPvcWredRunInfoEntry ::=
    SEQUENCE
    {
        hpnicfCBQoSAtmPvcWredRandomDiscardedPackets
            Counter64,
        hpnicfCBQoSAtmPvcWredTailDiscardedPackets
            Counter64
    }

hpnicfCBQoSAtmPvcWredRandomDiscardedPackets OBJECT-TYPE
    SYNTAX Counter64
    MAX-ACCESS read-only
    STATUS current
    DESCRIPTION
        "Number of packets randomly discarded by WRED."
    ::= { hpnicfCBQoSAtmPvcWredRunInfoEntry 1 }

hpnicfCBQoSAtmPvcWredTailDiscardedPackets OBJECT-TYPE
    SYNTAX Counter64
    MAX-ACCESS read-only
    STATUS current
    DESCRIPTION
        "Number of packets tail-discarded by WRED."
    ::= { hpnicfCBQoSAtmPvcWredRunInfoEntry 2 }

--
-- nodes of hpnicfCBQoSAtmPvcAccountingRunInfoTable
--
hpnicfCBQoSAtmPvcAccountingRunInfoTable OBJECT-TYPE
    SYNTAX SEQUENCE OF HpnicfCBQoSAtmPvcAccountingRunInfoEntry
    MAX-ACCESS not-accessible
    STATUS current
    DESCRIPTION
        "A table of Running statistics for account
         in a QoS policy applied on the ATM PVC."
    ::= { hpnicfCBQoSAtmPvcStaticsObjects 8 }

hpnicfCBQoSAtmPvcAccountingRunInfoEntry OBJECT-TYPE
    SYNTAX HpnicfCBQoSAtmPvcAccountingRunInfoEntry
    MAX-ACCESS not-accessible
    STATUS current
    DESCRIPTION
        "Account statistics entry."
    INDEX { hpnicfCBQoSAtmPvcApplyPolicyIfIndex,
            hpnicfCBQoSAtmPvcApplyPolicyVPI,
            hpnicfCBQoSAtmPvcApplyPolicyVCI,
            hpnicfCBQoSAtmPvcApplyPolicyDirection,
            hpnicfCBQoSPolicyClassIndex,
            hpnicfCBQoSWredClassValue
          }
    ::= { hpnicfCBQoSAtmPvcAccountingRunInfoTable 1 }

HpnicfCBQoSAtmPvcAccountingRunInfoEntry ::=
    SEQUENCE
    {
        hpnicfCBQoSAtmPvcAccountingPackets
            Counter64,
        hpnicfCBQoSAtmPvcAccountingBytes
            Counter64
    }

hpnicfCBQoSAtmPvcAccountingPackets OBJECT-TYPE
    SYNTAX Counter64
    MAX-ACCESS read-only
    STATUS current
    DESCRIPTION
        "Number of packets."
    ::= { hpnicfCBQoSAtmPvcAccountingRunInfoEntry 1 }

hpnicfCBQoSAtmPvcAccountingBytes OBJECT-TYPE
    SYNTAX Counter64
    MAX-ACCESS read-only
    STATUS current
    DESCRIPTION
        "Number of bytes."
    ::= { hpnicfCBQoSAtmPvcAccountingRunInfoEntry 2 }

-- FR Interface PVC: policy Running statistics information

hpnicfCBQoSFrPvcStaticsObjects OBJECT IDENTIFIER ::= { hpnicfCBQoSApplyPolicyStaticsObjects 3 }

-- FR PVC CBQ statistics

hpnicfCBQoSFrPvcCbqRunInfoTable OBJECT-TYPE
    SYNTAX SEQUENCE OF HpnicfCBQoSFrPvcCbqRunInfoEntry
    MAX-ACCESS not-accessible
    STATUS current
    DESCRIPTION
        "A table of FR PVC CBQ Running statistics.
         When policy using queue behavior is applied on FR PVC
         will using Class Based Queuing."
    ::= { hpnicfCBQoSFrPvcStaticsObjects 1 }

hpnicfCBQoSFrPvcCbqRunInfoEntry OBJECT-TYPE
    SYNTAX HpnicfCBQoSFrPvcCbqRunInfoEntry
    MAX-ACCESS not-accessible
    STATUS current
    DESCRIPTION
        "FR PVC CBQ statistics entry."
    INDEX { hpnicfCBQoSFrPvcApplyPolicyIfIndex, hpnicfCBQoSFrPvcApplyPolicyDlciNum }
    ::= { hpnicfCBQoSFrPvcCbqRunInfoTable 1 }

HpnicfCBQoSFrPvcCbqRunInfoEntry ::=
    SEQUENCE
    {
        hpnicfCBQoSFrPvcCbqQueueSize
            Integer32,
        hpnicfCBQoSFrPvcCbqDiscard
            Counter64,
        hpnicfCBQoSFrPvcCbqEfQueueSize
            Integer32,
        hpnicfCBQoSFrPvcCbqAfQueueSize
            Integer32,
        hpnicfCBQoSFrPvcCbqBeQueueSize
            Integer32,
        hpnicfCBQoSFrPvcCbqBeActiveQueueNum
            Integer32,
        hpnicfCBQoSFrPvcCbqBeMaxActiveQueueNum
            Integer32,
        hpnicfCBQoSFrPvcCbqBeTotalQueueNum
            Integer32,
        hpnicfCBQoSFrPvcCbqAfAllocatedQueueNum
            Integer32
    }

hpnicfCBQoSFrPvcCbqQueueSize OBJECT-TYPE
    SYNTAX Integer32
    MAX-ACCESS read-only
    STATUS current
    DESCRIPTION
        "Packet number of CBQ queue."
    ::= { hpnicfCBQoSFrPvcCbqRunInfoEntry 1 }

hpnicfCBQoSFrPvcCbqDiscard OBJECT-TYPE
    SYNTAX Counter64
    MAX-ACCESS read-only
    STATUS current
    DESCRIPTION
        "The number of discarded packets which could not be enqueued."
    ::= { hpnicfCBQoSFrPvcCbqRunInfoEntry 2 }

hpnicfCBQoSFrPvcCbqEfQueueSize OBJECT-TYPE
    SYNTAX Integer32
    MAX-ACCESS read-only
    STATUS current
    DESCRIPTION
        "Packet number of EF queue."
    ::= { hpnicfCBQoSFrPvcCbqRunInfoEntry 3 }

hpnicfCBQoSFrPvcCbqAfQueueSize OBJECT-TYPE
    SYNTAX Integer32
    MAX-ACCESS read-only
    STATUS current
    DESCRIPTION
        "Packet number of AF queue."
    ::= { hpnicfCBQoSFrPvcCbqRunInfoEntry 4 }

hpnicfCBQoSFrPvcCbqBeQueueSize OBJECT-TYPE
    SYNTAX Integer32
    MAX-ACCESS read-only
    STATUS current
    DESCRIPTION
        "Packet number of BE queue."
    ::= { hpnicfCBQoSFrPvcCbqRunInfoEntry 5 }

hpnicfCBQoSFrPvcCbqBeActiveQueueNum OBJECT-TYPE
    SYNTAX Integer32
    MAX-ACCESS read-only
    STATUS current
    DESCRIPTION
        "The packet number of Active Be Queue."
    ::= { hpnicfCBQoSFrPvcCbqRunInfoEntry 6 }

hpnicfCBQoSFrPvcCbqBeMaxActiveQueueNum OBJECT-TYPE
    SYNTAX Integer32
    MAX-ACCESS read-only
    STATUS current
    DESCRIPTION
        "The max packet number of Active Be Queue."
    ::= { hpnicfCBQoSFrPvcCbqRunInfoEntry 7 }

hpnicfCBQoSFrPvcCbqBeTotalQueueNum OBJECT-TYPE
    SYNTAX Integer32
    MAX-ACCESS read-only
    STATUS current
    DESCRIPTION
        "The total packet number of Be Queue."
    ::= { hpnicfCBQoSFrPvcCbqRunInfoEntry 8 }

hpnicfCBQoSFrPvcCbqAfAllocatedQueueNum OBJECT-TYPE
    SYNTAX Integer32
    MAX-ACCESS read-only
    STATUS current
    DESCRIPTION
        "The Allocated packet number of AF Queue."
    ::= { hpnicfCBQoSFrPvcCbqRunInfoEntry 9 }

-- Class match statistics

hpnicfCBQoSFrPvcClassMatchRunInfoTable OBJECT-TYPE
    SYNTAX SEQUENCE OF HpnicfCBQoSFrPvcClassMatchRunInfoEntry
    MAX-ACCESS not-accessible
    STATUS current
    DESCRIPTION
        "A table of Running statistics for matching a classifier
         in a QoS policy applied on FR PVC."
    ::= { hpnicfCBQoSFrPvcStaticsObjects 2 }

hpnicfCBQoSFrPvcClassMatchRunInfoEntry OBJECT-TYPE
    SYNTAX HpnicfCBQoSFrPvcClassMatchRunInfoEntry
    MAX-ACCESS not-accessible
    STATUS current
    DESCRIPTION
        "Classifier matching statistics entry."
    INDEX { hpnicfCBQoSFrPvcApplyPolicyIfIndex,
            hpnicfCBQoSFrPvcApplyPolicyDlciNum,
            hpnicfCBQoSFrPvcApplyPolicyDirection,
            hpnicfCBQoSPolicyClassIndex }
    ::= { hpnicfCBQoSFrPvcClassMatchRunInfoTable 1 }

HpnicfCBQoSFrPvcClassMatchRunInfoEntry ::=
    SEQUENCE
    {
        hpnicfCBQoSFrPvcClassMatchedPackets
            Counter64,
        hpnicfCBQoSFrPvcClassMatchedBytes
            Counter64,
        hpnicfCBQoSFrPvcClassAverageRate
            Counter64
    }

hpnicfCBQoSFrPvcClassMatchedPackets OBJECT-TYPE
    SYNTAX Counter64
    MAX-ACCESS read-only
    STATUS current
    DESCRIPTION
        "Number of packets matching a class in a QoS policy."
    ::= { hpnicfCBQoSFrPvcClassMatchRunInfoEntry 1 }

hpnicfCBQoSFrPvcClassMatchedBytes OBJECT-TYPE
    SYNTAX Counter64
    MAX-ACCESS read-only
    STATUS current
    DESCRIPTION
        "Number of bytes matching a class in a QoS policy."
    ::= { hpnicfCBQoSFrPvcClassMatchRunInfoEntry 2 }

hpnicfCBQoSFrPvcClassAverageRate OBJECT-TYPE
    SYNTAX Counter64
    MAX-ACCESS read-only
    STATUS current
    DESCRIPTION
        "Average rate matching a class of the last 5 minutes."
    ::= { hpnicfCBQoSFrPvcClassMatchRunInfoEntry 3 }

-- CAR statistics

hpnicfCBQoSFrPvcCarRunInfoTable OBJECT-TYPE
    SYNTAX SEQUENCE OF HpnicfCBQoSFrPvcCarRunInfoEntry
    MAX-ACCESS not-accessible
    STATUS current
    DESCRIPTION
        "A table of Running statistics for CAR
         in a QoS policy applied on FR PVC."
    ::= { hpnicfCBQoSFrPvcStaticsObjects 3 }

hpnicfCBQoSFrPvcCarRunInfoEntry OBJECT-TYPE
    SYNTAX HpnicfCBQoSFrPvcCarRunInfoEntry
    MAX-ACCESS not-accessible
    STATUS current
    DESCRIPTION
        "CAR statistics entry."
    INDEX { hpnicfCBQoSFrPvcApplyPolicyIfIndex,
            hpnicfCBQoSFrPvcApplyPolicyDlciNum,
            hpnicfCBQoSFrPvcApplyPolicyDirection,
            hpnicfCBQoSPolicyClassIndex }
    ::= { hpnicfCBQoSFrPvcCarRunInfoTable 1 }

HpnicfCBQoSFrPvcCarRunInfoEntry ::=
    SEQUENCE
    {
        hpnicfCBQoSFrPvcCarConformPackets
            Counter64,
        hpnicfCBQoSFrPvcCarConformBytes
            Counter64,
        hpnicfCBQoSFrPvcCarExceedPackets
            Counter64,
        hpnicfCBQoSFrPvcCarExceedBytes
            Counter64
    }

hpnicfCBQoSFrPvcCarConformPackets OBJECT-TYPE
    SYNTAX Counter64
    MAX-ACCESS read-only
    STATUS current
    DESCRIPTION
        "Number of packets conform CIR."
    ::= { hpnicfCBQoSFrPvcCarRunInfoEntry 1 }

hpnicfCBQoSFrPvcCarConformBytes OBJECT-TYPE
    SYNTAX Counter64
    MAX-ACCESS read-only
    STATUS current
    DESCRIPTION
        "Number of bytes conform CIR."
    ::= { hpnicfCBQoSFrPvcCarRunInfoEntry 2 }

hpnicfCBQoSFrPvcCarExceedPackets OBJECT-TYPE
    SYNTAX Counter64
    MAX-ACCESS read-only
    STATUS current
    DESCRIPTION
        "Number of packets exceed CIR."
    ::= { hpnicfCBQoSFrPvcCarRunInfoEntry 3 }

hpnicfCBQoSFrPvcCarExceedBytes OBJECT-TYPE
    SYNTAX Counter64
    MAX-ACCESS read-only
    STATUS current
    DESCRIPTION
        "Number of bytes exceed CIR."
    ::= { hpnicfCBQoSFrPvcCarRunInfoEntry 4 }

-- GTS statistics

hpnicfCBQoSFrPvcGtsRunInfoTable OBJECT-TYPE
    SYNTAX SEQUENCE OF HpnicfCBQoSFrPvcGtsRunInfoEntry
    MAX-ACCESS not-accessible
    STATUS current
    DESCRIPTION
        "A table of Running statistics for GTS
         in a QoS policy applied on FR PVC."
    ::= { hpnicfCBQoSFrPvcStaticsObjects 4 }

hpnicfCBQoSFrPvcGtsRunInfoEntry OBJECT-TYPE
    SYNTAX HpnicfCBQoSFrPvcGtsRunInfoEntry
    MAX-ACCESS not-accessible
    STATUS current
    DESCRIPTION
        "GTS statistics entry."
    INDEX { hpnicfCBQoSFrPvcApplyPolicyIfIndex,
            hpnicfCBQoSFrPvcApplyPolicyDlciNum,
            hpnicfCBQoSFrPvcApplyPolicyDirection,
            hpnicfCBQoSPolicyClassIndex }
    ::= { hpnicfCBQoSFrPvcGtsRunInfoTable 1 }

HpnicfCBQoSFrPvcGtsRunInfoEntry ::=
    SEQUENCE
    {
        hpnicfCBQoSFrPvcGtsPassedPackets
            Counter64,
        hpnicfCBQoSFrPvcGtsPassedBytes
            Counter64,
        hpnicfCBQoSFrPvcGtsDiscardedPackets
            Counter64,
        hpnicfCBQoSFrPvcGtsDiscardedBytes
            Counter64,
        hpnicfCBQoSFrPvcGtsDelayedPackets
            Counter64,
        hpnicfCBQoSFrPvcGtsDelayedBytes
            Counter64,
        hpnicfCBQoSFrPvcGtsQueueSize
            Integer32
    }

hpnicfCBQoSFrPvcGtsPassedPackets OBJECT-TYPE
    SYNTAX Counter64
    MAX-ACCESS read-only
    STATUS current
    DESCRIPTION
        "Number of packets passed by GTS."
    ::= { hpnicfCBQoSFrPvcGtsRunInfoEntry 1 }

hpnicfCBQoSFrPvcGtsPassedBytes OBJECT-TYPE
    SYNTAX Counter64
    MAX-ACCESS read-only
    STATUS current
    DESCRIPTION
        "Number of bytes passed by GTS."
    ::= { hpnicfCBQoSFrPvcGtsRunInfoEntry 2 }

hpnicfCBQoSFrPvcGtsDiscardedPackets OBJECT-TYPE
    SYNTAX Counter64
    MAX-ACCESS read-only
    STATUS current
    DESCRIPTION
        "Number of packets discarded by GTS."
    ::= { hpnicfCBQoSFrPvcGtsRunInfoEntry 3 }

hpnicfCBQoSFrPvcGtsDiscardedBytes OBJECT-TYPE
    SYNTAX Counter64
    MAX-ACCESS read-only
    STATUS current
    DESCRIPTION
        "Number of bytes discarded by GTS."
    ::= { hpnicfCBQoSFrPvcGtsRunInfoEntry 4 }

hpnicfCBQoSFrPvcGtsDelayedPackets OBJECT-TYPE
    SYNTAX Counter64
    MAX-ACCESS read-only
    STATUS current
    DESCRIPTION
        "Number of packets delayed by GTS."
    ::= { hpnicfCBQoSFrPvcGtsRunInfoEntry 5 }

hpnicfCBQoSFrPvcGtsDelayedBytes OBJECT-TYPE
    SYNTAX Counter64
    MAX-ACCESS read-only
    STATUS current
    DESCRIPTION
        "Number of bytes delayed by GTS."
    ::= { hpnicfCBQoSFrPvcGtsRunInfoEntry 6 }

hpnicfCBQoSFrPvcGtsQueueSize OBJECT-TYPE
    SYNTAX Integer32
    MAX-ACCESS read-only
    STATUS current
    DESCRIPTION
        "Packet number of GTS queue."
    ::= { hpnicfCBQoSFrPvcGtsRunInfoEntry 7 }

-- Remark statistics

hpnicfCBQoSFrPvcRemarkRunInfoTable OBJECT-TYPE
    SYNTAX SEQUENCE OF HpnicfCBQoSFrPvcRemarkRunInfoEntry
    MAX-ACCESS not-accessible
    STATUS current
    DESCRIPTION
        "A table of Running statistics for remarking
         in a QoS policy applied on FR PVC."
    ::= { hpnicfCBQoSFrPvcStaticsObjects 5 }

hpnicfCBQoSFrPvcRemarkRunInfoEntry OBJECT-TYPE
    SYNTAX HpnicfCBQoSFrPvcRemarkRunInfoEntry
    MAX-ACCESS not-accessible
    STATUS current
    DESCRIPTION
        "Remarking statistics entry."
    INDEX { hpnicfCBQoSFrPvcApplyPolicyIfIndex,
            hpnicfCBQoSFrPvcApplyPolicyDlciNum,
            hpnicfCBQoSFrPvcApplyPolicyDirection,
            hpnicfCBQoSPolicyClassIndex }
    ::= { hpnicfCBQoSFrPvcRemarkRunInfoTable 1 }

HpnicfCBQoSFrPvcRemarkRunInfoEntry ::=
    SEQUENCE
    {
        hpnicfCBQoSFrPvcRemarkedPackets
            Counter64
    }

hpnicfCBQoSFrPvcRemarkedPackets OBJECT-TYPE
    SYNTAX Counter64
    MAX-ACCESS read-only
    STATUS current
    DESCRIPTION
        "Number of packets remarked."
    ::= { hpnicfCBQoSFrPvcRemarkRunInfoEntry 1 }

-- Queue statistics

hpnicfCBQoSFrPvcQueueRunInfoTable OBJECT-TYPE
    SYNTAX SEQUENCE OF HpnicfCBQoSFrPvcQueueRunInfoEntry
    MAX-ACCESS not-accessible
    STATUS current
    DESCRIPTION
        "A table of Running statistics for queue
        in a QoS policy applied on FR PVC."
    ::= { hpnicfCBQoSFrPvcStaticsObjects 6 }

hpnicfCBQoSFrPvcQueueRunInfoEntry OBJECT-TYPE
    SYNTAX HpnicfCBQoSFrPvcQueueRunInfoEntry
    MAX-ACCESS not-accessible
    STATUS current
    DESCRIPTION
        "Queue statistics entry."
    INDEX { hpnicfCBQoSFrPvcApplyPolicyIfIndex,
            hpnicfCBQoSFrPvcApplyPolicyDlciNum,
            hpnicfCBQoSFrPvcApplyPolicyDirection,
            hpnicfCBQoSPolicyClassIndex }
    ::= { hpnicfCBQoSFrPvcQueueRunInfoTable 1 }

HpnicfCBQoSFrPvcQueueRunInfoEntry ::=
    SEQUENCE
    {
        hpnicfCBQoSFrPvcQueueMatchedPackets
            Counter64,
        hpnicfCBQoSFrPvcQueueMatchedBytes
            Counter64,
        hpnicfCBQoSFrPvcQueueEnqueuedPackets
            Counter64,
        hpnicfCBQoSFrPvcQueueEnqueuedBytes
            Counter64,
        hpnicfCBQoSFrPvcQueueDiscardedPackets
            Counter64,
        hpnicfCBQoSFrPvcQueueDiscardedBytes
            Counter64
    }

hpnicfCBQoSFrPvcQueueMatchedPackets OBJECT-TYPE
    SYNTAX Counter64
    MAX-ACCESS read-only
    STATUS current
    DESCRIPTION
        "Number of packets matched to enqueue."
    ::= { hpnicfCBQoSFrPvcQueueRunInfoEntry 1 }

hpnicfCBQoSFrPvcQueueMatchedBytes OBJECT-TYPE
    SYNTAX Counter64
    MAX-ACCESS read-only
    STATUS current
    DESCRIPTION
        "Number of bytes matched to en-queue."
    ::= { hpnicfCBQoSFrPvcQueueRunInfoEntry 2 }

hpnicfCBQoSFrPvcQueueEnqueuedPackets OBJECT-TYPE
    SYNTAX Counter64
    MAX-ACCESS read-only
    STATUS current
    DESCRIPTION
        "Number of packets en-queued."
    ::= { hpnicfCBQoSFrPvcQueueRunInfoEntry 3 }

hpnicfCBQoSFrPvcQueueEnqueuedBytes OBJECT-TYPE
    SYNTAX Counter64
    MAX-ACCESS read-only
    STATUS current
    DESCRIPTION
        "Number of bytes enqueued."
    ::= { hpnicfCBQoSFrPvcQueueRunInfoEntry 4 }

hpnicfCBQoSFrPvcQueueDiscardedPackets OBJECT-TYPE
    SYNTAX Counter64
    MAX-ACCESS read-only
    STATUS current
    DESCRIPTION
        "Number of packets discarded when enqueued by discard method."
    ::= { hpnicfCBQoSFrPvcQueueRunInfoEntry 5 }

hpnicfCBQoSFrPvcQueueDiscardedBytes OBJECT-TYPE
    SYNTAX Counter64
    MAX-ACCESS read-only
    STATUS current
    DESCRIPTION
        "Number of bytes discarded when enqueued by discard method."
    ::= { hpnicfCBQoSFrPvcQueueRunInfoEntry 6 }

-- WRED statistics

hpnicfCBQoSFrPvcWredRunInfoTable OBJECT-TYPE
    SYNTAX SEQUENCE OF HpnicfCBQoSFrPvcWredRunInfoEntry
    MAX-ACCESS not-accessible
    STATUS current
    DESCRIPTION
        "A table of Running statistics for WRED
         in a QoS policy applied on FR PVC.
        "
    ::= { hpnicfCBQoSFrPvcStaticsObjects 7 }

hpnicfCBQoSFrPvcWredRunInfoEntry OBJECT-TYPE
    SYNTAX HpnicfCBQoSFrPvcWredRunInfoEntry
    MAX-ACCESS not-accessible
    STATUS current
    DESCRIPTION
        "WRED statistics entry."
    INDEX { hpnicfCBQoSFrPvcApplyPolicyIfIndex,
            hpnicfCBQoSFrPvcApplyPolicyDlciNum,
            hpnicfCBQoSFrPvcApplyPolicyDirection,
            hpnicfCBQoSPolicyClassIndex,
            hpnicfCBQoSWredClassValue }
    ::= { hpnicfCBQoSFrPvcWredRunInfoTable 1 }

HpnicfCBQoSFrPvcWredRunInfoEntry ::=
    SEQUENCE
    {
        hpnicfCBQoSFrPvcWredRandomDiscardedPackets
            Counter64,
        hpnicfCBQoSFrPvcWredTailDiscardedPackets
            Counter64
    }

hpnicfCBQoSFrPvcWredRandomDiscardedPackets OBJECT-TYPE
    SYNTAX Counter64
    MAX-ACCESS read-only
    STATUS current
    DESCRIPTION
        "Number of packets randomly discarded by WRED."
    ::= { hpnicfCBQoSFrPvcWredRunInfoEntry 1 }

hpnicfCBQoSFrPvcWredTailDiscardedPackets OBJECT-TYPE
    SYNTAX Counter64
    MAX-ACCESS read-only
    STATUS current
    DESCRIPTION
        "Number of packets tail-discarded by WRED."
    ::= { hpnicfCBQoSFrPvcWredRunInfoEntry 2 }

--
-- nodes of hpnicfCBQoSFrPvcAccountingRunInfoTable
--
hpnicfCBQoSFrPvcAccountingRunInfoTable OBJECT-TYPE
    SYNTAX SEQUENCE OF HpnicfCBQoSFrPvcAccountingRunInfoEntry
    MAX-ACCESS not-accessible
    STATUS current
    DESCRIPTION
        "A table of Running statistics for account
         in a QoS policy applied on the interface."
    ::= { hpnicfCBQoSFrPvcStaticsObjects 8 }

hpnicfCBQoSFrPvcAccountingRunInfoEntry OBJECT-TYPE
    SYNTAX HpnicfCBQoSFrPvcAccountingRunInfoEntry
    MAX-ACCESS not-accessible
    STATUS current
    DESCRIPTION
        "Account statistics entry."
    INDEX { hpnicfCBQoSFrPvcApplyPolicyIfIndex,
            hpnicfCBQoSFrPvcApplyPolicyDlciNum,
            hpnicfCBQoSFrPvcApplyPolicyDirection,
            hpnicfCBQoSPolicyClassIndex,
            hpnicfCBQoSWredClassValue
          }
    ::= { hpnicfCBQoSFrPvcAccountingRunInfoTable 1 }

HpnicfCBQoSFrPvcAccountingRunInfoEntry ::=
    SEQUENCE
    {
        hpnicfCBQoSFrPvcAccountingPackets
            Counter64,
        hpnicfCBQoSFrPvcAccountingBytes
            Counter64
    }

hpnicfCBQoSFrPvcAccountingPackets OBJECT-TYPE
    SYNTAX Counter64
    MAX-ACCESS read-only
    STATUS current
    DESCRIPTION
        "Number of packets."
    ::= { hpnicfCBQoSFrPvcAccountingRunInfoEntry 1 }

hpnicfCBQoSFrPvcAccountingBytes OBJECT-TYPE
    SYNTAX Counter64
    MAX-ACCESS read-only
    STATUS current
    DESCRIPTION
        "Number of bytes."
    ::= { hpnicfCBQoSFrPvcAccountingRunInfoEntry 2 }

-- Ethernet Interface VLAN: policy Running statistics information

hpnicfCBQoSVlanStaticsObjects OBJECT IDENTIFIER ::= { hpnicfCBQoSApplyPolicyStaticsObjects 4 }

-- Class match statistics

hpnicfCBQoSVlanClassMatchRunInfoTable OBJECT-TYPE
    SYNTAX SEQUENCE OF HpnicfCBQoSVlanClassMatchRunInfoEntry
    MAX-ACCESS not-accessible
    STATUS current
    DESCRIPTION
        "A table of Running statistics for matching a classifier
         in a QoS policy applied on Ethernet VLAN.
        "
    ::= { hpnicfCBQoSVlanStaticsObjects 1 }

hpnicfCBQoSVlanClassMatchRunInfoEntry OBJECT-TYPE
    SYNTAX HpnicfCBQoSVlanClassMatchRunInfoEntry
    MAX-ACCESS not-accessible
    STATUS current
    DESCRIPTION
        "Classifier matching statistics entry."
    INDEX { hpnicfCBQoSVlanApplyPolicyVlanid,
            hpnicfCBQoSVlanApplyPolicyDirection,
            hpnicfCBQoSPolicyClassIndex }
    ::= { hpnicfCBQoSVlanClassMatchRunInfoTable 1 }

HpnicfCBQoSVlanClassMatchRunInfoEntry ::=
    SEQUENCE
    {
        hpnicfCBQoSVlanClassMatchedPackets
            Counter64
    }

hpnicfCBQoSVlanClassMatchedPackets OBJECT-TYPE
    SYNTAX Counter64
    MAX-ACCESS read-only
    STATUS current
    DESCRIPTION
        "Number of packets matching a class in a QoS policy."
    ::= { hpnicfCBQoSVlanClassMatchRunInfoEntry 1 }

--
-- nodes of hpnicfCBQoSIfVlanAccountingRunInfoTable
--
hpnicfCBQoSVlanAccountingRunInfoTable OBJECT-TYPE
    SYNTAX SEQUENCE OF HpnicfCBQoSVlanAccountingRunInfoEntry
    MAX-ACCESS not-accessible
    STATUS current
    DESCRIPTION
        "A table of Running statistics for account
         in a QoS policy applied on the interface."
    ::= { hpnicfCBQoSVlanStaticsObjects 2 }

hpnicfCBQoSVlanAccountingRunInfoEntry OBJECT-TYPE
    SYNTAX HpnicfCBQoSVlanAccountingRunInfoEntry
    MAX-ACCESS not-accessible
    STATUS current
    DESCRIPTION
        "Account statistics entry."
    INDEX { hpnicfCBQoSVlanApplyPolicyVlanid,
            hpnicfCBQoSVlanApplyPolicyDirection,
            hpnicfCBQoSPolicyClassIndex }
    ::= { hpnicfCBQoSVlanAccountingRunInfoTable 1 }

HpnicfCBQoSVlanAccountingRunInfoEntry ::=
    SEQUENCE
    {
        hpnicfCBQoSVlanAccountingPackets
            Counter64,
        hpnicfCBQoSVlanAccountingBytes
            Counter64
    }

hpnicfCBQoSVlanAccountingPackets OBJECT-TYPE
    SYNTAX Counter64
    MAX-ACCESS read-only
    STATUS current
    DESCRIPTION
        "Number of packets."
    ::= { hpnicfCBQoSVlanAccountingRunInfoEntry 1 }

hpnicfCBQoSVlanAccountingBytes OBJECT-TYPE
    SYNTAX Counter64
    MAX-ACCESS read-only
    STATUS current
    DESCRIPTION
        "Number of bytes."
    ::= { hpnicfCBQoSVlanAccountingRunInfoEntry 2 }

-- Index Object
hpnicfCBQoSApplyPolicyIndexObjects OBJECT IDENTIFIER
    ::= { hpnicfCBQoSApplyPolicyStaticsObjects 5 }

--
-- ApplyObjectTable
--
hpnicfCBQoSApplyObjectTable OBJECT-TYPE
    SYNTAX SEQUENCE OF HpnicfCBQoSApplyObjectEntry
    MAX-ACCESS not-accessible
    STATUS current
    DESCRIPTION
        "A table of QoS apply object index.  It provides the function
         of querying the information of QoS apply object, which
         consists of interface type, interface index, ATM PVC, FR DLCI
         and nesting policy index, using QoS apply object index."
    ::= { hpnicfCBQoSApplyPolicyIndexObjects 1 }

hpnicfCBQoSApplyObjectEntry OBJECT-TYPE
    SYNTAX HpnicfCBQoSApplyObjectEntry
    MAX-ACCESS not-accessible
    STATUS current
    DESCRIPTION
        "QoS apply object index entry."
    INDEX { hpnicfCBQoSApplyObjectIndex }
    ::= { hpnicfCBQoSApplyObjectTable 1 }

HpnicfCBQoSApplyObjectEntry ::=
    SEQUENCE
    {
        hpnicfCBQoSApplyObjectIndex
            Unsigned32,
        hpnicfCBQoSApplyObjectType
            ApplyObjectType,
        hpnicfCBQoSApplyObjectDirection
            DirectionType,
        hpnicfCBQoSApplyObjectMainSite
            Unsigned32,
        hpnicfCBQoSApplyObjectSubChannel
            Unsigned32,
        hpnicfCBQoSApplyObjectSubClass
            Unsigned32,
        hpnicfCBQoSApplyObjectSubClassSec
            Unsigned32
    }

hpnicfCBQoSApplyObjectIndex OBJECT-TYPE
    SYNTAX Unsigned32
    MAX-ACCESS not-accessible
    STATUS current
    DESCRIPTION
        "QoS apply object index.  It represents the unique identifier
         of QoS policy applied position.  It generates when QoS policy
         is applied considering ifIndex, VLAN ID, ATM PVC, FR DLCI and
         policy nesting."
    ::= { hpnicfCBQoSApplyObjectEntry 1 }

hpnicfCBQoSApplyObjectType OBJECT-TYPE
    SYNTAX ApplyObjectType
    MAX-ACCESS read-only
    STATUS current
    DESCRIPTION
        "Apply object type."
    ::= { hpnicfCBQoSApplyObjectEntry 2 }

hpnicfCBQoSApplyObjectDirection OBJECT-TYPE
    SYNTAX DirectionType
    MAX-ACCESS read-only
    STATUS current
    DESCRIPTION
        "The direction of QoS apply object."
    ::= { hpnicfCBQoSApplyObjectEntry 3 }

hpnicfCBQoSApplyObjectMainSite OBJECT-TYPE
    SYNTAX Unsigned32
    MAX-ACCESS read-only
    STATUS current
    DESCRIPTION
        "Its value depends on hpnicfCBQoSApplyObjectType.
         It represents VLAN ID when hpnicfCBQoSApplyObjectType
         is vlan, and represents chassis ID when hpnicfCBQoSApplyObjectType
         is controlPlane, otherwise it represents ifIndex."
    ::= { hpnicfCBQoSApplyObjectEntry 4 }

hpnicfCBQoSApplyObjectSubChannel OBJECT-TYPE
    SYNTAX Unsigned32
    MAX-ACCESS read-only
    STATUS current
    DESCRIPTION
        "Its value depends on hpnicfCBQoSApplyObjectType.
         It represents the value of VPI/VCI, of which high 16-bits
         is VPI and low 16-bits is VCI, when hpnicfCBQoSApplyObjectType
         is atmPvc.
         It represents the value of data link connection identifier
         in FR network, when hpnicfCBQoSApplyObjectType is frDlci.
         It represents slot ID, when hpnicfCBQoSApplyObjectType is controlPlane.
         Otherwise the value is '0xFFFFFFFF'."
    ::= { hpnicfCBQoSApplyObjectEntry 5 }

hpnicfCBQoSApplyObjectSubClass OBJECT-TYPE
    SYNTAX Unsigned32
    MAX-ACCESS read-only
    STATUS current
    DESCRIPTION
        "The value represents level-1 sub class index when the QoS
         apply object is level-2 or level-3 nesting policy.  Otherwise
         the value is '0xFFFFFFFF'."
    ::= { hpnicfCBQoSApplyObjectEntry 6 }

hpnicfCBQoSApplyObjectSubClassSec OBJECT-TYPE
    SYNTAX Unsigned32
    MAX-ACCESS read-only
    STATUS current
    DESCRIPTION
        "The value represents level-2 sub class index when the QoS
         apply object is level-3 nesting policy.  Otherwise
         the value is '0xFFFFFFFF'."
    ::= { hpnicfCBQoSApplyObjectEntry 7 }

--
-- IntApplyObjectTable
--
hpnicfCBQoSIntApplyObjectTable OBJECT-TYPE
    SYNTAX SEQUENCE OF HpnicfCBQoSIntApplyObjectEntry
    MAX-ACCESS not-accessible
    STATUS current
    DESCRIPTION
        "A table used for querying the QoS apply object indexes by
         interface index.  It is suitable for querying QoS apply
         object indexes for policies applied on Ethernet ports, ATM
         ports and FR ports."
    ::= { hpnicfCBQoSApplyPolicyIndexObjects 2 }

hpnicfCBQoSIntApplyObjectEntry OBJECT-TYPE
    SYNTAX HpnicfCBQoSIntApplyObjectEntry
    MAX-ACCESS not-accessible
    STATUS current
    DESCRIPTION
        "QoS apply object on interface index querying entry."
    INDEX { hpnicfCBQoSIntApplyObjectIfIndex,
            hpnicfCBQoSApplyObjectDirection }
    ::= { hpnicfCBQoSIntApplyObjectTable 1 }

HpnicfCBQoSIntApplyObjectEntry ::=
    SEQUENCE
    {
        hpnicfCBQoSIntApplyObjectIfIndex
            Unsigned32,
        hpnicfCBQoSIntApplyObjectIndex
            Unsigned32
    }

hpnicfCBQoSIntApplyObjectIfIndex OBJECT-TYPE
    SYNTAX Unsigned32
    MAX-ACCESS not-accessible
    STATUS current
    DESCRIPTION
        "Interface index."
    ::= { hpnicfCBQoSIntApplyObjectEntry 1 }

hpnicfCBQoSIntApplyObjectIndex OBJECT-TYPE
    SYNTAX Unsigned32
    MAX-ACCESS read-only
    STATUS current
    DESCRIPTION
        "QoS apply object index."
    ::= { hpnicfCBQoSIntApplyObjectEntry 2 }

--
-- VlanApplyObjectTable
--
hpnicfCBQoSVlanApplyObjectTable OBJECT-TYPE
    SYNTAX SEQUENCE OF HpnicfCBQoSVlanApplyObjectEntry
    MAX-ACCESS not-accessible
    STATUS current
    DESCRIPTION
        "A table used for querying the QoS apply object indexes by VLAN
         ID and policy direction.  It is suitable for querying QoS
         apply object indexes for policies applied on VLANs.  If the
         value of hpnicfCBQoSVlanApplyObjectVlanID is 0, it means querying
         Qos apply object index for policy applied on global."
    ::= { hpnicfCBQoSApplyPolicyIndexObjects 3 }

hpnicfCBQoSVlanApplyObjectEntry OBJECT-TYPE
    SYNTAX HpnicfCBQoSVlanApplyObjectEntry
    MAX-ACCESS not-accessible
    STATUS current
    DESCRIPTION
        "VLAN apply object entry."
    INDEX { hpnicfCBQoSVlanApplyObjectVlanID,
            hpnicfCBQoSApplyObjectDirection }
    ::= { hpnicfCBQoSVlanApplyObjectTable 1 }

HpnicfCBQoSVlanApplyObjectEntry ::=
    SEQUENCE
    {
        hpnicfCBQoSVlanApplyObjectVlanID
            Unsigned32,
        hpnicfCBQoSVlanApplyObjectIndex
            Unsigned32
    }

hpnicfCBQoSVlanApplyObjectVlanID OBJECT-TYPE
    SYNTAX Unsigned32 (0..4094)
    MAX-ACCESS not-accessible
    STATUS current
    DESCRIPTION
        "VLAN ID."
    ::= { hpnicfCBQoSVlanApplyObjectEntry 1 }

hpnicfCBQoSVlanApplyObjectIndex OBJECT-TYPE
    SYNTAX Unsigned32
    MAX-ACCESS read-only
    STATUS current
    DESCRIPTION
        "QoS apply object index."
    ::= { hpnicfCBQoSVlanApplyObjectEntry 2 }

--
-- PvcApplyObjectTable
--
hpnicfCBQoSPvcApplyObjectTable OBJECT-TYPE
    SYNTAX SEQUENCE OF HpnicfCBQoSPvcApplyObjectEntry
    MAX-ACCESS not-accessible
    STATUS current
    DESCRIPTION
        "A table used for querying the QoS apply object indexes by ATM
         PVC or FR DLCI, ifIndex and policy direction.  It is suitable
         for querying QoS apply object indexes for policies applied on
         ATM PVCs or FR DLCIs."
    ::= { hpnicfCBQoSApplyPolicyIndexObjects 4 }

hpnicfCBQoSPvcApplyObjectEntry OBJECT-TYPE
    SYNTAX HpnicfCBQoSPvcApplyObjectEntry
    MAX-ACCESS not-accessible
    STATUS current
    DESCRIPTION
        "QoS apply object querying entry for ATM PVC or FR
         DLCI."
    INDEX { hpnicfCBQoSPvcApplyObjectIfIndex,
            hpnicfCBQoSPvcApplyObjectPvcID,
            hpnicfCBQoSApplyObjectDirection }
    ::= { hpnicfCBQoSPvcApplyObjectTable 1 }

HpnicfCBQoSPvcApplyObjectEntry ::=
    SEQUENCE
    {
        hpnicfCBQoSPvcApplyObjectIfIndex
            Unsigned32,
        hpnicfCBQoSPvcApplyObjectPvcID
            Unsigned32,
        hpnicfCBQoSPvcApplyObjectIndex
            Unsigned32
    }

hpnicfCBQoSPvcApplyObjectIfIndex OBJECT-TYPE
    SYNTAX Unsigned32
    MAX-ACCESS not-accessible
    STATUS current
    DESCRIPTION
        "Interface index."
    ::= { hpnicfCBQoSPvcApplyObjectEntry 1 }

hpnicfCBQoSPvcApplyObjectPvcID OBJECT-TYPE
    SYNTAX Unsigned32
    MAX-ACCESS not-accessible
    STATUS current
    DESCRIPTION
        "If the QoS apply object queried is a ATM PVC, its input value
         represents a VPI/VCI.  If the QoS apply object queried is a FR
         DLCI, its input value represents a value of FR DLCI."
    ::= { hpnicfCBQoSPvcApplyObjectEntry 2 }

hpnicfCBQoSPvcApplyObjectIndex OBJECT-TYPE
    SYNTAX Unsigned32
    MAX-ACCESS read-only
    STATUS current
    DESCRIPTION
        "QoS apply object index."
    ::= { hpnicfCBQoSPvcApplyObjectEntry 3 }

--
-- hpnicfCBQoSNestPolicyApplyObjectTable
--
hpnicfCBQoSNestPolicyApplyObjectTable OBJECT-TYPE
    SYNTAX SEQUENCE OF HpnicfCBQoSNestPolicyApplyObjectEntry
    MAX-ACCESS not-accessible
    STATUS current
    DESCRIPTION
        "A table used for querying the nested QoS policy apply object indexes.
         It is suitable for querying nested QoS apply object indexes for policies
         applied on ifIndex, VLAN ID, ATM PVC or FR DLCI."
    ::= { hpnicfCBQoSApplyPolicyIndexObjects 5 }

hpnicfCBQoSNestPolicyApplyObjectEntry OBJECT-TYPE
    SYNTAX HpnicfCBQoSNestPolicyApplyObjectEntry
    MAX-ACCESS not-accessible
    STATUS current
    DESCRIPTION
        "QoS apply object on policy querying entry."
    INDEX { hpnicfCBQoSApplyObjectIndex,
            hpnicfCBQoSNestPolicyClassIndex}
    ::= { hpnicfCBQoSNestPolicyApplyObjectTable 1 }

HpnicfCBQoSNestPolicyApplyObjectEntry ::=
    SEQUENCE
    {
        hpnicfCBQoSNestPolicyClassIndex
            Unsigned32,
        hpnicfCBQoSNestPolicyApplyObjectIndex
            Unsigned32
    }

hpnicfCBQoSNestPolicyClassIndex OBJECT-TYPE
    SYNTAX Unsigned32
    MAX-ACCESS not-accessible
    STATUS current
    DESCRIPTION
        "Policyclass index in father policy."
    ::= { hpnicfCBQoSNestPolicyApplyObjectEntry 1 }

hpnicfCBQoSNestPolicyApplyObjectIndex OBJECT-TYPE
    SYNTAX Unsigned32
    MAX-ACCESS read-only
    STATUS current
    DESCRIPTION
        "QoS apply object index of the son policy."
    ::= { hpnicfCBQoSNestPolicyApplyObjectEntry 2 }

--
-- hpnicfCBQoSCpApplyObjectTable
--
hpnicfCBQoSCpApplyObjectTable OBJECT-TYPE
    SYNTAX SEQUENCE OF HpnicfCBQoSCpApplyObjectEntry
    MAX-ACCESS not-accessible
    STATUS current
    DESCRIPTION
        "A table used for querying the QoS policy apply object indexes
         by chassis ID and slot ID.  It is suitable for querying QoS apply
         object indexes for policies applied on control plane."
    ::= { hpnicfCBQoSApplyPolicyIndexObjects 6 }

hpnicfCBQoSCpApplyObjectEntry OBJECT-TYPE
    SYNTAX HpnicfCBQoSCpApplyObjectEntry
    MAX-ACCESS not-accessible
    STATUS current
    DESCRIPTION
        "QoS policy apply object on control plane querying entry."
    INDEX { hpnicfCBQoSCpApplyObjectChassis,
            hpnicfCBQoSCpApplyObjectSlot,
            hpnicfCBQoSApplyObjectDirection}
    ::= { hpnicfCBQoSCpApplyObjectTable 1 }

HpnicfCBQoSCpApplyObjectEntry ::=
    SEQUENCE
    {
        hpnicfCBQoSCpApplyObjectChassis
            Unsigned32,
        hpnicfCBQoSCpApplyObjectSlot
            Unsigned32,
        hpnicfCBQoSCpApplyObjectIndex
            Unsigned32
    }

hpnicfCBQoSCpApplyObjectChassis OBJECT-TYPE
    SYNTAX Unsigned32
    MAX-ACCESS not-accessible
    STATUS current
    DESCRIPTION
        "Chassis ID."
    ::= { hpnicfCBQoSCpApplyObjectEntry 1 }

hpnicfCBQoSCpApplyObjectSlot OBJECT-TYPE
    SYNTAX Unsigned32
    MAX-ACCESS not-accessible
    STATUS current
    DESCRIPTION
        "Slot ID."
    ::= { hpnicfCBQoSCpApplyObjectEntry 2 }

hpnicfCBQoSCpApplyObjectIndex OBJECT-TYPE
    SYNTAX Unsigned32
    MAX-ACCESS read-only
    STATUS current
    DESCRIPTION
        "QoS apply object index."
    ::= { hpnicfCBQoSCpApplyObjectEntry 3 }

-- Statistics

hpnicfCBQoSStaticsObjects OBJECT IDENTIFIER
    ::= { hpnicfCBQoSApplyPolicyStaticsObjects 6 }

-- CBQ statistics

hpnicfCBQoSCbqRunInfoTable OBJECT-TYPE
    SYNTAX SEQUENCE OF HpnicfCBQoSCbqRunInfoEntry
    MAX-ACCESS not-accessible
    STATUS current
    DESCRIPTION
        "A table of CBQ running statistics.
         When policy using queue behavior is applied on QoS apply
         object, the QoS apply object will use Class Based Queuing."
    ::= { hpnicfCBQoSStaticsObjects 1 }

hpnicfCBQoSCbqRunInfoEntry OBJECT-TYPE
    SYNTAX HpnicfCBQoSCbqRunInfoEntry
    MAX-ACCESS not-accessible
    STATUS current
    DESCRIPTION
        "CBQ statistics entry of QoS apply object."
    INDEX { hpnicfCBQoSApplyObjectIndex }
    ::= { hpnicfCBQoSCbqRunInfoTable 1 }

HpnicfCBQoSCbqRunInfoEntry ::=
    SEQUENCE
    {
        hpnicfCBQoSCbqQueueSize
            Integer32,
        hpnicfCBQoSCbqDiscard
            Counter64,
        hpnicfCBQoSCbqEfQueueSize
            Integer32,
        hpnicfCBQoSCbqAfQueueSize
            Integer32,
        hpnicfCBQoSCbqBeQueueSize
            Integer32,
        hpnicfCBQoSCbqBeActiveQueueNum
            Integer32,
        hpnicfCBQoSCbqBeMaxActiveQueueNum
            Integer32,
        hpnicfCBQoSCbqBeTotalQueueNum
            Integer32,
        hpnicfCBQoSCbqAfAllocatedQueueNum
            Integer32
    }

hpnicfCBQoSCbqQueueSize OBJECT-TYPE
    SYNTAX Integer32
    MAX-ACCESS read-only
    STATUS current
    DESCRIPTION
        "Number of packets in CBQ queue."
    ::= { hpnicfCBQoSCbqRunInfoEntry 1 }

hpnicfCBQoSCbqDiscard OBJECT-TYPE
    SYNTAX Counter64
    MAX-ACCESS read-only
    STATUS current
    DESCRIPTION
        "Number of discarded packets which couldn't queue."
    ::= { hpnicfCBQoSCbqRunInfoEntry 2 }

hpnicfCBQoSCbqEfQueueSize OBJECT-TYPE
    SYNTAX Integer32
    MAX-ACCESS read-only
    STATUS current
    DESCRIPTION
        "Number of packets in EF queue."
    ::= { hpnicfCBQoSCbqRunInfoEntry 3 }

hpnicfCBQoSCbqAfQueueSize OBJECT-TYPE
    SYNTAX Integer32
    MAX-ACCESS read-only
    STATUS current
    DESCRIPTION
        "Number of packets in AF queue."
    ::= { hpnicfCBQoSCbqRunInfoEntry 4 }

hpnicfCBQoSCbqBeQueueSize OBJECT-TYPE
    SYNTAX Integer32
    MAX-ACCESS read-only
    STATUS current
    DESCRIPTION
        "Number of packets in BE Queue."
    ::= { hpnicfCBQoSCbqRunInfoEntry 5 }

hpnicfCBQoSCbqBeActiveQueueNum OBJECT-TYPE
    SYNTAX Integer32
    MAX-ACCESS read-only
    STATUS current
    DESCRIPTION
        "Number of Active BE Queues."
    ::= { hpnicfCBQoSCbqRunInfoEntry 6 }

hpnicfCBQoSCbqBeMaxActiveQueueNum OBJECT-TYPE
    SYNTAX Integer32
    MAX-ACCESS read-only
    STATUS current
    DESCRIPTION
        "The max number of Active BE Queues."
    ::= { hpnicfCBQoSCbqRunInfoEntry 7 }

hpnicfCBQoSCbqBeTotalQueueNum OBJECT-TYPE
    SYNTAX Integer32
    MAX-ACCESS read-only
    STATUS current
    DESCRIPTION
        "Number of total BE Queues."
    ::= { hpnicfCBQoSCbqRunInfoEntry 8 }

hpnicfCBQoSCbqAfAllocatedQueueNum OBJECT-TYPE
    SYNTAX Integer32
    MAX-ACCESS read-only
    STATUS current
    DESCRIPTION
        "Number of allocated AF Queues."
    ::= { hpnicfCBQoSCbqRunInfoEntry 9 }

-- Class match statistics

hpnicfCBQoSClassMatchRunInfoTable OBJECT-TYPE
    SYNTAX SEQUENCE OF HpnicfCBQoSClassMatchRunInfoEntry
    MAX-ACCESS not-accessible
    STATUS current
    DESCRIPTION
        "A table of running statistics for matching a classifier on a
         QoS apply object."
    ::= { hpnicfCBQoSStaticsObjects 2 }

hpnicfCBQoSClassMatchRunInfoEntry OBJECT-TYPE
    SYNTAX HpnicfCBQoSClassMatchRunInfoEntry
    MAX-ACCESS not-accessible
    STATUS current
    DESCRIPTION
        "Classifier's matching statistics information entry."
    INDEX { hpnicfCBQoSApplyObjectIndex,
            hpnicfCBQoSPolicyClassIndex }
    ::= { hpnicfCBQoSClassMatchRunInfoTable 1 }

HpnicfCBQoSClassMatchRunInfoEntry ::=
    SEQUENCE
    {
        hpnicfCBQoSClassMatchedPackets
            Counter64,
        hpnicfCBQoSClassMatchedBytes
            Counter64,
        hpnicfCBQoSClassFwdPktpps
            Unsigned32,
        hpnicfCBQoSClassFwdPktbps
            Unsigned32,
        hpnicfCBQoSClassDropPktpps
            Unsigned32,
        hpnicfCBQoSClassDropPktbps
            Unsigned32,
        hpnicfCBQoSClassFlowStatInterval
            Unsigned32,
        hpnicfCBQoSClassBehaviorStatus
            INTEGER
    }

hpnicfCBQoSClassMatchedPackets OBJECT-TYPE
    SYNTAX Counter64
    MAX-ACCESS read-only
    STATUS current
    DESCRIPTION
        "Number of packets matching a class in a QoS policy."
    ::= { hpnicfCBQoSClassMatchRunInfoEntry 1 }

hpnicfCBQoSClassMatchedBytes OBJECT-TYPE
    SYNTAX Counter64
    MAX-ACCESS read-only
    STATUS current
    DESCRIPTION
        "Number of bytes matching a class in a QoS policy."
    ::= { hpnicfCBQoSClassMatchRunInfoEntry 2 }

hpnicfCBQoSClassFwdPktpps OBJECT-TYPE
    SYNTAX Unsigned32
    MAX-ACCESS read-only
    STATUS current
    DESCRIPTION
        "Average number of packets macthing the class forwarded
         per second in the last interval.
         Unit: pps."
    ::= { hpnicfCBQoSClassMatchRunInfoEntry 3 }

hpnicfCBQoSClassFwdPktbps OBJECT-TYPE
    SYNTAX Unsigned32
    MAX-ACCESS read-only
    STATUS current
    DESCRIPTION
        "Average bits of packets matching the class forwarded
         per second in the last interval.
         Unit: bps."
    ::= { hpnicfCBQoSClassMatchRunInfoEntry 4 }

hpnicfCBQoSClassDropPktpps OBJECT-TYPE
    SYNTAX Unsigned32
    MAX-ACCESS read-only
    STATUS current
    DESCRIPTION
        "Average number of packets matching the class dropped
         per second in the last interval.
         Unit: pps."
    ::= { hpnicfCBQoSClassMatchRunInfoEntry 5 }

hpnicfCBQoSClassDropPktbps OBJECT-TYPE
    SYNTAX Unsigned32
    MAX-ACCESS read-only
    STATUS current
    DESCRIPTION
        "Average bits of packets matching the class dropped
         per second in the last interval.
         Unit: bps."
    ::= { hpnicfCBQoSClassMatchRunInfoEntry 6 }

hpnicfCBQoSClassFlowStatInterval OBJECT-TYPE
    SYNTAX Unsigned32
    MAX-ACCESS read-only
    STATUS current
    DESCRIPTION
        "Interval of collecting traffic statistics.
         Unit: minute."
    ::= { hpnicfCBQoSClassMatchRunInfoEntry 7 }

hpnicfCBQoSClassBehaviorStatus OBJECT-TYPE
    SYNTAX INTEGER
    {
        success(1),
        failure(2),
        partialSuccess(3)
    }
    MAX-ACCESS read-only
    STATUS current
    DESCRIPTION
        "Classifier-behavior applying status."
    ::= { hpnicfCBQoSClassMatchRunInfoEntry 8 }

-- CAR statistics

hpnicfCBQoSCarRunInfoTable OBJECT-TYPE
    SYNTAX SEQUENCE OF HpnicfCBQoSCarRunInfoEntry
    MAX-ACCESS not-accessible
    STATUS current
    DESCRIPTION
        "A table of running statistics for CAR on a QoS apply object."
    ::= { hpnicfCBQoSStaticsObjects 3 }

hpnicfCBQoSCarRunInfoEntry OBJECT-TYPE
    SYNTAX HpnicfCBQoSCarRunInfoEntry
    MAX-ACCESS not-accessible
    STATUS current
    DESCRIPTION
        "CAR statistics information entry."
    INDEX { hpnicfCBQoSApplyObjectIndex,
            hpnicfCBQoSPolicyClassIndex }
    ::= { hpnicfCBQoSCarRunInfoTable 1 }

HpnicfCBQoSCarRunInfoEntry ::=
    SEQUENCE
    {
        hpnicfCBQoSCarGreenPackets
            Counter64,
        hpnicfCBQoSCarGreenBytes
            Counter64,
        hpnicfCBQoSCarRedPackets
            Counter64,
        hpnicfCBQoSCarRedBytes
            Counter64,
        hpnicfCBQoSCarYellowPackets
            Counter64,
        hpnicfCBQoSCarYellowBytes
            Counter64
    }

hpnicfCBQoSCarGreenPackets OBJECT-TYPE
    SYNTAX Counter64
    MAX-ACCESS read-only
    STATUS current
    DESCRIPTION
        "Number of green packets."
    ::= { hpnicfCBQoSCarRunInfoEntry 1 }

hpnicfCBQoSCarGreenBytes OBJECT-TYPE
    SYNTAX Counter64
    MAX-ACCESS read-only
    STATUS current
    DESCRIPTION
        "Number of green bytes."
    ::= { hpnicfCBQoSCarRunInfoEntry 2 }

hpnicfCBQoSCarRedPackets OBJECT-TYPE
    SYNTAX Counter64
    MAX-ACCESS read-only
    STATUS current
    DESCRIPTION
        "Number of red packets."
    ::= { hpnicfCBQoSCarRunInfoEntry 3 }

hpnicfCBQoSCarRedBytes OBJECT-TYPE
    SYNTAX Counter64
    MAX-ACCESS read-only
    STATUS current
    DESCRIPTION
        "Number of red bytes."
    ::= { hpnicfCBQoSCarRunInfoEntry 4 }

hpnicfCBQoSCarYellowPackets OBJECT-TYPE
    SYNTAX Counter64
    MAX-ACCESS read-only
    STATUS current
    DESCRIPTION
        "Number of yellow packets."
    ::= { hpnicfCBQoSCarRunInfoEntry 5 }

hpnicfCBQoSCarYellowBytes OBJECT-TYPE
    SYNTAX Counter64
    MAX-ACCESS read-only
    STATUS current
    DESCRIPTION
        "Number of yellow bytes."
    ::= { hpnicfCBQoSCarRunInfoEntry 6 }

-- GTS statistics

hpnicfCBQoSGtsRunInfoTable OBJECT-TYPE
    SYNTAX SEQUENCE OF HpnicfCBQoSGtsRunInfoEntry
    MAX-ACCESS not-accessible
    STATUS current
    DESCRIPTION
        "A table of running statistics for GTS on a QoS apply object."
    ::= { hpnicfCBQoSStaticsObjects 4 }

hpnicfCBQoSGtsRunInfoEntry OBJECT-TYPE
    SYNTAX HpnicfCBQoSGtsRunInfoEntry
    MAX-ACCESS not-accessible
    STATUS current
    DESCRIPTION
        "GTS statistics entry."
    INDEX { hpnicfCBQoSApplyObjectIndex,
            hpnicfCBQoSPolicyClassIndex }
    ::= { hpnicfCBQoSGtsRunInfoTable 1 }

HpnicfCBQoSGtsRunInfoEntry ::=
    SEQUENCE
    {
        hpnicfCBQoSGtsPassedPackets
            Counter64,
        hpnicfCBQoSGtsPassedBytes
            Counter64,
        hpnicfCBQoSGtsDiscardedPackets
            Counter64,
        hpnicfCBQoSGtsDiscardedBytes
            Counter64,
        hpnicfCBQoSGtsDelayedPackets
            Counter64,
        hpnicfCBQoSGtsDelayedBytes
            Counter64,
        hpnicfCBQoSGtsQueueSize
            Integer32
    }

hpnicfCBQoSGtsPassedPackets OBJECT-TYPE
    SYNTAX Counter64
    MAX-ACCESS read-only
    STATUS current
    DESCRIPTION
        "Number of packets passed by GTS."
    ::= { hpnicfCBQoSGtsRunInfoEntry 1 }

hpnicfCBQoSGtsPassedBytes OBJECT-TYPE
    SYNTAX Counter64
    MAX-ACCESS read-only
    STATUS current
    DESCRIPTION
        "Number of bytes passed by GTS."
    ::= { hpnicfCBQoSGtsRunInfoEntry 2 }

hpnicfCBQoSGtsDiscardedPackets OBJECT-TYPE
    SYNTAX Counter64
    MAX-ACCESS read-only
    STATUS current
    DESCRIPTION
        "Number of packets discarded by GTS."
    ::= { hpnicfCBQoSGtsRunInfoEntry 3 }

hpnicfCBQoSGtsDiscardedBytes OBJECT-TYPE
    SYNTAX Counter64
    MAX-ACCESS read-only
    STATUS current
    DESCRIPTION
        "Number of bytes discarded by GTS."
    ::= { hpnicfCBQoSGtsRunInfoEntry 4 }

hpnicfCBQoSGtsDelayedPackets OBJECT-TYPE
    SYNTAX Counter64
    MAX-ACCESS read-only
    STATUS current
    DESCRIPTION
        "Number of packets delayed by GTS."
    ::= { hpnicfCBQoSGtsRunInfoEntry 5 }

hpnicfCBQoSGtsDelayedBytes OBJECT-TYPE
    SYNTAX Counter64
    MAX-ACCESS read-only
    STATUS current
    DESCRIPTION
        "Number of bytes delayed by GTS."
    ::= { hpnicfCBQoSGtsRunInfoEntry 6 }

hpnicfCBQoSGtsQueueSize OBJECT-TYPE
    SYNTAX Integer32
    MAX-ACCESS read-only
    STATUS current
    DESCRIPTION
        "Number of packets in GTS queue."
    ::= { hpnicfCBQoSGtsRunInfoEntry 7 }

-- Remark statistics

hpnicfCBQoSRemarkRunInfoTable OBJECT-TYPE
    SYNTAX SEQUENCE OF HpnicfCBQoSRemarkRunInfoEntry
    MAX-ACCESS not-accessible
    STATUS current
    DESCRIPTION
        "A table of running statistics for remarking on a QoS apply
         object."
    ::= { hpnicfCBQoSStaticsObjects 5 }

hpnicfCBQoSRemarkRunInfoEntry OBJECT-TYPE
    SYNTAX HpnicfCBQoSRemarkRunInfoEntry
    MAX-ACCESS not-accessible
    STATUS current
    DESCRIPTION
        "Remarking statistics entry."
    INDEX { hpnicfCBQoSApplyObjectIndex,
            hpnicfCBQoSPolicyClassIndex }
    ::= { hpnicfCBQoSRemarkRunInfoTable 1 }

HpnicfCBQoSRemarkRunInfoEntry ::=
    SEQUENCE
    {
        hpnicfCBQoSRemarkedPackets
            Counter64
    }

hpnicfCBQoSRemarkedPackets OBJECT-TYPE
    SYNTAX Counter64
    MAX-ACCESS read-only
    STATUS current
    DESCRIPTION
        "Number of remarked packets."
    ::= { hpnicfCBQoSRemarkRunInfoEntry 1 }

-- Queue statistics

hpnicfCBQoSQueueRunInfoTable OBJECT-TYPE
    SYNTAX SEQUENCE OF HpnicfCBQoSQueueRunInfoEntry
    MAX-ACCESS not-accessible
    STATUS current
    DESCRIPTION
        "A table of running statistics for queue on a QoS apply
         object."
    ::= { hpnicfCBQoSStaticsObjects 6 }

hpnicfCBQoSQueueRunInfoEntry OBJECT-TYPE
    SYNTAX HpnicfCBQoSQueueRunInfoEntry
    MAX-ACCESS not-accessible
    STATUS current
    DESCRIPTION
        "Queue statistics entry."
    INDEX { hpnicfCBQoSApplyObjectIndex,
            hpnicfCBQoSPolicyClassIndex }
    ::= { hpnicfCBQoSQueueRunInfoTable 1 }

HpnicfCBQoSQueueRunInfoEntry ::=
    SEQUENCE
    {
        hpnicfCBQoSQueueMatchedPackets
            Counter64,
        hpnicfCBQoSQueueMatchedBytes
            Counter64,
        hpnicfCBQoSQueueEnqueuedPackets
            Counter64,
        hpnicfCBQoSQueueEnqueuedBytes
            Counter64,
        hpnicfCBQoSQueueDiscardedPackets
            Counter64,
        hpnicfCBQoSQueueDiscardedBytes
            Counter64
    }

hpnicfCBQoSQueueMatchedPackets OBJECT-TYPE
    SYNTAX Counter64
    MAX-ACCESS read-only
    STATUS current
    DESCRIPTION
        "Number of packets matched to queue."
    ::= { hpnicfCBQoSQueueRunInfoEntry 1 }

hpnicfCBQoSQueueMatchedBytes OBJECT-TYPE
    SYNTAX Counter64
    MAX-ACCESS read-only
    STATUS current
    DESCRIPTION
        "Number of bytes matched to queue."
    ::= { hpnicfCBQoSQueueRunInfoEntry 2 }

hpnicfCBQoSQueueEnqueuedPackets OBJECT-TYPE
    SYNTAX Counter64
    MAX-ACCESS read-only
    STATUS current
    DESCRIPTION
        "Number of packets queued."
    ::= { hpnicfCBQoSQueueRunInfoEntry 3 }

hpnicfCBQoSQueueEnqueuedBytes OBJECT-TYPE
    SYNTAX Counter64
    MAX-ACCESS read-only
    STATUS current
    DESCRIPTION
        "Number of bytes queued."
    ::= { hpnicfCBQoSQueueRunInfoEntry 4 }

hpnicfCBQoSQueueDiscardedPackets OBJECT-TYPE
    SYNTAX Counter64
    MAX-ACCESS read-only
    STATUS current
    DESCRIPTION
        "Number of packets discarded when queued by discard method."
    ::= { hpnicfCBQoSQueueRunInfoEntry 5 }

hpnicfCBQoSQueueDiscardedBytes OBJECT-TYPE
    SYNTAX Counter64
    MAX-ACCESS read-only
    STATUS current
    DESCRIPTION
        "Number of bytes discarded when queued by discard method."
    ::= { hpnicfCBQoSQueueRunInfoEntry 6 }

-- WRED statistics

hpnicfCBQoSWredRunInfoTable OBJECT-TYPE
    SYNTAX SEQUENCE OF HpnicfCBQoSWredRunInfoEntry
    MAX-ACCESS not-accessible
    STATUS current
    DESCRIPTION
        "A table of running statistics for WRED on a QoS apply object."
    ::= { hpnicfCBQoSStaticsObjects 7 }

hpnicfCBQoSWredRunInfoEntry OBJECT-TYPE
    SYNTAX HpnicfCBQoSWredRunInfoEntry
    MAX-ACCESS not-accessible
    STATUS current
    DESCRIPTION
        "WRED statistics entry."
    INDEX { hpnicfCBQoSApplyObjectIndex,
            hpnicfCBQoSPolicyClassIndex,
            hpnicfCBQoSWredClassValue }
    ::= { hpnicfCBQoSWredRunInfoTable 1 }

HpnicfCBQoSWredRunInfoEntry ::=
    SEQUENCE
    {
        hpnicfCBQoSWredRandomDiscardedPackets
            Counter64,
        hpnicfCBQoSWredTailDiscardedPackets
            Counter64
    }

hpnicfCBQoSWredRandomDiscardedPackets OBJECT-TYPE
    SYNTAX Counter64
    MAX-ACCESS read-only
    STATUS current
    DESCRIPTION
        "Number of packets random-discarded by WRED."
    ::= { hpnicfCBQoSWredRunInfoEntry 1 }

hpnicfCBQoSWredTailDiscardedPackets OBJECT-TYPE
    SYNTAX Counter64
    MAX-ACCESS read-only
    STATUS current
    DESCRIPTION
        "Number of packets tail-discarded by WRED."
    ::= { hpnicfCBQoSWredRunInfoEntry 2 }

--
-- Accounting RunInfo
--
hpnicfCBQoSAccountingRunInfoTable OBJECT-TYPE
    SYNTAX SEQUENCE OF HpnicfCBQoSAccountingRunInfoEntry
    MAX-ACCESS not-accessible
    STATUS current
    DESCRIPTION
        "A table of running statistics for account on a QoS apply
         object."
    ::= { hpnicfCBQoSStaticsObjects 8 }

hpnicfCBQoSAccountingRunInfoEntry OBJECT-TYPE
    SYNTAX HpnicfCBQoSAccountingRunInfoEntry
    MAX-ACCESS not-accessible
    STATUS current
    DESCRIPTION
        "Account statistics entry."
    INDEX { hpnicfCBQoSApplyObjectIndex,
            hpnicfCBQoSPolicyClassIndex
          }
    ::= { hpnicfCBQoSAccountingRunInfoTable 1 }

HpnicfCBQoSAccountingRunInfoEntry ::=
    SEQUENCE
    {
        hpnicfCBQoSAccountingPackets
            Counter64,
        hpnicfCBQoSAccountingBytes
            Counter64
    }

hpnicfCBQoSAccountingPackets OBJECT-TYPE
    SYNTAX Counter64
    MAX-ACCESS read-only
    STATUS current
    DESCRIPTION
        "Number of packets matching a class in QoS policy."
    ::= { hpnicfCBQoSAccountingRunInfoEntry 1 }

hpnicfCBQoSAccountingBytes OBJECT-TYPE
    SYNTAX Counter64
    MAX-ACCESS read-only
    STATUS current
    DESCRIPTION
        "Number of bytes matching a class in QoS policy."
    ::= { hpnicfCBQoSAccountingRunInfoEntry 2 }

-- Policy applying status

hpnicfCBQoSApplyingStatusObjects OBJECT IDENTIFIER ::= { hpnicfCBQoSObjects 6 }

-- System status when applying policy

hpnicfCBQoSApplyingStatus OBJECT-TYPE
    SYNTAX INTEGER
    {
        idle(1),
        busy(2)
    }
    MAX-ACCESS read-only
    STATUS current
    DESCRIPTION
        "This object shows the status of the system when applying policy.
        It is forbidden to set or read in this MIB module except current
        table when the value is busy."
    ::= { hpnicfCBQoSApplyingStatusObjects 1 }

-- Notifications

hpnicfCBQoSNotifications OBJECT IDENTIFIER ::= { hpnicfCBQoSObjects 7 }

-- All trap definitions should be placed under this object.

hpnicfCBQoSNotificationsPrefix OBJECT IDENTIFIER ::= { hpnicfCBQoSNotifications 0 }

-- All objects used for TRAP only are defined here.

hpnicfCBQoSIfPolicyChanged NOTIFICATION-TYPE
    OBJECTS
        {
            hpnicfCBQoSIfApplyPolicyIfIndex,
            hpnicfCBQoSIfApplyPolicyDirection
        }
    STATUS current
    DESCRIPTION
        "This notification will be sent when the applying status
        of the policy on the interface is changed."
    ::= { hpnicfCBQoSNotificationsPrefix 1 }

hpnicfCBQoSVlanPolicyChanged NOTIFICATION-TYPE
    OBJECTS
        {
            hpnicfCBQoSVlanApplyPolicyVlanid,
            hpnicfCBQoSVlanApplyPolicyDirection
        }
    STATUS current
    DESCRIPTION
        "This notification will be sent when the applying status
        of the policy on the VLAN is changed."
    ::= { hpnicfCBQoSNotificationsPrefix 2 }

END
