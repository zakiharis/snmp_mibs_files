HP-ICF-USBPORT DEFINITIONS ::= BEGIN

   IMPORTS
      OBJECT-TYPE, NOTIFICATION-TYPE, MODULE-IDENTITY
         FROM SNMPv2-SMI
      NOTIFICATION-GROUP, OBJECT-GROUP, MODULE-COMPLIANCE
         FROM SNMPv2-CONF
      hpSwitch
         FROM HP-ICF-OID;

   hpicfUSBPortMIB MODULE-IDENTITY
      LAST-UPDATED "200903110000Z"
      ORGANIZATION "HP Networking"
      CONTACT-INFO "Hewlett Packard Company
                    8000 Foothills Blvd.
                    Roseville, CA 95747"
      DESCRIPTION "This MIB module manages the USB Port."

      --
      -- Revision History
      --

      REVISION     "200903110000Z"        -- March 11, 2009
      DESCRIPTION  "Add hpicfUSBPortZeroPowerStatus object "

      REVISION     "200809170000Z"        -- September 17, 2008
      DESCRIPTION  "Move NOTIFICATIONS OID from 3 to 0"

      REVISION     "200809100000Z"        -- September 10, 2008
      DESCRIPTION  "Added NOTIFICATIONS for enabled/disabled"

      REVISION     "200806250000Z"        -- June 25, 2008
      DESCRIPTION   "Original version"

      ::= { hpSwitch 53 }

   -- USBPort Configuration

   hpicfUSBPortConfig    OBJECT IDENTIFIER ::= { hpicfUSBPortMIB 1 }

   hpicfUSBPortStatus OBJECT-TYPE
      SYNTAX      INTEGER {
                       notPresent(0),
                       enabled(1),
                       disabled(2) }

      MAX-ACCESS  read-write
      STATUS      current
      DESCRIPTION "hpicfUSBPortStatus control whether or not
                   the USB port is enabled.
                      notPresent(0)  - USBPort is not present 
                      enabled(1)  - USBPort Enabled.
                      disabled(2) - USBPort Disabled.
                  "
      DEFVAL { enabled }
      ::= { hpicfUSBPortConfig 1 }

   hpicfUSBPortZeroPowerStatus OBJECT-TYPE
      SYNTAX      INTEGER {
                       powerUnavailable(0),
                       powerOff(1),
                       powerOn(2) }

      MAX-ACCESS  read-only
      STATUS      current
      DESCRIPTION "hpicfUSBPortZeroPowerStatus indicates if 
                   the USB port zero power is on or off.
                      powerUnavailable(0)  - USBPort power reading is 
                                             unavailable. 
                      powerOff(1)  - USBPort power is off. 
                      powerOn(2)   - USBPort power is on.
                  "
      DEFVAL { powerOn }
      ::= { hpicfUSBPortConfig 2 }

    -- Notifications
   hpicfUSBPortNotifications OBJECT IDENTIFIER ::= { hpicfUSBPortMIB 0 }

   hpicfUSBPortEnabled NOTIFICATION-TYPE
      STATUS             current
      DESCRIPTION
              "An hpicfUSBPortEnabled notification signifies that the
               SNMP entity, acting in an agent role, has detected that
               the hpicfUSBPortStatus object has transitioned into the 
               'enabled' state."
     ::= { hpicfUSBPortNotifications 1 }

   hpicfUSBPortDisabled NOTIFICATION-TYPE
      STATUS             current
      DESCRIPTION
              "An hpicfUSBPortDisabled notification signifies that the
               SNMP entity, acting in an agent role, has detected that
               the hpicfUSBPortStatus object has transitioned into the 
               'disabled' state."
     ::= { hpicfUSBPortNotifications 2 }

  -- USBPort conformance information

   hpicfUSBPortConformance
      OBJECT IDENTIFIER ::= { hpicfUSBPortMIB 2 }

   hpicfUSBPortGroups
     OBJECT IDENTIFIER ::= { hpicfUSBPortConformance 1 }

   hpicfUSBPortBaseGroup OBJECT-GROUP
      OBJECTS     { 
                   hpicfUSBPortStatus,
                   hpicfUSBPortZeroPowerStatus
                  }
      STATUS      current
      DESCRIPTION "A mandatory group with an object to enable
                   or disable the USB port."
      ::= { hpicfUSBPortGroups 1 }

      hpicfUSBPortNotificationGroup NOTIFICATION-GROUP 
        NOTIFICATIONS {
                        hpicfUSBPortEnabled,
                        hpicfUSBPortDisabled
                      }
        STATUS      current
        DESCRIPTION "The hpicfUSBPort MIB Notification Group."
        ::= { hpicfUSBPortGroups 2 }

   -- USBPort conformance statements

   hpicfUSBPortCompliances
      OBJECT IDENTIFIER ::= { hpicfUSBPortConformance 2 }

   hpicfUSBPortCompliance MODULE-COMPLIANCE
      STATUS      current
      DESCRIPTION "Compliance statement for HP ICF USBPort
                   configuration"
      MODULE
         MANDATORY-GROUPS { hpicfUSBPortBaseGroup,
                            hpicfUSBPortNotificationGroup }
      ::= { hpicfUSBPortCompliances 1 }

   END
