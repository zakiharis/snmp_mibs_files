-- ----------------------------------------------------------------------------
--                  HUAWEI MUSA Enterprise MIB   
--                                       MusaSys MIB 
--      Copyright (c) 1999-2002 HUA WEI TECH CO.,LTD,SHENZHEN.
--      All rights reserved.
--
--  Created by:  Xieqiang
--  Create date: 99-07-24
--  Modify date: 99-09-20
-- ----------------------------------------------------------------------------

HUAWEI-MUSA-MA5100-MIB DEFINITIONS ::= BEGIN
IMPORTS
        IpAddress,Counter
                        FROM RFC1155-SMI
        OBJECT-TYPE
                        FROM RFC-1212                
        musa
                        FROM HUAWEI-MIB;
    
    DisplayString ::= OCTET STRING                  
    
    hwMa5100Mib     OBJECT IDENTIFIER ::= { musa 5 }
    hwMusaSysMib    OBJECT IDENTIFIER ::= { hwMa5100Mib 1 } 
    hwMusaDevice    OBJECT IDENTIFIER ::= { hwMusaSysMib 1 }
    hwMusaEndOfMib  OBJECT IDENTIFIER ::= { hwMa5100Mib 100 } 
     
    -- ------------------------------------------------------------------------
    -- MUSA system admin
    --      Device admin table
    -- ------------------------------------------------------------------------ 

    hwMusaSysDate    OBJECT-TYPE
        SYNTAX   DisplayString
        ACCESS   read-write
        STATUS   mandatory
    DESCRIPTION
    "the system date,include year,month,day."
    ::= { hwMusaDevice 9}
    
    hwMusaSysTime    OBJECT-TYPE
        SYNTAX   DisplayString
        ACCESS   read-write
        STATUS   mandatory
    DESCRIPTION
    "the system time,include hours,minutes,seconds."
    ::= { hwMusaDevice 10}
    
    hwMusaSysCpuRatio   OBJECT-TYPE
        SYNTAX   INTEGER
        ACCESS   read-only
        STATUS   mandatory
    DESCRIPTION
    "the musa system cpu ratio."
    ::= { hwMusaDevice 11 }
    
    hwMusaHostVersion   OBJECT-TYPE
        SYNTAX   DisplayString
        ACCESS   read-only
        STATUS   mandatory
    DESCRIPTION
    "the musa system host software version."
    ::= { hwMusaDevice 12 }
    
    hwMusaResetSys    OBJECT-TYPE
        SYNTAX   INTEGER
        ACCESS   write-only
        STATUS   mandatory
    DESCRIPTION
    "Reset Musa device."
    ::= { hwMusaDevice 13}
    
    hwMusaIpAddr    OBJECT-TYPE
        SYNTAX   IpAddress
        ACCESS   read-write
        STATUS   mandatory
    DESCRIPTION
    "The Musa device's Ethernet IP address."
    ::= { hwMusaDevice 14}
    
    hwMusaIpMask        OBJECT-TYPE
        SYNTAX   IpAddress
        ACCESS   read-write
        STATUS   mandatory
    DESCRIPTION
    "The Musa IP SubNet Mask."
    ::= { hwMusaDevice 15}
    
    hwMusaGatewayIpAddr    OBJECT-TYPE
        SYNTAX   IpAddress
        ACCESS   read-write
        STATUS   mandatory
    DESCRIPTION
    "The Musa gateway's IP address."
    ::= { hwMusaDevice 16}
    
    hwMusaMacAddr    OBJECT-TYPE
        SYNTAX   DisplayString
        ACCESS   read-only
        STATUS   mandatory
    DESCRIPTION
    "The Musa Mac address."
    ::= { hwMusaDevice 17}
    
    
    hwMusaIpAddrPermitTable OBJECT-TYPE
        SYNTAX      SEQUENCE OF HwMusaIpAddrPermitEntry
        ACCESS      not-accessible
        STATUS      mandatory
    DESCRIPTION
    "This table contains IP Addr scope that Musa device permit access."
    ::= { hwMusaDevice 18 }      

    hwMusaIpAddrPermitEntry    OBJECT-TYPE
        SYNTAX      HwMusaIpAddrPermitEntry
        ACCESS      not-accessible
        STATUS      mandatory
    DESCRIPTION
    "This list contains IP addr scope."
    INDEX { hwMusaIpPermitTableId }
    ::= { hwMusaIpAddrPermitTable  1}

   HwMusaIpAddrPermitEntry    ::= SEQUENCE  {
            hwMusaIpPermitTableId   INTEGER,
            hwMusaIpAddrPermitOper  INTEGER,
            hwMusaPermitBeginIp     IpAddress,
            hwMusaPermitEndIp       IpAddress,
            hwMusaPermitIpMask      IpAddress
            }
            
    hwMusaIpPermitTableId OBJECT-TYPE
        SYNTAX  INTEGER
        ACCESS  read-only
        STATUS  mandatory
    DESCRIPTION
    "The IP Address table ID that permit access the Musa device."
    ::= { hwMusaIpAddrPermitEntry 1 }

    hwMusaIpAddrPermitOper OBJECT-TYPE
        SYNTAX  INTEGER{
                        add(0),
                        del(1),
                        modify(2),
                        query(3)
                        }
        ACCESS  read-write
        STATUS  mandatory
    DESCRIPTION
    "The operation that permit access the Musa device."
    ::= { hwMusaIpAddrPermitEntry 2 }

    hwMusaPermitBeginIp OBJECT-TYPE
        SYNTAX  IpAddress
        ACCESS  read-write
        STATUS  mandatory
    DESCRIPTION
    "The begin IP Address that permit access the Musa device."
    ::= { hwMusaIpAddrPermitEntry 3 }

    hwMusaPermitEndIp OBJECT-TYPE
        SYNTAX  IpAddress
        ACCESS  read-write
        STATUS  mandatory
    DESCRIPTION
    "The end Ip address that permit access the Musa device."
    ::= { hwMusaIpAddrPermitEntry 4 }
    
    hwMusaPermitIpMask OBJECT-TYPE
        SYNTAX  IpAddress
        ACCESS  read-write
        STATUS  mandatory
    DESCRIPTION
    "The Ip address subnet mask that permit access the Musa device."
    ::= { hwMusaIpAddrPermitEntry 5 }
    
    
    -- ------------------------------------------------------------------------
    hwMusaIpAddrRejectTable OBJECT-TYPE
        SYNTAX      SEQUENCE OF HwMusaIpAddrRejectEntry
        ACCESS      not-accessible
        STATUS      mandatory
    DESCRIPTION
    "This table contains IP Addr scope that Musa device reject access."
    ::= { hwMusaDevice 19 }

    hwMusaIpAddrRejectEntry    OBJECT-TYPE
        SYNTAX      HwMusaIpAddrRejectEntry
        ACCESS      not-accessible
        STATUS      mandatory
    DESCRIPTION
    "This list contains IP addr scope."
    INDEX { hwMusaIpRejectTableId }
    ::= { hwMusaIpAddrRejectTable  1}

   HwMusaIpAddrRejectEntry    ::= SEQUENCE  {
            hwMusaIpRejectTableId   INTEGER,
            hwMusaIpAddrRejectOper  INTEGER,
            hwMusaRejectBeginIp     IpAddress,
            hwMusaRejectEndIp       IpAddress,
            hwMusaRejectIpMask      IpAddress
            }
            
    hwMusaIpRejectTableId OBJECT-TYPE
        SYNTAX  INTEGER
        ACCESS  read-only
        STATUS  mandatory
    DESCRIPTION
    "The IP Address table ID that reject access the Musa device."
    ::= { hwMusaIpAddrRejectEntry 1 }

    hwMusaIpAddrRejectOper OBJECT-TYPE
        SYNTAX  INTEGER{
                        add(0),
                        del(1),
                        modify(2),
                        query(3)
                        }
        ACCESS  read-write
        STATUS  mandatory
    DESCRIPTION
    "The operation that reject access the Musa device."
    ::= { hwMusaIpAddrRejectEntry 2 }

    hwMusaRejectBeginIp OBJECT-TYPE
        SYNTAX  IpAddress
        ACCESS  read-write
        STATUS  mandatory
    DESCRIPTION
    "The begin IP Address that reject access the Musa device."
    ::= { hwMusaIpAddrRejectEntry 3 }

    hwMusaRejectEndIp OBJECT-TYPE
        SYNTAX  IpAddress
        ACCESS  read-write
        STATUS  mandatory
    DESCRIPTION
    "The end Ip address that reject access the Musa device."
    ::= { hwMusaIpAddrRejectEntry 4 }
    
    hwMusaRejectIpMask OBJECT-TYPE
        SYNTAX  IpAddress
        ACCESS  read-write
        STATUS  mandatory
    DESCRIPTION
    "The Ip address subnet mask that reject access the Musa device."
    ::= { hwMusaIpAddrRejectEntry 5 }

    hwMusaAtmIpAddr    OBJECT-TYPE
        SYNTAX   IpAddress
        ACCESS   read-write
        STATUS   mandatory
    DESCRIPTION
    "The Musa device's IP address."
    ::= { hwMusaDevice 20}
    
    hwMusaAtmIpMask        OBJECT-TYPE
        SYNTAX   IpAddress
        ACCESS   read-write
        STATUS   mandatory
    DESCRIPTION
    "The Musa IP SubNet Mask."
    ::= { hwMusaDevice 21}
    
    hwMusaMtu    OBJECT-TYPE
        SYNTAX   INTEGER
        ACCESS   read-write
        STATUS   mandatory
    DESCRIPTION
    "The Musa Mtu value."
    ::= { hwMusaDevice 22}
    
   hwMusaOpticConvergentRate    OBJECT-TYPE
       SYNTAX   INTEGER
       ACCESS   read-write
       STATUS   mandatory
   DESCRIPTION
   "The bandwidth convergentrate."
   ::= { hwMusaDevice 23 }

    hwMusaCellbusID    OBJECT-TYPE
       SYNTAX   INTEGER{ ma5100(1),
		                 ma5103(2) 
		                }
       ACCESS   read-only
       STATUS   mandatory
   DESCRIPTION
   "The Cellbus ID."
   ::= { hwMusaDevice 24 }
   
   hwMusaResetSlaveMMX   OBJECT-TYPE
       SYNTAX   INTEGER{ loaddata(1),
		         noloaddata(2) 
		       }
       ACCESS   write-only
       STATUS   mandatory
   DESCRIPTION
   "Reset SLAVE MMX."
   ::= { hwMusaDevice 25 }
   
   hwMusaBiosVersion   OBJECT-TYPE
       SYNTAX   INTEGER
       ACCESS   read-only
       STATUS   mandatory
   DESCRIPTION
   "MMX Bios Version."
   ::= { hwMusaDevice 26 }
   
   hwMusaEthernetFirewall   OBJECT-TYPE
       SYNTAX   INTEGER{ enable(1),
		                 disable(2) 
		                }
       ACCESS   read-write
       STATUS   mandatory
   DESCRIPTION
   "MMX ethernet firewall switch."
   ::= { hwMusaDevice 27 }
   
    -- ------------------------------------------------------------------------
    -- NMS PVC config table
    -- ------------------------------------------------------------------------
    hwMusaNmsPvcConfTable    OBJECT-TYPE
        SYNTAX      SEQUENCE OF HwMusaNmsPvcConfEntry
        ACCESS      not-accessible
        STATUS      mandatory
    DESCRIPTION
    "Musa Nms PVC configuration table."
    ::= { hwMusaSysMib 3 }

   hwMusaNmsPvcConfEntry    OBJECT-TYPE
        SYNTAX         HwMusaNmsPvcConfEntry
        ACCESS         not-accessible
        STATUS         mandatory
    DESCRIPTION
    "This list contains Musa Nms Pvc Configuration
     parameters and variables."
    INDEX { hwMusaNmsPvcIndex}
    ::= { hwMusaNmsPvcConfTable  1 }

   HwMusaNmsPvcConfEntry    ::= SEQUENCE  {
            hwMusaNmsPvcIndex     INTEGER,
            hwMusaNmsRelayVpi     INTEGER,
            hwMusaNmsRelayVci     INTEGER,
            hwMusaNmsIp           IpAddress,
            hwMusaNmsPvcOper      INTEGER,
            hwMusaNmsRxTraffic    INTEGER,
            hwMusaNmsTxTraffic    INTEGER,
            hwMusaNmsSarVci       INTEGER,
            hwMusaNmsLLCVC        INTEGER,
            hwMusaNmsENCAP        INTEGER,
            hwMusaNmsFrameId      INTEGER,
            hwMusaNmsSlotId       INTEGER,
            hwMusaNmsPortVlanId   INTEGER
            }
    
    hwMusaNmsPvcIndex   OBJECT-TYPE
        SYNTAX          INTEGER
        ACCESS          not-accessible
        STATUS          mandatory
    DESCRIPTION
    "Nms Pvc index."
    ::= { hwMusaNmsPvcConfEntry  1 }
    
    hwMusaNmsRelayVpi OBJECT-TYPE
        SYNTAX          INTEGER
        ACCESS          read-write
        STATUS          mandatory
    DESCRIPTION
    "Nms Relay Pvc Vpi index."
    ::= { hwMusaNmsPvcConfEntry  2 }    

    hwMusaNmsRelayVci OBJECT-TYPE
        SYNTAX          INTEGER
        ACCESS          read-write
        STATUS          mandatory
    DESCRIPTION
    "Nms Relay Pvc Vci index."
    ::= { hwMusaNmsPvcConfEntry  3 }    
   
    hwMusaNmsIp     OBJECT-TYPE
        SYNTAX          IpAddress
        ACCESS          read-write
        STATUS          mandatory
    DESCRIPTION
    "Nms IP address."
    ::= { hwMusaNmsPvcConfEntry  4 }    
    
    hwMusaNmsPvcOper  OBJECT-TYPE
        SYNTAX          INTEGER{
                            add(0),
                            del(1)
                          }
        ACCESS          read-write
        STATUS          mandatory
    DESCRIPTION
    "Nms operate state,include:add/del."
    ::= { hwMusaNmsPvcConfEntry  6 }


    hwMusaNmsRxTraffic  OBJECT-TYPE
        SYNTAX          INTEGER
        ACCESS          read-write
        STATUS          mandatory
    DESCRIPTION
    "Nms PVC's receive traffic index."
    ::= { hwMusaNmsPvcConfEntry  8 }
    

    hwMusaNmsTxTraffic  OBJECT-TYPE
        SYNTAX          INTEGER
        ACCESS          read-write
        STATUS          mandatory
    DESCRIPTION
    "Nms PVC's transmit traffic index."
    ::= { hwMusaNmsPvcConfEntry  9 }
    
    hwMusaNmsSarVci   OBJECT-TYPE
       SYNTAX           INTEGER
       ACCESS           read-write
       STATUS           mandatory
    DESCRIPTION
    "Nms PVC's SAR VCI"
    ::= { hwMusaNmsPvcConfEntry  10 }
    
    hwMusaNmsLLCVC  OBJECT-TYPE
        SYNTAX          INTEGER{
                            llc(1),
                            vc(2)
                          }
        ACCESS          read-write
        STATUS          mandatory
    DESCRIPTION
    "1483B encapsulation state,include:llc/vc."
    ::= { hwMusaNmsPvcConfEntry  11 }

    hwMusaNmsENCAP  OBJECT-TYPE
        SYNTAX          INTEGER{
                            eipoa(0),
                            e1483B(1)
                          }
        ACCESS          read-write
        STATUS          mandatory
    DESCRIPTION
    "Nms encapsulation type,include:ipoa/1483B."
    ::= { hwMusaNmsPvcConfEntry  12 }

    hwMusaNmsFrameId  OBJECT-TYPE
        SYNTAX          INTEGER
        ACCESS          read-write
        STATUS          mandatory
    DESCRIPTION
    "Nms PVC's DstFrameId."
    ::= { hwMusaNmsPvcConfEntry  14 }
    
    hwMusaNmsSlotId  OBJECT-TYPE
        SYNTAX          INTEGER
        ACCESS          read-write
        STATUS          mandatory
    DESCRIPTION
    "Nms PVC's DstSlotId."
    ::= { hwMusaNmsPvcConfEntry  15 }

    hwMusaNmsPortVlanId OBJECT-TYPE
        SYNTAX          INTEGER
        ACCESS          read-write
        STATUS          mandatory
    DESCRIPTION
    "Nms PVC's DstPortVlanId."
    ::= { hwMusaNmsPvcConfEntry  16 }
  
    -- ------------------------------------------------------------------------
    -- NMS parameters config table
    -- ------------------------------------------------------------------------
    hwMusaNmsParaConfTable    OBJECT-TYPE
        SYNTAX      SEQUENCE OF HwMusaNmsParaConfEntry
        ACCESS      not-accessible
        STATUS      mandatory
    DESCRIPTION
    "Musa Nms PVC configuration table."
    ::= { hwMusaSysMib 5 }

   hwMusaNmsParaConfEntry    OBJECT-TYPE
        SYNTAX         HwMusaNmsParaConfEntry
        ACCESS         not-accessible
        STATUS         mandatory
    DESCRIPTION
    "This list contains Musa Nms Para Configuration
     parameters and variables."
    INDEX { hwMusaNmsID }
    ::= { hwMusaNmsParaConfTable  1 }

   HwMusaNmsParaConfEntry    ::= SEQUENCE  {
            hwMusaNmsID         INTEGER,
            hwMusaNmsOperState  INTEGER,
            hwMusaNmsName       DisplayString,
            hwMusaNmsIpAddr     IpAddress,
            hwMusaGetCommunity  DisplayString,
            hwMusaSetCommunity  DisplayString,
            hwMusaTrapPort      INTEGER,
            hwMusaGetSetPort    INTEGER,
            hwMusaNmsStatus     INTEGER,
            hwMusaNmsStyle      INTEGER
            }
    
    hwMusaNmsID       OBJECT-TYPE
        SYNTAX          INTEGER (0..7)
        ACCESS          not-accessible
        STATUS          mandatory
    DESCRIPTION
    "Nms ID,from 0 to 7."
    ::= { hwMusaNmsParaConfEntry  1 }
    
    hwMusaNmsOperState  OBJECT-TYPE
        SYNTAX          INTEGER{
                            add(0),
                            del(1),
                            modify(2),
                            active(4),
                            deactive(5)
                          }
        ACCESS          read-write
        STATUS          mandatory
    DESCRIPTION
    "Nms operate state,include:add/del/modify/act/deact."
    ::= { hwMusaNmsParaConfEntry  2 }
    
    hwMusaNmsName       OBJECT-TYPE
        SYNTAX          DisplayString
        ACCESS          read-write
        STATUS          mandatory
    DESCRIPTION
    "Nms name."
    ::= { hwMusaNmsParaConfEntry  3 }
    
    hwMusaNmsIpAddr    OBJECT-TYPE
        SYNTAX          IpAddress
        ACCESS          read-write
        STATUS          mandatory
    DESCRIPTION
    "Nms IP address."
    ::= { hwMusaNmsParaConfEntry  4 }    
    
    hwMusaGetCommunity  OBJECT-TYPE
        SYNTAX          DisplayString
        ACCESS          read-write
        STATUS          mandatory
    DESCRIPTION
    "Snmp get community name."
    ::= { hwMusaNmsParaConfEntry  5 }
        
    hwMusaSetCommunity  OBJECT-TYPE
        SYNTAX          DisplayString
        ACCESS          read-write
        STATUS          mandatory
    DESCRIPTION
    "Snmp set community name."
    ::= { hwMusaNmsParaConfEntry  6 }
    
    hwMusaTrapPort      OBJECT-TYPE
        SYNTAX          INTEGER
        ACCESS          read-write
        STATUS          mandatory
    DESCRIPTION
    "Snmp trap port."
    ::= { hwMusaNmsParaConfEntry  7 }
    
    hwMusaGetSetPort    OBJECT-TYPE
        SYNTAX          INTEGER
        ACCESS          read-write
        STATUS          mandatory
    DESCRIPTION
    "Snmp get/set port."
    ::= { hwMusaNmsParaConfEntry  8 }
            
    hwMusaNmsStatus     OBJECT-TYPE
        SYNTAX          INTEGER{
                            active(1),
                            deactive(2),
                            commfail(3),
                            uninstall(4)
                            }
        ACCESS          read-only
        STATUS          mandatory
    DESCRIPTION
    "Nms status."
    ::= { hwMusaNmsParaConfEntry  9 }       
    
    hwMusaNmsStyle     OBJECT-TYPE
        SYNTAX          INTEGER{
                            bandin(0),
                            bandout(1)
                            }
        ACCESS          read-write
        STATUS          mandatory
    DESCRIPTION
    "Nms admin style in-band or out-band."
    ::= { hwMusaNmsParaConfEntry  10 }
        
   -- -------------------------------------------------------------------------
   --  Frame slot description table
   -- ------------------------------------------------------------------------- 
    hwMusaSlotGroup OBJECT IDENTIFIER ::= { hwMusaSysMib  6 }
    hwMusaShelf     OBJECT IDENTIFIER ::= { hwMusaSlotGroup 1 }
    hwMusaFrame     OBJECT IDENTIFIER ::= { hwMusaSlotGroup 2 }
    hwMusaSlot      OBJECT IDENTIFIER ::= { hwMusaSlotGroup 3 }
    -- -------------------------------------------------------------------------
    --  Shelf information table
    -- -------------------------------------------------------------------------
    hwMusaShelfNumber   OBJECT-TYPE
        SYNTAX      INTEGER
        ACCESS      read-only
        STATUS      mandatory
    DESCRIPTION  
    "Musa shelf numbers."
    ::= { hwMusaShelf 1 }
    
   hwMusaShelfConfTable    OBJECT-TYPE
        SYNTAX      SEQUENCE OF HwMusaShelfConfEntry
        ACCESS      not-accessible
        STATUS      mandatory
    DESCRIPTION  
    "This table contains Musa slot configuration
     parameters, one entry per Musa slot."
    ::= { hwMusaShelf 2 }

   hwMusaShelfConfEntry    OBJECT-TYPE
        SYNTAX         HwMusaShelfConfEntry
        ACCESS         not-accessible
        STATUS         mandatory
    DESCRIPTION
    "This list contains Musa shelf configuration parameters and status variables."
    INDEX { hwMusaShelfIndex }
    ::= { hwMusaShelfConfTable  1}

   HwMusaShelfConfEntry    ::= SEQUENCE  {
            hwMusaShelfIndex    INTEGER,
            hwMusaShelfType     INTEGER,
            hwMusaShelfName     DisplayString,
            hwMusaFrameNumbers  INTEGER
            }
            
   hwMusaShelfIndex OBJECT-TYPE
        SYNTAX     INTEGER
        ACCESS     not-accessible
        STATUS     mandatory
    DESCRIPTION
    "the Musa shelf number. "
    ::= { hwMusaShelfConfEntry 1}

    hwMusaShelfType OBJECT-TYPE
        SYNTAX     INTEGER {
                     other(1),
                     empty(2)
                    }
        ACCESS     read-only
        STATUS     mandatory
    DESCRIPTION
    "The Musa shelf type."
    ::= { hwMusaShelfConfEntry 2}
    
    hwMusaShelfName OBJECT-TYPE
        SYNTAX     DisplayString
        ACCESS     read-only
        STATUS     mandatory
    DESCRIPTION
    "The Musa shelf name."
    ::= { hwMusaShelfConfEntry 3}

    hwMusaFrameNumbers  OBJECT-TYPE
        SYNTAX  INTEGER(0..255)
        ACCESS  read-only
        STATUS  mandatory
    DESCRIPTION
    "The frame numbers belong to this shelf."
    ::= { hwMusaShelfConfEntry 4}
   -- ----------------------------------------------------------------------------
   -- Frame information
   -- ----------------------------------------------------------------------------
   hwMusaFrameNumber    OBJECT-TYPE
        SYNTAX      INTEGER
        ACCESS      read-only
        STATUS      mandatory
    DESCRIPTION  
    "Musa frame numbers."
    ::= { hwMusaFrame 1 }
    
   hwMusaFrameConfTable    OBJECT-TYPE
        SYNTAX      SEQUENCE OF HwMusaFrameConfEntry
        ACCESS      not-accessible
        STATUS      mandatory
    DESCRIPTION  
    "This table contains Musa Frame configuration parameters."
    ::= { hwMusaFrame 2 }

   hwMusaFrameConfEntry    OBJECT-TYPE
        SYNTAX         HwMusaFrameConfEntry
        ACCESS         not-accessible
        STATUS         mandatory
    DESCRIPTION
    "This list contains Musa Frame configuration parameters and status variables."
    INDEX { hwMusaShelfIndex,
            hwMusaFrameIndex }
    ::= { hwMusaFrameConfTable  1}

   HwMusaFrameConfEntry    ::= SEQUENCE  {
            hwMusaFrameIndex                    INTEGER,
            hwMusaFrameType                     INTEGER,
            hwMusaFrameName                     DisplayString,
            hwMusaSlotNumbers                   INTEGER,
            hwMusaFrameBandWidth                INTEGER, 
            hwMusaFrameUsedBandWidth            INTEGER
            }
            
   hwMusaFrameIndex OBJECT-TYPE
        SYNTAX     INTEGER
        ACCESS     not-accessible
        STATUS     mandatory
    DESCRIPTION
    "The Musa Frame number."
    ::= { hwMusaFrameConfEntry 1}

    hwMusaFrameType OBJECT-TYPE
        SYNTAX     INTEGER {
            other(1),
            empty(2)
        }
        ACCESS     read-only
        STATUS     mandatory
    DESCRIPTION
    "The Musa Frame type."
    ::= { hwMusaFrameConfEntry 2}
    
    hwMusaFrameName OBJECT-TYPE
        SYNTAX     DisplayString(SIZE(0..20)) 
        ACCESS     read-write
        STATUS     mandatory
    DESCRIPTION
    "The Musa Frame name."
    ::= { hwMusaFrameConfEntry 3}

    hwMusaSlotNumbers   OBJECT-TYPE
        SYNTAX  INTEGER(0..255)
        ACCESS  read-only
        STATUS  mandatory
    DESCRIPTION
    "The Slot numbers belong to this frame."
    ::= { hwMusaFrameConfEntry 4}
    
    hwMusaFrameBandWidth  OBJECT-TYPE
        SYNTAX   INTEGER
        ACCESS   read-only
        STATUS   mandatory
    DESCRIPTION
    "The bandwidth(kpbs) of frame's backplane."
    ::= { hwMusaFrameConfEntry 5}
    
    hwMusaFrameUsedBandWidth    OBJECT-TYPE
        SYNTAX   INTEGER
        ACCESS   read-only
        STATUS   mandatory
    DESCRIPTION
    "The current used bandwidth(kpbs) of frame's backplane."
    ::= { hwMusaFrameConfEntry 6 }
    
   -- --------------------------------------------------------------------- 
   -- Slot description table
   -- ---------------------------------------------------------------------
   hwMusaSlotNumber OBJECT-TYPE
        SYNTAX      INTEGER
        ACCESS      read-only
        STATUS      mandatory
    DESCRIPTION  
    "Musa slot numbers."
    ::= { hwMusaSlot 1 }
    
    hwMusaSlotConfTable    OBJECT-TYPE
        SYNTAX      SEQUENCE OF HwMusaSlotConfEntry
        ACCESS      not-accessible
        STATUS      mandatory
    DESCRIPTION  
    "This table contains Musa slot configuration
     parameters, one entry per Musa slot."
    ::= { hwMusaSlot 2 }

   hwMusaSlotConfEntry    OBJECT-TYPE
        SYNTAX         HwMusaSlotConfEntry
        ACCESS         not-accessible
        STATUS         mandatory
    DESCRIPTION
    "This list contains Musa slot configuration parameters and status variables."
    INDEX { 
  --        hwMusaShelfIndex,
            hwMusaFrameIndex,
            hwMusaSlotIndex }
    ::= { hwMusaSlotConfTable  1}

   HwMusaSlotConfEntry    ::= SEQUENCE  {
            hwMusaSlotIndex             INTEGER,
            hwMusaSlotCardType          INTEGER,
            hwMusaSlotCardSerial        INTEGER,
            hwMusaSlotCardVersion       DisplayString,
            hwMusaSlotIpAddress         IpAddress,
            hwMusaSlotCardAdminStatus   INTEGER,
            hwMusaSlotCardOperStatus    INTEGER,
            hwMusaSlotDescript          DisplayString,
            hwMusaBoardCellLossPriority INTEGER,
            hwMusaBoardMaxBandwidth     INTEGER,
            hwMusaCpuOccupyRate         INTEGER,
            hwMusaQueryMemory           DisplayString,
            hwMusaLoadProtocol          INTEGER,
            hwMusaLoadContent           INTEGER,
            hwMusaLoadTftpServerIp      IpAddress,
            hwMusaLoadFileName          DisplayString,
            hwMusaLoadOperType          INTEGER,
            hwMusaSlotUpBandWidth       INTEGER,
            hwMusaSlotDownBandWidth     INTEGER,
            hwMusaSlotUsedUpBandWidth   INTEGER,
            hwMusaSlotUsedDownBandWidth INTEGER,
            hwMusaSlotUpPracticalBandWidth  INTEGER, 
            hwMusaSlotDownPracticalBandWidth  INTEGER 
            }
            
   hwMusaSlotIndex  OBJECT-TYPE
        SYNTAX     INTEGER(0..15)
        ACCESS     not-accessible
        STATUS     mandatory
    DESCRIPTION
    "the Musa slot number."
    ::= { hwMusaSlotConfEntry 1 }
    
   hwMusaSlotCardType   OBJECT-TYPE
        SYNTAX     INTEGER{
                    null(0),
                    mmx(1),
                    smx(2),
                    adl(3),
                    lanb(4),
                    lana(5),
                    cesa(6),
                    cesb(7),
                    spl(8),
                    fra(9),
                    adlb(10),
                    unknown(11),
                    splb(12),
                    sep(13),
                    smxa(14),
                    smxb(15),
                    pots(16),
                    splc(18),
                    lan(19),
                    adlc(21),
                    adld(25)
                    }
        ACCESS     read-only
        STATUS     mandatory
    DESCRIPTION
    "the Musa slot card type.
    The whole 16 bits is distributed to two parts. The whole low 8 bits is the type of board.
    In the high 8 bits, the whole high 4 bits is the type of the first subboard, 
    the whole low 4 bits is the type of the second subboard.
    The subboard types of all kinds of board are listed below:
    To mmx:
    0x00 MMX_NO_SUBBOARD  
    0x01 MMX_OIM_S155SM:  
    0x02 MMX_OIM_S155MM:  
    0x03 MMX_OIM_D155SM:  
    0x04 MMX_OIM_D155MM:  
    0x05 MMX_APON_R:      
    0x06 MMX_APON_C:      
    0x07: MMX_IMA_TYPE     
    0x08: MMX_IMA_TYPE_120 
    
    To frc:
    0x00 FRC_NON_SUBBOARD
    0x01 FRC_E1       
    0x02 FRC_T1       
    0x03 FRC_V35      
    0x04: FRC_E1_120   
    
    To cesc:
    0x00 CESC_NON_SUBBOARD
    0x01 CESC_E1      
    0x02 CESC_T1      
    0x03 CESC_V35     
    0x04: CESC_E1_120  
    
    To aiua:
    0x00 AIU_NO_SUBBOARD
    0x01 AIU_155M_SINGLE_PATH  
    0x02 AIU_155M_SINGLE_PATH_M
    0x03 AIU_155M_DOUBLE_PATH  
    0x04 AIU_155M_DOUBLE_PATH_M
    0x05 AIU_622M            
    0x06 AIU_APON_C          
    0x07 AIU_APON_R          
    0x08 AIU_E3              
    0x09: AIU_IMA             
    0x0a: AIU_IMA_120"
    ::= { hwMusaSlotConfEntry 2 }
    
   hwMusaSlotCardSerial   OBJECT-TYPE
        SYNTAX     INTEGER
        ACCESS     read-only
        STATUS     mandatory
    DESCRIPTION
    "The Musa slot card serial."
    ::= { hwMusaSlotConfEntry 3 }
    
   hwMusaSlotCardVersion  OBJECT-TYPE
        SYNTAX     DisplayString
        ACCESS     read-only
        STATUS     mandatory
    DESCRIPTION
    "The Musa slot card version."
    ::= { hwMusaSlotConfEntry 4 }
    
    hwMusaSlotIpAddress  OBJECT-TYPE
        SYNTAX     IpAddress
        ACCESS     read-write
        STATUS     mandatory
    DESCRIPTION
    "The Musa slot card Ip address."
    ::= { hwMusaSlotConfEntry 5 }
    
   hwMusaSlotCardAdminStatus OBJECT-TYPE
        SYNTAX     INTEGER{                               
                           noinstall(0), -- NOINSTALL     
                           normal(1),    -- NORMAL        
                           fault(2),     -- FAULT         
                           mainnormal(3),-- MAINNORMAL    
                           mainfault(4), -- MAINERROR     
                           baknormal(5), -- BAKNORMAL     
                           bakfault(6),  -- BAKERROR      
                           forbid(7),    -- FORBID        
                           config(8),    -- Configing    
                           online(10),   -- online       
                           none(11),     --none          
                           commok(12),   --communication ok
                           commfail(13)  --communication fail
                          }
        ACCESS     read-only
        STATUS     mandatory
    DESCRIPTION
    "The Musa slot card State."
    ::= { hwMusaSlotConfEntry 6 }

    hwMusaSlotCardOperStatus     OBJECT-TYPE
    SYNTAX  INTEGER{
                    del(0),
                    add(1),
                    reset(2),
                    use(3),
                    nouse(4),
                    inverse(5),
                    mmxswitchover(6),
                    delmmxsubboard(7),
                    addaiusubboard(8),
                    delaiusubboard(9)
                    } 
    ACCESS  write-only
    STATUS  mandatory
    DESCRIPTION
     "The slot card operate status."
    ::= { hwMusaSlotConfEntry 7 }
    
    hwMusaSlotDescript    OBJECT-TYPE
    SYNTAX  DisplayString 
    ACCESS  read-only
    STATUS  mandatory
    DESCRIPTION
     "The sl1ot card description."
    ::= { hwMusaSlotConfEntry 8 }
        
   hwMusaBoardCellLossPriority    OBJECT-TYPE
    SYNTAX  INTEGER{
                   low(0),
                   high(1)
                   }
    ACCESS  read-write
    STATUS  mandatory
    DESCRIPTION
     "The board service priority."
    ::= { hwMusaSlotConfEntry 9 }
    
    hwMusaBoardMaxBandwidth  OBJECT-TYPE
    SYNTAX  INTEGER{
                    b-155M(0),
                    b-80M(1),
                    b-20M(2),
                    b-4M(3)
                   }
    ACCESS  read-write
    STATUS  mandatory
    DESCRIPTION
     "The board Max outburst cell rate."
    ::= { hwMusaSlotConfEntry 10 }
    
    hwMusaCpuOccupyRate     OBJECT-TYPE
    SYNTAX  INTEGER 
    ACCESS  read-only
    STATUS  mandatory
    DESCRIPTION
     "The board cpu occupy rate."
    ::= { hwMusaSlotConfEntry 11 }
    
    hwMusaQueryMemory     OBJECT-TYPE
    SYNTAX  DisplayString 
    ACCESS  write-only
    STATUS  mandatory
    DESCRIPTION
     "Query the board memory."
    ::= { hwMusaSlotConfEntry 12 }
               
    hwMusaLoadProtocol    OBJECT-TYPE
    SYNTAX  INTEGER{
                tftp(0)                
                }
    ACCESS  write-only
    STATUS  mandatory
    DESCRIPTION
     "The protocal of load file:tftp."
    ::= { hwMusaSlotConfEntry 13 }
    
    hwMusaLoadContent    OBJECT-TYPE
    SYNTAX  INTEGER{
                program(6),
                data(8),
                fpga(7)
                } 
    ACCESS  write-only
    STATUS  mandatory
    DESCRIPTION
     "The type of load file:program or data."
    ::= { hwMusaSlotConfEntry 14 }
    
    hwMusaLoadTftpServerIp  OBJECT-TYPE
    SYNTAX  IpAddress
    ACCESS  write-only
    STATUS  mandatory
    DESCRIPTION
     "The NMS IP address."
    ::= { hwMusaSlotConfEntry 15 }
    
    hwMusaLoadFileName  OBJECT-TYPE
    SYNTAX  DisplayString
    ACCESS  write-only
    STATUS  mandatory
    DESCRIPTION
     "The load file name."
    ::= { hwMusaSlotConfEntry 16 }
                 
   hwMusaLoadOperType    OBJECT-TYPE
    SYNTAX  INTEGER{
                load(0),
                upback(1),
                downback(2),
                rollback(3),
                clearflash(4)
                } 
    ACCESS  write-only
    STATUS  mandatory
    DESCRIPTION
     "The type of back data."
    ::= { hwMusaSlotConfEntry 17 }
     
    hwMusaSlotUpBandWidth  OBJECT-TYPE
        SYNTAX   INTEGER
        ACCESS   read-write
        STATUS   mandatory
    DESCRIPTION
    "The bandwidth(kpbs) of Up slot."
    ::= { hwMusaSlotConfEntry 18 }
    
    hwMusaSlotDownBandWidth  OBJECT-TYPE
        SYNTAX   INTEGER
        ACCESS   read-write
        STATUS   mandatory
    DESCRIPTION
    "The main bandwidth(kpbs) of Down slot."
    ::= { hwMusaSlotConfEntry 19 }
    
    hwMusaSlotUsedUpBandWidth    OBJECT-TYPE
        SYNTAX   INTEGER
        ACCESS   read-only
        STATUS   mandatory
    DESCRIPTION
    "The current used up bandwidth(kpbs) of slot."
    ::= { hwMusaSlotConfEntry 20 }
    
    hwMusaSlotUsedDownBandWidth  OBJECT-TYPE
        SYNTAX   INTEGER
        ACCESS   read-only
        STATUS   mandatory
    DESCRIPTION
    "The current used down bandwidth(kpbs) of slot."
    ::= { hwMusaSlotConfEntry 21 }
    
    hwMusaSlotUpPracticalBandWidth  OBJECT-TYPE
        SYNTAX   INTEGER
        ACCESS   read-only
        STATUS   mandatory
    DESCRIPTION
    "The practical up bandwidth(kpbs) of slot."
         ::= { hwMusaSlotConfEntry 22 }
    
    hwMusaSlotDownPracticalBandWidth  OBJECT-TYPE
        SYNTAX   INTEGER
        ACCESS   read-only
        STATUS   mandatory
    DESCRIPTION
    "The practical down bandwidth(kpbs) of slot."
         ::= { hwMusaSlotConfEntry 23 }
    
    
    -- ------------------------------------------------------------------------
    -- OAM admin parameters
    -- ------------------------------------------------------------------------
    hwMusaOamGroup  OBJECT IDENTIFIER ::= { hwMusaSysMib 7 }
    
    hwMusaOimPhyTable    OBJECT-TYPE
        SYNTAX      SEQUENCE OF HwMusaOimPhyEntry
        ACCESS      not-accessible
        STATUS      mandatory
    DESCRIPTION
    "Musa OIM physical table."
    ::= { hwMusaOamGroup 1 }
   
    hwMusaOimPhyEntry    OBJECT-TYPE
        SYNTAX         HwMusaOimPhyEntry
        ACCESS         not-accessible
        STATUS         mandatory
    DESCRIPTION
    "This list contains Musa OIM physical variables."
    INDEX { hwMusaFrameIndex,
            hwMusaSlotIndex,
            hwOIMPortIndex}
    ::= { hwMusaOimPhyTable  1 } 
    
  
    HwMusaOimPhyEntry    ::= SEQUENCE  {
            hwOIMPortIndex          INTEGER,
            hwMusaSetSrcLoop            INTEGER,
            hwMusaSetLineLoop           INTEGER,
            hwMusaSetUtopiaLoop             INTEGER,
            hwMusaInsertLOF         INTEGER,
            hwMusaInsertLOS         INTEGER,
            hwMusaInsertBIP1            INTEGER,
            hwMusaInsertBIP2         INTEGER,
            hwMusaInsertBIP3            INTEGER,
            hwMusaInsertLAIS            INTEGER,
            hwMusaInsertPAIS            INTEGER,
            hwMusaInsertLRDI            INTEGER
            } 
  
    hwOIMPortIndex   OBJECT-TYPE
        SYNTAX     INTEGER
        ACCESS     not-accessible
        STATUS     mandatory
    DESCRIPTION
    "the Musa OIM number.(0--1) "
    ::= { hwMusaOimPhyEntry 1}
    
    hwMusaSetSrcLoop OBJECT-TYPE
        SYNTAX      INTEGER
                          {
                          notloop(0),
                          loop(1)
                          }
        ACCESS      read-write
        STATUS      mandatory
    DESCRIPTION
    "set source loop."
    ::= { hwMusaOimPhyEntry 2 }

    hwMusaSetLineLoop OBJECT-TYPE
        SYNTAX      INTEGER
                          {
                          notloop(0),
                          loop(1)
                          }
        ACCESS      read-write
        STATUS      mandatory
    DESCRIPTION
    "set line loop."
    ::= { hwMusaOimPhyEntry 3 }
    
    hwMusaSetUtopiaLoop OBJECT-TYPE
        SYNTAX      INTEGER
                          {
                          notloop(0),
                          loop(1)
                          }
        ACCESS      read-write
        STATUS      mandatory
    DESCRIPTION
    "set Utopia loop."
    ::= { hwMusaOimPhyEntry 4 }    
            
    hwMusaInsertLOF OBJECT-TYPE
        SYNTAX      INTEGER
                          {
                          notinsert(0),
                          insert(1)
                          }
        ACCESS      read-write
        STATUS      mandatory
    DESCRIPTION
    "insert LOF warning at the optic port."
    ::= { hwMusaOimPhyEntry 5 }
        
    hwMusaInsertLOS OBJECT-TYPE
        SYNTAX      INTEGER
                          {
                          notinsert(0),
                          insert(1)
                          }
        ACCESS      read-write
        STATUS      mandatory
    DESCRIPTION
    "insert LOS warning at the optic port."
    ::= { hwMusaOimPhyEntry 6 }
    
    hwMusaInsertBIP1 OBJECT-TYPE
        SYNTAX      INTEGER
        ACCESS      write-only
        STATUS      mandatory
    DESCRIPTION
    "Insert BIP1(SBIP) errorcode at the optic port."
    ::= { hwMusaOimPhyEntry 7 }

    hwMusaInsertBIP2 OBJECT-TYPE
        SYNTAX      INTEGER
        ACCESS      write-only
        STATUS      mandatory
    DESCRIPTION
    "Insert BIP2(LBIP) errorcode at the optic port."
    ::= { hwMusaOimPhyEntry 8 }

    hwMusaInsertBIP3 OBJECT-TYPE
        SYNTAX      INTEGER
        ACCESS      write-only
        STATUS      mandatory
    DESCRIPTION
    "Insert BIP3(PBIP) errorcode at the optic port."
    ::= { hwMusaOimPhyEntry 9 }
    
    hwMusaInsertLAIS OBJECT-TYPE
        SYNTAX      INTEGER
                          {
                          notinsert(0),
                          insert(1)
                          }
        ACCESS      read-write
        STATUS      mandatory
    DESCRIPTION
    "Insert LAIS warning at the optic port."
    ::= { hwMusaOimPhyEntry 10 }

    hwMusaInsertPAIS OBJECT-TYPE
        SYNTAX      INTEGER
                          {
                          notinsert(0),
                          insert(1)
                          }
        ACCESS      read-write
        STATUS      mandatory
    DESCRIPTION
    "Insert PAIS warning at the optic port."
    ::= { hwMusaOimPhyEntry 11 }

    hwMusaInsertLRDI OBJECT-TYPE
        SYNTAX      INTEGER
                          {
                          notinsert(0),
                          insert(1)
                          }
        ACCESS      read-write
        STATUS      mandatory
    DESCRIPTION
    "Insert LRDI warning at the optic port."
    ::= { hwMusaOimPhyEntry 12 }

   -- -------------------------------------------------------------------------
   --  OAM optic performance
   -- -------------------------------------------------------------------------
    hwMusaOimOpticTable    OBJECT-TYPE
        SYNTAX      SEQUENCE OF HwMusaOimOpticEntry
        ACCESS      not-accessible
        STATUS      mandatory
    DESCRIPTION
    "Musa OIM optical performance table."
    ::= { hwMusaOamGroup 2 }
   
    hwMusaOimOpticEntry    OBJECT-TYPE
        SYNTAX         HwMusaOimOpticEntry
        ACCESS         not-accessible
        STATUS         mandatory
    DESCRIPTION
    "This list contains Musa OIM optical performance variables."
    INDEX { hwMusaFrameIndex,
            hwMusaSlotIndex,
            hwOIMPortIndex}
    ::= { hwMusaOimOpticTable  1 } 
    
  
    HwMusaOimOpticEntry    ::= SEQUENCE  {
            hwMusaQueryCurBIP1              Counter,
            hwMusaQueryCurBIP2              Counter,
            hwMusaQueryCurBIP3              Counter,
            hwMusaQueryCurLFEBE         Counter,
            hwMusaQueryCurPFEBE         Counter,
            hwMusaQueryCurSendCellNum           Counter,
            hwMusaQueryCurReceiveCellNum            Counter,
            hwMusaQueryCurCorrectHECNum         Counter,
            hwMusaQueryCurNonCorrectHECNum          Counter,
            hwMusaQueryCurLOCDNum           Counter,
            hwMusaQueryCurUnmatchCellNum            Counter,
            hwMusaQueryCurOOFNum            Counter,   
            hwMusaClearAllAlarmStat             INTEGER,
            hwMusaClearOIMErrEventStat        INTEGER       
            } 

  
    hwMusaQueryCurBIP1 OBJECT-TYPE
        SYNTAX      Counter
        ACCESS      read-only
        STATUS      mandatory
    DESCRIPTION
    "Query current BIP1 errorcode since last query."
    ::= { hwMusaOimOpticEntry 1 }
    
    hwMusaQueryCurBIP2 OBJECT-TYPE
        SYNTAX      Counter
        ACCESS      read-only
        STATUS      mandatory
    DESCRIPTION
    "Query current BIP2 errorcode since last query."
    ::= { hwMusaOimOpticEntry 2 }
    
    hwMusaQueryCurBIP3 OBJECT-TYPE
        SYNTAX      Counter
        ACCESS      read-only
        STATUS      mandatory
    DESCRIPTION
    "Query current BIP3 errorcode since last query."
    ::= { hwMusaOimOpticEntry 3 }
    
    hwMusaQueryCurLFEBE OBJECT-TYPE
        SYNTAX      Counter
        ACCESS      read-only
        STATUS      mandatory
    DESCRIPTION
    "Query current LFEBE errorcode since last query."
    ::= { hwMusaOimOpticEntry 4 }
    
    hwMusaQueryCurPFEBE OBJECT-TYPE
        SYNTAX      Counter
        ACCESS      read-only
        STATUS      mandatory
    DESCRIPTION
    "Query current PFEBE errorcode since last query."
    ::= { hwMusaOimOpticEntry 5 }
    
    hwMusaQueryCurSendCellNum OBJECT-TYPE
        SYNTAX      Counter
        ACCESS      read-only
        STATUS      mandatory
    DESCRIPTION
    "Query current send cell numbers since last query."
    ::= { hwMusaOimOpticEntry 6 }
    
    hwMusaQueryCurReceiveCellNum OBJECT-TYPE
        SYNTAX      Counter
        ACCESS      read-only
        STATUS      mandatory
    DESCRIPTION
    "Query current receive cell numbers since last query."
    ::= { hwMusaOimOpticEntry 7 }
    
    hwMusaQueryCurCorrectHECNum OBJECT-TYPE
        SYNTAX      Counter
        ACCESS      read-only
        STATUS      mandatory
    DESCRIPTION
    "Query current can correct HEC numbers since last query."
    ::= { hwMusaOimOpticEntry 8 }
    
    hwMusaQueryCurNonCorrectHECNum OBJECT-TYPE
        SYNTAX      Counter
        ACCESS      read-only
        STATUS      mandatory
    DESCRIPTION
    "Query current cannot correct HEC numbers since last query."
    ::= { hwMusaOimOpticEntry 9 }
            
    hwMusaQueryCurLOCDNum OBJECT-TYPE
        SYNTAX      Counter
        ACCESS      read-only
        STATUS      mandatory
    DESCRIPTION
    "Query current LOCD numbers since last query."
    ::= { hwMusaOimOpticEntry 10 }
    
    hwMusaQueryCurUnmatchCellNum OBJECT-TYPE
        SYNTAX      Counter
        ACCESS      read-only
        STATUS      mandatory
    DESCRIPTION
    "Query current Unmatch cell numbers since last query."
    ::= { hwMusaOimOpticEntry 11 }   
    
    hwMusaQueryCurOOFNum OBJECT-TYPE
        SYNTAX      Counter
        ACCESS      read-only
        STATUS      mandatory
    DESCRIPTION
    "Query current OOF numbers since last query."
    ::= { hwMusaOimOpticEntry 12 }    
           
    hwMusaClearAllAlarmStat OBJECT-TYPE
        SYNTAX      INTEGER
        ACCESS      write-only
        STATUS      mandatory
    DESCRIPTION
    "Clear port cell statistics."
    ::= { hwMusaOimOpticEntry 13 }  
    
    hwMusaClearOIMErrEventStat  OBJECT-TYPE
        SYNTAX      INTEGER
        ACCESS      write-only
        STATUS      mandatory
    DESCRIPTION
    "Clear all OIM alarm statistics."
    ::= { hwMusaOimOpticEntry 14 }  
           
   -- -------------------------------------------------------------------------
   -- Alarm control table
   -- -------------------------------------------------------------------------
    hwMusaWarningCtrlTable    OBJECT-TYPE
        SYNTAX      SEQUENCE OF HwMusaWarningCtrlEntry
        ACCESS      not-accessible
        STATUS      mandatory
    DESCRIPTION
    "Musa warning control table."
    ::= { hwMusaSysMib 9 }

   hwMusaWarningCtrlEntry    OBJECT-TYPE
        SYNTAX         HwMusaWarningCtrlEntry
        ACCESS         not-accessible
        STATUS         mandatory
    DESCRIPTION
    "This list contains Musa warning Control parameters."
    INDEX { hwMusaWarningID }
    ::= { hwMusaWarningCtrlTable  1 }

   HwMusaWarningCtrlEntry    ::= SEQUENCE  {
            hwMusaWarningID           Counter,
            hwMusaWarningLevel        INTEGER,
            hwMusaWarningNmsCtrl      INTEGER,
            hwMusaWarningTerminalCtrl INTEGER,
            hwMusaWarningIsCount      INTEGER,
            hwMusaWarn15MinThreshold  INTEGER,
            hwMusaWarn24HourThreshold INTEGER,
            hwMusaWarningDesc         DisplayString,
            hwMusaWarningEngDesc      DisplayString
            }
      
   hwMusaWarningID OBJECT-TYPE
        SYNTAX  Counter
        ACCESS  read-only
        STATUS  mandatory
        DESCRIPTION
        "The MUSA Warning ID."
    ::= { hwMusaWarningCtrlEntry 1 }
    
   hwMusaWarningLevel OBJECT-TYPE
        SYNTAX  INTEGER{
                    notify(0),
                    normal(1),
                    serious(2),
                    fatal(3),
                    default(4)
                    }
        ACCESS  read-write
        STATUS  mandatory
        DESCRIPTION
        "The MUSA Warning level."
    ::= { hwMusaWarningCtrlEntry 2 }
        
    hwMusaWarningNmsCtrl OBJECT-TYPE
        SYNTAX  INTEGER{
        	    off(0),
        	    on(1)
        	    }
        ACCESS  read-write
        STATUS  mandatory
        DESCRIPTION
        "The MUSA Warning NMS filter."
    ::= { hwMusaWarningCtrlEntry 3 }

    hwMusaWarningTerminalCtrl OBJECT-TYPE
        SYNTAX  INTEGER{
        	    off(0),
        	    on(1)
        	    }
        ACCESS  read-write
        STATUS  mandatory
        DESCRIPTION
        "The MUSA Warning NMS filter."
    ::= { hwMusaWarningCtrlEntry 4 }
   
   hwMusaWarningIsCount   OBJECT-TYPE
        SYNTAX  INTEGER{
        	    off(0),
        	    on(1)
        	    }
        ACCESS  read-write
        STATUS  mandatory
        DESCRIPTION
        "The Warning is statics or not."
    ::= { hwMusaWarningCtrlEntry 5 }
    
   hwMusaWarn15MinThreshold  OBJECT-TYPE
        SYNTAX  INTEGER
        ACCESS  read-write
        STATUS  mandatory
        DESCRIPTION
        "The Warning 15 Minute threshold."
    ::= { hwMusaWarningCtrlEntry 6 }
            
   hwMusaWarn24HourThreshold OBJECT-TYPE
        SYNTAX  INTEGER
        ACCESS  read-write
        STATUS  mandatory
        DESCRIPTION
        "The Warning 24  Hour threshold."
    ::= { hwMusaWarningCtrlEntry 7 }
    
   hwMusaWarningDesc OBJECT-TYPE
        SYNTAX  DisplayString(SIZE(0..255))
        ACCESS  read-only
        STATUS  mandatory
        DESCRIPTION
        "The MUSA Warning Chinese description."
    ::= { hwMusaWarningCtrlEntry 8 } 

   hwMusaWarningEngDesc OBJECT-TYPE
        SYNTAX  DisplayString(SIZE(0..255))
        ACCESS  read-only
        STATUS  mandatory
        DESCRIPTION
        "The MUSA Warning English description."
    ::= { hwMusaWarningCtrlEntry 9 } 

    -- ------------------------------------------------------------------------
    -- System route config table
    -- ------------------------------------------------------------------------
    hwMusaSysRouteTable    OBJECT-TYPE
        SYNTAX      SEQUENCE OF HwMusaSysRouteEntry
        ACCESS      not-accessible
        STATUS      mandatory
    DESCRIPTION
    "Musa sys route table."
    ::= { hwMusaSysMib 10 }

   hwMusaSysRouteEntry    OBJECT-TYPE
        SYNTAX         HwMusaSysRouteEntry
        ACCESS         not-accessible
        STATUS         mandatory
    DESCRIPTION
    "This list contains Musa Sys Route Configuration
     parameters and variables."
    INDEX { hwMusaSysRouteIndex}
    ::= { hwMusaSysRouteTable  1 }

   HwMusaSysRouteEntry    ::= SEQUENCE  {
            hwMusaSysRouteIndex INTEGER,
            hwMusaDstIp         IpAddress,
            hwMusaDstIpMask     IpAddress,
            hwMusaGateIp        IpAddress,
            hwMusaSysRouteOper  INTEGER
            }
    
    hwMusaSysRouteIndex   OBJECT-TYPE
        SYNTAX          INTEGER
        ACCESS          not-accessible
        STATUS          mandatory
    DESCRIPTION
    "Sys Route index."
    ::= { hwMusaSysRouteEntry  1 }
    
    hwMusaDstIp     OBJECT-TYPE
        SYNTAX          IpAddress
        ACCESS          read-write
        STATUS          mandatory
    DESCRIPTION
    "Destination IP address."
    ::= { hwMusaSysRouteEntry  2 }    
    
    hwMusaDstIpMask     OBJECT-TYPE
        SYNTAX          IpAddress
        ACCESS          read-write
        STATUS          mandatory
    DESCRIPTION
    "Destination IP address Mask."
    ::= { hwMusaSysRouteEntry  3 }    

    hwMusaGateIp  OBJECT-TYPE
        SYNTAX          IpAddress
        ACCESS          read-write
        STATUS          mandatory
    DESCRIPTION
    "Gateway ipaddree."
    ::= { hwMusaSysRouteEntry  4 }

    hwMusaSysRouteOper  OBJECT-TYPE
        SYNTAX          INTEGER{
                            add(0),
                            del(1)
                          }
        ACCESS          read-write
        STATUS          mandatory
    DESCRIPTION
    "Sys route operate state,include:add/del."
    ::= { hwMusaSysRouteEntry  5 }
    

   -- -------------------------------------------------------------------------
   -- Load rate rate table
   -- -------------------------------------------------------------------------
    hwMusaLoadRateTable    OBJECT-TYPE
        SYNTAX      SEQUENCE OF HwMusaLoadRateEntry
        ACCESS      not-accessible
        STATUS      mandatory
    DESCRIPTION  
    "This table contains Musa slot load rate."
    ::= { hwMusaSysMib 11 }

   hwMusaLoadRateEntry    OBJECT-TYPE
        SYNTAX         HwMusaLoadRateEntry
        ACCESS         not-accessible
        STATUS         mandatory
    DESCRIPTION
    "This list contains Musa slot Load rate variables."
    INDEX { 
            hwMusaFrameIndex,
            hwMusaSlotIndex }
    ::= { hwMusaLoadRateTable  1}

   HwMusaLoadRateEntry    ::= SEQUENCE  {
            hwMusaLoadRate          INTEGER,
            hwMusaLoadType          INTEGER
            }

    hwMusaLoadRate  OBJECT-TYPE
        SYNTAX          INTEGER(0..100)
        ACCESS          read-only
        STATUS          mandatory
    DESCRIPTION
    "Load progress."
    ::= { hwMusaLoadRateEntry  1 }
    
    hwMusaLoadType  OBJECT-TYPE
        SYNTAX          INTEGER{
                            noOper(0),
                            backData(1),
                            dumpData(2),
                            loadData(3),
                            loadProc(4),
                            loadFpga(5),
                            program(6),
                            fpga(7),
                            data(8)
                            }
        ACCESS          read-only
        STATUS          mandatory
    DESCRIPTION
    "Load type."
    ::= { hwMusaLoadRateEntry  2 }
    
    -- ------------------------------------------------------------------------
    -- Musa traffic table
    -- ------------------------------------------------------------------------
    hwMusaTrafficTable    OBJECT-TYPE
        SYNTAX      SEQUENCE OF HwMusaTrafficEntry
        ACCESS      not-accessible
        STATUS      mandatory
    DESCRIPTION
    "Musa Pvc Traffic table."
    ::= { hwMusaSysMib 13 }

   hwMusaTrafficEntry    OBJECT-TYPE
        SYNTAX         HwMusaTrafficEntry
        ACCESS         not-accessible
        STATUS         mandatory
    DESCRIPTION
    "This list contains Musa Pvc Traffic Configuration
     parameters and variables."
    INDEX   {   
                hwMusaTrafficIndex
            }
    ::= { hwMusaTrafficTable  1 }

   HwMusaTrafficEntry    ::= SEQUENCE  {
            hwMusaTrafficIndex      INTEGER,
            hwMusaTrafficType       INTEGER,
            hwMusaServiceClass      INTEGER,
            hwMusaRefCount          INTEGER,
            hwMusaRecordState       INTEGER,
            hwMusaClp01pcr          INTEGER,
            hwMusaClp0pcr           INTEGER,
            hwMusaClp01scr          INTEGER,
            hwMusaClp0scr           INTEGER,
            hwMusaMbs               INTEGER,
            hwMusaMcr               INTEGER,
            hwMusaCDVT              INTEGER,
            hwMusaOperat            INTEGER,
            hwMusaNextTrafficIndex      INTEGER
            }
    
    hwMusaTrafficIndex    OBJECT-TYPE
        SYNTAX          INTEGER(1..5000)
        ACCESS          not-accessible
        STATUS          mandatory
    DESCRIPTION
    "Musa Traffic Table Index."
    ::= { hwMusaTrafficEntry  1 }   

    hwMusaTrafficType    OBJECT-TYPE
        SYNTAX          INTEGER{
                noclpnoscr(1),         
                clpnotaggingnoscr(2),  
                clptaggingnoscr(3),    
                noclpscr(4),           
                clpnotaggingscr(5),    
                clptaggingscr(6),      
                clpnotaggingmcr(7),    
                clptransparentnoscr(8),
                clptransparentscr(9),  
                noclptaggingnoscr(10),  
                noclpnoscrcdvt(11),     
                noclpscrcdvt(12),       
                clpnotaggingscrcdvt(13),
                clptaggingscrcdvt(14)   
                }

        ACCESS          read-write
        STATUS          mandatory
    DESCRIPTION
    "Musa Traffic table type.(0:NOCLPNOSCR,1:CLPNOTAGGINGNOSCR,
    2:CLPTAGGINGNOSCR,3:NOCLPSCR,4:CLPNOTAGGINGSCR,5:CLPTAGGINGSCR,
    6:CLPNOTAGGINGMCR,7:CLPTRANSPARENTNOSCR,8:CLPTRANSPARENTSCR,
    9:NOCLPTAGGINGNOSCR,10:NOCLPNOSCRCDVT,11;NOCLPSCRCDVT,12;CLPNOTAGGINGSCRCDVT,
    13:CLPTAGGINGSCRCDVT)"
    ::= { hwMusaTrafficEntry  2 }   

    hwMusaServiceClass    OBJECT-TYPE
        SYNTAX          INTEGER{
                cbr(2),
                rtVBR(3),
                nrtVBR(4),
                ubr(6)
                }
        ACCESS          read-write
        STATUS          mandatory
    DESCRIPTION
    "Musa Traffic service class.(1:other,2:CBR,3:rtVBR,4:nrtVBR,5:ABR:6:UBR)"
    ::= { hwMusaTrafficEntry  3 }   

    hwMusaRefCount    OBJECT-TYPE
        SYNTAX          INTEGER
        ACCESS          read-only
        STATUS          mandatory
    DESCRIPTION
    "Musa Traffic Traffic Record reference count."
    ::= { hwMusaTrafficEntry  4 }   

    hwMusaRecordState OBJECT-TYPE
        SYNTAX          INTEGER{
                                disable(0),
                                enable(1),
                                module(2)
                                }
        ACCESS          read-write
        STATUS          mandatory
    DESCRIPTION
    "Musa Traffic table record state.
    disable(0),enable(1),module(2)."
    ::= { hwMusaTrafficEntry  5 }   

    hwMusaClp01pcr OBJECT-TYPE
        SYNTAX          INTEGER
        ACCESS          read-write
        STATUS          mandatory
    DESCRIPTION
    "Musa Traffic table parameter Clp01pcr."
    ::= { hwMusaTrafficEntry  6 }
    
    hwMusaClp0pcr OBJECT-TYPE
        SYNTAX          INTEGER
        ACCESS          read-write
        STATUS          mandatory
    DESCRIPTION
    "Musa Traffic table parameter Clp0pcr."
    ::= { hwMusaTrafficEntry  7 }
    
    hwMusaClp01scr OBJECT-TYPE
        SYNTAX          INTEGER
        ACCESS          read-write
        STATUS          mandatory
    DESCRIPTION
    "Musa Traffic table parameter Clp01scr."
    ::= { hwMusaTrafficEntry  8}
    
    hwMusaClp0scr OBJECT-TYPE
        SYNTAX          INTEGER
        ACCESS          read-write
        STATUS          mandatory
    DESCRIPTION
    "Musa Traffic table parameter Clp0scr."
    ::= { hwMusaTrafficEntry  9 }
    
    hwMusaMbs OBJECT-TYPE
        SYNTAX          INTEGER
        ACCESS          read-write
        STATUS          mandatory
    DESCRIPTION
    "Musa Traffic table parameter Mbs."
    ::= { hwMusaTrafficEntry  10 }
    
    hwMusaMcr OBJECT-TYPE
        SYNTAX          INTEGER
        ACCESS          read-write
        STATUS          mandatory
    DESCRIPTION
    "Musa Traffic table parameter Mcr."
    ::= { hwMusaTrafficEntry  11 }
    
    hwMusaCDVT OBJECT-TYPE
        SYNTAX          INTEGER
        ACCESS          read-write
        STATUS          mandatory
    DESCRIPTION
    "Musa Traffic table parameter CDVT"
    ::= { hwMusaTrafficEntry  12 }
    
    hwMusaOperat OBJECT-TYPE
        SYNTAX          INTEGER{
                        add(0),
                        del(1)
                        }
        ACCESS          read-write
        STATUS          mandatory
    DESCRIPTION
    "Musa Traffic table operat.(0:add,1:del)"
    ::= { hwMusaTrafficEntry  13 }
    
    hwMusaNextTrafficIndex OBJECT-TYPE
        SYNTAX          INTEGER
        ACCESS          read-only
        STATUS          mandatory
    DESCRIPTION
    "Musa Traffic table next traffic index"
    ::= { hwMusaTrafficEntry  14 }
    
    -- ------------------------------------------------------------------------
    -- Campus pvc condig table
    -- ------------------------------------------------------------------------
    hwMusaCampusPvcConfTable    OBJECT-TYPE
        SYNTAX      SEQUENCE OF HwMusaCampusPvcConfEntry
        ACCESS      not-accessible
        STATUS      mandatory
    DESCRIPTION
    "Musa campus pvc configuration table."
    ::= { hwMusaSysMib 15 }

   hwMusaCampusPvcConfEntry    OBJECT-TYPE
        SYNTAX         HwMusaCampusPvcConfEntry
        ACCESS         not-accessible
        STATUS         mandatory
    DESCRIPTION
    "This list contains Musa campus pvc Configuration
     parameters and variables."
    INDEX       { 
                hwMusaFrameIndex, 
                hwMusaSlotIndex,
                hwMusaVlanId,
                hwMusaVlanIciIndex
                }
    ::= { hwMusaCampusPvcConfTable  1 }

   HwMusaCampusPvcConfEntry    ::= SEQUENCE  {
            hwMusaVlanId                INTEGER,
            hwMusaVlanIciIndex          INTEGER,
            hwMusaAdlPortCount          INTEGER,
            hwMusaAdlFrameId            INTEGER,
            hwMusaAdlSlotId             INTEGER,
            hwMusaAdlPortId             INTEGER,
            hwMusaAdlVpi                INTEGER,
            hwMusaAdlVci                INTEGER,
            hwMusaToLanTrafficId        INTEGER,
            hwMusaFromLanTrafficId      INTEGER,
            hwMusaAdlPortOperat         INTEGER
          }

    hwMusaVlanId    OBJECT-TYPE
        SYNTAX          INTEGER(1..63)
        ACCESS          read-only
        STATUS          mandatory
    DESCRIPTION
    "Musa campus VLan Id."
    ::= { hwMusaCampusPvcConfEntry  1 }   
    
    hwMusaVlanIciIndex    OBJECT-TYPE
        SYNTAX          INTEGER
        ACCESS          read-only
        STATUS          mandatory
    DESCRIPTION
    "Musa campus VLanIciIndex."
    ::= { hwMusaCampusPvcConfEntry  2 }   
    
    hwMusaAdlPortCount    OBJECT-TYPE
        SYNTAX          INTEGER
        ACCESS          read-only
        STATUS          mandatory
    DESCRIPTION
    "Musa campus adsl port counter."
    ::= { hwMusaCampusPvcConfEntry  3 }   

    hwMusaAdlFrameId    OBJECT-TYPE
        SYNTAX          INTEGER(0..4)
        ACCESS          read-write
        STATUS          mandatory
    DESCRIPTION
    "Musa campus ADL frame ID."
    ::= { hwMusaCampusPvcConfEntry  4 }       
    
    hwMusaAdlSlotId    OBJECT-TYPE
        SYNTAX          INTEGER(1..15)
        ACCESS          read-write
        STATUS          mandatory
    DESCRIPTION
    "Musa campus ADL slot ID."
    ::= { hwMusaCampusPvcConfEntry  5 }
    
    hwMusaAdlPortId    OBJECT-TYPE
        SYNTAX          INTEGER(0..15)
        ACCESS          read-write
        STATUS          mandatory
    DESCRIPTION
    "Musa campus ADL port ID."
    ::= { hwMusaCampusPvcConfEntry  6 }                           

    hwMusaAdlVpi    OBJECT-TYPE
        SYNTAX          INTEGER(0..127)
        ACCESS          read-only
        STATUS          mandatory
    DESCRIPTION
    "Musa campus VPI."
    ::= { hwMusaCampusPvcConfEntry  7 }       

    hwMusaAdlVci    OBJECT-TYPE
        SYNTAX          INTEGER(32..127)
        ACCESS          read-only
        STATUS          mandatory
    DESCRIPTION
    "Musa campus VCI."
    ::= { hwMusaCampusPvcConfEntry  8 }       

    hwMusaToLanTrafficId    OBJECT-TYPE
        SYNTAX          INTEGER
        ACCESS          read-write
        STATUS          mandatory
    DESCRIPTION
    "Musa campus to lan board traffic index."
    ::= { hwMusaCampusPvcConfEntry  9 }       

    hwMusaFromLanTrafficId    OBJECT-TYPE
        SYNTAX          INTEGER
        ACCESS          read-write
        STATUS          mandatory
    DESCRIPTION
    "Musa campus from lan board traffic index."
    ::= { hwMusaCampusPvcConfEntry  10 }  

    hwMusaAdlPortOperat    OBJECT-TYPE
        SYNTAX          INTEGER
                        {
                        add(0),
                        del(1)
                        }
        ACCESS          read-write
        STATUS          mandatory
    DESCRIPTION
    "Musa campus pvc Operat"
    ::= { hwMusaCampusPvcConfEntry  11 }            

   -- -------------------------------------------------------------------------
   -- Musa optic port bandwidth table
   -- -------------------------------------------------------------------------
    hwMusaOpticBandwidthTable    OBJECT-TYPE
        SYNTAX      SEQUENCE OF HwMusaOpticBandwidthEntry
        ACCESS      not-accessible
        STATUS      mandatory
    DESCRIPTION
    "Musa Optic port bandwidth configuration table."
    ::= { hwMusaSysMib 17 }

   hwMusaOpticBandwidthEntry    OBJECT-TYPE
        SYNTAX         HwMusaOpticBandwidthEntry
        ACCESS         not-accessible
        STATUS         mandatory
    DESCRIPTION
    "This list contains Musa optic port bandwidth Configuration."
    INDEX   { 
            hwMusaFrameIndex,
            hwMusaSlotIndex,     
            hwOIMPortIndex
            }
    ::= { hwMusaOpticBandwidthTable  1 }

   HwMusaOpticBandwidthEntry    ::= SEQUENCE  {
            hwMusaUpOpticMainBandWidth         INTEGER,
            hwMusaDnOpticMainBandWidth         INTEGER,
            hwMusaCurUsedUpBandWidth           INTEGER,
            hwMusaCurUsedDownBandWidth         INTEGER,                       
            hwMusaUpReservedBandWidth          INTEGER,
            hwMusaDownReservedBandWidth        INTEGER,
            hwMusaUpPracticalBandWidth         INTEGER,
            hwMusaDownPracticalBandWidth       INTEGER
          }
   
    hwMusaUpOpticMainBandWidth  OBJECT-TYPE
        SYNTAX   INTEGER
        ACCESS   read-write
        STATUS   mandatory
    DESCRIPTION
    "The main bandwidth(kpbs) of Up optic port."
    ::= { hwMusaOpticBandwidthEntry 1}
    
    hwMusaDnOpticMainBandWidth  OBJECT-TYPE
        SYNTAX   INTEGER
        ACCESS   read-write
        STATUS   mandatory
    DESCRIPTION
    "The main bandwidth(kpbs) of Down optic port."
    ::= { hwMusaOpticBandwidthEntry 2}
    
    hwMusaCurUsedUpBandWidth    OBJECT-TYPE
        SYNTAX   INTEGER
        ACCESS   read-only
        STATUS   mandatory
    DESCRIPTION
    "The current used up bandwidth(kpbs) of the optic port."
    ::= { hwMusaOpticBandwidthEntry 3 }
    
    hwMusaCurUsedDownBandWidth  OBJECT-TYPE
        SYNTAX   INTEGER
        ACCESS   read-only
        STATUS   mandatory
    DESCRIPTION
    "The current used down bandwidth(kpbs) of the optic port."
    ::= { hwMusaOpticBandwidthEntry 4 }
    
    hwMusaUpReservedBandWidth   OBJECT-TYPE
        SYNTAX   INTEGER
        ACCESS   read-write
        STATUS   mandatory
    DESCRIPTION
    "The up reserved bandwidth of the optic port."
    ::= { hwMusaOpticBandwidthEntry  5 }
    
    hwMusaDownReservedBandWidth OBJECT-TYPE
        SYNTAX   INTEGER
        ACCESS   read-write
        STATUS   mandatory
    DESCRIPTION
    "The down reserved bandwidth of the optic port."
    ::= { hwMusaOpticBandwidthEntry 6 }
        
    hwMusaUpPracticalBandWidth         OBJECT-TYPE
        SYNTAX   INTEGER
        ACCESS   read-write
        STATUS   mandatory
    DESCRIPTION
    "The up practical bandwidth of the optic port."
    ::= { hwMusaOpticBandwidthEntry 7 }
    
    hwMusaDownPracticalBandWidth      OBJECT-TYPE
        SYNTAX   INTEGER
        ACCESS   read-write
        STATUS   mandatory
    DESCRIPTION
    "The down practical bandwidth of the optic port."
    ::= { hwMusaOpticBandwidthEntry 8 } 
        
   -- -------------------------------------------------------------------------
   -- Traffic CBR PCR table
   -- -------------------------------------------------------------------------
    hwMusaTrafficCbrPcrTable    OBJECT-TYPE
        SYNTAX      SEQUENCE OF HwMusaTrafficCbrPcrEntry
        ACCESS      not-accessible
        STATUS      mandatory
    DESCRIPTION
    "CBR traffic PCR parameter table."
    ::= { hwMusaSysMib 18 }

   hwMusaTrafficCbrPcrEntry    OBJECT-TYPE
        SYNTAX         HwMusaTrafficCbrPcrEntry
        ACCESS         not-accessible
        STATUS         mandatory
    DESCRIPTION
    "This list contains CBR traffic's PCR parameter."
    INDEX   { 
               hwMusaCbrPcrIndex
            }
    ::= { hwMusaTrafficCbrPcrTable  1 }

   HwMusaTrafficCbrPcrEntry    ::= SEQUENCE  {
            hwMusaCbrPcrIndex         INTEGER,
            hwMusaCbrPcrValue         INTEGER,
            hwMusaCbrPcrRefCount      INTEGER
          }
   
    hwMusaCbrPcrIndex  OBJECT-TYPE
        SYNTAX   INTEGER
        ACCESS   not-accessible
        STATUS   mandatory
    DESCRIPTION
    "The index of CBR traffic PCR parameter table."
    ::= { hwMusaTrafficCbrPcrEntry 1}
   
    hwMusaCbrPcrValue  OBJECT-TYPE
        SYNTAX   INTEGER
        ACCESS   read-write
        STATUS   mandatory
    DESCRIPTION
    "The CBR traffic PCR parameter value."
    ::= { hwMusaTrafficCbrPcrEntry 2}    

   
    hwMusaCbrPcrRefCount  OBJECT-TYPE
        SYNTAX   INTEGER
        ACCESS   read-only
        STATUS   mandatory
    DESCRIPTION
    "The CBR traffic PCR parameter reference count."
    ::= { hwMusaTrafficCbrPcrEntry 3}

   -- -------------------------------------------------------------------------
   --Traffic RTVBR SCR table
   -- -------------------------------------------------------------------------
    hwMusaTrafficRtvbrScrTable    OBJECT-TYPE
        SYNTAX      SEQUENCE OF HwMusaTrafficRtvbrScrEntry
        ACCESS      not-accessible
        STATUS      mandatory
    DESCRIPTION
    "rtVbr traffic SCR parameter table."
    ::= { hwMusaSysMib 19 }

   hwMusaTrafficRtvbrScrEntry    OBJECT-TYPE
        SYNTAX         HwMusaTrafficRtvbrScrEntry
        ACCESS         not-accessible
        STATUS         mandatory
    DESCRIPTION
    "This list contains rtVbr traffic's SCR parameter."
    INDEX   { 
               hwMusaRtvbrScrIndex
            }
    ::= { hwMusaTrafficRtvbrScrTable  1 }

   HwMusaTrafficRtvbrScrEntry    ::= SEQUENCE  {
            hwMusaRtvbrScrIndex         INTEGER,
            hwMusaRtvbrScrValue         INTEGER,
            hwMusaRtvbrScrRefCount      INTEGER
          }
   
    hwMusaRtvbrScrIndex  OBJECT-TYPE
        SYNTAX   INTEGER
        ACCESS   not-accessible
        STATUS   mandatory
    DESCRIPTION
    "The index of rtVbr traffic SCR parameter table."
    ::= { hwMusaTrafficRtvbrScrEntry 1}
   
    hwMusaRtvbrScrValue  OBJECT-TYPE
        SYNTAX   INTEGER
        ACCESS   read-write
        STATUS   mandatory
    DESCRIPTION
    "The rtVbr traffic SCR parameter value."
    ::= { hwMusaTrafficRtvbrScrEntry 2}    

   
    hwMusaRtvbrScrRefCount  OBJECT-TYPE
        SYNTAX   INTEGER
        ACCESS   read-only
        STATUS   mandatory
    DESCRIPTION
    "The rtVbr traffic SCR parameter reference count."
    ::= { hwMusaTrafficRtvbrScrEntry 3}
    
   -- -------------------------------------------------------------------------   
   -- Musa pvc traffic statistics table
   -- -------------------------------------------------------------------------       
   
   hwMusaPvcTrafficStatisTable    OBJECT-TYPE
        SYNTAX      SEQUENCE OF HwMusaPvcTrafficStatisEntry
        ACCESS      not-accessible
        STATUS      mandatory
    DESCRIPTION
    "PVC traffic statistics table."
    ::= { hwMusaSysMib 21 }

   hwMusaPvcTrafficStatisEntry    OBJECT-TYPE
        SYNTAX         HwMusaPvcTrafficStatisEntry
        ACCESS         not-accessible
        STATUS         mandatory
    DESCRIPTION
    "PVC traffic statistics table entry."
    INDEX   { 
               hwMusaSPvcIndex
            }
    ::= { hwMusaPvcTrafficStatisTable  1 }

   HwMusaPvcTrafficStatisEntry    ::= SEQUENCE  {
            hwMusaUpStreamTrafficRx         Counter,
            hwMusaUpStreamTrafficTx         Counter,
            hwMusaDownStreamTrafficRx       Counter,
            hwMusaDownStreamTrafficTx       Counter
          }
   
    hwMusaUpStreamTrafficRx        OBJECT-TYPE
        SYNTAX   Counter
        ACCESS   read-only
        STATUS   mandatory
    DESCRIPTION
    "Up stream traffic Rx(cells)."
    ::= { hwMusaPvcTrafficStatisEntry 1}

    hwMusaUpStreamTrafficTx  OBJECT-TYPE
        SYNTAX   Counter
        ACCESS   read-only
        STATUS   mandatory
    DESCRIPTION
    "Up stream traffic Tx(cells)."
    ::= { hwMusaPvcTrafficStatisEntry 2}
   
    hwMusaDownStreamTrafficRx  OBJECT-TYPE
        SYNTAX   Counter
        ACCESS   read-only
        STATUS   mandatory
    DESCRIPTION
    "Down stream traffic Rx(cells)."
    ::= { hwMusaPvcTrafficStatisEntry 3}    
    
    hwMusaDownStreamTrafficTx  OBJECT-TYPE
        SYNTAX   Counter
        ACCESS   read-only
        STATUS   mandatory
    DESCRIPTION
    "Down stream traffic Tx(cells)."
    ::= { hwMusaPvcTrafficStatisEntry 4}    


   -- ------------------------------------------------------------------------
   -- All pvc table
   -- ------------------------------------------------------------------------

   hwMusaAllPvcConfTable   OBJECT-TYPE
       SYNTAX      SEQUENCE OF HwMusaAllPvcConfEntry
       ACCESS      not-accessible
       STATUS      mandatory
   DESCRIPTION
    "The  config talbe of all kinds of PVC."
   ::= { hwMusaSysMib 22 }
   
   hwMusaAllPvcConfEntry   OBJECT-TYPE
       SYNTAX      HwMusaAllPvcConfEntry
       ACCESS      not-accessible
       STATUS      mandatory
   DESCRIPTION
    "This lists config variables of all kinds of PVC."
   INDEX {  hwMusaTypeOfPvcPvp,
            hwMusaCidIndex }
   ::= { hwMusaAllPvcConfTable 1 }
   
   HwMusaAllPvcConfEntry   ::= SEQUENCE  {
             hwMusaCidIndex                  Counter,
             hwMusaSrcFrameId                INTEGER,
             hwMuasSrcSlotId                 INTEGER,
             hwMusaSrcPortVlanVccId          INTEGER,
             hwMusaSrcOnuId                  INTEGER,
             hwMusaSrcBoardVpi               INTEGER,
             hwMusaSrcBoardVci               INTEGER,
             hwMusaSrcPortType               INTEGER,
             hwMusaSrcCescChannelId          INTEGER,
             hwMusaSrcCescChannelBitmap      INTEGER,
             hwMusaSrcCescFillDegree         INTEGER,
             hwMusaSrcCescV35N               INTEGER,
             hwMusaSrcFrcDlciType            INTEGER,
             hwMusaSrcFrcIwfType             INTEGER,
             hwMusaSrcFrcActiveStatus        INTEGER,
             hwMusaSrcFrcFreeBandwidth       INTEGER,
             hwMusaSrcApcConnectAttribute    INTEGER,
             hwMusaDestFrameId               INTEGER,
             hwMusaDestSlotId                INTEGER,
             hwMusaDestPortVlanVccId         INTEGER,
             hwMusaDestOnuId                 INTEGER,
             hwMusaDestBoardVpi              INTEGER,
             hwMusaDestBoardVci              INTEGER,
             hwMusaDestPortType              INTEGER,
             hwMusaDestCescChannelId         INTEGER,
             hwMusaDestCescChannelBitmap     INTEGER,
             hwMusaDestCescFillDegree        INTEGER,
             hwMusaDestCescV35N              INTEGER,
             hwMusaDestFrcDlciType           INTEGER,
             hwMusaDestFrcIwfType            INTEGER,
             hwMusaDestFrcActiveStatus       INTEGER,
             hwMusaDestFrcFreeBandwidth      INTEGER,
             hwMusaDestApcConnectAttribute   INTEGER,
             hwMusaSrcToDestTraffic          INTEGER,
             hwMusaDestToSrcTraffic          INTEGER,
             hwMusaAllPvcOperater            INTEGER,
             hwMusaTypeOfPvcPvp              INTEGER,
             hwMusaPvcPvpState               INTEGER
             }
   
    hwMusaCidIndex    OBJECT-TYPE
        SYNTAX          Counter
        ACCESS          read-only
        STATUS          mandatory
    DESCRIPTION
    "The CID index."
    ::= { hwMusaAllPvcConfEntry  1 }
    
    hwMusaSrcFrameId    OBJECT-TYPE
        SYNTAX          INTEGER
        ACCESS          read-write
        STATUS          mandatory
    DESCRIPTION
    "The Frame id of source board."
    ::= { hwMusaAllPvcConfEntry  2 }
    
    hwMuasSrcSlotId    OBJECT-TYPE
        SYNTAX          INTEGER
        ACCESS          read-write
        STATUS          mandatory
    DESCRIPTION
    "The slot id of source board."
    ::= { hwMusaAllPvcConfEntry  3 }
    
    hwMusaSrcPortVlanVccId    OBJECT-TYPE
        SYNTAX          INTEGER
        ACCESS          read-write
        STATUS          mandatory
    DESCRIPTION
    "The Port/VlanID/VCC Index of source board."
    ::= { hwMusaAllPvcConfEntry  4 }
    
    hwMusaSrcOnuId    OBJECT-TYPE
        SYNTAX          INTEGER
        ACCESS          read-write
        STATUS          mandatory
    DESCRIPTION
    "The ONUID of source board."
    ::= { hwMusaAllPvcConfEntry  5 }
    
    hwMusaSrcBoardVpi    OBJECT-TYPE
        SYNTAX          INTEGER
        ACCESS          read-write
        STATUS          mandatory
    DESCRIPTION
    "Src board Port vpi Index."
    ::= { hwMusaAllPvcConfEntry  6 }   

    hwMusaSrcBoardVci    OBJECT-TYPE
        SYNTAX          INTEGER
        ACCESS          read-write
        STATUS          mandatory
    DESCRIPTION
    "Src board VCI Index."
    ::= { hwMusaAllPvcConfEntry  7 }
    
   hwMusaSrcPortType    OBJECT-TYPE
        SYNTAX          INTEGER{
                                uni(0),
                                sdt(1),
                                udt(2)
                               }
        ACCESS          read-write
        STATUS          mandatory
    DESCRIPTION
    "The type of CESC port."
    ::= { hwMusaAllPvcConfEntry  8 }
    
   hwMusaSrcCescChannelId OBJECT-TYPE
   SYNTAX         INTEGER
   ACCESS         read-write
   STATUS         mandatory
   DESCRIPTION    "Cesc channel Id"
   ::= { hwMusaAllPvcConfEntry 9 }

   hwMusaSrcCescChannelBitmap   OBJECT-TYPE
   SYNTAX         INTEGER
   ACCESS         read-write
   STATUS         mandatory
   DESCRIPTION    "Cesc channel Bitmap"
   ::= { hwMusaAllPvcConfEntry 10 }

   hwMusaSrcCescFillDegree    OBJECT-TYPE
   SYNTAX         INTEGER (20..47)
   ACCESS         read-write
   STATUS         mandatory
   DESCRIPTION    "Cesc fill degree(20-47)"
   ::= { hwMusaAllPvcConfEntry 11 }
   
   hwMusaSrcFrcDlciType  OBJECT-TYPE
        SYNTAX  INTEGER(1..5)
        ACCESS  read-write
        STATUS  mandatory
        DESCRIPTION
        "The ATM Logical Port DLCI."
    ::= { hwMusaAllPvcConfEntry 12 }    
            
    hwMusaSrcFrcIwfType  OBJECT-TYPE
        SYNTAX  INTEGER{
	                network11(0),
	                service(1),
	                hdlc(2),
	                networkN1(3)
                        }
        ACCESS  read-write
        STATUS  mandatory
        DESCRIPTION
        "The ATM Logical Port have service."
    ::= { hwMusaAllPvcConfEntry 13 }
    
   hwMusaSrcFrcActiveStatus  OBJECT-TYPE
        SYNTAX  INTEGER{
                        block(0),
                        unblock(1)
                        }
        ACCESS  read-write
        STATUS  mandatory
        DESCRIPTION
        "The FRC ATM logical port BLOCK/UNBLOCK."
    ::= { hwMusaAllPvcConfEntry 14 }        

   hwMusaSrcFrcFreeBandwidth  OBJECT-TYPE
        SYNTAX  INTEGER
        ACCESS  read-write
        STATUS  mandatory
        DESCRIPTION
        "The ATM logical port free bandwidth."
    ::= { hwMusaAllPvcConfEntry 15 }
    
   hwMusaSrcApcConnectAttribute  OBJECT-TYPE
        SYNTAX  INTEGER
        ACCESS  read-write
        STATUS  mandatory
        DESCRIPTION
        "The APC connection attribute of MMX(source) board."
    ::= { hwMusaAllPvcConfEntry 16 } 
    
   hwMusaSrcCescV35N  OBJECT-TYPE
        SYNTAX  INTEGER
        ACCESS  read-write
        STATUS  mandatory
        DESCRIPTION
        "The N value of V35 subboard of CESC."
    ::= { hwMusaAllPvcConfEntry 17 } 
   hwMusaDestFrameId    OBJECT-TYPE
        SYNTAX          INTEGER
        ACCESS          read-write
        STATUS          mandatory
    DESCRIPTION
    "Destination frame Index."
    ::= { hwMusaAllPvcConfEntry  20 }
   
   hwMusaDestSlotId    OBJECT-TYPE
        SYNTAX          INTEGER
        ACCESS          read-write
        STATUS          mandatory
    DESCRIPTION
    "Destination slot Index."
    ::= { hwMusaAllPvcConfEntry  21 }
    
   hwMusaDestPortVlanVccId    OBJECT-TYPE
        SYNTAX          INTEGER
        ACCESS          read-write
        STATUS          mandatory
    DESCRIPTION
    "Destination port Index."
    ::= { hwMusaAllPvcConfEntry  22 }
    
    hwMusaDestOnuId    OBJECT-TYPE
        SYNTAX          INTEGER
        ACCESS          read-write
        STATUS          mandatory
    DESCRIPTION
    "Destination ONU Index."
    ::= { hwMusaAllPvcConfEntry  23 }
    
    hwMusaDestBoardVpi    OBJECT-TYPE
        SYNTAX          INTEGER
        ACCESS          read-write
        STATUS          mandatory
    DESCRIPTION
    "Destination Port vpi Index."
    ::= { hwMusaAllPvcConfEntry  24 }   

    hwMusaDestBoardVci    OBJECT-TYPE
        SYNTAX          INTEGER
        ACCESS          read-write
        STATUS          mandatory
    DESCRIPTION
    "Destination VCI Index."
    ::= { hwMusaAllPvcConfEntry  25 }
   
   hwMusaDestPortType    OBJECT-TYPE
        SYNTAX          INTEGER{
                                uni(0),
                                sdt(1),
                                udt(2)
                               }
        ACCESS          read-write
        STATUS          mandatory
    DESCRIPTION
    "The type of CESC port."
    ::= { hwMusaAllPvcConfEntry  26 } 
    
   hwMusaDestCescChannelId OBJECT-TYPE
   SYNTAX         INTEGER
   ACCESS         read-write
   STATUS         mandatory
   DESCRIPTION    "Cesc channelId"
   ::= { hwMusaAllPvcConfEntry 27 }

   hwMusaDestCescChannelBitmap   OBJECT-TYPE
   SYNTAX         INTEGER
   ACCESS         read-write
   STATUS         mandatory
   DESCRIPTION    "Cesc channelbitmap"
   ::= { hwMusaAllPvcConfEntry 28 }

   hwMusaDestCescFillDegree    OBJECT-TYPE
   SYNTAX         INTEGER (20..47)
   ACCESS         read-write
   STATUS         mandatory
   DESCRIPTION    "Cesc fill degree(20-47)"
   ::= { hwMusaAllPvcConfEntry 29 }
   
   hwMusaDestFrcDlciType  OBJECT-TYPE
        SYNTAX  INTEGER(1..5)
        ACCESS  read-write
        STATUS  mandatory
        DESCRIPTION
        "The ATM Logical Port DLCI."
    ::= { hwMusaAllPvcConfEntry 30}    
            
    hwMusaDestFrcIwfType  OBJECT-TYPE
        SYNTAX  INTEGER{	     
                        network11(0),
	                service(1),
	                hdlc(2),
	                networkN1(3)
                        }
        ACCESS  read-write
        STATUS  mandatory
        DESCRIPTION
        "The ATM Logical Port have service."
    ::= { hwMusaAllPvcConfEntry 31 }
    
   hwMusaDestFrcActiveStatus  OBJECT-TYPE
        SYNTAX  INTEGER{
                        block(0),
                        unblock(1)
                        }
        ACCESS  read-write
        STATUS  mandatory
        DESCRIPTION
        "The FRC ATM logical port BLOCK/UNBLOCK."
    ::= { hwMusaAllPvcConfEntry 32 }        

   hwMusaDestFrcFreeBandwidth  OBJECT-TYPE
        SYNTAX  INTEGER
        ACCESS  read-write
        STATUS  mandatory
        DESCRIPTION
        "The ATM logical port free bandwidth."
    ::= { hwMusaAllPvcConfEntry 33 }
    
   hwMusaDestApcConnectAttribute    OBJECT-TYPE
        SYNTAX          INTEGER
        ACCESS          read-write
        STATUS          mandatory
    DESCRIPTION
    "connect attribut of AIU to source board."
   ::= { hwMusaAllPvcConfEntry  34 }
   
   hwMusaDestCescV35N  OBJECT-TYPE
        SYNTAX  INTEGER
        ACCESS  read-write
        STATUS  mandatory
        DESCRIPTION
        "The N value of V35 subboard of CESC."
    ::= { hwMusaAllPvcConfEntry 35 } 
   hwMusaSrcToDestTraffic  OBJECT-TYPE
        SYNTAX  INTEGER
        ACCESS  read-write
        STATUS  mandatory
        DESCRIPTION
        "The source board to destination traffic."
    ::= { hwMusaAllPvcConfEntry 38 }
    
   hwMusaDestToSrcTraffic  OBJECT-TYPE
        SYNTAX  INTEGER
        ACCESS  read-write
        STATUS  mandatory
        DESCRIPTION
        "The destination to source board traffic."
    ::= { hwMusaAllPvcConfEntry 39 }
       
   hwMusaAllPvcOperater    OBJECT-TYPE
        SYNTAX          INTEGER
                        {
                        add(0),
                        del(1)
                        }
        ACCESS          read-write
        STATUS          mandatory
    DESCRIPTION
    "Add or delete PVC."
    ::= { hwMusaAllPvcConfEntry  40}

   hwMusaTypeOfPvcPvp    OBJECT-TYPE
       SYNTAX          INTEGER
                        {
                        pvc(0),
                        pvp(1)
                        }
        ACCESS          read-write
        STATUS          mandatory
    DESCRIPTION
    "Identified type of Pvc or Pvp"
    ::= { hwMusaAllPvcConfEntry  41}
    
    hwMusaPvcPvpState  OBJECT-TYPE
       SYNTAX          INTEGER
                        {
                        normal(1),
                        invalid(2),
                        delete(3) 
                        }
        ACCESS          read-only
        STATUS          mandatory
    DESCRIPTION
    "Pvc or Pvp  state "
    ::= { hwMusaAllPvcConfEntry  42}
   
   -- ------------------------------------------------------------------------
   -- PVC-CID 
   -- ------------------------------------------------------------------------

   hwMusaPvcCidTable   OBJECT-TYPE
       SYNTAX      SEQUENCE OF HwMusaPvcCidEntry
       ACCESS      not-accessible
       STATUS      mandatory
   DESCRIPTION
    "The  CID talbe of all kinds of PVC."
   ::= { hwMusaSysMib 23 }
   
   hwMusaPvcCidEntry   OBJECT-TYPE
       SYNTAX      HwMusaPvcCidEntry
       ACCESS      not-accessible
       STATUS      mandatory
   DESCRIPTION
    "This lists CID corresponding to the PVC."
   INDEX { hwMusaFrameIndex,
           hwMusaSlotIndex ,
           hwMusaSrcPortVlanVccId,
           hwMusaSrcOnuId,
           hwMusaSrcBoardVpi,
           hwMusaSrcBoardVci   }
   ::= { hwMusaPvcCidTable 1 }
   
   HwMusaPvcCidEntry   ::= SEQUENCE  {
             hwMusaPvcCid       Counter
             }
   
    hwMusaPvcCid    OBJECT-TYPE
        SYNTAX          Counter
        ACCESS          read-write
        STATUS          mandatory
    DESCRIPTION
    "The CID corresponding to the PVC."
    ::= { hwMusaPvcCidEntry  1 }   
    
    -- ----------------------------------------------------------------------------
    -- Musa patch operate table
    -- ----------------------------------------------------------------------------    
    
   hwMusaPatchOperateTable    OBJECT-TYPE
        SYNTAX      SEQUENCE OF HwMusaPatchOperateEntry
        ACCESS      not-accessible
        STATUS      mandatory
   DESCRIPTION
    "Musa Mmx patch table."
    ::= { hwMusaSysMib 24 }

   hwMusaPatchOperateEntry    OBJECT-TYPE
        SYNTAX         HwMusaPatchOperateEntry
        ACCESS         not-accessible
        STATUS         mandatory
    DESCRIPTION
    "This list contains Musa patch description variables."
    INDEX {hwMusaPatchIdIndex
           }
    ::= { hwMusaPatchOperateTable  1 }

   HwMusaPatchOperateEntry    ::= SEQUENCE  {
            hwMusaPatchIdIndex              INTEGER,
            hwMusaPatchLoadProtocol         INTEGER,
            hwMusaPatchLoadFilename         DisplayString,
            hwMusaPatchLoadSerIp	    IpAddress,
            hwMusaPatchOper                 INTEGER
           }
           
           
    hwMusaPatchIdIndex			  OBJECT-TYPE
        SYNTAX          INTEGER
        ACCESS          not-accessible
        STATUS          mandatory
    DESCRIPTION
    "The PatchId index."
    ::= { hwMusaPatchOperateEntry  1 }            
    
    hwMusaPatchLoadProtocol     OBJECT-TYPE
        SYNTAX          INTEGER{ tftp(1)  
                                }
        ACCESS          write-only
        STATUS          mandatory
    DESCRIPTION
    "The patch load protocol."
    ::= { hwMusaPatchOperateEntry  2 }
        
    hwMusaPatchLoadFilename      	OBJECT-TYPE
        SYNTAX          DisplayString
        ACCESS          write-only
        STATUS          mandatory
    DESCRIPTION
    "The patch load filename."
    ::= { hwMusaPatchOperateEntry  3 }
    
    hwMusaPatchLoadSerIp	OBJECT-TYPE
        SYNTAX          IpAddress
        ACCESS          write-only
        STATUS          mandatory
    DESCRIPTION
    "The patch load server IP."
    ::= { hwMusaPatchOperateEntry  4 }
    
    hwMusaPatchOper                 OBJECT-TYPE
        SYNTAX          INTEGER{
                                   activate(1),
                                   deactivate(2),
                                   load(3),
                                   remove(4),
                                   run(5)
                                } 
        ACCESS          write-only
        STATUS          mandatory
    DESCRIPTION
    "The patch load operate type."
    ::= { hwMusaPatchOperateEntry  5 }
    
-- ----------------------------------------------------------------------------
-- Musa patch table
-- ----------------------------------------------------------------------------        
    
   hwMusaPatchTable    OBJECT-TYPE
        SYNTAX      SEQUENCE OF HwMusaPatchEntry
        ACCESS      not-accessible
        STATUS      mandatory
   DESCRIPTION
    "Musa Mmx patch table."
    ::= { hwMusaSysMib 25 }
    
   hwMusaPatchEntry    OBJECT-TYPE
        SYNTAX         HwMusaPatchEntry
        ACCESS         not-accessible
        STATUS         mandatory
    DESCRIPTION
    "This list contains Musa patch description variables."
    INDEX {hwMusaPatchIdIndex
           }
    ::= { hwMusaPatchTable  1 }

   HwMusaPatchEntry    ::= SEQUENCE  {
            hwMusaPatchShowIdIndex          INTEGER,
            hwMusaPatchCRC		    INTEGER,
            hwMusaPatchType		    INTEGER,
            hwMusaPatchState		    INTEGER,
            hwMusaPatchCodeAddress          INTEGER,
            hwMusaPatchCodeLength           INTEGER, 
            hwMusaPatchDataAddress          INTEGER,	
            hwMusaPatchDataLength	    INTEGER,
            hwMusaPatchFunctionNumber	    INTEGER
           }
           
           
    hwMusaPatchShowIdIndex  		  OBJECT-TYPE
        SYNTAX          INTEGER
        ACCESS          not-accessible
        STATUS          mandatory
    DESCRIPTION
    "The PatchId index."
    ::= { hwMusaPatchEntry  1 }  
    
    hwMusaPatchCRC			      	OBJECT-TYPE
        SYNTAX          INTEGER
        ACCESS          read-only
        STATUS          mandatory
    DESCRIPTION
    "The Patch CRC."
    ::= { hwMusaPatchEntry  2 }  
    
    hwMusaPatchType			      	OBJECT-TYPE
        SYNTAX          INTEGER { 
             			    c-Commonpatch(1),
                                    t-Temporarypatch(2)
                                 }
        ACCESS          read-only
        STATUS          mandatory
    DESCRIPTION
    "The Patch type."
    ::= { hwMusaPatchEntry  3 }  
    
    hwMusaPatchState		   		OBJECT-TYPE
        SYNTAX          INTEGER { 
             			  run(1),
                                  activate(2),
                                  deactivate(3) 
                                 }
        ACCESS          read-only
        STATUS          mandatory
    DESCRIPTION
    "The Patch state."
    ::= { hwMusaPatchEntry  4 }  
    
    hwMusaPatchCodeAddress          OBJECT-TYPE
        SYNTAX          INTEGER 
        ACCESS          read-only
        STATUS          mandatory
    DESCRIPTION
    "The Patch code address."
    ::= { hwMusaPatchEntry  5 }  
    
    hwMusaPatchCodeLength           OBJECT-TYPE
        SYNTAX          INTEGER 
        ACCESS          read-only
        STATUS          mandatory
    DESCRIPTION
    "The Patch code length."
    ::= { hwMusaPatchEntry  6 }  
    
    hwMusaPatchDataAddress        	OBJECT-TYPE
        SYNTAX          INTEGER 
        ACCESS          read-only
        STATUS          mandatory
    DESCRIPTION
    "The Patch data address."
    ::= { hwMusaPatchEntry  7 }  
    
    hwMusaPatchDataLength			OBJECT-TYPE
        SYNTAX          INTEGER 
        ACCESS          read-only
        STATUS          mandatory
    DESCRIPTION
    "The Patch data length."
    ::= { hwMusaPatchEntry  8 }  
    
    hwMusaPatchFunctionNumber		OBJECT-TYPE
        SYNTAX          INTEGER 
        ACCESS          read-only
        STATUS          mandatory
    DESCRIPTION
    "The Patch function number."
    ::= { hwMusaPatchEntry  9 }  
   	
    -- ------------------------------------------------------------------------
    -- End of HW MA5100 mib
    -- ------------------------------------------------------------------------ 
       
    hwMa5100EndOfMib  OBJECT-TYPE
        SYNTAX   INTEGER
        ACCESS   read-only
        STATUS   mandatory
    DESCRIPTION
    "End of HW MA5100 mib"
    ::= { hwMusaEndOfMib 1}

END
