--
-- HUAWEI-LOOPDETECT-MIB.mib
-- MIB generated by MG-SOFT Visual MIB Builder Version 3.0 Build 271
-- Friday, September 21, 2007 at 17:12:10
--

--  HUAWEI-SAFETYSTRATEGY-MIB.mib
-- MIB generated by MG-SOFT Visual MIB Builder Version 3.0 Build 271
-- Monday, January 22, 2007 at 10:16:10
-- 
--   ====================================================================
-- Copyright (C) 2003 by  HUAWEI TECHNOLOGIES. All rights reserved.
-- 
-- Description: Huawei Static Arp MIB Definition
-- Reference:   Huawei Enterprise MIB
-- Version:     V1.0
-- History:
-- 
-- =====================================================================

    HUAWEI-LOOPDETECT-MIB DEFINITIONS ::= BEGIN
 
        IMPORTS
            huawei            
                FROM HUAWEI-MIB            
            Integer32, OBJECT-TYPE, NOTIFICATION-TYPE            
                FROM SNMPv2-SMI;
            
--
-- Node definitions
--
    
--  Node definitions
-- 
-- 1.3.6.1.4.1.2011.25
        -- 1.3.6.1.4.1.2011.25
        hwDatacomm OBJECT IDENTIFIER ::= { huawei 25 }
        
        -- 1.3.6.1.4.1.2011.25.180    
        hwLoopDetectMIB MODULE-IDENTITY
        LAST-UPDATED "200810070000Z"        -- October 07, 2008 at 00:00 GMT
        ORGANIZATION 
        "Huawei Technologies co.,Ltd."
        CONTACT-INFO 
        "L2-Adp Team Huawei Technologies co.,Ltd.
        Huawei Bld.,NO.3 Xinxi Rd., 
        Shang-Di Information Industry Base,
        Hai-Dian District Beijing P.R. China
        http://www.huawei.com
            Zip:100085
        "
        DESCRIPTION
            "The LoopDetect MIB module is defined to indicate loop-detect function of Huawei Technologies co.,Ltd."
            ::= { hwDatacomm 180 }

        -- hwLoopDetectMIB OBJECT IDENTIFIER ::= { hwDatacomm 180 }
        
        -- 1.3.6.1.4.1.2011.25.180.1
        hwLoopDetectCfgTable OBJECT-TYPE
            SYNTAX SEQUENCE OF HwLoopDetectCfgEntry
            MAX-ACCESS not-accessible
            STATUS current
            DESCRIPTION
                "Indicates the table that shows the loop detect configuration and blocking state."
            ::= {hwLoopDetectMIB 1}    
        
        hwLoopDetectCfgEntry OBJECT-TYPE
            SYNTAX     HwLoopDetectCfgEntry
            MAX-ACCESS not-accessible
            STATUS current
            DESCRIPTION
                "Indicates the entries about the loop detect configuration and blocking state."
            INDEX {hwLoopDetectCfgPortIndex}
            ::= {hwLoopDetectCfgTable 1}
         
          HwLoopDetectCfgEntry ::=  
              SEQUENCE { 
              hwLoopDetectCfgPortIndex Integer32,
              hwLoopDetectCfgPortName OCTET STRING,
              hwLoopDetectCfg    Integer32,
              hwLoopDetectCfgBlock Integer32,        
            hwLoopDetectCfgBlockTime Integer32,
            hwLoopDetectCfgPriority Integer32,
            hwLoopDetectCfgTrigger Integer32,
            hwLoopDetectCfgSta    Integer32 
          }   
          
          hwLoopDetectCfgPortIndex OBJECT-TYPE
              SYNTAX  Integer32 (0..2147483647)
              MAX-ACCESS not-accessible
              STATUS current
              DESCRIPTION
                  "Indicates the interface index."
              ::= {hwLoopDetectCfgEntry 1}  
              
          hwLoopDetectCfgPortName OBJECT-TYPE
               SYNTAX  OCTET STRING(SIZE (0..80)) 
                   MAX-ACCESS read-only
              STATUS current
              DESCRIPTION
                  "Indicates the interface name."
              ::= {hwLoopDetectCfgEntry 2}
              
          hwLoopDetectCfg OBJECT-TYPE
              SYNTAX Integer32
              MAX-ACCESS read-only
              STATUS current
              DESCRIPTION
                  "Indicates whether the loop detect function is enabled." 
              ::= {hwLoopDetectCfgEntry 3}
              
          hwLoopDetectCfgBlock OBJECT-TYPE
              SYNTAX Integer32
              MAX-ACCESS read-only
              STATUS current
              DESCRIPTION 
                  "Indicates whether the interface can enter the blocking state after a loop is detected."
              ::= {hwLoopDetectCfgEntry 4}
              
          hwLoopDetectCfgBlockTime OBJECT-TYPE
              SYNTAX Integer32
              MAX-ACCESS read-only
              STATUS current
              DESCRIPTION
                  "Indicates the interval that is used to judge whether the loop disappears and the blocking state ends."
              ::= {hwLoopDetectCfgEntry 5}        

          hwLoopDetectCfgPriority OBJECT-TYPE
              SYNTAX Integer32
              MAX-ACCESS read-only
              STATUS current
              DESCRIPTION
                  "Indicates the priority in loop detect."
              ::= {hwLoopDetectCfgEntry 6}
              
          hwLoopDetectCfgTrigger OBJECT-TYPE
              SYNTAX Integer32
              MAX-ACCESS read-only
              STATUS current
              DESCRIPTION
                  "Indicates whether the function of immediate interface Down/Up is triggered after a loop is detected."
              ::= {hwLoopDetectCfgEntry 7}
              
          hwLoopDetectCfgSta OBJECT-TYPE
              SYNTAX Integer32
              MAX-ACCESS read-only
              STATUS current
              DESCRIPTION
                  "Identify the interface that is blocked after a loop is detected."
              ::= {hwLoopDetectCfgEntry 8}     
                      
        -- 1.3.6.1.4.1.2011.25.180.2
        hwLoopDetectTraps OBJECT IDENTIFIER ::= { hwLoopDetectMIB 2 }
        
        -- 1.3.6.1.4.1.2011.25.180.2.1
        hwLoopDetectEnabled NOTIFICATION-TYPE
            OBJECTS { hwLoopDetectCfgPortName }
            STATUS current
            DESCRIPTION 
                "The loop detect function is enabled."
            ::= { hwLoopDetectTraps 1 }
        
        -- 1.3.6.1.4.1.2011.25.180.2.2
        hwLoopDetectDisabled NOTIFICATION-TYPE
            OBJECTS { hwLoopDetectCfgPortName }
            STATUS current
            DESCRIPTION 
                "The loop detect function is disabled."
            ::= { hwLoopDetectTraps 2 }
        
        -- 1.3.6.1.4.1.2011.25.180.2.3
        hwLoopDetectBlocked NOTIFICATION-TYPE
            OBJECTS { hwLoopDetectCfgPortName }
            STATUS current
            DESCRIPTION 
                "The interface is blocked."
            ::= { hwLoopDetectTraps 3 }
        
        -- 1.3.6.1.4.1.2011.25.180.2.4
        hwLoopDetectUnBlocked NOTIFICATION-TYPE
            OBJECTS { hwLoopDetectCfgPortName }
            STATUS current
            DESCRIPTION 
                "The interface is unblocked."
            ::= { hwLoopDetectTraps 4 }   
            
        -- for compile builder     
        -- 1.3.6.1.4.1.2011.25.180.3
        hwLoopDetectGroups OBJECT IDENTIFIER ::= { hwLoopDetectMIB 3 }

        hwLoopDetectCfgEntryGroup OBJECT-GROUP
            OBJECTS{ 
            hwLoopDetectCfgPortName,
              hwLoopDetectCfg,
              hwLoopDetectCfgBlock,        
            hwLoopDetectCfgBlockTime,
            hwLoopDetectCfgPriority,
            hwLoopDetectCfgTrigger,
            hwLoopDetectCfgSta 
            }
           STATUS      current
           DESCRIPTION
               "Entries about the loop detect configuration and blocking state group."
           ::= { hwLoopDetectGroups 1 }    
           
        hwLoopDetectTrapsGroup NOTIFICATION-GROUP
            NOTIFICATIONS 
                    {
                        hwLoopDetectEnabled,  
                        hwLoopDetectDisabled,
                        hwLoopDetectBlocked,
                        hwLoopDetectUnBlocked
                    }
            STATUS current
            DESCRIPTION 
                "Loop-detect traps group."
            ::= { hwLoopDetectGroups 2 } 
            
    END

--
-- HUAWEI-LOOPDETECT-MIB.mib
--
