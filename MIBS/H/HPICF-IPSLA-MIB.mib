--**MOD+***********************************************************************
--* Module:    hpicfIpSla.mib
--*
--* Copyright (C) 2016 Hewlett Packard Enterprise Development LP
--* All Rights Reserved.
--* 
--* The contents of this software are proprietary and confidential
--* to the Hewlett Packard Enterprise Development LP.  No part of this
--* program may be photocopied, reproduced, or translated into another
--* programming language without prior written consent of the
--* Hewlett Packard Enterprise Development LP.
--*
--* Purpose: This file contains MIB definition of HPICF-IPSLA-MIB
--*
--**MOD-***********************************************************************

HPICF-IPSLA-MIB DEFINITIONS ::= BEGIN

	IMPORTS
		hpSwitch            
			FROM HP-ICF-OID            
		OBJECT-TYPE, MODULE-IDENTITY, Integer32,
		Unsigned32, NOTIFICATION-TYPE
			FROM SNMPv2-SMI
		MODULE-COMPLIANCE, OBJECT-GROUP, NOTIFICATION-GROUP
			FROM SNMPv2-CONF
		InterfaceIndexOrZero
			FROM IF-MIB
		RowStatus, DateAndTime
			FROM SNMPv2-TC
		InetAddressType,InetAddress, InetPortNumber
			FROM INET-ADDRESS-MIB;


	-- 1.3.6.1.4.1.11.2.14.11.5.1.57
	hpicfIpSla MODULE-IDENTITY 
		LAST-UPDATED	"201603140000Z"  -- March 14, 2016 at 00:00 GMT
		ORGANIZATION 	"HP Networking."
		CONTACT-INFO 	"Hewlett Packard Enterprise Development LP.
						    8000 Foothills Blvd.
						    Roseville, CA 95747"
		DESCRIPTION 	"This MIB module contains HP proprietary
						    objects for managing IP Service Level
						    Agreement (SLA)."

		REVISION       "201603140000Z" -- March 14, 2016 at 00:00 GMT
		DESCRIPTION    "Removed Added codec type and advantage factor."

		REVISION 		"201602160000Z"  -- February 16, 2016 at 00:00 GMT
		DESCRIPTION 	"Added codec type and advantage factor."

		REVISION 		"201506010000Z"  -- June 1, 2015 at 00:00 GMT
		DESCRIPTION 	"Initial revision."

		::= { hpSwitch 127 }

-- -------------------------------------------------------------
-- Start of MIB Objects
-- -------------------------------------------------------------
hpicfIpSlaNotifications OBJECT IDENTIFIER ::= { hpicfIpSla 0 }
hpicfIpSlaObjects       OBJECT IDENTIFIER ::= { hpicfIpSla 1 }
hpicfIpSlaConformance   OBJECT IDENTIFIER ::= { hpicfIpSla 2 }

--
-- MIB objects
--
hpicfIpSlaTable OBJECT-TYPE
   SYNTAX            SEQUENCE OF HpicfIpSlaEntry
   MAX-ACCESS        not-accessible
   STATUS            current
   DESCRIPTION       "This table specifies IP SLA test parameters as SLA entries."
   ::= { hpicfIpSlaObjects 1 }

hpicfIpSlaEntry OBJECT-TYPE
   SYNTAX            HpicfIpSlaEntry
   MAX-ACCESS        not-accessible
   STATUS            current
   DESCRIPTION       "An entry on this table specifies the destination IP address/
                      Hostname, Source address, Source Interface ID & Row status
                      corresponding to each SLA test."
   INDEX { hpicfIpSlaID }
   ::= { hpicfIpSlaTable 1 }

HpicfIpSlaEntry ::= SEQUENCE 
   {
      hpicfIpSlaID                  Integer32,
      hpicfIpSlaType                INTEGER,
      hpicfIpSlaAdminState          INTEGER,
      hpicfIpSlaSourceAddressType   InetAddressType,
      hpicfIpSlaSourceAddress       InetAddress,
      hpicfIpSlaL4SourcePort        InetPortNumber,
      hpicfIpSlaSourceInterface     InterfaceIndexOrZero,
      hpicfIpSlaDestAddressType     InetAddressType,
      hpicfIpSlaDestAddress         InetAddress,
      hpicfIpSlaL4DestPort          InetPortNumber,
      hpicfIpSlaRowStatus           RowStatus
   }

hpicfIpSlaID    OBJECT-TYPE
   SYNTAX            Integer32 (1..255)
   MAX-ACCESS        not-accessible
   STATUS            current
   DESCRIPTION       "This is an identifier for the IP SLA."
   ::= { hpicfIpSlaEntry 1 }

hpicfIpSlaType OBJECT-TYPE
   SYNTAX    INTEGER   
   {
      icmpEcho(1),
      udpEcho(2),
      udpJitter(3),
      udpJitterVoIP(4),
      tcpConnect(5)						
   }
  MAX-ACCESS         read-create
  STATUS             current
  DESCRIPTION        "SLA Probe Type. IcmpEcho is similar to ping protocol and
                      the destination should be enabled with responder
                      functionality for udpEcho, udpJitter, udpJitterVoIP and
                      tcpConnect."
  ::= { hpicfIpSlaEntry 2 }

hpicfIpSlaAdminState     OBJECT-TYPE    
   SYNTAX  INTEGER 
   {
      enable (1),
      disable (2)
   }
   MAX-ACCESS        read-create
   STATUS            current
   DESCRIPTION       "Enable or disable the IP Service Level Agreement (SLA) probe."
   DEFVAL{ disable }
   ::= { hpicfIpSlaEntry 3}

hpicfIpSlaSourceAddressType OBJECT-TYPE
   SYNTAX            InetAddressType
   MAX-ACCESS        read-create
   STATUS            current
   DESCRIPTION       "SLA source address type."
   ::= { hpicfIpSlaEntry 4 }

hpicfIpSlaSourceAddress OBJECT-TYPE
   SYNTAX            InetAddress
   MAX-ACCESS        read-create
   STATUS            current
   DESCRIPTION       "SLA source address."
   ::= { hpicfIpSlaEntry 5 }

hpicfIpSlaL4SourcePort OBJECT-TYPE
   SYNTAX            InetPortNumber
   MAX-ACCESS        read-create
   STATUS            current
   DESCRIPTION       "SLA source port to be used for SLA probes that use a 
                      transport layer such as udpEcho, udpJitter, udpJitterVoIP  
                      and tcpConnect. The allowed range is from 1024 to 65535."
  ::= { hpicfIpSlaEntry 6 }

hpicfIpSlaSourceInterface OBJECT-TYPE
   SYNTAX            InterfaceIndexOrZero
   MAX-ACCESS        read-create
   STATUS            current
   DESCRIPTION       "SLA source interface."
   ::= { hpicfIpSlaEntry 7 }

hpicfIpSlaDestAddressType OBJECT-TYPE
   SYNTAX            InetAddressType
   MAX-ACCESS        read-create
   STATUS            current
   DESCRIPTION       "SLA destination address type."
   ::= { hpicfIpSlaEntry 8 }

hpicfIpSlaDestAddress OBJECT-TYPE
   SYNTAX            InetAddress
   MAX-ACCESS        read-create
   STATUS            current
   DESCRIPTION       "SLA destination address."
   ::= { hpicfIpSlaEntry 9 }

hpicfIpSlaL4DestPort OBJECT-TYPE
   SYNTAX            InetPortNumber
   MAX-ACCESS        read-create
   STATUS            current
   DESCRIPTION       "Port on target device which responds back to the probe.
                      This is used for SLA probes that use a transport layer
                      such as udpEcho, udpJitter, udpJitterVoIP and tcpConnect
                      SLA types. The allowed range is from 1024 to 65535."
   ::= { hpicfIpSlaEntry 10 }

hpicfIpSlaRowStatus OBJECT-TYPE
   SYNTAX            RowStatus
   MAX-ACCESS        read-create
   STATUS            current
   DESCRIPTION       "SLA row status."
   ::= { hpicfIpSlaEntry 11 }

-- 
--- SLA to Probe attributes Configuration - Table
--
hpicfIpSlaAttrTable OBJECT-TYPE
   SYNTAX            SEQUENCE OF HpicfIpSlaAttrEntry
   MAX-ACCESS        not-accessible
   STATUS            current
   DESCRIPTION       "This table specifies IP SLA test parameters as SLA
                      entries."
   ::= { hpicfIpSlaObjects 2 }

hpicfIpSlaAttrEntry OBJECT-TYPE
   SYNTAX            HpicfIpSlaAttrEntry
   MAX-ACCESS        not-accessible
   STATUS            current
   DESCRIPTION       "An entry on this table specifies the attributes of SLA 
                      test such as scheduling parameters, TOS, payload size, 
                      history bucket size and inter packet interval,
                      corresponding to each SLA test."
   INDEX { hpicfIpSlaID }
   ::= { hpicfIpSlaAttrTable 1 }

HpicfIpSlaAttrEntry ::= SEQUENCE 
   {
      hpicfIpSlaSchedStartTime      DateAndTime,
      hpicfIpSlaSchedEndTime        DateAndTime,
      hpicfIpSlaSchedFreq           Unsigned32,
      hpicfIpSlaSchedRepeat         Unsigned32,
      hpicfIpSlaAttrTOS             Unsigned32,
      hpicfIpSlaAttrHistorySize     Unsigned32,
      hpicfIpSlaAttrPayloadSize     Unsigned32,
      hpicfIpSlaAttrNumPkts         Unsigned32,
      hpicfIpSlaAttrPktInterval     Unsigned32,
      hpicfIpSlaAttrRowStatus       RowStatus
   }

hpicfIpSlaSchedStartTime OBJECT-TYPE
   SYNTAX            DateAndTime
   MAX-ACCESS        read-create
   STATUS            current
   DESCRIPTION       "Timestamp to denote when to start this SLA probe."
   ::= { hpicfIpSlaAttrEntry 1 }

hpicfIpSlaSchedEndTime OBJECT-TYPE
   SYNTAX            DateAndTime
   MAX-ACCESS        read-create
   STATUS            current
   DESCRIPTION       "Timestamp to denote when to end this SLA probe."
   ::= { hpicfIpSlaAttrEntry 2 }

hpicfIpSlaSchedFreq OBJECT-TYPE
   SYNTAX            Unsigned32
   MAX-ACCESS        read-create
   STATUS            current
   DESCRIPTION       "Frequency in seconds. This value is used to send probes."
   DEFVAL   { 60 }
   ::= { hpicfIpSlaAttrEntry 3 }

hpicfIpSlaSchedRepeat OBJECT-TYPE
   SYNTAX            Unsigned32
   MAX-ACCESS        read-create
   STATUS            current
   DESCRIPTION       "Number of times this test will be repeated."
   ::= { hpicfIpSlaAttrEntry 4 }

hpicfIpSlaAttrTOS OBJECT-TYPE
   SYNTAX            Unsigned32 (0..255)
   MAX-ACCESS        read-create
   STATUS            current
   DESCRIPTION       "Type of service value to be set for the probe packet."
   ::= { hpicfIpSlaAttrEntry 5 }

hpicfIpSlaAttrHistorySize OBJECT-TYPE
   SYNTAX            Unsigned32
   MAX-ACCESS        read-create
   STATUS            current
   DESCRIPTION       "Number of history records to be maintained for SLA test.
					       Size can vary from 1 to 50."
	DEFVAL          { 25 }
	::= { hpicfIpSlaAttrEntry 6 }

hpicfIpSlaAttrPayloadSize OBJECT-TYPE
   SYNTAX            Unsigned32
   MAX-ACCESS        read-create
   STATUS            current
   DESCRIPTION       "Size of the packet payload to be sent out for each probe. 
                      It can be set from 10 to 1440."
   DEFVAL   { 0 }
   ::= { hpicfIpSlaAttrEntry 7 }

hpicfIpSlaAttrNumPkts OBJECT-TYPE
   SYNTAX            Unsigned32
   MAX-ACCESS        read-create
   STATUS            current
   DESCRIPTION       "Number of packets to be sent out for a single probe."
   DEFVAL   { 1 }
	::= { hpicfIpSlaAttrEntry 8 }

hpicfIpSlaAttrPktInterval OBJECT-TYPE
   SYNTAX            Unsigned32
   MAX-ACCESS        read-create
   STATUS            current
   DESCRIPTION       "Inter packet interval to be used for packets that are sent
                      out for a single probe. This value is not applicable if
                      the hpicfIpSlaAttrNumPkts is set to 1."
	::= { hpicfIpSlaAttrEntry 9 }
hpicfIpSlaAttrRowStatus OBJECT-TYPE
   SYNTAX            RowStatus
   MAX-ACCESS        read-create
   STATUS            current
   DESCRIPTION       "SLA attribute row status."
   ::= { hpicfIpSlaAttrEntry 10 }
-- 
-- SLA to Threshold Configuration  Table
--
hpicfIpSlaThrTable OBJECT-TYPE
   SYNTAX            SEQUENCE OF HpicfIpSlaThrEntry
   MAX-ACCESS        not-accessible
   STATUS            current
   DESCRIPTION       "This table specifies IP SLA threshold-action parameters as
                      entries. When one of the monitored parameters of an SLA
                      test goes beyond the configured thresholds, notifications
                      are generated either as traps or syslog messages."
	::= { hpicfIpSlaObjects 3 }

hpicfIpSlaThrEntry OBJECT-TYPE
   SYNTAX            HpicfIpSlaThrEntry
   MAX-ACCESS        not-accessible
   STATUS            current
   DESCRIPTION       "An entry on this table specifies the Metric type, upper  
					       and lower limit of thresholds, threshold type and action
                      to be taken."
  INDEX { hpicfIpSlaID,  hpicfIpSlaThrMetricType}
	::= { hpicfIpSlaThrTable 1 }

HpicfIpSlaThrEntry ::= SEQUENCE
   {
      hpicfIpSlaThrMetricType       INTEGER,
      hpicfIpSlaThrUpper            Integer32,
      hpicfIpSlaThrLower            Integer32,
      hpicfIpSlaThrType             INTEGER,
      hpicfIpSlaThrCount            Unsigned32,
      hpicfIpSlaThrAction           INTEGER,
      hpicfIpSlaThrRowStatus        RowStatus
	}

hpicfIpSlaThrMetricType OBJECT-TYPE
   SYNTAX    INTEGER 
   {
      rtt(1),
      jitter(2),
      srcTodstTime(3),
      dstTosrcTime(4),
      mos(5),
      icpif(6),
      packetLoss(7),
      testCompletion(8)
   }
   MAX-ACCESS        not-accessible
   STATUS            current
   DESCRIPTION       "SLA metric type to be monitored. The rtt type is the round
                      trip time of the probe packet. The jitter type is the
                      inter-packet delay variance. The srcTodstTime type is the
                      one-way trip time from source to destination. The dstTosrcTtime
                      type is the one-way trip time from destination to source. The
                      Mean Opinion Scores (MOS) type is derived only for
                      udpJitterVoIP SLA. The Calculated Planning Impairment Factor
                      (ICPIF) type is derived only for udpJitterVoIP SLA. The
                      packetLoss type is to monitor loss of communication. The
                      testCompletion type is for notifying about the completion of
                      probe test."
   ::= { hpicfIpSlaThrEntry 1 }

hpicfIpSlaThrUpper OBJECT-TYPE
   SYNTAX            Integer32
   MAX-ACCESS        read-create
   STATUS            current
   DESCRIPTION       "Acceptable upper-limit of threshold value for SLA. This 
                      value is not applicable when hpicfIpSlaThrMetricType
                      is set to packetLoss and testCompletion."
	::= { hpicfIpSlaThrEntry 2 }

hpicfIpSlaThrLower OBJECT-TYPE
   SYNTAX            Integer32
   MAX-ACCESS        read-create
   STATUS            current
   DESCRIPTION       "Acceptable lower-limit of threshold value for SLA. This  
                      value is not applicable when hpicfIpSlaThrMetricType
                      is set to packetLoss and testCompletion."                      
   ::= { hpicfIpSlaThrEntry 3 }

hpicfIpSlaThrType      OBJECT-TYPE
   SYNTAX   INTEGER 
   {
      immediate(1),
      consecutive(2)
   }
   MAX-ACCESS        read-create
   STATUS            current
   DESCRIPTION       "Configure threshold type to trigger action. This value is
                      not applicable when hpicfIpSlaThrMetricType is set to
                      testCompletion."
	::= { hpicfIpSlaThrEntry 4}

hpicfIpSlaThrCount      OBJECT-TYPE
   SYNTAX            Unsigned32 
   MAX-ACCESS        read-create
   STATUS            current
   DESCRIPTION       "Configure the count of the number of times the threshold
                      value can cross the upper/lower limits. This value is 
                      applicable only if hpicfIpSlaThrType is set to consecutive."
   ::= { hpicfIpSlaThrEntry 5}

hpicfIpSlaThrAction      OBJECT-TYPE
   SYNTAX   INTEGER
   {
      none(0),
      trap(1),
      log(2),
      trapAndLog(3)
   }
   MAX-ACCESS      read-create
   STATUS          current
   DESCRIPTION     "The action to be taken when the threshold value
                    exceeds the limit."
   ::= { hpicfIpSlaThrEntry 6}

hpicfIpSlaThrRowStatus OBJECT-TYPE
   SYNTAX            RowStatus
   MAX-ACCESS        read-create
   STATUS            current
   DESCRIPTION       "Threshold table row status."
	::= { hpicfIpSlaThrEntry 7}

--
-- IP SLA Responder objects
--
hpicfIpSlaRespTable OBJECT-TYPE
   SYNTAX            SEQUENCE OF HpicfIpSlaRespEntry
   MAX-ACCESS        not-accessible
   STATUS            current
   DESCRIPTION       "This table specifies IP SLA responder parameters as entries."
   ::= { hpicfIpSlaObjects 4 }

hpicfIpSlaRespEntry OBJECT-TYPE
   SYNTAX            HpicfIpSlaRespEntry
   MAX-ACCESS        not-accessible
   STATUS            current
   DESCRIPTION       "An entry on this table specifies the local IP address,
                      port number and row status corresponding to each SLA
                      responder config."
   INDEX 
   { 
      hpicfIpSlaRespType,
      hpicfIpSlaRespAddress,
      hpicfIpSlaRespL4Port
   }
   ::= { hpicfIpSlaRespTable 1 }

   HpicfIpSlaRespEntry ::= SEQUENCE 
   {
      hpicfIpSlaRespType            INTEGER,
      hpicfIpSlaRespAddressType     InetAddressType,
      hpicfIpSlaRespAddress         InetAddress,
      hpicfIpSlaRespL4Port          InetPortNumber,
      hpicfIpSlaRespRowStatus       RowStatus
   }

hpicfIpSlaRespType OBJECT-TYPE
   SYNTAX  INTEGER 
   {
      udpEcho(1),
      udpJitter(2),
      udpJitterVoIP(3),
      tcpConnect(4)
   }
   MAX-ACCESS        not-accessible
   STATUS            current
   DESCRIPTION       "The SLA responder type. The udpEcho and tcpConnect objects 
                      are for UDP and TCP packets, respectively. The udpJitter
                      and udpJitterVoIP values calculate one-way delay, therefore
                      a timestamp has to be embedded while replying back. This is
                      one of the indexes for the hpicfIpSlaRespTable."
   ::= { hpicfIpSlaRespEntry 1 }

hpicfIpSlaRespAddressType OBJECT-TYPE
   SYNTAX            InetAddressType
   MAX-ACCESS        read-create
   STATUS            current
   DESCRIPTION       "SLA responder IP address type."
   ::= { hpicfIpSlaRespEntry 2 }

hpicfIpSlaRespAddress OBJECT-TYPE
   SYNTAX            InetAddress
   MAX-ACCESS        not-accessible
   STATUS            current
   DESCRIPTION       "The local IP address to which the responder is bound.
                      This is one of the indexes for the hpicfIpSlaRespTable."
  ::= { hpicfIpSlaRespEntry 3 }

hpicfIpSlaRespL4Port OBJECT-TYPE
   SYNTAX            InetPortNumber
   MAX-ACCESS        not-accessible
   STATUS            current
   DESCRIPTION       "L4 port number on hpicfIpSlaRespAddress where the responder
                      listens for probe packets from SLA source. This is one of
                      the indexes for the hpicfIpSlaRespTable. The allowed range
                      is from 1024 to 65535."
   ::= { hpicfIpSlaRespEntry 4 }

hpicfIpSlaRespRowStatus OBJECT-TYPE
   SYNTAX            RowStatus
   MAX-ACCESS        read-create
   STATUS            current
   DESCRIPTION       "SLA responder row status."
   ::= { hpicfIpSlaRespEntry 5}


--*************************************************************
--*    hpicfIpSlaNotifications
--*************************************************************

hpicfIpSlaThresholdexceeded  NOTIFICATION-TYPE
   OBJECTS 
   { 
      hpicfIpSlaThrUpper
   }  
   STATUS            current
   DESCRIPTION       "This notification is generated when the metric calculated
                      from the SLA result exceeds the configured threshold value.
                      The hpicfIpSlaThrUpper is not applicable when 
                      hpicfIpSlaThrMetricType is set to packetLoss or 
                      testCompletion."
  ::= { hpicfIpSlaNotifications 1 }
  
hpicfIpSlaTestCompletion  NOTIFICATION-TYPE
   OBJECTS 
   { 
      hpicfIpSlaThrType               
   }
   STATUS            current
   DESCRIPTION       "This notification is generated when the SLA test is
                      completed either by reaching stopTime or 
                      hpicfIpSlaAttrNumPkts. This notification is sent only 
                      when the action type is set to trap or trap-log."
  ::= { hpicfIpSlaNotifications 2 }

hpicfIpSlaThresholdPktLoss  NOTIFICATION-TYPE
   OBJECTS
   { 
      hpicfIpSlaThrCount
   }
   STATUS            current
   DESCRIPTION       "This notification is generated when SLA test probe reply
                      packets are lost consecutively for the configured number
                      of hpicfIpSlaThrCount. This notification is sent only when
                      the action type is set to trap or trap-log."
  ::= { hpicfIpSlaNotifications 3 }

------------------------------------------------------------------------------
-- Conformance Information
------------------------------------------------------------------------------

hpicfIpSlaGroups        OBJECT IDENTIFIER    ::= { hpicfIpSlaConformance 1 }
hpicfIpSlaCompliances   OBJECT IDENTIFIER    ::= { hpicfIpSlaConformance 2 }

-- compliance statements

hpicfIpSlaCompliance MODULE-COMPLIANCE
   STATUS            current
   DESCRIPTION       "The compliance statement for HP switches that support IP SLA."
   MODULE            -- this module
   MANDATORY-GROUPS 
   { 
      hpicfIpSlaGroup,
      hpicfIpSlaAttrGroup,
      hpicfIpSlaThrGroup,
      hpicfIpSlaRespGroup,
      hpicfIpSlaNotificationsGroup 
   }
   ::= { hpicfIpSlaCompliances 1 }

-- MIB Groupings

hpicfIpSlaGroup OBJECT-GROUP
   OBJECTS 
   {
      hpicfIpSlaType,
      hpicfIpSlaAdminState,
      hpicfIpSlaSourceAddressType,
      hpicfIpSlaSourceAddress,
      hpicfIpSlaL4SourcePort,
      hpicfIpSlaSourceInterface,
      hpicfIpSlaDestAddressType,
      hpicfIpSlaDestAddress,
      hpicfIpSlaL4DestPort,
      hpicfIpSlaRowStatus
  }
   STATUS            current
   DESCRIPTION       "A mandatory group with a set of IP SLA objects."
   ::= { hpicfIpSlaGroups 1 }

hpicfIpSlaAttrGroup OBJECT-GROUP
   OBJECTS 
   {
      hpicfIpSlaSchedStartTime,
      hpicfIpSlaSchedEndTime,
      hpicfIpSlaSchedFreq,
      hpicfIpSlaSchedRepeat,
      hpicfIpSlaAttrTOS,
      hpicfIpSlaAttrHistorySize,
      hpicfIpSlaAttrPayloadSize,
      hpicfIpSlaAttrNumPkts,
      hpicfIpSlaAttrPktInterval,      
      hpicfIpSlaAttrRowStatus
   }
   STATUS            current
   DESCRIPTION       "A group with a set of IP SLA attribute objects."
   ::= { hpicfIpSlaGroups 2 }

hpicfIpSlaThrGroup OBJECT-GROUP
   OBJECTS 
   {
      hpicfIpSlaThrUpper,
      hpicfIpSlaThrLower,
      hpicfIpSlaThrType,
      hpicfIpSlaThrCount,
      hpicfIpSlaThrAction,
      hpicfIpSlaThrRowStatus
   }
   STATUS            current
   DESCRIPTION       "A group with a set of IP SLA threshold objects."
   ::= { hpicfIpSlaGroups 3 }

hpicfIpSlaRespGroup OBJECT-GROUP
   OBJECTS 
   {
      hpicfIpSlaRespRowStatus             
   }
   STATUS            current
   DESCRIPTION       "A group with a set of IP SLA responder objects."
   ::= { hpicfIpSlaGroups 4 }

hpicfIpSlaNotificationsGroup NOTIFICATION-GROUP
   NOTIFICATIONS   
   {
      hpicfIpSlaThresholdexceeded,
      hpicfIpSlaTestCompletion,
      hpicfIpSlaThresholdPktLoss
   }
   STATUS            current
   DESCRIPTION       "A collection of IP SLA source and responder notifications 
                      objects."
   ::= { hpicfIpSlaGroups 5 }
END
