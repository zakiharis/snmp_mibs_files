-- ===============================================================
-- Reference:  
-- Version:     V1.1
-- History:
-- V1.0 2004/06/15 created by zhangqiang  
-- V1.1 2004-10-27 updated by gaolong
--      Add TEXTUAL-CONVENTION into IMPORTS clause.
-- ===============================================================
HUAWEI-ISIS-MIB DEFINITIONS ::= BEGIN
 
		IMPORTS
			huaweiMgmt			
				FROM HUAWEI-3COM-OID-MIB			
			isisSysVersion, isisSysType, isisSysID, isisSysMaxAreaAddresses, isisSysL1State, isisSysCorrLSPs, 
			isisSysLSPL1DbaseOloads, isisSysManAddrDropFromAreas, isisSysAttmptToExMaxSeqNums, isisSysSeqNumSkips, 
			isisSysOwnLSPPurges, isisSysIDFieldLenMismatches, isisSysMaxAreaAddrMismatches, isisSysL2State, 
			isisSysLSPL2DbaseOloads, isisSysAuthFails, isisCircAdjChanges, 
			isisCircInitFails, isisCircRejAdjs, isisCircLANL1DesISChanges, isisCircLANL2DesISChanges, 
			isisISAdjState, isisISAdjNeighSysID, isisIPRAEntry, isisSysEntry, isisCircEntry			
				FROM ISIS-MIB				
			OBJECT-GROUP, MODULE-COMPLIANCE, NOTIFICATION-GROUP			
				FROM SNMPv2-CONF			
			IpAddress, Integer32, Counter32, OBJECT-TYPE, MODULE-IDENTITY, 
			OBJECT-IDENTITY, NOTIFICATION-TYPE			
				FROM SNMPv2-SMI			
			DisplayString, TruthValue, TEXTUAL-CONVENTION			
				FROM SNMPv2-TC;
	
	
		hwISIS MODULE-IDENTITY 
			LAST-UPDATED "200306110000Z"		-- June 11, 2003 at 00:00 GMT
			ORGANIZATION 
				"Huawei Technologies co.,Ltd."
			CONTACT-INFO 
				" R&D BeiJing, Huawei Technologies co.,Ltd.
				Huawei Bld.,NO.3 Xinxi Rd., 
				Shang-Di Information Industry Base,
                		Hai-Dian District Beijing P.R. China
				Zip:100085 
				Http://www.huawei.com                                       
	        		E-mail:support@huawei.com "
			DESCRIPTION 
				"The private ISIS MIB contains objects to manage the ISIS routing 
				protocol private objects in pure IP environment."
			::= { huaweiDatacomm 24 }

	
--
-- Textual conventions
--		

		LSPID ::= TEXTUAL-CONVENTION
           		STATUS current
           		DESCRIPTION
                 		"ID of an LSP."
           		SYNTAX OCTET STRING (SIZE(0..20))
	
	
--
-- Node definitions
--        
-- Operstate and OSINSAddress added to fix compilation errors due to change to draft-ietf-isis-mib-02 
--
                     
OperState ::= INTEGER
                               {
                                  off(1),
                                  on(2)
                               }
OSINSAddress ::= OCTET STRING (SIZE(0..20))

	
		huaweiDatacomm OBJECT IDENTIFIER ::= { huaweiMgmt 25 }
		hwIsisSystem OBJECT-IDENTITY
			STATUS current
			DESCRIPTION 
				"ISIS global system information."
			::= { hwISIS 1 }
		
		
		hwIsisSysTable OBJECT-TYPE
			SYNTAX SEQUENCE OF HwIsisSysEntry
			MAX-ACCESS not-accessible
			STATUS current
			DESCRIPTION
				"The set of instances of the Integrated IS-IS protocol
				existing on the system."
			::= { hwIsisSystem 1 }
		
		
		hwIsisSysEntry OBJECT-TYPE
			SYNTAX HwIsisSysEntry
			MAX-ACCESS not-accessible
			STATUS current
			DESCRIPTION
				"Each row defines Huawei priviate information specific to a single
				instance of the protocol existing on the system."
			REFERENCE
				"ISIS.poi cLNSISISBasic-P (1)"
			AUGMENTS { isisSysEntry }
			::= { hwIsisSysTable 1 }
		
		HwIsisSysEntry ::=
			SEQUENCE { 
				hwIsisSysWrongSysTypes
					Counter32,
				hwIsisSysAuthAreaRecvPwd1
					OCTET STRING,
				hwIsisSysAuthAreaRecvPwd2
					OCTET STRING,
				hwIsisSysAuthAreaRecvPwd3
					OCTET STRING,
				hwIsisSysAuthDomainRecvPwd1
					OCTET STRING,
				hwIsisSysAuthDomainRecvPwd2
					OCTET STRING,
				hwIsisSysAuthDomainRecvPwd3
					OCTET STRING,
				hwIsisSysSetLSDBOload
					TruthValue
			 }

		hwIsisSysWrongSysTypes OBJECT-TYPE
			SYNTAX Counter32
			MAX-ACCESS read-only
			STATUS current
			DESCRIPTION
				"Number of Times Wrong System Types requested for Adjacencies."
			::= { hwIsisSysEntry 1 }
		
			hwIsisSysAuthAreaRecvPwd1 OBJECT-TYPE
			SYNTAX OCTET STRING
			MAX-ACCESS read-write
			STATUS current
			DESCRIPTION
				"The value to be used as the Authentication Key in
				Level 1 Link State Packets receivied from the neighbouring
				systems, whenever the value of isisSysAuthAreaType 
				has a value of plaintext or md5. Authentication of the 
				received LSP is successful, when authentication is successful 
				on using any one of the RecvPwd?. A modification of 
				isisSysAuthAreaType does not modify the 
				hwIsisSysAuthAreaRecvPwd1 value.
				
				Reading this object always results in an  OCTET
				STRING of length zero; authentication may not
				be bypassed by reading the MIB object."
			DEFVAL { "" }
			::= { hwIsisSysEntry 2 }
		
		hwIsisSysAuthAreaRecvPwd2 OBJECT-TYPE
			SYNTAX OCTET STRING
			MAX-ACCESS read-write
			STATUS current
			DESCRIPTION
				"The value to be used as the Authentication Key in
				Level 1 Link State Packets receivied from the neighbouring
				systems, whenever the value of isisSysAuthAreaType 
				has a value of plaintext or md5. Authentication of the 
				received LSP is successful, when authentication is successful 
				on using any one of the RecvPwd?. A modification of 
				isisSysAuthAreaType does not modify the 
				hwIsisSysAuthAreaRecvPwd2 value.
				
				Reading this object always results in an  OCTET
				STRING of length zero; authentication may not
				be bypassed by reading the MIB object."
			DEFVAL { "" }
			::= { hwIsisSysEntry 3 }
		
		hwIsisSysAuthAreaRecvPwd3 OBJECT-TYPE
			SYNTAX OCTET STRING
			MAX-ACCESS read-write
			STATUS current
			DESCRIPTION
				"The value to be used as the Authentication Key in
				Level 1 Link State Packets receivied from the neighbouring
				systems, whenever the value of isisSysAuthAreaType 
				has a value of plaintext or md5. Authentication of the 
				received LSP is successful, when authentication is successful 
				on using any one of the RecvPwd?. A modification of 
				isisSysAuthAreaType does not modify the 
				hwIsisSysAuthAreaRecvPwd3 value.
				
				Reading this object always results in an  OCTET
				STRING of length zero; authentication may not
				be bypassed by reading the MIB object."
			DEFVAL { "" }
			::= { hwIsisSysEntry 4 }
		
		hwIsisSysAuthDomainRecvPwd1 OBJECT-TYPE
			SYNTAX OCTET STRING
			MAX-ACCESS read-write
			STATUS current
			DESCRIPTION
				"The value to be used as the Authentication Key in
				Level 2 Link State Packets receivied from the neighbouring
				systems, whenever the value of isisSysDomainAreaType 
				has a value of plaintext or md5. Authentication of the 
				received LSP is successful, when authentication is successful 
				on using any one of the RecvPwd?. A modification of 
				isisSysAuthDomainType does not modify the 
				hwIsisSysAuthDomainRecvPwd1 value.
				
				Reading this object always results in an  OCTET
				STRING of length zero; authentication may not
				be bypassed by reading the MIB object."
			DEFVAL { "" }
			::= { hwIsisSysEntry 5 }
		
		hwIsisSysAuthDomainRecvPwd2 OBJECT-TYPE
			SYNTAX OCTET STRING
			MAX-ACCESS read-write
			STATUS current
			DESCRIPTION
				"The value to be used as the Authentication Key in
				Level 2 Link State Packets receivied from the neighbouring
				systems, whenever the value of isisSysAuthDomainType 
				has a value of plaintext or md5. Authentication of the 
				received LSP is successful, when authentication is successful 
				on using any one of the RecvPwd?. A modification of 
				isisSysAuthDomainType does not modify the 
				hwIsisSysAuthDomainRecvPwd2 value.
				
				Reading this object always results in an  OCTET
				STRING of length zero; authentication may not
				be bypassed by reading the MIB object."
			DEFVAL { "" }
			::= { hwIsisSysEntry 6 }
		
		hwIsisSysAuthDomainRecvPwd3 OBJECT-TYPE
			SYNTAX OCTET STRING
			MAX-ACCESS read-write
			STATUS current
			DESCRIPTION
				"The value to be used as the Authentication Key in
				Level 2 Link State Packets receivied from the neighbouring
				systems, whenever the value of isisSysDomainAreaType 
				has a value of plaintext or md5. Authentication of the 
				received LSP is successful, when authentication is successful 
				on using any one of the RecvPwd?. A modification of 
				isisSysAuthDomainType does not modify the 
				hwIsisSysAuthDomainRecvPwd3 value.
				Reading this object always results in an  
				of length zero; authentication may not
				be bypassed by reading the MIB object."
			DEFVAL { "" }
			::= { hwIsisSysEntry 7 }
		
		hwIsisSysSetLSDBOload OBJECT-TYPE
			SYNTAX TruthValue
			MAX-ACCESS read-write
			STATUS current
			DESCRIPTION
				"Setting this object to 'true' forces the system to set the 
				overload bit in its non-pseudonode LSPs. The result will 
				be that no paths through this system are seen by other 
				systems in the IS-IS area."
			DEFVAL { false }
			::= { hwIsisSysEntry 8 }
		
		hwIsisCirc OBJECT-IDENTITY
			STATUS current
			DESCRIPTION 
				"ISIS local circuits information."
			::= { hwISIS 2 }
		
		hwIsisCircTable OBJECT-TYPE
			SYNTAX SEQUENCE OF HwIsisCircEntry
			MAX-ACCESS not-accessible
			STATUS current
			DESCRIPTION
				"The table of circuits used by each instance of
				Integrated IS-IS on this system."
			::= { hwIsisCirc 1 }
		
		hwIsisCircEntry OBJECT-TYPE
			SYNTAX HwIsisCircEntry
			MAX-ACCESS not-accessible
			STATUS current
			DESCRIPTION
				"An isisCircEntry exists for each circuit used by
				Integrated IS-IS on this system."
			AUGMENTS { isisCircEntry }
			::= { hwIsisCircTable 1 }
		
		HwIsisCircEntry ::=
			SEQUENCE { 
				hwIsisCircFuncState
					OperState,
				hwIsisCircLevel
					INTEGER,
				hwIsisCircL1TransPassword
					OCTET STRING,
				hwIsisCircL1RecvPassword1
					OCTET STRING,
				hwIsisCircL1RecvPassword2
					OCTET STRING,
				hwIsisCircL1RecvPassword3
					OCTET STRING,
				hwIsisCircL2TransPassword
					OCTET STRING,
				hwIsisCircL2RecvPassword1
					OCTET STRING,
				hwIsisCircL2RecvPassword2
					OCTET STRING,
				hwIsisCircL2RecvPassword3
					OCTET STRING,
				hwIsisCircVersionSkews
					Counter32,
				hwIsisCircStateChanges
					Counter32,
				hwIsisCircAreaMismatches
					Counter32
			 }

		hwIsisCircFuncState OBJECT-TYPE
			SYNTAX OperState
			MAX-ACCESS read-only
			STATUS current
			DESCRIPTION
				"The functional state of the circuit. This specifies 
				whether the circuit is currently active or not."
			DEFVAL { off }
			::= { hwIsisCircEntry 1 }
		
		hwIsisCircLevel OBJECT-TYPE
			SYNTAX INTEGER
				{
				level1(1),
				level2(2),
				level12(3)
				}
			MAX-ACCESS read-write
			STATUS current
			DESCRIPTION
				"The level of the circuit. This object follows the
				replaceOnlyWhileDisabled behaviour. "
			DEFVAL { level12 }
			::= { hwIsisCircEntry 2 }
		
		hwIsisCircL1TransPassword OBJECT-TYPE
			SYNTAX OCTET STRING
			MAX-ACCESS read-write
			STATUS current
			DESCRIPTION
				"The value to be used as the Authentication Key in Level 1
				and Point-to-Point hello packets while transmitting, 
				whenever the corresponding instance of isisCircL1AuthType 
				has a value of plaintext or md5. A modification of the 
				corresponding instance of isisCircL1AuthType does not 
				modify the hwIsisCircL1TransPassword value.
				
				Reading this object always results in an  OCTET
				STRING of length zero; authentication may not
				be bypassed by reading the MIB object."
			REFERENCE
				" "
			DEFVAL { ''h }
			::= { hwIsisCircEntry 3 }
		
		hwIsisCircL1RecvPassword1 OBJECT-TYPE
			SYNTAX OCTET STRING
			MAX-ACCESS read-write
			STATUS current
			DESCRIPTION
				"The value to be used as the Authentication Key in Level 1
				and Point-to-Point hello packets that are receivied from 
				the neighboring Systems, whenever the corresponding instance 
				of isisCircL1AuthType has a value of plaintext or md5. 
				Authentication of the received LSP is successful, when 
				authentication is successful on using any one of the 
				RecvPwd?. A modification of the corresponding instance of 
				isisCircL1AuthType does not modify the 
				hwIsisCircL1RecvPassword1 value.
				
				Reading this object always results in an  OCTET
				STRING of length zero; authentication may not
				be bypassed by reading the MIB object."
			REFERENCE
				" "
			DEFVAL { ''h }
			::= { hwIsisCircEntry 4 }
		
		hwIsisCircL1RecvPassword2 OBJECT-TYPE
			SYNTAX OCTET STRING
			MAX-ACCESS read-write
			STATUS current
			DESCRIPTION
				"The value to be used as the Authentication Key in Level 1
				and Point-to-Point hello packets that are receivied from 
				the neighboring Systems, whenever the corresponding instance 
				of isisCircL1AuthType has a value of plaintext or md5. 
				Authentication of the received LSP is successful, when 
				authentication is successful on using any one of the 
				RecvPwd?. A modification of the corresponding instance of 
				isisCircL1AuthType does not modify the 
				hwIsisCircL1RecvPassword2 value.
				
				Reading this object always results in an  OCTET
				STRING of length zero; authentication may not
				be bypassed by reading the MIB object."
			REFERENCE
				" "
			DEFVAL { ''h }
			::= { hwIsisCircEntry 5 }
		
		hwIsisCircL1RecvPassword3 OBJECT-TYPE
			SYNTAX OCTET STRING
			MAX-ACCESS read-write
			STATUS current
			DESCRIPTION
				"The value to be used as the Authentication Key in Level 1
				and Point-to-Point hello packets that are receivied from 
				the neighboring Systems, whenever the corresponding instance 
				of isisCircL1AuthType has a value of plaintext or md5. 
				Authentication of the received LSP is successful, when 
				authentication is successful on using any one of the 
				RecvPwd?. A modification of the corresponding instance of 
				isisCircL1AuthType does not modify the 
				hwIsisCircL1RecvPassword3 value.
				
				Reading this object always results in an  OCTET
				STRING of length zero; authentication may not
				be bypassed by reading the MIB object."
			REFERENCE
				" "
			DEFVAL { ''h }
			::= { hwIsisCircEntry 6 }
		
		hwIsisCircL2TransPassword OBJECT-TYPE
			SYNTAX OCTET STRING
			MAX-ACCESS read-write
			STATUS current
			DESCRIPTION
				"The value to be used as the Authentication Key in Level 2
				and Point-to-Point hello packets while transmitting, 
				whenever the corresponding instance of isisCircL2AuthType 
				has a value of plaintext or md5. A modification of the 
				corresponding instance of isisCircL2AuthType does not 
				modify the hwIsisCircL2TransPassword value.
				
				Reading this object always results in an  OCTET
				STRING of length zero; authentication may not
				be bypassed by reading the MIB object."
			REFERENCE
				" "
			DEFVAL { ''h }
			::= { hwIsisCircEntry 7 }
		

		hwIsisCircL2RecvPassword1 OBJECT-TYPE
			SYNTAX OCTET STRING
			MAX-ACCESS read-write
			STATUS current
			DESCRIPTION
				"The value to be used as the Authentication Key in Level 1
				and Point-to-Point hello packets that are receivied from 
				the neighboring Systems, whenever the corresponding instance 
				of isisCircL2AuthType has a value of plaintext or md5. 
				Authentication of the received LSP is successful, when 
				authentication is successful on using any one of the 
				RecvPwd?. A modification of the corresponding instance of 
				isisCircL2AuthType does not modify the 
				hwIsisCircL2RecvPassword1 value.
				
				Reading this object always results in an  OCTET
				STRING of length zero; authentication may not
				be bypassed by reading the MIB object."
			REFERENCE
				" "
			DEFVAL { ''h }
			::= { hwIsisCircEntry 8 }
		
		hwIsisCircL2RecvPassword2 OBJECT-TYPE
			SYNTAX OCTET STRING
			MAX-ACCESS read-write
			STATUS current
			DESCRIPTION
				"The value to be used as the Authentication Key in Level 1
				and Point-to-Point hello packets that are receivied from 
				the neighboring Systems, whenever the corresponding instance 
				of isisCircL2AuthType has a value of plaintext or md5. 
				Authentication of the received LSP is successful, when 
				authentication is successful on using any one of the 
				RecvPwd?. A modification of the corresponding instance of 
				isisCircL2AuthType does not modify the 
				hwIsisCircL2RecvPassword2 value.
				
				Reading this object always results in an  OCTET
				STRING of length zero; authentication may not
				be bypassed by reading the MIB object."
			REFERENCE
				" "
			DEFVAL { ''h }
			::= { hwIsisCircEntry 9 }
		
		hwIsisCircL2RecvPassword3 OBJECT-TYPE
			SYNTAX OCTET STRING
			MAX-ACCESS read-write
			STATUS current
			DESCRIPTION
				"The value to be used as the Authentication Key in Level 1
				and Point-to-Point hello packets that are receivied from 
				the neighboring Systems, whenever the corresponding instance 
				of isisCircL2AuthType has a value of plaintext or md5. 
				Authentication of the received LSP is successful, when 
				authentication is successful on using any one of the 
				RecvPwd?. A modification of the corresponding instance of 
				isisCircL2AuthType does not modify the 
				hwIsisCircL2RecvPassword3 value.
				
				Reading this object always results in an  OCTET
				STRING of length zero; authentication may not
				be bypassed by reading the MIB object."
			REFERENCE
				" "
			DEFVAL { ''h }
			::= { hwIsisCircEntry 10 }
		

		hwIsisCircVersionSkews OBJECT-TYPE
			SYNTAX Counter32
			MAX-ACCESS read-only
			STATUS current
			DESCRIPTION
				"The number of PDUs of different version was received"
			::= { hwIsisCircEntry 11 }
		
		hwIsisCircStateChanges OBJECT-TYPE
			SYNTAX Counter32
			MAX-ACCESS read-only
			STATUS current
			DESCRIPTION
				"The number of times the circuit has changed the state."
			::= { hwIsisCircEntry 12 }
		
		hwIsisCircAreaMismatches OBJECT-TYPE
			SYNTAX Counter32
			MAX-ACCESS read-only
			STATUS current
			DESCRIPTION
				"The number PDUs from an unrecognised area was received"
			::= { hwIsisCircEntry 13 }
		
		hwIsisIPReachAddr OBJECT-IDENTITY
			STATUS current
			DESCRIPTION 
				"ISIS local interface IP address information."
			::= { hwISIS 3 }
		
		hwIsisIPRATable OBJECT-TYPE
			SYNTAX SEQUENCE OF HwIsisIPRAEntry
			MAX-ACCESS not-accessible
			STATUS current
			DESCRIPTION
				"The table of IP Reachable Addresses to networks,
				subnetworks or hosts either manually configured or
				learned from another protocol."
			::= { hwIsisIPReachAddr 1 }
		
		hwIsisIPRAEntry OBJECT-TYPE
			SYNTAX HwIsisIPRAEntry
			MAX-ACCESS not-accessible
			STATUS current
			DESCRIPTION
				"Each entry defines an IP Reachable Address to a network,
				subnetwork or host."
			AUGMENTS { isisIPRAEntry }
			::= { hwIsisIPRATable 1 }
		
		HwIsisIPRAEntry ::=
			SEQUENCE { 
				hwIsisIPRAFuncState
					OperState,
				hwIsisIPRANextHopAddress
					IpAddress
			 }

		hwIsisIPRAFuncState OBJECT-TYPE
			SYNTAX OperState
			MAX-ACCESS read-only
			STATUS current
			DESCRIPTION
				"The functional state of the IP reachable address. This 
                 		specifies whether this RA is active or not."
			DEFVAL { off }
			::= { hwIsisIPRAEntry 1 }
		
		hwIsisIPRANextHopAddress OBJECT-TYPE
			SYNTAX IpAddress
			MAX-ACCESS read-write
			STATUS current
			DESCRIPTION
				"The Next Hop IP Address to which a PDU may be 
                 		forwarded in order to reach a destination which matches this IP
                 		Reachable Address. This object follows the manualOrAutomatic behaviour."
			::= { hwIsisIPRAEntry 3 }
		
		hwIsisNotifications OBJECT-IDENTITY
			STATUS current
			DESCRIPTION 
				"ISIS trap information."
			::= { hwISIS 4 }
		
		hwIsisCorruptedLSPDetected NOTIFICATION-TYPE
			STATUS current
			DESCRIPTION 
				"The Corrupted LSP Detected Notification is generated when 
				a corrupted Link State PDU is detected in memory. "
			::= { hwIsisNotifications 1 }
		
		hwIsisCorruptedLSPReceived NOTIFICATION-TYPE
			OBJECTS { hwIsisTrapCorruptedLSPID, isisSysCorrLSPs }
			STATUS current
			DESCRIPTION 
				"The Corrupted LSP Received Notification is generated when 
				a corrupted Link State PDU is Received.  The occurance of 
				this event is counted by the isisSysCorrLSPscounter."
			::= { hwIsisNotifications 2 }
		
		hwIsisLSPL1DatabaseOverload NOTIFICATION-TYPE
			OBJECTS { isisSysL1State, isisSysID, isisSysLSPL1DbaseOloads }
			STATUS current
			DESCRIPTION 
				"The LSP L1 Database Overload Notification is generated when the 
				l1State of the system changes between On and Waiting or Waiting
				and  On. The isisSysL1State argument is set to indicate the 
				resulting state, and in the case of Waiting the isisSysID is 
				set to indicate the source of the LSP which precipitated the 
				overload.  The occurance of this event is counted by the 
				isisSysLSPL1DbaseOloads counter."
			::= { hwIsisNotifications 3 }
		
		hwIsisLSPL2DatabaseOverload NOTIFICATION-TYPE
			OBJECTS { isisSysL2State, isisSysID, isisSysLSPL2DbaseOloads }
			STATUS current
			DESCRIPTION 
				"The LSP L2 Database Overload Notification is generated when the 
				l2State of the system changes between On and Waiting or Waiting and             
				On. The isisSysL2State argument is set to indicate the  
				resulting state, and in the case of Waiting the isisSysID is set to 
				indicate the source of the LSP which precipitated the overload.  
				The occurance of this event is counted by the 
				isisSysLSPL2DbaseOloads counter."
			::= { hwIsisNotifications 4 }
		
		hwIsisAuthenticationFailure NOTIFICATION-TYPE
			OBJECTS { isisISAdjNeighSysID, hwIsisTrapAuthErrorType, hwIsisTrapAuthErrorInfo, isisSysAuthFails }
			STATUS current
			DESCRIPTION 
				"Generated when a PDU is received with an incorrect 
				Authentication information field"
			::= { hwIsisNotifications 5 }
		
		hwIsisWrongSysType NOTIFICATION-TYPE
			OBJECTS { isisSysID, isisSysType, hwIsisTrapRecdSysType, hwIsisSysWrongSysTypes }
			STATUS current
			DESCRIPTION 
				"Generated when a Adjacency Request for Wrong/unsupported 
				adjacency type is made."
			::= { hwIsisNotifications 6 }
		
		hwIsisVersionSkew NOTIFICATION-TYPE
			OBJECTS { isisSysVersion, hwIsisTrapRecdVersion, hwIsisCircVersionSkews }
			STATUS current
			DESCRIPTION 
				"Generated when a PDU of Wrong/different version is received"
			::= { hwIsisNotifications 7 }
		
		hwIsisIDFieldLengthMismatch NOTIFICATION-TYPE
			OBJECTS { hwIsisTrapSysIDLength, hwIsisTrapRecdSysIDLength, isisSysIDFieldLenMismatches }
			STATUS current
			DESCRIPTION 
				"The hwIsisIDFieldLengthMismatch Notification is generated when a PDU is 
				received with a different value for ID field length to that of the  
				receiving Intermediate system. The occurance of this  
				event is counted by the isisSysIDFieldLenMismatches."
			::= { hwIsisNotifications 8 }
		
		hwIsisAreaMismatch NOTIFICATION-TYPE
			OBJECTS { isisSysID, hwIsisTrapRecdAreaAddr, hwIsisCircAreaMismatches }
			STATUS current
			DESCRIPTION 
				"Generated when a PDU is received from Wrong/different 
				area not recognised by this system"
			::= { hwIsisNotifications 9 }
		
		hwIsisMaxAreaAddrMismatch NOTIFICATION-TYPE
			OBJECTS { isisSysID, isisSysMaxAreaAddresses, hwIsisTrapRecdMaxAreaAddr, isisSysMaxAreaAddrMismatches }
			STATUS current
			DESCRIPTION 
				"Generated when a PDU is received from Wrong/different 
				area not recognised by this system"
			::= { hwIsisNotifications 10 }
		
		hwIsisManualAddressDroppedFromArea NOTIFICATION-TYPE
			OBJECTS { hwIsisTrapDroppedAreaAddr, isisSysManAddrDropFromAreas }
			STATUS current
			DESCRIPTION 
				"The Manual Address Dropped From Area Notification is generated 
				when one of the manualAreaAddresses (specified on this system) is 
				ignored when computing partitionAreaAddresses or areaAddresses 
				because there are more than MaximumAreaAddresses distinct 
				Area Addresses. The hwIsisTrapDroppedAreaAddr argument 
				is set to the ignored Area Address. It is generated once for 
				each Area Address in manualAreaAddresses which is dropped. 
				The occurance of this event is counted by the 
				isisSysManAddrDropFromAreas counter."
			::= { hwIsisNotifications 11 }
		
		hwIsisAttemptToExceedMaximumSequenceNumber NOTIFICATION-TYPE
			OBJECTS { isisSysAttmptToExMaxSeqNums }
			STATUS current
			DESCRIPTION 
				"The Attempt To Exceed Maximum Sequence Number Notification is 
				generated when an attempt is made to increment the sequence 
				number of an LSP beyond the maximum sequence number.  
				Following the generation of this event the operation  of the 
				Routeing state machine shall be disabled for atleast
				(MaxAge + ZeroAgeLifetime) seconds.  The occurance of this
				event is counted by the  isisSysAttmptToExMaxSeqNums  
				counter."
			::= { hwIsisNotifications 12 }
		
		hwIsisSequenceNumberSkip NOTIFICATION-TYPE
			OBJECTS { isisSysSeqNumSkips }
			STATUS current
			DESCRIPTION 
				"The Sequence Number Skipped Notification is generated when the 
				sequence number of an LSP is incremented by more than one.  The 
				occurance of this event is counted by the isisSysSeqNumSkips 
				      counter."
			::= { hwIsisNotifications 13 }
		
		hwIsisOwnLSPPurge NOTIFICATION-TYPE
			OBJECTS { isisSysOwnLSPPurges }
			STATUS current
			DESCRIPTION 
				"The Own LSP Purged Notification is generated when a zero aged copy 
				of a system's own LSP is received from some other system. This 
				   represents an erroneous attempt to purge the local system's LSP.
				   The occurance of this event is counted by the isisSysOwnLSPPurges 
				   counter."
			::= { hwIsisNotifications 14 }
		
		hwIsisCircuitChange NOTIFICATION-TYPE
			OBJECTS { hwIsisCircFuncState, hwIsisCircStateChanges }
			STATUS current
			DESCRIPTION 
				"The Circuit Change Notification is generated when the state of 
				the Circuit changes from On to Off or from Off to On. The relative 
				     order of events relating to the same Circuit must be preserved."
			::= { hwIsisNotifications 15 }
		
		hwIsisAdjacencyStateChange NOTIFICATION-TYPE
			OBJECTS { isisISAdjState, isisCircAdjChanges, isisISAdjNeighSysID }
			STATUS current
			DESCRIPTION 
				"The Adjacency State Change Notification is generated when the state 
				of an Adjacency on the Circuit changes from Up to Down or Down to  
				Up. For these purposes the states Up and Up/dormant are considered 
				to be Up, and any other state is considered to be Down. The occurance 
				of this event is counted by  the isisCircAdjChanges counter."
			::= { hwIsisNotifications 16 }
		
		hwIsisInitializationFailure NOTIFICATION-TYPE
			OBJECTS { isisISAdjNeighSysID, isisCircInitFails }
			STATUS current
			DESCRIPTION 
				"The Initialisation Failure Notification is  
				generated when an attempt to initialise with an adjacent system fails 
				as a result of either Version Skew or Area Mismatch. In the case of 
				Version Skew, the  Adjacent system argument is not present.  The 
				occurance of this event is counted by the isisCircInitFails counter."
			::= { hwIsisNotifications 17 }
		
		hwIsisRejectedAdjacency NOTIFICATION-TYPE
			OBJECTS { isisISAdjNeighSysID, isisCircRejAdjs }
			STATUS current
			DESCRIPTION 
				"The Rejected Adjacency Notification is generated when an attempt 
				to create a new adjacency is rejected, because of a lack of resources.          The occurance of this event is counted by the isisCircRejAdjs counter."
			::= { hwIsisNotifications 18 }
		
		hwIsisLanL1DesignatedIntermediateSystemChange NOTIFICATION-TYPE
			OBJECTS { isisCircLANL1DesISChanges }
			STATUS current
			DESCRIPTION 
				"The LAN L1 Designated Intermediate System Change Notification 
				is generated when the local system either elects itself or resigns as 
				being the LAN L1 Designated Intermediate System on this  
				circuit. The relative order of these events must be  
				preserved. The occurance of this event is counted by  
				the isisCircLANL1DesISChanges counter."
			::= { hwIsisNotifications 19 }
		
		hwIsisLanL2DesignatedIntermediateSystemChange NOTIFICATION-TYPE
			OBJECTS { isisCircLANL2DesISChanges }
			STATUS current
			DESCRIPTION 
				"The LAN L2 Designated Intermediate System Change Notification 
				is generated when the local system either elects itself or resigns as 
				being the LAN L2 Designated Intermediate System on this  
				circuit. The relative order of these events must be  
				preserved. The occurance of this event is counted by  
				the isisCircLANL2DesISChanges counter."
			::= { hwIsisNotifications 20 }
		
		hwIsisTrapTable OBJECT-TYPE
			SYNTAX SEQUENCE OF HwIsisTrapEntry
			MAX-ACCESS not-accessible
			STATUS current
			DESCRIPTION
				"The set of Values needed for trap support."
			::= { hwISIS 5 }
		
		hwIsisTrapEntry OBJECT-TYPE
			SYNTAX HwIsisTrapEntry
			MAX-ACCESS not-accessible
			STATUS current
			DESCRIPTION
				"Each row defines information specific to a Trap information"
			INDEX { hwIsisTrapSysInstance }
			::= { hwIsisTrapTable 1 }
		
		HwIsisTrapEntry ::=
			SEQUENCE { 
				hwIsisTrapSysInstance
					Integer32,
				hwIsisTrapDroppedAreaAddr
					OSINSAddress,
				hwIsisTrapCorruptedLSPID
					LSPID,
				hwIsisTrapSysIDLength
					Integer32,
				hwIsisTrapRecdSysIDLength
					Integer32,
				hwIsisTrapRecdAreaAddr
					OSINSAddress,
				hwIsisTrapAuthErrorType
					Integer32,
				hwIsisTrapAuthErrorInfo
					OCTET STRING,
				hwIsisTrapRecdSysType
					Integer32,
				hwIsisTrapRecdVersion
					DisplayString,
				hwIsisTrapRecdMaxAreaAddr
					Integer32
			 }

		hwIsisTrapSysInstance OBJECT-TYPE
			SYNTAX Integer32(0..2147483647)
			MAX-ACCESS not-accessible
			STATUS current
			DESCRIPTION
				"The unique identifier of the Integrated IS-IS instance
				to which this row corresponds. This object follows the
				index behaviour."
			::= { hwIsisTrapEntry 1 }
		
		hwIsisTrapDroppedAreaAddr OBJECT-TYPE
			SYNTAX OSINSAddress
			MAX-ACCESS read-only
			STATUS current
			DESCRIPTION
				"The Area Address that was dropped by 
				the system when the count of area 
				addresses exceeded the Maximum ."
			::= { hwIsisTrapEntry 2 }
		
		hwIsisTrapCorruptedLSPID OBJECT-TYPE
			SYNTAX LSPID
			MAX-ACCESS read-only
			STATUS current
			DESCRIPTION
				"The ID of the LSP that was found to be Corrupted."
			::= { hwIsisTrapEntry 3 }
		
		hwIsisTrapSysIDLength OBJECT-TYPE
			SYNTAX Integer32
			MAX-ACCESS read-only
			STATUS current
			DESCRIPTION
				"The Length of the SystemID of current system."
			::= { hwIsisTrapEntry 4 }
		
		hwIsisTrapRecdSysIDLength OBJECT-TYPE
			SYNTAX Integer32
			MAX-ACCESS read-only
			STATUS current
			DESCRIPTION
				"The Receined systemID Length"
			::= { hwIsisTrapEntry 5 }
		
		hwIsisTrapRecdAreaAddr OBJECT-TYPE
			SYNTAX OSINSAddress
			MAX-ACCESS read-only
			STATUS current
			DESCRIPTION
				"The Received Area Address"
			::= { hwIsisTrapEntry 6 }
		
		hwIsisTrapAuthErrorType OBJECT-TYPE
			SYNTAX Integer32
			MAX-ACCESS read-only
			STATUS current
			DESCRIPTION
				"The type of Authentication Error."
			::= { hwIsisTrapEntry 7 }
		
		hwIsisTrapAuthErrorInfo OBJECT-TYPE
			SYNTAX OCTET STRING (SIZE (0..64))
			MAX-ACCESS read-only
			STATUS current
			DESCRIPTION
				"The Information Pertaining to the Authentication error."
			::= { hwIsisTrapEntry 8 }
		
		hwIsisTrapRecdSysType OBJECT-TYPE
			SYNTAX Integer32
			MAX-ACCESS read-only
			STATUS current
			DESCRIPTION
				"The Received system Type."
			::= { hwIsisTrapEntry 9 }
		
		hwIsisTrapRecdVersion OBJECT-TYPE
			SYNTAX DisplayString
			MAX-ACCESS read-only
			STATUS current
			DESCRIPTION
				"The version number of the IS-IS protocol that was received."
			::= { hwIsisTrapEntry 10 }
		
		hwIsisTrapRecdMaxAreaAddr OBJECT-TYPE
			SYNTAX Integer32
			MAX-ACCESS read-only
			STATUS current
			DESCRIPTION
				"The Max Area Address Count in a received PDU."
			::= { hwIsisTrapEntry 11 }
		
		hwIsisConformance OBJECT IDENTIFIER ::= { hwISIS 6 }
		
		hwIsisCompliances OBJECT IDENTIFIER ::= { hwIsisConformance 1 }
		
		hwIsisCompliance MODULE-COMPLIANCE
			STATUS current
			DESCRIPTION 
				"The compliance statement for entities implementing
				the Huawei ISIS MIB"
			MODULE -- this module
				MANDATORY-GROUPS { hwIsisGroup, hwIsisNotificationGroup, hwIsisTrapInfoGroup }
			::= { hwIsisCompliances 1 }
		
		hwIsisGroups OBJECT IDENTIFIER ::= { hwIsisConformance 2 }
		
		-- 1.3.6.1.4.1.2011.5.25.24.6.2.1
		hwIsisGroup OBJECT-GROUP
			OBJECTS { hwIsisSysWrongSysTypes, hwIsisSysAuthAreaRecvPwd1, hwIsisSysAuthAreaRecvPwd2, hwIsisSysAuthAreaRecvPwd3, hwIsisSysAuthDomainRecvPwd1, 
				hwIsisSysAuthDomainRecvPwd2, hwIsisSysAuthDomainRecvPwd3, hwIsisSysSetLSDBOload, hwIsisCircFuncState, hwIsisCircLevel, 
				hwIsisCircL1TransPassword, hwIsisCircL1RecvPassword1, hwIsisCircL1RecvPassword2, hwIsisCircL1RecvPassword3, hwIsisCircL2TransPassword, 
				hwIsisCircL2RecvPassword1, hwIsisCircL2RecvPassword2, hwIsisCircL2RecvPassword3, hwIsisCircVersionSkews, hwIsisCircStateChanges, 
				hwIsisCircAreaMismatches, hwIsisIPRAFuncState, hwIsisIPRANextHopAddress }
			STATUS current
			DESCRIPTION 
				"A collection of objects."
			::= { hwIsisGroups 1 }
		
		hwIsisNotificationGroup NOTIFICATION-GROUP
			NOTIFICATIONS { hwIsisCorruptedLSPDetected, hwIsisCorruptedLSPReceived, hwIsisLSPL1DatabaseOverload, hwIsisLSPL2DatabaseOverload, hwIsisAuthenticationFailure, 
				hwIsisWrongSysType, hwIsisVersionSkew, hwIsisIDFieldLengthMismatch, hwIsisAreaMismatch, hwIsisMaxAreaAddrMismatch, 
				hwIsisManualAddressDroppedFromArea, hwIsisAttemptToExceedMaximumSequenceNumber, hwIsisSequenceNumberSkip, hwIsisOwnLSPPurge, hwIsisCircuitChange, 
				hwIsisAdjacencyStateChange, hwIsisInitializationFailure, hwIsisRejectedAdjacency, hwIsisLanL1DesignatedIntermediateSystemChange, hwIsisLanL2DesignatedIntermediateSystemChange
				 }
			STATUS current
			DESCRIPTION 
				"A collection of isis notification objects."
			::= { hwIsisGroups 2 }
		
		hwIsisTrapInfoGroup OBJECT-GROUP
			OBJECTS { hwIsisTrapDroppedAreaAddr, hwIsisTrapCorruptedLSPID, hwIsisTrapSysIDLength, hwIsisTrapRecdSysIDLength, hwIsisTrapRecdAreaAddr, 
				hwIsisTrapAuthErrorType, hwIsisTrapAuthErrorInfo, hwIsisTrapRecdSysType, hwIsisTrapRecdVersion, hwIsisTrapRecdMaxAreaAddr
				 }
			STATUS current
			DESCRIPTION 
				"A collection of objects providing trap records."
			::= { hwIsisGroups 3 }
		
	
	END

--
-- HUAWEI-ISIS-MIB.my
--
