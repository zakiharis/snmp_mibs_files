--**MOD+***********************************************************************
--* Module:    hpicfActivate.mib
--*
--* Copyright (C) 2016 Hewlett Packard Enterprise Development LP
--* All Rights Reserved.
--*
--* The contents of this software are proprietary and confidential
--* to the Hewlett Packard Enterprise Development LP.  No part of this
--* program may be photocopied, reproduced, or translated into another
--* programming language without prior written consent of the
--* Hewlett Packard Enterprise Development LP.
--*
--* Purpose: This file contains MIB definition of HPICF-ACTIVATE-MIB
--*
--**MOD-***********************************************************************

HPICF-ACTIVATE-MIB DEFINITIONS ::= BEGIN

IMPORTS
    OBJECT-TYPE, MODULE-IDENTITY
        FROM SNMPv2-SMI
    OBJECT-GROUP, MODULE-COMPLIANCE
        FROM SNMPv2-CONF
    TruthValue
       FROM SNMPv2-TC
    hpSwitch
        FROM HP-ICF-OID;


    hpicfActivateMIB MODULE-IDENTITY
        LAST-UPDATED "201605030000Z"  -- May 03, 2016
        ORGANIZATION "HPE Networking"
        CONTACT-INFO "Hewlett Packard Enterprise Company
                      8000 Foothills Blvd.
                      Roseville, CA 95747"
        DESCRIPTION  "This MIB defines HPE proprietary objects used to
                      configure the Activate feature."

        REVISION     "201605030000Z"  -- May 03, 2016
        DESCRIPTION  "Initial version"
        ::= { hpSwitch 129 }

    hpicfActivateObjects        OBJECT IDENTIFIER ::= { hpicfActivateMIB 1 }
    hpicfActivateConformance    OBJECT IDENTIFIER ::= { hpicfActivateMIB 2 }

    hpicfActivateSoftwareUpdateMode OBJECT-TYPE
        SYNTAX      TruthValue
        MAX-ACCESS  read-write
        STATUS      current
        DESCRIPTION "Enable polling the Aruba Activate server for software updates."
        DEFVAL      { true }
        ::= { hpicfActivateObjects 1 }

    hpicfActivateProvisionMode OBJECT-TYPE
        SYNTAX      TruthValue
        MAX-ACCESS  read-write
        STATUS      current
        DESCRIPTION "Enable Activate provision service."
        DEFVAL      { true }
        ::= { hpicfActivateObjects 2 }

    hpicfActivateMIBCompliances  OBJECT IDENTIFIER ::= { hpicfActivateConformance 1 }
    hpicfActivateMIBGroups       OBJECT IDENTIFIER ::= { hpicfActivateConformance 2 }

    hpicfActivateMIBCompliance MODULE-COMPLIANCE
        STATUS      current
        DESCRIPTION "The compliance statement for HPE switches implementing
                     the HPICF-Activate MIB."
        MODULE
            MANDATORY-GROUPS { hpicfActivateConfigGroup }
        ::= { hpicfActivateMIBCompliances 1 }

    hpicfActivateConfigGroup OBJECT-GROUP
        OBJECTS {
        hpicfActivateSoftwareUpdateMode,
        hpicfActivateProvisionMode
    }
        STATUS      current
        DESCRIPTION "A collection of objects to support the Activate feature."
        ::= { hpicfActivateMIBGroups 1 }

END
