-- *****************************************************************************
--                     HP NetServer Trap Manager Information 
--          Management Information Base for SNMP Network Management
--
--  Copyright 1996 Hewlett-Packard Company
--  All Rights Reserved.
--
--  The information in this document is subject to change without notice. 
--  The HP enterprise number is 11.
--  The ASN.1 prefix to, and including the HP Enterprise is: 1.3.6.1.4.1.11
--
--
-- ****************************************************************************
-- Summary of HP NSA Trap Manager Information MIB
-- ****************************************************************************
-- hp                                                     (1.3.6.1.4.1.11)
--   nm                                                   (hp.2)
--     hpnsa                                              (nm.23)
--       hpnsaTrapMgr Group                               (hpnsa.23) 
--
--          hpnsaTrapMgrRev Group                         (hpnsa.23.1)
--             hpnsaTrapMgrMibRevMajor                    (hpnsa.23.1.1)
--             hpnsaTrapMgrMibRevMinor                    (hpnsa.23.1.2)
--
--          hpnsaTrapMgrAgentInfo Group                   (hpnsa.23.2)
--             hpnsaTrapMgrAgentTable                     (hpnsa.23.2.1)
--                hpnsaTrapMgrAgentEntry                  (hpnsa.23.2.1.1)
--                   hpnsaTrapMgrAgentIndex               (hpnsa.23.2.1.1.1)
--                   hpnsaTrapMgrAgentName                (hpnsa.23.2.1.1.2)
--                   hpnsaTrapMgrAgentVersion             (hpnsa.23.2.1.1.3)
--                   hpnsaTrapMgrAgentDate                (hpnsa.23.2.1.1.4)
--
--          hpnsaTrapMgrStats Group                       (hpnsa.23.3)
--             hpnsaTrapMgrNumActive                      (hpnsa.23.3.1)
--             hpnsaTrapMgrNumHistory                     (hpnsa.23.3.2)
--             hpnsaTrapMgrMaxHistory                     (hpnsa.23.3.3)
--             hpnsaTrapMgrEraseTraps                     (hpnsa.23.3.4)
--
--          hpnsaTrapMgrActive Group                      (hpnsa.23.4)
--             hpnsaTrapMgrActiveTable                    (hpnsa.23.4.1)
--                hpnsaTrapMgrActiveTableEntry            (hpnsa.23.4.1.1)
--                    hpnsaTrapMgrActiveTrapHandleIndex   (hpnsa.23.4.1.1.1)
--                    hpnsaTrapMgrActiveTrapID            (hpnsa.23.4.1.1.2) 
--                    hpnsaTrapMgrActiveTimeStamp         (hpnsa.23.4.1.1.3) 
--                    hpnsaTrapMgrActiveSeverity          (hpnsa.23.4.1.1.4) 
--                    hpnsaTrapMgrActiveCustomString      (hpnsa.23.4.1.1.5) 
--                    hpnsaTrapMgrActiveEnterpriseID      (hpnsa.23.4.1.1.6) 
--                    hpnsaTrapMgrActiveSpecificID        (hpnsa.23.4.1.1.7)
--      
--          hpnsaTrapMgrAck Group                         (hpnsa.23.5)
--             hpnsaTrapMgrTrapHandleAck                  (hpnsa.23.5.1)
--
--          hpnsaTrapMgrHist Group                        (hpnsa.23.6)
--             hpnsaTrapMgrHistTable                      (hpnsa.23.6.1)
--                hpnsaTrapMgrHistTableEntry              (hpnsa.23.6.1.1)
--                    hpnsaTrapMgrHistTrapHandleIndex     (hpnsa.23.6.1.1.1)
--                    hpnsaTrapMgrHistTrapID              (hpnsa.23.4.1.1.2) 
--                    hpnsaTrapMgrHistTimeStamp           (hpnsa.23.6.1.1.3) 
--                    hpnsaTrapMgrHistSeverity            (hpnsa.23.6.1.1.4) 
--                    hpnsaTrapMgrHistCustomString        (hpnsa.23.6.1.1.5) 
--                    hpnsaTrapMgrHistEnterpriseID        (hpnsa.23.6.1.1.6) 
--                    hpnsaTrapMgrHistSpecificID          (hpnsa.23.6.1.1.7)
--                    hpnsaTrapMgrHistAck                 (hpnsa.23.6.1.1.8)
--
-- ****************************************************************************

HPNSATRAPMNGR-MIB DEFINITIONS ::= BEGIN

   IMPORTS
   enterprises    FROM RFC1155-SMI
   Counter        FROM RFC1155-SMI
   DisplayString  FROM RFC1213-MIB
   OBJECT-TYPE    FROM RFC-1212;
--
    hp                      OBJECT IDENTIFIER ::= { enterprises 11 }
    nm                      OBJECT IDENTIFIER ::= { hp 2 }
    hpnsa                   OBJECT IDENTIFIER ::= { nm 23 }  
    hpnsaTrapMgr            OBJECT IDENTIFIER ::= { hpnsa 23 }
    hpnsaTrapMgrRev         OBJECT IDENTIFIER ::= { hpnsaTrapMgr 1 }
    hpnsaTrapMgrAgentInfo   OBJECT IDENTIFIER ::= { hpnsaTrapMgr 2 }
    hpnsaTrapMgrStats       OBJECT IDENTIFIER ::= { hpnsaTrapMgr 3 }
    hpnsaTrapMgrActive      OBJECT IDENTIFIER ::= { hpnsaTrapMgr 4 }
    hpnsaTrapMgrAck         OBJECT IDENTIFIER ::= { hpnsaTrapMgr 5 }
    hpnsaTrapMgrHist        OBJECT IDENTIFIER ::= { hpnsaTrapMgr 6 }

-- *************************************************************************
-- hpnsaTrapMgrMibRev (1.3.6.1.4.1.11.2.23.23.1)
-- **************************************************************************

hpnsaTrapMgrMibRevMajor OBJECT-TYPE
    SYNTAX INTEGER (0..65535)
    ACCESS read-only
    STATUS mandatory
    DESCRIPTION
   "The major revision level of the MIB (left of the decimal)."
    ::= { hpnsaTrapMgrRev 1 }

hpnsaTrapMgrMibRevMinor OBJECT-TYPE
    SYNTAX INTEGER (0..65535)
    ACCESS read-only
    STATUS mandatory
    DESCRIPTION
   "The minor revision level of the MIB (right of the decimal)."
    ::= { hpnsaTrapMgrRev 2 }


-- *************************************************************************
-- hpnsaTrapMgrAgentInfo (1.3.6.1.4.1.11.2.23.23.2)
-- **************************************************************************

hpnsaTrapMgrAgentTable OBJECT-TYPE
    SYNTAX  SEQUENCE OF HPnsaTrapMgrAgentEntry
    ACCESS  not-accessible
    STATUS  mandatory
    DESCRIPTION
   "A table of SNMP Agents that satisfy requests for this MIB."
    ::= { hpnsaTrapMgrAgentInfo 1 }

hpnsaTrapMgrAgentEntry OBJECT-TYPE
    SYNTAX  HPnsaTrapMgrAgentEntry
    ACCESS  not-accessible
    STATUS  mandatory
    DESCRIPTION
   "A description of the agents that manage NSA traps."
    INDEX   { hpnsaTrapMgrAgentIndex }
    ::= { hpnsaTrapMgrAgentTable 1 }
       
HPnsaTrapMgrAgentEntry ::= SEQUENCE {
    hpnsaTrapMgrAgentIndex       INTEGER,
    hpnsaTrapMgrAgentName        DisplayString,
    hpnsaTrapMgrAgentVersion     DisplayString,
    hpnsaTrapMgrAgentDate        OCTET STRING
}


hpnsaTrapMgrAgentIndex OBJECT-TYPE
    SYNTAX  INTEGER (0..255)
    ACCESS  read-only
    STATUS  mandatory
    DESCRIPTION
   "A unique index for this module description."
    ::= { hpnsaTrapMgrAgentEntry 1 }

hpnsaTrapMgrAgentName OBJECT-TYPE
    SYNTAX  DisplayString (SIZE (0..255))
    ACCESS  read-only
    STATUS  mandatory
    DESCRIPTION
   "Name of the Agent/Agents satisfying SNMP requests for this MIB."
    ::= { hpnsaTrapMgrAgentEntry 2 }

hpnsaTrapMgrAgentVersion OBJECT-TYPE
    SYNTAX  DisplayString (SIZE (0..5))
    ACCESS  read-only
    STATUS  mandatory
    DESCRIPTION
   "Version number of the Agent/Agents satisfying SNMP requests for
    this MIB."
    ::= { hpnsaTrapMgrAgentEntry 3 }

hpnsaTrapMgrAgentDate OBJECT-TYPE
    SYNTAX  OCTET STRING (SIZE (6))
    ACCESS  read-only
    STATUS  mandatory
    DESCRIPTION
   "The date on which this Agent was created.

	 field  octets  contents                  range
	 _________________________________________________
	   1       1    years since 1900          0..255
	   2       2    month                     1..12
	   3       3    day                       1..31
	   4       4    hour                      0..23
	   5       5    minute                    0..59  
	   6       6    second                    0..59
	     "
      ::= { hpnsaTrapMgrAgentEntry 4 }
 


-- *************************************************************************
-- hpnsaTrapMgrStats (1.3.6.1.4.1.11.2.23.23.3)
-- **************************************************************************

hpnsaTrapMgrNumActive OBJECT-TYPE
    SYNTAX INTEGER (0..255)
    ACCESS read-only
    STATUS mandatory
    DESCRIPTION 
   "Number of active SNMP traps that have not been acknowledged."
    ::= { hpnsaTrapMgrStats 1 }

hpnsaTrapMgrNumHistory OBJECT-TYPE
    SYNTAX INTEGER (0..255)
    ACCESS read-only
    STATUS mandatory
    DESCRIPTION 
   "Number of SNMP traps in the history log."
    ::= { hpnsaTrapMgrStats 2 }

hpnsaTrapMgrMaxHistory OBJECT-TYPE
    SYNTAX INTEGER (0..255)
    ACCESS read-only
    STATUS mandatory
    DESCRIPTION 
   "Maximum number of SNMP traps allowed in the history log."
    ::= { hpnsaTrapMgrStats 3 }

hpnsaTrapMgrEraseTraps OBJECT-TYPE
    SYNTAX INTEGER {
    eraseLogNow(1234)
    }
    ACCESS read-write
    STATUS mandatory
    DESCRIPTION
   "Set this variable to integer value of 1234 in order 
    to erase the entire log area."
    ::= { hpnsaTrapMgrStats 4 }


-- *************************************************************************
-- hpnsaTrapMgrActive (1.3.6.1.4.1.11.2.23.23.4)
-- **************************************************************************

hpnsaTrapMgrActiveTable OBJECT-TYPE
    SYNTAX SEQUENCE OF HPnsaTrapMgrActiveTableEntry
    ACCESS not-accessible
    STATUS mandatory
    DESCRIPTION
   "A table that contains all active NSA SNMP traps sent by
    this server. An active traps is defined as a trap that has 
    not been acknowledged. The table is indexed by the trap handle."
    ::= { hpnsaTrapMgrActive 1 }

hpnsaTrapMgrActiveTableEntry OBJECT-TYPE
    SYNTAX HPnsaTrapMgrActiveTableEntry
    ACCESS not-accessible
    STATUS mandatory
    DESCRIPTION 
   "Information provided for each NSA SNMP trap sent by this server."
    INDEX { hpnsaTrapMgrActiveTrapHandleIndex }
    ::= { hpnsaTrapMgrActiveTable 1 }

HPnsaTrapMgrActiveTableEntry ::= SEQUENCE {
    hpnsaTrapMgrActiveTrapHandleIndex  INTEGER,
    hpnsaTrapMgrActiveTrapID           DisplayString,
    hpnsaTrapMgrActiveTimeStamp        INTEGER,
    hpnsaTrapMgrActiveSeverity         INTEGER,
    hpnsaTrapMgrActiveCustomString     DisplayString,
    hpnsaTrapMgrActiveEnterpriseID     INTEGER,
    hpnsaTrapMgrActiveSpecificID       INTEGER
}


hpnsaTrapMgrActiveTrapHandleIndex OBJECT-TYPE
    SYNTAX  INTEGER (1..65534)
    ACCESS  read-only
    STATUS  mandatory
    DESCRIPTION
   "A handle for each NSA SNMP trap that is received. The
    value of the handle starts at 1 and increments to 65534.
    Each trap received is given a handle and the handle remains
    the same even if the SNMP agent is reloaded." 
    ::= { hpnsaTrapMgrActiveTableEntry 1 }

hpnsaTrapMgrActiveTrapID OBJECT-TYPE
    SYNTAX  DisplayString (SIZE (0..50))
    ACCESS read-only
    STATUS mandatory
    DESCRIPTION
   "A unique identifier for the trap type. The format consists of
    the NSA Enterprise ID appended with the specific trap type."
    ::= { hpnsaTrapMgrActiveTableEntry 2 }

hpnsaTrapMgrActiveTimeStamp OBJECT-TYPE
    SYNTAX INTEGER
    ACCESS read-only
    STATUS mandatory
    DESCRIPTION
   "The time and date the SNMP trap was transmitted.  The format is
    based on the time in seconds since January 1, 1970 (Greenwhich
    Mean Time."
    ::= { hpnsaTrapMgrActiveTableEntry 3 }

hpnsaTrapMgrActiveSeverity OBJECT-TYPE
    SYNTAX INTEGER {
                     unknown(1),
                     informational(2),
                     normal(3),
                     warning(4),
                     critical(5)
                   }
    ACCESS read-only
    STATUS mandatory
    DESCRIPTION
   "The severity level of the SNMP trap."
    ::= { hpnsaTrapMgrActiveTableEntry 4 }

hpnsaTrapMgrActiveCustomString OBJECT-TYPE
    SYNTAX  DisplayString (SIZE (0..80))
    ACCESS  read-only
    STATUS  mandatory
    DESCRIPTION
   "The custom string typically sent with an NSA trap"
    ::= { hpnsaTrapMgrActiveTableEntry 5 }

hpnsaTrapMgrActiveEnterpriseID OBJECT-TYPE
    SYNTAX DisplayString (SIZE (0..50))
    ACCESS read-only
    STATUS mandatory
    DESCRIPTION
   "The Enterprise ID of the of the SNMP trap."
    ::= { hpnsaTrapMgrActiveTableEntry 6 }

hpnsaTrapMgrActiveSpecificID OBJECT-TYPE
    SYNTAX INTEGER (1..65535)
    ACCESS read-only
    STATUS mandatory
    DESCRIPTION
   "The Specific trap type of the SNMP trap."
    ::= { hpnsaTrapMgrActiveTableEntry 7 }

	 
-- *************************************************************************
-- hpnsaTrapMgrAck (1.3.6.1.4.1.11.2.23.23.5)
-- **************************************************************************

hpnsaTrapMgrTrapHandleAck OBJECT-TYPE
    SYNTAX  INTEGER (1..65534)
    ACCESS read-write
    STATUS mandatory
    DESCRIPTION
   "Acknowledge a trap by setting this variable to a value that
    matches a trap handle in the hpnsaTrapMgrActiveTable. Once a
    trap is acknowledged, it is removed from the active table, but
    remains in the history table."
    ::= { hpnsaTrapMgrAck 1 }


-- *************************************************************************
-- hpnsaTrapMgrHist (1.3.6.1.4.1.11.2.23.23.6)
-- **************************************************************************

hpnsaTrapMgrHistTable OBJECT-TYPE
    SYNTAX SEQUENCE OF HPnsaTrapMgrHistTableEntry
    ACCESS not-accessible
    STATUS mandatory
    DESCRIPTION
	"A table that contains a history of NSA SNMP traps sent by
    this server. The table is indexed by the trap handle."
    ::= { hpnsaTrapMgrHist 1 }

hpnsaTrapMgrHistTableEntry OBJECT-TYPE
    SYNTAX HPnsaTrapMgrHistTableEntry
    ACCESS not-accessible
    STATUS mandatory
    DESCRIPTION 
   "Information provided for each NSA SNMP trap sent by this server."
    INDEX { hpnsaTrapMgrHistTrapHandleIndex }
    ::= { hpnsaTrapMgrHistTable 1 }

HPnsaTrapMgrHistTableEntry ::= SEQUENCE {
    hpnsaTrapMgrHistTrapHandleIndex  INTEGER,
    hpnsaTrapMgrHistTrapID           DisplayString,
    hpnsaTrapMgrHistTimeStamp        INTEGER,
    hpnsaTrapMgrHistSeverity         INTEGER,
    hpnsaTrapMgrHistCustomString     DisplayString,
    hpnsaTrapMgrHistEnterpriseID     INTEGER,
    hpnsaTrapMgrHistSpecificID       INTEGER,
    hpnsaTrapMgrHistAck              INTEGER
}


hpnsaTrapMgrHistTrapHandleIndex OBJECT-TYPE
    SYNTAX  INTEGER (1..65534)
    ACCESS  read-only
    STATUS  mandatory
    DESCRIPTION
	"A handle for each NSA SNMP trap that is received. The
    value of the handle starts at 1 and increments to 65534.
    Each trap received is given a handle and the handle remains
	 the same even if the SNMP agent is reloaded." 
    ::= { hpnsaTrapMgrHistTableEntry 1 }

hpnsaTrapMgrHistTrapID OBJECT-TYPE
    SYNTAX  DisplayString (SIZE (0..50))
    ACCESS read-only
    STATUS mandatory
    DESCRIPTION
   "A unique identifier for the trap type. The format consists of
    the NSA Enterprise ID appended with the specific trap type."
    ::= { hpnsaTrapMgrHistTableEntry 2 }

hpnsaTrapMgrHistTimeStamp OBJECT-TYPE
    SYNTAX INTEGER
    ACCESS read-only
    STATUS mandatory
    DESCRIPTION
   "The time and date the SNMP trap was transmitted.  The format is
    based on the time in seconds since January 1, 1970 (Greenwhich
    Mean Time."
    ::= { hpnsaTrapMgrHistTableEntry 3 }

hpnsaTrapMgrHistSeverity OBJECT-TYPE
    SYNTAX INTEGER {
                     unknown(1),
                     informational(2),
                     normal(3),
                     warning(4),
                     critical(5)
                   }
    ACCESS read-only
    STATUS mandatory
    DESCRIPTION
	 "The severity level of the SNMP trap."
    ::= { hpnsaTrapMgrHistTableEntry 4 }

hpnsaTrapMgrHistCustomString OBJECT-TYPE
    SYNTAX  DisplayString (SIZE (0..80))
    ACCESS  read-only
    STATUS  mandatory
    DESCRIPTION
    "The custom string typically sent with an NSA trap"
    ::= { hpnsaTrapMgrHistTableEntry 5 }

hpnsaTrapMgrHistEnterpriseID OBJECT-TYPE
    SYNTAX DisplayString (SIZE (0..50))
    ACCESS read-only
    STATUS mandatory
    DESCRIPTION
	 "The actual Enterprise ID of the of the SNMP trap."
    ::= { hpnsaTrapMgrHistTableEntry 6 }

hpnsaTrapMgrHistSpecificID OBJECT-TYPE
    SYNTAX INTEGER (1..65535)
    ACCESS read-only
    STATUS mandatory
    DESCRIPTION
	 "The Specific trap type of the SNMP trap."
    ::= { hpnsaTrapMgrHistTableEntry 7 }

hpnsaTrapMgrHistAck OBJECT-TYPE
    SYNTAX INTEGER {
    active(0),
    acknowledged(1)
    }
    ACCESS read-only
    STATUS mandatory
    DESCRIPTION
    "Defines whether or not the trap has been acknowledged or not."
    ::= { hpnsaTrapMgrHistTableEntry 8 }
END
