HIPATH-WIRELESS-BRANCH-OFFICE-MIB DEFINITIONS ::= BEGIN
 
		IMPORTS
			apIndex			
				FROM HIPATH-WIRELESS-HWC-MIB			
			hiPathWirelessMgmt, hiPathWirelessModules			
				FROM HIPATH-WIRELESS-SMI			
			OBJECT-GROUP, MODULE-COMPLIANCE			
				FROM SNMPv2-CONF			
			IpAddress, Integer32, OBJECT-TYPE, MODULE-IDENTITY			
				FROM SNMPv2-SMI			
			RowStatus			
				FROM SNMPv2-TC;
	
	
--  July 29, 2005 at 14:43 GMT
-- July 29, 2005 at 14:43 GMT
		-- 1.3.6.1.4.1.4329.15.5.4
		hiPathWirelessBranchOfficeMIB MODULE-IDENTITY 
			LAST-UPDATED "200507291443Z"		-- July 29, 2005 at 14:43 GMT
			ORGANIZATION 
				"Chantry Networks Inc."
			CONTACT-INFO 
				"Behrouz Sultan
				Chantry Networks, Inc.
				
				1900 Minnesota Court, Suite 125
				Mississauga ON, L5N 3C9
				
				Email: behrouz.sultan@siemens.com
				Phone 1-905-363-6400
				Fax   1-905-567-0099"
			DESCRIPTION 
				"Branch office configuration MIB for the high path wireless LAN access controller."
			REVISION "200507291443Z"		-- July 29, 2005 at 14:43 GMT
			DESCRIPTION 
				"Initial version."
			::= { hiPathWirelessModules 4 }

		
	
	
--
-- Node definitions
--
	
		-- 1.3.6.1.4.1.4329.15.3.22
		hiPathWirelessBranchOfficeMib OBJECT IDENTIFIER ::= { hiPathWirelessMgmt 22 }

		
		-- 1.3.6.1.4.1.4329.15.3.22.1
		branchOfficeObjects OBJECT IDENTIFIER ::= { hiPathWirelessBranchOfficeMib 1 }

		
		-- 1.3.6.1.4.1.4329.15.3.22.1.1
		branchOfficeTable OBJECT-TYPE
			SYNTAX SEQUENCE OF BranchOfficeEntry
			MAX-ACCESS not-accessible
			STATUS obsolete
			DESCRIPTION
				"Table of branch office configuration values for the access points."
			::= { branchOfficeObjects 1 }

		
		-- 1.3.6.1.4.1.4329.15.3.22.1.1.1
		branchOfficeEntry OBJECT-TYPE
			SYNTAX BranchOfficeEntry
			MAX-ACCESS not-accessible
			STATUS obsolete
			DESCRIPTION
				"Branch office configuration values for a specific access point."
			INDEX { apIndex }
			::= { branchOfficeTable 1 }

		
		BranchOfficeEntry ::=
			SEQUENCE { 
				boConnectMode
					INTEGER,
				boIpAllocation
					INTEGER,
				boStaticIpAddress
					IpAddress,
				boStaticNetmask
					IpAddress,
				boStaticGateway
					IpAddress,
				boRebootOnPollFailure
					Integer32
			 }

		-- 1.3.6.1.4.1.4329.15.3.22.1.1.1.1
		boConnectMode OBJECT-TYPE
			SYNTAX INTEGER
				{
				autoDiscovery(1),
				staticConnect(2)
				}
			MAX-ACCESS read-write
			STATUS obsolete
			DESCRIPTION
				"Access point connection mode - use a static definition or service discovery."
			::= { branchOfficeEntry 1 }

		
		-- 1.3.6.1.4.1.4329.15.3.22.1.1.1.2
		boIpAllocation OBJECT-TYPE
			SYNTAX INTEGER
				{
				dhcp(1),
				static(2)
				}
			MAX-ACCESS read-write
			STATUS obsolete
			DESCRIPTION
				"Indicates if access point is to use DHCP to acquire an IP address or has a statically configured IP address."
			::= { branchOfficeEntry 2 }

		
		-- 1.3.6.1.4.1.4329.15.3.22.1.1.1.3
		boStaticIpAddress OBJECT-TYPE
			SYNTAX IpAddress
			MAX-ACCESS read-write
			STATUS obsolete
			DESCRIPTION
				"If access point is statically configured, contains the IP addres."
			::= { branchOfficeEntry 3 }

		
		-- 1.3.6.1.4.1.4329.15.3.22.1.1.1.4
		boStaticNetmask OBJECT-TYPE
			SYNTAX IpAddress
			MAX-ACCESS read-write
			STATUS obsolete
			DESCRIPTION
				"Netmask for the access point if statically configured."
			::= { branchOfficeEntry 4 }

		
		-- 1.3.6.1.4.1.4329.15.3.22.1.1.1.5
		boStaticGateway OBJECT-TYPE
			SYNTAX IpAddress
			MAX-ACCESS read-write
			STATUS obsolete
			DESCRIPTION
				"Default gateway for the access point if statically configured."
			::= { branchOfficeEntry 5 }

		
		-- 1.3.6.1.4.1.4329.15.3.22.1.1.1.6
		boRebootOnPollFailure OBJECT-TYPE
			SYNTAX Integer32
			MAX-ACCESS read-write
			STATUS obsolete
			DESCRIPTION
				"Indicates if access point should reboot on a poll failure (disabling wireless access) or continue to provide limited local wireless service."
			::= { branchOfficeEntry 6 }

		
		-- 1.3.6.1.4.1.4329.15.3.22.1.2
		branchOfficeHWCTable OBJECT-TYPE
			SYNTAX SEQUENCE OF BranchOfficeHWCEntry
			MAX-ACCESS not-accessible
			STATUS current
			DESCRIPTION
				"Contains the list of access controller IP addressIf an access point has a static."
			::= { branchOfficeObjects 2 }

		
		-- 1.3.6.1.4.1.4329.15.3.22.1.2.1
		branchOfficeHWCEntry OBJECT-TYPE
			SYNTAX BranchOfficeHWCEntry
			MAX-ACCESS not-accessible
			STATUS current
			DESCRIPTION
				"The access controller search list for an access point."
			INDEX { apIndex }
			::= { branchOfficeHWCTable 1 }

		
		BranchOfficeHWCEntry ::=
			SEQUENCE { 
				boHWCConnectOrder
					Integer32,
				boHWCIpAddress
					IpAddress,
				boHWCRowStatus
					RowStatus
			 }

		-- 1.3.6.1.4.1.4329.15.3.22.1.2.1.1
		boHWCConnectOrder OBJECT-TYPE
			SYNTAX Integer32
			MAX-ACCESS read-write
			STATUS current
			DESCRIPTION
				"The position of the access controller in the search list."
			::= { branchOfficeHWCEntry 1 }

		
		-- 1.3.6.1.4.1.4329.15.3.22.1.2.1.2
		boHWCIpAddress OBJECT-TYPE
			SYNTAX IpAddress
			MAX-ACCESS read-write
			STATUS current
			DESCRIPTION
				"IP address of the access controller."
			::= { branchOfficeHWCEntry 2 }

		
		-- 1.3.6.1.4.1.4329.15.3.22.1.2.1.3
		boHWCRowStatus OBJECT-TYPE
			SYNTAX RowStatus
			MAX-ACCESS read-write
			STATUS current
			DESCRIPTION
				"RowStatus attribute to control modification of branchOfficeHWCTable."
			::= { branchOfficeHWCEntry 3 }

		
		-- 1.3.6.1.4.1.4329.15.3.22.2
		hiPathWirelessBranchOfficeConformance OBJECT IDENTIFIER ::= { hiPathWirelessBranchOfficeMib 2 }

		
		-- 1.3.6.1.4.1.4329.15.3.22.2.1
		hiPathWirelessBranchOfficeGroup OBJECT-GROUP
			OBJECTS { boHWCRowStatus, boHWCIpAddress, boHWCConnectOrder }
			STATUS current
			DESCRIPTION 
				"Conformance group definitions for the branch office MIB."
			::= { hiPathWirelessBranchOfficeConformance 1 }

		
--  this module
		-- 1.3.6.1.4.1.4329.15.3.22.2.2
		hiPathWirelessBOConformance MODULE-COMPLIANCE
			STATUS current
			DESCRIPTION 
				"Compliance group definitions for the branch office MIB."
			MODULE -- this module
				MANDATORY-GROUPS { hiPathWirelessBranchOfficeGroup }
			::= { hiPathWirelessBranchOfficeConformance 2 }

		
		-- 1.3.6.1.4.1.4329.15.3.22.2.3
		hiPathWirelessBOObsoleteGroup OBJECT-GROUP
			OBJECTS { boConnectMode, boIpAllocation, boStaticIpAddress, boStaticNetmask, boStaticGateway, 
				boRebootOnPollFailure }
			STATUS obsolete
			DESCRIPTION 
				"Description."
			::= { hiPathWirelessBranchOfficeConformance 3 }

		
	
	END
