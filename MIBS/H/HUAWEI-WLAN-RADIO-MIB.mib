--
-- HUAWEI-WLAN-RADIO-MIB.my
-- MIB generated by MG-SOFT Visual MIB Builder Version 4.0 Build 341
-- Thursday, Nov 27, 2014 at 14:45:27
--

--
-- HUAWEI-WLAN-RADIO-MIB.my
-- MIB generated by MG-SOFT Visual MIB Builder Version 4.0 Build 341
-- Tuesday, Sep 28, 2014 at 10:27:30
--

--
-- HUAWEI-WLAN-RADIO-MIB.my
-- MIB generated by MG-SOFT Visual MIB Builder Version 4.0 Build 341
-- Tuesday, Sep 16, 2014 at 10:08:40
--

--
-- HUAWEI-WLAN-RADIO-MIB.my
-- MIB generated by MG-SOFT Visual MIB Builder Version 4.0 Build 341
-- Wednesday, May 21, 2014 at 17:20:37
--

-- HUAWEI-WLAN-RADIO-MIB.mib
-- MIB generated by MG-SOFT Visual MIB Builder Version 4.0 Build 341
-- Monday, July 7, 2014 at 14:49:15

--
-- HUAWEI-WLAN-RADIO-MIB.mib
-- MIB generated by MG-SOFT Visual MIB Builder Version 4.0 Build 341
-- Monday, May 26, 2014 at 18:56:15

--
-- HUAWEI-WLAN-RADIO-MIB-563.my
-- MIB generated by MG-SOFT Visual MIB Builder Version 4.0 Build 341
-- Tuesday, May 06, 2014 at 21:16:15
--

--  HUAWEI-WLAN-RADIO-MIB-562.my
-- MIB generated by MG-SOFT Visual MIB Builder Version 4.0 Build 341
-- Tuesday, May 06, 2014 at 10:30:27
--

--  HUAWEI-WLAN-RADIO-MIB.my
-- MIB generated by MG-SOFT Visual MIB Builder Version 3.0 Build 253
-- Friday, May 20, 2011 at 16:57:18
--

--  HUAWEI-WLAN-RADIO-MIB.mib
-- MIB generated by MG-SOFT Visual MIB Builder Version 3.0 Build 253
-- Wednesday, May 18, 2011 at 15:40:10
-- 
--  HUAWEI-WLAN-RADIO-MIB.mib
-- MIB generated by MG-SOFT Visual MIB Builder Version 3.0 Build 253
-- Sunday, May 15, 2011 at 15:52:00
-- 
--  HUAWEI-WLAN-RADIO-MIB.mib
-- MIB generated by MG-SOFT Visual MIB Builder Version 3.0 Build 253
-- Saturday, May 14, 2011 at 18:08:48
-- 
--  =========================================================================================================================================
-- Copyright (C) 2010 by  HUAWEI TECHNOLOGIES. All rights reserved.
-- Description:  The mib is used for defining the management of huawei AC at the side of the quality of wireless signal for AP MIB objects.
-- Reference: MIB description_20091130.doc, SSMP-USER-BASED-SM-MIB.mib.
-- Version: V1.18
-- History: V1.17
-- =========================================================================================================================================

	HUAWEI-WLAN-RADIO-MIB DEFINITIONS ::= BEGIN
 
		IMPORTS
			hwApRegionIndex, hwApIndex, hwApMac			
				FROM HUAWEI-WLAN-DEVICE-MIB			
			hwWlan			
				FROM HUAWEI-WLAN-MIB
			OBJECT-GROUP, MODULE-COMPLIANCE, NOTIFICATION-GROUP			
				FROM SNMPv2-CONF							
			Integer32, Unsigned32, Counter64, OBJECT-TYPE, MODULE-IDENTITY, 
			NOTIFICATION-TYPE			
				FROM SNMPv2-SMI			
			MacAddress, RowStatus, DateAndTime			
				FROM SNMPv2-TC;
	

		hwRadio MODULE-IDENTITY 
			LAST-UPDATED "201412171145Z"		-- Dec 17, 2014 at 11:45 GMT
			ORGANIZATION 
				"Huawei Technologies Co.,Ltd."
			CONTACT-INFO 
            	"Huawei Industrial Base
				   Bantian, Longgang
				   Shenzhen 518129
				   People's Republic of China
				   Website: http://www.huawei.com
				   Email: support@huawei.com
				  "
			DESCRIPTION 
				"The HUAWEI-WLAN-RADIO-MIB contains objects to realize the management of AC 
				at the side of the quality of wireless signal for AP.
				" 

			REVISION "201412171145Z"
			DESCRIPTION
				"Version: V1.18, V2R5C10."
				
            REVISION "201412161600Z"
			DESCRIPTION
				"Version: V1.17, V2R5C10 hwConnectRxOKUcastDataFrames->hwConnectRxOkUcastDataFrames."
				
			REVISION "201412161015Z"
			DESCRIPTION
				"Version: V1.16, V2R5C10 add NPE radio HT mode and GI mode."

			REVISION "201411271445Z"
			DESCRIPTION
				"Version: V1.15, V2R5C10 add radio power change reason."
				
                                                       REVISION "201409281027Z"
			DESCRIPTION
				"Version: V1.14, V2R5C10 add nodes for hwRadioQueryPowerlevel."

                                                       REVISION "201409161008Z"
			DESCRIPTION
				"Version: V1.13, V2R5C10 add radio location channel set."
				
			REVISION "201407171427Z"
			DESCRIPTION
				"Version: V1.12, V2R5C10 add radio performance stat buffer nodes."
				
			REVISION "201407111427Z"
			DESCRIPTION
				"Version: V1.11, V2R3C10 add para for NPE config change."
								
			REVISION "201407071449Z"
			DESCRIPTION
				"Version: V1.10, V2R5C00 add para for hwRadioChannelChangedNotify & add auto calibrate start-time"
				
			REVISION "201405261856Z"
			DESCRIPTION
				"Version: V1.09, V2R5C00 add para for a-msdu send"
				
			REVISION "201405061130Z"
			DESCRIPTION
				"Version: V1.08, V2R3C10 add for 'NPE' "
				
			REVISION "201402131330Z"
			DESCRIPTION
				"Version: V1.07, V2R5 add for 'rate' "	
				
 			REVISION "201401261330Z"
			DESCRIPTION
				"Version: V1.06, V2R5 add for 'delete hwRadioUserTrafficScheduler  hwMacRadioUserTrafficScheduler ' "
 			
			REVISION "201401131030Z"
			DESCRIPTION
				"Version: V1.05, V2R5 add for '[undo] legacy-station enable' "	

 			REVISION "201310231141Z"		-- October 23, 2013 at 11:41 GMT
			DESCRIPTION
				"Version: V1.04, add V2R5 MIB"	
								
 			REVISION "201309061514Z"		-- September 6, 2013 at 15:14 GMT
			DESCRIPTION
				"Version: V1.03, add mib change for DTS2013072701899 and DTS2013073103616"
							
 			REVISION "201308211514Z"		-- August 21, 2013 at 15:14 GMT
			DESCRIPTION
				"Version: V1.02, add mib change for calibrate"

			REVISION "201305211514Z"		-- May 21, 2013 at 15:14 GMT
			DESCRIPTION
				"Version: V1.03, add mib change for V2R3"

			REVISION "201011111000Z"		-- November 11, 2010 at 10:00 GMT
			DESCRIPTION
				"Version: V1.02, modify the characteristic of 80211n."
			REVISION "201005251000Z"		-- May 25, 2010 at 10:00 GMT
			DESCRIPTION
				"Version: V1.00, the initial revision of this MIB module."
			::= { hwWlan 3 }
		
	
	
--
-- Node definitions
--
	
--  Node definitions
-- 
-- Node definitions
-- 
-- Node definitions
-- 
-- 1.3.6.1.4.1.2011.6.139.3.1
-- 1.3.6.1.4.1.2011.6.139.3.1
-- 1.3.6.1.4.1.2011.6.139.3.1
		-- 1.3.6.1.4.1.2011.6.139.3.1
		hwRadioProfileTable OBJECT-TYPE
			SYNTAX SEQUENCE OF HwRadioProfileEntry
			MAX-ACCESS not-accessible
			STATUS current
			DESCRIPTION
				"Huawei radio profile table. Radio profile is aggregate of a group of configuration. 
				The content of the table contains : radio profile name, radio type, radio rate mode , the value of radio rate,
				radio channel mode, radio power mode, radio calibrate interval, radio PER threshold, radio confict rate threshold,
				radio RTS/CTS threshold, radio fragment threshold, radio short frame retry times, radio long frame retry times,
				radio support short preamble, radio DTIM interval, radio WMM profile name, radio profile row status, radio 80211n channel
				bandwidth, radio 80211n fast MCS feedback, radio 80211n guard interval mode, radio 80211n reduced Inter frame Space,
				radio 80211n AMSDU length capability, radio 80211n AMPDU length capability,	radio 80211n MCS Spatial streams,
				radio 80211n MCS modulation, radio 80211n MCS code rate. 
				    
				   The index of the radio profile table is hwRadioProfileName, A radio profile name is an unique identifier to a radio profile.
				      The detail description about the index can refer to the node hwRadioProfileName description. 
				"
			::= { hwRadio 1 }
		
--    1.3.6.1.4.1.2011.6.139.3.1.1
-- 1.3.6.1.4.1.2011.6.139.3.1.1
-- 1.3.6.1.4.1.2011.6.139.3.1.1
		-- 1.3.6.1.4.1.2011.6.139.3.1.1
		hwRadioProfileEntry OBJECT-TYPE
			SYNTAX HwRadioProfileEntry
			MAX-ACCESS not-accessible
			STATUS current
			DESCRIPTION
				"Huawei radio profile table entry. The entry of the huawei radio profile table, all the nodes of the huawei
				radio profile table are been configured. The detail of the table entry would be explained by the description
				of the nodes of the table. 
				
				The index of the radio profile table is hwRadioProfileName, A radio profile name is an unique identifier to a radio profile.
				   The detail description about the index can refer to the node hwRadioProfileName description. 
				"
			INDEX { hwRadioProfileName }
			::= { hwRadioProfileTable 1 }
		
		HwRadioProfileEntry ::=
			SEQUENCE { 
				hwRadioProfileName
					OCTET STRING,
				hwRadioType
					INTEGER,
				hwRadioRateMode
					INTEGER,
				hwRadioRateValue
					INTEGER,
				hwRadioChannelMode
					INTEGER,
				hwRadioPowerMode
					INTEGER,
				hwRadioCalibrateInterval
					Unsigned32,
				hwRadioPERThreshold
					Unsigned32,
				hwRadioConfictRateThreshold
					Unsigned32,
				hwRadioRTSThreshold
					Unsigned32,
				hwRadioFragmentThreshold
					Unsigned32,
				hwRadioShortFrameRetryTimes
					Unsigned32,
				hwRadioLongFrameRetryTimes
					Unsigned32,
				hwRadioSupportShortPreamble
					INTEGER,
				hwRadioDTIMInterval
					Unsigned32,
				hwRadioBeaconInterval
					Unsigned32,
				hwRadioWMMProfileName
					OCTET STRING,
				hwRadioProfileRowStatus
					RowStatus,
				hwRadio80211nGuardIntervalMode
					INTEGER,
				hwRadio80211nAMPDUMaxLengthExponent
					Integer32,
				hwRadioCalibrateEnable
					INTEGER,
				hwRadioInterfDetDevice
					Integer32,
				hwRadioApComInterfThreshold
					Integer32,
				hwRadioApAdjInterfThreshold
					Integer32,
				hwRadioStaInterfThreshold
					Integer32,
				hwRadioDeviceReportDuration
					Integer32,
				hwRadioRTSMode
					INTEGER,
				hwRadioWifiLight
					INTEGER,
				hwRadioBeamformingSwitch
					INTEGER,
				hwRadioWidsDevSynchronizationInt
					Integer32,
				hwRadioChannelSwitchAnnouncement
					INTEGER,
				hwRadioChannelSwitchMode
					INTEGER,
				hwRadioStaAccessSignalStrengthSwitch
					INTEGER,
				hwRadioStaAccessSignalStrengthThreshold
					Integer32,
				hwRadioBackgroundListenNeighborSwitch
					INTEGER,
				hwRadioBackgroundScanningServiceThreshold
					Integer32,
				hwRadioBackgroundScanningClientThreshold
					Integer32,
				hwRadioStaAccessRateLimitSwitch
					INTEGER,
				hwRadioStaAccessRateLimitThreshold
					INTEGER,
				hwRadioSpectrumAnalysisScanPeriod
					Integer32,
				hwRadioSpectrumAnalysisScanInterval
					Integer32,
				hwRadioHighDenseSwitch
					Integer32,
				hwRadioHighDenseMode
					Integer32,
				hwRadioStaOfflineSignalStrengthSwitch
					Integer32,
				hwRadioStaOfflineSignalStrengthThreshold
					Integer32,
				hwRadioStaOfflineRateLimitSwitch
					Integer32,
				hwRadioStaOfflineRateThreshold
					Integer32,
				hwRadioDynamicAdjustPowerSwitch
					Integer32,
				hwRadioLocationReportTime
					Integer32,
				hwRadioLocationScanInterval
					Integer32,
				hwRadioLocationScanPeriod
					Integer32,
				hwRadioAirTimeScheduleSwitch
					Integer32,
				hwRadioCalibrateScanCycle
					Unsigned32,
				hwRadioUacPolicyType
					INTEGER,
				hwRadioUacPolicySwitch
					INTEGER,
				hwRadioUacAccessThreshold
					Integer32,
				hwRadioUacRoamThreshold					
					Integer32,
				hwRadioUacHideSSIDSwitch
					INTEGER,
				hwRadio80211acGuardIntervalMode
					INTEGER,
				hwRadio80211acAMPDUMaxLengthExponent
					Integer32,
				hwRadio80211bgBasicRateSet
					OCTET STRING,
				hwRadio80211bgSupportRateSet
					OCTET STRING,
				hwRadio80211aBasicRateSet
					OCTET STRING,
				hwRadio80211aSupportRateSet
					OCTET STRING,
				hwRadio80211nSupportMCS
					OCTET STRING,
				hwRadio80211acSupportMcsMapMcs
					OCTET STRING,
				hwRadioMulticastRate2G
					Integer32,
				hwRadioMulticastRate5G
					Integer32,
				hwRadioLegacyStationEnable
					INTEGER,
				hwRadioLocationScanChannel2G
					INTEGER,
				hwRadioLocationScanChannel5G
					INTEGER,
				hwRadioAMSDUTxEnable
					INTEGER,
				hwRadioAMSDUTxMaxSubFrames
					Integer32	
			 }

--    1.3.6.1.4.1.2011.6.139.3.1.1.1
-- 1.3.6.1.4.1.2011.6.139.3.1.1.1
-- 1.3.6.1.4.1.2011.6.139.3.1.1.1
		-- 1.3.6.1.4.1.2011.6.139.3.1.1.1
		hwRadioProfileName OBJECT-TYPE
			SYNTAX OCTET STRING (SIZE (1..31))
			MAX-ACCESS not-accessible
			STATUS current
			DESCRIPTION
				"A human readable string representing the name of the radio profile.
				
				This is the (radio profile) model dependent radio profile ID.
				
				The request of the radio parofile name string in detail as follows:
				  - The length of the radio profile name at least contain 1 Byte ASCII characters,at most contain 31 Byte ASCII characters. 
				  - Any ASCII characters value must be included from 0x20 to 0x7E.
				  - The question mark ASCII characters can't be included .
				  - The double quotation marks ASCII characters can't appear at the beginning and the end. 
				  - The blank ASCII characters can't follow the double quotation marks ASCII characters.
				  - The blank ASCII characters can't appear at the beginning and the end.
				"
			::= { hwRadioProfileEntry 1 }
		
--    1.3.6.1.4.1.2011.6.139.3.1.1.2
-- 1.3.6.1.4.1.2011.6.139.3.1.1.2
-- 1.3.6.1.4.1.2011.6.139.3.1.1.2
		-- 1.3.6.1.4.1.2011.6.139.3.1.1.2
		hwRadioType OBJECT-TYPE
			SYNTAX INTEGER
				{
				auto(1),
				dot11b(2),
				dot11a(3),
				dot11g(4),
				dot11n(5),
				dot11bg(6),
				dot11an(7),
				dot11bgn(8),
				dot11gn(9),
				dot11ac(10)
				}
			MAX-ACCESS read-create
			STATUS current
			DESCRIPTION
				"The radio type is supported by the radio profile.Each radio type has its corresponding radio model.
				
				This is the (radio profile) model dependent radio profile ID.
				
				The value of the radio type will be chosen one of the following enum value:
				auto,dot11b,dot11a,dot11g,dot11n,dot11bg,dot11an,dot11bgn.
				Each eadion type will set the radio profile work on the given radio mode,and the radion has its corresponding 
				frequency range of the wireless signal. The corresponding relationship between the radion type and the radion mode 
				as follows:
				- auto,it chose the supported radio mode by the radio in itself, chose the frist reported mode defaultly.
				- dot11b, it set the radio profile work on 802.11b mode.
				- dot11a, it set the radio profile work on 802.11a mode.
				- dot11g, it set the radio profile work on 802.11g mode.
				- dot11n, it set the radio profile work on 802.11n mode.
				- dot11bg,it set the radio profile work on compatiblt mode of 802.11b and 802.11g.
				- dot11an,it set the radio profile work on compatiblt mode of 802.11a and 802.11n.
				- dot11gn,it set the radio profile work on compatiblt mode of 802.11n and 802.11g.
				- dot11bgn,it set the radio profile work on compatiblt mode of 802.11b , 802.11g and 802.11n.
					               
				Notes if the  setted radio type for the radio profile isn't the supported radion type of a radio in itself ,
				the radon wouldn't work normally .
				"
			::= { hwRadioProfileEntry 2 }
		
--    1.3.6.1.4.1.2011.6.139.3.1.1.3
-- 1.3.6.1.4.1.2011.6.139.3.1.1.3
-- 1.3.6.1.4.1.2011.6.139.3.1.1.3
		-- 1.3.6.1.4.1.2011.6.139.3.1.1.3
		hwRadioRateMode OBJECT-TYPE
			SYNTAX INTEGER
				{
				unknown(-1),
				auto(1),
				designate(2)
				}
			MAX-ACCESS read-only
			STATUS current
			DESCRIPTION
				"An object, which causes the way change to the radio support rate as the given mode when it's been modified.
				The meaning of the value in the enum list describe as following.
				Auto mode means the radio could working on all of the radio's  support rates and hwRadioRateValue has the rate, which may be below or equal max rate automaticly.
				Designate mode means you can set a radio's specified support rate by the node hwRadioRateValue.
				"
			DEFVAL { 0 }
			::= { hwRadioProfileEntry 3 }
		
--    1.3.6.1.4.1.2011.6.139.3.1.1.4
-- 1.3.6.1.4.1.2011.6.139.3.1.1.4
-- 1.3.6.1.4.1.2011.6.139.3.1.1.4
		-- 1.3.6.1.4.1.2011.6.139.3.1.1.4
		hwRadioRateValue OBJECT-TYPE
			SYNTAX INTEGER
				{
				unknown(-1),
				rate1(1),
				rate2(2),
				rate55(3),
				rate6(4),
				rate9(5),
				rate11(6),
				rate12(7),
				rate18(8),
				rate22(9),
				rate24(10),
				rate33(11),
				rate36(12),
				rate48(13),
				rate54(14)
				}
			MAX-ACCESS read-create
			STATUS current
			DESCRIPTION
				"The value of radio support rate, which is used together with the radio rate mode, designates the max rate of transmission by the radio profile.
				While the radio rate mode is auto, the radio rate value specify the max rate defaultly, and this node is useless.
				While  the radio rate mode is designate, the radio rate value specify the max rate by the way of designation as the chosed rate value.
				It will give the combination meaning of enum member. each enum member fits together as tow part,the frist part is rate which means 
				the radio rate, the second part means the magnitude of the support rate value, and the units is Mbps, such as rate1 means the max rate
				value supported by the radio profile is 1Mbps, rate2 means the max rate value supported by the radio profile is 2Mbps..., and so on.
				
				Notes the setting of this node must set the hwRadioRateMode node as designate. Please refer to the description of hwRadioRateMode.
				"
			::= { hwRadioProfileEntry 4 }
		
--    1.3.6.1.4.1.2011.6.139.3.1.1.5
-- 1.3.6.1.4.1.2011.6.139.3.1.1.5
-- 1.3.6.1.4.1.2011.6.139.3.1.1.5
		-- 1.3.6.1.4.1.2011.6.139.3.1.1.5
		hwRadioChannelMode OBJECT-TYPE
			SYNTAX INTEGER
				{
				auto(1),
				fixed(2)
				}
			MAX-ACCESS read-create
			STATUS current
			DESCRIPTION
				"The control mode of radio's channel.
				Auto means radio chooses the feat channel automatically on the basis of the detectted circumambienceis of the wireless signal in itself;
				Fixed means radio uses the channel as the configuration of administrator.
				
				Notes: The auto mode is recommended thanks to the changeful working circumambienceis of the radio wireless signal. 
				If it uses the fixed mode, must detect the working circumambienceis of the radio wireless signal for the ap fristly,
				then choose the feat channel, otherwise the wireless signal maybe coflict and it would make worse to the quality of the communication.
				"
			::= { hwRadioProfileEntry 5 }
		
--    1.3.6.1.4.1.2011.6.139.3.1.1.6
-- 1.3.6.1.4.1.2011.6.139.3.1.1.6
-- 1.3.6.1.4.1.2011.6.139.3.1.1.6
		-- 1.3.6.1.4.1.2011.6.139.3.1.1.6
		hwRadioPowerMode OBJECT-TYPE
			SYNTAX INTEGER
				{
				auto(1),
				fixed(2)
				}
			MAX-ACCESS read-create
			STATUS current
			DESCRIPTION
				"The control mode of radio's power level.
				Auto means radio chooses the feat power level automatically on the basis of the detectted circumambienceis of the wireless signal in itself;
				Fixed means radio uses the power level as the configuration of administrator.
				
				Notes: The auto mode is recommended thanks to the changeful working circumambienceis of the radio wireless signal. 
				If it uses the fixed mode, must detect the working circumambienceis of the radio wireless signal for the ap fristly,
				then choose the feat power level, otherwise the wireless signal maybe coflict and it would make worse to the quality of the communication.
				"
			::= { hwRadioProfileEntry 6 }
		
--    1.3.6.1.4.1.2011.6.139.3.1.1.7
-- 1.3.6.1.4.1.2011.6.139.3.1.1.7
-- 1.3.6.1.4.1.2011.6.139.3.1.1.7
		-- 1.3.6.1.4.1.2011.6.139.3.1.1.7
		hwRadioCalibrateInterval OBJECT-TYPE
			SYNTAX Unsigned32
			MAX-ACCESS read-create
			STATUS current
			DESCRIPTION
				"An interval uses to detect the rate of the lost signal packets and the conflicted signal packets periodically.
				If it sets the interval, radio will detect the signal quality in the configed calibrate interval. 
				the units of the interval is minute, the range of the interval is from 5 minutes to 10080 minutes,
				and the default calibrate interval is 720 minutes.
				"
			::= { hwRadioProfileEntry 7 }
		
--    1.3.6.1.4.1.2011.6.139.3.1.1.8
-- 1.3.6.1.4.1.2011.6.139.3.1.1.8
-- 1.3.6.1.4.1.2011.6.139.3.1.1.8
		-- 1.3.6.1.4.1.2011.6.139.3.1.1.8
		hwRadioPERThreshold OBJECT-TYPE
			SYNTAX Unsigned32
			MAX-ACCESS read-create
			STATUS current
			DESCRIPTION
				"A threshold standard, which uses the units percent ,gives an utmost rate to the lost signal packet or the error signal packet.
				The range of the threshold is from 3 to 50 percent, and the default PER threshold is 30 percent. If the average percent is out 
				of the threshold, the Radio's channel or power level would be changed.
				
				when the MAC layer of the radio sends a signal packet at the least speed, and retransmits it the largest times, still could 
				not receive any ACK or NACK packet, it will be thought as signal packet lost or error. 
				"
			::= { hwRadioProfileEntry 8 }
		
--    1.3.6.1.4.1.2011.6.139.3.1.1.9
-- 1.3.6.1.4.1.2011.6.139.3.1.1.9
-- 1.3.6.1.4.1.2011.6.139.3.1.1.9
		-- 1.3.6.1.4.1.2011.6.139.3.1.1.9
		hwRadioConfictRateThreshold OBJECT-TYPE
			SYNTAX Unsigned32
			MAX-ACCESS read-create
			STATUS current
			DESCRIPTION
				"A threshold standard, which uses the units percent ,gives an utmost rate to the conflicted signal packet.
				The range of the threshold is from 20 to 80 percent, and the default conflict rate threshold is 60 percent. 
				If the average percent is out of the threshold, the Radio's channel or power level would be changed.
				
				when the MAC layer of the radio sends a signal packet at the least speed, and retransmits it the largest times, still could 
				not receive any ACK packet, it will be thought as signal packet conflicted.
				"
			::= { hwRadioProfileEntry 9 }
		
--    1.3.6.1.4.1.2011.6.139.3.1.1.10
-- 1.3.6.1.4.1.2011.6.139.3.1.1.10
-- 1.3.6.1.4.1.2011.6.139.3.1.1.10
		-- 1.3.6.1.4.1.2011.6.139.3.1.1.10
		hwRadioRTSThreshold OBJECT-TYPE
			SYNTAX Unsigned32
			MAX-ACCESS read-create
			STATUS current
			DESCRIPTION
				"A threshold standard, which judges whether need to send a RTS frame, gives an utmost length to the frame packet from the MAC layer.
				Once the length of a frame from MAC layer preponderates over the RTS/CTS threshold, it needs to send RTS	frame befor the frame from MAC layer.
				the units of the  RTS/CTS threshold is byte, the range of the threshold is from 64 Bytes to 2347 Bytes,
				and the default RTS/CTS threshold is 2347 Bytes.
				"
			::= { hwRadioProfileEntry 10 }
		
--    1.3.6.1.4.1.2011.6.139.3.1.1.11
-- 1.3.6.1.4.1.2011.6.139.3.1.1.11
-- 1.3.6.1.4.1.2011.6.139.3.1.1.11
		-- 1.3.6.1.4.1.2011.6.139.3.1.1.11
		hwRadioFragmentThreshold OBJECT-TYPE
			SYNTAX Unsigned32
			MAX-ACCESS read-create
			STATUS current
			DESCRIPTION
				"A threshold standard, which judges whether need to split a frame to several frames, gives an utmost length to the frame packet from the MAC layer.
				Once the length of a frame from MAC layer preponderates over the fragment threshold, it needs to  split the frame to several splited frames.
				the units of the  fragment threshold is byte, the range of the threshold is from 64 Bytes to 2346 Bytes,
				and the default fragment threshold is 2346 Bytes.
				"
			::= { hwRadioProfileEntry 11 }
		
--    1.3.6.1.4.1.2011.6.139.3.1.1.12
-- 1.3.6.1.4.1.2011.6.139.3.1.1.12
-- 1.3.6.1.4.1.2011.6.139.3.1.1.12
		-- 1.3.6.1.4.1.2011.6.139.3.1.1.12
		hwRadioShortFrameRetryTimes OBJECT-TYPE
			SYNTAX Unsigned32
			MAX-ACCESS read-create
			STATUS current
			DESCRIPTION
				"A threshold standard, which judges whether a frame need to retry to send or discard, gives an utmost times to retry to 
				send a short frame packet from the MAC layer. A short frame means the lenth of the frame doesn't preponderate over the RTS/CTS threshold.
				Once the times to retry to send a short frame from MAC layer preponderates over the frame retry times, the frame would be discarded.
				The range of the short frame retry times is from 1 to 255 times, and the default of the short frame retry times is 7 times.
				"
			::= { hwRadioProfileEntry 12 }
		
--    1.3.6.1.4.1.2011.6.139.3.1.1.13
-- 1.3.6.1.4.1.2011.6.139.3.1.1.13
-- 1.3.6.1.4.1.2011.6.139.3.1.1.13
		-- 1.3.6.1.4.1.2011.6.139.3.1.1.13
		hwRadioLongFrameRetryTimes OBJECT-TYPE
			SYNTAX Unsigned32
			MAX-ACCESS read-create
			STATUS current
			DESCRIPTION
				"A threshold standard, which judges whether a frame need to retry to send or discard, gives an utmost times to retry to 
				send a long frame packet from the MAC layer. A long frame means the lenth of the frame preponderates over the RTS/CTS threshold.
				Once the times to retry to send a long frame from MAC layer preponderates over the frame retry times, the frame would be discarded.
				The range of the long frame retry times is from 1 to 255 times, and the default of the long frame retry times is 4 times.
				"
			::= { hwRadioProfileEntry 13 }
		
--    1.3.6.1.4.1.2011.6.139.3.1.1.14
-- 1.3.6.1.4.1.2011.6.139.3.1.1.14
-- 1.3.6.1.4.1.2011.6.139.3.1.1.14
		-- 1.3.6.1.4.1.2011.6.139.3.1.1.14
		hwRadioSupportShortPreamble OBJECT-TYPE
			SYNTAX INTEGER
				{
				disable(1),
				enable(2)
				}
			MAX-ACCESS read-create
			STATUS current
			DESCRIPTION
				"A switch flag, which set the short preamble status as enable or disable, tells whether the short preamble is supported by the radio.
				Enable means the radio supports short preamble, disable means the radio doesn't support short preamble. 
				Preamble, which is used to identify synchronization and the data packet that immediately follows, is a set of 
				bits in the front of a data packet by receiver. It recommends to use short preamble, because it can make the 
				synchronous performance of the network well. 
				Preamble includes short preamble and normal preamble, the normal preamble usually is used at the scene 
				compatible with some old kind of client network Adapter. 
				"
			::= { hwRadioProfileEntry 14 }
		
--    1.3.6.1.4.1.2011.6.139.3.1.1.15
-- 1.3.6.1.4.1.2011.6.139.3.1.1.15
-- 1.3.6.1.4.1.2011.6.139.3.1.1.15
		-- 1.3.6.1.4.1.2011.6.139.3.1.1.15
		hwRadioDTIMInterval OBJECT-TYPE
			SYNTAX Unsigned32
			MAX-ACCESS read-create
			STATUS current
			DESCRIPTION
				"An interval uses to set the parameter of DTIM periods of a radio profile. The DTIM interval means between two DTIM beacon how much 
				Beacons have been sended. 
				 
				DTIM is the abbreviation of Delivery Traffic Indication Map. AP will conserve the BTV and broadcast frames for a STA provisionally,
				when the STA is in the resting mode. If DTIM is included in a beacon from a ap to a sta, the ap will send the BTV and broadcast 
				frames which have been conserved provisionally to the STA immediately. 
				 
				The units of the DTIM interval is beacon, the range of the DTIM interval is from 1 beacon to 255 beacons,
				and the default DTIM interval is 3 beacons.
				"
			::= { hwRadioProfileEntry 15 }
		
--    1.3.6.1.4.1.2011.6.139.3.1.1.16
-- 1.3.6.1.4.1.2011.6.139.3.1.1.16
-- 1.3.6.1.4.1.2011.6.139.3.1.1.16
		-- 1.3.6.1.4.1.2011.6.139.3.1.1.16
		hwRadioBeaconInterval OBJECT-TYPE
			SYNTAX Unsigned32
			MAX-ACCESS read-create
			STATUS current
			DESCRIPTION
				"An interval uses to specify the number of TUs that a station should use for scheduling Beacon 
				transmissions. This value is transmitted in Beacon and Probe Response frames. 
				The units of the beacon interval is tu, the range of the beacon interval is from 20 tus to 1000tus,
				   and the default beacon interval is 1000 tus. 1 tu equals to 1024 ms.
				"
			::= { hwRadioProfileEntry 16 }
		
--    1.3.6.1.4.1.2011.6.139.3.1.1.17
-- 1.3.6.1.4.1.2011.6.139.3.1.1.17
-- 1.3.6.1.4.1.2011.6.139.3.1.1.17
		-- 1.3.6.1.4.1.2011.6.139.3.1.1.17
		hwRadioWMMProfileName OBJECT-TYPE
			SYNTAX OCTET STRING (SIZE (1..31))
			MAX-ACCESS read-create
			STATUS current
			DESCRIPTION
				"A human readable string representing the name of the WMM profile. WMM means WI-FI multimedia.
				
				This is the (radio profile) model dependent WMM profile ID.
				
				The request of the WMM parofile name string in detail as follows:
				  - The length of the radio profile name at least contain 1 Byte ASCII characters,at most contain 31 Byte ASCII characters. 
				  - Any ASCII characters value must be included from 0x20 to 0x7E.
				  - The question mark ASCII characters can't be included .
				  - The double quotation marks ASCII characters can't appear at the beginning and the end. 
				  - The blank ASCII characters can't follow the double quotation marks ASCII characters.
				  - The blank ASCII characters can't appear at the beginning and the end. 
				
				Notes the WMM profile name can't be binded until the corresponding WMM profile is exist. 
				"
			::= { hwRadioProfileEntry 17 }
		
--    1.3.6.1.4.1.2011.6.139.3.1.1.18
-- 1.3.6.1.4.1.2011.6.139.3.1.1.18
-- 1.3.6.1.4.1.2011.6.139.3.1.1.18
		-- 1.3.6.1.4.1.2011.6.139.3.1.1.18
		hwRadioProfileRowStatus OBJECT-TYPE
			SYNTAX RowStatus
			MAX-ACCESS read-create
			STATUS current
			DESCRIPTION
				"An object is used to create or delete a radio profile.
				
				There are some restrictions of operation of the radio profile.
				  - It needs a radio profile id for the creation of the radio profile.
				  - A newly created row for a radio profile can't bind the node hwRadioWMMProfileName, until the corresponding
				    hwRadioWMMProfileName have been set.
				  - If A newly created row for a radio profile binds the node of hwRadioRateValue and hwRadioType,
				    the value of hwRadioType must be supported radio type.
				  - If a WMM profile have been binded to a radio profile, the radio profile can't be deleted.
				"
			::= { hwRadioProfileEntry 18 }
		
--     1.3.6.1.4.1.2011.6.139.3.1.1.21
-- 1.3.6.1.4.1.2011.6.139.3.1.1.19
-- 1.3.6.1.4.1.2011.6.139.3.1.1.19
-- 1.3.6.1.4.1.2011.6.139.3.1.1.19
		-- 1.3.6.1.4.1.2011.6.139.3.1.1.19
		hwRadio80211nGuardIntervalMode OBJECT-TYPE
			SYNTAX INTEGER
				{
				unknown(-1),
				normal(1),
				short(2)
				}
			MAX-ACCESS read-create
			STATUS current
			DESCRIPTION
				"The mode uses to set the guard interval which is the necessary interval to receive and dispatch wireless signal to make the communication well.
				Normal means it sets the normal guard interval, short means it sets the short guard interval. The default guard interval mode is normal mode.
				The normal guard interval is 800 ns, and the short guard interval is 400 ns.
				If it's is not a kind of 11n or mixed with 11n AP, you can't config the it's hwRadio80211nGuardIntervalMode value. 
				When the AP changed to be other kinds, the value of hwRadio80211nGuardIntervalMode will change to be default value.
				"
			::= { hwRadioProfileEntry 19 }
		
--    1.3.6.1.4.1.2011.6.139.3.1.1.20
-- 1.3.6.1.4.1.2011.6.139.3.1.1.20
-- 1.3.6.1.4.1.2011.6.139.3.1.1.20
		-- 1.3.6.1.4.1.2011.6.139.3.1.1.20
		hwRadio80211nAMPDUMaxLengthExponent OBJECT-TYPE
			SYNTAX Integer32 (-1 | 0..3)
			MAX-ACCESS read-create
			STATUS current
			DESCRIPTION
				"The limit length of an AMPDU frame. AMPDU is the abbreviation of aggregate MAC protocol data unit.
				
				In order to reduce the spending of transmission, 80211n brings forward the frames aggregate technology that it aggregates several network 
				frames to a singlehanded 80211 frame and transmit it. There are two ways of frames aggregate, one is the AMSDU and the other is AMPDU. 
				AMPDU means it converts every network frame to 80211 frame, then aggregates serveral 80211 frames which go to the same destination to 
				a singlehanded frame and transmit it.   
				The units of the AMPDU frame is Byte, the range of the AMPDU frame is from 1024 Bytes to 65535 Bytes, and the default AMPDU frame is 1024 Bytes.
				If it's is not a kind of 11n or mixed with 11n AP, you can't config the it's AMPDU param value. 
				When the AP changed to be other kinds, the value of AMPDU param will change  to be default value.
				
				If the AMPDU param value is set to be 65535, that means the AMPDU module is closed, and if it set to be [0,3], that will enable the AMPDU module
				and set the AMPDU param value.
				"
			::= { hwRadioProfileEntry 20 }
		
--    1.3.6.1.4.1.2011.6.139.3.1.1.21
-- 1.3.6.1.4.1.2011.6.139.3.1.1.21
-- 1.3.6.1.4.1.2011.6.139.3.1.1.21
		-- 1.3.6.1.4.1.2011.6.139.3.1.1.21
		hwRadioCalibrateEnable OBJECT-TYPE
			SYNTAX INTEGER
				{
				off(1),
				on(2)
				}
			MAX-ACCESS read-create
			STATUS current
			DESCRIPTION
				"Description."
			::= { hwRadioProfileEntry 21 }
		
--    1.3.6.1.4.1.2011.6.139.3.1.1.22
-- 1.3.6.1.4.1.2011.6.139.3.1.1.22
-- 1.3.6.1.4.1.2011.6.139.3.1.1.22
		-- 1.3.6.1.4.1.2011.6.139.3.1.1.22
		hwRadioInterfDetDevice OBJECT-TYPE
			SYNTAX Integer32
			MAX-ACCESS read-create
			STATUS current
			DESCRIPTION
				"Description."
			::= { hwRadioProfileEntry 22 }
		
--    1.3.6.1.4.1.2011.6.139.3.1.1.23
-- 1.3.6.1.4.1.2011.6.139.3.1.1.23
-- 1.3.6.1.4.1.2011.6.139.3.1.1.23
		-- 1.3.6.1.4.1.2011.6.139.3.1.1.23
		hwRadioApComInterfThreshold OBJECT-TYPE
			SYNTAX Integer32
			MAX-ACCESS read-create
			STATUS current
			DESCRIPTION
				"Description."
			::= { hwRadioProfileEntry 23 }
		
--    1.3.6.1.4.1.2011.6.139.3.1.1.24
-- 1.3.6.1.4.1.2011.6.139.3.1.1.24
-- 1.3.6.1.4.1.2011.6.139.3.1.1.24
		-- 1.3.6.1.4.1.2011.6.139.3.1.1.24
		hwRadioApAdjInterfThreshold OBJECT-TYPE
			SYNTAX Integer32
			MAX-ACCESS read-create
			STATUS current
			DESCRIPTION
				"Description."
			::= { hwRadioProfileEntry 24 }
		
--    1.3.6.1.4.1.2011.6.139.3.1.1.25
-- 1.3.6.1.4.1.2011.6.139.3.1.1.25
-- 1.3.6.1.4.1.2011.6.139.3.1.1.25
		-- 1.3.6.1.4.1.2011.6.139.3.1.1.25
		hwRadioStaInterfThreshold OBJECT-TYPE
			SYNTAX Integer32
			MAX-ACCESS read-create
			STATUS current
			DESCRIPTION
				"Description."
			::= { hwRadioProfileEntry 25 }
		
		-- 1.3.6.1.4.1.2011.6.139.3.1.1.26
		hwRadioDeviceReportDuration OBJECT-TYPE
			SYNTAX Integer32 (10..3600)
			UNITS "second"
			MAX-ACCESS read-create
			STATUS current
			DESCRIPTION
				"The reporting duration of the radio device."
			DEFVAL { 300 }
			::= { hwRadioProfileEntry 26 }

		-- 1.3.6.1.4.1.2011.6.139.3.1.1.27
		hwRadioRTSMode OBJECT-TYPE
			SYNTAX INTEGER
				{
				disable(1),
				ctsToSelf(2),
				rtsCts(3)
				}
			MAX-ACCESS read-create
			STATUS current
			DESCRIPTION
				"Description."
			::= { hwRadioProfileEntry 27 }

		
		-- 1.3.6.1.4.1.2011.6.139.3.1.1.28
		hwRadioWifiLight OBJECT-TYPE
			SYNTAX INTEGER
				{
				signalStrength(1),
				traffic(2)
				}
			MAX-ACCESS read-create
			STATUS current
			DESCRIPTION
				"Description."
			::= { hwRadioProfileEntry 28 }
		
		-- 1.3.6.1.4.1.2011.6.139.3.1.1.29
		hwRadioBeamformingSwitch OBJECT-TYPE
			SYNTAX INTEGER
				{
				disable(1),
				enable(2)
				}
			MAX-ACCESS read-create
			STATUS current
			DESCRIPTION
				"Description."
			::= { hwRadioProfileEntry 29 }


	-- 1.3.6.1.4.1.2011.6.139.3.1.1.30
			-- 1.3.6.1.4.1.2011.6.139.3.1.1.30
			hwRadioWidsDevSynchronizationInt OBJECT-TYPE
				SYNTAX Integer32
				MAX-ACCESS read-write
				STATUS current
				DESCRIPTION
					"Description."
				::= { hwRadioProfileEntry 30 }
	
	-- 1.3.6.1.4.1.2011.6.139.3.1.1.31
			-- 1.3.6.1.4.1.2011.6.139.3.1.1.31
			hwRadioChannelSwitchAnnouncement OBJECT-TYPE
				SYNTAX INTEGER
					{
					disable(1),
					enable(2)
					}
				MAX-ACCESS read-create
				STATUS current
				DESCRIPTION
					"Description."
				::= { hwRadioProfileEntry 31 }
	-- 1.3.6.1.4.1.2011.6.139.3.1.1.32
			-- 1.3.6.1.4.1.2011.6.139.3.1.1.32
			hwRadioChannelSwitchMode OBJECT-TYPE
				SYNTAX INTEGER
					{
					continueTransmitting(1),
					stopTransmitting(2)
					}
				MAX-ACCESS read-create
				STATUS current
				DESCRIPTION
					"Description."
				::= { hwRadioProfileEntry 32 }
	-- 1.3.6.1.4.1.2011.6.139.3.1.1.33
			-- 1.3.6.1.4.1.2011.6.139.3.1.1.33
			hwRadioStaAccessSignalStrengthSwitch OBJECT-TYPE
				SYNTAX INTEGER
					{
					disable(1),
					enable(2)
					}
				MAX-ACCESS read-create
				STATUS current
				DESCRIPTION
					"Description."
				::= { hwRadioProfileEntry 33 }
	-- 1.3.6.1.4.1.2011.6.139.3.1.1.34
			-- 1.3.6.1.4.1.2011.6.139.3.1.1.34
             hwRadioStaAccessSignalStrengthThreshold OBJECT-TYPE
				SYNTAX Integer32
				MAX-ACCESS read-create
				STATUS current
				DESCRIPTION
					"Description."
				::= { hwRadioProfileEntry 34 }
	-- 1.3.6.1.4.1.2011.6.139.3.1.1.35
			-- 1.3.6.1.4.1.2011.6.139.3.1.1.35
			hwRadioBackgroundListenNeighborSwitch OBJECT-TYPE
				SYNTAX INTEGER
					{
					disable(1),
					enable(2)
					}
				MAX-ACCESS read-create
				STATUS current
				DESCRIPTION
					"Description."
				::= { hwRadioProfileEntry 35 }
	-- 1.3.6.1.4.1.2011.6.139.3.1.1.36
		hwRadioBackgroundScanningServiceThreshold OBJECT-TYPE
			SYNTAX Integer32
			MAX-ACCESS read-write
			STATUS current
			DESCRIPTION
				"Description."
			::= { hwRadioProfileEntry 36 }

		
	-- 1.3.6.1.4.1.2011.6.139.3.1.1.37
		hwRadioBackgroundScanningClientThreshold OBJECT-TYPE
			SYNTAX Integer32
			MAX-ACCESS read-write
			STATUS current
			DESCRIPTION
				"Description."
			::= { hwRadioProfileEntry 37 }
		-- 1.3.6.1.4.1.2011.6.139.3.1.1.38
		hwRadioStaAccessRateLimitSwitch OBJECT-TYPE
			SYNTAX INTEGER
				{
				unknown(-1),
				disable(1),
				enable(2)
				}
			MAX-ACCESS read-write
			STATUS current
			DESCRIPTION
				"Description."
			::= { hwRadioProfileEntry 38 }
		-- 1.3.6.1.4.1.2011.6.139.3.1.1.39
		hwRadioStaAccessRateLimitThreshold OBJECT-TYPE
			SYNTAX INTEGER
				{
				unknown(-1),
				rate1(1),
				rate2(2),
				rate55(3),
				rate6(4),
				rate9(5),
				rate11(6),
				rate12(7),
				rate18(8),
				rate22(9),
				rate24(10),
				rate33(11),
				rate36(12),
				rate48(13),
				rate54(14)
			}
			MAX-ACCESS read-write
			STATUS current
			DESCRIPTION
				"Description."
			::= { hwRadioProfileEntry 39 }
		-- 1.3.6.1.4.1.2011.6.139.3.1.1.40
		hwRadioSpectrumAnalysisScanPeriod OBJECT-TYPE
			SYNTAX Integer32
			MAX-ACCESS read-write
			STATUS current
			DESCRIPTION
				"Description."
			::= { hwRadioProfileEntry 40 }

		
		-- 1.3.6.1.4.1.2011.6.139.3.1.1.41
		hwRadioSpectrumAnalysisScanInterval OBJECT-TYPE
			SYNTAX Integer32
			MAX-ACCESS read-write
			STATUS current
			DESCRIPTION
				"Description."
			::= { hwRadioProfileEntry 41 }

		
		-- 1.3.6.1.4.1.2011.6.139.3.1.1.42
		hwRadioHighDenseSwitch OBJECT-TYPE
			SYNTAX Integer32 (0..1)
			MAX-ACCESS read-write
			STATUS current
			DESCRIPTION
				"0:disable
				 1:enable"
			DEFVAL { 0 }
			::= { hwRadioProfileEntry 42 }

		
		-- 1.3.6.1.4.1.2011.6.139.3.1.1.43
		hwRadioHighDenseMode OBJECT-TYPE
			SYNTAX Integer32
			MAX-ACCESS read-write
			STATUS current
			DESCRIPTION
				"0:low mode
				 1:middle mode
				 2:high mode"
			::= { hwRadioProfileEntry 43 }

		
		-- 1.3.6.1.4.1.2011.6.139.3.1.1.44
		hwRadioStaOfflineSignalStrengthSwitch OBJECT-TYPE
			SYNTAX Integer32 (0..1)
			MAX-ACCESS read-write
			STATUS current
			DESCRIPTION
				"0:disable
				 1:enable"
			DEFVAL { 0 }
			::= { hwRadioProfileEntry 44 }

		
		-- 1.3.6.1.4.1.2011.6.139.3.1.1.45
		hwRadioStaOfflineSignalStrengthThreshold OBJECT-TYPE
			SYNTAX Integer32 (-90..-20)
			UNITS "dbm"
			MAX-ACCESS read-write
			STATUS current
			DESCRIPTION
				"Description."
			DEFVAL { -70 }
			::= { hwRadioProfileEntry 45 }

		
		-- 1.3.6.1.4.1.2011.6.139.3.1.1.46
		hwRadioStaOfflineRateLimitSwitch OBJECT-TYPE
			SYNTAX Integer32 (0..1)
			MAX-ACCESS read-write
			STATUS current
			DESCRIPTION
				"0:disable
				 1:enable"
			DEFVAL { 0 }
			::= { hwRadioProfileEntry 46 }

		
		-- 1.3.6.1.4.1.2011.6.139.3.1.1.47
		hwRadioStaOfflineRateThreshold OBJECT-TYPE
			SYNTAX Integer32 (1..100)
			UNITS "%"
			MAX-ACCESS read-write
			STATUS current
			DESCRIPTION
				"Description."
			DEFVAL { 20 }
			::= { hwRadioProfileEntry 47 }

		
		-- 1.3.6.1.4.1.2011.6.139.3.1.1.48
		hwRadioDynamicAdjustPowerSwitch OBJECT-TYPE
			SYNTAX Integer32 (0..1)
			MAX-ACCESS read-write
			STATUS current
			DESCRIPTION
				"0:disable
				 1:enable"
			DEFVAL { 0 }
			::= { hwRadioProfileEntry 48 }
		-- 1.3.6.1.4.1.2011.6.139.3.1.1.49
		hwRadioLocationReportTime OBJECT-TYPE
			SYNTAX Integer32
			MAX-ACCESS read-write
			STATUS current
			DESCRIPTION			" "
			::= { hwRadioProfileEntry 49 }
		-- 1.3.6.1.4.1.2011.6.139.3.1.1.50
		hwRadioLocationScanInterval OBJECT-TYPE
			SYNTAX Integer32
			MAX-ACCESS read-write
			STATUS current
			DESCRIPTION
				" "
			::= { hwRadioProfileEntry 50 }
		-- 1.3.6.1.4.1.2011.6.139.3.1.1.51
		hwRadioLocationScanPeriod OBJECT-TYPE
			SYNTAX Integer32
			MAX-ACCESS read-write
			STATUS current
			DESCRIPTION
				" "
			::= { hwRadioProfileEntry 51 }

		
		-- 1.3.6.1.4.1.2011.6.139.3.1.1.52
		hwRadioAirTimeScheduleSwitch OBJECT-TYPE
			SYNTAX Integer32 (0..1)
			MAX-ACCESS read-write
			STATUS current
			DESCRIPTION
				"0:disable
				 1:enable"  
		    DEFVAL { 0 }
			::= { hwRadioProfileEntry 52 }

		
		-- 1.3.6.1.4.1.2011.6.139.3.1.1.53
		hwRadioCalibrateScanCycle  OBJECT-TYPE
			SYNTAX Unsigned32
			MAX-ACCESS read-write
			STATUS current
			DESCRIPTION
				"Description."
			::= { hwRadioProfileEntry 53 }
		-- 1.3.6.1.4.1.2011.6.139.3.1.1.54
		hwRadioUacPolicyType OBJECT-TYPE
			SYNTAX INTEGER
				{				
				users(1),
				channelUtilization(2)
				}
			MAX-ACCESS read-write
			STATUS current
			DESCRIPTION
				"Description."
			::= { hwRadioProfileEntry 54 }

		
		-- 1.3.6.1.4.1.2011.6.139.3.1.1.55
			hwRadioUacPolicySwitch OBJECT-TYPE
			SYNTAX INTEGER
				{				
				disable(1),
				enable(2)
				}
			MAX-ACCESS read-write
			STATUS current
			DESCRIPTION
				"Description."
			::= { hwRadioProfileEntry 55 }

		
		-- 1.3.6.1.4.1.2011.6.139.3.1.1.56
		hwRadioUacAccessThreshold OBJECT-TYPE
			SYNTAX Integer32
			MAX-ACCESS read-write
			STATUS current
			DESCRIPTION
				"when uac policy type is users, the value range from 0 to 128,
				 when uac policy type is channel utilization, the value range from 0 to 100."
			::= { hwRadioProfileEntry 56 }

		
		-- 1.3.6.1.4.1.2011.6.139.3.1.1.57
		hwRadioUacRoamThreshold OBJECT-TYPE
			SYNTAX Integer32
			MAX-ACCESS read-write
			STATUS current
			DESCRIPTION
				"when uac policy type is users, the value range from 0 to 128,
				 when uac policy type is channel utilization, the value range from 0 to 100.
				 the value of Roam threshold is bigger than access threshold."
			::= { hwRadioProfileEntry 57 }

		
		-- 1.3.6.1.4.1.2011.6.139.3.1.1.58
		hwRadioUacHideSSIDSwitch OBJECT-TYPE
			SYNTAX INTEGER
				{
				disable(1),
				enable(2)
				}
			MAX-ACCESS read-write
			STATUS current
			DESCRIPTION
				"Description."
			::= { hwRadioProfileEntry 58 }
			
		-- 1.3.6.1.4.1.2011.6.139.3.1.1.59
		hwRadio80211acGuardIntervalMode OBJECT-TYPE
			SYNTAX INTEGER
				{
				unknown(-1),
				normal(1),
				short(2)
				}
			MAX-ACCESS read-create
			STATUS current
			DESCRIPTION
				"The mode uses to set the guard interval which is the necessary interval to receive and dispatch wireless signal to make the communication well.
				Normal means it sets the normal guard interval, short means it sets the short guard interval. The default guard interval mode is normal mode.
				The normal guard interval is 800 ns, and the short guard interval is 400 ns.
				If AP is not 11ac or mixed with 11ac, you can't config the hwRadio80211acGuardIntervalMode value. 
				When the AP changed to be other kinds, the value of hwRadio80211acGuardIntervalMode will change to be default value.
				"
			::= { hwRadioProfileEntry 59 }

		-- 1.3.6.1.4.1.2011.6.139.3.1.1.60
		hwRadio80211acAMPDUMaxLengthExponent OBJECT-TYPE
			SYNTAX Integer32 (-1 | 0..7)
			MAX-ACCESS read-create
			STATUS current
			DESCRIPTION
				"The limit length of an AMPDU frame. AMPDU is the abbreviation of aggregate MAC protocol data unit.
				
				In order to reduce the spending of transmission, 80211ac brings forward the frames aggregate technology that it aggregates several network 
				frames to a singlehanded 80211 frame and transmit it. There are two ways of frames aggregate, one is the AMSDU and the other is AMPDU. 
				AMPDU means it converts every network frame to 80211 frame, then aggregates serveral 80211 frames which go to the same destination to 
				a singlehanded frame and transmit it.   
				The units of the AMPDU frame is Byte, the range of the AMPDU frame is from 1024 Bytes to 65535 Bytes, and the default AMPDU frame is 1024 Bytes.
				If AP is not 11ac or mixed with 11ac, you can't config the AMPDU param value.
				When the AP changed to be other kinds, the value of AMPDU param will change to be default value.
				
				If the AMPDU param value is set to be 65535, that means the AMPDU module is closed, and if it set to be [0,7], that will enable the AMPDU module
				and set the AMPDU param value.
				"
			::= { hwRadioProfileEntry 60 }
			
		-- 1.3.6.1.4.1.2011.6.139.3.1.1.61
		hwRadio80211bgBasicRateSet OBJECT-TYPE
			SYNTAX OCTET STRING (SIZE (0..127))
			MAX-ACCESS read-write
			STATUS current
			DESCRIPTION
				"Description."
			::= { hwRadioProfileEntry 61 }

		
		-- 1.3.6.1.4.1.2011.6.139.3.1.1.62
		hwRadio80211bgSupportRateSet OBJECT-TYPE
			SYNTAX OCTET STRING (SIZE (0..127))
			MAX-ACCESS read-write
			STATUS current
			DESCRIPTION
				"Description."
			::= { hwRadioProfileEntry 62 }

		
		-- 1.3.6.1.4.1.2011.6.139.3.1.1.63
		hwRadio80211aBasicRateSet OBJECT-TYPE
			SYNTAX OCTET STRING (SIZE (0..127))
			MAX-ACCESS read-write
			STATUS current
			DESCRIPTION
				"Description."
			::= { hwRadioProfileEntry 63 }

		
		-- 1.3.6.1.4.1.2011.6.139.3.1.1.64
		hwRadio80211aSupportRateSet OBJECT-TYPE
			SYNTAX OCTET STRING (SIZE (0..127))
			MAX-ACCESS read-write
			STATUS current
			DESCRIPTION
				"Description."
			::= { hwRadioProfileEntry 64 }

		
		-- 1.3.6.1.4.1.2011.6.139.3.1.1.65
		hwRadio80211nSupportMCS OBJECT-TYPE
			SYNTAX OCTET STRING (SIZE (0..255))
			MAX-ACCESS read-write
			STATUS current
			DESCRIPTION
				"Description."
			::= { hwRadioProfileEntry 65 }


		
		-- 1.3.6.1.4.1.2011.6.139.3.1.1.67
		hwRadio80211acSupportMcsMapMcs OBJECT-TYPE
			SYNTAX OCTET STRING (SIZE (0..255))
			MAX-ACCESS read-write
			STATUS current
			DESCRIPTION
				"Description."
			::= { hwRadioProfileEntry 67 }

		
		-- 1.3.6.1.4.1.2011.6.139.3.1.1.68
		hwRadioMulticastRate2G OBJECT-TYPE
			SYNTAX Integer32 (1 | 2 | 5 | 6 | 9 | 11 | 12 | 18 | 24 | 36 | 48 | 54)
			MAX-ACCESS read-write
			STATUS current
			DESCRIPTION
				"Description."
			::= { hwRadioProfileEntry 68 }

		
		-- 1.3.6.1.4.1.2011.6.139.3.1.1.69
		hwRadioMulticastRate5G OBJECT-TYPE
			SYNTAX Integer32 (6 | 9 | 12 | 18 | 24 | 36 | 48 | 54)
			MAX-ACCESS read-write
			STATUS current
			DESCRIPTION
				"Description."
			DEFVAL { 6 }
			::= { hwRadioProfileEntry 69 }
			
		-- 1.3.6.1.4.1.2011.6.139.3.1.1.70
		hwRadioLegacyStationEnable OBJECT-TYPE
			SYNTAX INTEGER
				{
				enable(1),
				disable(2)
				}
			MAX-ACCESS read-create
			STATUS current
			DESCRIPTION
				"Allow legacy station access.
				"
			::= { hwRadioProfileEntry 70 }
		-- 1.3.6.1.4.1.2011.6.139.3.1.1.71
		hwRadioLocationScanChannel2G OBJECT-TYPE
			SYNTAX INTEGER
				{
				countrychannel(1),
				dcachannel(2)
				}
			MAX-ACCESS read-write
			STATUS current
			DESCRIPTION
				"Description."
			::= { hwRadioProfileEntry 71 }

		
		-- 1.3.6.1.4.1.2011.6.139.3.1.1.72
		hwRadioLocationScanChannel5G OBJECT-TYPE
			SYNTAX INTEGER
				{
				countrychannel(1),
				dcachannel(2)
				}
			MAX-ACCESS read-write
			STATUS current
			DESCRIPTION
				"Description."
			::= { hwRadioProfileEntry 72 }

			
		-- 1.3.6.1.4.1.2011.6.139.3.1.1.73
		hwRadioAMSDUTxEnable OBJECT-TYPE
			SYNTAX INTEGER
				{
				disable(1),
				enable(2)
				}
			MAX-ACCESS read-create
			STATUS current
			DESCRIPTION
				"Send with A-MSDU."
			::= { hwRadioProfileEntry 73 }

			
		-- 1.3.6.1.4.1.2011.6.139.3.1.1.74
		hwRadioAMSDUTxMaxSubFrames OBJECT-TYPE
			SYNTAX Integer32 (2..15)
			MAX-ACCESS read-create
			STATUS current
			DESCRIPTION
				"The maximum number of sub MSDUs in a A-MSDU."
			DEFVAL { 2 }
			::= { hwRadioProfileEntry 74 }
-- 1.3.6.1.4.1.2011.6.139.3.2
		-- 1.3.6.1.4.1.2011.6.139.3.2
		hwRadioManageTable OBJECT-TYPE
			SYNTAX SEQUENCE OF HwRadioManageEntry
			MAX-ACCESS not-accessible
			STATUS current
			DESCRIPTION
				"Huawei radio manage table, it is aggregate of a group of management of radio, such as modification and display.
				The content of the table contains: radio ID, radio manage base BSSID, radio manage radio profile name, radio manage state,
				radio manage channel, radio manage power level, radio manage power, set radio available antenna number, set radio working channel,
				set radio working power level.
				
				The index of the radio management table is hwApIndex and hwRadioID, an Ap index is an unique identifier to a AP, A radio ID is an unique identifier to a radio.
				   The Ap index is a index import from HUAWEI-WLAN-DEVICE-MIB, the detail description about the index can refer to the node hwApIndex and hwRadioID description.
				"
			::= { hwRadio 2 }
		
		-- 1.3.6.1.4.1.2011.6.139.3.2.1
		hwRadioManageEntry OBJECT-TYPE
			SYNTAX HwRadioManageEntry
			MAX-ACCESS not-accessible
			STATUS current
			DESCRIPTION
				"Huawei radio management table entry. The entry of the huawei radio management table, all the nodes of the huawei
				radio management table are been operated here. The detail of the table entry would be explained by the description
				of the nodes of the table. 
				
				The index of the radio management table is hwApIndex and hwRadioID, an Ap index is an unique identifier to a AP, A radio ID is an unique identifier to a radio.
				   The Ap index is a index import from HUAWEI-WLAN-DEVICE-MIB, the detail description about the index can refer to the node hwApIndex and hwRadioID description.
				"
			INDEX { hwApIndex, hwRadioID }
			::= { hwRadioManageTable 1 }
		
		HwRadioManageEntry ::=
			SEQUENCE { 
				hwRadioID
					Unsigned32,
				hwRadioMngBaseBssID
					MacAddress,
				hwRadioMngRadioProfileName
					OCTET STRING,
				hwRadioMngState
					INTEGER,
				hwRadioMngChannel
					Unsigned32,
				hwRadioMngPowerLevel
					Unsigned32,
				hwRadioMngPower
					Integer32,
				hwRadioAvailableSntennaNumber
					INTEGER,
				hwRadioWorkingChannel
					Unsigned32,
				hwRadioWorkingPowerLevel
					Unsigned32,
				hwRadioWorkingPower
					Unsigned32,
				hwRadioMngChannelBandwidth
					INTEGER,
				hwRadioWorkingChannelBandwidth
					INTEGER,
				hwRadio80211nMCSValue
					Integer32,
				hwRadioWidsWorkMode
					INTEGER,
				hwRadioMngBinded                          
					INTEGER,
				hwRadioDeviceDetectEnable
					INTEGER,
				hwRadioMaxTxPwrLvl
					Integer32,
				hwRadioPwrAttRange
					Integer32,
				hwRadioPwrAttValue
					Integer32,
				hwRadioAntennaGain
					Integer32,
				hwRadioBridgeWhitelistEnable
					INTEGER,
				hwRadioBridgeWhitelistName
					OCTET STRING,
				hwRadioBridgeStpSwitch
					INTEGER,
				hwRadioBridgeSwitch
					INTEGER,
				hwRadioBridgeMode
					INTEGER,
				hwRadioUndoBridgeWhitelist
					Integer32,
				hwRadioUserTrafficScheduler
					INTEGER,
				hwRadioCountermeasuresMode
					Unsigned32,
				hwRadioFrequency
					INTEGER,
				hwRadioCountermeasuresSwitch
					INTEGER,
				hwRadioSpectrumAnalysisEnable
					Integer32,
				hwRadioWidsAttackDetEnable 
					Integer32,
				hwRadioMeshWhitelistName
					OCTET STRING,
				hwRadioUndoMeshWhitelist
					Integer32,
				hwRadioMeshRole
					INTEGER,
				hwRadioLocationEnable
					Integer32,
				hwRadioLocationScanChannelEnable
					Integer32,
				hwRadio80211nMulticastMCSValue
					Integer32,
				hwRadioSpectrogramServerReportEnable
					Integer32,
				hwRadioRadioMulticastRateValue
					INTEGER,
				hwRadio11acSpatialStream
					Integer32,
				hwRadio11acMCSValue
					Integer32,
				hwRadioActiveSwitch
					INTEGER
			 }

--    1.3.6.1.4.1.2011.6.139.3.2.1.1
-- 1.3.6.1.4.1.2011.6.139.3.2.1.1
-- 1.3.6.1.4.1.2011.6.139.3.2.1.1
		-- 1.3.6.1.4.1.2011.6.139.3.2.1.1
		hwRadioID OBJECT-TYPE
			SYNTAX Unsigned32
			MAX-ACCESS accessible-for-notify
			STATUS current
			DESCRIPTION
				"A exclusive identifier of a radio.
				The range of the radio id is from 0 to 3, and the default radio id is 0.
				Notes the setting of radio id must insure the radio of a AP exist.
				"
			::= { hwRadioManageEntry 1 }
		
--    1.3.6.1.4.1.2011.6.139.3.2.1.2
-- 1.3.6.1.4.1.2011.6.139.3.2.1.2
-- 1.3.6.1.4.1.2011.6.139.3.2.1.2
		-- 1.3.6.1.4.1.2011.6.139.3.2.1.2
		hwRadioMngBaseBssID OBJECT-TYPE
			SYNTAX MacAddress
			MAX-ACCESS read-only
			STATUS current
			DESCRIPTION
				"You can get an effective baseBssID ,only when wlan 1 is created. Or you will get a noneffective value.
                                BSSID identifies a minimum service set,When administrator binds a ESS to a radio, it use base BSSID and WlanID to 
				generate a BSSID. The format of the bssid is a max address which contains 3 sets of 2 Btyes hexadecimal character 
				join up with - character, such as 00e0-5678-12fa. 
				"
			::= { hwRadioManageEntry 2 }
		
--    1.3.6.1.4.1.2011.6.139.3.2.1.3
-- 1.3.6.1.4.1.2011.6.139.3.2.1.3
-- 1.3.6.1.4.1.2011.6.139.3.2.1.3
		-- 1.3.6.1.4.1.2011.6.139.3.2.1.3
		hwRadioMngRadioProfileName OBJECT-TYPE
			SYNTAX OCTET STRING (SIZE (1..31))
			MAX-ACCESS read-write
			STATUS current
			DESCRIPTION
				"The radio profile which is binded to this radio. 
				
				The request of the radio parofile name string in detail as follows:
				 - The length of the radio profile name at least contain 1 Byte ASCII characters,at most contain 31 Byte ASCII characters. 
				 - Any ASCII characters value must be included from 0x20 to 0x7E.
				 - The question mark ASCII characters can't be included .
				 - The double quotation marks ASCII characters can't appear at the beginning and the end. 
				 - The blank ASCII characters can't follow the double quotation marks ASCII characters.
				 - The blank ASCII characters can't appear at the beginning and the end. 
				 
				Notes the radio profile name can't be binded until the corresponding radio profile is exist. 
				"
			::= { hwRadioManageEntry 3 }
		
--    1.3.6.1.4.1.2011.6.139.3.2.1.4
-- 1.3.6.1.4.1.2011.6.139.3.2.1.4
-- 1.3.6.1.4.1.2011.6.139.3.2.1.4
		-- 1.3.6.1.4.1.2011.6.139.3.2.1.4
		hwRadioMngState OBJECT-TYPE
			SYNTAX INTEGER
				{
				disable(1),
				enable(2)
				}
			MAX-ACCESS read-write
			STATUS current
			DESCRIPTION
				"A switch flag, which set the radio status as enable or disable, tells whether the wireless signal transmission is supported by the radio.
				Enable means the radio supports transmission, disable means the radio doesn't support transmission. The default setting of the wireless 
				signal transmission is enable.
				"
			::= { hwRadioManageEntry 4 }
		
--    1.3.6.1.4.1.2011.6.139.3.2.1.5
-- 1.3.6.1.4.1.2011.6.139.3.2.1.5
-- 1.3.6.1.4.1.2011.6.139.3.2.1.5
		-- 1.3.6.1.4.1.2011.6.139.3.2.1.5
		hwRadioMngChannel OBJECT-TYPE
			SYNTAX Unsigned32
			MAX-ACCESS read-write
			STATUS current
			DESCRIPTION
				"An object uses to set the channel of a radio. 
				The value of the channel is decided by the channel mode.Such as ,the enum value of channel is 1, 6, 11 on the condition of the 80211 b/g channel mode,
				the enum value of channel is 36, 40, 44, 48, 52, 56, 60, 64, 149, 153,157, 161 on the condition80 of 80211a channel mode.
				"
			::= { hwRadioManageEntry 5 }
		
--    1.3.6.1.4.1.2011.6.139.3.2.1.6
-- 1.3.6.1.4.1.2011.6.139.3.2.1.6
-- 1.3.6.1.4.1.2011.6.139.3.2.1.6
		-- 1.3.6.1.4.1.2011.6.139.3.2.1.6
		hwRadioMngPowerLevel OBJECT-TYPE
			SYNTAX Unsigned32
			MAX-ACCESS read-write
			STATUS current
			DESCRIPTION
				"An object uses to set the power level of a radio. The range of the power level of a radio is from 0 to 3. 
				the power of power level 0 is the maximum power, the power of power level 1 is a half of the maximum power, 
				the power of power level 2 is a quarter of the maximum power, the power of power level 3 is one of eight equal parts of the maximum power.
				"
			::= { hwRadioManageEntry 6 }
		
--    1.3.6.1.4.1.2011.6.139.3.2.1.7
-- 1.3.6.1.4.1.2011.6.139.3.2.1.7
-- 1.3.6.1.4.1.2011.6.139.3.2.1.7
		-- 1.3.6.1.4.1.2011.6.139.3.2.1.7
		hwRadioMngPower OBJECT-TYPE
			SYNTAX Integer32
			MAX-ACCESS read-write
			STATUS current
			DESCRIPTION
				"An object uses to display the power (in 0.01dbm) which is currently used by this radio.
				"
			::= { hwRadioManageEntry 7 }
		
--    1.3.6.1.4.1.2011.6.139.3.2.1.8
-- 1.3.6.1.4.1.2011.6.139.3.2.1.8
-- 1.3.6.1.4.1.2011.6.139.3.2.1.8
		-- 1.3.6.1.4.1.2011.6.139.3.2.1.8
		hwRadioAvailableSntennaNumber OBJECT-TYPE
			SYNTAX INTEGER
				{
				all(1),
				num0(2),
				num1(3),
				num2(4),
				num3(5),
				num4(6),
				num5(7)
				}
			MAX-ACCESS read-create
			STATUS current
			DESCRIPTION
				"An object set the available antenna number,which can close some antennas to save electric power.
				All means it uses all the available antenna, Num1 means it uses one of the available antennas, Num2 means it uses two of the available antennas,
				Num3 means it uses three of the available antennas, Num4 means it uses four of the available antennas, Num5 means it uses five of the available antennas.
				Notes the configured available antenna number can't be larger than the real available antenna number.
				"
			::= { hwRadioManageEntry 8 }
		
--    1.3.6.1.4.1.2011.6.139.3.2.1.9
-- 1.3.6.1.4.1.2011.6.139.3.2.1.9
-- 1.3.6.1.4.1.2011.6.139.3.2.1.9
		-- 1.3.6.1.4.1.2011.6.139.3.2.1.9
		hwRadioWorkingChannel OBJECT-TYPE
			SYNTAX Unsigned32
			MAX-ACCESS read-only
			STATUS current
			DESCRIPTION
				"An object uses to display the working channel which is currently used by this radio.
				Notes the radio working channel just can be display,but can't be configured.
				"
			::= { hwRadioManageEntry 9 }
		
--    1.3.6.1.4.1.2011.6.139.3.2.1.10
-- 1.3.6.1.4.1.2011.6.139.3.2.1.10
-- 1.3.6.1.4.1.2011.6.139.3.2.1.10
		-- 1.3.6.1.4.1.2011.6.139.3.2.1.10
		hwRadioWorkingPowerLevel OBJECT-TYPE
			SYNTAX Unsigned32
			MAX-ACCESS read-only
			STATUS current
			DESCRIPTION
				"An object uses to display the working power level which is currently used by this radio.
				Notes the radio working power level just can be display,but can't be configured.
				"
			::= { hwRadioManageEntry 10 }
		
--     1.3.6.1.4.1.2011.6.139.3.2.1.11
-- 1.3.6.1.4.1.2011.6.139.3.2.1.11
-- 1.3.6.1.4.1.2011.6.139.3.2.1.11
-- 1.3.6.1.4.1.2011.6.139.3.2.1.11
		-- 1.3.6.1.4.1.2011.6.139.3.2.1.11
		hwRadioWorkingPower OBJECT-TYPE
			SYNTAX Unsigned32
			MAX-ACCESS read-only
			STATUS current
			DESCRIPTION
				"An object is used to describing the working porwer (in 0.01dbm) that the radio is working on actually.
				You just can read it when the radio is working."
			::= { hwRadioManageEntry 11 }
		
--     1.3.6.1.4.1.2011.6.139.3.2.1.12
-- 1.3.6.1.4.1.2011.6.139.3.2.1.12
-- 1.3.6.1.4.1.2011.6.139.3.2.1.12
-- 1.3.6.1.4.1.2011.6.139.3.2.1.12
		-- 1.3.6.1.4.1.2011.6.139.3.2.1.12
		hwRadioMngChannelBandwidth OBJECT-TYPE
			SYNTAX INTEGER
				{
				ht20(1),
				ht40Plus(2),
				ht40Minus(3),
				ht80(4)
				}
			MAX-ACCESS read-write
			STATUS current
			DESCRIPTION
				"An object is used to describing the bandwidth that the AP support .You can config the AP bandwidth  by the hwRadioMngChannelBandwidth,
				but the AP may be not working on  value of the your config bandwidth. you can get the actual bandwidth by hwRadioWorkingChannelBandwidth.
				At present, 802.11n AP supports three kinds of bandwidth listed in the enum, and 802.11a/b/g  AP just only supports HT20(1).
				"
			DEFVAL { 1 }
			::= { hwRadioManageEntry 12 }
		
--     1.3.6.1.4.1.2011.6.139.3.2.1.13
-- 1.3.6.1.4.1.2011.6.139.3.2.1.13
-- 1.3.6.1.4.1.2011.6.139.3.2.1.13
-- 1.3.6.1.4.1.2011.6.139.3.2.1.13
		-- 1.3.6.1.4.1.2011.6.139.3.2.1.13
		hwRadioWorkingChannelBandwidth OBJECT-TYPE
			SYNTAX INTEGER
				{
				unknown(-1),
				ht20(1),
				ht40Plus(2),
				ht40Minus(3),
				ht80(4)
				}
			MAX-ACCESS read-only
			STATUS current
			DESCRIPTION
				"An object is used to describing the bandwidth that the AP working on actually.
				the value may be unknown(-1) HT20(1) HT40-plus(2) or HT40-minus(3) ."
			::= { hwRadioManageEntry 13 }
		
--     1.3.6.1.4.1.2011.6.139.3.2.1.14
-- 1.3.6.1.4.1.2011.6.139.3.2.1.14
-- 1.3.6.1.4.1.2011.6.139.3.2.1.14
-- 1.3.6.1.4.1.2011.6.139.3.2.1.14
		-- 1.3.6.1.4.1.2011.6.139.3.2.1.14
		hwRadio80211nMCSValue OBJECT-TYPE
			SYNTAX Integer32 (-1 | 0..15)
			MAX-ACCESS read-write
			STATUS current
			DESCRIPTION
				" An object is used to describing the 802.11n AP's MCS Value. The MCS means modulation and coding scheme.
				Tha value of MCS will changed for value of spatial streams has been changed. when spatial streams's value is 1,
				MCS's value may be 0 to 7, default value is 7; when spatial streams's value is 2, MCS's value may be 0 to 15, default value is 15.
				If it is a not 802.11n AP, don't config it's MCS value.
				"
			::= { hwRadioManageEntry 14 }
		
--    1.3.6.1.4.1.2011.6.139.3.2.1.15
-- 1.3.6.1.4.1.2011.6.139.3.2.1.15
-- 1.3.6.1.4.1.2011.6.139.3.2.1.15
-- 1.3.6.1.4.1.2011.6.139.3.2.1.15
		-- 1.3.6.1.4.1.2011.6.139.3.2.1.15
		hwRadioWidsWorkMode OBJECT-TYPE
			SYNTAX INTEGER
				{
				normal(1),
				monitor(2),
				hybrid(3)
				}
			MAX-ACCESS read-write
			STATUS current
			DESCRIPTION
				"Description."
			::= { hwRadioManageEntry 15 }

--    1.3.6.1.4.1.2011.6.139.3.2.1.16
-- 1.3.6.1.4.1.2011.6.139.3.2.1.16
-- 1.3.6.1.4.1.2011.6.139.3.2.1.16			
              -- 1.3.6.1.4.1.2011.6.139.3.2.1.16			
              hwRadioMngBinded OBJECT-TYPE
                        SYNTAX INTEGER
				{
				 unknown(-1),
                                 true(1),
                                 false(2)                                  
				}
                     MAX-ACCESS read-write
                     STATUS current
                     DESCRIPTION
                                  "Object selects a mechanism for bind/unbind the radio-profile"
                     ::= { hwRadioManageEntry 16 }
		
		-- 1.3.6.1.4.1.2011.6.139.3.2.1.17
		hwRadioDeviceDetectEnable OBJECT-TYPE
			SYNTAX INTEGER
				{
				enable(1),
				disable(2)
				}
			MAX-ACCESS read-write
			STATUS current
			DESCRIPTION
				"Description."
			::= { hwRadioManageEntry 17 }

		
		-- 1.3.6.1.4.1.2011.6.139.3.2.1.18
		hwRadioMaxTxPwrLvl OBJECT-TYPE
			SYNTAX Integer32
			MAX-ACCESS read-only
			STATUS current
			DESCRIPTION
				"Description."
			::= { hwRadioManageEntry 18 }

		
		-- 1.3.6.1.4.1.2011.6.139.3.2.1.19
		hwRadioPwrAttRange OBJECT-TYPE
			SYNTAX Integer32
			MAX-ACCESS read-only
			STATUS current
			DESCRIPTION
				"Description."
			::= { hwRadioManageEntry 19 }

		
		-- 1.3.6.1.4.1.2011.6.139.3.2.1.20
		hwRadioPwrAttValue OBJECT-TYPE
			SYNTAX Integer32
			MAX-ACCESS read-only
			STATUS current
			DESCRIPTION
				"Description."
			::= { hwRadioManageEntry 20 }

		
		-- 1.3.6.1.4.1.2011.6.139.3.2.1.21
		hwRadioAntennaGain OBJECT-TYPE
			SYNTAX Integer32
			MAX-ACCESS read-write
			STATUS current
			DESCRIPTION
				"Description."
			::= { hwRadioManageEntry 21 }

		
		-- 1.3.6.1.4.1.2011.6.139.3.2.1.22
		hwRadioBridgeWhitelistEnable OBJECT-TYPE
			SYNTAX INTEGER
				{
				enable(1),
				disable(2)
				}
			MAX-ACCESS read-write
			STATUS current
			DESCRIPTION
				"Description."
			::= { hwRadioManageEntry 22 }

		
		-- 1.3.6.1.4.1.2011.6.139.3.2.1.23
		hwRadioBridgeWhitelistName OBJECT-TYPE
			SYNTAX OCTET STRING (SIZE (0..31))
			MAX-ACCESS read-write
			STATUS current
			DESCRIPTION
				"Description."
			::= { hwRadioManageEntry 23 }
		
		-- 1.3.6.1.4.1.2011.6.139.3.2.1.24
		hwRadioBridgeStpSwitch OBJECT-TYPE
			SYNTAX INTEGER
				{
				enable(1),
				disable(2)
				}
			MAX-ACCESS read-write
			STATUS current
			DESCRIPTION
				"Description."
			::= { hwRadioManageEntry 24 }

		-- 1.3.6.1.4.1.2011.6.139.3.2.1.25
		hwRadioBridgeSwitch OBJECT-TYPE
			SYNTAX INTEGER
				{
				disable(1),
				enable(2)
				}
			MAX-ACCESS read-write
			STATUS current
			DESCRIPTION
				"Description."
			::= { hwRadioManageEntry 25 }
		-- 1.3.6.1.4.1.2011.6.139.3.2.1.26
		hwRadioBridgeMode OBJECT-TYPE
			SYNTAX INTEGER
				{
				middle(1),
				root(2),
				leaf(3)
				}
			MAX-ACCESS read-write
			STATUS current
			DESCRIPTION
				"Description."
			::= { hwRadioManageEntry 26 }

		
		-- 1.3.6.1.4.1.2011.6.139.3.2.1.27
		hwRadioUndoBridgeWhitelist OBJECT-TYPE
			SYNTAX Integer32
			MAX-ACCESS read-write
			STATUS current
			DESCRIPTION
				"Description."
			::= { hwRadioManageEntry 27 }

		-- 1.3.6.1.4.1.2011.6.139.3.2.1.28
		hwRadioUserTrafficScheduler OBJECT-TYPE
			SYNTAX INTEGER
				{
				enable(1),
				disable(2)
				}
			MAX-ACCESS read-write
			STATUS obsolete
			DESCRIPTION
				"Description."
			::= { hwRadioManageEntry 28 }
		-- 1.3.6.1.4.1.2011.6.139.3.2.1.29
		hwRadioCountermeasuresMode OBJECT-TYPE
			SYNTAX Unsigned32
			MAX-ACCESS read-write
			STATUS current
			DESCRIPTION        
				"Description." 
			DEFVAL { 0 }
			::= { hwRadioManageEntry 29 }

		
		-- 1.3.6.1.4.1.2011.6.139.3.2.1.30
		hwRadioFrequency OBJECT-TYPE
			SYNTAX INTEGER
				{
				frequency2G(1),
				frequency5G(2)
				}
			MAX-ACCESS read-write
			STATUS current
			DESCRIPTION
				"Description."
			::= { hwRadioManageEntry 30 }

		-- 1.3.6.1.4.1.2011.6.139.3.2.1.31
		hwRadioCountermeasuresSwitch OBJECT-TYPE
			SYNTAX INTEGER
				{
				disable(1),
				enable(2)
				}
			MAX-ACCESS read-write
			STATUS current
			DESCRIPTION
				"Description." 
			DEFVAL { 1 }
			::= { hwRadioManageEntry 31 }
			
		-- 1.3.6.1.4.1.2011.6.139.3.2.1.32
		hwRadioSpectrumAnalysisEnable OBJECT-TYPE
			SYNTAX Integer32
			MAX-ACCESS read-write
			STATUS current
			DESCRIPTION
				"Description."
			::= { hwRadioManageEntry 32 }  
			
 		-- 1.3.6.1.4.1.2011.6.139.3.2.1.33
		hwRadioWidsAttackDetEnable OBJECT-TYPE
			SYNTAX Integer32
			MAX-ACCESS read-write
			STATUS current
			DESCRIPTION
				"Description."
			::= { hwRadioManageEntry 33 }
		  
		-- 1.3.6.1.4.1.2011.6.139.3.2.1.34
		hwRadioMeshWhitelistName OBJECT-TYPE
			SYNTAX OCTET STRING
			MAX-ACCESS read-write
			STATUS current
			DESCRIPTION
				"Description."
			::= { hwRadioManageEntry 34 }

		
		-- 1.3.6.1.4.1.2011.6.139.3.2.1.35
		hwRadioUndoMeshWhitelist OBJECT-TYPE
			SYNTAX Integer32
			MAX-ACCESS read-write
			STATUS current
			DESCRIPTION
				"Description."
			::= { hwRadioManageEntry 35 }

		
		-- 1.3.6.1.4.1.2011.6.139.3.2.1.36
		hwRadioMeshRole OBJECT-TYPE
			SYNTAX INTEGER
				{
				meshNode(1),
				meshPortal(2)
				}
			MAX-ACCESS read-write
			STATUS current
			DESCRIPTION
				"Description."
			::= { hwRadioManageEntry 36 }
		-- 1.3.6.1.4.1.2011.6.139.3.2.1.37
		hwRadioLocationEnable OBJECT-TYPE
			SYNTAX Integer32 (0..1)
			MAX-ACCESS read-write
			STATUS current
			DESCRIPTION
				"0: disable
				1: enable."
			::= { hwRadioManageEntry 37 }
		-- 1.3.6.1.4.1.2011.6.139.3.2.1.38
		hwRadioLocationScanChannelEnable OBJECT-TYPE
			SYNTAX Integer32 (0..1)
			MAX-ACCESS read-write
			STATUS current
			DESCRIPTION
				"0: disable
				1: enable."
			::= { hwRadioManageEntry 38 }

		
		-- 1.3.6.1.4.1.2011.6.139.3.2.1.39
		hwRadio80211nMulticastMCSValue OBJECT-TYPE
			SYNTAX Integer32 (-1 | 0..15)
			MAX-ACCESS read-write
			STATUS current
			DESCRIPTION
				"Description."
			::= { hwRadioManageEntry 39 }

		
		-- 1.3.6.1.4.1.2011.6.139.3.2.1.40
		hwRadioSpectrogramServerReportEnable OBJECT-TYPE
			SYNTAX Integer32 (0..1)
			MAX-ACCESS read-write
			STATUS current
			DESCRIPTION
				"0: disable
				1: enable"
			::= { hwRadioManageEntry 40 }

		
		-- 1.3.6.1.4.1.2011.6.139.3.2.1.41
		hwRadioRadioMulticastRateValue OBJECT-TYPE
			SYNTAX INTEGER
				{
				unknown(-1),
				rate1(1),
				rate2(2),
				rate55(3),
				rate6(4),
				rate9(5),
				rate11(6),
				rate12(7),
				rate18(8),
				rate24(10),
				rate36(12),
				rate48(13),
				rate54(14)
				}
			MAX-ACCESS read-write
			STATUS current
			DESCRIPTION
				"Description."
			::= { hwRadioManageEntry 41 }

		-- 1.3.6.1.4.1.2011.6.139.3.2.1.42
		hwRadio11acSpatialStream OBJECT-TYPE
			SYNTAX Integer32 (-1 | 1..3)
			MAX-ACCESS read-write
			STATUS current
			DESCRIPTION
				"Description."
			::= { hwRadioManageEntry 42 }
			
		-- 1.3.6.1.4.1.2011.6.139.3.2.1.43
		hwRadio11acMCSValue OBJECT-TYPE
			SYNTAX Integer32 (-1 | 0..9)
			MAX-ACCESS read-write
			STATUS current
			DESCRIPTION
				"Description."
			::= { hwRadioManageEntry 43 }

		
		-- 1.3.6.1.4.1.2011.6.139.3.2.1.44
		hwRadioActiveSwitch OBJECT-TYPE
			SYNTAX INTEGER
				{
				dormancy(1),
				active(2)
				}
			MAX-ACCESS read-write
			STATUS current
			DESCRIPTION
				"Mesh handover feature: Fat AP receive dormancy or active signal through snmp. 
				 When the signal is active, radio of fat ap is enable and send RARP packet;
				 When the signal is dormancy, radio of fat ap is disable."
			::= { hwRadioManageEntry 44 }

		-- 1.3.6.1.4.1.2011.6.139.3.3
		hwRadioCalibrateStatisicsTable OBJECT-TYPE
			SYNTAX SEQUENCE OF HwRadioCalibrateStatisicsEntry
			MAX-ACCESS not-accessible
			STATUS current
			DESCRIPTION
				"Huawei radio manage table, it is aggregate of a group of operation to the containing attributes of radio calibrate counters. Such as display and cleanup.
				The content of the containing attributes of radio calibrate contains: radio calibrate statistic signal bad count, radio calibrate statistic calibrate power count,
				   radio calibrate statistic calibrate channel count,radio calibrate statistic operate mode.
				
				The index of the radio calibrate statisics table is hwApIndex and hwRadioID, an Ap index is an unique identifier to a AP, A radio ID is an unique identifier to a radio.
				   The Ap index is a index import from HUAWEI-WLAN-DEVICE-MIB, the detail description about the index can refer to the node hwApIndex and hwRadioID description.
				"
			::= { hwRadio 3 }
		
--    1.3.6.1.4.1.2011.6.139.3.3.1
-- 1.3.6.1.4.1.2011.6.139.3.3.1
-- 1.3.6.1.4.1.2011.6.139.3.3.1
		-- 1.3.6.1.4.1.2011.6.139.3.3.1
		hwRadioCalibrateStatisicsEntry OBJECT-TYPE
			SYNTAX HwRadioCalibrateStatisicsEntry
			MAX-ACCESS not-accessible
			STATUS current
			DESCRIPTION
				"Huawei radio calibrate statisics entry. The entry of the huawei radio calibrate statisics table, all the nodes of the huawei
				radio calibrate statisics table are been operated here. The detail of the table entry would be explained by the description
				of the nodes of the table.
				
				The index of the radio calibrate statisics table is hwApIndex and hwRadioID, an Ap index is an unique identifier to a AP, A radio ID is an unique identifier to a radio.
				   The Ap index is a index import from HUAWEI-WLAN-DEVICE-MIB, the detail description about the index can refer to the node hwApIndex and hwRadioID description.
				"
			INDEX { hwApIndex, hwRadioID }
			::= { hwRadioCalibrateStatisicsTable 1 }
		
		HwRadioCalibrateStatisicsEntry ::=
			SEQUENCE { 
				hwRadioCalStatisSignalBadCount
					Unsigned32,
				hwRadioCalStatisCalibratePowerCount
					Unsigned32,
				hwRadioCalStatisCalibrateChannelCount
					Unsigned32,
				hwRadioCalibrateStatisicsOperMode
					INTEGER
			 }

--    1.3.6.1.4.1.2011.6.139.3.3.1.1
-- 1.3.6.1.4.1.2011.6.139.3.3.1.1
-- 1.3.6.1.4.1.2011.6.139.3.3.1.1
		-- 1.3.6.1.4.1.2011.6.139.3.3.1.1
		hwRadioCalStatisSignalBadCount OBJECT-TYPE
			SYNTAX Unsigned32
			MAX-ACCESS read-only
			STATUS current
			DESCRIPTION
				"An object uses to display the radio calibrate statistic signal bad count. This count shall increment when a rado calibration is caused by 
				bad signal qaulity, such as, once the rate of lost packet or conflicted packet preponderates over its threshold. 
				"
			::= { hwRadioCalibrateStatisicsEntry 1 }
		
--    1.3.6.1.4.1.2011.6.139.3.3.1.2
-- 1.3.6.1.4.1.2011.6.139.3.3.1.2
-- 1.3.6.1.4.1.2011.6.139.3.3.1.2
		-- 1.3.6.1.4.1.2011.6.139.3.3.1.2
		hwRadioCalStatisCalibratePowerCount OBJECT-TYPE
			SYNTAX Unsigned32
			MAX-ACCESS read-only
			STATUS current
			DESCRIPTION
				"An object uses to display the radio calibrate statistic calibrate power count. This count shall increment 
				when rado calibrates the power level of this radio.
				"
			::= { hwRadioCalibrateStatisicsEntry 2 }
		
--    1.3.6.1.4.1.2011.6.139.3.3.1.3
-- 1.3.6.1.4.1.2011.6.139.3.3.1.3
-- 1.3.6.1.4.1.2011.6.139.3.3.1.3
		-- 1.3.6.1.4.1.2011.6.139.3.3.1.3
		hwRadioCalStatisCalibrateChannelCount OBJECT-TYPE
			SYNTAX Unsigned32
			MAX-ACCESS read-only
			STATUS current
			DESCRIPTION
				"An object uses to display the radio calibrate statistic calibrate channel count. This count shall increment 
				when rado calibrates the channel of this radio.
				"
			::= { hwRadioCalibrateStatisicsEntry 3 }
		
--    1.3.6.1.4.1.2011.6.139.3.3.1.4
-- 1.3.6.1.4.1.2011.6.139.3.3.1.4
-- 1.3.6.1.4.1.2011.6.139.3.3.1.4
		-- 1.3.6.1.4.1.2011.6.139.3.3.1.4
		hwRadioCalibrateStatisicsOperMode OBJECT-TYPE
			SYNTAX INTEGER
				{
				invalid(-1),
				clearstatistic(1)
				}
			MAX-ACCESS read-write
			STATUS current
			DESCRIPTION
				"An object uses to set the radio calibrate statisics operation mode.
				Invalid means the operation is invalid, clear-statistic means it clear the radio calibrate statisics. 
				Notes it just support clear calibrate statisics, Any other operation about this node is invalid.
				"
			::= { hwRadioCalibrateStatisicsEntry 4 }
		
--    1.3.6.1.4.1.2011.6.139.3.4
-- 1.3.6.1.4.1.2011.6.139.3.4
-- 1.3.6.1.4.1.2011.6.139.3.4
		-- 1.3.6.1.4.1.2011.6.139.3.4
		hwRadioAuthNeighborInfTable OBJECT-TYPE
			SYNTAX SEQUENCE OF HwRadioAuthNeighborInfEntry
			MAX-ACCESS not-accessible
			STATUS current
			DESCRIPTION
				"Huawei radio authentic neighbor information table, it is aggregate of a group of display to the authentic neighbor AP infomation of radio.
				The authentic neighbor AP infomation of radio to display of the table contains: authentic neighbor AP ID list, authentic neighbor AP channel list,
				authentic neighbor AP front attenuation list, authentic neighbor AP back attenuation list. 
				
				The index of the radio authentic neighbor onformation table is hwApIndex and hwRadioID, an Ap index is an unique identifier to a AP, A radio ID is an unique identifier to a radio.
				   The Ap index is a index import from HUAWEI-WLAN-DEVICE-MIB, the detail description about the index can refer to the node hwApIndex and hwRadioID description.
				"
			::= { hwRadio 4 }
		
--    1.3.6.1.4.1.2011.6.139.3.4.1
-- 1.3.6.1.4.1.2011.6.139.3.4.1
-- 1.3.6.1.4.1.2011.6.139.3.4.1
		-- 1.3.6.1.4.1.2011.6.139.3.4.1
		hwRadioAuthNeighborInfEntry OBJECT-TYPE
			SYNTAX HwRadioAuthNeighborInfEntry
			MAX-ACCESS not-accessible
			STATUS current
			DESCRIPTION
				"Huawei radio authentic neighbor information table entry. The entry of the huawei radio authentic neighbor information table, all the nodes of the huawei
				radio neighbor information table are been operated here. The detail of the table entry would be explained by the description
				of the nodes of the table.
				
				The index of the radio authentic neighbor onformation table is hwApIndex and hwRadioID, an Ap index is an unique identifier to a AP, A radio ID is an unique identifier to a radio.
				   The Ap index is a index import from HUAWEI-WLAN-DEVICE-MIB, the detail description about the index can refer to the node hwApIndex and hwRadioID description.
				"
			INDEX { hwApIndex, hwRadioID }
			::= { hwRadioAuthNeighborInfTable 1 }
		
		HwRadioAuthNeighborInfEntry ::=
			SEQUENCE { 
				hwAuthenticRadioNeighborAPID
					OCTET STRING,
				hwAuthenticRadioNeighborChannel
					OCTET STRING,
				hwAuthenticRadioNeighborFrontAttenu
					OCTET STRING,
				hwAuthenticRadioNeighborBackAttenu
					OCTET STRING,
				hwAuthenticRadioNeighborSSID
					OCTET STRING
			 }

--    1.3.6.1.4.1.2011.6.139.3.4.1.1
-- 1.3.6.1.4.1.2011.6.139.3.4.1.1
-- 1.3.6.1.4.1.2011.6.139.3.4.1.1
		-- 1.3.6.1.4.1.2011.6.139.3.4.1.1
		hwAuthenticRadioNeighborAPID OBJECT-TYPE
			SYNTAX OCTET STRING
			MAX-ACCESS read-only
			STATUS current
			DESCRIPTION
				"An object uses to display the AP ID list of the authentic neighbor ap of the radio. Any of two authentic neighbor AP ID 
				of the list should separate with question mark. 
				"
			::= { hwRadioAuthNeighborInfEntry 1 }
		
--    1.3.6.1.4.1.2011.6.139.3.4.1.2
-- 1.3.6.1.4.1.2011.6.139.3.4.1.2
-- 1.3.6.1.4.1.2011.6.139.3.4.1.2
		-- 1.3.6.1.4.1.2011.6.139.3.4.1.2
		hwAuthenticRadioNeighborChannel OBJECT-TYPE
			SYNTAX OCTET STRING
			MAX-ACCESS read-only
			STATUS current
			DESCRIPTION
				"An object uses to display the signal channel list of the authentic neighbor ap of the radio. Any of two authentic 
				neighbor AP signal channel of the list should separate with question mark. 
				"
			::= { hwRadioAuthNeighborInfEntry 2 }
		
--    1.3.6.1.4.1.2011.6.139.3.4.1.3
-- 1.3.6.1.4.1.2011.6.139.3.4.1.3
-- 1.3.6.1.4.1.2011.6.139.3.4.1.3
		-- 1.3.6.1.4.1.2011.6.139.3.4.1.3
		hwAuthenticRadioNeighborFrontAttenu OBJECT-TYPE
			SYNTAX OCTET STRING
			MAX-ACCESS read-only
			STATUS current
			DESCRIPTION
				"An object uses to display the front attenuation list of the authentic neighbor ap of the radio. Any of two authentic neighbor  
				front attenuation of the list should separate with question mark.  The front attenuation indicates the attenuation of signal 
				which is send from the radio of the operating AP to the neighbor radio.
				"
			::= { hwRadioAuthNeighborInfEntry 3 }
		
--    1.3.6.1.4.1.2011.6.139.3.4.1.4
-- 1.3.6.1.4.1.2011.6.139.3.4.1.4
-- 1.3.6.1.4.1.2011.6.139.3.4.1.4
		-- 1.3.6.1.4.1.2011.6.139.3.4.1.4
		hwAuthenticRadioNeighborBackAttenu OBJECT-TYPE
			SYNTAX OCTET STRING
			MAX-ACCESS read-only
			STATUS current
			DESCRIPTION
				"An object uses to display the back attenuation list of the authentic neighbor ap of the radio. Any of two authentic neighbor  
				back attenuation of the list should separate with question mark.  The back attenuation indicates the attenuation of signal 
				which is send from the neighbor radio to the radio of the operating AP .
				"
			::= { hwRadioAuthNeighborInfEntry 4 }
		
		-- 1.3.6.1.4.1.2011.6.139.3.4.1.5
		hwAuthenticRadioNeighborSSID OBJECT-TYPE
			SYNTAX OCTET STRING
			MAX-ACCESS read-only
			STATUS current
			DESCRIPTION
				"Description."
			::= { hwRadioAuthNeighborInfEntry 5 }

--    1.3.6.1.4.1.2011.6.139.3.5
-- 1.3.6.1.4.1.2011.6.139.3.5
-- 1.3.6.1.4.1.2011.6.139.3.5
		-- 1.3.6.1.4.1.2011.6.139.3.5
		hwRadioLoadBalanceGroupTable OBJECT-TYPE
			SYNTAX SEQUENCE OF HwRadioLoadBalanceGroupEntry
			MAX-ACCESS not-accessible
			STATUS current
			DESCRIPTION
				"Huawei radio load balance group table, it is aggregate of a group of operation to load balance group and its parameter. it can balance the 
				connected use number or traffic in several radios.
				The content of the table contains: load balance group name, load balance group mode, load balance group gap threshold, load balance group 
				associate threshold, load balance group status, load balance group row status.
				
				The index of the load balance group table is hwLBGroupName, a load balance group name is an unique identifier to a oad balance group.
				   The detail description about the index can refer to the node hwLBGroupName description.
				"
			::= { hwRadio 5 }
		
--    1.3.6.1.4.1.2011.6.139.3.5.1
-- 1.3.6.1.4.1.2011.6.139.3.5.1
-- 1.3.6.1.4.1.2011.6.139.3.5.1
		-- 1.3.6.1.4.1.2011.6.139.3.5.1
		hwRadioLoadBalanceGroupEntry OBJECT-TYPE
			SYNTAX HwRadioLoadBalanceGroupEntry
			MAX-ACCESS not-accessible
			STATUS current
			DESCRIPTION
				"Huawei radio load balance group table entry. The entry of the huawei radio load balance group table, all the nodes of the huawei
				radio load balance group table are been operated here. The detail of the table entry would be explained by the description
				of the nodes of the table.
				
				The index of the load balance group table is hwLBGroupName, a load balance group name is an unique identifier to a oad balance group.
				   The detail description about the index can refer to the node hwLBGroupName description.
				"
			INDEX { hwLBGroupName }
			::= { hwRadioLoadBalanceGroupTable 1 }
		
		HwRadioLoadBalanceGroupEntry ::=
			SEQUENCE { 
				hwLBGroupName
					OCTET STRING,
				hwLBGroupMode
					INTEGER,
				hwLBGapThreshold
					Integer32,
				hwLBAssociateThreshold
					Unsigned32,
				hwLBGroupStatus
					INTEGER,
				hwLBGroupRowStatus
					RowStatus
			 }

--    1.3.6.1.4.1.2011.6.139.3.5.1.1
-- 1.3.6.1.4.1.2011.6.139.3.5.1.1
-- 1.3.6.1.4.1.2011.6.139.3.5.1.1
		-- 1.3.6.1.4.1.2011.6.139.3.5.1.1
		hwLBGroupName OBJECT-TYPE
			SYNTAX OCTET STRING
			MAX-ACCESS not-accessible
			STATUS current
			DESCRIPTION
				"A human readable string representing the name of the radio load balance group.
				
				The request of the radio radio load balance group name string in detail as follows:
				  - The length of the radio profile name at least contain 1 Byte ASCII characters,at most contain 31 Byte ASCII characters. 
				  - Any ASCII characters value must be included from 0x20 to 0x7E.
				  - The question mark ASCII characters can't be included .
				  - The double quotation marks ASCII characters can't appear at the beginning and the end. 
				  - The blank ASCII characters can't follow the double quotation marks ASCII characters.
				  - The blank ASCII characters can't appear at the beginning and the end.
				"
			::= { hwRadioLoadBalanceGroupEntry 1 }
		
--    1.3.6.1.4.1.2011.6.139.3.5.1.2
-- 1.3.6.1.4.1.2011.6.139.3.5.1.2
-- 1.3.6.1.4.1.2011.6.139.3.5.1.2
		-- 1.3.6.1.4.1.2011.6.139.3.5.1.2
		hwLBGroupMode OBJECT-TYPE
			SYNTAX INTEGER
				{
				session(1),
				traffic(2)
				}
			MAX-ACCESS read-create
			STATUS current
			DESCRIPTION
				"An object to set the load balance mode of radio load balance group. 
				Session means it adjust the radio load balance on the basis of the user numbers, traffic means it adjust the 
				radio load balance on the basis of the traffic.
				"
			::= { hwRadioLoadBalanceGroupEntry 2 }
		
--    1.3.6.1.4.1.2011.6.139.3.5.1.3
-- 1.3.6.1.4.1.2011.6.139.3.5.1.3
-- 1.3.6.1.4.1.2011.6.139.3.5.1.3
		-- 1.3.6.1.4.1.2011.6.139.3.5.1.3
		hwLBGapThreshold OBJECT-TYPE
			SYNTAX Integer32
			MAX-ACCESS read-create
			STATUS current
			DESCRIPTION
				"When connected use number or traffic gap overreach the threshold,
				the balance will be effected.
				The units of the load balance group threshold is %, the range is from 1 to 100, and the default value is 4%.
				"
			::= { hwRadioLoadBalanceGroupEntry 3 }
		
--    1.3.6.1.4.1.2011.6.139.3.5.1.4
-- 1.3.6.1.4.1.2011.6.139.3.5.1.4
-- 1.3.6.1.4.1.2011.6.139.3.5.1.4
		-- 1.3.6.1.4.1.2011.6.139.3.5.1.4
		hwLBAssociateThreshold OBJECT-TYPE
			SYNTAX Unsigned32
			MAX-ACCESS read-create
			STATUS current
			DESCRIPTION
				"When the connection request number of terminal user send to AP reachs the 
				associate threshold in one minute, and connected user number is not reach 
				the max connect	number in a radio , it must agree the user's connect request.
				The units of the load balance associae threshold is time, the range is from 1 to 30, and the default value is 6 times.
				"
			::= { hwRadioLoadBalanceGroupEntry 4 }
		
--    1.3.6.1.4.1.2011.6.139.3.5.1.5
-- 1.3.6.1.4.1.2011.6.139.3.5.1.5
-- 1.3.6.1.4.1.2011.6.139.3.5.1.5
		-- 1.3.6.1.4.1.2011.6.139.3.5.1.5
		hwLBGroupStatus OBJECT-TYPE
			SYNTAX INTEGER
				{
				unbalanced(1),
				balanced(2)
				}
			MAX-ACCESS read-only
			STATUS current
			DESCRIPTION
				"An object uses to display the load balance group status, It indicates whether the load gap is above the load balance gap threshold.
				unbalanced means the load balance gap of two radios preponderate over the maximum of the load balance gap. 
				balanced means the load balance gap of two radios don't preponderate over the maximum of the load balance gap. 
				Notes the load balance group status just can be display,but can't be modified.
				"
			::= { hwRadioLoadBalanceGroupEntry 5 }
		
--    1.3.6.1.4.1.2011.6.139.3.5.1.6
-- 1.3.6.1.4.1.2011.6.139.3.5.1.6
-- 1.3.6.1.4.1.2011.6.139.3.5.1.6
		-- 1.3.6.1.4.1.2011.6.139.3.5.1.6
		hwLBGroupRowStatus OBJECT-TYPE
			SYNTAX RowStatus
			MAX-ACCESS read-create
			STATUS current
			DESCRIPTION
				"Huawei radio load balance group rowstatus is used to create or delete a	radio load balance group.
				"
			::= { hwRadioLoadBalanceGroupEntry 6 }
		
--    1.3.6.1.4.1.2011.6.139.3.6
-- 1.3.6.1.4.1.2011.6.139.3.6
-- 1.3.6.1.4.1.2011.6.139.3.6
		-- 1.3.6.1.4.1.2011.6.139.3.6
		hwRadioLoadBalanceGroupMemberTable OBJECT-TYPE
			SYNTAX SEQUENCE OF HwRadioLoadBalanceGroupMemberEntry
			MAX-ACCESS not-accessible
			STATUS current
			DESCRIPTION
				"Huawei Radio Load Banlance Group Member Table, it describes members which is added to the Radio Load Banlance Group.  
				The content of the table contains: load balance member radio channel, load balance member radio power level, load balance member radio power,
				load balance member radio session number, load balance member radio traffic, load balance member radio row status.  
				
				The index of the radio profile table is hwLBGroupName, hwApIndex and hwRadioID, a Load Banlance Group name is an unique identifier to a Load Banlance Group, 
				an Ap index is an unique identifier to a AP, A radio ID is an unique identifier to a radio.
				   The Ap index is a index import from HUAWEI-WLAN-DEVICE-MIB, the detail description about the index can refer to the node hwLBGroupName, hwApIndex and hwRadioID description.
				"
			::= { hwRadio 6 }
		
--    1.3.6.1.4.1.2011.6.139.3.6.1
-- 1.3.6.1.4.1.2011.6.139.3.6.1
-- 1.3.6.1.4.1.2011.6.139.3.6.1
		-- 1.3.6.1.4.1.2011.6.139.3.6.1
		hwRadioLoadBalanceGroupMemberEntry OBJECT-TYPE
			SYNTAX HwRadioLoadBalanceGroupMemberEntry
			MAX-ACCESS not-accessible
			STATUS current
			DESCRIPTION
				"Huawei Radio Load Banlance Group Member table entry. The entry of the huawei radio Load Banlance Group Member table, all the nodes of the huawei
				radio Load Banlance Group Member table are been operated here. The detail of the table entry would be explained by the description
				of the nodes of the table. 
				
				The index of the radio profile table is hwLBGroupName, hwApIndex and hwRadioID, a Load Banlance Group name is an unique identifier to a Load Banlance Group, 
				an Ap index is an unique identifier to a AP, A radio ID is an unique identifier to a radio.
				   The Ap index is a index import from HUAWEI-WLAN-DEVICE-MIB, the detail description about the index can refer to the node hwLBGroupName, hwApIndex and hwRadioID description.
				"
			INDEX { hwLBGroupName, hwApIndex, hwRadioID }
			::= { hwRadioLoadBalanceGroupMemberTable 1 }
		
		HwRadioLoadBalanceGroupMemberEntry ::=
			SEQUENCE { 
				hwLBMemberRadioChannel
					Unsigned32,
				hwLBMemberRadioPowerLevel
					Unsigned32,
				hwLBMemberRadioPower
					Unsigned32,
				hwLBMemberRadioSeesionNum
					Unsigned32,
				hwLBMemberRadioTraffic
					Unsigned32,
				hwLBMemberRowStatus
					RowStatus
			 }

--    1.3.6.1.4.1.2011.6.139.3.6.1.1
-- 1.3.6.1.4.1.2011.6.139.3.6.1.1
-- 1.3.6.1.4.1.2011.6.139.3.6.1.1
		-- 1.3.6.1.4.1.2011.6.139.3.6.1.1
		hwLBMemberRadioChannel OBJECT-TYPE
			SYNTAX Unsigned32
			MAX-ACCESS read-only
			STATUS current
			DESCRIPTION
				"An object uses to display the working channel which is currently used by the load balance member radio.
				Notes the radio working channel of the load balance member radio just can be display,but can't be configured.
				"
			::= { hwRadioLoadBalanceGroupMemberEntry 1 }
		
--    1.3.6.1.4.1.2011.6.139.3.6.1.2
-- 1.3.6.1.4.1.2011.6.139.3.6.1.2
-- 1.3.6.1.4.1.2011.6.139.3.6.1.2
		-- 1.3.6.1.4.1.2011.6.139.3.6.1.2
		hwLBMemberRadioPowerLevel OBJECT-TYPE
			SYNTAX Unsigned32
			MAX-ACCESS read-only
			STATUS current
			DESCRIPTION
				"An object uses to display the working power level which is currently used by this radio.
				Notes the radio working power level just can be display,but can't be configured.
				"
			::= { hwRadioLoadBalanceGroupMemberEntry 2 }
		
--    1.3.6.1.4.1.2011.6.139.3.6.1.3
-- 1.3.6.1.4.1.2011.6.139.3.6.1.3
-- 1.3.6.1.4.1.2011.6.139.3.6.1.3
		-- 1.3.6.1.4.1.2011.6.139.3.6.1.3
		hwLBMemberRadioPower OBJECT-TYPE
			SYNTAX Unsigned32
			MAX-ACCESS read-only
			STATUS current
			DESCRIPTION
				"An object uses to display the power which is currently used by this radio.
				Notes the radio power just can be display,but can't be configured.
				"
			::= { hwRadioLoadBalanceGroupMemberEntry 3 }
		
--    1.3.6.1.4.1.2011.6.139.3.6.1.4
-- 1.3.6.1.4.1.2011.6.139.3.6.1.4
-- 1.3.6.1.4.1.2011.6.139.3.6.1.4
		-- 1.3.6.1.4.1.2011.6.139.3.6.1.4
		hwLBMemberRadioSeesionNum OBJECT-TYPE
			SYNTAX Unsigned32
			MAX-ACCESS read-only
			STATUS current
			DESCRIPTION
				"An object uses to display the connected user number which is currently used by this radio.
				Notes the radio connected user number just can be display,but can't be configured.
				"
			::= { hwRadioLoadBalanceGroupMemberEntry 4 }
		
--    1.3.6.1.4.1.2011.6.139.3.6.1.5
-- 1.3.6.1.4.1.2011.6.139.3.6.1.5
-- 1.3.6.1.4.1.2011.6.139.3.6.1.5
		-- 1.3.6.1.4.1.2011.6.139.3.6.1.5
		hwLBMemberRadioTraffic OBJECT-TYPE
			SYNTAX Unsigned32
			MAX-ACCESS read-only
			STATUS current
			DESCRIPTION
				"An object uses to display the traffic which is currently used by this radio.
				Notes the radio traffic just can be display,but can't be configured.
				"
			::= { hwRadioLoadBalanceGroupMemberEntry 5 }
		
--    1.3.6.1.4.1.2011.6.139.3.6.1.6
-- 1.3.6.1.4.1.2011.6.139.3.6.1.6
-- 1.3.6.1.4.1.2011.6.139.3.6.1.6
		-- 1.3.6.1.4.1.2011.6.139.3.6.1.6
		hwLBMemberRowStatus OBJECT-TYPE
			SYNTAX RowStatus
			MAX-ACCESS read-create
			STATUS current
			DESCRIPTION
				"Huawei Radio Load Banlance Group Member rowstatus is used to create or delete a Radio Load Banlance Group Member.
				"
			::= { hwRadioLoadBalanceGroupMemberEntry 6 }
		
--    1.3.6.1.4.1.2011.6.139.3.7
-- 1.3.6.1.4.1.2011.6.139.3.7
-- 1.3.6.1.4.1.2011.6.139.3.7
		-- 1.3.6.1.4.1.2011.6.139.3.7
		hwRadioUncontrolAPInfTable OBJECT-TYPE
			SYNTAX SEQUENCE OF HwRadioUncontrolAPInfEntry
			MAX-ACCESS not-accessible
			STATUS current
			DESCRIPTION
				"Huawei radio uncontrol ap information table,it describes the information about ap which is not authorized by AC. 
				it is aggregate of a group of display to the uncontrol AP infomation of radio. The uncontrol AP infomation of radio 
				to display of the table contains: uncontrol AP index, uncontrol ap bssid, the AP index of the uncontrol	AP neighbor,	
				Uncontrol AP channel, Uncontrol AP RSSI.  
				
				The index of the radio uncontrol ap information table is hwUncontrolAPIndex, an uncontrol Ap index is an unique identifier to a uncontrol AP.
				  The detail description about the index can refer to the node hwUncontrolAPIndex description.                  
				"
			::= { hwRadio 7 }
		
--    1.3.6.1.4.1.2011.6.139.3.7.1
-- 1.3.6.1.4.1.2011.6.139.3.7.1
-- 1.3.6.1.4.1.2011.6.139.3.7.1
		-- 1.3.6.1.4.1.2011.6.139.3.7.1
		hwRadioUncontrolAPInfEntry OBJECT-TYPE
			SYNTAX HwRadioUncontrolAPInfEntry
			MAX-ACCESS not-accessible
			STATUS current
			DESCRIPTION
				"Huawei radio uncontrol ap information table entry. The entry of the huawei radio uncontrol ap information table, all the nodes of the huawei
				radio uncontrol ap information table are been operated here. The detail of the table entry would be explained by the description
				of the nodes of the table. 
				
				The index of the radio uncontrol ap information table is hwUncontrolAPIndex, an uncontrol Ap index is an unique identifier to a uncontrol AP.
				   The detail description about the index can refer to the node hwUncontrolAPIndex description.
				"
			INDEX { hwUncontrolAPIndex }
			::= { hwRadioUncontrolAPInfTable 1 }
		
		HwRadioUncontrolAPInfEntry ::=
			SEQUENCE { 
				hwUncontrolAPIndex
					Integer32,
				hwUncontrolAPBSSID
					MacAddress,
				hwAuthAPIndex
					Integer32,
				hwUncontrolAPChannel
					Unsigned32,
				hwUncontrolAPRSSI
					Integer32,
				hwUncontrolAPSSID
					OCTET STRING
			 }

--    1.3.6.1.4.1.2011.6.139.3.7.1.1
-- 1.3.6.1.4.1.2011.6.139.3.7.1.1
-- 1.3.6.1.4.1.2011.6.139.3.7.1.1
		-- 1.3.6.1.4.1.2011.6.139.3.7.1.1
		hwUncontrolAPIndex OBJECT-TYPE
			SYNTAX Integer32
			MAX-ACCESS not-accessible
			STATUS current
			DESCRIPTION
				"An object uses to display the index of the uncontrol ap.
				Notes the index of the uncontrol ap just can be display, but can't be configured.
				"
			::= { hwRadioUncontrolAPInfEntry 1 }
		
--    1.3.6.1.4.1.2011.6.139.3.7.1.2
-- 1.3.6.1.4.1.2011.6.139.3.7.1.2
-- 1.3.6.1.4.1.2011.6.139.3.7.1.2
		-- 1.3.6.1.4.1.2011.6.139.3.7.1.2
		hwUncontrolAPBSSID OBJECT-TYPE
			SYNTAX MacAddress
			MAX-ACCESS read-only
			STATUS current
			DESCRIPTION
				"An object uses to display the BSSID of uncontrol ap. BSSID identifies a minimum service set,When administrator binds a ESS to a radio,
				it use base BSSID and WlanID to generate a BSSID. The format of the bssid is a max address which contains 3 sets of 2 Btyes hexadecimal character 
				join up with - character, such as 00e0-5678-12fa.
				Notes the BSSID of uncontrol ap just can be display, but can't be configured.
				"
			::= { hwRadioUncontrolAPInfEntry 2 }
		
--    1.3.6.1.4.1.2011.6.139.3.7.1.3
-- 1.3.6.1.4.1.2011.6.139.3.7.1.3
-- 1.3.6.1.4.1.2011.6.139.3.7.1.3
		-- 1.3.6.1.4.1.2011.6.139.3.7.1.3
		hwAuthAPIndex OBJECT-TYPE
			SYNTAX Integer32
			MAX-ACCESS read-only
			STATUS current
			DESCRIPTION
				"An object uses to display the index of the latest authentic ap.
				Notes the index of the latest authentic ap just can be display, but can't be configured.
				"
			::= { hwRadioUncontrolAPInfEntry 3 }
		
--    1.3.6.1.4.1.2011.6.139.3.7.1.4
-- 1.3.6.1.4.1.2011.6.139.3.7.1.4
-- 1.3.6.1.4.1.2011.6.139.3.7.1.4
		-- 1.3.6.1.4.1.2011.6.139.3.7.1.4
		hwUncontrolAPChannel OBJECT-TYPE
			SYNTAX Unsigned32
			MAX-ACCESS read-only
			STATUS current
			DESCRIPTION
				"An object uses to display the working channel which is currently used by the uncontrol ap.
				Notes the radio working channel of the uncontrol ap just can be display, but can't be configured.
				"
			::= { hwRadioUncontrolAPInfEntry 4 }
		
--    1.3.6.1.4.1.2011.6.139.3.7.1.5
-- 1.3.6.1.4.1.2011.6.139.3.7.1.5
-- 1.3.6.1.4.1.2011.6.139.3.7.1.5
		-- 1.3.6.1.4.1.2011.6.139.3.7.1.5
		hwUncontrolAPRSSI OBJECT-TYPE
			SYNTAX Integer32
			MAX-ACCESS read-only
			STATUS current
			DESCRIPTION
				"An object uses to display the the RSSI from uncontrol ap to this radio.
				RSSI means the signal intensity of the rceived signal.
				Notes the RSSI from uncontrol ap to the radio just can be display,but can't be configured.
				"
			::= { hwRadioUncontrolAPInfEntry 5 }
		
		-- 1.3.6.1.4.1.2011.6.139.3.7.1.6
		hwUncontrolAPSSID OBJECT-TYPE
			SYNTAX OCTET STRING
			MAX-ACCESS read-only
			STATUS current
			DESCRIPTION
				"Description."
			::= { hwRadioUncontrolAPInfEntry 6 }
--    1.3.6.1.4.1.2011.6.139.3.8
-- 1.3.6.1.4.1.2011.6.139.3.8
-- 1.3.6.1.4.1.2011.6.139.3.8
		-- 1.3.6.1.4.1.2011.6.139.3.8
		hwRadioPerformanceStatTable OBJECT-TYPE
			SYNTAX SEQUENCE OF HwRadioPerformanceStatEntry
			MAX-ACCESS not-accessible
			STATUS current
			DESCRIPTION
				"Huawei radio performance statistic table, it is aggregate of a group of operation to the performance statistic of radio calibrate counters. Such as display and cleanup.
				The content of the table contains: radio received frames, radio received bytes, radio sent frames, radio sent bytes, radio sent success RTS frames,
				radio sent unicast frames, radio sent broadcast frames, radio sent failed frames, radio received error frames, radio received physics layer error frames, 
				radio received CRC error frames, radio received MIC error frames, radio received key decrypt error frames, radio retry frames, radio error rate,
				radio channel utilization rate, radio performance Statics operate mode, radio error rate of last periods, radio received signal strength, radio down mac 
				error frames, radio received power.    
				
				The index of the radio performance statistic table is hwApIndex and hwRadioID, an Ap index is an unique identifier to a AP, A radio ID is an unique identifier to a radio.
				   The Ap index is a index import from HUAWEI-WLAN-DEVICE-MIB, the detail description about the index can refer to the node hwApIndex and hwRadioID description.
				"
			::= { hwRadio 8 }
		
--    1.3.6.1.4.1.2011.6.139.3.8.1
-- 1.3.6.1.4.1.2011.6.139.3.8.1
-- 1.3.6.1.4.1.2011.6.139.3.8.1
		-- 1.3.6.1.4.1.2011.6.139.3.8.1
		hwRadioPerformanceStatEntry OBJECT-TYPE
			SYNTAX HwRadioPerformanceStatEntry
			MAX-ACCESS not-accessible
			STATUS current
			DESCRIPTION
				"Huawei radio performance statistic table entry. The entry of the huawei radio performance statistic table, all the nodes of the huawei
				radio performance statistic table are been operated here. The detail of the table entry would be explained by the description
				of the nodes of the table.  
				
				The index of the radio performance statistic table is hwApIndex and hwRadioID, an Ap index is an unique identifier to a AP, A radio ID is an unique identifier to a radio.
				   The Ap index is a index import from HUAWEI-WLAN-DEVICE-MIB, the detail description about the index can refer to the node hwApIndex and hwRadioID description.
				"
			INDEX { hwApIndex, hwRadioID }
			::= { hwRadioPerformanceStatTable 1 }
		
		HwRadioPerformanceStatEntry ::=
			SEQUENCE { 
				hwRadioRcvFrames
					Unsigned32,
				hwRadioRcvBytes
					Unsigned32,
				hwRadioSendFrames
					Unsigned32,
				hwRadioSendBytes
					Unsigned32,
				hwRadioSendRtsSuccess
					Unsigned32,
				hwRadioSendUnicast
					Unsigned32,
				hwRadioSendBroadcast
					Unsigned32,
				hwRadioSendFailFrames
					Unsigned32,
				hwRadioRcvErrFrames
					Unsigned32,
				hwRadioRcvPhyErrFrames
					Unsigned32,
				hwRadioRcvCrcErrFrames
					Unsigned32,
				hwRadioRcvMicErrFrames
					Unsigned32,
				hwRadioRcvKeyDecryptErrFrames
					Unsigned32,
				hwRadioRetryFrames
					Unsigned32,
				hwRadioPER
					Unsigned32,
				hwRadioChUtilizationRate
					Unsigned32,
				hwRadioPerformanceStatOperMode
					INTEGER,
				hwRadioPEROfLastPeriod
					Unsigned32,
				hwRadioRcvSignalStrength
					Integer32,
				hwRadioDownMacErrFrames
					Unsigned32,
				hwRadioRcvPower
					Integer32,
				hwRadioRcvUnicastFrames
					Counter64,
				hwRadioRcvMngFrames
					Counter64,
				hwRadioRcvCtrlFrames
					Counter64,
				hwRadioRcvDataFrames
					Counter64,
				hwRadioSendMngFrames
					Counter64,
				hwRadioSendCtrlFrames
					Counter64,
				hwRadioSendDataFrames
					Counter64,
				hwRadioStaMaxSignalStrength
					Integer32,
				hwRadioStaMinSignalStrength
					Integer32,
				hwRadioStaAvgSignalStrength
					Integer32,
				hwRadioSendRate
					Unsigned32,
				hwRadioRecvRate
					Unsigned32,
				hwRadioDropRate
					Unsigned32,
				hwRadioAirPortDhcpFrames
					Counter64,
				hwRadioAirPortEapolFrames
					Counter64,
				hwRadioAirPortPsPollFrames
					Counter64,
				hwRadioAssocRequestFrames
					Counter64,
				hwRadioAssocResponseFrames
					Counter64,
				hwRadioReassocRequestFrames
					Counter64,
				hwRadioReassocResponseFrames
					Counter64,
				hwRadioDisassocFrames
					Counter64,
				hwRadioDisauthFrames
					Counter64,
				hwRadioRcvFrames64Bits
					Counter64,
				hwRadioRcvBytes64Bits
					Counter64,
				hwRadioSendFrames64Bits
					Counter64,
				hwRadioSendBytes64Bits
					Counter64,
				hwRadioSendRtsSuccess64Bits
					Counter64,
				hwRadioSendUnicast64Bits
					Counter64,
				hwRadioSendBroadcast64Bits
					Counter64,
				hwRadioSendFailFrames64Bits
					Counter64,
				hwRadioRcvErrFrames64Bits
					Counter64,
				hwRadioRcvPhyErrFrames64Bits
					Counter64,
				hwRadioRcvCrcErrFrames64Bits
					Counter64,
				hwRadioRcvMicErrFrames64Bits
					Counter64,
				hwRadioRcvKeyDecryptErrFrames64Bits
					Counter64,
				hwRadioRetryFrames64Bits
					Counter64,
				hwRadioDownMacErrFrames64Bits
					Counter64,
				hwRadioNoise
					Integer32,
				hwRadioActualBandwidth
					Unsigned32,
				hwRadioFrames
					Counter64,
				hwRadioSendDropFrames64Bits
					Counter64,
				hwRadioRcvDropFrames64Bits
					Counter64,
				hwRadioChannelFreeRate
					Unsigned32,
				hwRadioTxRate
					Unsigned32,
				hwRadioRxRate
					Unsigned32,
				hwRadioChInterferenceRate
					Unsigned32
			 }

--    1.3.6.1.4.1.2011.6.139.3.8.1.1
-- 1.3.6.1.4.1.2011.6.139.3.8.1.1
-- 1.3.6.1.4.1.2011.6.139.3.8.1.1
		-- 1.3.6.1.4.1.2011.6.139.3.8.1.1
		hwRadioRcvFrames OBJECT-TYPE
			SYNTAX Unsigned32
			MAX-ACCESS read-only
			STATUS current
			DESCRIPTION
				"An object uses to display the counter of wireless received frames.
				Notes the counter of wireless received frames just can be display, but can't be configured.
				"
			::= { hwRadioPerformanceStatEntry 1 }
		
--    1.3.6.1.4.1.2011.6.139.3.8.1.2
-- 1.3.6.1.4.1.2011.6.139.3.8.1.2
-- 1.3.6.1.4.1.2011.6.139.3.8.1.2
		-- 1.3.6.1.4.1.2011.6.139.3.8.1.2
		hwRadioRcvBytes OBJECT-TYPE
			SYNTAX Unsigned32
			MAX-ACCESS read-only
			STATUS current
			DESCRIPTION
				"An object uses to display the counter of wireless received bytes.
				Notes the counter of wireless received bytes just can be display, but can't be configured.
				"
			::= { hwRadioPerformanceStatEntry 2 }
		
--    1.3.6.1.4.1.2011.6.139.3.8.1.3
-- 1.3.6.1.4.1.2011.6.139.3.8.1.3
-- 1.3.6.1.4.1.2011.6.139.3.8.1.3
		-- 1.3.6.1.4.1.2011.6.139.3.8.1.3
		hwRadioSendFrames OBJECT-TYPE
			SYNTAX Unsigned32
			MAX-ACCESS read-only
			STATUS current
			DESCRIPTION
				"An object uses to display the counter of wireless transmitted frames.
				Notes the counter of wireless transmitted frames just can be display, but can't be configured.
				"
			::= { hwRadioPerformanceStatEntry 3 }
		
--    1.3.6.1.4.1.2011.6.139.3.8.1.4
-- 1.3.6.1.4.1.2011.6.139.3.8.1.4
-- 1.3.6.1.4.1.2011.6.139.3.8.1.4
		-- 1.3.6.1.4.1.2011.6.139.3.8.1.4
		hwRadioSendBytes OBJECT-TYPE
			SYNTAX Unsigned32
			MAX-ACCESS read-only
			STATUS current
			DESCRIPTION
				"An object uses to display the counter of wireless transmitted bytes.
				Notes the counter of wireless transmitted bytes just can be display, but can't be configured.
				"
			::= { hwRadioPerformanceStatEntry 4 }
		
--    1.3.6.1.4.1.2011.6.139.3.8.1.5
-- 1.3.6.1.4.1.2011.6.139.3.8.1.5
-- 1.3.6.1.4.1.2011.6.139.3.8.1.5
		-- 1.3.6.1.4.1.2011.6.139.3.8.1.5
		hwRadioSendRtsSuccess OBJECT-TYPE
			SYNTAX Unsigned32
			MAX-ACCESS read-only
			STATUS current
			DESCRIPTION
				"An object uses to display the counter of wireless transmitted RTS successes.
				Notes the counter of wireless transmitted RTS successes just can be display, but can't be configured.
				"
			::= { hwRadioPerformanceStatEntry 5 }
		
--    1.3.6.1.4.1.2011.6.139.3.8.1.6
-- 1.3.6.1.4.1.2011.6.139.3.8.1.6
-- 1.3.6.1.4.1.2011.6.139.3.8.1.6
		-- 1.3.6.1.4.1.2011.6.139.3.8.1.6
		hwRadioSendUnicast OBJECT-TYPE
			SYNTAX Unsigned32
			MAX-ACCESS read-only
			STATUS current
			DESCRIPTION
				"An object uses to display the counter of wireless transmitted unicast frames.
				Notes the counter of wireless transmitted unicast frames just can be display, but can't be configured.
				"
			::= { hwRadioPerformanceStatEntry 6 }
		
--    1.3.6.1.4.1.2011.6.139.3.8.1.7
-- 1.3.6.1.4.1.2011.6.139.3.8.1.7
-- 1.3.6.1.4.1.2011.6.139.3.8.1.7
		-- 1.3.6.1.4.1.2011.6.139.3.8.1.7
		hwRadioSendBroadcast OBJECT-TYPE
			SYNTAX Unsigned32
			MAX-ACCESS read-only
			STATUS current
			DESCRIPTION
				"An object uses to display the counter of wireless transmitted broadcast frames.
				Notes the counter of wireless transmitted broadcast frames just can be display, but can't be configured.
				"
			::= { hwRadioPerformanceStatEntry 7 }
		
--    1.3.6.1.4.1.2011.6.139.3.8.1.8
-- 1.3.6.1.4.1.2011.6.139.3.8.1.8
-- 1.3.6.1.4.1.2011.6.139.3.8.1.8
		-- 1.3.6.1.4.1.2011.6.139.3.8.1.8
		hwRadioSendFailFrames OBJECT-TYPE
			SYNTAX Unsigned32
			MAX-ACCESS read-only
			STATUS current
			DESCRIPTION
				"An object uses to display the counter of wireless transmitted failure frames.
				Notes the counter of wireless transmitted failure frames just can be display, but can't be configured.
				"
			::= { hwRadioPerformanceStatEntry 8 }
		
--    1.3.6.1.4.1.2011.6.139.3.8.1.9
-- 1.3.6.1.4.1.2011.6.139.3.8.1.9
-- 1.3.6.1.4.1.2011.6.139.3.8.1.9
		-- 1.3.6.1.4.1.2011.6.139.3.8.1.9
		hwRadioRcvErrFrames OBJECT-TYPE
			SYNTAX Unsigned32
			MAX-ACCESS read-only
			STATUS current
			DESCRIPTION
				"An object uses to display the counter of wireless received error frames.
				Notes the counter of wireless received error frames just can be display, but can't be configured.
				"
			::= { hwRadioPerformanceStatEntry 9 }
		
--    1.3.6.1.4.1.2011.6.139.3.8.1.10
-- 1.3.6.1.4.1.2011.6.139.3.8.1.10
-- 1.3.6.1.4.1.2011.6.139.3.8.1.10
		-- 1.3.6.1.4.1.2011.6.139.3.8.1.10
		hwRadioRcvPhyErrFrames OBJECT-TYPE
			SYNTAX Unsigned32
			MAX-ACCESS read-only
			STATUS current
			DESCRIPTION
				"An object uses to display the counter of wireless received physical layer frames.
				Notes the counter of wireless received physical layer frames just can be display, but can't be configured.
				"
			::= { hwRadioPerformanceStatEntry 10 }
		
--    1.3.6.1.4.1.2011.6.139.3.8.1.11
-- 1.3.6.1.4.1.2011.6.139.3.8.1.11
-- 1.3.6.1.4.1.2011.6.139.3.8.1.11
		-- 1.3.6.1.4.1.2011.6.139.3.8.1.11
		hwRadioRcvCrcErrFrames OBJECT-TYPE
			SYNTAX Unsigned32
			MAX-ACCESS read-only
			STATUS current
			DESCRIPTION
				"An object uses to display the counter of received CRC error frames.	CRC means the circulative redundancy code, CRC error frame is
				one of the FCS error frames.
				Notes the counter of received CRC error frames just can be display, but can't be configured.
				"
			::= { hwRadioPerformanceStatEntry 11 }
		
--    1.3.6.1.4.1.2011.6.139.3.8.1.12
-- 1.3.6.1.4.1.2011.6.139.3.8.1.12
-- 1.3.6.1.4.1.2011.6.139.3.8.1.12
		-- 1.3.6.1.4.1.2011.6.139.3.8.1.12
		hwRadioRcvMicErrFrames OBJECT-TYPE
			SYNTAX Unsigned32
			MAX-ACCESS read-only
			STATUS current
			DESCRIPTION
				"An object uses to display the counter of wireless received MIC error frames.
				Notes the counter of wireless received MIC error frames just can be display, but can't be configured.
				"
			::= { hwRadioPerformanceStatEntry 12 }
		
--    1.3.6.1.4.1.2011.6.139.3.8.1.13
-- 1.3.6.1.4.1.2011.6.139.3.8.1.13
-- 1.3.6.1.4.1.2011.6.139.3.8.1.13
		-- 1.3.6.1.4.1.2011.6.139.3.8.1.13
		hwRadioRcvKeyDecryptErrFrames OBJECT-TYPE
			SYNTAX Unsigned32
			MAX-ACCESS read-only
			STATUS current
			DESCRIPTION
				"An object uses to display the counter of wireless received private key and decrypt fail frames.
				Notes the counter of wireless received private key and decrypt fail frames just can be display, but can't be configured.
				"
			::= { hwRadioPerformanceStatEntry 13 }
		
--    1.3.6.1.4.1.2011.6.139.3.8.1.14
-- 1.3.6.1.4.1.2011.6.139.3.8.1.14
-- 1.3.6.1.4.1.2011.6.139.3.8.1.14
		-- 1.3.6.1.4.1.2011.6.139.3.8.1.14
		hwRadioRetryFrames OBJECT-TYPE
			SYNTAX Unsigned32
			MAX-ACCESS read-only
			STATUS current
			DESCRIPTION
				"An object uses to display the counter of wireless retry frames.
				Notes the counter of wireless retry frames just can be display, but can't be configured.
				"
			::= { hwRadioPerformanceStatEntry 14 }
		
--    1.3.6.1.4.1.2011.6.139.3.8.1.15
-- 1.3.6.1.4.1.2011.6.139.3.8.1.15
-- 1.3.6.1.4.1.2011.6.139.3.8.1.15
		-- 1.3.6.1.4.1.2011.6.139.3.8.1.15
		hwRadioPER OBJECT-TYPE
			SYNTAX Unsigned32
			MAX-ACCESS read-only
			STATUS current
			DESCRIPTION
				"An object uses to display the wireless PER(packet error rate.
				Notes the wireless PER(packet error rate just can be display, but can't be configured.
				"
			::= { hwRadioPerformanceStatEntry 15 }
		
--    1.3.6.1.4.1.2011.6.139.3.8.1.16
-- 1.3.6.1.4.1.2011.6.139.3.8.1.16
-- 1.3.6.1.4.1.2011.6.139.3.8.1.16
		-- 1.3.6.1.4.1.2011.6.139.3.8.1.16
		hwRadioChUtilizationRate OBJECT-TYPE
			SYNTAX Unsigned32
			MAX-ACCESS read-only
			STATUS current
			DESCRIPTION
				"An object uses to display the wireless channel utilization of the radio.
				Notes the wireless channel utilization of the radio just can be display, but can't be configured.
				"
			::= { hwRadioPerformanceStatEntry 16 }
		
--    1.3.6.1.4.1.2011.6.139.3.8.1.17
-- 1.3.6.1.4.1.2011.6.139.3.8.1.17
-- 1.3.6.1.4.1.2011.6.139.3.8.1.17
		-- 1.3.6.1.4.1.2011.6.139.3.8.1.17
		hwRadioPerformanceStatOperMode OBJECT-TYPE
			SYNTAX INTEGER
				{
				invalid(-1),
				clearstatistic(1)
				}
			MAX-ACCESS read-write
			STATUS current
			DESCRIPTION
				"An object uses to set the radio performance statisics operation mode.
				Invalid means the operation is invalid, clear-statistic means it clear the radio performance statisics. 
				Notes it just support clear performance statisics, Any other operation about this node is invalid.
				"
			::= { hwRadioPerformanceStatEntry 17 }
		
--    1.3.6.1.4.1.2011.6.139.3.8.1.18
-- 1.3.6.1.4.1.2011.6.139.3.8.1.18
-- 1.3.6.1.4.1.2011.6.139.3.8.1.18
		-- 1.3.6.1.4.1.2011.6.139.3.8.1.18
		hwRadioPEROfLastPeriod OBJECT-TYPE
			SYNTAX Unsigned32
			MAX-ACCESS read-only
			STATUS current
			DESCRIPTION
				"An object uses to display the wireless error rate of the last statistic period.
				Notes the wireless error rate of the last statistic period just can be display, but can't be configured.
				"
			::= { hwRadioPerformanceStatEntry 18 }
		
--    1.3.6.1.4.1.2011.6.139.3.8.1.19
-- 1.3.6.1.4.1.2011.6.139.3.8.1.19
-- 1.3.6.1.4.1.2011.6.139.3.8.1.19
		-- 1.3.6.1.4.1.2011.6.139.3.8.1.19
		hwRadioRcvSignalStrength OBJECT-TYPE
			SYNTAX Integer32
			MAX-ACCESS read-only
			STATUS current
			DESCRIPTION
				"An object uses to display the wireless received signal strength.
				Notes the wireless received signal strength just can be display, but can't be configured.
				"
			::= { hwRadioPerformanceStatEntry 19 }
		
--    1.3.6.1.4.1.2011.6.139.3.8.1.20
-- 1.3.6.1.4.1.2011.6.139.3.8.1.20
-- 1.3.6.1.4.1.2011.6.139.3.8.1.20
		-- 1.3.6.1.4.1.2011.6.139.3.8.1.20
		hwRadioDownMacErrFrames OBJECT-TYPE
			SYNTAX Unsigned32
			MAX-ACCESS read-only
			STATUS obsolete
			DESCRIPTION
				"An object uses to display the counter of wireless down-stream MAC error frames.
				Notes the counter of wireless down-stream MAC error frames just can be display, but can't be configured.
				"
			::= { hwRadioPerformanceStatEntry 20 }
		
--    1.3.6.1.4.1.2011.6.139.3.8.1.21
-- 1.3.6.1.4.1.2011.6.139.3.8.1.21
-- 1.3.6.1.4.1.2011.6.139.3.8.1.21
		-- 1.3.6.1.4.1.2011.6.139.3.8.1.21
		hwRadioRcvPower OBJECT-TYPE
			SYNTAX Integer32
			MAX-ACCESS read-only
			STATUS current
			DESCRIPTION
				"An object uses to display the receive power of the radio.
				Notes the receive power of the radio just can be display, but can't be configured.
				"
			::= { hwRadioPerformanceStatEntry 21 }
		
		-- 1.3.6.1.4.1.2011.6.139.3.8.1.22
		hwRadioRcvUnicastFrames OBJECT-TYPE
			SYNTAX Counter64
			MAX-ACCESS read-only
			STATUS current
			DESCRIPTION
				"Description."
			::= { hwRadioPerformanceStatEntry 22 }

		
		-- 1.3.6.1.4.1.2011.6.139.3.8.1.23
		hwRadioRcvMngFrames OBJECT-TYPE
			SYNTAX Counter64
			MAX-ACCESS read-only
			STATUS current
			DESCRIPTION
				"Description."
			::= { hwRadioPerformanceStatEntry 23 }

		
		-- 1.3.6.1.4.1.2011.6.139.3.8.1.24
		hwRadioRcvCtrlFrames OBJECT-TYPE
			SYNTAX Counter64
			MAX-ACCESS read-only
			STATUS current
			DESCRIPTION
				"Description."
			::= { hwRadioPerformanceStatEntry 24 }

		
		-- 1.3.6.1.4.1.2011.6.139.3.8.1.25
		hwRadioRcvDataFrames OBJECT-TYPE
			SYNTAX Counter64
			MAX-ACCESS read-only
			STATUS current
			DESCRIPTION
				"Description."
			::= { hwRadioPerformanceStatEntry 25 }

		
		-- 1.3.6.1.4.1.2011.6.139.3.8.1.26
		hwRadioSendMngFrames OBJECT-TYPE
			SYNTAX Counter64
			MAX-ACCESS read-only
			STATUS current
			DESCRIPTION
				"Description."
			::= { hwRadioPerformanceStatEntry 26 }

		
		-- 1.3.6.1.4.1.2011.6.139.3.8.1.27
		hwRadioSendCtrlFrames OBJECT-TYPE
			SYNTAX Counter64
			MAX-ACCESS read-only
			STATUS current
			DESCRIPTION
				"Description."
			::= { hwRadioPerformanceStatEntry 27 }

		
		-- 1.3.6.1.4.1.2011.6.139.3.8.1.28
		hwRadioSendDataFrames OBJECT-TYPE
			SYNTAX Counter64
			MAX-ACCESS read-only
			STATUS current
			DESCRIPTION
				"Description."
			::= { hwRadioPerformanceStatEntry 28 }

		
		-- 1.3.6.1.4.1.2011.6.139.3.8.1.29
		hwRadioStaMaxSignalStrength OBJECT-TYPE
			SYNTAX Integer32
			MAX-ACCESS read-only
			STATUS current
			DESCRIPTION
				"Description."
			::= { hwRadioPerformanceStatEntry 29 }

		
		-- 1.3.6.1.4.1.2011.6.139.3.8.1.30
		hwRadioStaMinSignalStrength OBJECT-TYPE
			SYNTAX Integer32
			MAX-ACCESS read-only
			STATUS current
			DESCRIPTION
				"Description."
			::= { hwRadioPerformanceStatEntry 30 }

		
		-- 1.3.6.1.4.1.2011.6.139.3.8.1.31
		hwRadioStaAvgSignalStrength OBJECT-TYPE
			SYNTAX Integer32
			MAX-ACCESS read-only
			STATUS current
			DESCRIPTION
				"Description."
			::= { hwRadioPerformanceStatEntry 31 }
			
			--  1.3.6.1.4.1.2011.6.139.3.8.1.32
		-- 1.3.6.1.4.1.2011.6.139.3.8.1.32
		hwRadioSendRate OBJECT-TYPE
			SYNTAX Unsigned32
			MAX-ACCESS read-only
			STATUS current
			DESCRIPTION
				"Description."
			::= { hwRadioPerformanceStatEntry 32 }

		
--  1.3.6.1.4.1.2011.6.139.3.8.1.33
		-- 1.3.6.1.4.1.2011.6.139.3.8.1.33
		hwRadioRecvRate OBJECT-TYPE
			SYNTAX Unsigned32
			MAX-ACCESS read-only
			STATUS current
			DESCRIPTION
				"Description."
			::= { hwRadioPerformanceStatEntry 33 }

		
--  1.3.6.1.4.1.2011.6.139.3.8.1.34
		-- 1.3.6.1.4.1.2011.6.139.3.8.1.34
		hwRadioDropRate OBJECT-TYPE
			SYNTAX Unsigned32
			MAX-ACCESS read-only
			STATUS current
			DESCRIPTION
				"Description."
			::= { hwRadioPerformanceStatEntry 34 }

		
		-- 1.3.6.1.4.1.2011.6.139.3.8.1.35
		hwRadioAirPortDhcpFrames OBJECT-TYPE
			SYNTAX Counter64
			MAX-ACCESS read-only
			STATUS current
			DESCRIPTION
				"Description."
			::= { hwRadioPerformanceStatEntry 35 }

		
		-- 1.3.6.1.4.1.2011.6.139.3.8.1.36
		hwRadioAirPortEapolFrames OBJECT-TYPE
			SYNTAX Counter64
			MAX-ACCESS read-only
			STATUS current
			DESCRIPTION
				"Description."
			::= { hwRadioPerformanceStatEntry 36 }

		
		-- 1.3.6.1.4.1.2011.6.139.3.8.1.37
		hwRadioAirPortPsPollFrames OBJECT-TYPE
			SYNTAX Counter64
			MAX-ACCESS read-only
			STATUS current
			DESCRIPTION
				"Description."
			::= { hwRadioPerformanceStatEntry 37 }

		
		-- 1.3.6.1.4.1.2011.6.139.3.8.1.38
		hwRadioAssocRequestFrames OBJECT-TYPE
			SYNTAX Counter64
			MAX-ACCESS read-only
			STATUS current
			DESCRIPTION
				"Description."
			::= { hwRadioPerformanceStatEntry 38 }

		
		-- 1.3.6.1.4.1.2011.6.139.3.8.1.39
		hwRadioAssocResponseFrames OBJECT-TYPE
			SYNTAX Counter64
			MAX-ACCESS read-only
			STATUS current
			DESCRIPTION
				"Description."
			::= { hwRadioPerformanceStatEntry 39 }

		
		-- 1.3.6.1.4.1.2011.6.139.3.8.1.40
		hwRadioReassocRequestFrames OBJECT-TYPE
			SYNTAX Counter64
			MAX-ACCESS read-only
			STATUS current
			DESCRIPTION
				"Description."
			::= { hwRadioPerformanceStatEntry 40 }

		
		-- 1.3.6.1.4.1.2011.6.139.3.8.1.41
		hwRadioReassocResponseFrames OBJECT-TYPE
			SYNTAX Counter64
			MAX-ACCESS read-only
			STATUS current
			DESCRIPTION
				"Description."
			::= { hwRadioPerformanceStatEntry 41 }

		
		-- 1.3.6.1.4.1.2011.6.139.3.8.1.42
		hwRadioDisassocFrames OBJECT-TYPE
			SYNTAX Counter64
			MAX-ACCESS read-only
			STATUS current
			DESCRIPTION
				"Description."
			::= { hwRadioPerformanceStatEntry 42 }

		
		-- 1.3.6.1.4.1.2011.6.139.3.8.1.43
		hwRadioDisauthFrames OBJECT-TYPE
			SYNTAX Counter64
			MAX-ACCESS read-only
			STATUS current
			DESCRIPTION
				"Description."
			::= { hwRadioPerformanceStatEntry 43 }

		
		-- 1.3.6.1.4.1.2011.6.139.3.8.1.44
		hwRadioRcvFrames64Bits OBJECT-TYPE
			SYNTAX Counter64
			MAX-ACCESS read-only
			STATUS current
			DESCRIPTION
				"Description."
			::= { hwRadioPerformanceStatEntry 44 }

		
		-- 1.3.6.1.4.1.2011.6.139.3.8.1.45
		hwRadioRcvBytes64Bits OBJECT-TYPE
			SYNTAX Counter64
			MAX-ACCESS read-only
			STATUS current
			DESCRIPTION
				"Description."
			::= { hwRadioPerformanceStatEntry 45 }

		
		-- 1.3.6.1.4.1.2011.6.139.3.8.1.46
		hwRadioSendFrames64Bits OBJECT-TYPE
			SYNTAX Counter64
			MAX-ACCESS read-only
			STATUS current
			DESCRIPTION
				"Description."
			::= { hwRadioPerformanceStatEntry 46 }

		
		-- 1.3.6.1.4.1.2011.6.139.3.8.1.47
		hwRadioSendBytes64Bits OBJECT-TYPE
			SYNTAX Counter64
			MAX-ACCESS read-only
			STATUS current
			DESCRIPTION
				"Description."
			::= { hwRadioPerformanceStatEntry 47 }

		
		-- 1.3.6.1.4.1.2011.6.139.3.8.1.48
		hwRadioSendRtsSuccess64Bits OBJECT-TYPE
			SYNTAX Counter64
			MAX-ACCESS read-only
			STATUS current
			DESCRIPTION
				"Description."
			::= { hwRadioPerformanceStatEntry 48 }

		
		-- 1.3.6.1.4.1.2011.6.139.3.8.1.49
		hwRadioSendUnicast64Bits OBJECT-TYPE
			SYNTAX Counter64
			MAX-ACCESS read-only
			STATUS current
			DESCRIPTION
				"Description."
			::= { hwRadioPerformanceStatEntry 49 }

		
		-- 1.3.6.1.4.1.2011.6.139.3.8.1.50
		hwRadioSendBroadcast64Bits OBJECT-TYPE
			SYNTAX Counter64
			MAX-ACCESS read-only
			STATUS current
			DESCRIPTION
				"Description."
			::= { hwRadioPerformanceStatEntry 50 }

		
		-- 1.3.6.1.4.1.2011.6.139.3.8.1.51
		hwRadioSendFailFrames64Bits OBJECT-TYPE
			SYNTAX Counter64
			MAX-ACCESS read-only
			STATUS current
			DESCRIPTION
				"Description."
			::= { hwRadioPerformanceStatEntry 51 }

		
		-- 1.3.6.1.4.1.2011.6.139.3.8.1.52
		hwRadioRcvErrFrames64Bits OBJECT-TYPE
			SYNTAX Counter64
			MAX-ACCESS read-only
			STATUS current
			DESCRIPTION
				"Description."
			::= { hwRadioPerformanceStatEntry 52 }

		
		-- 1.3.6.1.4.1.2011.6.139.3.8.1.53
		hwRadioRcvPhyErrFrames64Bits OBJECT-TYPE
			SYNTAX Counter64
			MAX-ACCESS read-only
			STATUS current
			DESCRIPTION
				"Description."
			::= { hwRadioPerformanceStatEntry 53 }

		
		-- 1.3.6.1.4.1.2011.6.139.3.8.1.54
		hwRadioRcvCrcErrFrames64Bits OBJECT-TYPE
			SYNTAX Counter64
			MAX-ACCESS read-only
			STATUS current
			DESCRIPTION
				"Description."
			::= { hwRadioPerformanceStatEntry 54 }

		
		-- 1.3.6.1.4.1.2011.6.139.3.8.1.55
		hwRadioRcvMicErrFrames64Bits OBJECT-TYPE
			SYNTAX Counter64
			MAX-ACCESS read-only
			STATUS current
			DESCRIPTION
				"Description."
			::= { hwRadioPerformanceStatEntry 55 }

		
		-- 1.3.6.1.4.1.2011.6.139.3.8.1.56
		hwRadioRcvKeyDecryptErrFrames64Bits OBJECT-TYPE
			SYNTAX Counter64
			MAX-ACCESS read-only
			STATUS current
			DESCRIPTION
				"Description."
			::= { hwRadioPerformanceStatEntry 56 }

		
		-- 1.3.6.1.4.1.2011.6.139.3.8.1.57
		hwRadioRetryFrames64Bits OBJECT-TYPE
			SYNTAX Counter64
			MAX-ACCESS read-only
			STATUS current
			DESCRIPTION
				"Description."
			::= { hwRadioPerformanceStatEntry 57 }

		
		-- 1.3.6.1.4.1.2011.6.139.3.8.1.58
		hwRadioDownMacErrFrames64Bits OBJECT-TYPE
			SYNTAX Counter64
			MAX-ACCESS read-only
			STATUS obsolete
			DESCRIPTION
				"Description."
			::= { hwRadioPerformanceStatEntry 58 }

		
		-- 1.3.6.1.4.1.2011.6.139.3.8.1.59
		hwRadioNoise OBJECT-TYPE
			SYNTAX Integer32
			MAX-ACCESS read-write
			STATUS current
			DESCRIPTION
				"Description."
			::= { hwRadioPerformanceStatEntry 59 }

		
		-- 1.3.6.1.4.1.2011.6.139.3.8.1.60
		hwRadioActualBandwidth OBJECT-TYPE
			SYNTAX Unsigned32
			MAX-ACCESS read-only
			STATUS current
			DESCRIPTION
				"It means actual bandwidth, include all of both the sent rate and the received rate."
			::= { hwRadioPerformanceStatEntry 60 }

		
		-- 1.3.6.1.4.1.2011.6.139.3.8.1.61
		hwRadioFrames OBJECT-TYPE
			SYNTAX Counter64
			MAX-ACCESS read-only
			STATUS current
			DESCRIPTION
				"It means all of both the sent frames and the received frames."
			::= { hwRadioPerformanceStatEntry 61 }

		
		-- 1.3.6.1.4.1.2011.6.139.3.8.1.62
		hwRadioSendDropFrames64Bits OBJECT-TYPE
			SYNTAX Counter64
			MAX-ACCESS read-only
			STATUS current
			DESCRIPTION
				"It means the sent and dropped frames."
			::= { hwRadioPerformanceStatEntry 62 }

		
		-- 1.3.6.1.4.1.2011.6.139.3.8.1.63
		hwRadioRcvDropFrames64Bits OBJECT-TYPE
			SYNTAX Counter64
			MAX-ACCESS read-only
			STATUS current
			DESCRIPTION
				"It means the received and droped frames."
			::= { hwRadioPerformanceStatEntry 63 }

		
		-- 1.3.6.1.4.1.2011.6.139.3.8.1.64
		hwRadioChannelFreeRate OBJECT-TYPE
			SYNTAX Unsigned32
			MAX-ACCESS read-only
			STATUS current
			DESCRIPTION
				"It means the rate of free channel."
			::= { hwRadioPerformanceStatEntry 64 }

		
		-- 1.3.6.1.4.1.2011.6.139.3.8.1.65
		hwRadioTxRate OBJECT-TYPE
			SYNTAX Unsigned32
			MAX-ACCESS read-only
			STATUS current
			DESCRIPTION
				"It means the utilization rate of sending packets."
			::= { hwRadioPerformanceStatEntry 65 }

		
		-- 1.3.6.1.4.1.2011.6.139.3.8.1.66
		hwRadioRxRate OBJECT-TYPE
			SYNTAX Unsigned32
			MAX-ACCESS read-only
			STATUS current
			DESCRIPTION
				"It means the utilization rate of receiving packets."
			::= { hwRadioPerformanceStatEntry 66 }

		
		-- 1.3.6.1.4.1.2011.6.139.3.8.1.67
		hwRadioChInterferenceRate OBJECT-TYPE
			SYNTAX Unsigned32
			MAX-ACCESS read-only
			STATUS current
			DESCRIPTION
				"It means the rate of channel interference."
			::= { hwRadioPerformanceStatEntry 67 }

--   1.3.6.1.4.1.2011.6.139.3.9
-- 1.3.6.1.4.1.2011.6.139.3.9
-- 1.3.6.1.4.1.2011.6.139.3.9
-- 1.3.6.1.4.1.2011.6.139.3.9
		-- 1.3.6.1.4.1.2011.6.139.3.9
		hwRadioUnauthenticNeighborInfoTable OBJECT-TYPE
			SYNTAX SEQUENCE OF HwRadioUnauthenticNeighborInfoEntry
			MAX-ACCESS not-accessible
			STATUS current
			DESCRIPTION
				"Huawei radio unauthentic neighbor information table, it describes the information about the neighbor ap which is not authorized by AC. 
				it is aggregate of a group of display to the unauthentic neighbor AP infomation of radio. The unauthentic neighbor AP infomation of radio 
				to display of the table contains: the radio BSSID of the unauthentic neighbor ap, the radio RSSI of the unauthentic neighbor ap, the radio 
				channel of the unauthentic neighbor ap.
				
				The index of the radio unauthentic neighbor infomation table is hwApIndex and hwRadioID, an Ap index is an unique identifier to a AP, A radio ID is an unique identifier to a radio.
				   The Ap index is a index import from HUAWEI-WLAN-DEVICE-MIB, the detail description about the index can refer to the node hwApIndex and hwRadioID description.
				"
			::= { hwRadio 9 }
		
--    1.3.6.1.4.1.2011.6.139.3.9.1
-- 1.3.6.1.4.1.2011.6.139.3.9.1
-- 1.3.6.1.4.1.2011.6.139.3.9.1
		-- 1.3.6.1.4.1.2011.6.139.3.9.1
		hwRadioUnauthenticNeighborInfoEntry OBJECT-TYPE
			SYNTAX HwRadioUnauthenticNeighborInfoEntry
			MAX-ACCESS not-accessible
			STATUS current
			DESCRIPTION
				"Huawei radio unauthentic neighbor information table entry. The entry of the huawei radio unauthentic neighbor information table, all the nodes of the huawei
				radio unauthentic neighbor information table are been operated here. The detail of the table entry would be explained by the description
				of the nodes of the table.
				
				The index of the radio unauthentic neighbor infomation table is hwApIndex and hwRadioID, an Ap index is an unique identifier to a AP, A radio ID is an unique identifier to a radio.
				   The Ap index is a index import from HUAWEI-WLAN-DEVICE-MIB, the detail description about the index can refer to the node hwApIndex and hwRadioID description.
				"
			INDEX { hwApIndex, hwRadioID }
			::= { hwRadioUnauthenticNeighborInfoTable 1 }
		
		HwRadioUnauthenticNeighborInfoEntry ::=
			SEQUENCE { 
				hwUnauthenticRadioNeighborBSSID
					OCTET STRING,
				hwUnauthenticRadioNeighborRSSI
					OCTET STRING,
				hwunauthenticRadioNeighborChannel
					OCTET STRING,
				hwUnauthenticRadioNeighborSSID
					OCTET STRING
			 }

--    1.3.6.1.4.1.2011.6.139.3.9.1.1
-- 1.3.6.1.4.1.2011.6.139.3.9.1.1
-- 1.3.6.1.4.1.2011.6.139.3.9.1.1
		-- 1.3.6.1.4.1.2011.6.139.3.9.1.1
		hwUnauthenticRadioNeighborBSSID OBJECT-TYPE
			SYNTAX OCTET STRING
			MAX-ACCESS read-only
			STATUS current
			DESCRIPTION
				"An object uses to display the BSSID of unauthentic neighbor ap. BSSID identifies a minimum service set,When administrator binds a ESS to a radio,
				it use base BSSID and WlanID to generate a BSSID. The format of the bssid is a max address which contains 3 sets of 2 Btyes hexadecimal character 
				join up with - character, such as 00e0-5678-12fa.
				Notes the BSSID of unauthentic neighbor ap just can be display, but can't be configured.
				"
			::= { hwRadioUnauthenticNeighborInfoEntry 1 }
		
--    1.3.6.1.4.1.2011.6.139.3.9.1.2
-- 1.3.6.1.4.1.2011.6.139.3.9.1.2
-- 1.3.6.1.4.1.2011.6.139.3.9.1.2
		-- 1.3.6.1.4.1.2011.6.139.3.9.1.2
		hwUnauthenticRadioNeighborRSSI OBJECT-TYPE
			SYNTAX OCTET STRING
			MAX-ACCESS read-only
			STATUS current
			DESCRIPTION
				"An object uses to display the the RSSI from unauthentic neighbor ap to this radio.
				RSSI means the signal intensity of the rceived signal.
				Notes the RSSI from unauthentic neighbor ap to the radio just can be display,but can't be configured.
				"
			::= { hwRadioUnauthenticNeighborInfoEntry 2 }
		
--    1.3.6.1.4.1.2011.6.139.3.9.1.3
-- 1.3.6.1.4.1.2011.6.139.3.9.1.3
-- 1.3.6.1.4.1.2011.6.139.3.9.1.3
		-- 1.3.6.1.4.1.2011.6.139.3.9.1.3
		hwunauthenticRadioNeighborChannel OBJECT-TYPE
			SYNTAX OCTET STRING
			MAX-ACCESS read-only
			STATUS current
			DESCRIPTION
				"An object uses to display the working channel which is currently used by the unauthentic neighbor ap.
				Notes the radio working channel of the unauthentic neighbor ap just can be display, but can't be configured.
				"
			::= { hwRadioUnauthenticNeighborInfoEntry 3 }
		
		-- 1.3.6.1.4.1.2011.6.139.3.9.1.4
		hwUnauthenticRadioNeighborSSID OBJECT-TYPE
			SYNTAX OCTET STRING
			MAX-ACCESS read-only
			STATUS current
			DESCRIPTION
				"Description."
			::= { hwRadioUnauthenticNeighborInfoEntry 4 }

--    1.3.6.1.4.1.2011.6.139.3.10
-- 1.3.6.1.4.1.2011.6.139.3.10
-- 1.3.6.1.4.1.2011.6.139.3.10
		-- 1.3.6.1.4.1.2011.6.139.3.10
		hwRadioRegionCalibrateTable OBJECT-TYPE
			SYNTAX SEQUENCE OF HwRadioRegionCalibrateEntry
			MAX-ACCESS not-accessible
			STATUS current
			DESCRIPTION
				"Huawei global calibrate config table, the global calibrate is based on AP region.Huawei radio manage table.
				The content of the table contains: region calibrate startup mode, region calibrate auto time, region calibrate listen mode,
				region calibrate status. 
				
				The index of the radio global calibrate config table is hwApRegionIndex, an Ap region index is an unique identifier to a AP region.
				   The Ap region index is a index import from HUAWEI-WLAN-DEVICE-MIB, the detail description about the index can refer to the node hwApRegionIndex description. 
				"
			::= { hwRadio 10 }
		
--    1.3.6.1.4.1.2011.6.139.3.10.1
-- 1.3.6.1.4.1.2011.6.139.3.10.1
-- 1.3.6.1.4.1.2011.6.139.3.10.1
		-- 1.3.6.1.4.1.2011.6.139.3.10.1
		hwRadioRegionCalibrateEntry OBJECT-TYPE
			SYNTAX HwRadioRegionCalibrateEntry
			MAX-ACCESS not-accessible
			STATUS current
			DESCRIPTION
				"Huawei radio global calibrate config table entry. The entry of the huawei radio global calibrate config table, all the nodes of the huawei
				radio global calibrate config table are been operated here. The detail of the table entry would be explained by the description
				of the nodes of the table. 
				
				The index of the radio global calibrate config table is hwApRegionIndex, an Ap region index is an unique identifier to a AP region.
				   The Ap region index is a index import from HUAWEI-WLAN-DEVICE-MIB, the detail description about the index can refer to the node hwApRegionIndex description.
				"
			INDEX { hwApRegionIndex }
			::= { hwRadioRegionCalibrateTable 1 }
		
		HwRadioRegionCalibrateEntry ::=
			SEQUENCE { 
				hwRegionCalibrateStartupMode
					INTEGER,
				hwRegionCalibrateAutoTime
					DateAndTime,
				hwRegionCalibrateListenMode
					INTEGER,
				hwRegionCalibrateStatus
					INTEGER
			 }

--    1.3.6.1.4.1.2011.6.139.3.10.1.1
-- 1.3.6.1.4.1.2011.6.139.3.10.1.1
-- 1.3.6.1.4.1.2011.6.139.3.10.1.1
		-- 1.3.6.1.4.1.2011.6.139.3.10.1.1
		hwRegionCalibrateStartupMode OBJECT-TYPE
			SYNTAX INTEGER
				{
				immediate(1),
				periodic(2),
				cancelPeriodic(3)
				}
			MAX-ACCESS read-write
			STATUS current
			DESCRIPTION
				"The mode uses to set the golbal calibrate startup mode.Immediate means startup immediately. Here, hwRegionCalibrateAutoTime is meanningless.
				Periodic means startup calibrate periodically. In accordance, hwRegionCalibrateAutoTime specify the time when startup everyday.
				   Cancel periodic means cancel the periodically calibrate. Here, hwRegionCalibrateAutoTime is meanningless.
				Please refer to the description of hwRegionCalibrateAutoTime.
				"
			::= { hwRadioRegionCalibrateEntry 1 }
		
--    1.3.6.1.4.1.2011.6.139.3.10.1.2
-- 1.3.6.1.4.1.2011.6.139.3.10.1.2
-- 1.3.6.1.4.1.2011.6.139.3.10.1.2
		-- 1.3.6.1.4.1.2011.6.139.3.10.1.2
		hwRegionCalibrateAutoTime OBJECT-TYPE
			SYNTAX DateAndTime
			MAX-ACCESS read-write
			STATUS current
			DESCRIPTION
				"An object uses to set the time when startup everyday on the basic of the periodic calibrate startup mode.
				Please refer to the description of hwRegionCalibrateStartupMode. 
				Notes it just can support the hour, minute and second ,the real date can't be support and the fixed date JAN 1st 2001 changelessly must be set, when the auto startup time is been set,
				notwithstanding it can get the date of the auto startup time too, but the value of the date is JAN 1st 2001 changelessly.
				"
			::= { hwRadioRegionCalibrateEntry 2 }
		
--    1.3.6.1.4.1.2011.6.139.3.10.1.3
-- 1.3.6.1.4.1.2011.6.139.3.10.1.3
-- 1.3.6.1.4.1.2011.6.139.3.10.1.3
		-- 1.3.6.1.4.1.2011.6.139.3.10.1.3
		hwRegionCalibrateListenMode OBJECT-TYPE
			SYNTAX INTEGER
				{
				enable(1),
				disable(2)
				}
			MAX-ACCESS read-write
			STATUS current
			DESCRIPTION
				"A switch flag, which set the radio region calibrate listen mode as enable or disable, tells whether the listen unauthentic neighbor while calibrating is supported.
				Because listen unauthentic neighbor will need added time, so it as a option. 
				enable means it listens unauthentic neighbor while calibrating, disable means it would not listen unauthentic neighbor, 
				In this case, we can't get unauthentic neighbor information after calibrate done. 
				Notes the setting of radio region calibrate listen mode must have the corresponding setting of the golbal calibrate startup mode, and the golbal calibrate startup mode
				can't be cancel-periodic. 
				"
			DEFVAL { 2 }
			::= { hwRadioRegionCalibrateEntry 3 }
		
--    1.3.6.1.4.1.2011.6.139.3.10.1.4
-- 1.3.6.1.4.1.2011.6.139.3.10.1.4
-- 1.3.6.1.4.1.2011.6.139.3.10.1.4
		-- 1.3.6.1.4.1.2011.6.139.3.10.1.4
		hwRegionCalibrateStatus OBJECT-TYPE
			SYNTAX INTEGER
				{
				running(1),
				stop(2)
				}
			MAX-ACCESS read-only
			STATUS current
			DESCRIPTION
				"An object uses to display the status of the global calibrate.running means the global calibrate is running.
				stop means the global calibrate had over.
				   Notes the status of the global calibrate just can be display, but can't be configured.
				   "
			::= { hwRadioRegionCalibrateEntry 4 }
		
--    1.3.6.1.4.1.2011.6.139.3.11
-- 1.3.6.1.4.1.2011.6.139.3.11
-- 1.3.6.1.4.1.2011.6.139.3.11
		-- 1.3.6.1.4.1.2011.6.139.3.11
		hwBatchRadioProfileStartNumber OBJECT-TYPE
			SYNTAX Integer32
			MAX-ACCESS read-write
			STATUS current
			DESCRIPTION
				"An object uses to set the start number of the first radio profile in batch operation.
				The range of the first radio profile start number is from 1 to 512. 
				Notes radio profile name is the unique identification of a radio profile, so the start number isn't the ID of the radio profile.  
				"
			::= { hwRadio 11 }
		
--    1.3.6.1.4.1.2011.6.139.3.12
-- 1.3.6.1.4.1.2011.6.139.3.12
-- 1.3.6.1.4.1.2011.6.139.3.12
		-- 1.3.6.1.4.1.2011.6.139.3.12
		hwBatchRadioProfileNumber OBJECT-TYPE
			SYNTAX Integer32
			MAX-ACCESS read-write
			STATUS current
			DESCRIPTION
				"An object uses to set the radio profile number which want to get in batch operation.
				The range of the radio profile number is from 1 to 128.
				"
			::= { hwRadio 12 }
		
--    1.3.6.1.4.1.2011.6.139.3.13
-- 1.3.6.1.4.1.2011.6.139.3.13
-- 1.3.6.1.4.1.2011.6.139.3.13
		-- 1.3.6.1.4.1.2011.6.139.3.13
		hwBatchRadioProfileReturnNumber OBJECT-TYPE
			SYNTAX Integer32
			MAX-ACCESS read-only
			STATUS current
			DESCRIPTION
				"An object uses to display the radio profile number which can get in batch operation.
				
				The sum of the batch radio profile start number and the batch radio profile number should not be larger than the total radio profile number 
				in the system, so the real batch radio profile number maybe not equal to the setting batch radio profile number. no matter how the real batch
				radio profile number is the batch radio profile return number. For example, the setting batch radio profile start number is 3, the setting batch radio profile 
				number is 4 and the total radio profile number in the system is 5, the real batch radio profile number would be 2, and the batch radio profile return number 
				must be 2, the batch radio profile return number isn't equal to the batch radio profile number, otherwise, the total radio profile number in the 
				system is 7, the real batch radio profile number would be 4, and the batch radio profile return number must be 4 too, the batch radio profile 
				return number is equal to the batch radio profile number.
				"
			::= { hwRadio 13 }
		
--    1.3.6.1.4.1.2011.6.139.3.14
-- 1.3.6.1.4.1.2011.6.139.3.14
-- 1.3.6.1.4.1.2011.6.139.3.14
		-- 1.3.6.1.4.1.2011.6.139.3.14
		hwBatchRadioProfileName OBJECT-TYPE
			SYNTAX OCTET STRING
			MAX-ACCESS read-only
			STATUS current
			DESCRIPTION
				"An object uses to display the names of radio profiles which is in the range of batch radio profile names which are determined by the batch radio profile start number 
				and the batch radio profile number. Any two batch radio profile names of the list should separate with question mark.
				"
			::= { hwRadio 14 }
		
--    1.3.6.1.4.1.2011.6.139.3.15
-- 1.3.6.1.4.1.2011.6.139.3.15
-- 1.3.6.1.4.1.2011.6.139.3.15
		-- 1.3.6.1.4.1.2011.6.139.3.15
		hwBatchLoadBalanceGroupStartNumber OBJECT-TYPE
			SYNTAX Integer32
			MAX-ACCESS read-write
			STATUS current
			DESCRIPTION
				"An object uses to set the start number of the first load balance group in batch operation.
				The range of the first load balance group start number is from 1 to 4096. 
				Notes the load balance group name is the unique identification of a load balance group, so the start number isn't the ID of the load balance group.  
				"
			::= { hwRadio 15 }
		
--    1.3.6.1.4.1.2011.6.139.3.16
-- 1.3.6.1.4.1.2011.6.139.3.16
-- 1.3.6.1.4.1.2011.6.139.3.16
		-- 1.3.6.1.4.1.2011.6.139.3.16
		hwBatchLoadBalanceGroupNumber OBJECT-TYPE
			SYNTAX Integer32
			MAX-ACCESS read-write
			STATUS current
			DESCRIPTION
				"An object uses to set the load balance group number which want to get in batch operation.
				The range of the load balance group number is from 1 to 4096.
				"
			::= { hwRadio 16 }
		
--    1.3.6.1.4.1.2011.6.139.3.17
-- 1.3.6.1.4.1.2011.6.139.3.17
-- 1.3.6.1.4.1.2011.6.139.3.17
		-- 1.3.6.1.4.1.2011.6.139.3.17
		hwBatchLoadBalanceGroupReturnNumber OBJECT-TYPE
			SYNTAX Integer32
			MAX-ACCESS read-only
			STATUS current
			DESCRIPTION
				"An object uses to display the load balance group number which can get in batch operation.
				
				The sum of the batch load balance group start number and the batch load balance group number should not be larger than the total load balance group number 
				in the system, so the real batch load balance group number maybe not equal to the setting batch load balance group number. no matter how the real batch
				load balance group number is the batch load balance group return number. For example, the setting batch load balance group start number is 3, the setting batch load balance group 
				number is 4 and the total load balance group number in the system is 5, the real batch load balance group number would be 2, and the batch load balance group return number 
				must be 2, the batch load balance group return number isn't equal to the batch load balance group number, otherwise, the total load balance group number in the 
				system is 7, the real batch load balance group number would be 4, and the batch load balance group return number must be 4 too, the batch load balance group 
				return number is equal to the batch load balance group number.
				"
			::= { hwRadio 17 }
		
--    1.3.6.1.4.1.2011.6.139.3.18
-- 1.3.6.1.4.1.2011.6.139.3.18
-- 1.3.6.1.4.1.2011.6.139.3.18
		-- 1.3.6.1.4.1.2011.6.139.3.18
		hwBatchLoadBalanceGroupName OBJECT-TYPE
			SYNTAX OCTET STRING
			MAX-ACCESS read-only
			STATUS current
			DESCRIPTION
				"An object uses to display the names of load balance group which is in the range of batch load balance group names which are determined by the batch load balance group start number 
				and the batch load balance group number. Any two batch load balance group names of the list should separate with question mark.
				"
			::= { hwRadio 18 }
		
--    1.3.6.1.4.1.2011.6.139.3.19
-- 1.3.6.1.4.1.2011.6.139.3.19
-- 1.3.6.1.4.1.2011.6.139.3.19
		-- 1.3.6.1.4.1.2011.6.139.3.19
		hwBatchUncontrolAPStartNumber OBJECT-TYPE
			SYNTAX Integer32
			MAX-ACCESS read-write
			STATUS current
			DESCRIPTION
				"An object uses to set the start number of the first uncontrol AP in batch operation.
				The range of the first uncontrol AP start number is from 1 to 512. 
				Notes the start number isn't the ID of the uncontrol AP.
				"
			::= { hwRadio 19 }
		
--    1.3.6.1.4.1.2011.6.139.3.20
-- 1.3.6.1.4.1.2011.6.139.3.20
-- 1.3.6.1.4.1.2011.6.139.3.20
		-- 1.3.6.1.4.1.2011.6.139.3.20
		hwBatchUncontrolAPNumber OBJECT-TYPE
			SYNTAX Integer32
			MAX-ACCESS read-write
			STATUS current
			DESCRIPTION
				"An object uses to set the uncontrol AP number which want to get in batch operation.
				The range of the uncontrol AP start number is from 1 to 512.
				"
			::= { hwRadio 20 }
		
--    1.3.6.1.4.1.2011.6.139.3.21
-- 1.3.6.1.4.1.2011.6.139.3.21
-- 1.3.6.1.4.1.2011.6.139.3.21
		-- 1.3.6.1.4.1.2011.6.139.3.21
		hwBatchUncontrolAPReturnNumber OBJECT-TYPE
			SYNTAX Integer32
			MAX-ACCESS read-only
			STATUS current
			DESCRIPTION
				"An object uses to display the uncontrol AP number which can get in batch operation.
				
				The sum of the batch uncontrol AP start number and the batch uncontrol AP number should not be larger than the total uncontrol AP number 
				in the system, so the real batch uncontrol AP number maybe not equal to the setting batch uncontrol AP number. no matter how the real batch
				uncontrol AP number is the batch uncontrol AP return number. For example, the setting batch uncontrol AP start number is 3, the setting batch uncontrol AP 
				number is 4 and the total uncontrol AP number in the system is 5, the real batch uncontrol AP number would be 2, and the batch uncontrol AP return number 
				must be 2, the batch uncontrol AP return number isn't equal to the batch uncontrol AP number, otherwise, the total uncontrol AP number in the 
				system is 7, the real batch uncontrol AP number would be 4, and the batch uncontrol AP return number must be 4 too, the batch uncontrol AP 
				return number is equal to the batch uncontrol AP number.
				"
			::= { hwRadio 21 }
		
--    1.3.6.1.4.1.2011.6.139.3.22
-- 1.3.6.1.4.1.2011.6.139.3.22
-- 1.3.6.1.4.1.2011.6.139.3.22
		-- 1.3.6.1.4.1.2011.6.139.3.22
		hwBatchUncontrolAPBssid OBJECT-TYPE
			SYNTAX OCTET STRING
			MAX-ACCESS read-only
			STATUS current
			DESCRIPTION
				"An object uses to display the the BSSID of uncontrol AP which is in the range of batch uncontrol AP BSSID which are determined by the batch uncontrol AP start number 
				and the batch uncontrol AP BSSID. Any two batch uncontrol AP BSSID of the list should separate with question mark.
				BSSID identifies a minimum service set,When administrator binds a ESS to a radio, it use base BSSID and WlanID to generate a BSSID. The format of 
				the bssid is a max address which contains 3 sets of 2 Btyes hexadecimal character join up with - character, such as 00e0-5678-12fa.
				Notes the BSSID of unauthentic neighbor ap just can be display, but can't be configured.
				"
			::= { hwRadio 22 }
		
--    1.3.6.1.4.1.2011.6.139.3.23
-- 1.3.6.1.4.1.2011.6.139.3.23
-- 1.3.6.1.4.1.2011.6.139.3.23
		-- 1.3.6.1.4.1.2011.6.139.3.23
		hwBatchUncontrolAPAuthNeighborIndex OBJECT-TYPE
			SYNTAX OCTET STRING
			MAX-ACCESS read-only
			STATUS current
			DESCRIPTION
				"An object uses to display the authentic neighbor ap index of uncontrol ap which is in the range of batch uncontrol ap which are determined 
				by the batch uncontrol ap start number and the batch uncontrol ap number. Any two authentic neighbor ap indexs of the batch uncontrol ap of the list should separate with question mark.
				"
			::= { hwRadio 23 }
		
--    1.3.6.1.4.1.2011.6.139.3.24
-- 1.3.6.1.4.1.2011.6.139.3.24
-- 1.3.6.1.4.1.2011.6.139.3.24
		-- 1.3.6.1.4.1.2011.6.139.3.24
		hwRadioNotifications OBJECT IDENTIFIER ::= { hwRadio 24 }
		
--    1.3.6.1.4.1.2011.6.139.3.24.1
-- 1.3.6.1.4.1.2011.6.139.3.24.1
-- 1.3.6.1.4.1.2011.6.139.3.24.1
		-- 1.3.6.1.4.1.2011.6.139.3.24.1
		hwRadioNotify OBJECT IDENTIFIER ::= { hwRadioNotifications 1 }
		
--    1.3.6.1.4.1.2011.6.139.3.24.1.1
-- 1.3.6.1.4.1.2011.6.139.3.24.1.1
-- 1.3.6.1.4.1.2011.6.139.3.24.1.1
		-- 1.3.6.1.4.1.2011.6.139.3.24.1.1
		hwRadioChannelChangedNotify NOTIFICATION-TYPE
			OBJECTS { hwApIndex, hwRadioID, hwRadioActualChannel, hwApMac, hwRadioChannelChangedReason, 
				hwRadioChannelChangedReasonStr, hwRadioPreActualChannel }
			STATUS current
			DESCRIPTION 
				"A notification which is sent out when actual channel of radio is changed.
				"
			::= { hwRadioNotify 1 }
		
--    1.3.6.1.4.1.2011.6.139.3.24.1.2
-- 1.3.6.1.4.1.2011.6.139.3.24.1.2
-- 1.3.6.1.4.1.2011.6.139.3.24.1.2
		-- 1.3.6.1.4.1.2011.6.139.3.24.1.2
		hwRadioSignalEnvDeteriorationNotify NOTIFICATION-TYPE
			OBJECTS { hwApIndex, hwRadioID, hwRadioPER, hwRadioConflictRate, hwApMac
				 }
			STATUS current
			DESCRIPTION 
				"A notification which is sent out when radio report singal environment deterioration. 
				The objects included with the Notification may be used to read further information using AP index ,radio ID radio PER and radio conflict rate.
				"
			::= { hwRadioNotify 2 }
		
--    1.3.6.1.4.1.2011.6.139.3.24.1.3
-- 1.3.6.1.4.1.2011.6.139.3.24.1.3
-- 1.3.6.1.4.1.2011.6.139.3.24.1.3
		-- 1.3.6.1.4.1.2011.6.139.3.24.1.3
		hwRadioSignalEnvResumeNotify NOTIFICATION-TYPE
			OBJECTS { hwApIndex, hwRadioID, hwApMac }
			STATUS current
			DESCRIPTION 
				"A notification which is sent out when radio report singal environment resume.
				The objects included with the Notification may be used to read further information using AP index and radio ID.
				"
			::= { hwRadioNotify 3 }
		
--    1.3.6.1.4.1.2011.6.139.3.24.1.4
-- 1.3.6.1.4.1.2011.6.139.3.24.1.4
-- 1.3.6.1.4.1.2011.6.139.3.24.1.4
		-- 1.3.6.1.4.1.2011.6.139.3.24.1.4
		hwApMonitorModeChangedNotify NOTIFICATION-TYPE
			OBJECTS { hwApIndex, hwApMac, hwRadioID, hwApMonitorMode, hwApPreMonitorMode
				 }
			STATUS current
			DESCRIPTION 
				"Description."
			::= { hwRadioNotify 4 }
		
--    1.3.6.1.4.1.2011.6.139.3.24.1.5
-- 1.3.6.1.4.1.2011.6.139.3.24.1.5
-- 1.3.6.1.4.1.2011.6.139.3.24.1.5
		-- 1.3.6.1.4.1.2011.6.139.3.24.1.5
		hwAPCoInterfDetectedNotify NOTIFICATION-TYPE
			OBJECTS { hwApIndex, hwApMac, hwRadioID, hwApChannel, hwApInterfBssid, 
				hwInterfRSSI }
			STATUS current
			DESCRIPTION 
				"Description."
			::= { hwRadioNotify 5 }
		
--    1.3.6.1.4.1.2011.6.139.3.24.1.6
-- 1.3.6.1.4.1.2011.6.139.3.24.1.6
-- 1.3.6.1.4.1.2011.6.139.3.24.1.6
		-- 1.3.6.1.4.1.2011.6.139.3.24.1.6
		hwAPCoInterfClearNotify NOTIFICATION-TYPE
			OBJECTS { hwApIndex, hwApMac, hwRadioID, hwApChannel, hwApInterfBssid}
			STATUS current
			DESCRIPTION 
				"Description."
			::= { hwRadioNotify 6 }
		
--    1.3.6.1.4.1.2011.6.139.3.24.1.7
-- 1.3.6.1.4.1.2011.6.139.3.24.1.7
-- 1.3.6.1.4.1.2011.6.139.3.24.1.7
		-- 1.3.6.1.4.1.2011.6.139.3.24.1.7
		hwNerborInterfDetectedNotify NOTIFICATION-TYPE
			OBJECTS { hwApIndex, hwApMac, hwRadioID, hwApChannel, hwApInterfBssid, 
				hwInterfApChannel, hwInterfRSSI }
			STATUS current
			DESCRIPTION 
				"Description."
			::= { hwRadioNotify 7 }
		
--    1.3.6.1.4.1.2011.6.139.3.24.1.8
-- 1.3.6.1.4.1.2011.6.139.3.24.1.8
-- 1.3.6.1.4.1.2011.6.139.3.24.1.8
		-- 1.3.6.1.4.1.2011.6.139.3.24.1.8
		hwNeiborInterfClearNotify NOTIFICATION-TYPE
			OBJECTS { hwApIndex, hwApMac, hwRadioID, hwApChannel, hwApInterfBssid, 
				hwInterfApChannel }
			STATUS current
			DESCRIPTION 
				"Description."
			::= { hwRadioNotify 8 }
		
--    1.3.6.1.4.1.2011.6.139.3.24.1.9
-- 1.3.6.1.4.1.2011.6.139.3.24.1.9
-- 1.3.6.1.4.1.2011.6.139.3.24.1.9
		-- 1.3.6.1.4.1.2011.6.139.3.24.1.9
		hwStaInterfDetectedNotify NOTIFICATION-TYPE
			OBJECTS { hwApIndex, hwApMac, hwRadioID, hwApChannel, hwInterfStaMac
				 }
			STATUS current
			DESCRIPTION 
				"Description."
			::= { hwRadioNotify 9 }
		
--    1.3.6.1.4.1.2011.6.139.3.24.1.10
-- 1.3.6.1.4.1.2011.6.139.3.24.1.10
-- 1.3.6.1.4.1.2011.6.139.3.24.1.10
		-- 1.3.6.1.4.1.2011.6.139.3.24.1.10
		hwStaInterfClearNotify NOTIFICATION-TYPE
			OBJECTS { hwApIndex, hwApMac, hwRadioID, hwApChannel, hwInterfStaMac
				 }
			STATUS current
			DESCRIPTION 
				"Description."
			::= { hwRadioNotify 10 }
		
--    1.3.6.1.4.1.2011.6.139.3.24.1.11
-- 1.3.6.1.4.1.2011.6.139.3.24.1.11
-- 1.3.6.1.4.1.2011.6.139.3.24.1.11
		-- 1.3.6.1.4.1.2011.6.139.3.24.1.11
		hwOtherDeviceInterfDetectedNotify NOTIFICATION-TYPE
			OBJECTS { hwApIndex, hwApMac, hwRadioID, hwApChannel }
			STATUS current
			DESCRIPTION 
				"Description."
			::= { hwRadioNotify 11 }
		
--    1.3.6.1.4.1.2011.6.139.3.24.1.12
-- 1.3.6.1.4.1.2011.6.139.3.24.1.12
-- 1.3.6.1.4.1.2011.6.139.3.24.1.12
		-- 1.3.6.1.4.1.2011.6.139.3.24.1.12
		hwOtherDeviceInterfClearNotify NOTIFICATION-TYPE
			OBJECTS { hwApIndex, hwApMac, hwRadioID, hwApChannel }
			STATUS current
			DESCRIPTION 
				"Description."
			::= { hwRadioNotify 12 }
		
--    1.3.6.1.4.1.2011.6.139.3.24.1.13
-- 1.3.6.1.4.1.2011.6.139.3.24.1.13
-- 1.3.6.1.4.1.2011.6.139.3.24.1.13
		-- 1.3.6.1.4.1.2011.6.139.3.24.1.13
		hwRadioDownNotify NOTIFICATION-TYPE
			OBJECTS { hwApIndex, hwApMac, hwRadioID, hwRadioDownCause, hwRadioDownCauseStr
				 }
			STATUS current
			DESCRIPTION 
				"Description."
			::= { hwRadioNotify 13 }
		
--    1.3.6.1.4.1.2011.6.139.3.24.1.14
-- 1.3.6.1.4.1.2011.6.139.3.24.1.14
-- 1.3.6.1.4.1.2011.6.139.3.24.1.14
		-- 1.3.6.1.4.1.2011.6.139.3.24.1.14
		hwRadioDownRecovNotify NOTIFICATION-TYPE
			OBJECTS { hwApIndex, hwApMac, hwRadioID, hwRadioDownCause, hwRadioDownCauseStr
				 }
			STATUS current
			DESCRIPTION 
				"Description."
			::= { hwRadioNotify 14 }
		
		-- 1.3.6.1.4.1.2011.6.139.3.24.1.15
		hwWIDSDetectRogueNotify NOTIFICATION-TYPE
			OBJECTS { hwWIDSTrapInfoAPID, hwWIDSTrapInfoRadioId, hwWIDSTrapInfoAPMAC, hwWIDSTrapInfoRogueMAC, hwWIDSTrapInfoRogueSSId, 
				hwWIDSTrapInfoRogueType, hwWIDSTrapInfoRogueRSSI, hwWIDSTrapInfoRogueChanID }
			STATUS current
			DESCRIPTION 
				"A notification which is sent out when a rogue device is found."
			::= { hwRadioNotify 15 }

		
		-- 1.3.6.1.4.1.2011.6.139.3.24.1.16
		hwRadioNotSupportChannelNotify NOTIFICATION-TYPE
			OBJECTS { hwApIndex, hwApMac, hwRadioID, hwRadioMngChannelBandwidth, hwRadioMngChannel, 
				hwRadioActualChannelBandwidth, hwRadioActualChannel }
			STATUS current
			DESCRIPTION 
				"Description."
			::= { hwRadioNotify 16 }

		
		-- 1.3.6.1.4.1.2011.6.139.3.24.1.17
		hwRadioNotSupportPowerLevelNotify NOTIFICATION-TYPE
			OBJECTS { hwApIndex, hwApMac, hwRadioID, hwRadioMngPowerLevel, hwRadioActualPowerLevel
				 }
			STATUS current
			DESCRIPTION 
				"Description."
			::= { hwRadioNotify 17 }

		
		-- 1.3.6.1.4.1.2011.6.139.3.24.1.18
		hwRadioAntennaGainIsUnlawfulNotify NOTIFICATION-TYPE
			OBJECTS { hwApIndex, hwApMac, hwRadioID, hwRadioActualAntennaGain, hwRadioLegitimateAntennaGain
				 }
			STATUS current
			DESCRIPTION 
				"Description."
			::= { hwRadioNotify 18 }

		
		-- 1.3.6.1.4.1.2011.6.139.3.24.1.19
		hwRadioPowerChangedNotify NOTIFICATION-TYPE
			OBJECTS { hwApIndex, hwApMac, hwRadioID, hwRadioActualPowerLevel, hwRadioWorkingPower, hwRadioPowerChangedReasonStr
				 }
			STATUS current
			DESCRIPTION 
				"Description."
			::= { hwRadioNotify 19 }

		
		-- 1.3.6.1.4.1.2011.6.139.3.24.1.20
		hwApAccessUserNumExceedThresholdNotify NOTIFICATION-TYPE
			OBJECTS { hwApIndex, hwApMac, hwRadioID, hwRadioUacUserNum 
				 }
			STATUS current
			DESCRIPTION 
				"Description."
			::= { hwRadioNotify 20 }

		
		-- 1.3.6.1.4.1.2011.6.139.3.24.1.21
		hwApAccessUserNumExceedThresholdRecovNotify NOTIFICATION-TYPE
			OBJECTS { hwApIndex, hwApMac, hwRadioID, hwRadioUacUserNum 
				 }
			STATUS current
			DESCRIPTION 
				"Description."
			::= { hwRadioNotify 21 }

		
		-- 1.3.6.1.4.1.2011.6.139.3.24.1.22
		hwApRoamUserNumExceedThresholdNotify NOTIFICATION-TYPE
			OBJECTS { hwApIndex, hwApMac, hwRadioID, hwRadioUacUserNum 
				 }
			STATUS current
			DESCRIPTION 
				"Description."
			::= { hwRadioNotify 22 }

		
		-- 1.3.6.1.4.1.2011.6.139.3.24.1.23
		hwApRoamUserNumExceedThresholdRecovNotify NOTIFICATION-TYPE
			OBJECTS { hwApIndex, hwApMac, hwRadioID, hwRadioUacUserNum 
				 }
			STATUS current
			DESCRIPTION 
				"Description."
			::= { hwRadioNotify 23 }

		
		-- 1.3.6.1.4.1.2011.6.139.3.24.1.24
		hwApAccessChannelUtilExceedThresholdNotify NOTIFICATION-TYPE
			OBJECTS { hwApIndex, hwApMac, hwRadioID, hwRadioUacUserNum 
				 }
			STATUS current
			DESCRIPTION 
				"Description."
			::= { hwRadioNotify 24 }

		
		-- 1.3.6.1.4.1.2011.6.139.3.24.1.25
		hwApAccessChannelUtilExceedThresholdRecovNotify NOTIFICATION-TYPE
			OBJECTS { hwApIndex, hwApMac, hwRadioID, hwRadioUacUserNum 
				 }
			STATUS current
			DESCRIPTION 
				"Description."
			::= { hwRadioNotify 25 }

		
		-- 1.3.6.1.4.1.2011.6.139.3.24.1.26
		hwApRoamChannelUtilExceedThresholdNotify NOTIFICATION-TYPE
			OBJECTS { hwApIndex, hwApMac, hwRadioID, hwRadioUacUserNum 
				 }
			STATUS current
			DESCRIPTION 
				"Description."
			::= { hwRadioNotify 26 }

		
		-- 1.3.6.1.4.1.2011.6.139.3.24.1.27
		hwApRoamChannelUtilExceedThresholdRecovNotify NOTIFICATION-TYPE
			OBJECTS { hwApIndex, hwApMac, hwRadioID, hwRadioUacUserNum 
				 }
			STATUS current
			DESCRIPTION 
				"Description."
			::= { hwRadioNotify 27 }

		hwRadioUploadRemoteCaptureFileNotify NOTIFICATION-TYPE
			OBJECTS { hwApIndex, hwApMac, hwRadioID }
			STATUS current
			DESCRIPTION
				"Description."
			::= { hwRadioNotify 28 }
		
--     1.3.6.1.4.1.2011.6.139.3.24.3
-- 1.3.6.1.4.1.2011.6.139.3.24.2
-- 1.3.6.1.4.1.2011.6.139.3.24.3
		-- 1.3.6.1.4.1.2011.6.139.3.24.3
		hwRadioNotifyObjects OBJECT IDENTIFIER ::= { hwRadioNotifications 3 }
		
--    1.3.6.1.4.1.2011.6.139.3.24.3.1
-- 1.3.6.1.4.1.2011.6.139.3.24.2.1
-- 1.3.6.1.4.1.2011.6.139.3.24.3.1
		-- 1.3.6.1.4.1.2011.6.139.3.24.3.1
		hwRadioActualChannel OBJECT-TYPE
			SYNTAX Unsigned32
			MAX-ACCESS read-only
			STATUS current
			DESCRIPTION
				"An object uses to display the actual working channel which is currently used by the radio.
				Notes the radio actual working channel just can be display, but can't be configured.
				"
			::= { hwRadioNotifyObjects 1 }
		
--    1.3.6.1.4.1.2011.6.139.3.24.3.2
-- 1.3.6.1.4.1.2011.6.139.3.24.2.2
-- 1.3.6.1.4.1.2011.6.139.3.24.3.2
		-- 1.3.6.1.4.1.2011.6.139.3.24.3.2
		hwRadioConflictRate OBJECT-TYPE
			SYNTAX Unsigned32
			MAX-ACCESS read-only
			STATUS current
			DESCRIPTION
				"An object uses to display the wireless conflict rate of the radio.
				Notes the wireless conflict rate of the radio just can be display, but can't be configured.
				"
			::= { hwRadioNotifyObjects 2 }
		
--    1.3.6.1.4.1.2011.6.139.3.24.3.3
-- 1.3.6.1.4.1.2011.6.139.3.24.2.3
-- 1.3.6.1.4.1.2011.6.139.3.24.3.3
		-- 1.3.6.1.4.1.2011.6.139.3.24.3.3
		hwApMonitorMode OBJECT-TYPE
			SYNTAX Integer32
			MAX-ACCESS read-only
			STATUS current
			DESCRIPTION
				"Description."
			::= { hwRadioNotifyObjects 3 }
		
--   1.3.6.1.4.1.2011.6.139.3.24.2.4
-- 1.3.6.1.4.1.2011.6.139.3.24.3.4
		-- 1.3.6.1.4.1.2011.6.139.3.24.3.4
		hwApPreMonitorMode OBJECT-TYPE
			SYNTAX Integer32
			MAX-ACCESS read-only
			STATUS current
			DESCRIPTION
				"Description."
			::= { hwRadioNotifyObjects 4 }
		
--   1.3.6.1.4.1.2011.6.139.3.24.2.5
-- 1.3.6.1.4.1.2011.6.139.3.24.3.5
		-- 1.3.6.1.4.1.2011.6.139.3.24.3.5
		hwApChannel OBJECT-TYPE
			SYNTAX Integer32
			MAX-ACCESS read-only
			STATUS current
			DESCRIPTION
				"Description."
			::= { hwRadioNotifyObjects 5 }
		
--   1.3.6.1.4.1.2011.6.139.3.24.2.6
-- 1.3.6.1.4.1.2011.6.139.3.24.3.6
		-- 1.3.6.1.4.1.2011.6.139.3.24.3.6
		hwApInterfBssid OBJECT-TYPE
			SYNTAX MacAddress
			MAX-ACCESS read-only
			STATUS current
			DESCRIPTION
				"Description."
			::= { hwRadioNotifyObjects 6 }
		
--   1.3.6.1.4.1.2011.6.139.3.24.2.7
-- 1.3.6.1.4.1.2011.6.139.3.24.3.7
		-- 1.3.6.1.4.1.2011.6.139.3.24.3.7
		hwInterfStaMac OBJECT-TYPE
			SYNTAX OCTET STRING
			MAX-ACCESS read-only
			STATUS current
			DESCRIPTION
				"Description."
			::= { hwRadioNotifyObjects 7 }
		
--   1.3.6.1.4.1.2011.6.139.3.24.2.8
-- 1.3.6.1.4.1.2011.6.139.3.24.3.8
		-- 1.3.6.1.4.1.2011.6.139.3.24.3.8
		hwRadioDownCause OBJECT-TYPE
			SYNTAX Integer32
			MAX-ACCESS read-only
			STATUS current
			DESCRIPTION
				"Description."
			::= { hwRadioNotifyObjects 8 }
		
--  1.3.6.1.4.1.2011.6.139.3.24.3.9
		-- 1.3.6.1.4.1.2011.6.139.3.24.3.9
		hwInterfApChannel OBJECT-TYPE
			SYNTAX Integer32
			MAX-ACCESS read-only
			STATUS current
			DESCRIPTION
				"Description."
			::= { hwRadioNotifyObjects 9 }
		
--  1.3.6.1.4.1.2011.6.139.3.24.3.10
		-- 1.3.6.1.4.1.2011.6.139.3.24.3.10
		hwInterfRSSI OBJECT-TYPE
			SYNTAX Integer32
			MAX-ACCESS read-only
			STATUS current
			DESCRIPTION
				"Description."
			::= { hwRadioNotifyObjects 10 }
		
		-- 1.3.6.1.4.1.2011.6.139.3.24.3.11
		hwWIDSTrapInfoAPID OBJECT-TYPE
			SYNTAX Integer32
			MAX-ACCESS read-only
			STATUS current
			DESCRIPTION
				"The ID of AP that is monitoring."
			::= { hwRadioNotifyObjects 11 }

		-- 1.3.6.1.4.1.2011.6.139.3.24.3.12
		hwWIDSTrapInfoRadioId OBJECT-TYPE
			SYNTAX Integer32
			MAX-ACCESS read-only
			STATUS current
			DESCRIPTION
				"The Radio ID of AP that is monitoring."
			::= { hwRadioNotifyObjects 12 }

		
		-- 1.3.6.1.4.1.2011.6.139.3.24.3.13
		hwWIDSTrapInfoAPMAC OBJECT-TYPE
			SYNTAX MacAddress
			MAX-ACCESS read-only
			STATUS current
			DESCRIPTION
				"The MAC address of AP that is monitoring."
			::= { hwRadioNotifyObjects 13 }

		
		-- 1.3.6.1.4.1.2011.6.139.3.24.3.14
		hwWIDSTrapInfoRogueMAC OBJECT-TYPE
			SYNTAX MacAddress
			MAX-ACCESS read-only
			STATUS current
			DESCRIPTION
				"The MAC address of the rogue device that is monitored."
			::= { hwRadioNotifyObjects 14 }

		
		-- 1.3.6.1.4.1.2011.6.139.3.24.3.15
		hwWIDSTrapInfoRogueSSId OBJECT-TYPE
			SYNTAX OCTET STRING (SIZE (0..32))
			MAX-ACCESS read-only
			STATUS current
			DESCRIPTION
				"The SSID of the rogue device that is monitored."
			::= { hwRadioNotifyObjects 15 }

		
		-- 1.3.6.1.4.1.2011.6.139.3.24.3.16
		hwWIDSTrapInfoRogueType OBJECT-TYPE
			SYNTAX Integer32
			MAX-ACCESS read-only
			STATUS current
			DESCRIPTION
				"The type of the rogue device that is monitored(1 stands for a rogue AP)."
			::= { hwRadioNotifyObjects 16 }

		
		-- 1.3.6.1.4.1.2011.6.139.3.24.3.17
		hwWIDSTrapInfoRogueRSSI OBJECT-TYPE
			SYNTAX Integer32
			MAX-ACCESS read-only
			STATUS current
			DESCRIPTION
				"Description."
			::= { hwRadioNotifyObjects 17 }

		
		-- 1.3.6.1.4.1.2011.6.139.3.24.3.18
		hwWIDSTrapInfoRogueChanID OBJECT-TYPE
			SYNTAX Integer32
			MAX-ACCESS read-only
			STATUS current
			DESCRIPTION
				"Description."
			::= { hwRadioNotifyObjects 18 }

		
		-- 1.3.6.1.4.1.2011.6.139.3.24.3.19
		hwRadioActualChannelBandwidth OBJECT-TYPE
			SYNTAX INTEGER
				{
				ht20(1),
				ht40Plus(2),
				ht40Minus(3)
				}
			MAX-ACCESS read-only
			STATUS current
			DESCRIPTION
				"Description."
			::= { hwRadioNotifyObjects 19 }

		
		-- 1.3.6.1.4.1.2011.6.139.3.24.3.20
		hwRadioActualPowerLevel OBJECT-TYPE
			SYNTAX Integer32
			MAX-ACCESS read-only
			STATUS current
			DESCRIPTION
				"Description."
			::= { hwRadioNotifyObjects 20 }

		
		-- 1.3.6.1.4.1.2011.6.139.3.24.3.21
		hwRadioActualAntennaGain OBJECT-TYPE
			SYNTAX Integer32
			MAX-ACCESS read-only
			STATUS current
			DESCRIPTION
				"Description."
			::= { hwRadioNotifyObjects 21 }

		
		-- 1.3.6.1.4.1.2011.6.139.3.24.3.22
		hwRadioLegitimateAntennaGain OBJECT-TYPE
			SYNTAX Integer32
			MAX-ACCESS read-only
			STATUS current
			DESCRIPTION
				"Description."
			::= { hwRadioNotifyObjects 22 }

		-- 1.3.6.1.4.1.2011.6.139.3.24.3.23
		hwRadioChannelChangedReason OBJECT-TYPE
			SYNTAX INTEGER
				{
				unknown(1),  
				dfs(2),				
				wds(3),
				config(4),
				calibrate(5),
				mesh(6)
				}
			MAX-ACCESS read-only
			STATUS current
			DESCRIPTION
				"Description."
			::= { hwRadioNotifyObjects 23 }

		-- 1.3.6.1.4.1.2011.6.139.3.24.3.24
		hwRadioChannelChangedReasonStr OBJECT-TYPE
			SYNTAX OCTET STRING
			MAX-ACCESS read-only
			STATUS current
			DESCRIPTION
				"Description."
			::= { hwRadioNotifyObjects 24 }

		
		-- 1.3.6.1.4.1.2011.6.139.3.24.3.25
		hwRadioDownCauseStr OBJECT-TYPE
			SYNTAX OCTET STRING
			MAX-ACCESS read-only
			STATUS current
			DESCRIPTION
				"Description."
			::= { hwRadioNotifyObjects 25 }
			
		-- 1.3.6.1.4.1.2011.6.139.3.24.3.26
		hwRadioUacUserNum OBJECT-TYPE
			SYNTAX Integer32
			MAX-ACCESS read-only
			STATUS current
			DESCRIPTION
				"Description."
			::= { hwRadioNotifyObjects 26 }

		-- 1.3.6.1.4.1.2011.6.139.3.24.3.27
		hwRadioPreActualChannel OBJECT-TYPE
			SYNTAX Integer32
			MAX-ACCESS read-only
			STATUS current
			DESCRIPTION
				"Actual channel before being changed. Used in channel change alarm."
			::= { hwRadioNotifyObjects 27 }

			-- 1.3.6.1.4.1.2011.6.139.3.24.3.28
		hwRadioPowerChangedReasonStr OBJECT-TYPE
			SYNTAX OCTET STRING
			MAX-ACCESS read-only
			STATUS current
			DESCRIPTION
				"Radio power change reason."
			::= { hwRadioNotifyObjects 28 }

		

--   1.3.6.1.4.1.2011.6.139.3.25
-- 1.3.6.1.4.1.2011.6.139.3.25
		-- 1.3.6.1.4.1.2011.6.139.3.25
		hwRadioParaStatisticTable OBJECT-TYPE
			SYNTAX SEQUENCE OF HwRadioParaStatisticEntry
			MAX-ACCESS not-accessible
			STATUS current
			DESCRIPTION
				"Description."
			::= { hwRadio 25 }
		
--   1.3.6.1.4.1.2011.6.139.3.25.1
-- 1.3.6.1.4.1.2011.6.139.3.25.1
		-- 1.3.6.1.4.1.2011.6.139.3.25.1
		hwRadioParaStatisticEntry OBJECT-TYPE
			SYNTAX HwRadioParaStatisticEntry
			MAX-ACCESS not-accessible
			STATUS current
			DESCRIPTION
				"Description."
			INDEX { hwApMac, hwRadioID }
			::= { hwRadioParaStatisticTable 1 }
		
		HwRadioParaStatisticEntry ::=
			SEQUENCE { 
				hwRadioStaAveSignalStrength
					Integer32
			 }

--   1.3.6.1.4.1.2011.6.139.3.25.1.1
-- 1.3.6.1.4.1.2011.6.139.3.25.1.1
		-- 1.3.6.1.4.1.2011.6.139.3.25.1.1
		hwRadioStaAveSignalStrength OBJECT-TYPE
			SYNTAX Integer32
			MAX-ACCESS read-only
			STATUS current
			DESCRIPTION
				"Description."
			::= { hwRadioParaStatisticEntry 1 }
		
--   1.3.6.1.4.1.2011.6.139.3.26
-- 1.3.6.1.4.1.2011.6.139.3.26
		-- 1.3.6.1.4.1.2011.6.139.3.26
		hwMacRadioManageTable OBJECT-TYPE
			SYNTAX SEQUENCE OF HwMacRadioManageEntry
			MAX-ACCESS not-accessible
			STATUS current
			DESCRIPTION
				"Description."
			::= { hwRadio 26 }
		
--   1.3.6.1.4.1.2011.6.139.3.26.1
-- 1.3.6.1.4.1.2011.6.139.3.26.1
		-- 1.3.6.1.4.1.2011.6.139.3.26.1
		hwMacRadioManageEntry OBJECT-TYPE
			SYNTAX HwMacRadioManageEntry
			MAX-ACCESS not-accessible
			STATUS current
			DESCRIPTION
				"Description."
			INDEX { hwApMac, hwMacRadioID }
			::= { hwMacRadioManageTable 1 }
		
		HwMacRadioManageEntry ::=
			SEQUENCE { 
				hwMacRadioID
					Unsigned32,
				hwMacRadioMngBaseBssID
					MacAddress,
				hwMacRadioMngRadioProfileName
					OCTET STRING,
				hwMacRadioMngState
					INTEGER,
				hwMacRadioMngChannel
					Unsigned32,
				hwMacRadioMngPowerLevel
					Unsigned32,
				hwMacRadioMngPower
					Integer32,
				hwMacRadioAvailableSntennaNumber
					INTEGER,
				hwMacRadioWorkingChannel
					Unsigned32,
				hwMacRadioWorkingPowerLevel
					Unsigned32,
				hwMacRadioWorkingPower
					Unsigned32,
				hwMacRadioMngChannelBandwidth
					INTEGER,
				hwMacRadioWorkingChannelBandwidth
					INTEGER,
				hwMacRadio80211nMCSValue
					Integer32,
				hwMacRadioWidsWorkMode
					INTEGER,
				hwMacRadioMngBinded
				        INTEGER,
				hwMacRadioMaxTxPwrLvl
					Integer32,
				hwMacRadioPwrAttRange
					Integer32,
				hwMacRadioPwrAttValue
					Integer32,
				hwMacRadioAntennaGain
					Integer32,
				hwMacRadioBridgeWhitelistEnable
					INTEGER,
				hwMacRadioBridgeWhitelistName
					OCTET STRING,
				hwMacRadioBridgeStpSwitch
					INTEGER,
				hwMacRadioBridgeSwitch
					INTEGER,
				hwMacRadioBridgeMode
					INTEGER,
				hwMacRadioUndoBridgeWhitelist
					Integer32,
				hwMacRadioUserTrafficScheduler
					INTEGER,
				hwMacRadioCountermeasuresMode
					Unsigned32,
				hwMacRadioFrequency
					INTEGER,
				hwMacRadioCountermeasuresSwitch
					INTEGER,
				hwMacRadioSpectrumAnalysisEnable
					Integer32,
				hwMACRadioWidsAttackDetEnable
					Integer32,
				hwMacRadioMeshWhitelistName
					OCTET STRING,
				hwMacUndoMeshWhitelist
					Integer32,
				hwMacRadioMeshRole
					INTEGER,
				hwMacRadioLocationEnable
					Integer32,
				hwMacRadioLocationScanChannelEnable
					Integer32,
				hwMacRadio80211nMulticastMCSValue
					Integer32,
				hwMacRadioSpectrogramServerReportEnable
					Integer32,
				hwMacRadioMulticastRateValue
					INTEGER,
				hwMacRadio11acSpatialStream
					Integer32,
				hwMacRadio11acMCSValue
					Integer32,
				hwMacRadioActiveSwitch
					INTEGER					
			 }

--   1.3.6.1.4.1.2011.6.139.3.26.1.1
-- 1.3.6.1.4.1.2011.6.139.3.26.1.1
		-- 1.3.6.1.4.1.2011.6.139.3.26.1.1
		hwMacRadioID OBJECT-TYPE
			SYNTAX Unsigned32
			MAX-ACCESS not-accessible
			STATUS current
			DESCRIPTION
				"Description."
			::= { hwMacRadioManageEntry 1 }
		
--   1.3.6.1.4.1.2011.6.139.3.26.1.2
-- 1.3.6.1.4.1.2011.6.139.3.26.1.2
		-- 1.3.6.1.4.1.2011.6.139.3.26.1.2
		hwMacRadioMngBaseBssID OBJECT-TYPE
			SYNTAX MacAddress
			MAX-ACCESS read-only
			STATUS current
			DESCRIPTION
				"You can get an effective baseBssID ,only when wlan 1 is created. Or you will get a noneffective value.
                                BSSID identifies a minimum service set,When administrator binds a ESS to a radio, it use base BSSID and WlanID to 
				generate a BSSID. The format of the bssid is a max address which contains 3 sets of 2 Btyes hexadecimal character 
				join up with - character, such as 00e0-5678-12fa. 
				"
			::= { hwMacRadioManageEntry 2 }
		
--   1.3.6.1.4.1.2011.6.139.3.26.1.3
-- 1.3.6.1.4.1.2011.6.139.3.26.1.3
		-- 1.3.6.1.4.1.2011.6.139.3.26.1.3
		hwMacRadioMngRadioProfileName OBJECT-TYPE
			SYNTAX OCTET STRING
			MAX-ACCESS read-write
			STATUS current
			DESCRIPTION
				"Description."
			::= { hwMacRadioManageEntry 3 }
		
--   1.3.6.1.4.1.2011.6.139.3.26.1.4
-- 1.3.6.1.4.1.2011.6.139.3.26.1.4
		-- 1.3.6.1.4.1.2011.6.139.3.26.1.4
		hwMacRadioMngState OBJECT-TYPE
			SYNTAX INTEGER
				{
				disable(1),
				enable(2)
				}
			MAX-ACCESS read-write
			STATUS current
			DESCRIPTION
				"Description."
			::= { hwMacRadioManageEntry 4 }
		
--   1.3.6.1.4.1.2011.6.139.3.26.1.5
-- 1.3.6.1.4.1.2011.6.139.3.26.1.5
		-- 1.3.6.1.4.1.2011.6.139.3.26.1.5
		hwMacRadioMngChannel OBJECT-TYPE
			SYNTAX Unsigned32
			MAX-ACCESS read-write
			STATUS current
			DESCRIPTION
				"Description."
			::= { hwMacRadioManageEntry 5 }
		
--   1.3.6.1.4.1.2011.6.139.3.26.1.6
-- 1.3.6.1.4.1.2011.6.139.3.26.1.6
		-- 1.3.6.1.4.1.2011.6.139.3.26.1.6
		hwMacRadioMngPowerLevel OBJECT-TYPE
			SYNTAX Unsigned32
			MAX-ACCESS read-write
			STATUS current
			DESCRIPTION
				"Description."
			::= { hwMacRadioManageEntry 6 }
		
--   1.3.6.1.4.1.2011.6.139.3.26.1.7
-- 1.3.6.1.4.1.2011.6.139.3.26.1.7
		-- 1.3.6.1.4.1.2011.6.139.3.26.1.7
		hwMacRadioMngPower OBJECT-TYPE
			SYNTAX Integer32
			UNITS "dBm"
			MAX-ACCESS read-write
			STATUS current
			DESCRIPTION
				"Description."
			::= { hwMacRadioManageEntry 7 }
		
--   1.3.6.1.4.1.2011.6.139.3.26.1.8
-- 1.3.6.1.4.1.2011.6.139.3.26.1.8
		-- 1.3.6.1.4.1.2011.6.139.3.26.1.8
		hwMacRadioAvailableSntennaNumber OBJECT-TYPE
			SYNTAX INTEGER
				{
				all(1),
				num0(2),
				num1(3),
				num2(4),
				num3(5),
				num4(6),
				num5(7)
				}
			MAX-ACCESS read-write
			STATUS current
			DESCRIPTION
				"Description."
			::= { hwMacRadioManageEntry 8 }
		
--   1.3.6.1.4.1.2011.6.139.3.26.1.9
-- 1.3.6.1.4.1.2011.6.139.3.26.1.9
		-- 1.3.6.1.4.1.2011.6.139.3.26.1.9
		hwMacRadioWorkingChannel OBJECT-TYPE
			SYNTAX Unsigned32
			MAX-ACCESS read-only
			STATUS current
			DESCRIPTION
				"Description."
			::= { hwMacRadioManageEntry 9 }
		
--   1.3.6.1.4.1.2011.6.139.3.26.1.10
-- 1.3.6.1.4.1.2011.6.139.3.26.1.10
		-- 1.3.6.1.4.1.2011.6.139.3.26.1.10
		hwMacRadioWorkingPowerLevel OBJECT-TYPE
			SYNTAX Unsigned32
			MAX-ACCESS read-only
			STATUS current
			DESCRIPTION
				"Description."
			::= { hwMacRadioManageEntry 10 }
		
--   1.3.6.1.4.1.2011.6.139.3.26.1.11
-- 1.3.6.1.4.1.2011.6.139.3.26.1.11
		-- 1.3.6.1.4.1.2011.6.139.3.26.1.11
		hwMacRadioWorkingPower OBJECT-TYPE
			SYNTAX Unsigned32
			MAX-ACCESS read-only
			STATUS current
			DESCRIPTION
				"Description."
			::= { hwMacRadioManageEntry 11 }
		
--   1.3.6.1.4.1.2011.6.139.3.26.1.12
-- 1.3.6.1.4.1.2011.6.139.3.26.1.12
		-- 1.3.6.1.4.1.2011.6.139.3.26.1.12
		hwMacRadioMngChannelBandwidth OBJECT-TYPE
			SYNTAX INTEGER
				{
				ht20(1),
				ht40Plus(2),
				ht40Minus(3),
				ht80(4)
				}
			MAX-ACCESS read-write
			STATUS current
			DESCRIPTION
				"Description."
			::= { hwMacRadioManageEntry 12 }
		
--   1.3.6.1.4.1.2011.6.139.3.26.1.13
-- 1.3.6.1.4.1.2011.6.139.3.26.1.13
		-- 1.3.6.1.4.1.2011.6.139.3.26.1.13
		hwMacRadioWorkingChannelBandwidth OBJECT-TYPE
			SYNTAX INTEGER
				{
				unknown(-1),
				ht20(1),
				ht40Plus(2),
				ht40Minus(3),
				ht80(4)
				}
			MAX-ACCESS read-only
			STATUS current
			DESCRIPTION
				"Description."
			::= { hwMacRadioManageEntry 13 }
		
--   1.3.6.1.4.1.2011.6.139.3.26.1.14
-- 1.3.6.1.4.1.2011.6.139.3.26.1.14
		-- 1.3.6.1.4.1.2011.6.139.3.26.1.14
		hwMacRadio80211nMCSValue OBJECT-TYPE
			SYNTAX Integer32
			MAX-ACCESS read-write
			STATUS current
			DESCRIPTION
				"Description."
			::= { hwMacRadioManageEntry 14 }
		
--   1.3.6.1.4.1.2011.6.139.3.26.1.15
-- 1.3.6.1.4.1.2011.6.139.3.26.1.15
		-- 1.3.6.1.4.1.2011.6.139.3.26.1.15
		hwMacRadioWidsWorkMode OBJECT-TYPE
			SYNTAX INTEGER
				{
				normal(1),
				monitor(2),
				hybrid(3)
				}
			MAX-ACCESS read-write
			STATUS current
			DESCRIPTION
				"Description."
			::= { hwMacRadioManageEntry 15 }
			
			
--   1.3.6.1.4.1.2011.6.139.3.26.1.16
-- 1.3.6.1.4.1.2011.6.139.3.26.1.16
		-- 1.3.6.1.4.1.2011.6.139.3.26.1.16			
              hwMacRadioMngBinded OBJECT-TYPE
                     SYNTAX INTEGER
				{
				 unknown(-1),
                                 true(1),
                                 false(2)                                  
				}
                     MAX-ACCESS read-write
                     STATUS current
                     DESCRIPTION
                                  "Object selects a mechanism for bind/unbind the radio-profile"
                     ::= { hwMacRadioManageEntry 16 }
		
		-- 1.3.6.1.4.1.2011.6.139.3.26.1.18
		hwMacRadioMaxTxPwrLvl OBJECT-TYPE
			SYNTAX Integer32
			MAX-ACCESS read-only
			STATUS current
			DESCRIPTION
				"Description."
			::= { hwMacRadioManageEntry 18 }

		
		-- 1.3.6.1.4.1.2011.6.139.3.26.1.19
		hwMacRadioPwrAttRange OBJECT-TYPE
			SYNTAX Integer32
			MAX-ACCESS read-only
			STATUS current
			DESCRIPTION
				"Description."
			::= { hwMacRadioManageEntry 19 }

		
		-- 1.3.6.1.4.1.2011.6.139.3.26.1.20
		hwMacRadioPwrAttValue OBJECT-TYPE
			SYNTAX Integer32
			MAX-ACCESS read-only
			STATUS current
			DESCRIPTION
				"Description."
			::= { hwMacRadioManageEntry 20 }

		
		-- 1.3.6.1.4.1.2011.6.139.3.26.1.21
		hwMacRadioAntennaGain OBJECT-TYPE
			SYNTAX Integer32
			MAX-ACCESS read-write
			STATUS current
			DESCRIPTION
				"Description."
			::= { hwMacRadioManageEntry 21 }
		
		-- 1.3.6.1.4.1.2011.6.139.3.26.1.22
		hwMacRadioBridgeWhitelistEnable OBJECT-TYPE
			SYNTAX INTEGER
				{
				enable(1),
				disable(2)
				}
			MAX-ACCESS read-write
			STATUS current
			DESCRIPTION
				"Description."
			::= { hwMacRadioManageEntry 22 }

		
		-- 1.3.6.1.4.1.2011.6.139.3.26.1.23
		hwMacRadioBridgeWhitelistName OBJECT-TYPE
			SYNTAX OCTET STRING (SIZE (0..31))
			MAX-ACCESS read-write
			STATUS current
			DESCRIPTION
				"Description."
			::= { hwMacRadioManageEntry 23 }

		
		-- 1.3.6.1.4.1.2011.6.139.3.26.1.24
		hwMacRadioBridgeStpSwitch OBJECT-TYPE
			SYNTAX INTEGER
				{
				enable(1),
				disable(2)
				}
			MAX-ACCESS read-write
			STATUS current
			DESCRIPTION
				"Description."
			::= { hwMacRadioManageEntry 24 }

		-- 1.3.6.1.4.1.2011.6.139.3.26.1.25
		hwMacRadioBridgeSwitch OBJECT-TYPE
			SYNTAX INTEGER
				{
				disable(1),
				enable(2)
				}
			MAX-ACCESS read-write
			STATUS current
			DESCRIPTION
				"Description."
			::= { hwMacRadioManageEntry 25 }

		
		-- 1.3.6.1.4.1.2011.6.139.3.26.1.26
		hwMacRadioBridgeMode OBJECT-TYPE
			SYNTAX INTEGER
				{
				middle(1),
				root(2),
				leaf(3)
				}
			MAX-ACCESS read-write
			STATUS current
			DESCRIPTION
				"Description."
			::= { hwMacRadioManageEntry 26 }

		
		-- 1.3.6.1.4.1.2011.6.139.3.26.1.27
		hwMacRadioUndoBridgeWhitelist OBJECT-TYPE
			SYNTAX Integer32
			MAX-ACCESS read-write
			STATUS current
			DESCRIPTION
				"Description."
			::= { hwMacRadioManageEntry 27 }

		-- 1.3.6.1.4.1.2011.6.139.3.26.1.28
		hwMacRadioUserTrafficScheduler OBJECT-TYPE
			SYNTAX INTEGER
			        { 
			        enable(1),
			        disable(2)
			        }
			MAX-ACCESS read-write
			STATUS obsolete
			DESCRIPTION
				"Description."
			::= { hwMacRadioManageEntry 28 }
		-- 1.3.6.1.4.1.2011.6.139.3.26.1.29
		hwMacRadioCountermeasuresMode OBJECT-TYPE
			SYNTAX Unsigned32
			MAX-ACCESS read-write
			STATUS current
			DESCRIPTION        
				"Description." 
			DEFVAL { 0 }
			::= { hwMacRadioManageEntry 29 }

		
		-- 1.3.6.1.4.1.2011.6.139.3.26.1.30
		hwMacRadioFrequency OBJECT-TYPE
			SYNTAX INTEGER
				{
				frequency2G(1),
				frequency5G(2)
				}
			MAX-ACCESS read-write
			STATUS current
			DESCRIPTION
				"Description."
			::= { hwMacRadioManageEntry 30 }

		-- 1.3.6.1.4.1.2011.6.139.3.26.1.31
		hwMacRadioCountermeasuresSwitch OBJECT-TYPE
			SYNTAX INTEGER
				{
				disable(1),
				enable(2)
				}
			MAX-ACCESS read-write
			STATUS current
			DESCRIPTION
				"Description." 
			DEFVAL { 1 }
			::= { hwMacRadioManageEntry 31 }

		
		-- 1.3.6.1.4.1.2011.6.139.3.26.1.32
		hwMacRadioSpectrumAnalysisEnable OBJECT-TYPE
			SYNTAX Integer32
			MAX-ACCESS read-write
			STATUS current
			DESCRIPTION
				"Description."
			::= { hwMacRadioManageEntry 32 }   
			
 		-- 1.3.6.1.4.1.2011.6.139.3.26.1.33
		hwMACRadioWidsAttackDetEnable OBJECT-TYPE
			SYNTAX Integer32
			MAX-ACCESS read-write
			STATUS current
			DESCRIPTION
				"Description."
			::= { hwMacRadioManageEntry 33 }
					
		-- 1.3.6.1.4.1.2011.6.139.3.26.1.34
		hwMacRadioMeshWhitelistName OBJECT-TYPE
			SYNTAX OCTET STRING
			MAX-ACCESS read-write
			STATUS current
			DESCRIPTION
				"Description."
			::= { hwMacRadioManageEntry 34 }

		
		-- 1.3.6.1.4.1.2011.6.139.3.26.1.35
		hwMacUndoMeshWhitelist OBJECT-TYPE
			SYNTAX Integer32
			MAX-ACCESS read-write
			STATUS current
			DESCRIPTION
				"Description."
			::= { hwMacRadioManageEntry 35 }

		
		-- 1.3.6.1.4.1.2011.6.139.3.26.1.36
		hwMacRadioMeshRole OBJECT-TYPE
			SYNTAX INTEGER
				{
				meshNode(1),
				meshPortal(2)
				}
			MAX-ACCESS read-write
			STATUS current
			DESCRIPTION
				"Description."
			::= { hwMacRadioManageEntry 36 }
		-- 1.3.6.1.4.1.2011.6.139.3.26.1.37
		hwMacRadioLocationEnable OBJECT-TYPE
			SYNTAX Integer32 (0..1)
			MAX-ACCESS read-write
			STATUS current
			DESCRIPTION
				"0: disable
				1: enable"
			::= { hwMacRadioManageEntry 37 }
		-- 1.3.6.1.4.1.2011.6.139.3.26.1.38
		hwMacRadioLocationScanChannelEnable OBJECT-TYPE
			SYNTAX Integer32 (0..1)
			MAX-ACCESS read-write
			STATUS current
			DESCRIPTION
				"0: disable
				1: enable"
			::= { hwMacRadioManageEntry 38 }

		
		-- 1.3.6.1.4.1.2011.6.139.3.26.1.39
		hwMacRadio80211nMulticastMCSValue OBJECT-TYPE
			SYNTAX Integer32
			MAX-ACCESS read-write
			STATUS current
			DESCRIPTION
				"Description."
			::= { hwMacRadioManageEntry 39 }

		
		-- 1.3.6.1.4.1.2011.6.139.3.26.1.40
		hwMacRadioSpectrogramServerReportEnable OBJECT-TYPE
			SYNTAX Integer32 (0..1)
			MAX-ACCESS read-write
			STATUS current
			DESCRIPTION
				"0: disable
				1: enable"
			::= { hwMacRadioManageEntry 40 }

		
		-- 1.3.6.1.4.1.2011.6.139.3.26.1.41
		hwMacRadioMulticastRateValue OBJECT-TYPE
			SYNTAX INTEGER
				{
				unknow(-1),
				rate1(1),
				rate2(2),
				rate55(3),
				rate6(4),
				rate9(5),
				rate11(6),
				rate12(7),
				rate18(8),
				rate24(10),
				rate36(12),
				rate48(13),
				rate54(14)
				}
			MAX-ACCESS read-write
			STATUS current
			DESCRIPTION
				"Description."
			::= { hwMacRadioManageEntry 41 }

		-- 1.3.6.1.4.1.2011.6.139.3.26.1.42
		hwMacRadio11acSpatialStream OBJECT-TYPE
			SYNTAX Integer32 (-1 | 1..3)
			MAX-ACCESS read-write
			STATUS current
			DESCRIPTION
				"Description."
			::= { hwMacRadioManageEntry 42 }
		
		-- 1.3.6.1.4.1.2011.6.139.3.26.1.43
		hwMacRadio11acMCSValue OBJECT-TYPE
			SYNTAX Integer32 (-1 | 0..9)
			MAX-ACCESS read-write
			STATUS current
			DESCRIPTION
				"Description."
			::= { hwMacRadioManageEntry 43 }
		
		-- 1.3.6.1.4.1.2011.6.139.3.26.1.44
		hwMacRadioActiveSwitch OBJECT-TYPE
			SYNTAX INTEGER
				{
				dormancy(1),
				active(2)
				}
			MAX-ACCESS read-write
			STATUS current
			DESCRIPTION
				"Mesh handover feature: Fat AP receive dormancy or active signal through snmp. 
				 When the signal is active, radio of fat ap is enable and send RARP packet;
				 When the signal is dormancy, radio of fat ap is disable."
			::= { hwMacRadioManageEntry 44 }


		-- 1.3.6.1.4.1.2011.6.139.3.27
		hwMacRadioCalibrateStatisicsTable OBJECT-TYPE
			SYNTAX SEQUENCE OF HwMacRadioCalibrateStatisicsEntry
			MAX-ACCESS not-accessible
			STATUS current
			DESCRIPTION
				"Description."
			::= { hwRadio 27 }
		
--   1.3.6.1.4.1.2011.6.139.3.27.1
-- 1.3.6.1.4.1.2011.6.139.3.27.1
		-- 1.3.6.1.4.1.2011.6.139.3.27.1
		hwMacRadioCalibrateStatisicsEntry OBJECT-TYPE
			SYNTAX HwMacRadioCalibrateStatisicsEntry
			MAX-ACCESS not-accessible
			STATUS current
			DESCRIPTION
				"Description."
			INDEX { hwApMac, hwRadioID }
			::= { hwMacRadioCalibrateStatisicsTable 1 }
		
		HwMacRadioCalibrateStatisicsEntry ::=
			SEQUENCE { 
				hwMacRadioCalStatisSignalBadCount
					Unsigned32,
				hwMacRadioCalStatisCalibratePowerCount
					Unsigned32,
				hwMacRadioCalStatisCalibrateChannelCount
					Unsigned32,
				hwMacRadioCalibrateStatisicsOperMode
					INTEGER
			 }

--   1.3.6.1.4.1.2011.6.139.3.27.1.1
-- 1.3.6.1.4.1.2011.6.139.3.27.1.1
		-- 1.3.6.1.4.1.2011.6.139.3.27.1.1
		hwMacRadioCalStatisSignalBadCount OBJECT-TYPE
			SYNTAX Unsigned32
			MAX-ACCESS read-only
			STATUS current
			DESCRIPTION
				"Description."
			::= { hwMacRadioCalibrateStatisicsEntry 1 }
		
--   1.3.6.1.4.1.2011.6.139.3.27.1.2
-- 1.3.6.1.4.1.2011.6.139.3.27.1.2
		-- 1.3.6.1.4.1.2011.6.139.3.27.1.2
		hwMacRadioCalStatisCalibratePowerCount OBJECT-TYPE
			SYNTAX Unsigned32
			MAX-ACCESS read-only
			STATUS current
			DESCRIPTION
				"Description."
			::= { hwMacRadioCalibrateStatisicsEntry 2 }
		
--   1.3.6.1.4.1.2011.6.139.3.27.1.3
-- 1.3.6.1.4.1.2011.6.139.3.27.1.3
		-- 1.3.6.1.4.1.2011.6.139.3.27.1.3
		hwMacRadioCalStatisCalibrateChannelCount OBJECT-TYPE
			SYNTAX Unsigned32
			MAX-ACCESS read-only
			STATUS current
			DESCRIPTION
				"Description."
			::= { hwMacRadioCalibrateStatisicsEntry 3 }
		
--   1.3.6.1.4.1.2011.6.139.3.27.1.4
-- 1.3.6.1.4.1.2011.6.139.3.27.1.4
		-- 1.3.6.1.4.1.2011.6.139.3.27.1.4
		hwMacRadioCalibrateStatisicsOperMode OBJECT-TYPE
			SYNTAX INTEGER
				{
				invalid(-1),
				clearstatistic(1)
				}
			MAX-ACCESS read-write
			STATUS current
			DESCRIPTION
				"Description."
			::= { hwMacRadioCalibrateStatisicsEntry 4 }
		
--   1.3.6.1.4.1.2011.6.139.3.28
-- 1.3.6.1.4.1.2011.6.139.3.28
		-- 1.3.6.1.4.1.2011.6.139.3.28
		hwMacRadioAuthNeighborInfTable OBJECT-TYPE
			SYNTAX SEQUENCE OF HwMacRadioAuthNeighborInfEntry
			MAX-ACCESS not-accessible
			STATUS current
			DESCRIPTION
				"Description."
			::= { hwRadio 28 }
		
--   1.3.6.1.4.1.2011.6.139.3.28.1
-- 1.3.6.1.4.1.2011.6.139.3.28.1
		-- 1.3.6.1.4.1.2011.6.139.3.28.1
		hwMacRadioAuthNeighborInfEntry OBJECT-TYPE
			SYNTAX HwMacRadioAuthNeighborInfEntry
			MAX-ACCESS not-accessible
			STATUS current
			DESCRIPTION
				"Description."
			INDEX { hwApMac, hwRadioID }
			::= { hwMacRadioAuthNeighborInfTable 1 }
		
		HwMacRadioAuthNeighborInfEntry ::=
			SEQUENCE { 
				hwMacAuthenticRadioNeighborAPID
					OCTET STRING,
				hwMacAuthenticRadioNeighborChannel
					OCTET STRING,
				hwMacAuthenticRadioNeighborFrontAttenu
					OCTET STRING,
				hwMacAuthenticRadioNeighborBackAttenu
					OCTET STRING,
				hwMacAuthenticRadioNeighborAPMac
					OCTET STRING,
				hwMacAuthenticRadioNeighborSSID
					OCTET STRING
			 }

--   1.3.6.1.4.1.2011.6.139.3.28.1.1
-- 1.3.6.1.4.1.2011.6.139.3.28.1.1
		-- 1.3.6.1.4.1.2011.6.139.3.28.1.1
		hwMacAuthenticRadioNeighborAPID OBJECT-TYPE
			SYNTAX OCTET STRING
			MAX-ACCESS read-only
			STATUS current
			DESCRIPTION
				"Description."
			::= { hwMacRadioAuthNeighborInfEntry 1 }
		
--   1.3.6.1.4.1.2011.6.139.3.28.1.2
-- 1.3.6.1.4.1.2011.6.139.3.28.1.2
		-- 1.3.6.1.4.1.2011.6.139.3.28.1.2
		hwMacAuthenticRadioNeighborChannel OBJECT-TYPE
			SYNTAX OCTET STRING
			MAX-ACCESS read-only
			STATUS current
			DESCRIPTION
				"Description."
			::= { hwMacRadioAuthNeighborInfEntry 2 }
		
--   1.3.6.1.4.1.2011.6.139.3.28.1.3
-- 1.3.6.1.4.1.2011.6.139.3.28.1.3
		-- 1.3.6.1.4.1.2011.6.139.3.28.1.3
		hwMacAuthenticRadioNeighborFrontAttenu OBJECT-TYPE
			SYNTAX OCTET STRING
			MAX-ACCESS read-only
			STATUS current
			DESCRIPTION
				"Description."
			::= { hwMacRadioAuthNeighborInfEntry 3 }
		
--   1.3.6.1.4.1.2011.6.139.3.28.1.4
-- 1.3.6.1.4.1.2011.6.139.3.28.1.4
		-- 1.3.6.1.4.1.2011.6.139.3.28.1.4
		hwMacAuthenticRadioNeighborBackAttenu OBJECT-TYPE
			SYNTAX OCTET STRING
			MAX-ACCESS read-only
			STATUS current
			DESCRIPTION
				"Description."
			::= { hwMacRadioAuthNeighborInfEntry 4 }
		
--  1.3.6.1.4.1.2011.6.139.3.28.1.5
		-- 1.3.6.1.4.1.2011.6.139.3.28.1.5
		hwMacAuthenticRadioNeighborAPMac OBJECT-TYPE
			SYNTAX OCTET STRING
			MAX-ACCESS read-only
			STATUS current
			DESCRIPTION
				"Description."
			::= { hwMacRadioAuthNeighborInfEntry 5 }
		
		-- 1.3.6.1.4.1.2011.6.139.3.28.1.6
		hwMacAuthenticRadioNeighborSSID OBJECT-TYPE
			SYNTAX OCTET STRING
			MAX-ACCESS read-only
			STATUS current
			DESCRIPTION
				"Description."
			::= { hwMacRadioAuthNeighborInfEntry 6 }

--   1.3.6.1.4.1.2011.6.139.3.29
-- 1.3.6.1.4.1.2011.6.139.3.29
		-- 1.3.6.1.4.1.2011.6.139.3.29
		hwMacRadioLoadBalanceGroupMemberTable OBJECT-TYPE
			SYNTAX SEQUENCE OF HwMacRadioLoadBalanceGroupMemberEntry
			MAX-ACCESS not-accessible
			STATUS current
			DESCRIPTION
				"Description."
			::= { hwRadio 29 }
		
--   1.3.6.1.4.1.2011.6.139.3.29.1
-- 1.3.6.1.4.1.2011.6.139.3.29.1
		-- 1.3.6.1.4.1.2011.6.139.3.29.1
		hwMacRadioLoadBalanceGroupMemberEntry OBJECT-TYPE
			SYNTAX HwMacRadioLoadBalanceGroupMemberEntry
			MAX-ACCESS not-accessible
			STATUS current
			DESCRIPTION
				"Description."
			INDEX { hwLBGroupName, hwApMac, hwRadioID }
			::= { hwMacRadioLoadBalanceGroupMemberTable 1 }
		
		HwMacRadioLoadBalanceGroupMemberEntry ::=
			SEQUENCE { 
				hwMacLBMemberRadioChannel
					Unsigned32,
				hwMacLBMemberRadioPowerLevel
					Unsigned32,
				hwMacLBMemberRadioPower
					Unsigned32,
				hwMacLBMemberRadioSeesionNum
					Unsigned32,
				hwMacLBMemberRadioTraffic
					Unsigned32,
				hwMacLBMemberRowStatus
					RowStatus
			 }

--   1.3.6.1.4.1.2011.6.139.3.29.1.1
-- 1.3.6.1.4.1.2011.6.139.3.29.1.1
		-- 1.3.6.1.4.1.2011.6.139.3.29.1.1
		hwMacLBMemberRadioChannel OBJECT-TYPE
			SYNTAX Unsigned32
			MAX-ACCESS read-only
			STATUS current
			DESCRIPTION
				"Description."
			::= { hwMacRadioLoadBalanceGroupMemberEntry 1 }
		
--   1.3.6.1.4.1.2011.6.139.3.29.1.2
-- 1.3.6.1.4.1.2011.6.139.3.29.1.2
		-- 1.3.6.1.4.1.2011.6.139.3.29.1.2
		hwMacLBMemberRadioPowerLevel OBJECT-TYPE
			SYNTAX Unsigned32
			MAX-ACCESS read-only
			STATUS current
			DESCRIPTION
				"Description."
			::= { hwMacRadioLoadBalanceGroupMemberEntry 2 }
		
--   1.3.6.1.4.1.2011.6.139.3.29.1.3
-- 1.3.6.1.4.1.2011.6.139.3.29.1.3
		-- 1.3.6.1.4.1.2011.6.139.3.29.1.3
		hwMacLBMemberRadioPower OBJECT-TYPE
			SYNTAX Unsigned32
			MAX-ACCESS read-only
			STATUS current
			DESCRIPTION
				"Description."
			::= { hwMacRadioLoadBalanceGroupMemberEntry 3 }
		
--   1.3.6.1.4.1.2011.6.139.3.29.1.4
-- 1.3.6.1.4.1.2011.6.139.3.29.1.4
		-- 1.3.6.1.4.1.2011.6.139.3.29.1.4
		hwMacLBMemberRadioSeesionNum OBJECT-TYPE
			SYNTAX Unsigned32
			MAX-ACCESS read-only
			STATUS current
			DESCRIPTION
				"Description."
			::= { hwMacRadioLoadBalanceGroupMemberEntry 4 }
		
--   1.3.6.1.4.1.2011.6.139.3.29.1.5
-- 1.3.6.1.4.1.2011.6.139.3.29.1.5
		-- 1.3.6.1.4.1.2011.6.139.3.29.1.5
		hwMacLBMemberRadioTraffic OBJECT-TYPE
			SYNTAX Unsigned32
			MAX-ACCESS read-only
			STATUS current
			DESCRIPTION
				"Description."
			::= { hwMacRadioLoadBalanceGroupMemberEntry 5 }
		
--   1.3.6.1.4.1.2011.6.139.3.29.1.6
-- 1.3.6.1.4.1.2011.6.139.3.29.1.6
		-- 1.3.6.1.4.1.2011.6.139.3.29.1.6
		hwMacLBMemberRowStatus OBJECT-TYPE
			SYNTAX RowStatus
			MAX-ACCESS read-create
			STATUS current
			DESCRIPTION
				"Description."
			::= { hwMacRadioLoadBalanceGroupMemberEntry 6 }
		
--   1.3.6.1.4.1.2011.6.139.3.30
-- 1.3.6.1.4.1.2011.6.139.3.30
		-- 1.3.6.1.4.1.2011.6.139.3.30
		hwMacRadioPerformanceStatTable OBJECT-TYPE
			SYNTAX SEQUENCE OF HwMacRadioPerformanceStatEntry
			MAX-ACCESS not-accessible
			STATUS current
			DESCRIPTION
				"Description."
			::= { hwRadio 30 }
		
--   1.3.6.1.4.1.2011.6.139.3.30.1
-- 1.3.6.1.4.1.2011.6.139.3.30.1
		-- 1.3.6.1.4.1.2011.6.139.3.30.1
		hwMacRadioPerformanceStatEntry OBJECT-TYPE
			SYNTAX HwMacRadioPerformanceStatEntry
			MAX-ACCESS not-accessible
			STATUS current
			DESCRIPTION
				"Description."
			INDEX { hwApMac, hwRadioID }
			::= { hwMacRadioPerformanceStatTable 1 }
		
		HwMacRadioPerformanceStatEntry ::=
			SEQUENCE { 
				hwMacRadioRcvFrames
					Unsigned32,
				hwMacRadioRcvBytes
					Unsigned32,
				hwMacRadioSendFrames
					Unsigned32,
				hwMacRadioSendBytes
					Unsigned32,
				hwMacRadioSendRtsSuccess
					Unsigned32,
				hwMacRadioSendUnicast
					Unsigned32,
				hwMacRadioSendBroadcast
					Unsigned32,
				hwMacRadioSendFailFrames
					Unsigned32,
				hwMacRadioRcvErrFrames
					Unsigned32,
				hwMacRadioRcvPhyErrFrames
					Unsigned32,
				hwMacRadioRcvCrcErrFrames
					Unsigned32,
				hwMacRadioRcvMicErrFrames
					Unsigned32,
				hwMacRadioRcvKeyDecryptErrFrames
					Unsigned32,
				hwMacRadioRetryFrames
					Unsigned32,
				hwMacRadioPER
					Unsigned32,
				hwMacRadioChUtilizationRate
					Unsigned32,
				hwMacRadioPerformanceStatOperMode
					INTEGER,
				hwMacRadioPEROfLastPeriod
					Unsigned32,
				hwMacRadioRcvSignalStrength
					Integer32,
				hwMacRadioDownMacErrFrames
					Unsigned32,
				hwMacRadioRcvPower
					Integer32,
				hwMacRadioRcvUnicastFrames
					Counter64,
				hwMacRadioRcvMngFrames
					Counter64,
				hwMacRadioRcvCtrlFrames
					Counter64,
				hwMacRadioRcvDataFrames
					Counter64,
				hwMacRadioSendMngFrames
					Counter64,
				hwMacRadioSendCtrlFrames
					Counter64,
				hwMacRadioSendDataFrames
					Counter64,
				hwMacRadioStaMaxSignalStrength
					Integer32,
				hwMacRadioStaMinSignalStrength
					Integer32,
				hwMacRadioStaAvgSignalStrength
					Integer32,
				hwMacRadioSendRate
					Unsigned32,
				hwMacRadioRecvRate
					Unsigned32,
				hwMacRadioDropRate
					Unsigned32,
				hwMacRadioAirPortDhcpFrames
					Counter64,
				hwMacRadioAirPortEapolFrames
					Counter64,
				hwMacRadioAirPortPsPollFrames
					Counter64,
				hwMacRadioAssocRequestFrames
					Counter64,
				hwMacRadioAssocResponseFrames
					Counter64,
				hwMacRadioReassocRequestFrames
					Counter64,
				hwMacRadioReassocResponseFrames
					Counter64,
				hwMacRadioDisassocFrames
					Counter64,
				hwMacRadioDisauthFrames
					Counter64,
				hwMacRadioRcvFrames64Bits
					Counter64,
				hwMacRadioRcvBytes64Bits
					Counter64,
				hwMacRadioSendFrames64Bits
					Counter64,
				hwMacRadioSendBytes64Bits
					Counter64,
				hwMacRadioSendRtsSuccess64Bits
					Counter64,
				hwMacRadioSendUnicast64Bits
					Counter64,
				hwMacRadioSendBroadcast64Bits
					Counter64,
				hwMacRadioSendFailFrames64Bits
					Counter64,
				hwMacRadioRcvErrFrames64Bits
					Counter64,
				hwMacRadioRcvPhyErrFrames64Bits
					Counter64,
				hwMacRadioRcvCrcErrFrames64Bits
					Counter64,
				hwMacRadioRcvMicErrFrames64Bits
					Counter64,
				hwMacRadioRcvKeyDecryptErrFrames64Bits
					Counter64,
				hwMacRadioRetryFrames64Bits
					Counter64,
				hwMacRadioDownMacErrFrames64Bits
					Counter64,
				hwMacRadioNoise
					Integer32,
				hwMacRadioActualBandwidth
					Unsigned32,
				hwMacRadioFrames
					Counter64,
				hwMacRadioSendDropFrames64Bits
					Counter64,
				hwMacRadioRcvDropFrames64Bits
					Counter64,
				hwMacRadioChannelFreeRate
					Unsigned32,
				hwMacRadioTxRate
					Unsigned32,
				hwMacRadioRxRate
					Unsigned32,
				hwMacRadioChInterferenceRate
					Unsigned32
			 }

--   1.3.6.1.4.1.2011.6.139.3.30.1.1
-- 1.3.6.1.4.1.2011.6.139.3.30.1.1
		-- 1.3.6.1.4.1.2011.6.139.3.30.1.1
		hwMacRadioRcvFrames OBJECT-TYPE
			SYNTAX Unsigned32
			MAX-ACCESS read-only
			STATUS current
			DESCRIPTION
				"Description."
			::= { hwMacRadioPerformanceStatEntry 1 }
		
--   1.3.6.1.4.1.2011.6.139.3.30.1.2
-- 1.3.6.1.4.1.2011.6.139.3.30.1.2
		-- 1.3.6.1.4.1.2011.6.139.3.30.1.2
		hwMacRadioRcvBytes OBJECT-TYPE
			SYNTAX Unsigned32
			MAX-ACCESS read-only
			STATUS current
			DESCRIPTION
				"Description."
			::= { hwMacRadioPerformanceStatEntry 2 }
		
--   1.3.6.1.4.1.2011.6.139.3.30.1.3
-- 1.3.6.1.4.1.2011.6.139.3.30.1.3
		-- 1.3.6.1.4.1.2011.6.139.3.30.1.3
		hwMacRadioSendFrames OBJECT-TYPE
			SYNTAX Unsigned32
			MAX-ACCESS read-only
			STATUS current
			DESCRIPTION
				"Description."
			::= { hwMacRadioPerformanceStatEntry 3 }
		
--   1.3.6.1.4.1.2011.6.139.3.30.1.4
-- 1.3.6.1.4.1.2011.6.139.3.30.1.4
		-- 1.3.6.1.4.1.2011.6.139.3.30.1.4
		hwMacRadioSendBytes OBJECT-TYPE
			SYNTAX Unsigned32
			MAX-ACCESS read-only
			STATUS current
			DESCRIPTION
				"Description."
			::= { hwMacRadioPerformanceStatEntry 4 }
		
--   1.3.6.1.4.1.2011.6.139.3.30.1.5
-- 1.3.6.1.4.1.2011.6.139.3.30.1.5
		-- 1.3.6.1.4.1.2011.6.139.3.30.1.5
		hwMacRadioSendRtsSuccess OBJECT-TYPE
			SYNTAX Unsigned32
			MAX-ACCESS read-only
			STATUS current
			DESCRIPTION
				"Description."
			::= { hwMacRadioPerformanceStatEntry 5 }
		
--   1.3.6.1.4.1.2011.6.139.3.30.1.6
-- 1.3.6.1.4.1.2011.6.139.3.30.1.6
		-- 1.3.6.1.4.1.2011.6.139.3.30.1.6
		hwMacRadioSendUnicast OBJECT-TYPE
			SYNTAX Unsigned32
			MAX-ACCESS read-only
			STATUS current
			DESCRIPTION
				"Description."
			::= { hwMacRadioPerformanceStatEntry 6 }
		
--   1.3.6.1.4.1.2011.6.139.3.30.1.7
-- 1.3.6.1.4.1.2011.6.139.3.30.1.7
		-- 1.3.6.1.4.1.2011.6.139.3.30.1.7
		hwMacRadioSendBroadcast OBJECT-TYPE
			SYNTAX Unsigned32
			MAX-ACCESS read-only
			STATUS current
			DESCRIPTION
				"Description."
			::= { hwMacRadioPerformanceStatEntry 7 }
		
--   1.3.6.1.4.1.2011.6.139.3.30.1.8
-- 1.3.6.1.4.1.2011.6.139.3.30.1.8
		-- 1.3.6.1.4.1.2011.6.139.3.30.1.8
		hwMacRadioSendFailFrames OBJECT-TYPE
			SYNTAX Unsigned32
			MAX-ACCESS read-only
			STATUS current
			DESCRIPTION
				"Description."
			::= { hwMacRadioPerformanceStatEntry 8 }
		
--   1.3.6.1.4.1.2011.6.139.3.30.1.9
-- 1.3.6.1.4.1.2011.6.139.3.30.1.9
		-- 1.3.6.1.4.1.2011.6.139.3.30.1.9
		hwMacRadioRcvErrFrames OBJECT-TYPE
			SYNTAX Unsigned32
			MAX-ACCESS read-only
			STATUS current
			DESCRIPTION
				"Description."
			::= { hwMacRadioPerformanceStatEntry 9 }
		
--   1.3.6.1.4.1.2011.6.139.3.30.1.10
-- 1.3.6.1.4.1.2011.6.139.3.30.1.10
		-- 1.3.6.1.4.1.2011.6.139.3.30.1.10
		hwMacRadioRcvPhyErrFrames OBJECT-TYPE
			SYNTAX Unsigned32
			MAX-ACCESS read-only
			STATUS current
			DESCRIPTION
				"Description."
			::= { hwMacRadioPerformanceStatEntry 10 }
		
--   1.3.6.1.4.1.2011.6.139.3.30.1.11
-- 1.3.6.1.4.1.2011.6.139.3.30.1.11
		-- 1.3.6.1.4.1.2011.6.139.3.30.1.11
		hwMacRadioRcvCrcErrFrames OBJECT-TYPE
			SYNTAX Unsigned32
			MAX-ACCESS read-only
			STATUS current
			DESCRIPTION
				"Description."
			::= { hwMacRadioPerformanceStatEntry 11 }
		
--   1.3.6.1.4.1.2011.6.139.3.30.1.12
-- 1.3.6.1.4.1.2011.6.139.3.30.1.12
		-- 1.3.6.1.4.1.2011.6.139.3.30.1.12
		hwMacRadioRcvMicErrFrames OBJECT-TYPE
			SYNTAX Unsigned32
			MAX-ACCESS read-only
			STATUS current
			DESCRIPTION
				"Description."
			::= { hwMacRadioPerformanceStatEntry 12 }
		
--   1.3.6.1.4.1.2011.6.139.3.30.1.13
-- 1.3.6.1.4.1.2011.6.139.3.30.1.13
		-- 1.3.6.1.4.1.2011.6.139.3.30.1.13
		hwMacRadioRcvKeyDecryptErrFrames OBJECT-TYPE
			SYNTAX Unsigned32
			MAX-ACCESS read-only
			STATUS current
			DESCRIPTION
				"Description."
			::= { hwMacRadioPerformanceStatEntry 13 }
		
--   1.3.6.1.4.1.2011.6.139.3.30.1.14
-- 1.3.6.1.4.1.2011.6.139.3.30.1.14
		-- 1.3.6.1.4.1.2011.6.139.3.30.1.14
		hwMacRadioRetryFrames OBJECT-TYPE
			SYNTAX Unsigned32
			MAX-ACCESS read-only
			STATUS current
			DESCRIPTION
				"Description."
			::= { hwMacRadioPerformanceStatEntry 14 }
		
--   1.3.6.1.4.1.2011.6.139.3.30.1.15
-- 1.3.6.1.4.1.2011.6.139.3.30.1.15
		-- 1.3.6.1.4.1.2011.6.139.3.30.1.15
		hwMacRadioPER OBJECT-TYPE
			SYNTAX Unsigned32
			MAX-ACCESS read-only
			STATUS current
			DESCRIPTION
				"Description."
			::= { hwMacRadioPerformanceStatEntry 15 }
		
--   1.3.6.1.4.1.2011.6.139.3.30.1.16
-- 1.3.6.1.4.1.2011.6.139.3.30.1.16
		-- 1.3.6.1.4.1.2011.6.139.3.30.1.16
		hwMacRadioChUtilizationRate OBJECT-TYPE
			SYNTAX Unsigned32
			MAX-ACCESS read-only
			STATUS current
			DESCRIPTION
				"Description."
			::= { hwMacRadioPerformanceStatEntry 16 }
		
--   1.3.6.1.4.1.2011.6.139.3.30.1.17
-- 1.3.6.1.4.1.2011.6.139.3.30.1.17
		-- 1.3.6.1.4.1.2011.6.139.3.30.1.17
		hwMacRadioPerformanceStatOperMode OBJECT-TYPE
			SYNTAX INTEGER
				{
				invalid(-1),
				clearstatistic(1)
				}
			MAX-ACCESS read-write
			STATUS current
			DESCRIPTION
				"Description."
			::= { hwMacRadioPerformanceStatEntry 17 }
		
--   1.3.6.1.4.1.2011.6.139.3.30.1.18
-- 1.3.6.1.4.1.2011.6.139.3.30.1.18
		-- 1.3.6.1.4.1.2011.6.139.3.30.1.18
		hwMacRadioPEROfLastPeriod OBJECT-TYPE
			SYNTAX Unsigned32
			MAX-ACCESS read-only
			STATUS current
			DESCRIPTION
				"Description."
			::= { hwMacRadioPerformanceStatEntry 18 }
		
--   1.3.6.1.4.1.2011.6.139.3.30.1.19
-- 1.3.6.1.4.1.2011.6.139.3.30.1.19
		-- 1.3.6.1.4.1.2011.6.139.3.30.1.19
		hwMacRadioRcvSignalStrength OBJECT-TYPE
			SYNTAX Integer32
			MAX-ACCESS read-only
			STATUS current
			DESCRIPTION
				"Description."
			::= { hwMacRadioPerformanceStatEntry 19 }
		
--   1.3.6.1.4.1.2011.6.139.3.30.1.20
-- 1.3.6.1.4.1.2011.6.139.3.30.1.20
		-- 1.3.6.1.4.1.2011.6.139.3.30.1.20
		hwMacRadioDownMacErrFrames OBJECT-TYPE
			SYNTAX Unsigned32
			MAX-ACCESS read-only
			STATUS current
			DESCRIPTION
				"Description."
			::= { hwMacRadioPerformanceStatEntry 20 }
		
--   1.3.6.1.4.1.2011.6.139.3.30.1.21
-- 1.3.6.1.4.1.2011.6.139.3.30.1.21
		-- 1.3.6.1.4.1.2011.6.139.3.30.1.21
		hwMacRadioRcvPower OBJECT-TYPE
			SYNTAX Integer32
			MAX-ACCESS read-only
			STATUS current
			DESCRIPTION
				"Description."
			::= { hwMacRadioPerformanceStatEntry 21 }
		
		-- 1.3.6.1.4.1.2011.6.139.3.30.1.22
		hwMacRadioRcvUnicastFrames OBJECT-TYPE
			SYNTAX Counter64
			MAX-ACCESS read-only
			STATUS current
			DESCRIPTION
				"Description."
			::= { hwMacRadioPerformanceStatEntry 22 }

		
		-- 1.3.6.1.4.1.2011.6.139.3.30.1.23
		hwMacRadioRcvMngFrames OBJECT-TYPE
			SYNTAX Counter64
			MAX-ACCESS read-only
			STATUS current
			DESCRIPTION
				"Description."
			::= { hwMacRadioPerformanceStatEntry 23 }

		
		-- 1.3.6.1.4.1.2011.6.139.3.30.1.24
		hwMacRadioRcvCtrlFrames OBJECT-TYPE
			SYNTAX Counter64
			MAX-ACCESS read-only
			STATUS current
			DESCRIPTION
				"Description."
			::= { hwMacRadioPerformanceStatEntry 24 }

		
		-- 1.3.6.1.4.1.2011.6.139.3.30.1.25
		hwMacRadioRcvDataFrames OBJECT-TYPE
			SYNTAX Counter64
			MAX-ACCESS read-only
			STATUS current
			DESCRIPTION
				"Description."
			::= { hwMacRadioPerformanceStatEntry 25 }

		
		-- 1.3.6.1.4.1.2011.6.139.3.30.1.26
		hwMacRadioSendMngFrames OBJECT-TYPE
			SYNTAX Counter64
			MAX-ACCESS read-only
			STATUS current
			DESCRIPTION
				"Description."
			::= { hwMacRadioPerformanceStatEntry 26 }

		
		-- 1.3.6.1.4.1.2011.6.139.3.30.1.27
		hwMacRadioSendCtrlFrames OBJECT-TYPE
			SYNTAX Counter64
			MAX-ACCESS read-only
			STATUS current
			DESCRIPTION
				"Description."
			::= { hwMacRadioPerformanceStatEntry 27 }

		
		-- 1.3.6.1.4.1.2011.6.139.3.30.1.28
		hwMacRadioSendDataFrames OBJECT-TYPE
			SYNTAX Counter64
			MAX-ACCESS read-only
			STATUS current
			DESCRIPTION
				"Description."
			::= { hwMacRadioPerformanceStatEntry 28 }

		
		-- 1.3.6.1.4.1.2011.6.139.3.30.1.29
		hwMacRadioStaMaxSignalStrength OBJECT-TYPE
			SYNTAX Integer32
			MAX-ACCESS read-only
			STATUS current
			DESCRIPTION
				"Description."
			::= { hwMacRadioPerformanceStatEntry 29 }

		
		-- 1.3.6.1.4.1.2011.6.139.3.30.1.30
		hwMacRadioStaMinSignalStrength OBJECT-TYPE
			SYNTAX Integer32
			MAX-ACCESS read-only
			STATUS current
			DESCRIPTION
				"Description."
			::= { hwMacRadioPerformanceStatEntry 30 }

		
		-- 1.3.6.1.4.1.2011.6.139.3.30.1.31
		hwMacRadioStaAvgSignalStrength OBJECT-TYPE
			SYNTAX Integer32
			MAX-ACCESS read-only
			STATUS current
			DESCRIPTION
				"Description."
			::= { hwMacRadioPerformanceStatEntry 31 }
			
			-- 1.3.6.1.4.1.2011.6.139.3.30.1.32
		hwMacRadioSendRate OBJECT-TYPE
			SYNTAX Unsigned32
			MAX-ACCESS read-only
			STATUS current
			DESCRIPTION
				"Description."
			::= { hwMacRadioPerformanceStatEntry 32 }

		
		-- 1.3.6.1.4.1.2011.6.139.3.30.1.33
		hwMacRadioRecvRate OBJECT-TYPE
			SYNTAX Unsigned32
			MAX-ACCESS read-only
			STATUS current
			DESCRIPTION
				"Description."
			::= { hwMacRadioPerformanceStatEntry 33 }

		
		-- 1.3.6.1.4.1.2011.6.139.3.30.1.34
		hwMacRadioDropRate OBJECT-TYPE
			SYNTAX Unsigned32
			MAX-ACCESS read-only
			STATUS current
			DESCRIPTION
				"Description."
			::= { hwMacRadioPerformanceStatEntry 34 }
		
		-- 1.3.6.1.4.1.2011.6.139.3.8.1.35
		hwMacRadioAirPortDhcpFrames OBJECT-TYPE
			SYNTAX Counter64
			MAX-ACCESS read-only
			STATUS current
			DESCRIPTION
				"Description."
			::= { hwMacRadioPerformanceStatEntry 35 }

		
		-- 1.3.6.1.4.1.2011.6.139.3.8.1.36
		hwMacRadioAirPortEapolFrames OBJECT-TYPE
			SYNTAX Counter64
			MAX-ACCESS read-only
			STATUS current
			DESCRIPTION
				"Description."
			::= { hwMacRadioPerformanceStatEntry 36 }

		
		-- 1.3.6.1.4.1.2011.6.139.3.8.1.37
		hwMacRadioAirPortPsPollFrames OBJECT-TYPE
			SYNTAX Counter64
			MAX-ACCESS read-only
			STATUS current
			DESCRIPTION
				"Description."
			::= { hwMacRadioPerformanceStatEntry 37 }

		
		-- 1.3.6.1.4.1.2011.6.139.3.8.1.38
		hwMacRadioAssocRequestFrames OBJECT-TYPE
			SYNTAX Counter64
			MAX-ACCESS read-only
			STATUS current
			DESCRIPTION
				"Description."
			::= { hwMacRadioPerformanceStatEntry 38 }

		
		-- 1.3.6.1.4.1.2011.6.139.3.8.1.39
		hwMacRadioAssocResponseFrames OBJECT-TYPE
			SYNTAX Counter64
			MAX-ACCESS read-only
			STATUS current
			DESCRIPTION
				"Description."
			::= { hwMacRadioPerformanceStatEntry 39 }

		
		-- 1.3.6.1.4.1.2011.6.139.3.8.1.40
		hwMacRadioReassocRequestFrames OBJECT-TYPE
			SYNTAX Counter64
			MAX-ACCESS read-only
			STATUS current
			DESCRIPTION
				"Description."
			::= { hwMacRadioPerformanceStatEntry 40 }

		
		-- 1.3.6.1.4.1.2011.6.139.3.8.1.41
		hwMacRadioReassocResponseFrames OBJECT-TYPE
			SYNTAX Counter64
			MAX-ACCESS read-only
			STATUS current
			DESCRIPTION
				"Description."
			::= { hwMacRadioPerformanceStatEntry 41 }

		
		-- 1.3.6.1.4.1.2011.6.139.3.8.1.42
		hwMacRadioDisassocFrames OBJECT-TYPE
			SYNTAX Counter64
			MAX-ACCESS read-only
			STATUS current
			DESCRIPTION
				"Description."
			::= { hwMacRadioPerformanceStatEntry 42 }

		
		-- 1.3.6.1.4.1.2011.6.139.3.8.1.43
		hwMacRadioDisauthFrames OBJECT-TYPE
			SYNTAX Counter64
			MAX-ACCESS read-only
			STATUS current
			DESCRIPTION
				"Description."
			::= { hwMacRadioPerformanceStatEntry 43 }

		
		-- 1.3.6.1.4.1.2011.6.139.3.30.1.44
		hwMacRadioRcvFrames64Bits OBJECT-TYPE
			SYNTAX Counter64
			MAX-ACCESS read-only
			STATUS current
			DESCRIPTION
				"Description."
			::= { hwMacRadioPerformanceStatEntry 44 }

		
		-- 1.3.6.1.4.1.2011.6.139.3.30.1.45
		hwMacRadioRcvBytes64Bits OBJECT-TYPE
			SYNTAX Counter64
			MAX-ACCESS read-only
			STATUS current
			DESCRIPTION
				"Description."
			::= { hwMacRadioPerformanceStatEntry 45 }

		
		-- 1.3.6.1.4.1.2011.6.139.3.30.1.46
		hwMacRadioSendFrames64Bits OBJECT-TYPE
			SYNTAX Counter64
			MAX-ACCESS read-only
			STATUS current
			DESCRIPTION
				"Description."
			::= { hwMacRadioPerformanceStatEntry 46 }

		
		-- 1.3.6.1.4.1.2011.6.139.3.30.1.47
		hwMacRadioSendBytes64Bits OBJECT-TYPE
			SYNTAX Counter64
			MAX-ACCESS read-only
			STATUS current
			DESCRIPTION
				"Description."
			::= { hwMacRadioPerformanceStatEntry 47 }

		
		-- 1.3.6.1.4.1.2011.6.139.3.30.1.48
		hwMacRadioSendRtsSuccess64Bits OBJECT-TYPE
			SYNTAX Counter64
			MAX-ACCESS read-only
			STATUS current
			DESCRIPTION
				"Description."
			::= { hwMacRadioPerformanceStatEntry 48 }

		
		-- 1.3.6.1.4.1.2011.6.139.3.30.1.49
		hwMacRadioSendUnicast64Bits OBJECT-TYPE
			SYNTAX Counter64
			MAX-ACCESS read-only
			STATUS current
			DESCRIPTION
				"Description."
			::= { hwMacRadioPerformanceStatEntry 49 }

		
		-- 1.3.6.1.4.1.2011.6.139.3.30.1.50
		hwMacRadioSendBroadcast64Bits OBJECT-TYPE
			SYNTAX Counter64
			MAX-ACCESS read-only
			STATUS current
			DESCRIPTION
				"Description."
			::= { hwMacRadioPerformanceStatEntry 50 }

		
		-- 1.3.6.1.4.1.2011.6.139.3.30.1.51
		hwMacRadioSendFailFrames64Bits OBJECT-TYPE
			SYNTAX Counter64
			MAX-ACCESS read-only
			STATUS current
			DESCRIPTION
				"Description."
			::= { hwMacRadioPerformanceStatEntry 51 }

		
		-- 1.3.6.1.4.1.2011.6.139.3.30.1.52
		hwMacRadioRcvErrFrames64Bits OBJECT-TYPE
			SYNTAX Counter64
			MAX-ACCESS read-only
			STATUS current
			DESCRIPTION
				"Description."
			::= { hwMacRadioPerformanceStatEntry 52 }

		
		-- 1.3.6.1.4.1.2011.6.139.3.30.1.53
		hwMacRadioRcvPhyErrFrames64Bits OBJECT-TYPE
			SYNTAX Counter64
			MAX-ACCESS read-only
			STATUS current
			DESCRIPTION
				"Description."
			::= { hwMacRadioPerformanceStatEntry 53 }

		
		-- 1.3.6.1.4.1.2011.6.139.3.30.1.54
		hwMacRadioRcvCrcErrFrames64Bits OBJECT-TYPE
			SYNTAX Counter64
			MAX-ACCESS read-only
			STATUS current
			DESCRIPTION
				"Description."
			::= { hwMacRadioPerformanceStatEntry 54 }

		
		-- 1.3.6.1.4.1.2011.6.139.3.30.1.55
		hwMacRadioRcvMicErrFrames64Bits OBJECT-TYPE
			SYNTAX Counter64
			MAX-ACCESS read-only
			STATUS current
			DESCRIPTION
				"Description."
			::= { hwMacRadioPerformanceStatEntry 55 }

		
		-- 1.3.6.1.4.1.2011.6.139.3.30.1.56
		hwMacRadioRcvKeyDecryptErrFrames64Bits OBJECT-TYPE
			SYNTAX Counter64
			MAX-ACCESS read-only
			STATUS current
			DESCRIPTION
				"Description."
			::= { hwMacRadioPerformanceStatEntry 56 }

		
		-- 1.3.6.1.4.1.2011.6.139.3.30.1.57
		hwMacRadioRetryFrames64Bits OBJECT-TYPE
			SYNTAX Counter64
			MAX-ACCESS read-only
			STATUS current
			DESCRIPTION
				"Description."
			::= { hwMacRadioPerformanceStatEntry 57 }

		
		-- 1.3.6.1.4.1.2011.6.139.3.30.1.58
		hwMacRadioDownMacErrFrames64Bits OBJECT-TYPE
			SYNTAX Counter64
			MAX-ACCESS read-only
			STATUS current
			DESCRIPTION
				"Description."
			::= { hwMacRadioPerformanceStatEntry 58 }

		
		-- 1.3.6.1.4.1.2011.6.139.3.30.1.59
		hwMacRadioNoise OBJECT-TYPE
			SYNTAX Integer32
			MAX-ACCESS read-write
			STATUS current
			DESCRIPTION
				"Description."
			::= { hwMacRadioPerformanceStatEntry 59 }
			
		-- 1.3.6.1.4.1.2011.6.139.3.30.1.60
		hwMacRadioActualBandwidth OBJECT-TYPE
			SYNTAX Unsigned32
			MAX-ACCESS read-only
			STATUS current
			DESCRIPTION
				"Description."
			::= { hwMacRadioPerformanceStatEntry 60 }

		
		-- 1.3.6.1.4.1.2011.6.139.3.30.1.61
		hwMacRadioFrames OBJECT-TYPE
			SYNTAX Counter64
			MAX-ACCESS read-only
			STATUS current
			DESCRIPTION
				"Description."
			::= { hwMacRadioPerformanceStatEntry 61 }

		
		-- 1.3.6.1.4.1.2011.6.139.3.30.1.62
		hwMacRadioSendDropFrames64Bits OBJECT-TYPE
			SYNTAX Counter64
			MAX-ACCESS read-only
			STATUS current
			DESCRIPTION
				"Description."
			::= { hwMacRadioPerformanceStatEntry 62 }

		
		-- 1.3.6.1.4.1.2011.6.139.3.30.1.63
		hwMacRadioRcvDropFrames64Bits OBJECT-TYPE
			SYNTAX Counter64
			MAX-ACCESS read-only
			STATUS current
			DESCRIPTION
				"Description."
			::= { hwMacRadioPerformanceStatEntry 63 }

		
		-- 1.3.6.1.4.1.2011.6.139.3.30.1.64
		hwMacRadioChannelFreeRate OBJECT-TYPE
			SYNTAX Unsigned32
			MAX-ACCESS read-only
			STATUS current
			DESCRIPTION
				"Description."
			::= { hwMacRadioPerformanceStatEntry 64 }

		
		-- 1.3.6.1.4.1.2011.6.139.3.30.1.65
		hwMacRadioTxRate OBJECT-TYPE
			SYNTAX Unsigned32
			MAX-ACCESS read-only
			STATUS current
			DESCRIPTION
				"Description."
			::= { hwMacRadioPerformanceStatEntry 65 }

		
		-- 1.3.6.1.4.1.2011.6.139.3.30.1.66
		hwMacRadioRxRate OBJECT-TYPE
			SYNTAX Unsigned32
			MAX-ACCESS read-only
			STATUS current
			DESCRIPTION
				"Description."
			::= { hwMacRadioPerformanceStatEntry 66 }

		
		-- 1.3.6.1.4.1.2011.6.139.3.30.1.67
		hwMacRadioChInterferenceRate OBJECT-TYPE
			SYNTAX Unsigned32
			MAX-ACCESS read-only
			STATUS current
			DESCRIPTION
				"Description."
			::= { hwMacRadioPerformanceStatEntry 67 }



-- 1.3.6.1.4.1.2011.6.139.3.31
		-- 1.3.6.1.4.1.2011.6.139.3.31
		hwMacRadioUnauthenticNeighborInfoTable OBJECT-TYPE
			SYNTAX SEQUENCE OF HwMacRadioUnauthenticNeighborInfoEntry
			MAX-ACCESS not-accessible
			STATUS current
			DESCRIPTION
				"Description."
			::= { hwRadio 31 }
		
--   1.3.6.1.4.1.2011.6.139.3.31.1
-- 1.3.6.1.4.1.2011.6.139.3.31.1
		-- 1.3.6.1.4.1.2011.6.139.3.31.1
		hwMacRadioUnauthenticNeighborInfoEntry OBJECT-TYPE
			SYNTAX HwMacRadioUnauthenticNeighborInfoEntry
			MAX-ACCESS not-accessible
			STATUS current
			DESCRIPTION
				"Description."
			INDEX { hwApMac, hwRadioID }
			::= { hwMacRadioUnauthenticNeighborInfoTable 1 }
		
		HwMacRadioUnauthenticNeighborInfoEntry ::=
			SEQUENCE { 
				hwMacUnauthenticRadioNeighborBSSID
					OCTET STRING,
				hwMacUnauthenticRadioNeighborRSSI
					OCTET STRING,
				hwMacunauthenticRadioNeighborChannel
					OCTET STRING,
				hwMacUnauthenticRadioNeighborSSID
					OCTET STRING
			 }

--   1.3.6.1.4.1.2011.6.139.3.31.1.1
-- 1.3.6.1.4.1.2011.6.139.3.31.1.1
		-- 1.3.6.1.4.1.2011.6.139.3.31.1.1
		hwMacUnauthenticRadioNeighborBSSID OBJECT-TYPE
			SYNTAX OCTET STRING
			MAX-ACCESS read-only
			STATUS current
			DESCRIPTION
				"Description."
			::= { hwMacRadioUnauthenticNeighborInfoEntry 1 }
		
--   1.3.6.1.4.1.2011.6.139.3.31.1.2
-- 1.3.6.1.4.1.2011.6.139.3.31.1.2
		-- 1.3.6.1.4.1.2011.6.139.3.31.1.2
		hwMacUnauthenticRadioNeighborRSSI OBJECT-TYPE
			SYNTAX OCTET STRING
			MAX-ACCESS read-only
			STATUS current
			DESCRIPTION
				"Description."
			::= { hwMacRadioUnauthenticNeighborInfoEntry 2 }
		
--   1.3.6.1.4.1.2011.6.139.3.31.1.3
-- 1.3.6.1.4.1.2011.6.139.3.31.1.3
		-- 1.3.6.1.4.1.2011.6.139.3.31.1.3
		hwMacunauthenticRadioNeighborChannel OBJECT-TYPE
			SYNTAX OCTET STRING
			MAX-ACCESS read-only
			STATUS current
			DESCRIPTION
				"Description."
			::= { hwMacRadioUnauthenticNeighborInfoEntry 3 }
		
--   1.3.6.1.4.1.2011.6.139.3.31.1.4
-- 1.3.6.1.4.1.2011.6.139.3.31.1.4
		-- 1.3.6.1.4.1.2011.6.139.3.31.1.4
		hwMacUnauthenticRadioNeighborSSID OBJECT-TYPE
			SYNTAX OCTET STRING
			MAX-ACCESS read-only
			STATUS current
			DESCRIPTION
				"Description."
			::= { hwMacRadioUnauthenticNeighborInfoEntry 4 }

		
--  1.3.6.1.4.1.2011.6.139.3.32
		-- 1.3.6.1.4.1.2011.6.139.3.32
		hwRadioInfoTable OBJECT-TYPE
			SYNTAX SEQUENCE OF HwRadioInfoEntry
			MAX-ACCESS not-accessible
			STATUS current
			DESCRIPTION
				"Huawei radio wireless port information table.
				."
			::= { hwRadio 32 }

		
--  1.3.6.1.4.1.2011.6.139.3.32.1
		-- 1.3.6.1.4.1.2011.6.139.3.32.1
		hwRadioInfoEntry OBJECT-TYPE
			SYNTAX HwRadioInfoEntry
			MAX-ACCESS not-accessible
			STATUS current
			DESCRIPTION
				"Description."
			INDEX { hwApIndex, hwRadioID }
			::= { hwRadioInfoTable 1 }

		
		HwRadioInfoEntry ::=
			SEQUENCE { 
				hwRadioDecsption
					OCTET STRING,
				hwRadioPortType
					OCTET STRING,
				hwRadioMaxMtu
					Integer32,
				hwRadioBandwidth
					Integer32,
				hwRadioMac
					MacAddress,
				hwRadioAdminStatus
					INTEGER,
				hwRadioOperStatus
					INTEGER,
				hwRadioLastChange
					Integer32,
				hwRadioInfoUpDownTimes
					Integer32,
				hwRadioAutoOffSwitch
					INTEGER,
				hwRadioAutoOffStartTime
					OCTET STRING,
				hwRadioAutoOffEndTime
					OCTET STRING
			 }

--  1.3.6.1.4.1.2011.6.139.3.32.1.1
		-- 1.3.6.1.4.1.2011.6.139.3.32.1.1
		hwRadioDecsption OBJECT-TYPE
			SYNTAX OCTET STRING
			MAX-ACCESS read-only
			STATUS current
			DESCRIPTION
				"Description."
			::= { hwRadioInfoEntry 1 }

		
--  1.3.6.1.4.1.2011.6.139.3.32.1.2
		-- 1.3.6.1.4.1.2011.6.139.3.32.1.2
		hwRadioPortType OBJECT-TYPE
			SYNTAX OCTET STRING
			MAX-ACCESS read-only
			STATUS current
			DESCRIPTION
				"Description."
			::= { hwRadioInfoEntry 2 }

		
--  1.3.6.1.4.1.2011.6.139.3.32.1.3
		-- 1.3.6.1.4.1.2011.6.139.3.32.1.3
		hwRadioMaxMtu OBJECT-TYPE
			SYNTAX Integer32
			UNITS "byte"
			MAX-ACCESS read-only
			STATUS current
			DESCRIPTION
				"Description."
			::= { hwRadioInfoEntry 3 }

		
--  1.3.6.1.4.1.2011.6.139.3.32.1.4
		-- 1.3.6.1.4.1.2011.6.139.3.32.1.4
		hwRadioBandwidth OBJECT-TYPE
			SYNTAX Integer32
			UNITS "Mbps"
			MAX-ACCESS read-only
			STATUS current
			DESCRIPTION
				"Description."
			::= { hwRadioInfoEntry 4 }

		
--  1.3.6.1.4.1.2011.6.139.3.32.1.5
		-- 1.3.6.1.4.1.2011.6.139.3.32.1.5
		hwRadioMac OBJECT-TYPE
			SYNTAX MacAddress
			MAX-ACCESS read-only
			STATUS current
			DESCRIPTION
				"Description."
			::= { hwRadioInfoEntry 5 }

		
		-- 1.3.6.1.4.1.2011.6.139.3.32.1.6
		hwRadioAdminStatus OBJECT-TYPE
			SYNTAX INTEGER
				{
				up(1),
				admindown(2)
				}
			MAX-ACCESS read-write
			STATUS current
			DESCRIPTION
				"The admin status only can be 1 or 2.
				1 stands for up, and 2 stands for admindown."
			::= { hwRadioInfoEntry 6 }

		
		-- 1.3.6.1.4.1.2011.6.139.3.32.1.7
		hwRadioOperStatus OBJECT-TYPE
			SYNTAX INTEGER
				{
				up(1),
				down(2),
				admindown(3)
				}
			MAX-ACCESS read-only
			STATUS current
			DESCRIPTION
				"The current status only can be 1, 2 or 3.
				1 stands for up, 2 stands for down, and 3 stands for admindown."
			::= { hwRadioInfoEntry 7 }

		
		-- 1.3.6.1.4.1.2011.6.139.3.32.1.8
		hwRadioLastChange OBJECT-TYPE
			SYNTAX Integer32
			MAX-ACCESS read-only
			STATUS current
			DESCRIPTION
				"Description."
			::= { hwRadioInfoEntry 8 }

		
		-- 1.3.6.1.4.1.2011.6.139.3.32.1.9
		hwRadioInfoUpDownTimes OBJECT-TYPE
			SYNTAX Integer32
			MAX-ACCESS read-only
			STATUS current
			DESCRIPTION
				"Description."
			::= { hwRadioInfoEntry 9 }

		
--  1.3.6.1.4.1.2011.6.139.3.32.1.10
		-- 1.3.6.1.4.1.2011.6.139.3.32.1.10
		hwRadioAutoOffSwitch OBJECT-TYPE
			SYNTAX INTEGER
				{
				disable(1),
				enable(2)
				}
			MAX-ACCESS read-write
			STATUS current
			DESCRIPTION
				"Description."
			::= { hwRadioInfoEntry 10 }

		
--  1.3.6.1.4.1.2011.6.139.3.32.1.11
		-- 1.3.6.1.4.1.2011.6.139.3.32.1.11
		hwRadioAutoOffStartTime OBJECT-TYPE
			SYNTAX OCTET STRING (SIZE (1..11))
			MAX-ACCESS read-write
			STATUS current
			DESCRIPTION
				"Description."
			::= { hwRadioInfoEntry 11 }

		
--  1.3.6.1.4.1.2011.6.139.3.32.1.12
		-- 1.3.6.1.4.1.2011.6.139.3.32.1.12
		hwRadioAutoOffEndTime OBJECT-TYPE
			SYNTAX OCTET STRING (SIZE (1..11))
			MAX-ACCESS read-write
			STATUS current
			DESCRIPTION
				"Description."
			::= { hwRadioInfoEntry 12 }

		
--  1.3.6.1.4.1.2011.6.139.3.33
-- 1.3.6.1.4.1.2011.6.139.3.33
		-- 1.3.6.1.4.1.2011.6.139.3.33
		hwMacRadioInfoTable OBJECT-TYPE
			SYNTAX SEQUENCE OF HwMacRadioInfoEntry
			MAX-ACCESS not-accessible
			STATUS current
			DESCRIPTION
				"Huawei radio wireless port information table."
			::= { hwRadio 33 }

		
--  1.3.6.1.4.1.2011.6.139.3.33.1
		-- 1.3.6.1.4.1.2011.6.139.3.33.1
		hwMacRadioInfoEntry OBJECT-TYPE
			SYNTAX HwMacRadioInfoEntry
			MAX-ACCESS not-accessible
			STATUS current
			DESCRIPTION
				"Description."
			INDEX { hwApMac, hwRadioID }
			::= { hwMacRadioInfoTable 1 }

		
		HwMacRadioInfoEntry ::=
			SEQUENCE { 
				hwMacRadioDecsption
					OCTET STRING,
				hwMacRadioPortType
					OCTET STRING,
				hwMacRadioMaxMtu
					Integer32,
				hwMacRadioBandwidth
					Integer32,
				hwMacRadioMac
					MacAddress,
				hwMacRadioAdminStatus
					INTEGER,
				hwMacRadioOperStatus
					INTEGER,
				hwMacRadioLastChange
					Integer32,
				hwMacRadioInfoUpDownTimes
					Integer32,
				hwMacRadioAutoOffSwitch
					INTEGER,
				hwMacRadioAutoOffStartTime
					OCTET STRING,
				hwMacRadioAutoOffEndTime
					OCTET STRING
			 }

--  1.3.6.1.4.1.2011.6.139.3.33.1.1
		-- 1.3.6.1.4.1.2011.6.139.3.33.1.1
		hwMacRadioDecsption OBJECT-TYPE
			SYNTAX OCTET STRING
			MAX-ACCESS read-only
			STATUS current
			DESCRIPTION
				"Description."
			::= { hwMacRadioInfoEntry 1 }

		
--  1.3.6.1.4.1.2011.6.139.3.33.1.2
		-- 1.3.6.1.4.1.2011.6.139.3.33.1.2
		hwMacRadioPortType OBJECT-TYPE
			SYNTAX OCTET STRING
			MAX-ACCESS read-only
			STATUS current
			DESCRIPTION
				"Description."
			::= { hwMacRadioInfoEntry 2 }

		
--  1.3.6.1.4.1.2011.6.139.3.33.1.3
		-- 1.3.6.1.4.1.2011.6.139.3.33.1.3
		hwMacRadioMaxMtu OBJECT-TYPE
			SYNTAX Integer32
			MAX-ACCESS read-only
			STATUS current
			DESCRIPTION
				"Description."
			::= { hwMacRadioInfoEntry 3 }

		
--  1.3.6.1.4.1.2011.6.139.3.33.1.4
		-- 1.3.6.1.4.1.2011.6.139.3.33.1.4
		hwMacRadioBandwidth OBJECT-TYPE
			SYNTAX Integer32
			MAX-ACCESS read-only
			STATUS current
			DESCRIPTION
				"Description."
			::= { hwMacRadioInfoEntry 4 }

		
--  1.3.6.1.4.1.2011.6.139.3.33.1.5
		-- 1.3.6.1.4.1.2011.6.139.3.33.1.5
		hwMacRadioMac OBJECT-TYPE
			SYNTAX MacAddress
			MAX-ACCESS read-only
			STATUS current
			DESCRIPTION
				"Description."
			::= { hwMacRadioInfoEntry 5 }

		
		-- 1.3.6.1.4.1.2011.6.139.3.33.1.6
		hwMacRadioAdminStatus OBJECT-TYPE
			SYNTAX INTEGER
				{
				up(1),
				admindown(2)
				}
			MAX-ACCESS read-write
			STATUS current
			DESCRIPTION
				"The admin status only can be 0 or 1.
				0 stands for up, and 1 stands for admindown.."
			::= { hwMacRadioInfoEntry 6 }

		
		-- 1.3.6.1.4.1.2011.6.139.3.33.1.7
		hwMacRadioOperStatus OBJECT-TYPE
			SYNTAX INTEGER
				{
				up(1),
				down(2),
				admindown(3)
				}
			MAX-ACCESS read-only
			STATUS current
			DESCRIPTION
				"The current status only can be 0, 1 or 2.
				0 stands for up, 1 stands for down, and 2 stands for admindown.."
			::= { hwMacRadioInfoEntry 7 }

		
		-- 1.3.6.1.4.1.2011.6.139.3.33.1.8
		hwMacRadioLastChange OBJECT-TYPE
			SYNTAX Integer32
			MAX-ACCESS read-only
			STATUS current
			DESCRIPTION
				"Description."
			::= { hwMacRadioInfoEntry 8 }

		
		-- 1.3.6.1.4.1.2011.6.139.3.33.1.9
		hwMacRadioInfoUpDownTimes OBJECT-TYPE
			SYNTAX Integer32
			MAX-ACCESS read-only
			STATUS current
			DESCRIPTION
				"Description."
			::= { hwMacRadioInfoEntry 9 }

		
--  1.3.6.1.4.1.2011.6.139.3.33.1.10
		-- 1.3.6.1.4.1.2011.6.139.3.33.1.10
		hwMacRadioAutoOffSwitch OBJECT-TYPE
			SYNTAX INTEGER
				{
				disable(1),
				enable(2)
				}
			MAX-ACCESS read-write
			STATUS current
			DESCRIPTION
				"Description."
			::= { hwMacRadioInfoEntry 10 }

		
--  1.3.6.1.4.1.2011.6.139.3.33.1.11
		-- 1.3.6.1.4.1.2011.6.139.3.33.1.11
		hwMacRadioAutoOffStartTime OBJECT-TYPE
			SYNTAX OCTET STRING (SIZE (1..11))
			MAX-ACCESS read-write
			STATUS current
			DESCRIPTION
				"Description."
			::= { hwMacRadioInfoEntry 11 }

		
--  1.3.6.1.4.1.2011.6.139.3.33.1.12
		-- 1.3.6.1.4.1.2011.6.139.3.33.1.12
		hwMacRadioAutoOffEndTime OBJECT-TYPE
			SYNTAX OCTET STRING (SIZE (1..11))
			MAX-ACCESS read-write
			STATUS current
			DESCRIPTION
				"Description."
			::= { hwMacRadioInfoEntry 12 }

		
		-- 1.3.6.1.4.1.2011.6.139.3.34
		hwRadioObjects OBJECT IDENTIFIER ::= { hwRadio 34 }

		
		-- 1.3.6.1.4.1.2011.6.139.3.34.1
		hwRadioCalibrateTable OBJECT IDENTIFIER ::= { hwRadioObjects 1 }

		
		-- 1.3.6.1.4.1.2011.6.139.3.34.1.1
		hwRadioCalibrateMode OBJECT-TYPE
			SYNTAX Integer32
			MAX-ACCESS read-write
			STATUS current
			DESCRIPTION
				"Description."
			::= { hwRadioCalibrateTable 1 }

		
		-- 1.3.6.1.4.1.2011.6.139.3.34.1.2
		hwRadioCalibrateTime OBJECT-TYPE
			SYNTAX OCTET STRING
			MAX-ACCESS read-write
			STATUS current
			DESCRIPTION
				"Description."
			::= { hwRadioCalibrateTable 2 }

		
		-- 1.3.6.1.4.1.2011.6.139.3.34.1.3
		hwRadioCalibrateManualStartup OBJECT-TYPE
			SYNTAX Integer32
			MAX-ACCESS read-write
			STATUS current
			DESCRIPTION
				"Description."
			::= { hwRadioCalibrateTable 3 }

		
		-- 1.3.6.1.4.1.2011.6.139.3.34.1.4
		hwRadioCalibrateCycle OBJECT-TYPE
			SYNTAX Integer32
			MAX-ACCESS read-write
			STATUS current
			DESCRIPTION
				"Description."
			::= { hwRadioCalibrateTable 4 }

		
		-- 1.3.6.1.4.1.2011.6.139.3.34.1.5
		hwRadioCalibratePolicy OBJECT-TYPE
			SYNTAX Unsigned32
			MAX-ACCESS read-write
			STATUS current
			DESCRIPTION
				"Description."
			::= { hwRadioCalibrateTable 5 }

		
		-- 1.3.6.1.4.1.2011.6.139.3.34.1.6
		hwRadioCalibratesensitivity OBJECT-TYPE
			SYNTAX Unsigned32
			MAX-ACCESS read-write
			STATUS current
			DESCRIPTION
				"Description."
			::= { hwRadioCalibrateTable 6 }
		
--  1.3.6.1.4.1.2011.6.139.3.34.1.7
		-- 1.3.6.1.4.1.2011.6.139.3.34.1.7
		hwRadioGlobalCalibrateChannel2G OBJECT-TYPE
			SYNTAX OCTET STRING
			MAX-ACCESS read-write
			STATUS current
			DESCRIPTION
				"Description."
			::= { hwRadioCalibrateTable 7 }


		-- 1.3.6.1.4.1.2011.6.139.3.34.1.8
		hwRadioGlobalCalibrateChannel5G OBJECT-TYPE
			SYNTAX OCTET STRING
			MAX-ACCESS read-write
			STATUS current
			DESCRIPTION
				"Description."
			::= { hwRadioCalibrateTable 8 }

		
		-- 1.3.6.1.4.1.2011.6.139.3.34.1.9
		hwRadioGlobalScanChannel2G OBJECT-TYPE
			SYNTAX OCTET STRING
			MAX-ACCESS read-write
			STATUS current
			DESCRIPTION
				"Description."
			::= { hwRadioCalibrateTable 9 }

		
		-- 1.3.6.1.4.1.2011.6.139.3.34.1.10
		hwRadioGlobalScanChannel5G OBJECT-TYPE
			SYNTAX OCTET STRING
			MAX-ACCESS read-write
			STATUS current
			DESCRIPTION
				"Description."
			::= { hwRadioCalibrateTable 10 }


		-- 1.3.6.1.4.1.2011.6.139.3.34.1.11
		hwRadioGlobalCalibrate5gBandWidth OBJECT-TYPE
			SYNTAX INTEGER
				{
				ht20(1),
				ht40(2),
				ht80(3)
				}
			MAX-ACCESS read-write
			STATUS current
			DESCRIPTION
				"Global calibrate 5G band width."
			DEFVAL { 1 }
			::= { hwRadioCalibrateTable 11 }


		-- 1.3.6.1.4.1.2011.6.139.3.34.1.12
		hwRadioCalibrateAutoStartTime OBJECT-TYPE
			SYNTAX OCTET STRING
			MAX-ACCESS read-write
			STATUS current
			DESCRIPTION
				"Auto calibrate start time."
			::= { hwRadioCalibrateTable 12 }

		
		-- 1.3.6.1.4.1.2011.6.139.3.34.2
		hwConnectProfileTable OBJECT-TYPE
			SYNTAX SEQUENCE OF HwConnectProfileEntry
			MAX-ACCESS not-accessible
			STATUS current
			DESCRIPTION
				"Huawei connect profile table.
				This table is used to create connect profile and config the element in this profile.The element 
				include as fllows:
				 - huawei connect profile name.
				 - huawei connect ssid.
				 - huawei connect peer mac.
				 - huawei connect psk.
				 - huawei connect distance kilo.
				 - huawei connect distance mile.
				 - huawei connect profile active.
				 - huawei connect profile rowstatus."
			::= { hwRadioObjects 2 }

		
		-- 1.3.6.1.4.1.2011.6.139.3.34.2.1
		hwConnectProfileEntry OBJECT-TYPE
			SYNTAX HwConnectProfileEntry
			MAX-ACCESS not-accessible
			STATUS current
			DESCRIPTION
				"Description."
			INDEX { hwConnectProfileName }
			::= { hwConnectProfileTable 1 }

		
		HwConnectProfileEntry ::=
			SEQUENCE { 
				hwConnectProfileName
					OCTET STRING,
				hwConnectSsid
					OCTET STRING,
				hwConnectPeerMac
					MacAddress,
				hwConnectPskPassPhase
					OCTET STRING,
				hwConnectProfileActived
					Integer32,
				hwConnectProfileRowStatus
					RowStatus
			 }

		-- 1.3.6.1.4.1.2011.6.139.3.34.2.1.1
		hwConnectProfileName OBJECT-TYPE
			SYNTAX OCTET STRING (SIZE (1..31))
			MAX-ACCESS not-accessible
			STATUS current
			DESCRIPTION
				"An object is uesd to set connect profile name,if access to connect profile must through this name only.
				Generally,it can set 32 connect profiles and the name not samely."
			::= { hwConnectProfileEntry 1 }

		
		-- 1.3.6.1.4.1.2011.6.139.3.34.2.1.2
		hwConnectSsid OBJECT-TYPE
			SYNTAX OCTET STRING (SIZE (1..32))
			MAX-ACCESS read-write
			STATUS current
			DESCRIPTION
				"The string of ssid has no more than 32 character."
			::= { hwConnectProfileEntry 2 }

		
		-- 1.3.6.1.4.1.2011.6.139.3.34.2.1.3
		hwConnectPeerMac OBJECT-TYPE
			SYNTAX MacAddress
			MAX-ACCESS read-write
			STATUS current
			DESCRIPTION
				"Description."
			::= { hwConnectProfileEntry 3 }

		
		-- 1.3.6.1.4.1.2011.6.139.3.34.2.1.4
		hwConnectPskPassPhase OBJECT-TYPE
			SYNTAX OCTET STRING
			MAX-ACCESS read-write
			STATUS current
			DESCRIPTION
				"An object is used to set psk for safe connect. The encrpytion tachniques only sustain wpa2-ccmp.
				The psk maybe 32 to 104 cryptograph character or 8 to 63  colloquial character."
			::= { hwConnectProfileEntry 4 }

		
		-- 1.3.6.1.4.1.2011.6.139.3.34.2.1.5
		hwConnectProfileActived OBJECT-TYPE
			SYNTAX Integer32 (0..1)
			MAX-ACCESS read-write
			STATUS current
			DESCRIPTION
				"An object is used to display and set connect profile's status.
				0 show not connected,1 show connecting. "
			REFERENCE
				"0"
			::= { hwConnectProfileEntry 5 }

		
		-- 1.3.6.1.4.1.2011.6.139.3.34.2.1.6
		hwConnectProfileRowStatus OBJECT-TYPE
			SYNTAX RowStatus
			MAX-ACCESS read-write
			STATUS current
			DESCRIPTION
				"An object is used to create or delete a connect profile.
				
				There are some restrictions of operation of the connect profile.
				  - It needs a connect profile name for the creation of the radio profile.
				  - if hwconnect profile active value is 1,the connect profile can not delete.
				  - if delete a connect profile,but the profile name not exist,it cannot delete. "
			::= { hwConnectProfileEntry 6 }

		
		-- 1.3.6.1.4.1.2011.6.139.3.34.3
		hwRadioBasicSettingTable OBJECT-TYPE
			SYNTAX SEQUENCE OF HwRadioBasicSettingEntry
			MAX-ACCESS not-accessible
			STATUS current
			DESCRIPTION
				"Description."
			::= { hwRadioObjects 3 }

		
		-- 1.3.6.1.4.1.2011.6.139.3.34.3.1
		hwRadioBasicSettingEntry OBJECT-TYPE
			SYNTAX HwRadioBasicSettingEntry
			MAX-ACCESS not-accessible
			STATUS current
			DESCRIPTION
				"Description."
			INDEX { hwApRadioID }
			::= { hwRadioBasicSettingTable 1 }

		
		HwRadioBasicSettingEntry ::=
			SEQUENCE { 
				hwApRadioID
					Integer32,
				hwApRadioTxPower
					Integer32,
				hwApRadioRtsThreshold
					Integer32
			 }

		-- 1.3.6.1.4.1.2011.6.139.3.34.3.1.1
		hwApRadioID OBJECT-TYPE
			SYNTAX Integer32
			MAX-ACCESS not-accessible
			STATUS current
			DESCRIPTION
				"The index of radio parameter."
			::= { hwRadioBasicSettingEntry 1 }

		
		-- 1.3.6.1.4.1.2011.6.139.3.34.3.1.2
		hwApRadioTxPower OBJECT-TYPE
			SYNTAX Integer32 (17..36)
			MAX-ACCESS read-write
			STATUS current
			DESCRIPTION
				"An object is used to set transmittion power for wireless. The range is from 16 to 36.
				if not setting,the txpower is max power which the device hold."
			::= { hwRadioBasicSettingEntry 2 }

		
		-- 1.3.6.1.4.1.2011.6.139.3.34.3.1.3
		hwApRadioRtsThreshold OBJECT-TYPE
			SYNTAX Integer32 (64..2347)
			MAX-ACCESS read-write
			STATUS current
			DESCRIPTION
				" "
			REFERENCE
				"2347 bytes"
			::= { hwRadioBasicSettingEntry 3 }

		
		hwConnectStatusTable OBJECT-TYPE
			SYNTAX SEQUENCE OF HwConnectStatusEntry
			MAX-ACCESS not-accessible
			STATUS current
			DESCRIPTION
				"Description."
			::= { hwRadioObjects 4 }

		
		hwConnectStatusEntry OBJECT-TYPE
			SYNTAX HwConnectStatusEntry
			MAX-ACCESS not-accessible
			STATUS current
			DESCRIPTION
				"Description."
			INDEX { hwConnectStatusPeerMac }
			::= { hwConnectStatusTable 1 }

		
		HwConnectStatusEntry ::=
			SEQUENCE { 
				hwConnectStatusPeerMac
					MacAddress,
				hwConnectStatusSsid
					OCTET STRING,
				hwConnectStatus
					INTEGER,
				hwConnectStatusSNR
					Integer32,
				hwConnectStatusNoiseFloor
					Integer32,
				hwConnectStatusChannel
					Integer32,
				hwConnectStatusActualTxPower
					Integer32,
				hwConnectStatusBeaconInterval
					Integer32,
				hwConnectStatusCurrentRate
					Integer32,
				hwConnectStatusTxBeamforming
					Integer32,
				hwConnectStatusActualCountryCode
					Integer32,
				hwConnectStatusDistance
					Integer32,
				hwConnectStatusCurrentRateKbps
					Integer32,
				hwConnectStatusHtMode
					INTEGER,
				hwConnectStatusGIMode
					INTEGER
			 }

		-- 1.3.6.1.4.1.2011.6.139.3.34.4.1.1
		hwConnectStatusPeerMac OBJECT-TYPE
			SYNTAX MacAddress
			MAX-ACCESS not-accessible
			STATUS current
			DESCRIPTION
				"Description."
			::= { hwConnectStatusEntry 1 }

		
		-- 1.3.6.1.4.1.2011.6.139.3.34.4.1.2
		hwConnectStatusSsid OBJECT-TYPE
			SYNTAX OCTET STRING (SIZE (1..32))
			MAX-ACCESS read-only
			STATUS current
			DESCRIPTION
				"Description."
			::= { hwConnectStatusEntry 2 }

		
		-- 1.3.6.1.4.1.2011.6.139.3.34.4.1.3
		hwConnectStatus OBJECT-TYPE
			SYNTAX INTEGER
				{
				disconnect(1),
				connect(2)
				}
			MAX-ACCESS read-only
			STATUS current
			DESCRIPTION
				"An object is used to display connect status now.
				1 shows connection, 2 shows disconnection."
			::= { hwConnectStatusEntry 3 }

		
		-- 1.3.6.1.4.1.2011.6.139.3.34.4.1.4
		hwConnectStatusSNR OBJECT-TYPE
			SYNTAX Integer32
			MAX-ACCESS read-only
			STATUS current
			DESCRIPTION
				"An object is used to display the snr of current link."
			::= { hwConnectStatusEntry 4 }

		
		-- 1.3.6.1.4.1.2011.6.139.3.34.4.1.5
		hwConnectStatusNoiseFloor OBJECT-TYPE
			SYNTAX Integer32
			MAX-ACCESS read-only
			STATUS current
			DESCRIPTION
				"An object is used to display the noise of current link."
			::= { hwConnectStatusEntry 5 }

		
		-- 1.3.6.1.4.1.2011.6.139.3.34.4.1.6
		hwConnectStatusChannel OBJECT-TYPE
			SYNTAX Integer32
			MAX-ACCESS read-only
			STATUS current
			DESCRIPTION
				"An object is used to display the channel of current link."
			::= { hwConnectStatusEntry 6 }

		
		-- 1.3.6.1.4.1.2011.6.139.3.34.4.1.7
		hwConnectStatusActualTxPower OBJECT-TYPE
			SYNTAX Integer32
			MAX-ACCESS read-only
			STATUS current
			DESCRIPTION
				"An object is used to display the actual tx power of current link."
			::= { hwConnectStatusEntry 7 }

		
		-- 1.3.6.1.4.1.2011.6.139.3.34.4.1.8
		hwConnectStatusBeaconInterval OBJECT-TYPE
			SYNTAX Integer32
			MAX-ACCESS read-only
			STATUS current
			DESCRIPTION
				"An object is used to display the beacon interval of current link."
			::= { hwConnectStatusEntry 8 }

		
		-- 1.3.6.1.4.1.2011.6.139.3.34.4.1.9
		hwConnectStatusCurrentRate OBJECT-TYPE
			SYNTAX Integer32
			MAX-ACCESS read-only
			STATUS current
			DESCRIPTION
				"An object is used to display the rate of current link."
			::= { hwConnectStatusEntry 9 }

		
		-- 1.3.6.1.4.1.2011.6.139.3.34.4.1.10
		hwConnectStatusTxBeamforming OBJECT-TYPE
			SYNTAX Integer32
			MAX-ACCESS read-only
			STATUS current
			DESCRIPTION
				"An object is used to display the tx beam forming of current link."
			::= { hwConnectStatusEntry 10 }

		
		-- 1.3.6.1.4.1.2011.6.139.3.34.4.1.11
		hwConnectStatusActualCountryCode OBJECT-TYPE
			SYNTAX Integer32
			MAX-ACCESS read-only
			STATUS current
			DESCRIPTION
				"An object is used to display the current countrycode of current device."
			::= { hwConnectStatusEntry 11 }

		
		-- 1.3.6.1.4.1.2011.6.139.3.34.4.1.12
		hwConnectStatusDistance OBJECT-TYPE
			SYNTAX Integer32
			MAX-ACCESS read-only
			STATUS current
			DESCRIPTION
				"An object is used to get the distance setting for the connection. 
				The unit is 0.1 km."
			::= { hwConnectStatusEntry 12 }


		-- 1.3.6.1.4.1.2011.6.139.3.34.4.1.13
		hwConnectStatusCurrentRateKbps OBJECT-TYPE
			SYNTAX Integer32
			MAX-ACCESS read-only
			STATUS current
			DESCRIPTION
				"An object is used to display the rate of current link, the unit is Kbps."
			::= { hwConnectStatusEntry 13 }	
				
		-- 1.3.6.1.4.1.2011.6.139.3.34.4.1.14
		hwConnectStatusHtMode OBJECT-TYPE
			SYNTAX INTEGER
				{
				ht20(1),
				ht40(2)
				}
			MAX-ACCESS read-only
			STATUS current
			DESCRIPTION
				"An object is used to display the HT mode of current link."
			::= { hwConnectStatusEntry 14 }

		
		-- 1.3.6.1.4.1.2011.6.139.3.34.4.1.15
		hwConnectStatusGIMode OBJECT-TYPE
			SYNTAX INTEGER
				{
				normal(1),
				short(2)
				}
			MAX-ACCESS read-only
			STATUS current
			DESCRIPTION
				"An object is used to display the GI mode of current link."
			::= { hwConnectStatusEntry 15 }

				
		-- 1.3.6.1.4.1.2011.6.139.3.34.5
		hwConnectStatisticsTable OBJECT-TYPE
			SYNTAX SEQUENCE OF HwConnectStatisticsEntry
			MAX-ACCESS not-accessible
			STATUS current
			DESCRIPTION
				"Description."
			::= { hwRadioObjects 5 }

		
		-- 1.3.6.1.4.1.2011.6.139.3.34.5.1
		hwConnectStatisticsEntry OBJECT-TYPE
			SYNTAX HwConnectStatisticsEntry
			MAX-ACCESS not-accessible
			STATUS current
			DESCRIPTION
				"Description."
			INDEX { hwConnectStatisticsPeerMac }
			::= { hwConnectStatisticsTable 1 }

		
		HwConnectStatisticsEntry ::=
			SEQUENCE { 
				hwConnectStatisticsPeerMac
					MacAddress,
				hwConnectRxOkUcastDataFrames
					Counter64,
				hwConnectRxOkUcastDataBytes
					Counter64,
				hwConnectTxOkUcastDataFrames
					Counter64,
				hwConnectTxOkUcastDataBytes
					Counter64,
				hwConnectRxThroughput
					Unsigned32,
				hwConnectTxThroughput
					Unsigned32,
				hwConnectRxErrFrames
					Counter64,
				hwConnectTxErrUcastDataFrames
					Counter64,
				hwConnectUcastDataFrameTxRetryRatio
					Unsigned32,
				hwConnectOnlineTime
					Unsigned32,
				hwConnectStatisticsReset
					INTEGER
			 }

--  1.3.6.1.4.1.2011.6.139.3.34.4.1.1
		-- 1.3.6.1.4.1.2011.6.139.3.34.5.1.1
		hwConnectStatisticsPeerMac OBJECT-TYPE
			SYNTAX MacAddress
			MAX-ACCESS not-accessible
			STATUS current
			DESCRIPTION
				"Description."
			::= { hwConnectStatisticsEntry 1 }

				
		-- 1.3.6.1.4.1.2011.6.139.3.34.5.1.2
		hwConnectRxOkUcastDataFrames OBJECT-TYPE
			SYNTAX Counter64
			MAX-ACCESS read-only
			STATUS current
			DESCRIPTION
				"An object is used to display the count of correct unicast Rx message."
			::= { hwConnectStatisticsEntry 2 }

		
		-- 1.3.6.1.4.1.2011.6.139.3.34.5.1.3
		hwConnectRxOkUcastDataBytes OBJECT-TYPE
			SYNTAX Counter64
			MAX-ACCESS read-only
			STATUS current
			DESCRIPTION
				"An object is used to display the bytes count of correct unicast Rx message."
			::= { hwConnectStatisticsEntry 3 }

		
		-- 1.3.6.1.4.1.2011.6.139.3.34.5.1.4
		hwConnectTxOkUcastDataFrames OBJECT-TYPE
			SYNTAX Counter64
			MAX-ACCESS read-only
			STATUS current
			DESCRIPTION
				"An object is used to display the count of correct unicast Tx message."
			::= { hwConnectStatisticsEntry 4 }

		
		-- 1.3.6.1.4.1.2011.6.139.3.34.5.1.5
		hwConnectTxOkUcastDataBytes OBJECT-TYPE
			SYNTAX Counter64
			MAX-ACCESS read-only
			STATUS current
			DESCRIPTION
				"An object is used to display the bytes count of correct unicast Tx message."
			::= { hwConnectStatisticsEntry 5 }

		
		-- 1.3.6.1.4.1.2011.6.139.3.34.5.1.6
		hwConnectRxThroughput OBJECT-TYPE
			SYNTAX Unsigned32
			MAX-ACCESS read-only
			STATUS current
			DESCRIPTION
				"An object is used to display the rate of  Rx message.The unit is Mbps."
			::= { hwConnectStatisticsEntry 6 }

		
		-- 1.3.6.1.4.1.2011.6.139.3.34.5.1.7
		hwConnectTxThroughput OBJECT-TYPE
			SYNTAX Unsigned32
			MAX-ACCESS read-only
			STATUS current
			DESCRIPTION
				"An object is used to display the rate of  Tx message.The unit is Mbps."
			::= { hwConnectStatisticsEntry 7 }

		
		-- 1.3.6.1.4.1.2011.6.139.3.34.5.1.8
		hwConnectRxErrFrames OBJECT-TYPE
			SYNTAX Counter64
			MAX-ACCESS read-only
			STATUS current
			DESCRIPTION
				"An object is used to display the count of Rx message which is wrong."
			::= { hwConnectStatisticsEntry 8 }

		
		-- 1.3.6.1.4.1.2011.6.139.3.34.5.1.9
		hwConnectTxErrUcastDataFrames OBJECT-TYPE
			SYNTAX Counter64
			MAX-ACCESS read-only
			STATUS current
			DESCRIPTION
				"An object is used to display the count of Tx message which is wrong."
			::= { hwConnectStatisticsEntry 9 }

		
		-- 1.3.6.1.4.1.2011.6.139.3.34.5.1.10
		hwConnectUcastDataFrameTxRetryRatio OBJECT-TYPE
			SYNTAX Unsigned32
			MAX-ACCESS read-only
			STATUS current
			DESCRIPTION
				"An object is used to display the repeate message rate of unicast Tx message.The range id from 0 to 100.
				"
			::= { hwConnectStatisticsEntry 10 }

		
		-- 1.3.6.1.4.1.2011.6.139.3.34.5.1.11
		hwConnectOnlineTime OBJECT-TYPE
			SYNTAX Unsigned32
			MAX-ACCESS read-only
			STATUS current
			DESCRIPTION
				"An object is used to display the connection time length which connected last time."
			::= { hwConnectStatisticsEntry 11 }

				
		-- 1.3.6.1.4.1.2011.6.139.3.34.5.1.12
		hwConnectStatisticsReset OBJECT-TYPE
			SYNTAX INTEGER
				{
				reset(1),
				unreset(2)
				}
			MAX-ACCESS read-write
			STATUS current
			DESCRIPTION
				"An object is used to reset the statistics datas of current device."
			::= { hwConnectStatisticsEntry 12 }

		
		-- 1.3.6.1.4.1.2011.6.139.3.34.6
		hwConnectRateHistogramTable OBJECT-TYPE
			SYNTAX SEQUENCE OF HwConnectRateHistogramEntry
			MAX-ACCESS not-accessible
			STATUS current
			DESCRIPTION
				"Huawei connect rate histogram table. 
				This table is uses to display connect rate histogram.The content of the table contains:connect rate histogram
				TxRx,connect rate histogram rate and connect rate histogram ucast date frames."
			::= { hwRadioObjects 6 }

		-- 1.3.6.1.4.1.2011.6.139.3.34.6.1
		hwConnectRateHistogramEntry OBJECT-TYPE
			SYNTAX HwConnectRateHistogramEntry
			MAX-ACCESS not-accessible
			STATUS current
			DESCRIPTION
				"Huawei connect rate histogram table entry. 
				The index of the connect rate histogram table is hwConnectRateHistogramTxRx and 
				hwconnectRateHistogramRate."
			INDEX { hwConnectRateStatDirection, hwConnectRateStatRange }
			::= { hwConnectRateHistogramTable 1 }

		
		HwConnectRateHistogramEntry ::=
			SEQUENCE { 
				hwConnectRateStatDirection
					INTEGER,
				hwConnectRateStatRange
					Integer32,
				hwConnectRateStatUcastDataFrames
					Counter64
			 }
		-- 1.3.6.1.4.1.2011.6.139.3.34.6.1.1
		hwConnectRateStatDirection OBJECT-TYPE
			SYNTAX INTEGER
				{
				txRate(1),
				rxRate(2)
				}
			MAX-ACCESS not-accessible
			STATUS current
			DESCRIPTION
				"The first index is connect rate histogram TxRx,the detail ranges as follows:
				- 1 express Received rate histogram of unicast data frames.
				- 2 express Transmit rate histogram of unicast data frames."
			::= { hwConnectRateHistogramEntry 1 }

		
		-- 1.3.6.1.4.1.2011.6.139.3.34.6.1.2
		hwConnectRateStatRange OBJECT-TYPE
			SYNTAX Integer32
			MAX-ACCESS not-accessible
			STATUS current
			DESCRIPTION
				"The second index is connect rate histogram rate.The range as follows:
				- MCS0,MCS1,MCS2,MCS3,MCS4,MCS5,MCS6,MCS7,MCS8,MCS9,MCS10,MCS11,MCS12 show 0 to 12
				- MCS13,MCS14,MCS15,MCS16,MCS17,MCS18,MCS19,MCS20,MCS21,MCS22,MCS23 show 13 to 23
				- 32 shows rate6 from 36M to 48M
				- 33 shows rate4 from 18M to 24M
				- 34 shows rate2 from 9M to 12M
				- 35 shows rate0 less than 6M
				- 36 shows rate7 from 48M to 54M
				- 37 shows rate5 from 24M to 36M
				- 38 shows rate3 from 12M to 18M
				- 39 shows rate1 from 6M to 9M"
			::= { hwConnectRateHistogramEntry 2 }

		
		-- 1.3.6.1.4.1.2011.6.139.3.34.6.1.3
		hwConnectRateStatUcastDataFrames OBJECT-TYPE
			SYNTAX Counter64
			MAX-ACCESS read-only
			STATUS current
			DESCRIPTION
				"An object uses to display connect rate histogram ucast data frames through the connect rate histogram
				TxRx and the connect rate histogram rate.
				"
			::= { hwConnectRateHistogramEntry 3 }

		
		-- 1.3.6.1.4.1.2011.6.139.3.34.7
		hwConnectAMPDUHistogramTable OBJECT-TYPE
			SYNTAX SEQUENCE OF HwConnectAMPDUHistogramEntry
			MAX-ACCESS not-accessible
			STATUS current
			DESCRIPTION
				"Description."
			::= { hwRadioObjects 7 }

		
		-- 1.3.6.1.4.1.2011.6.139.3.34.7.1
		hwConnectAMPDUHistogramEntry OBJECT-TYPE
			SYNTAX HwConnectAMPDUHistogramEntry
			MAX-ACCESS not-accessible
			STATUS current
			DESCRIPTION
				"Description."
			INDEX { hwConnectAMPDUStatDirection, hwConnectAMPDUStatRange }
			::= { hwConnectAMPDUHistogramTable 1 }

		
		HwConnectAMPDUHistogramEntry ::=
			SEQUENCE { 
				hwConnectAMPDUStatDirection
					INTEGER,
				hwConnectAMPDUStatRange
					Integer32,
				hwConnectAMPDUStatUcastDataFrames
					Counter64
			 }

		-- 1.3.6.1.4.1.2011.6.139.3.34.7.1.1
		hwConnectAMPDUStatDirection OBJECT-TYPE
			SYNTAX INTEGER
				{
				txAMPDU(1),
				rxAMPDU(2)
				}
			MAX-ACCESS not-accessible
			STATUS current
			DESCRIPTION
				"The first index is connect AMPDU histogram TxRx,the detail ranges as follows:
				- 1 express Received rate histogram of unicast data frames.
				- 2 express Transmit rate histogram of unicast data frames."
			::= { hwConnectAMPDUHistogramEntry 1 }

		
		-- 1.3.6.1.4.1.2011.6.139.3.34.7.1.2
		hwConnectAMPDUStatRange OBJECT-TYPE
			SYNTAX Integer32
			MAX-ACCESS not-accessible
			STATUS current
			DESCRIPTION
				"The range is from 0 to 64.Different number make up different length of AMPDU.
				For example,32 express the length of AMPDU is 32. "
			::= { hwConnectAMPDUHistogramEntry 2 }

		
		-- 1.3.6.1.4.1.2011.6.139.3.34.7.1.3
		hwConnectAMPDUStatUcastDataFrames OBJECT-TYPE
			SYNTAX Counter64
			MAX-ACCESS read-only
			STATUS current
			DESCRIPTION
				"An object uses to display connect AMPDU ucast data frames through the connect AMPDU stat direction
				 and the connect AMPDU stat range.
				"
			::= { hwConnectAMPDUHistogramEntry 3 }

		
		-- 1.3.6.1.4.1.2011.6.139.3.34.8
		hwConnectLenHistogramTable OBJECT-TYPE
			SYNTAX SEQUENCE OF HwConnectLenHistogramEntry
			MAX-ACCESS not-accessible
			STATUS current
			DESCRIPTION
				"Description."
			::= { hwRadioObjects 8 }

		
		-- 1.3.6.1.4.1.2011.6.139.3.34.8.1
		hwConnectLenHistogramEntry OBJECT-TYPE
			SYNTAX HwConnectLenHistogramEntry
			MAX-ACCESS not-accessible
			STATUS current
			DESCRIPTION
				"Description."
			INDEX { hwConnectDataLenStatDirection, hwConnectDataLenStatLength }
			::= { hwConnectLenHistogramTable 1 }

		
		HwConnectLenHistogramEntry ::=
			SEQUENCE { 
				hwConnectDataLenStatDirection
					INTEGER,
				hwConnectDataLenStatLength
					Integer32,
				hwConnectDataLenStatFrameCounts
					Counter64
			 }

		-- 1.3.6.1.4.1.2011.6.139.3.34.8.1.1
		hwConnectDataLenStatDirection OBJECT-TYPE
			SYNTAX INTEGER
				{
				txLen(1),
				rxLen(2)
				}
			MAX-ACCESS not-accessible
			STATUS current
			DESCRIPTION
				"The first index is connect datalen stat direction,the detail ranges as follows:
				- 1 express Received rate histogram of unicast data frames.
				- 2 express Transmit rate histogram of unicast data frames."
			::= { hwConnectLenHistogramEntry 1 }

		
		-- 1.3.6.1.4.1.2011.6.139.3.34.8.1.2
		hwConnectDataLenStatLength OBJECT-TYPE
			SYNTAX Integer32
			MAX-ACCESS not-accessible
			STATUS current
			DESCRIPTION
				"The second index is connect data length.The range as follows:
				 -0 shows 0 to 255
				 -1 shows 256 to 511
				 -2 shows 512 to 767
				 -3 shows 768 to 1023
				 -4 shows 1024 to 1279
				 -5 shows 1280 to 1535
				 -6 shows 1536 to 1791
				 -7 shows 1792 to 2047"
			::= { hwConnectLenHistogramEntry 2 }

		
		-- 1.3.6.1.4.1.2011.6.139.3.34.8.1.3
		hwConnectDataLenStatFrameCounts OBJECT-TYPE
			SYNTAX Counter64
			MAX-ACCESS read-only
			STATUS current
			DESCRIPTION
				"An object uses to display connect data length stat frame counts through the connect data length dir-
				ection and the connect data length.
				"
			::= { hwConnectLenHistogramEntry 3 }

				
		-- 1.3.6.1.4.1.2011.6.139.3.34.9
		hwConnectMaxSnrTable OBJECT-TYPE
			SYNTAX SEQUENCE OF HwConnectMaxSnrEntry
			MAX-ACCESS not-accessible
			STATUS current
			DESCRIPTION
				"Description."
			::= { hwRadioObjects 9 }

		
		-- 1.3.6.1.4.1.2011.6.139.3.34.9.1
		hwConnectMaxSnrEntry OBJECT-TYPE
			SYNTAX HwConnectMaxSnrEntry
			MAX-ACCESS not-accessible
			STATUS current
			DESCRIPTION
				"Description."
			INDEX { hwConnectMaxSnrPeerMAC }
			::= { hwConnectMaxSnrTable 1 }

		
		HwConnectMaxSnrEntry ::=
			SEQUENCE { 
				hwConnectMaxSnrPeerMAC
					MacAddress,
				hwConnectMaxSnrValue
					Integer32,
				hwConnectMaxSnrNoiseFloor
					Integer32,
				hwConnectMaxSnrSSID
					OCTET STRING,
				hwConnectMaxSnrTime
					DateAndTime
			 }

		-- 1.3.6.1.4.1.2011.6.139.3.34.9.1.1
		hwConnectMaxSnrPeerMAC OBJECT-TYPE
			SYNTAX MacAddress
			MAX-ACCESS not-accessible
			STATUS current
			DESCRIPTION
				"Description."
			::= { hwConnectMaxSnrEntry 1 }

		
		-- 1.3.6.1.4.1.2011.6.139.3.34.9.1.2
		hwConnectMaxSnrValue OBJECT-TYPE
			SYNTAX Integer32
			MAX-ACCESS read-only
			STATUS current
			DESCRIPTION
				"An object is used to display max snr value when connection."
			::= { hwConnectMaxSnrEntry 2 }

		
		-- 1.3.6.1.4.1.2011.6.139.3.34.9.1.3
		hwConnectMaxSnrNoiseFloor OBJECT-TYPE
			SYNTAX Integer32
			MAX-ACCESS read-only
			STATUS current
			DESCRIPTION
				"noise floor"
			::= { hwConnectMaxSnrEntry 3 }

		
		-- 1.3.6.1.4.1.2011.6.139.3.34.9.1.4
		hwConnectMaxSnrSSID OBJECT-TYPE
			SYNTAX OCTET STRING
			MAX-ACCESS read-only
			STATUS current
			DESCRIPTION
				"neighbor ssid"
			::= { hwConnectMaxSnrEntry 4 }

		
		-- 1.3.6.1.4.1.2011.6.139.3.34.9.1.5
		hwConnectMaxSnrTime OBJECT-TYPE
			SYNTAX DateAndTime
			MAX-ACCESS read-only
			STATUS current
			DESCRIPTION
				"last time"
			::= { hwConnectMaxSnrEntry 5 }

		-- 1.3.6.1.4.1.2011.6.139.3.34.10
		hwRadioQueryPowerlevelTable OBJECT-TYPE
			SYNTAX SEQUENCE OF HwRadioQueryPowerlevelEntry
			MAX-ACCESS not-accessible
			STATUS current
			DESCRIPTION
				"Table for query powerlevel of the appointed AP if set channel and bandwidth."
			::= { hwRadioObjects 10 }

		
		-- 1.3.6.1.4.1.2011.6.139.3.34.10.1
		hwRadioQueryPowerlevelEntry OBJECT-TYPE
			SYNTAX HwRadioQueryPowerlevelEntry
			MAX-ACCESS not-accessible
			STATUS current
			DESCRIPTION
				"Entry for query powerlevel table ."
			INDEX { hwApIndex, hwRadioID, hwRadioQueryPowerlevelChannel, hwRadioQueryPowerlevelBandwidth }
			::= { hwRadioQueryPowerlevelTable 1 }

		
		HwRadioQueryPowerlevelEntry ::=
			SEQUENCE { 
				hwRadioQueryPowerlevelChannel
					Integer32,
				hwRadioQueryPowerlevelBandwidth
					Integer32,
				hwRadioQueryPowerlevelMax
					Integer32
			 }

		-- 1.3.6.1.4.1.2011.6.139.3.34.10.1.1
		hwRadioQueryPowerlevelChannel OBJECT-TYPE
			SYNTAX Integer32
			MAX-ACCESS not-accessible
			STATUS current
			DESCRIPTION
				"The channel if it will be set as an index."
			::= { hwRadioQueryPowerlevelEntry 1 }

		
		-- 1.3.6.1.4.1.2011.6.139.3.34.10.1.2
		hwRadioQueryPowerlevelBandwidth OBJECT-TYPE
			SYNTAX Integer32
			MAX-ACCESS not-accessible
			STATUS current
			DESCRIPTION
				"The bandwidth if it will be set as an index."
			::= { hwRadioQueryPowerlevelEntry 2 }

		
		-- 1.3.6.1.4.1.2011.6.139.3.34.10.1.3
		hwRadioQueryPowerlevelMax OBJECT-TYPE
			SYNTAX Integer32
			MAX-ACCESS read-only
			STATUS current
			DESCRIPTION
				"The result ,it shows the number of powerlevel , which begins from zero."
			::= { hwRadioQueryPowerlevelEntry 3 }

		-- 1.3.6.1.4.1.2011.6.139.3.35
		hwRadioConformance OBJECT IDENTIFIER ::= { hwRadio 35 }

		
		-- 1.3.6.1.4.1.2011.6.139.3.35.1
		hwRadioCompliances OBJECT IDENTIFIER ::= { hwRadioConformance 1 }

		
		-- 1.3.6.1.4.1.2011.6.139.3.35.1.1
		hwRadioCompliance MODULE-COMPLIANCE
			STATUS current
			DESCRIPTION 
				"Description."
			MODULE -- this module
				MANDATORY-GROUPS { hwRadioProfileGroup, hwRadioManageGroup, hwRadioCalibrateStatisicsGroup, hwRadioAuthNeighborInfGroup, hwRadioLoadBalanceGroupGroup, 
					hwRadioLoadBalanceGroupMemberGroup, hwRadioUncontrolAPInfGroup, hwRadioPerformanceStatGroup, hwRadioUnauthenticNeighborInfoGroup, hwRadioRegionCalibrateGroup, 
					hwRadioGlobalGroup, hwRadioNotifyGroup, hwRadioNotifyObjectGroup, hwRadioParaStatisticGroup, hwMacRadioManageGroup, 
					hwMacRadioCalibrateStatisicsGroup, hwMacRadioAuthNeighborInfGroup, hwMacRadioLoadBalanceGroupMemberGroup, hwMacRadioPerformanceStatGroup, hwMacRadioUnauthenticNeighborInfoGroup, 
					hwRadioInfoGroup, hwMacRadioInfoGroup, hwRadioCalibrateGroup }
			::= { hwRadioCompliances 1 }

		
		-- 1.3.6.1.4.1.2011.6.139.3.35.2
		hwRadioObjectGroups OBJECT IDENTIFIER ::= { hwRadioConformance 2 }

		
		-- 1.3.6.1.4.1.2011.6.139.3.35.2.1
		hwRadioProfileGroup OBJECT-GROUP
			OBJECTS { hwRadioType, hwRadioRateMode, hwRadioRateValue, hwRadioChannelMode, hwRadioPowerMode, 
				hwRadioCalibrateInterval, hwRadioPERThreshold, hwRadioConfictRateThreshold, hwRadioRTSThreshold, hwRadioFragmentThreshold, 
				hwRadioShortFrameRetryTimes, hwRadioLongFrameRetryTimes, hwRadioSupportShortPreamble, hwRadioDTIMInterval, hwRadioBeaconInterval, 
				hwRadioWMMProfileName, hwRadioProfileRowStatus, hwRadio80211nGuardIntervalMode, hwRadio80211nAMPDUMaxLengthExponent, hwRadioCalibrateEnable, 
				hwRadioInterfDetDevice, hwRadioApComInterfThreshold, hwRadioApAdjInterfThreshold, hwRadioStaInterfThreshold, hwRadioDeviceReportDuration, 
				hwRadioRTSMode, hwRadioWifiLight, hwRadioBeamformingSwitch, hwRadioWidsDevSynchronizationInt, hwRadioChannelSwitchAnnouncement, 
				hwRadioChannelSwitchMode, hwRadioStaAccessSignalStrengthSwitch, hwRadioStaAccessSignalStrengthThreshold, hwRadioBackgroundListenNeighborSwitch, hwRadioBackgroundScanningServiceThreshold, 
				hwRadioBackgroundScanningClientThreshold, hwRadioStaAccessRateLimitSwitch, hwRadioStaAccessRateLimitThreshold, hwRadioSpectrumAnalysisScanPeriod, hwRadioSpectrumAnalysisScanInterval, 
				hwRadioHighDenseSwitch, hwRadioHighDenseMode, hwRadioStaOfflineSignalStrengthSwitch, hwRadioStaOfflineSignalStrengthThreshold, hwRadioStaOfflineRateLimitSwitch, 
				hwRadioStaOfflineRateThreshold, hwRadioDynamicAdjustPowerSwitch, hwRadioLocationReportTime, hwRadioLocationScanInterval, hwRadioLocationScanPeriod, hwRadioAirTimeScheduleSwitch,hwRadioCalibrateScanCycle,
				hwRadioUacPolicyType, hwRadioUacPolicySwitch, hwRadioUacAccessThreshold, hwRadioUacRoamThreshold, hwRadioUacHideSSIDSwitch, 
				hwRadio80211acGuardIntervalMode, hwRadio80211acAMPDUMaxLengthExponent, hwRadio80211bgBasicRateSet, hwRadio80211bgSupportRateSet, hwRadio80211aBasicRateSet, hwRadio80211aSupportRateSet, 
				hwRadio80211nSupportMCS,hwRadio80211acSupportMcsMapMcs,hwRadioMulticastRate2G,hwRadioMulticastRate5G, hwRadioLegacyStationEnable, 
				hwRadioLocationScanChannel2G, hwRadioLocationScanChannel5G, hwRadioAMSDUTxEnable, hwRadioAMSDUTxMaxSubFrames}
			STATUS current
			DESCRIPTION 
				"Description."
			::= { hwRadioObjectGroups 1 }

		
		-- 1.3.6.1.4.1.2011.6.139.3.35.2.2
		hwRadioManageGroup OBJECT-GROUP
			OBJECTS { hwRadioID, hwRadioMngBaseBssID, hwRadioMngRadioProfileName, hwRadioMngState, hwRadioMngChannel, 
				hwRadioMngPowerLevel, hwRadioMngPower, hwRadioAvailableSntennaNumber, hwRadioWorkingChannel, hwRadioWorkingPowerLevel, 
				hwRadioWorkingPower, hwRadioMngChannelBandwidth, hwRadioWorkingChannelBandwidth, hwRadio80211nMCSValue, hwRadioWidsWorkMode, 
				hwRadioMngBinded, hwRadioDeviceDetectEnable, hwRadioMaxTxPwrLvl, hwRadioPwrAttRange, hwRadioPwrAttValue, 
				hwRadioAntennaGain, hwRadioBridgeWhitelistEnable, hwRadioBridgeWhitelistName, hwRadioBridgeStpSwitch, hwRadioBridgeSwitch, 
				hwRadioBridgeMode, hwRadioUndoBridgeWhitelist, hwRadioUserTrafficScheduler, hwRadioCountermeasuresMode, hwRadioFrequency, 
				hwRadioCountermeasuresSwitch, hwRadioSpectrumAnalysisEnable, hwRadioWidsAttackDetEnable, hwRadioMeshWhitelistName, hwRadioUndoMeshWhitelist, 
				hwRadioMeshRole, hwRadioLocationEnable, hwRadioLocationScanChannelEnable, hwRadio80211nMulticastMCSValue,
				hwRadioSpectrogramServerReportEnable, hwRadioRadioMulticastRateValue, hwRadio11acSpatialStream, hwRadio11acMCSValue, hwRadioActiveSwitch }
			STATUS current
			DESCRIPTION 
				"Description."
			::= { hwRadioObjectGroups 2 }

		
		-- 1.3.6.1.4.1.2011.6.139.3.35.2.3
		hwRadioCalibrateStatisicsGroup OBJECT-GROUP
			OBJECTS { hwRadioCalStatisSignalBadCount, hwRadioCalStatisCalibratePowerCount, hwRadioCalStatisCalibrateChannelCount, hwRadioCalibrateStatisicsOperMode }
			STATUS current
			DESCRIPTION 
				"Description."
			::= { hwRadioObjectGroups 3 }

		
		-- 1.3.6.1.4.1.2011.6.139.3.35.2.4
		hwRadioAuthNeighborInfGroup OBJECT-GROUP
			OBJECTS { hwAuthenticRadioNeighborAPID, hwAuthenticRadioNeighborChannel, hwAuthenticRadioNeighborFrontAttenu, hwAuthenticRadioNeighborBackAttenu, hwAuthenticRadioNeighborSSID
				 }
			STATUS current
			DESCRIPTION 
				"Description."
			::= { hwRadioObjectGroups 4 }

		
		-- 1.3.6.1.4.1.2011.6.139.3.35.2.5
		hwRadioLoadBalanceGroupGroup OBJECT-GROUP
			OBJECTS { hwLBGroupMode, hwLBGapThreshold, hwLBAssociateThreshold, hwLBGroupStatus, hwLBGroupRowStatus
				 }
			STATUS current
			DESCRIPTION 
				"Description."
			::= { hwRadioObjectGroups 5 }

		
		-- 1.3.6.1.4.1.2011.6.139.3.35.2.6
		hwRadioLoadBalanceGroupMemberGroup OBJECT-GROUP
			OBJECTS { hwLBMemberRadioChannel, hwLBMemberRadioPowerLevel, hwLBMemberRadioPower, hwLBMemberRadioSeesionNum, hwLBMemberRadioTraffic, 
				hwLBMemberRowStatus }
			STATUS current
			DESCRIPTION 
				"Description."
			::= { hwRadioObjectGroups 6 }

		
		-- 1.3.6.1.4.1.2011.6.139.3.35.2.7
		hwRadioUncontrolAPInfGroup OBJECT-GROUP
			OBJECTS { hwUncontrolAPBSSID, hwAuthAPIndex, hwUncontrolAPChannel, hwUncontrolAPRSSI, hwUncontrolAPSSID
				 }
			STATUS current
			DESCRIPTION 
				"Description."
			::= { hwRadioObjectGroups 7 }

		
		-- 1.3.6.1.4.1.2011.6.139.3.35.2.8
		hwRadioPerformanceStatGroup OBJECT-GROUP
			OBJECTS { hwRadioRcvFrames, hwRadioRcvBytes, hwRadioSendFrames, hwRadioSendBytes, hwRadioSendRtsSuccess, 
				hwRadioSendUnicast, hwRadioSendBroadcast, hwRadioSendFailFrames, hwRadioRcvErrFrames, hwRadioRcvPhyErrFrames, 
				hwRadioRcvCrcErrFrames, hwRadioRcvMicErrFrames, hwRadioRcvKeyDecryptErrFrames, hwRadioRetryFrames, hwRadioPER, 
				hwRadioChUtilizationRate, hwRadioPerformanceStatOperMode, hwRadioPEROfLastPeriod, hwRadioRcvSignalStrength, hwRadioDownMacErrFrames, 
				hwRadioRcvPower, hwRadioRcvUnicastFrames, hwRadioRcvMngFrames, hwRadioRcvCtrlFrames, hwRadioRcvDataFrames, 
				hwRadioSendMngFrames, hwRadioSendCtrlFrames, hwRadioSendDataFrames, hwRadioStaMaxSignalStrength, hwRadioStaMinSignalStrength, 
				hwRadioStaAvgSignalStrength, hwRadioSendRate, hwRadioRecvRate, hwRadioDropRate, hwRadioAirPortDhcpFrames, 
				hwRadioAirPortEapolFrames, hwRadioAirPortPsPollFrames, hwRadioAssocRequestFrames, hwRadioAssocResponseFrames, hwRadioReassocRequestFrames, 
				hwRadioReassocResponseFrames, hwRadioDisassocFrames, hwRadioDisauthFrames,
				hwRadioRcvFrames64Bits, hwRadioRcvBytes64Bits, hwRadioSendFrames64Bits, hwRadioSendBytes64Bits, hwRadioSendRtsSuccess64Bits,
				hwRadioSendUnicast64Bits, hwRadioSendBroadcast64Bits, hwRadioSendFailFrames64Bits, hwRadioRcvErrFrames64Bits, hwRadioRcvPhyErrFrames64Bits,
				hwRadioRcvCrcErrFrames64Bits, hwRadioRcvMicErrFrames64Bits, hwRadioRcvKeyDecryptErrFrames64Bits, hwRadioRetryFrames64Bits, hwRadioDownMacErrFrames64Bits,
				hwRadioNoise, hwRadioActualBandwidth, hwRadioFrames, hwRadioSendDropFrames64Bits, hwRadioRcvDropFrames64Bits, hwRadioChannelFreeRate, hwRadioTxRate, 
				hwRadioRxRate, hwRadioChInterferenceRate }
			STATUS current
			DESCRIPTION 
				"Description."
			::= { hwRadioObjectGroups 8 }

		
		-- 1.3.6.1.4.1.2011.6.139.3.35.2.9
		hwRadioUnauthenticNeighborInfoGroup OBJECT-GROUP
			OBJECTS { hwUnauthenticRadioNeighborBSSID, hwUnauthenticRadioNeighborRSSI, hwunauthenticRadioNeighborChannel, hwUnauthenticRadioNeighborSSID }
			STATUS current
			DESCRIPTION 
				"Description."
			::= { hwRadioObjectGroups 9 }

		
		-- 1.3.6.1.4.1.2011.6.139.3.35.2.10
		hwRadioRegionCalibrateGroup OBJECT-GROUP
			OBJECTS { hwRegionCalibrateStartupMode, hwRegionCalibrateAutoTime, hwRegionCalibrateListenMode, hwRegionCalibrateStatus }
			STATUS current
			DESCRIPTION 
				"Description."
			::= { hwRadioObjectGroups 10 }

		
		-- 1.3.6.1.4.1.2011.6.139.3.35.2.11
		hwRadioGlobalGroup OBJECT-GROUP
			OBJECTS { hwBatchRadioProfileStartNumber, hwBatchRadioProfileNumber, hwBatchRadioProfileReturnNumber, hwBatchRadioProfileName, hwBatchLoadBalanceGroupStartNumber, 
				hwBatchLoadBalanceGroupNumber, hwBatchLoadBalanceGroupReturnNumber, hwBatchLoadBalanceGroupName, hwBatchUncontrolAPStartNumber, hwBatchUncontrolAPNumber, 
				hwBatchUncontrolAPReturnNumber, hwBatchUncontrolAPBssid, hwBatchUncontrolAPAuthNeighborIndex }
			STATUS current
			DESCRIPTION 
				"Description."
			::= { hwRadioObjectGroups 11 }

		
		-- 1.3.6.1.4.1.2011.6.139.3.35.2.12
		hwRadioNotifyGroup NOTIFICATION-GROUP
			NOTIFICATIONS { hwRadioChannelChangedNotify, hwRadioSignalEnvDeteriorationNotify, hwRadioSignalEnvResumeNotify, hwApMonitorModeChangedNotify, hwAPCoInterfDetectedNotify, 
				hwAPCoInterfClearNotify, hwNerborInterfDetectedNotify, hwNeiborInterfClearNotify, hwStaInterfDetectedNotify, hwStaInterfClearNotify, 
				hwOtherDeviceInterfDetectedNotify, hwOtherDeviceInterfClearNotify, hwRadioDownNotify, hwRadioDownRecovNotify, hwWIDSDetectRogueNotify, 
				hwRadioNotSupportChannelNotify, hwRadioNotSupportPowerLevelNotify, hwRadioAntennaGainIsUnlawfulNotify, hwRadioPowerChangedNotify,
				hwApAccessUserNumExceedThresholdNotify, hwApAccessUserNumExceedThresholdRecovNotify, hwApRoamUserNumExceedThresholdNotify, hwApRoamUserNumExceedThresholdRecovNotify,
				hwApAccessChannelUtilExceedThresholdNotify, hwApAccessChannelUtilExceedThresholdRecovNotify, hwApRoamChannelUtilExceedThresholdNotify, hwApRoamChannelUtilExceedThresholdRecovNotify,
				hwRadioUploadRemoteCaptureFileNotify}
			STATUS current
			DESCRIPTION 
				"Description."
			::= { hwRadioObjectGroups 12 }

		
		-- 1.3.6.1.4.1.2011.6.139.3.35.2.13
		hwRadioNotifyObjectGroup OBJECT-GROUP
			OBJECTS { hwRadioActualChannel, hwRadioConflictRate, hwApMonitorMode, hwApPreMonitorMode, hwApChannel, 
				hwApInterfBssid, hwInterfStaMac, hwRadioDownCause, hwInterfApChannel, hwInterfRSSI, 
				hwWIDSTrapInfoAPID, hwWIDSTrapInfoRadioId, hwWIDSTrapInfoAPMAC, hwWIDSTrapInfoRogueMAC, hwWIDSTrapInfoRogueSSId, 
				hwWIDSTrapInfoRogueType, hwWIDSTrapInfoRogueRSSI, hwWIDSTrapInfoRogueChanID, hwRadioActualChannelBandwidth, hwRadioActualPowerLevel, 
				hwRadioActualAntennaGain, hwRadioLegitimateAntennaGain, hwRadioChannelChangedReason, hwRadioChannelChangedReasonStr, hwRadioDownCauseStr, 
				hwRadioUacUserNum, hwRadioPreActualChannel, hwRadioPowerChangedReasonStr }
			STATUS current
			DESCRIPTION 
				"Description."
			::= { hwRadioObjectGroups 13 }

		
		-- 1.3.6.1.4.1.2011.6.139.3.35.2.14
		hwRadioParaStatisticGroup OBJECT-GROUP
			OBJECTS { hwRadioStaAveSignalStrength }
			STATUS current
			DESCRIPTION 
				"Description."
			::= { hwRadioObjectGroups 14 }

		
		-- 1.3.6.1.4.1.2011.6.139.3.35.2.15
		hwMacRadioManageGroup OBJECT-GROUP
			OBJECTS { hwMacRadioMngBaseBssID, hwMacRadioMngRadioProfileName, hwMacRadioMngState, hwMacRadioMngChannel, hwMacRadioMngPowerLevel, 
				hwMacRadioMngPower, hwMacRadioAvailableSntennaNumber, hwMacRadioWorkingChannel, hwMacRadioWorkingPowerLevel, hwMacRadioWorkingPower, 
				hwMacRadioMngChannelBandwidth, hwMacRadioWorkingChannelBandwidth, hwMacRadio80211nMCSValue, hwMacRadioWidsWorkMode, hwMacRadioMngBinded, 
				hwMacRadioMaxTxPwrLvl, hwMacRadioPwrAttRange, hwMacRadioPwrAttValue, hwMacRadioAntennaGain, hwMacRadioBridgeWhitelistEnable, 
				hwMacRadioBridgeWhitelistName, hwMacRadioBridgeStpSwitch, hwMacRadioBridgeSwitch, hwMacRadioBridgeMode, hwMacRadioUndoBridgeWhitelist, 
				hwMacRadioUserTrafficScheduler, hwMacRadioCountermeasuresMode, hwMacRadioFrequency, hwMacRadioCountermeasuresSwitch, hwMacRadioSpectrumAnalysisEnable, 
				hwMACRadioWidsAttackDetEnable, hwMacRadioMeshWhitelistName, hwMacUndoMeshWhitelist, hwMacRadioMeshRole, hwMacRadioLocationEnable, 
				hwMacRadioLocationScanChannelEnable, hwMacRadio80211nMulticastMCSValue,
				hwMacRadioSpectrogramServerReportEnable, hwMacRadioMulticastRateValue, hwMacRadio11acSpatialStream, hwMacRadio11acMCSValue, hwMacRadioActiveSwitch}
			STATUS current
			DESCRIPTION 
				"Description."
			::= { hwRadioObjectGroups 15 }

		
		-- 1.3.6.1.4.1.2011.6.139.3.35.2.16
		hwMacRadioCalibrateStatisicsGroup OBJECT-GROUP
			OBJECTS { hwMacRadioCalStatisSignalBadCount, hwMacRadioCalStatisCalibratePowerCount, hwMacRadioCalStatisCalibrateChannelCount, hwMacRadioCalibrateStatisicsOperMode }
			STATUS current
			DESCRIPTION 
				"Description."
			::= { hwRadioObjectGroups 16 }

		
		-- 1.3.6.1.4.1.2011.6.139.3.35.2.17
		hwMacRadioAuthNeighborInfGroup OBJECT-GROUP
			OBJECTS { hwMacAuthenticRadioNeighborChannel, hwMacAuthenticRadioNeighborFrontAttenu, hwMacAuthenticRadioNeighborBackAttenu, hwMacAuthenticRadioNeighborAPMac, hwMacAuthenticRadioNeighborSSID, 
				hwMacAuthenticRadioNeighborAPID }
			STATUS current
			DESCRIPTION 
				"Description."
			::= { hwRadioObjectGroups 17 }

		
		-- 1.3.6.1.4.1.2011.6.139.3.35.2.18
		hwMacRadioLoadBalanceGroupMemberGroup OBJECT-GROUP
			OBJECTS { hwMacLBMemberRadioChannel, hwMacLBMemberRadioPowerLevel, hwMacLBMemberRadioPower, hwMacLBMemberRadioSeesionNum, hwMacLBMemberRadioTraffic, 
				hwMacLBMemberRowStatus }
			STATUS current
			DESCRIPTION 
				"Description."
			::= { hwRadioObjectGroups 18 }

		
		-- 1.3.6.1.4.1.2011.6.139.3.35.2.19
		hwMacRadioPerformanceStatGroup OBJECT-GROUP
			OBJECTS { hwMacRadioRcvFrames, hwMacRadioRcvBytes, hwMacRadioSendFrames, hwMacRadioSendBytes, hwMacRadioSendRtsSuccess, 
				hwMacRadioSendUnicast, hwMacRadioSendBroadcast, hwMacRadioSendFailFrames, hwMacRadioRcvErrFrames, hwMacRadioRcvPhyErrFrames, 
				hwMacRadioRcvCrcErrFrames, hwMacRadioRcvMicErrFrames, hwMacRadioRcvKeyDecryptErrFrames, hwMacRadioRetryFrames, hwMacRadioPER, 
				hwMacRadioChUtilizationRate, hwMacRadioPerformanceStatOperMode, hwMacRadioPEROfLastPeriod, hwMacRadioRcvSignalStrength, hwMacRadioDownMacErrFrames, 
				hwMacRadioRcvPower, hwMacRadioRcvUnicastFrames, hwMacRadioRcvMngFrames, hwMacRadioRcvCtrlFrames, hwMacRadioRcvDataFrames, 
				hwMacRadioSendMngFrames, hwMacRadioSendCtrlFrames, hwMacRadioSendDataFrames, hwMacRadioStaMaxSignalStrength, hwMacRadioStaMinSignalStrength, 
				hwMacRadioStaAvgSignalStrength, hwMacRadioSendRate, hwMacRadioRecvRate, hwMacRadioDropRate, hwMacRadioAirPortDhcpFrames, 
				hwMacRadioAirPortEapolFrames, hwMacRadioAirPortPsPollFrames, hwMacRadioAssocRequestFrames, hwMacRadioAssocResponseFrames, hwMacRadioReassocRequestFrames, 
				hwMacRadioReassocResponseFrames, hwMacRadioDisassocFrames, hwMacRadioDisauthFrames,
				hwMacRadioRcvFrames64Bits, hwMacRadioRcvBytes64Bits, hwMacRadioSendFrames64Bits, hwMacRadioSendBytes64Bits, hwMacRadioSendRtsSuccess64Bits,
				hwMacRadioSendUnicast64Bits, hwMacRadioSendBroadcast64Bits, hwMacRadioSendFailFrames64Bits, hwMacRadioRcvErrFrames64Bits, hwMacRadioRcvPhyErrFrames64Bits,
				hwMacRadioRcvCrcErrFrames64Bits, hwMacRadioRcvMicErrFrames64Bits, hwMacRadioRcvKeyDecryptErrFrames64Bits, hwMacRadioRetryFrames64Bits, hwMacRadioDownMacErrFrames64Bits,
				hwMacRadioNoise, hwMacRadioActualBandwidth, hwMacRadioFrames, hwMacRadioSendDropFrames64Bits, hwMacRadioRcvDropFrames64Bits, hwMacRadioChannelFreeRate, hwMacRadioTxRate, 
				hwMacRadioRxRate, hwMacRadioChInterferenceRate }
			STATUS current
			DESCRIPTION 
				"Description."
			::= { hwRadioObjectGroups 19 }

		
		-- 1.3.6.1.4.1.2011.6.139.3.35.2.20
		hwMacRadioUnauthenticNeighborInfoGroup OBJECT-GROUP
			OBJECTS { hwMacUnauthenticRadioNeighborBSSID, hwMacUnauthenticRadioNeighborRSSI, hwMacunauthenticRadioNeighborChannel, hwMacUnauthenticRadioNeighborSSID }
			STATUS current
			DESCRIPTION 
				"Description."
			::= { hwRadioObjectGroups 20 }

		
		-- 1.3.6.1.4.1.2011.6.139.3.35.2.21
		hwRadioInfoGroup OBJECT-GROUP
			OBJECTS { hwRadioDecsption, hwRadioPortType, hwRadioMaxMtu, hwRadioBandwidth, hwRadioMac, 
				hwRadioAdminStatus, hwRadioOperStatus, hwRadioLastChange, hwRadioInfoUpDownTimes, hwRadioAutoOffSwitch, 
				hwRadioAutoOffStartTime, hwRadioAutoOffEndTime }
			STATUS current
			DESCRIPTION 
				"Description."
			::= { hwRadioObjectGroups 21 }

		
		-- 1.3.6.1.4.1.2011.6.139.3.35.2.22
		hwMacRadioInfoGroup OBJECT-GROUP
			OBJECTS { hwMacRadioDecsption, hwMacRadioPortType, hwMacRadioMaxMtu, hwMacRadioBandwidth, hwMacRadioMac, 
				hwMacRadioAdminStatus, hwMacRadioOperStatus, hwMacRadioLastChange, hwMacRadioInfoUpDownTimes, hwMacRadioAutoOffSwitch, 
				hwMacRadioAutoOffStartTime, hwMacRadioAutoOffEndTime }
			STATUS current
			DESCRIPTION 
				"Description."
			::= { hwRadioObjectGroups 22 }
			
		-- 1.3.6.1.4.1.2011.6.139.3.35.2.23
		hwRadioCalibrateGroup OBJECT-GROUP
			OBJECTS { hwRadioCalibrateMode, hwRadioCalibrateTime, hwRadioCalibrateManualStartup, hwRadioCalibrateCycle, hwRadioCalibratePolicy, 
				hwRadioCalibratesensitivity, hwRadioGlobalCalibrateChannel5G, hwRadioGlobalScanChannel5G, hwRadioGlobalCalibrateChannel2G, hwRadioGlobalScanChannel2G,
				hwRadioGlobalCalibrate5gBandWidth, hwRadioCalibrateAutoStartTime
				 }
			STATUS current
			DESCRIPTION 
				"Description."
			::= { hwRadioObjectGroups 23 }
		
		-- 1.3.6.1.4.1.2011.6.139.3.35.2.24
		hwConnectStatusGroup OBJECT-GROUP
			OBJECTS { hwConnectStatusPeerMac, hwConnectStatusSsid, hwConnectStatus, hwConnectStatusSNR, hwConnectStatusNoiseFloor, 
				hwConnectStatusChannel, hwConnectStatusActualTxPower, hwConnectStatusBeaconInterval, hwConnectStatusCurrentRate, hwConnectStatusTxBeamforming, 
				hwConnectStatusActualCountryCode, hwConnectStatusDistance }
			STATUS current
			DESCRIPTION 
				"Description."
			::= { hwRadioObjectGroups 24 }
		
		-- 1.3.6.1.4.1.2011.6.139.3.35.2.25
		hwConnectStatisticsGruop OBJECT-GROUP
			OBJECTS { hwConnectStatisticsPeerMac, hwConnectRxOkUcastDataFrames, hwConnectRxOkUcastDataBytes, hwConnectTxOkUcastDataFrames, hwConnectTxOkUcastDataBytes, 
				hwConnectRxThroughput, hwConnectTxThroughput, hwConnectRxErrFrames, hwConnectTxErrUcastDataFrames, hwConnectUcastDataFrameTxRetryRatio, 
				hwConnectOnlineTime, hwConnectStatisticsReset }
			STATUS current
			DESCRIPTION 
				"Description."
			::= { hwRadioObjectGroups 25 }

		
		-- 1.3.6.1.4.1.2011.6.139.3.35.2.26
		hwConnectRateHistogramGruop OBJECT-GROUP
			OBJECTS { hwConnectRateStatDirection, hwConnectRateStatRange, hwConnectRateStatUcastDataFrames }
			STATUS current
			DESCRIPTION 
				"Description."
			::= { hwRadioObjectGroups 26 }

		
		-- 1.3.6.1.4.1.2011.6.139.3.35.2.27
		hwConnectAMPDUHistogramGruop OBJECT-GROUP
			OBJECTS { hwConnectAMPDUStatDirection, hwConnectAMPDUStatRange, hwConnectAMPDUStatUcastDataFrames }
			STATUS current
			DESCRIPTION 
				"Description."
			::= { hwRadioObjectGroups 27 }

		
		-- 1.3.6.1.4.1.2011.6.139.3.35.2.28
		hwConnectLenHistogramGruop OBJECT-GROUP
			OBJECTS { hwConnectDataLenStatDirection, hwConnectDataLenStatLength, hwConnectDataLenStatFrameCounts }
			STATUS current
			DESCRIPTION 
				"Description."
			::= { hwRadioObjectGroups 28 }

		
		-- 1.3.6.1.4.1.2011.6.139.3.35.2.29
		hwConnectMaxSnrGruop OBJECT-GROUP
			OBJECTS { hwConnectMaxSnrPeerMAC, hwConnectMaxSnrValue, hwConnectMaxSnrNoiseFloor, hwConnectMaxSnrSSID, hwConnectMaxSnrTime }
			STATUS current
			DESCRIPTION 
				"Description."
			::= { hwRadioObjectGroups 29 }

		
	
	END

--
-- HUAWEI-WLAN-RADIO-MIB.mib
--
