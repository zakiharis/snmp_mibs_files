-- =================================================================
-- Copyright (C) 2007 by  HUAWEI TECHNOLOGIES. All rights reserved
-- 
-- Description: The HUAWEI-TUNNEL-MIB provides information about 
--        Tunnel configuration
--              
-- Reference:
-- Version:     V2.05
-- History:
-- V1.0 2009-06-19, publish
-- =================================================================
HUAWEI-TUNNEL-MIB DEFINITIONS ::= BEGIN

    IMPORTS
        hwDatacomm
            FROM HUAWEI-MIB
        ifIndex
            FROM IF-MIB
        OBJECT-GROUP, MODULE-COMPLIANCE, NOTIFICATION-GROUP
            FROM SNMPv2-CONF
        OBJECT-TYPE, MODULE-IDENTITY, Unsigned32, Integer32, Counter64, NOTIFICATION-TYPE
            FROM SNMPv2-SMI
        RowStatus, DisplayString, TruthValue 
            FROM SNMPv2-TC 
         Ipv6Address                             
            FROM IPV6-TC
        ipv6IfIndex
            FROM IPV6-MIB           
        EnabledStatus                                   
            FROM P-BRIDGE-MIB
        InetAddressType, InetAddress        
            FROM INET-ADDRESS-MIB;


    hwTunnelMib MODULE-IDENTITY
        LAST-UPDATED "201410240000Z"
        ORGANIZATION "Huawei Technologies Co.,Ltd."
        CONTACT-INFO
            "Huawei Industrial Base
              Bantian, Longgang
               Shenzhen 518129
               People's Republic of China
               Website: http://www.huawei.com
               Email: support@huawei.com
             "
        DESCRIPTION
            "V2.05 Update hwHybridDynBwPunish and hwHybridDynBwResume, modify their description."
        REVISION "201410240000Z"  
        DESCRIPTION
            "The MIB module for entities implementing the Tunnel protocol configuration."
        REVISION "201407260000Z"        
        DESCRIPTION
                "This object indicates the hybrid-access traps, such as tunnel create fail, tunnel switch, dynamic bandwidth adjust."              
        REVISION "201312180000Z"        
        DESCRIPTION
                "This object modify 'prior' to 'priority'." 
        REVISION "201311130000Z"        
        DESCRIPTION
                "This object indicates the hybrid-access tunnel timeout traps." 
        REVISION "201310140000Z"        
        DESCRIPTION
                "This object indicates the hybrid-access tunnel statistics table about the global configurations and traps."                          
        ::= { hwDatacomm 201 } 
        
    hwTunnelMibObjects OBJECT IDENTIFIER ::= { hwTunnelMib 1 }


    -- ==============================    
    -- the IPv6 tunnel configure table
    -- ==============================    
             
    hwTunnelCfgTable OBJECT-TYPE
        SYNTAX     SEQUENCE OF HwTunnelCfgEntry
        MAX-ACCESS not-accessible
        STATUS     current
        DESCRIPTION
            "MIB table for the tunnel configuration information."  
        ::= { hwTunnelMibObjects 1 }
       
    hwTunnelCfgEntry OBJECT-TYPE
        SYNTAX     HwTunnelCfgEntry
        MAX-ACCESS not-accessible
        STATUS     current
        DESCRIPTION
            "Describes tunnel interface configuration information."
        INDEX   { ipv6IfIndex }
        ::= { hwTunnelCfgTable 1 }     
                
    HwTunnelCfgEntry ::= SEQUENCE {
        hwTunnelProtocol          INTEGER,
        hwTunnelSourceType        INTEGER,
        hwTunnelSrcIfName         DisplayString,
        hwTunnelAddrType          InetAddressType,
        hwTunnelSourceAddr        InetAddress,
        hwTunnelDestinationAddr   InetAddress,
        hwTunnelCfgUndoFlag       INTEGER
    }                  
              
    hwTunnelProtocol OBJECT-TYPE
        SYNTAX    INTEGER {
            gre(1),               
            mplsTe(2),            
            ipv6Ipv4(3),          
            ipv6Ipv4Auto(4),      
            ipv6Ipv46to4(5),      
            ipv6Ipv4Isatap(6),    
            ipv4Ipv6(7),          
            none(8)               
            }  
        MAX-ACCESS read-write
        STATUS     current
        DESCRIPTION
            "This object specifies the Tunnel protocol type."
        ::= { hwTunnelCfgEntry 1 }     
        
    hwTunnelSourceType OBJECT-TYPE
           SYNTAX       INTEGER {
               interfaceName(1),  
               sourceAddress(2),  
               unknown (3)               
            }  
        MAX-ACCESS read-write
        STATUS     current
        DESCRIPTION
            "This object specifies the Tunnel source type."

        ::= { hwTunnelCfgEntry 2 }     

    hwTunnelSrcIfName OBJECT-TYPE
        SYNTAX     DisplayString
        MAX-ACCESS read-write
        STATUS     current
        DESCRIPTION
            "This object specifies the tunnel source interface name."
        ::= { hwTunnelCfgEntry 3 }        

    hwTunnelAddrType OBJECT-TYPE
        SYNTAX     InetAddressType
        MAX-ACCESS read-write
        STATUS     current
        DESCRIPTION
            "This object specifies the address type for Tunnel source and 
            destination address."
        ::= { hwTunnelCfgEntry 4 }        

    hwTunnelSourceAddr OBJECT-TYPE
        SYNTAX     InetAddress
        MAX-ACCESS read-write
        STATUS     current
        DESCRIPTION
            "This object specifies source address of the tunnel interface."
        ::= { hwTunnelCfgEntry 5 }        
                     
    hwTunnelDestinationAddr OBJECT-TYPE
        SYNTAX     InetAddress
        MAX-ACCESS read-write
        STATUS     current
        DESCRIPTION
            "This object specifies destination address of the tunnel interface."
        ::= { hwTunnelCfgEntry 6 } 

   hwTunnelCfgUndoFlag OBJECT-TYPE
        SYNTAX INTEGER {
            undoTunnelProtocol(1),
            undoTunnelSource(2),
            undoTunnelDestination(3),
            invalid(4)
            }
        MAX-ACCESS read-write
        STATUS current
        DESCRIPTION
            "This object specifies undo operation for specified hwTunnelCfgTable parameter."
        ::= { hwTunnelCfgEntry 7 } 


    -- ==============================    
    -- the IPv6 tunnel 4Over6 parameter configure table
    -- ==============================    
             
    hwIpv6Tunnel4Over6CfgTable OBJECT-TYPE
        SYNTAX     SEQUENCE OF HwIpv6Tunnel4Over6CfgEntry
        MAX-ACCESS not-accessible
        STATUS     current
        DESCRIPTION
            "MIB table for 4Over6 tunnel configuration information."
        ::= { hwTunnelMibObjects 2 }
       
    hwIpv6Tunnel4Over6CfgEntry OBJECT-TYPE
        SYNTAX     HwIpv6Tunnel4Over6CfgEntry
        MAX-ACCESS not-accessible
        STATUS     current
        DESCRIPTION
            "Describes IPv6 tunnel 4Over6 parameters."
        INDEX   { ipv6IfIndex }
        ::= { hwIpv6Tunnel4Over6CfgTable 1 } 
                
    HwIpv6Tunnel4Over6CfgEntry ::= SEQUENCE {
        hwIpv6TunnelEncapLimit           Integer32, 
        hwIpv6TunnelEncapLimitDisable    TruthValue,
        hwIpv6TunnelFlowLabel            Integer32, 
        hwIpv6TunnelHopLimit             Integer32, 
        hwIpv6TunnelTrafficClass         Integer32, 
        hwIpv6TunnelTrafficOriginal      TruthValue,
        hwIPv6Tunnel4Over6CfgUndoFlag    INTEGER    
        }                  
              
    hwIpv6TunnelEncapLimit OBJECT-TYPE
        SYNTAX     Integer32(0..255)
        MAX-ACCESS read-write
        STATUS     current
        DESCRIPTION
            "This object specifies Tunnel ipv4-ipv6 encapsulation limit."    
    DEFVAL       { 4 }            
    
        ::= { hwIpv6Tunnel4Over6CfgEntry 1 }     

  hwIpv6TunnelEncapLimitDisable   OBJECT-TYPE
        SYNTAX     TruthValue
        MAX-ACCESS read-only
        STATUS     current
        DESCRIPTION
            "This object specifies Tunnel encapsulation is disabled or not.
            Default value is false."           
        ::= { hwIpv6Tunnel4Over6CfgEntry 2 }  
        
    hwIpv6TunnelFlowLabel OBJECT-TYPE
        SYNTAX     Integer32(0..1048575)
        MAX-ACCESS read-write
        STATUS     current
        DESCRIPTION
            "This object specifies Tunnel ipv4-ipv6 flow label." 
    DEFVAL       { 0 }            
        ::= { hwIpv6Tunnel4Over6CfgEntry 3 }                 
  
    hwIpv6TunnelHopLimit OBJECT-TYPE
        SYNTAX     Integer32(1..255)
        MAX-ACCESS read-write
        STATUS     current
        DESCRIPTION
            "This object specifies Tunnel ipv4-ipv6 hop limit."
    DEFVAL       { 64 }            
        ::= { hwIpv6Tunnel4Over6CfgEntry 4 }   
                            
    hwIpv6TunnelTrafficClass OBJECT-TYPE
        SYNTAX     Integer32(0..255)
        MAX-ACCESS read-write
        STATUS     current
        DESCRIPTION
            "This object specifies Tunnel ipv4-ipv6 traffic-class." 
    DEFVAL       { 0 }             
        ::= { hwIpv6Tunnel4Over6CfgEntry 5 }    
        
    hwIpv6TunnelTrafficOriginal OBJECT-TYPE
        SYNTAX     TruthValue
        MAX-ACCESS read-write
        STATUS     current
        DESCRIPTION
            "Specifies Tunnel ipv4-ipv6 traffic-class original is enabled or not."
    DEFVAL       { false }            
        ::= { hwIpv6Tunnel4Over6CfgEntry 6 }  

   hwIPv6Tunnel4Over6CfgUndoFlag OBJECT-TYPE
        SYNTAX INTEGER {
            undoTunnelEncapLimit(1),
            undoTunnelFlowLabel(2),
            undoTunnelHopLimit(3),
            undoTunnelTrafficClass(4),
            invalid(5)
            }
        MAX-ACCESS read-write
        STATUS current
        DESCRIPTION
         "This object specifies undo operation for specified hwIpv6Tunnel4Over6CfgTable parameter."            
        ::= { hwIpv6Tunnel4Over6CfgEntry 7 } 
        
    hwTunnelGlobalConfigObject OBJECT IDENTIFIER ::= { hwTunnelMibObjects 3 }
         
    hwTunnelCreateFailCheckPeriod  OBJECT-TYPE
        SYNTAX  Integer32 (1..1440)
        MAX-ACCESS read-write
        STATUS current
        DESCRIPTION 
        "This value of this object identifies the interval used to check tunnel failures."
        ::= { hwTunnelGlobalConfigObject  1 }        

    hwTunnelCreateFailThreshold  OBJECT-TYPE
        SYNTAX  Integer32 (1..102400)
        MAX-ACCESS read-write
        STATUS current
        DESCRIPTION 
        "This value of this object identifies the threshold of tunnel failures."
        ::= { hwTunnelGlobalConfigObject  2 }    
        
    hwTunnelKeepaliveTimeoutPeriod  OBJECT-TYPE
        SYNTAX  Integer32 (1..1440)
        MAX-ACCESS read-write
        STATUS current
        DESCRIPTION 
        "This value of this object identifies the interval used to check tunnel keepalive timeouts."
        ::= { hwTunnelGlobalConfigObject  3 }        

    hwTunnelKeepaliveTimeoutThreshold  OBJECT-TYPE
        SYNTAX  Integer32 (1..102400)
        MAX-ACCESS read-write
        STATUS current
        DESCRIPTION 
        "This value of this object identifies the threshold of tunnel keepalive timeouts."
        ::= { hwTunnelGlobalConfigObject  4 }             
          
    -- hwHaapTunnelStatTable   
    
    hwHybridAccessTunnelGlobalStatTable OBJECT-TYPE
        SYNTAX     SEQUENCE OF HwHybridAccessTunnelGlobalStatEntry
        MAX-ACCESS not-accessible
        STATUS     current
        DESCRIPTION
            "This object indicates the MIB table for hybrid access tunnel statistics information."
        ::= { hwTunnelMibObjects 4 }
       
    hwHybridAccessTunnelGlobalStatEntry OBJECT-TYPE
        SYNTAX     HwHybridAccessTunnelGlobalStatEntry
        MAX-ACCESS not-accessible
        STATUS     current
        DESCRIPTION
            "This object indicates the hybrid access tunnel statistics parameters."
        INDEX   { hwTunnelType }
        ::= { hwHybridAccessTunnelGlobalStatTable 1 } 
                
    HwHybridAccessTunnelGlobalStatEntry ::= SEQUENCE {
        hwTunnelType           INTEGER, 
        hwTunnelCreateSuccessCnt    Counter64,
        hwTunnelRequestPktRcvCnt            Counter64, 
        hwTunnelAuthenSuccessCnt             Counter64, 
        hwTunnelAuthorSuccessCnt         Counter64, 
        hwTunnelAuthenAttemptCnt      Counter64,
        hwTunnelAuthorAttemptCnt    Counter64,
        hwTunnelTimeOutCnt      Counter64,
        hwTunnelAuthUnknownCnt      Counter64,
        hwTunnelAuthNotAllowedCnt      Counter64,
        hwTunnelAuthFailOthersCnt      Counter64,
        hwTunnelCreateFailCnt      Counter64,
        hwTunnelInDataFlow      Counter64,
        hwTunnelOutDataFlow      Counter64
        }            

    hwTunnelType  OBJECT-TYPE
        SYNTAX INTEGER {
            overflow(1),
            priority(2)
            }
        MAX-ACCESS not-accessible
        STATUS current
        DESCRIPTION "This object indicates the tunnel type."
        ::= { hwHybridAccessTunnelGlobalStatEntry 1 } 
            
    hwTunnelCreateSuccessCnt  OBJECT-TYPE
        SYNTAX  Counter64
        MAX-ACCESS read-only
        STATUS current
        DESCRIPTION "The value of this object identifies the total number of GRE tunnels set up on each device."
        ::= { hwHybridAccessTunnelGlobalStatEntry 2 }      

    hwTunnelRequestPktRcvCnt  OBJECT-TYPE
        SYNTAX  Counter64
        MAX-ACCESS read-only
        STATUS current
        DESCRIPTION "The value of this object identifies the total number of requests to create GRE tunnels on each device."
        ::= { hwHybridAccessTunnelGlobalStatEntry 3 }      

    hwTunnelAuthenSuccessCnt  OBJECT-TYPE
        SYNTAX  Counter64
        MAX-ACCESS read-only
        STATUS current
        DESCRIPTION "The value of this object identifies the number of authentication successes of GRE Tunnels."
        ::= { hwHybridAccessTunnelGlobalStatEntry 4 }                          

    hwTunnelAuthorSuccessCnt  OBJECT-TYPE
        SYNTAX  Counter64
        MAX-ACCESS read-only
        STATUS current
        DESCRIPTION "The value of this object identifies the number of authorization successes of GRE Tunnels."
        ::= { hwHybridAccessTunnelGlobalStatEntry 5 } 
        
    hwTunnelAuthenAttemptCnt  OBJECT-TYPE
        SYNTAX  Counter64
        MAX-ACCESS read-only
        STATUS current
        DESCRIPTION "The value of this object identifies the number of authentication attempts of GRE Tunnels."
        ::= { hwHybridAccessTunnelGlobalStatEntry 6 } 
        
    hwTunnelAuthorAttemptCnt  OBJECT-TYPE
        SYNTAX  Counter64
        MAX-ACCESS read-only
        STATUS current
        DESCRIPTION "The value of this object identifies the number of of authorization attempts of GRE Tunnels."
        ::= { hwHybridAccessTunnelGlobalStatEntry 7 }         
        
    hwTunnelTimeOutCnt  OBJECT-TYPE
        SYNTAX  Counter64
        MAX-ACCESS read-only
        STATUS current
        DESCRIPTION "The value of this object identifies the number of of tunnels that have timed out."
        ::= { hwHybridAccessTunnelGlobalStatEntry 8 }                     
        
    hwTunnelAuthUnknownCnt  OBJECT-TYPE
        SYNTAX  Counter64
        MAX-ACCESS read-only
        STATUS current
        DESCRIPTION "The value of this object identifies the number of authentication/authorization requests rejected because of Unknown Customer"
        ::= { hwHybridAccessTunnelGlobalStatEntry 9 }     
                
    hwTunnelAuthNotAllowedCnt  OBJECT-TYPE
        SYNTAX  Counter64
        MAX-ACCESS read-only
        STATUS current
        DESCRIPTION "The value of this object identifies the number of authentication/authorization requests rejected because of Service not allowed"
        ::= { hwHybridAccessTunnelGlobalStatEntry 10 }     
        
    hwTunnelAuthFailOthersCnt  OBJECT-TYPE
        SYNTAX  Counter64
        MAX-ACCESS read-only
        STATUS current
        DESCRIPTION "The value of this object identifies the number of authentication/authorization requests rejected because of Others reason."
        ::= { hwHybridAccessTunnelGlobalStatEntry 11 }          
        
    hwTunnelCreateFailCnt  OBJECT-TYPE
        SYNTAX  Counter64
        MAX-ACCESS read-only
        STATUS current
        DESCRIPTION "The value of this object identifies the total number of GRE tunnel creation failures on each device."
        ::= { hwHybridAccessTunnelGlobalStatEntry 12 }   
        
    hwTunnelInDataFlow  OBJECT-TYPE
        SYNTAX  Counter64
        MAX-ACCESS read-only
        STATUS current
        DESCRIPTION "This object indicates the uplink data volume using the tunnel connection."
        ::= { hwHybridAccessTunnelGlobalStatEntry 13 }      
        
    hwTunnelOutDataFlow  OBJECT-TYPE
        SYNTAX  Counter64
        MAX-ACCESS read-only
        STATUS current
        DESCRIPTION "This object indicates the downlink data volume using the tunnel connection."
        ::= { hwHybridAccessTunnelGlobalStatEntry 14 }                    
        
    hwTunnelTrapObjects OBJECT IDENTIFIER ::= { hwTunnelMibObjects 5 }
               
    hwHybridRttThreshold  OBJECT-TYPE
                SYNTAX  Integer32
                MAX-ACCESS accessible-for-notify
                STATUS current
                DESCRIPTION "The value of this object identifies the hybrid-access tunnel rtt check threshold."
                ::= { hwTunnelTrapObjects  1 }
        
    hwHybridRttCheckTimes  OBJECT-TYPE
               SYNTAX Integer32
               MAX-ACCESS accessible-for-notify
               STATUS current
               DESCRIPTION "The value of this object identifies the hybrid-access tunnel rtt check times."
               ::= { hwTunnelTrapObjects  2 }
               
    hwHybridCreateFailValue  OBJECT-TYPE
               SYNTAX Integer32
               MAX-ACCESS accessible-for-notify
               STATUS current
               DESCRIPTION "The value of this object identifies the hybrid-access tunnel create fail error value."
               ::= { hwTunnelTrapObjects  3 }     
               
    hwHybridTunnelType  OBJECT-TYPE
               SYNTAX Integer32
               MAX-ACCESS accessible-for-notify
               STATUS current
               DESCRIPTION "The value of this object identifies the hybrid-access tunnel type."
               ::= { hwTunnelTrapObjects  4 }                            
               
    hwHybridDynDLBwAdjustValue  OBJECT-TYPE
               SYNTAX Integer32
               MAX-ACCESS accessible-for-notify
               STATUS current
               DESCRIPTION "The value of this object identifies the hybrid-access tunnel down-link bandwith adjust value."
               ::= { hwTunnelTrapObjects  5 }
               
    hwHybridDynULBwAdjustValue  OBJECT-TYPE
               SYNTAX Integer32
               MAX-ACCESS accessible-for-notify
               STATUS current
               DESCRIPTION "The value of this object identifies the hybrid-access tunnel up-link bandwith adjust value."
               ::= { hwTunnelTrapObjects  6 }               

    -- ==============================    
    -- hwTunnelMibConformance
    -- ============================== 
                   
    hwTunnelMibConformance OBJECT IDENTIFIER ::= { hwTunnelMib 2 }
    
    hwTunnelCompliances  OBJECT IDENTIFIER ::= { hwTunnelMibConformance 1 }
    hwTunnelCompliance  MODULE-COMPLIANCE
        STATUS  current
        DESCRIPTION
            "The compliance statement for systems supporting 
             the HUAWEI-TUNNEL-MIB."
        MODULE -- this module
        MANDATORY-GROUPS {
            hwTunnelGroup
            }
        ::= { hwTunnelCompliances 1 }
    
    hwTunnelGroups OBJECT IDENTIFIER ::= { hwTunnelMibConformance 2 }
    hwTunnelGroup OBJECT-GROUP
        OBJECTS { 
        hwTunnelProtocol,
        hwTunnelSourceType,
        hwTunnelSrcIfName,
        hwTunnelAddrType,
        hwTunnelSourceAddr,
        hwTunnelDestinationAddr,
        hwTunnelCfgUndoFlag,  
        hwIpv6TunnelEncapLimit,     
        hwIpv6TunnelEncapLimitDisable,
        hwIpv6TunnelFlowLabel,
        hwIpv6TunnelHopLimit,
        hwIpv6TunnelTrafficClass,
        hwIpv6TunnelTrafficOriginal,
        hwIPv6Tunnel4Over6CfgUndoFlag,
        hwTunnelCreateFailCheckPeriod,
        hwTunnelCreateFailThreshold,
        hwTunnelKeepaliveTimeoutPeriod,
        hwTunnelKeepaliveTimeoutThreshold,
        hwTunnelType,
        hwTunnelCreateSuccessCnt,
        hwTunnelRequestPktRcvCnt,
        hwTunnelAuthenSuccessCnt,
        hwTunnelAuthorSuccessCnt,
        hwTunnelAuthenAttemptCnt,
        hwTunnelAuthorAttemptCnt,
        hwTunnelTimeOutCnt,
        hwTunnelAuthUnknownCnt,
        hwTunnelAuthNotAllowedCnt,
        hwTunnelAuthFailOthersCnt,
        hwTunnelCreateFailCnt,
        hwTunnelInDataFlow,
        hwTunnelOutDataFlow,
        hwHybridRttThreshold,
        hwHybridRttCheckTimes,
        hwHybridCreateFailValue,
        hwHybridTunnelType,
        hwHybridDynDLBwAdjustValue,
        hwHybridDynULBwAdjustValue
        }

        STATUS current
        DESCRIPTION 
            "The Tunnel table member."
        ::= { hwTunnelGroups 1 }       

        hwTunnelNotificationGroup NOTIFICATION-GROUP
            NOTIFICATIONS {
            hwTunnelCreateFailOverThreshold, 
            hwOverflowTunnelTimeoutOverThreshold,
            hwPriorTunnelTimeoutOverThreshold,
            hwHybridTunnelCreateFail,
            hwHybridSwitch2PriorTunnel,
            hwHybridSwitch2OverflowTunnel,
            hwHybridDynBwPunish,
            hwHybridDynBwResume
            }
            STATUS current
            DESCRIPTION
                "Tunnel trap group."
            ::= { hwTunnelGroups 2 }
            
    -- hwTunnelTraps
        
    hwTunnelNotifications OBJECT IDENTIFIER ::= { hwTunnelMib 3 }

    hwTunnelCreateFailOverThreshold  NOTIFICATION-TYPE
            OBJECTS { hwTunnelCreateFailCheckPeriod, hwTunnelCreateFailThreshold, hwTunnelCreateFailCnt, hwTunnelCreateFailCnt }
            STATUS current
            DESCRIPTION 
               "This object indicates that an alarm is generated if the number of tunnel failures exceeds the threshold during a period."
            ::= { hwTunnelNotifications 1 }
            
    hwOverflowTunnelTimeoutOverThreshold  NOTIFICATION-TYPE
            OBJECTS { hwTunnelKeepaliveTimeoutPeriod, hwTunnelKeepaliveTimeoutThreshold, hwTunnelTimeOutCnt }
            STATUS current
            DESCRIPTION 
               "This object indicates that an alarm is generated if the number of overflow tunnel timeouts of hello packets exceeds the threshold during a period."
            ::= { hwTunnelNotifications 2 }  
            
    hwPriorTunnelTimeoutOverThreshold  NOTIFICATION-TYPE
            OBJECTS { hwTunnelKeepaliveTimeoutPeriod, hwTunnelKeepaliveTimeoutThreshold, hwTunnelTimeOutCnt }
            STATUS current
            DESCRIPTION 
               "This object indicates that an alarm is generated if the number of priority tunnel timeouts of hello packets exceeds the threshold during a period."
            ::= { hwTunnelNotifications 3 }                         
                
    hwHybridTunnelCreateFail  NOTIFICATION-TYPE
            OBJECTS { ifIndex, hwHybridTunnelType, hwHybridCreateFailValue }
            STATUS current
            DESCRIPTION 
               "This object indicates that the overflow or priority tunnel fails to be created."
            ::= { hwTunnelNotifications 4 }      
            
    hwHybridSwitch2PriorTunnel  NOTIFICATION-TYPE
            OBJECTS { ifIndex, hwHybridRttThreshold, hwHybridRttCheckTimes }
            STATUS current
            DESCRIPTION 
               "This object indicates that the delay of the overflow tunnel exceeds the threshold and traffic is switched to the priority tunnel."
            ::= { hwTunnelNotifications 5 }
            
    hwHybridSwitch2OverflowTunnel  NOTIFICATION-TYPE
            OBJECTS { ifIndex, hwHybridRttThreshold, hwHybridRttCheckTimes }
            STATUS current
            DESCRIPTION 
               "This object indicates that that the delay of the overflow tunnel falls below the threshold and can be used to forward traffic again."
            ::= { hwTunnelNotifications 6 }
            
    hwHybridDynBwPunish  NOTIFICATION-TYPE
            OBJECTS { ifIndex, hwHybridDynDLBwAdjustValue, hwHybridDynULBwAdjustValue }
            STATUS current
            DESCRIPTION 
               "This object indicates that the bandwidth of the priority tunnel needs to be reduced."
            ::= { hwTunnelNotifications 7 }     
            
    hwHybridDynBwResume  NOTIFICATION-TYPE
            OBJECTS { ifIndex, hwHybridDynDLBwAdjustValue, hwHybridDynULBwAdjustValue }
            STATUS current
            DESCRIPTION 
               "This object indicates that the bandwidth of the priority tunnel needs to be increased."
            ::= { hwTunnelNotifications 8 }                           
                            
END
