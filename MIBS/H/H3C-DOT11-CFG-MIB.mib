-- =============================================================================
-- Copyright (c) 2004-2012 Hangzhou H3C Tech. Co., Ltd. All rights reserved.
--
-- Description:
--   The file defines a MIB to provide WLAN configuration information.
-- Reference:
-- Version: V2.8
-- History:
--   V1.0 2006-05-10 Initial version, created by shiyang (Richard)
--   V1.1 2007-02-01 modified by xingjichen(Daniel)
--        Added h3cDot11RadioIntfConfigTable,h3cDot11RadioIntfBindTable,
--        h3cDot11StaKeepALiveTimerIntvl,h3cDot11StaIdleTimerIntvl,
--        h3cDot11BroadcastProbeReply.
--   V1.2 2007-04-27 modified by shiyang(Richard)
--        Replace h3cDot11UnicastCipherKeyIndex, h3cDot11UnicastCipherKey,
--        h3cDot11BroadcastCipherKeyIndex and h3cDot11BroadcastCipherKey
--        with h3cDot11CipherKeyIndex, h3cDot11CipherKey as per CLI change.
--        Delete h3cDot11MaxTxLifetime as per CLI change.
--        Add h3cDot11GlobalCountryCode,h3cDot11APScanMode.
--        h3cDot11ACCtrlTunnelSecSupport and h3cDot11ACDataTunnelSecSupport.
--        Move h3cDot11StaKeepALiveTimerIntvl,h3cDot11StaIdleTimerIntvl
--        and so on to h3cDot11GlobeConfigGroup.
--        Split h3cDot11ServicePolicyTable into h3cDot11ServicePolicyTable
--        and h3cDot11ServicePolicyExtTable.
--        For h3cDot11SecurityCiphers node,update its description for case of
--        value equals to zero.
--   V1.3 2007-06-19 modified by Vikas K
--        Add new table of h3cDot11DataRateConfigTable for AP Configuration
--        Group.
--        Add new node of h3cDot11APName for h3cDot11APTemplateTable.
--        Modify the h3cDot11APScanMode from read-only to read-write.
--        Add undo functionality to node h3cDot11WlanInfBindingID and
--        h3cDot11Description.
--        Add h3cDot11StatisInterv to the h3cDot11APTemplateTable.
--   V1.4 2007-10-9 modified by Jagan K
--        Add new table h3cDot11WlanBssIfTable for WLAN BSS interface
--        configuration.
--        Add new table h3cDot11WlanEssIfTable for WLAN ESS interface
--        configuration.
--        Add new table h3cDot11WlanEthernetIfTable for WLAN Ethernet interface
--        configuration.
--   V1.5 2007-12-21 modified by wanghao (Kumar)
--        Add h3cDot11ACAutoAPSupport, h3cDot11AutoAPName,
--        h3cDot11PersistentName to h3cDot11GlobeConfigGroup
--        Add h3cDot11ClientMaxCount to h3cDot11ServicePolicyTable
--        Add h3cDot11APBroadcastProbeReply, h3cDot11StaIdleTimerInterv,
--        h3cDot11StaKeepAliveTimerInterv, h3cDot11APCir, h3cDot11APCbs
--        to h3cDot11APTemplateTable.
--   V1.6 2008-02-25 modified by wanghao (Kumar)
--        Add h3cDot11RdoClientMaxCount to h3cDot11RadioPolicyTable.
--   V1.7 2008-04-01 modified by wangbin
--        Add h3cDot11PortSecurityTable to h3cDot11InterfaceConfigGroup.
--        Add h3cDot11PortSecurityMode, h3cDot11SecurityUserLoginTxKeyType,
--        h3cDot11SecurityPskKeyMode, h3cDot11SecurityPskKeyString
--        to h3cDot11PortSecurityTable.
--   V1.8 2008-08-01 modified by ChangHuifeng
--        Add h3cDot11ACBackupGroup and
--        h3cDot11RadioElementConfigGroup.
--        Add h3cDot11WlanMeshIfTable to h3cDot11InterfaceConfigGroup.
--        Add h3cDot11APPriorityLevel and h3cDot11APElementID to
--        h3cDot11APTemplateTable.
--        Add h3cDot11CfgRdElementID to h3cDot11RadioToConfigTable.
--        Add h3cDot11APDevDetectEnable to h3cDot11APTemplateEntry.
--        Obsolete h3cDot11StatisInterv
--        Change default value of h3cDot11APScanMode to passive.
--        Change units of h3cDot11BeaconInterval and
--        h3cDot11RadioCfgBeaconIntvl to TU.
--        Remove default value of h3cDot11SSIDEncryptionMode.
--        Change MAC-ACCESS of objects in h3cDot11RadioToConfigTable
--        from read-create to read-write.
--        Change name of h3cDot11IWlanEssRowStatus to h3cDot11WlanEssRowStatus.
--        Change description of h3cDot11PortSecurityTable.
--   V1.9 2008-11-07 modified by Wang Lu and Li Yugang
--        Add h3cDot11IntfTrapThreshold to h3cDot11GlobeConfigGroup
--        Add h3cDot11SPInCirMode, h3cDot11SPInCirValue, h3cDot11SPOutCirMode,
--        h3cDot11SPOutCirValue to h3cDot11ServicePolicyTable
--        Add h3cDot11CfgWorkMode to h3cDot11RadioToConfigTable
--        Add h3cDot11RadioCfgWorkMode to h3cDot11RadioIntfConfigTable.
--        Add new traps h3cDot11CfgCipherChange and h3cDot11CfgPSKChange.
--        Add h3cDot11MonitorInterval, h3cDot11SampleInterval,
--        h3cDot11ChnlSwitChkInterval, h3cDot11APUserUplimit,
--        h3cDot11APL2IsolateEnable to h3cDot11GlobeConfigGroup.
--        Add h3cDot11RadioCfgOnly11gEnable to h3cDot11RadioIntfConfigTable.
--        Add h3cDot11RadioWDSTable to h3cDot11RadioElementConfigGroup.
--   V2.0 2009-03-20 modified by caizibin
--        Add value ext(6) to h3cDot11PortSecurityMode
--   V2.1 2009-05-07 modified by Li Yugang, Wang Shaojie, Jin Yi
--        Add h3cDot11APBSSIDSupportNum, h3cDot11APLastUpdateStatTime,
--        h3cDot11APDoSProtectEnable, h3cDot11MaxAPPerIf to
--        h3cDot11GlobeConfigGroup.
--        Add h3cDot11WlanInfPVID to h3cDot11ServicePolicyTable.
--        Add h3cDot11CipherKeyType to h3cDot11ServicePolicyExtTable.
--        Add h3cDot11CfgPwrAttValue to h3cDot11RadioToConfigTable.
--        Add new table h3cDot11APSysInfoSetTable to h3cDot11APConfigGroup.
--        Add h3cDot11SSIDWepIDConflictTrap to h3cDot11CfgNotifications.
--        Add new table h3cDot11CfgTrapVarObjects to h3cDot11CfgNotifyGroup.
--   V2.2 2009-07-29 modified by Heziqi
--        Add new node h3cDot11ServiceSetVlanId for h3cDot11APServiceSetTable.
--        Add h3cDot11UplinkTrackId to h3cDot11GlobeConfigGroup.
--        Add h3cDot11APLimitTable.
--        Change description of h3cDot11StaKeepALiveTimerIntvl.
--        Add new node h3cDot11RadioTxArithmetic for H3cDot11RadioToConfigTable.
--   V2.3 2009-07-29 modified by Jinyi
--        Add new table h3cDot11APIfSetTable
--   V2.4 2009-12-01 modified by Wang Shaojie
--        Add new node h3cDot11APGetIPMethod for h3cDot11APTemplateTable.
--        Add new group h3cDot11CfgTrapConfigGroup.
--        Add new table h3cDot11CfgSwitchTrapTable to h3cDot11CfgTrapConfigGroup.
--        Add new node h3cDot11BeaconIntervalMs to h3cDot11RadioPolicyTable.
--        Add new node h3cDot11SPInCirStaticValue, h3cDot11SPOutCirStaticValue
--        to h3cDot11ServicePolicyTable.
--        Modify description of h3cDot11SecurityCiphers.
--        Add new node h3cDot11StatisIntervMode to h3cDot11APTemplateTable.
--        Modify SYNTAX of h3cDot11APWorkMode.
--        Modify STATUS of h3cDot11StatisInterv.
--        Add new node h3cDot11SmartRateSet to h3cDot11DataRateConfigTable.
--        2010-02-22 modified by Wang Chunsheng
--        Add new node h3cDot11CfgChannelLockStat, h3cDot11CfgPowerLockStat,
--        h3cDot11CfgLBRdGroupId, h3cDot11CfgRRMSDRdGroupId to h3cDot11RadioToConfigTable.
--        2010-03-15 modified by Wang Lu
--        Add h3cDot11RtCollectSwitch, h3cDot11RglCollectIntvl, and
--        h3cDot11RtCollectIntvl to h3cDot11GlobeConfigGroup
--        Add h3cDot11SPIsolate to h3cDot11ServicePolicyTable
--        Add h3cDot11APServiceVlanTable, h3cDot11RadioConfigTable,
--        h3cDot11RadioPolicyExtTable and h3cDot11RadioSSIDCfgTable
--        Remove h3cDot11CfgTrapConfigGroup
--        Add h3cDot11SrvPortSecurityTable
--        2010-06-01 Modified by Wang Shaojie, Yin Junjie
--        Add h3cDot11RCApPowerLevel, h3cDot11RCDynamicChlState,
--        h3cDot11RCDynamicPowerState to h3cDot11RadioConfigTable.
--        Add h3cDot11APSerialIDTable
--        Add h3cDot11APSTVlanTable
--        2010-07-08 Modified the index of h3cDot11APSysInfoSetTable by jinyi
--        2010-08-05 Modified by Yin Junjie
--        Add new table h3cDot11SrvPolicyExtendTable
--        Add h3cDot11SPEnable to h3cDot11SrvPolicyExtendTable
--        2010-09-02 Modified by Yin Junjie
--        Add new node h3cDot11AdjIntfTrapThreshold
--        to h3cDot11GlobeConfigGroup
--        Add h3cDot11RCRadioStatus to h3cDot11RadioConfigTable
--   V2.5 2010-09-25 Modified by Wu Xiaopeng
--        Remove Size list of h3cDot11APName.
--   V2.6 2011-05-23 Modified by Cui Kai
--        Add new node h3cDot11WAPIAuthServerIP to h3cDot11ServicePolicyTable
--        2011-07-08 Modified by Niu Jian
--        Change type of h3cDot11CfgSTNASPortID to OCTET STRING
--   V2.7 2011-07-13 Modified by Yu Bo
--        Add new node h3cDot11RCRadioRate to h3cDot11RadioConfigTable
--        Add new node h3cDot11RCPwrAdjustStepLength to h3cDot11RadioConfigTable
--        2011-08-08 Modified by Xiao Min
--        Add new table h3cDot11nRadioCfg2Table
--        2011-08-10 Modified by limingjin
--        Add h3cDot11RadioCfgType2 to h3cDot11RadioIntfConfigTable
--        Add h3cDot11RCRadioType2 to h3cDot11RadioConfigTable
--        Add h3cDot11CfgRadioType2 to h3cDot11RadioToConfigTable
--   V2.8 2011-09-28 Modified by zhanghu
--        Add h3cDot11ApTrapEnabled to h3cDot11APTemplateTable
--        Add h3cDot11AllAPMonitorMode to h3cDot11APTemplateTable
--        Add h3cDot11SIDAPTemplateName, h3cDot11SIDModelAlias, h3cDot11SIDAPDescription, h3cDot11SIDRowStatus,
--        h3cDot11SIDAPName, h3cDot11SIDStatisInterv, h3cDot11SIDAPBroadcastProbeReply,
--        h3cDot11SIDAPStaIdleTimerInterv, h3cDot11SIDStaKeepAliveTimerInterv,
--        h3cDot11SIDAPCir, h3cDot11SIDAPCbs, h3cDot11SIDAPPriorityLevel,
--        h3cDot11SIDAPElementID, h3cDot11SIDAPDevDetectEnable, h3cDot11SIDAPStatisIntervMode
--        to h3cDot11APSerialIDTable
--        2011-08-28 Modified by Wang Lu
--        Add h3cDot11CfgSaEnable, h3cDot11CfgSaBand, h3cDot11CfgIDSEnable,
--        h3cDot11CfgSaCltRtFFTData to h3cDot11RadioToConfigTable
-- =============================================================================
H3C-DOT11-CFG-MIB DEFINITIONS ::= BEGIN

IMPORTS
        TruthValue,
        RowStatus,
        DisplayString,
        DateAndTime,
        MacAddress,
        IpAddress
    FROM SNMPv2-TC
        ifIndex
    FROM RFC1213-MIB
        MODULE-IDENTITY,
        NOTIFICATION-TYPE,
        OBJECT-TYPE,
        Integer32,
        Unsigned32
    FROM SNMPv2-SMI
        InetAddress
    FROM INET-ADDRESS-MIB
        h3cDot11,
        H3cDot11RadioType,
        H3cDot11TxPwrLevelScopeType,
        H3cDot11ChannelScopeType,
        H3cDot11SSIDStringType,
        H3cDot11AuthenType,
        H3cDot11RadioScopeType,
        H3cDot11SSIDEncryptModeType,
        H3cDot11SecIEStatusType,
        H3cDot11PreambleType,
        H3cDot11ServicePolicyIDType,
        H3cDot11TunnelSecSchemType,
        H3cDot11RadioElementIndex,
        H3cDot11WorkMode,
        H3cDot11CirMode,
        h3cDot11APElementIndex,
        H3cDot11ObjectIDType,
        H3cDot11RadioType2
    FROM H3C-DOT11-REF-MIB;

h3cDot11CFG MODULE-IDENTITY
    LAST-UPDATED "201009251800Z"        -- Sep 25, 2010 at 18:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB provides information about WLAN configuration.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        Control And Provisioning of Wireless Access Points Protocol
        The short name of protocol is CAPWAP. AC will control
        and manage AP by CAPWAP tunnel protocol defined by IETF.
        Also, a data tunnel will be set up between AC and AP.

        BSS
        IEEE 802.11 Basic Service Set (Radio Cell).  The
        BSS of an AP comprises of the stations directly
        associating with the AP.

        Radio
        The chip set to receive and send wireless signal.

        Association
        The service used to establish access point
        or station mapping and enable station invocation
        of the distribution system services.
        (Wireless clients attempt to connect to
        access points.)

        Basic Rate
        A data rate that is mandatory for client
        devices to support in order for them to achieve
        successful association.

        MSDU
        MAC Service Data Unit, it is frame format defined by
        802.11.

        TU
        It is 1,024 microseconds (ms), which is about 1
        millisecond.

        AKM
        The authentication and key management method defined by
        802.11i, and which includes 802.1x and pre-shared key."
    REVISION "201009251800Z"        -- Sep 25, 2010 at 18:00 GMT
    DESCRIPTION
        "Modified to remove some issue."
    REVISION "201009021800Z"        -- Sep 2, 2010 at 18:00 GMT
    DESCRIPTION
        "Modified to add new node."
    REVISION "200907291800Z"        -- Jul 29, 2009 at 18:00 GMT
    DESCRIPTION
        "Modified to add new nodes and new table."
    REVISION "200905072000Z"        -- May 7, 2009 at 20:00 GMT
    DESCRIPTION
        "Modified to add new nodes and new table."
    REVISION "200903201530Z"        -- Mar 20, 2009 at 15:30 GMT
    DESCRIPTION
        "Modified to add new value for appointed node."
    REVISION "200811071530Z"        -- Nov 07, 2008 at 15:30 GMT
    DESCRIPTION
        "Modified to add new nodes and new table."
    REVISION "200807091800Z"        -- July 09, 2008 at 18:00 GMT
    DESCRIPTION
        "Modified to add new groups."
    REVISION "200802251800Z"        -- Feb 25, 2008 at 18:00 GMT
    DESCRIPTION
        "Modified to add new nodes."
    REVISION "200712211800Z"        -- Dec 21, 2007 at 18:00 GMT
    DESCRIPTION
        "Modified to add new nodes."
    REVISION "200710091655Z"    -- October 09, 2007 at 16:55 GMT
    DESCRIPTION
        "changed for new requirements"
    REVISION "200706191800Z"        -- June 19, 2007 at 18:00 GMT
    DESCRIPTION
        "Modified to add new table."
    REVISION "200704272000Z"        -- Apr 27, 2007 at 20:00 GMT
    DESCRIPTION
        "Modified to fix some issue."
    REVISION "200702012000Z"        -- February 01, 2007 at 20:00 GMT
    DESCRIPTION
        "Modified to support fat AP."
    REVISION "200605101900Z"        -- May 10, 2006 at 19:00 GMT
    DESCRIPTION
        "The initial revision of this MIB module."
    ::= { h3cDot11 4 }

-- *****************************************************************************
-- *  Major sections
-- *****************************************************************************
--  AP Configuration Group
--  DEFINED AS "The group to provide the configuration information
--  for APs.
h3cDot11GlobeConfigGroup OBJECT IDENTIFIER  ::= { h3cDot11CFG 1 }

h3cDot11PolicyConfigGroup OBJECT IDENTIFIER ::= { h3cDot11CFG 2 }
--  Policy Configuration Group has the following children:
--  h3cDot11RadioPolicyTable            ::= { h3cDot11PolicyConfigGroup 1 }
--  h3cDot11ServicePolicyTable          ::= { h3cDot11PolicyConfigGroup 2 }
--  h3cDot11ServicePolicyExtTable       ::= { h3cDot11PolicyConfigGroup 3 }
--  h3cDot11RadioPolicyExtTable         ::= { h3cDot11PolicyConfigGroup 4 }

h3cDot11APConfigGroup OBJECT IDENTIFIER     ::= { h3cDot11CFG 3 }
--  AP Configuration Group has the following children:
--  h3cDot11APTemplateTable                 ::= { h3cDot11APConfigGroup 1 }
--  h3cDot11RadioToConfigTable              ::= { h3cDot11APConfigGroup 2 }
--  h3cDot11APServiceSetTable               ::= { h3cDot11APConfigGroup 3 }
--  h3cDot11APSysInfoSetTable               ::= { h3cDot11APConfigGroup 4 }
--  h3cDot11APLimitTable                    ::= { h3cDot11APConfigGroup 5 }
--  h3cDot11APSerialIDTable                 ::= { h3cDot11APConfigGroup 10 }
--  h3cDot11APSTVlanTable                   ::= { h3cDot11APConfigGroup 11 }
h3cDot11RadioIntfConfigGroup OBJECT IDENTIFIER ::= { h3cDot11CFG 4 }
--  Radio Interface Group has the following children:
--  h3cDot11RadioIntfConfigTable          ::= { h3cDot11RadioIntfConfigGroup 1 }
--  h3cDot11RadioIntfBindTable            ::= { h3cDot11RadioIntfConfigGroup 2 }

h3cDot11DataRateConfigGroup OBJECT IDENTIFIER ::= { h3cDot11CFG 5 }
--  Data Rate Config Group has the following children:
--  h3cDot11DataRateConfigTable           ::= { h3cDot11DataRateConfigGroup 1 }

h3cDot11InterfaceConfigGroup OBJECT IDENTIFIER ::= { h3cDot11CFG 6 }
--  Interface Config Group has the following children:
--  h3cDot11WlanEssIfTable               ::= { h3cDot11InterfaceConfigGroup 1 }
--  h3cDot11WlanBssIfTable               ::= { h3cDot11InterfaceConfigGroup 2 }
--  h3cDot11WLANEthernetIfTable          ::= { h3cDot11InterfaceConfigGroup 3 }
--  h3cDot11PortSecurityTable            ::= { h3cDot11InterfaceConfigGroup 4 }
--  h3cDot11WlanMeshIfTable              ::= { h3cDot11InterfaceConfigGroup 5 }

h3cDot11ACBackupGroup OBJECT IDENTIFIER ::= { h3cDot11CFG 7 }

h3cDot11RadioElementConfigGroup OBJECT IDENTIFIER ::= { h3cDot11CFG 8 }
--  Radio Element Config Group has the following children:
--  h3cDot11nRadioCfgTable           ::= { h3cDot11RadioElementConfigGroup 1 }
--  h3cDot11RadioWDSTable            ::= { h3cDot11RadioElementConfigGroup 2 }
--  h3cDot11nRadioCfg2Table          ::= { h3cDot11RadioElementConfigGroup 3 }

h3cDot11CfgNotifyGroup OBJECT IDENTIFIER ::= { h3cDot11CFG 9 }

-- *****************************************************************************
-- *  h3cDot11GlobeConfigGroup Definition
-- *****************************************************************************
h3cDot11GlobalCountryCode OBJECT-TYPE
    SYNTAX      OCTET STRING(SIZE(3))
    MAX-ACCESS  read-write
    STATUS      current
    DESCRIPTION
        "Represents the country code for wireless network."
    ::= { h3cDot11GlobeConfigGroup 1 }

h3cDot11StaKeepALiveTimerIntvl OBJECT-TYPE
    SYNTAX      Unsigned32
    UNITS       "second"
    MAX-ACCESS  read-write
    STATUS      current
    DESCRIPTION
        "Represents the interval of the keep alive requests sent between
        AP and STA.
        Default value 0 : The keep alive function is disabled."
    DEFVAL      { 0 }
    ::= { h3cDot11GlobeConfigGroup 2 }

h3cDot11StaIdleTimerIntvl OBJECT-TYPE
    SYNTAX      Integer32
    UNITS       "second"
    MAX-ACCESS  read-write
    STATUS      current
    DESCRIPTION
        "Represents the interval for which the link between AP and STA
        ( power-save or awake ) can be idle."
    ::= { h3cDot11GlobeConfigGroup 3 }

h3cDot11BroadcastProbeReply OBJECT-TYPE
    SYNTAX      TruthValue
    MAX-ACCESS  read-write
    STATUS      current
    DESCRIPTION
        "Represents enable the AP to reply broadcast probe or not.
        'true' : The AP to reply broadcast probe is enabled.
        'false': The AP to reply broadcast probe is disabled"
    DEFVAL      { true }
    ::= { h3cDot11GlobeConfigGroup 4 }

h3cDot11APScanMode OBJECT-TYPE
    SYNTAX      INTEGER
        {
            active(1),
            passive(2)
        }
    MAX-ACCESS  read-write
    STATUS      current
    DESCRIPTION
        "Represents the scanning mode for AP.
        The following values are supported:
        active(1),  - AP will actively do scan.
        passive(2)  - AP will passively do scan."
    DEFVAL      { passive }
    ::= { h3cDot11GlobeConfigGroup 5 }

h3cDot11ACCtrlTunnelSecSupport OBJECT-TYPE
    SYNTAX      H3cDot11TunnelSecSchemType
    MAX-ACCESS  read-write
    STATUS      current
    DESCRIPTION
        "Represents what security schemes are supported for CAPWAP Control
        tunnel."
    ::= { h3cDot11GlobeConfigGroup 6 }

h3cDot11ACDataTunnelSecSupport OBJECT-TYPE
    SYNTAX      H3cDot11TunnelSecSchemType
    MAX-ACCESS  read-write
    STATUS      current
    DESCRIPTION
        "Represents what security schemes are supported for CAPWAP data
        tunnel. The cleartxt is the default scheme."
    DEFVAL      { cleartxt }
    ::= { h3cDot11GlobeConfigGroup 7 }

h3cDot11ACAutoAPSupport OBJECT-TYPE
    SYNTAX      TruthValue
    MAX-ACCESS  read-write
    STATUS      current
    DESCRIPTION
        "Represents enable the auto AP functionality or not.
        'true' : The auto AP functionality is enabled.
        'false': The auto AP functionality is disabled"
    DEFVAL      { false }
    ::= { h3cDot11GlobeConfigGroup 8 }

h3cDot11AutoAPName OBJECT-TYPE
    SYNTAX      OCTET STRING(SIZE(0..127))
    MAX-ACCESS  read-write
    STATUS      current
    DESCRIPTION
        "Represents the name of auto AP which need to be made persistent.
        When read the value from the node, NULL value be returned."
    ::= { h3cDot11GlobeConfigGroup 9 }

h3cDot11PersistentName OBJECT-TYPE
    SYNTAX      OCTET STRING(SIZE(0..127))
    MAX-ACCESS  read-write
    STATUS      current
    DESCRIPTION
        "Represents the new name of auto AP after being made persistent.
        When read the value from the node, NULL value be returned."
    ::= { h3cDot11GlobeConfigGroup 10 }

h3cDot11IntfTrapThreshold OBJECT-TYPE
    SYNTAX      Integer32
    UNITS       "dbm"
    MAX-ACCESS  read-write
    STATUS      current
    DESCRIPTION
        "Represents threshold of interference trap.  If signal strength of
        the device exceeds this threshold, corresponding trap will
        be sent."
    ::= { h3cDot11GlobeConfigGroup 11 }

h3cDot11MonitorInterval OBJECT-TYPE
    SYNTAX      Unsigned32(0 | 5..15)
    UNITS       "minute"
    MAX-ACCESS  read-write
    STATUS      current
    DESCRIPTION
        "Represents the monitoring interval.
        Default value 0 : The monitoring functionality is changed to
        real-time mode."
    DEFVAL      { 0 }
    ::= { h3cDot11GlobeConfigGroup 12 }

h3cDot11SampleInterval OBJECT-TYPE
    SYNTAX      Unsigned32(0 | 10..300)
    UNITS       "second"
    MAX-ACCESS  read-write
    STATUS      current
    DESCRIPTION
        "Represents the sampling interval.
        Default value 0 : The sampling functionality is disabled."
    DEFVAL      { 0 }
    ::= { h3cDot11GlobeConfigGroup 13 }

h3cDot11ChnlSwitChkInterval OBJECT-TYPE
    SYNTAX      Unsigned32(8..180)
    UNITS       "minute"
    MAX-ACCESS  read-write
    STATUS      current
    DESCRIPTION
        "Represents the checking interval of channel switch."
    DEFVAL      { 8 }
    ::= { h3cDot11GlobeConfigGroup 14 }

h3cDot11APUserUplimit OBJECT-TYPE
    SYNTAX      Unsigned32(0..65535)
    MAX-ACCESS  read-write
    STATUS      current
    DESCRIPTION
        "Represents the upper limit of user which has access to this AP."
    ::= { h3cDot11GlobeConfigGroup 15 }

h3cDot11APL2IsolateEnable OBJECT-TYPE
    SYNTAX      TruthValue
    MAX-ACCESS  read-write
    STATUS      current
    DESCRIPTION
        "Represents enable the layer2 isolation or not.
        'true' : The layer2 isolation functionality is enabled.
        'false': The layer2 isolation functionality is disabled."
    DEFVAL      { false }
    ::= { h3cDot11GlobeConfigGroup 16 }

h3cDot11APBSSIDSupportNum OBJECT-TYPE
    SYNTAX      Integer32
    MAX-ACCESS  read-only
    STATUS      current
    DESCRIPTION
        "Represents the max number of BSSID supported by Current AP."
    ::= { h3cDot11GlobeConfigGroup 17 }

h3cDot11APLastUpdateStatTime OBJECT-TYPE
    SYNTAX      DateAndTime
    MAX-ACCESS  read-only
    STATUS      current
    DESCRIPTION
        "Represents date and time update statistic information lately."
    ::= { h3cDot11GlobeConfigGroup 18 }

h3cDot11APDoSProtectEnable OBJECT-TYPE
    SYNTAX      TruthValue
    MAX-ACCESS  read-write
    STATUS      current
    DESCRIPTION
        "Represents enable the DOS protection or not.
        'true' : The DOS protection functionality is enabled.
        'false': The DOS protection functionality is disabled."
    DEFVAL      { false }
    ::= { h3cDot11GlobeConfigGroup 19 }

h3cDot11MaxAPPerIf OBJECT-TYPE
    SYNTAX      Unsigned32(0..65535)
    MAX-ACCESS  read-write
    STATUS      current
    DESCRIPTION
        "Represents max AP number that can be connected to AC interface."
    ::= { h3cDot11GlobeConfigGroup 20 }

h3cDot11SampleTimeStamp OBJECT-TYPE
    SYNTAX      DateAndTime
    MAX-ACCESS  read-only
    STATUS      current
    DESCRIPTION
        "Represents the start time of current sample period."
    ::= { h3cDot11GlobeConfigGroup 21 }

h3cDot11UplinkTrackId OBJECT-TYPE
    SYNTAX      Unsigned32
    MAX-ACCESS  read-write
    STATUS      current
    DESCRIPTION
        "Represents the track id of AP.
        Default value 0 : The uplink track function for AP is disabled."
    DEFVAL      { 0 }
    ::= { h3cDot11GlobeConfigGroup 22 }

h3cDot11RtCollectSwitch OBJECT-TYPE
    SYNTAX      TruthValue
    MAX-ACCESS  read-write
    STATUS      current
    DESCRIPTION
        "This object is used to turn on/off real-time statistics collection
         between AC and AP.  If the value is true, h3cDot11RtCollectIntvl will
         take effect.  Otherwise, h3cDot11RglCollectIntvl will take effect."
    DEFVAL      { false }
    ::= { h3cDot11GlobeConfigGroup 23 }

h3cDot11RglCollectIntvl OBJECT-TYPE
    SYNTAX      Integer32
    UNITS       "second"
    MAX-ACCESS  read-write
    STATUS      current
    DESCRIPTION
        "This object represents interval to regularly collect statistics from
         AC to AP."
    ::= { h3cDot11GlobeConfigGroup 24 }

h3cDot11RtCollectIntvl OBJECT-TYPE
    SYNTAX      Integer32
    UNITS       "second"
    MAX-ACCESS  read-write
    STATUS      current
    DESCRIPTION
        "This object represents interval to collect real-time statistics from
         AC to AP."
    ::= { h3cDot11GlobeConfigGroup 25 }

h3cDot11AllAPCpuUsageThreshold OBJECT-TYPE
    SYNTAX      Integer32(0..100)
    UNITS       "onepercent"
    MAX-ACCESS  read-write
    STATUS      current
    DESCRIPTION
        "The CPU usage threshold for all AP."
    ::= { h3cDot11GlobeConfigGroup 26 }

h3cDot11AllAPMemUsageThreshold OBJECT-TYPE
    SYNTAX      Integer32(0..100)
    UNITS       "onepercent"
    MAX-ACCESS  read-write
    STATUS      current
    DESCRIPTION
        "The memory usage threshold for all AP."
    ::= { h3cDot11GlobeConfigGroup 27 }

h3cDot11AdjIntfTrapThreshold OBJECT-TYPE
    SYNTAX      Integer32
    UNITS       "dbm"
    MAX-ACCESS  read-write
    STATUS      current
    DESCRIPTION
        "Represents threshold of adjacent interference trap. If signal strength
        of the device exceeds this threshold, corresponding trap will be sent."
    ::= { h3cDot11GlobeConfigGroup 28 }

h3cDot11AllAPMonitorMode OBJECT-TYPE
    SYNTAX      INTEGER
        {
            normal(1),
            monitor(2),
            hybrid(3)
        }
    MAX-ACCESS  read-write
    STATUS      current
    DESCRIPTION
        "Represents what work mode for All AP.
        The following values are supported:
        normal,     - AP will supply WLAN service.
        monitor     - AP will be a monitor to find attack.
        hybrid      - AP will supply WLAN service and Device detection is
        enabled."
    DEFVAL      { normal }
    ::= { h3cDot11GlobeConfigGroup 29 }
-- *****************************************************************************
-- * End of h3cDot11GlobeConfigGroup Definition
-- *****************************************************************************

-- *****************************************************************************
-- *  h3cDot11RadioPolicyTable Definition
-- *****************************************************************************
h3cDot11RadioPolicyTable OBJECT-TYPE
    SYNTAX      SEQUENCE OF H3cDot11RadioPolicyEntry
    MAX-ACCESS  not-accessible
    STATUS      current
    DESCRIPTION
        "The table defines the parameters for radio policy, as per
        radio policy of CLI.
        One radio policy could be assigned to the different radios (AP)."
    ::= { h3cDot11PolicyConfigGroup 1 }

h3cDot11RadioPolicyEntry OBJECT-TYPE
    SYNTAX      H3cDot11RadioPolicyEntry
    MAX-ACCESS  not-accessible
    STATUS      current
    DESCRIPTION
        "Each entry contains information of each radio policy."
    INDEX
        {
            IMPLIED h3cDot11RadioPolicyName
        }
    ::= { h3cDot11RadioPolicyTable 1 }

H3cDot11RadioPolicyEntry ::= SEQUENCE
    {
        h3cDot11RadioPolicyName        OCTET STRING,
        h3cDot11BeaconInterval         Integer32,
        h3cDot11DtimInterval           Integer32,
        h3cDot11RtsThreshold           Integer32,
        h3cDot11FragThreshold          Integer32,
        h3cDot11ShortRetryThreshold    Integer32,
        h3cDot11LongRetryThreshold     Integer32,
        h3cDot11MaxRxLifetime          Unsigned32,
        h3cDot11RdoPolicyRowStatus     RowStatus,
        h3cDot11RdoClientMaxCount      Integer32,
        h3cDot11BeaconIntervalMs       Integer32
    }

h3cDot11RadioPolicyName OBJECT-TYPE
    SYNTAX      OCTET STRING(SIZE(0..127))
    MAX-ACCESS  not-accessible
    STATUS      current
    DESCRIPTION
        "Represents the name of radio policy."
    ::= { h3cDot11RadioPolicyEntry 1 }

h3cDot11BeaconInterval OBJECT-TYPE
    SYNTAX      Integer32
    UNITS       "TU"
    MAX-ACCESS  read-create
    STATUS      current
    DESCRIPTION
        "Represents the interval for Beacon management frame."
    DEFVAL      { 100 }
    ::= { h3cDot11RadioPolicyEntry 2 }

h3cDot11DtimInterval OBJECT-TYPE
    SYNTAX      Integer32
    MAX-ACCESS  read-create
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL      { 1 }
    ::= { h3cDot11RadioPolicyEntry 3 }

h3cDot11RtsThreshold OBJECT-TYPE
    SYNTAX      Integer32
    UNITS       "byte"
    MAX-ACCESS  read-create
    STATUS      current
    DESCRIPTION
        "Represents the current minimum size,in octets,of the MAC
        protocol data unit (MPDU), below which a Request to send/Clear
        to send (RTS/CTS) handshake shall not be performed."
    DEFVAL      { 2346 }
    ::= { h3cDot11RadioPolicyEntry 4 }

h3cDot11FragThreshold OBJECT-TYPE
    SYNTAX      Integer32
    UNITS       "byte"
    MAX-ACCESS  read-create
    STATUS      current
    DESCRIPTION
        "Represents the current maximum size, in octets, of the MPDU that
        may be delivered to the PHY. A MSDU shall be broken into
        fragments if its size exceeds the value of this attribute after
        adding MAC headers and trailers."
    DEFVAL      { 2346 }
    ::= { h3cDot11RadioPolicyEntry 5 }

h3cDot11ShortRetryThreshold OBJECT-TYPE
    SYNTAX      Integer32
    MAX-ACCESS  read-create
    STATUS      current
    DESCRIPTION
        "Represents the maximum number of transmission attempts of a
        frame, the length of which is less than or equal to
        h3cDot11RTSThreshold, that shall be made before a failure
        condition is indicated."
    DEFVAL      { 7 }
    ::= { h3cDot11RadioPolicyEntry 6 }

h3cDot11LongRetryThreshold OBJECT-TYPE
    SYNTAX      Integer32
    MAX-ACCESS  read-create
    STATUS      current
    DESCRIPTION
        "Represents the maximum number of transmission attempts of a
        frame, the length of which is longer than h3cDot11RTSThreshold,
        that shall be made before a failure condition is indicated."
    DEFVAL      { 4 }
    ::= { h3cDot11RadioPolicyEntry 7 }

h3cDot11MaxRxLifetime OBJECT-TYPE
    SYNTAX      Unsigned32
    UNITS       "millisecond"
    MAX-ACCESS  read-create
    STATUS      current
    DESCRIPTION
        "Represents the elapsed time. After the time specified by
        h3cDot11MaxRxLifetime, the further attempts to reassemble the
        MSDU shall be terminated."
    DEFVAL      { 2000 }
    ::= { h3cDot11RadioPolicyEntry 8 }

h3cDot11RdoPolicyRowStatus OBJECT-TYPE
    SYNTAX      RowStatus
    MAX-ACCESS  read-create
    STATUS      current
    DESCRIPTION
        "The status of this table entry."
    ::= { h3cDot11RadioPolicyEntry 9 }

h3cDot11RdoClientMaxCount OBJECT-TYPE
    SYNTAX      Integer32(0..2147483647)
    MAX-ACCESS  read-create
    STATUS      current
    DESCRIPTION
        "Represent the maximum number of stations supported by
        this radio policy."
    ::= { h3cDot11RadioPolicyEntry 10 }

h3cDot11BeaconIntervalMs OBJECT-TYPE
    SYNTAX      Integer32
    UNITS       "ms"
    MAX-ACCESS  read-create
    STATUS      current
    DESCRIPTION
        "Represents the interval for Beacon management frame."
    ::= { h3cDot11RadioPolicyEntry 11 }
-- *****************************************************************************
-- * End of h3cDot11RadioPolicyTable Definition
-- *****************************************************************************

-- *****************************************************************************
-- *  h3cDot11ServicePolicyTable Definition
-- *****************************************************************************
h3cDot11ServicePolicyTable OBJECT-TYPE
    SYNTAX      SEQUENCE OF H3cDot11ServicePolicyEntry
    MAX-ACCESS  not-accessible
    STATUS      current
    DESCRIPTION
        "The table defines the parameters for ESS, as per service policy
        of CLI.
        One service policy could be assigned to the different radios
        (AP)."
    ::= { h3cDot11PolicyConfigGroup 2 }

h3cDot11ServicePolicyEntry OBJECT-TYPE
    SYNTAX      H3cDot11ServicePolicyEntry
    MAX-ACCESS  not-accessible
    STATUS      current
    DESCRIPTION
        "Each entry contains information of each service policy."
    INDEX
        {
            h3cDot11ServicePolicyID
        }
    ::= { h3cDot11ServicePolicyTable 1 }

H3cDot11ServicePolicyEntry ::= SEQUENCE
    {
        h3cDot11ServicePolicyID       H3cDot11ServicePolicyIDType,
        h3cDot11SSIDName              H3cDot11SSIDStringType,
        h3cDot11SSIDHidden            TruthValue,
        h3cDot11AuthenMode            H3cDot11AuthenType,
        h3cDot11SSIDEncryptionMode    H3cDot11SSIDEncryptModeType,
        h3cDot11WlanInfBindingType    OCTET STRING,
        h3cDot11WlanInfBindingID      Integer32,
        h3cDot11SrvPolicyRowStatus    RowStatus,
        h3cDot11ClientMaxCount        Integer32,
        h3cDot11SPInCirMode           H3cDot11CirMode,
        h3cDot11SPInCirValue          Integer32,
        h3cDot11SPOutCirMode          H3cDot11CirMode,
        h3cDot11SPOutCirValue         Integer32,
        h3cDot11WlanInfPVID           Integer32,
        h3cDot11SPInCirStaticValue    Integer32,
        h3cDot11SPOutCirStaticValue   Integer32,
        h3cDot11SPIsolate             TruthValue,
        h3cDot11WAPIAuthServerIP      IpAddress
    }

h3cDot11ServicePolicyID OBJECT-TYPE
    SYNTAX      H3cDot11ServicePolicyIDType
    MAX-ACCESS  not-accessible
    STATUS      current
    DESCRIPTION
        "Represents the ID of each service policy."
    ::= { h3cDot11ServicePolicyEntry 1 }

h3cDot11SSIDName OBJECT-TYPE
    SYNTAX      H3cDot11SSIDStringType
    MAX-ACCESS  read-create
    STATUS      current
    DESCRIPTION
        "Represents the ESS. As per CLI, the value of
        service policy name will be SSID."
    ::= { h3cDot11ServicePolicyEntry 2 }

h3cDot11SSIDHidden OBJECT-TYPE
    SYNTAX      TruthValue
    MAX-ACCESS  read-create
    STATUS      current
    DESCRIPTION
        "This attribute controls whether the SSID will be advertised in
        the beacon frame.
        If it is true, then SSID will not be advertised in the beacon
        frame."
    DEFVAL      { false }
    ::= { h3cDot11ServicePolicyEntry 3 }

h3cDot11AuthenMode OBJECT-TYPE
    SYNTAX      H3cDot11AuthenType
    MAX-ACCESS  read-create
    STATUS      current
    DESCRIPTION
        "Represents the Authentication mode defined by 802.11."
    ::= { h3cDot11ServicePolicyEntry 4 }

h3cDot11SSIDEncryptionMode OBJECT-TYPE
    SYNTAX      H3cDot11SSIDEncryptModeType
    MAX-ACCESS  read-create
    STATUS      current
    DESCRIPTION
        "Represents the encryption mode for this ESS."
    ::= { h3cDot11ServicePolicyEntry 5 }

h3cDot11WlanInfBindingType OBJECT-TYPE
    SYNTAX      OCTET STRING
    MAX-ACCESS  read-create
    STATUS      current
    DESCRIPTION
        "Represents the service policy will bind to what kind of
        data forwarding interface."
    DEFVAL      { "WLAN-ESS" }
    ::= { h3cDot11ServicePolicyEntry 6 }

h3cDot11WlanInfBindingID OBJECT-TYPE
    SYNTAX      Integer32
    MAX-ACCESS  read-create
    STATUS      current
    DESCRIPTION
        "Represents the interface ID of the interface that ESS will
        bind to.
        If the value is set to -1, the binding will be removed."
    ::= { h3cDot11ServicePolicyEntry 7 }

h3cDot11SrvPolicyRowStatus OBJECT-TYPE
    SYNTAX      RowStatus
    MAX-ACCESS  read-create
    STATUS      current
    DESCRIPTION
        "The status of this table entry."
    ::= { h3cDot11ServicePolicyEntry 8 }

h3cDot11ClientMaxCount OBJECT-TYPE
    SYNTAX      Integer32(0..2147483647)
    MAX-ACCESS  read-create
    STATUS      current
    DESCRIPTION
        "Represent the maximum number of stations supported by
        this service policy."
    ::= { h3cDot11ServicePolicyEntry 9 }

h3cDot11SPInCirMode OBJECT-TYPE
    SYNTAX      H3cDot11CirMode
    MAX-ACCESS  read-create
    STATUS      current
    DESCRIPTION
        "
        CIR(committed information rate) mode of inbound direction.
        This object is useful only when the corresponding CIR is nonzero.
        If value of this object is changed, corresponding CIR will be reset."
    DEFVAL      { static }
    ::= { h3cDot11ServicePolicyEntry 10 }

h3cDot11SPInCirValue OBJECT-TYPE
    SYNTAX      Integer32
    UNITS       "Kbps"
    MAX-ACCESS  read-create
    STATUS      current
    DESCRIPTION
        "Represents the CIR of inbound direction of this service policy.
        If the value is 0, it means that no flow control is applied to
        the service policy, and the corresponding CIR mode is meaningless."
    DEFVAL      { 0 }
    ::= { h3cDot11ServicePolicyEntry 11 }

h3cDot11SPOutCirMode OBJECT-TYPE
    SYNTAX      H3cDot11CirMode
    MAX-ACCESS  read-create
    STATUS      current
    DESCRIPTION
        "
        CIR(committed information rate) mode of outbound direction.
        This object is useful only when the corresponding CIR is nonzero.
        If value of this object is changed, corresponding CIR will be reset."
    DEFVAL      { static }
    ::= { h3cDot11ServicePolicyEntry 12 }

h3cDot11SPOutCirValue OBJECT-TYPE
    SYNTAX      Integer32
    UNITS       "Kbps"
    MAX-ACCESS  read-create
    STATUS      current
    DESCRIPTION
        "Represents the CIR of outbound direction of this service policy.
        If the value is 0, it means that no flow control is applied to
        the service policy, and the corresponding CIR mode is meaningless."
    DEFVAL      { 0 }
    ::= { h3cDot11ServicePolicyEntry 13 }

h3cDot11WlanInfPVID OBJECT-TYPE
    SYNTAX      Integer32
    MAX-ACCESS  read-create
    STATUS      current
    DESCRIPTION
        "Represents the VLAN ID of SSID."
    DEFVAL      { 1 }
    ::= { h3cDot11ServicePolicyEntry 14 }

h3cDot11SPInCirStaticValue  OBJECT-TYPE
    SYNTAX      Integer32
    UNITS       "Kbps"
    MAX-ACCESS  read-create
    STATUS      current
    DESCRIPTION
        "Represents the CIR of inbound direction for static CIR mode."
    DEFVAL      { 0 }
        ::= { h3cDot11ServicePolicyEntry 15 }

h3cDot11SPOutCirStaticValue  OBJECT-TYPE
    SYNTAX      Integer32
    UNITS       "Kbps"
    MAX-ACCESS  read-create
    STATUS      current
    DESCRIPTION
        "Represents the CIR of outbound direction for static CIR mode."
    DEFVAL      { 0 }
        ::= { h3cDot11ServicePolicyEntry 16 }

h3cDot11SPIsolate OBJECT-TYPE
    SYNTAX      TruthValue
    MAX-ACCESS  read-create
    STATUS      current
    DESCRIPTION
        "If it is true, then stations connected with the service policy are
         isolated."
    DEFVAL      { false }
    ::= { h3cDot11ServicePolicyEntry 17 }

h3cDot11WAPIAuthServerIP OBJECT-TYPE
    SYNTAX     IpAddress
    MAX-ACCESS read-create
    STATUS     current
    DESCRIPTION
        "Represents the IP address of the WAPI Authentication server"
    ::= {  h3cDot11ServicePolicyEntry 18 }

-- *****************************************************************************
-- * End of h3cDot11ServicePolicyTable Definition
-- *****************************************************************************

-- *****************************************************************************
-- *  h3cDot11ServicePolicyExtTable Definition
-- *****************************************************************************
h3cDot11ServicePolicyExtTable OBJECT-TYPE
    SYNTAX      SEQUENCE OF H3cDot11ServicePolicyExtEntry
    MAX-ACCESS  not-accessible
    STATUS      current
    DESCRIPTION
        "The table defines the parameters for ESS, as per service policy
        of CLI.
        When the value of h3cDot11SSIDEncryptionMode equals to cipher(2),
        more configuration for a ESS will be put into the table."
    ::= { h3cDot11PolicyConfigGroup 3 }

h3cDot11ServicePolicyExtEntry OBJECT-TYPE
    SYNTAX      H3cDot11ServicePolicyExtEntry
    MAX-ACCESS  not-accessible
    STATUS      current
    DESCRIPTION
        "Each entry contains information of each service policy under cipher(2)
        mode."
    INDEX
        {
            h3cDot11ServicePolicyExtID
        }
    ::= { h3cDot11ServicePolicyExtTable 1 }

H3cDot11ServicePolicyExtEntry ::= SEQUENCE
    {
        h3cDot11ServicePolicyExtID       H3cDot11ServicePolicyIDType,
        h3cDot11SecIEStatus              H3cDot11SecIEStatusType,
        h3cDot11SecurityCiphers          INTEGER,
        h3cDot11CipherKeyIndex           INTEGER,
        h3cDot11CipherKey                OCTET STRING,
        h3cDot11SrvPolicyExtRowStatus    RowStatus,
        h3cDot11CipherKeyType            INTEGER
    }

h3cDot11ServicePolicyExtID OBJECT-TYPE
    SYNTAX      H3cDot11ServicePolicyIDType
    MAX-ACCESS  not-accessible
    STATUS      current
    DESCRIPTION
        "Represents the ID of each service policy."
    ::= { h3cDot11ServicePolicyExtEntry 1 }

h3cDot11SecIEStatus OBJECT-TYPE
    SYNTAX      H3cDot11SecIEStatusType
    MAX-ACCESS  read-create
    STATUS      current
    DESCRIPTION
        "To enable the security Information element in the beacon and
        probe response frames sent by AP."
    ::= { h3cDot11ServicePolicyExtEntry 2 }

h3cDot11SecurityCiphers OBJECT-TYPE
    SYNTAX      INTEGER
    MAX-ACCESS  read-create
    STATUS      current
    DESCRIPTION
        "The WLAN system support the following cipher type for data frame
        encryption.
        wep40(2)
        tkip(4)
        aesccmp(16)
        wep104(32)
        wpisms4(64)
        wep128(128)
        For each service policy,it could support multiple cipher types at
        the same time.So the value of object could combine multiple value
        of cipher type above.
        When the value of node equals to zero, it means no configuration or
        undo operation."
    ::= { h3cDot11ServicePolicyExtEntry 3 }

h3cDot11CipherKeyIndex OBJECT-TYPE
    SYNTAX      INTEGER
    MAX-ACCESS  read-create
    STATUS      current
    DESCRIPTION
        "Represents the key index of cipher key for packet.
        When h3cDot11SecurityCiphers value is wep40 or wep104,
        the configuration will take effective."
    DEFVAL      { 1 }
    ::= { h3cDot11ServicePolicyExtEntry 4 }

h3cDot11CipherKey OBJECT-TYPE
    SYNTAX      OCTET STRING
    MAX-ACCESS  read-create
    STATUS      current
    DESCRIPTION
        "Represents the cipher key for packet.
        When h3cDot11SecurityCiphers value is wep40 or wep104,
        the configuration will take effective."
    ::= { h3cDot11ServicePolicyExtEntry 5 }

h3cDot11SrvPolicyExtRowStatus OBJECT-TYPE
    SYNTAX      RowStatus
    MAX-ACCESS  read-create
    STATUS      current
    DESCRIPTION
        "The status of this table entry."
    ::= { h3cDot11ServicePolicyExtEntry 6 }

h3cDot11CipherKeyType OBJECT-TYPE
    SYNTAX      INTEGER
    {
        char(1),
        hex(2)
    }
    MAX-ACCESS  read-create
    STATUS      current
    DESCRIPTION
        "Represents the cipher key type of h3cDot11CipherKey."
    DEFVAL    {1}
    ::= { h3cDot11ServicePolicyExtEntry 7 }

-- *****************************************************************************
-- * End of h3cDot11ServicePolicyExtTable Definition
-- *****************************************************************************

-- *****************************************************************************
-- *  h3cDot11RadioPolicyExtTable Definition
-- *****************************************************************************
h3cDot11RadioPolicyExtTable OBJECT-TYPE
    SYNTAX      SEQUENCE OF H3cDot11RadioPolicyExtEntry
    MAX-ACCESS  not-accessible
    STATUS      current
    DESCRIPTION
        "The table defines the radio policy of each radio.
        It can't be modified if the radio policy is a default radio policy."
    ::= { h3cDot11PolicyConfigGroup 4 }

h3cDot11RadioPolicyExtEntry OBJECT-TYPE
    SYNTAX      H3cDot11RadioPolicyExtEntry
    MAX-ACCESS  not-accessible
    STATUS      current
    DESCRIPTION
        "Each entry contains information of each radio policy."
    INDEX
        {
            h3cDot11RPAPSerialID,
            h3cDot11RPRadioID
        }
    ::= { h3cDot11RadioPolicyExtTable 1 }

H3cDot11RadioPolicyExtEntry ::= SEQUENCE
    {
        h3cDot11RPAPSerialID             OCTET STRING,
        h3cDot11RPRadioID                H3cDot11RadioScopeType,
        h3cDot11RPBeaconInterval         Integer32,
        h3cDot11RPDtimInterval           Integer32,
        h3cDot11RPRtsThreshold           Integer32,
        h3cDot11RPFragThreshold          Integer32,
        h3cDot11RPShortRetryThreshold    Integer32,
        h3cDot11RPLongRetryThreshold     Integer32,
        h3cDot11RPClientMaxCount         Integer32
    }

h3cDot11RPAPSerialID OBJECT-TYPE
    SYNTAX      OCTET STRING(SIZE(0..127))
    MAX-ACCESS  not-accessible
    STATUS      current
    DESCRIPTION
        "This object represents the Serial ID of AP."
    ::= { h3cDot11RadioPolicyExtEntry 1 }

h3cDot11RPRadioID OBJECT-TYPE
    SYNTAX      H3cDot11RadioScopeType
    MAX-ACCESS  not-accessible
    STATUS      current
    DESCRIPTION
        "This object represents each radio."
    ::= { h3cDot11RadioPolicyExtEntry 2 }

h3cDot11RPBeaconInterval OBJECT-TYPE
    SYNTAX      Integer32
    UNITS       "milliseconds"
    MAX-ACCESS  read-write
    STATUS      current
    DESCRIPTION
        "This object represents the interval for Beacon management frame."
    DEFVAL      { 100 }
    ::= { h3cDot11RadioPolicyExtEntry 3 }

h3cDot11RPDtimInterval OBJECT-TYPE
    SYNTAX      Integer32
    MAX-ACCESS  read-write
    STATUS      current
    DESCRIPTION
        "This object represents the number of beacon intervals that shall elapse
        between transmissions of Beacons frames containing a Traffic
        Indication Map (TIM) element whose DTIM count field is 0.
        This value is transmitted in the Delivery TIM (DTIM) Period
        field of Beacon frames."
    DEFVAL      { 1 }
    ::= { h3cDot11RadioPolicyExtEntry 4 }

h3cDot11RPRtsThreshold OBJECT-TYPE
    SYNTAX      Integer32
    UNITS       "byte"
    MAX-ACCESS  read-write
    STATUS      current
    DESCRIPTION
        "This object represents the current minimum size, in octets, of the MAC
        protocol data unit (MPDU), below which a Request to send/Clear
        to send (RTS/CTS) handshake shall not be performed."
    DEFVAL      { 2346 }
    ::= { h3cDot11RadioPolicyExtEntry 5 }

h3cDot11RPFragThreshold OBJECT-TYPE
    SYNTAX      Integer32
    UNITS       "byte"
    MAX-ACCESS  read-write
    STATUS      current
    DESCRIPTION
        "This object represents the current maximum size, in octets, of the MPDU
         that may be delivered to the PHY.  A MSDU shall be broken into
        fragments if its size exceeds the value of this attribute after
        adding MAC headers and trailers."
    DEFVAL      { 2346 }
    ::= { h3cDot11RadioPolicyExtEntry 6 }

h3cDot11RPShortRetryThreshold OBJECT-TYPE
    SYNTAX      Integer32
    MAX-ACCESS  read-write
    STATUS      current
    DESCRIPTION
        "This object represents the maximum number of transmission attempts of a
        frame, the length of which is less than or equal to
        h3cDot11RTSThreshold, that shall be made before a failure
        condition is indicated."
    DEFVAL      { 7 }
    ::= { h3cDot11RadioPolicyExtEntry 7 }

h3cDot11RPLongRetryThreshold OBJECT-TYPE
    SYNTAX      Integer32
    MAX-ACCESS  read-write
    STATUS      current
    DESCRIPTION
        "This object represents the maximum number of transmission attempts of a
        frame, the length of which is longer than h3cDot11RTSThreshold,
        and that shall be made before a failure condition is indicated."
    DEFVAL      { 4 }
    ::= { h3cDot11RadioPolicyExtEntry 8 }

h3cDot11RPClientMaxCount OBJECT-TYPE
    SYNTAX      Integer32(0..2147483647)
    MAX-ACCESS  read-write
    STATUS      current
    DESCRIPTION
        "This object represents the maximum number of stations supported by
        this radio policy."
    ::= { h3cDot11RadioPolicyExtEntry 9 }

-- *****************************************************************************
-- * End of h3cDot11RadioPolicyTable Definition
-- *****************************************************************************
-- *****************************************************************************
-- *  h3cDot11ServicePolicyPortSecurityTable Definition
-- *****************************************************************************
h3cDot11SrvPortSecurityTable OBJECT-TYPE
    SYNTAX      SEQUENCE OF H3cDot11SrvPortSecurityEntry
    MAX-ACCESS  not-accessible
    STATUS      current
    DESCRIPTION
        "This table defines the WLAN security status for ESS, BSS and
        WLAN-Ethernet interface which binding the crypto service-template.
        Otherwise, when binding the clear service-template,
        h3cPortSecurityTables should be used to configure port security."
    ::= { h3cDot11PolicyConfigGroup 5 }

h3cDot11SrvPortSecurityEntry OBJECT-TYPE
    SYNTAX      H3cDot11SrvPortSecurityEntry
    MAX-ACCESS  not-accessible
    STATUS      current
    DESCRIPTION
        "There is a row in this table for service policy."
    INDEX
        {
            h3cDot11SecurityServicePolicyID
        }
    ::= { h3cDot11SrvPortSecurityTable 1 }

H3cDot11SrvPortSecurityEntry ::= SEQUENCE
    {
        h3cDot11SecurityServicePolicyID           H3cDot11ServicePolicyIDType,
        h3cDot11SrvPortSecurityMode               INTEGER,
        h3cDot11SrvSecurityKeyType                INTEGER,
        h3cDot11SrvSecurityPskKeyMode             INTEGER,
        h3cDot11SrvSecurityPskKeyString           DisplayString
    }

h3cDot11SecurityServicePolicyID OBJECT-TYPE
    SYNTAX      H3cDot11ServicePolicyIDType
    MAX-ACCESS  not-accessible
    STATUS      current
    DESCRIPTION
        "Represents the ID of each service policy."
    ::= { h3cDot11SrvPortSecurityEntry 1 }

h3cDot11SrvPortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions(1)  The default value,no any security mode is set.

        userLoginSecureExt(2) Access to the port is denied until the port
        client is authorized (by 802.1X).

        psk(3) Access to the port is denied until the port client is
        authorized (by 802.1X key negotiation).

        macAddressAndPsk(4) The MAC address is first authenticated and only if
        this succeeds does the psk then attempt user authentication.

        userLoginSecureExtOrPsk(5) This selects both the userLoginSecureExt and
        psk modes together such that either is allowed to authorized access.
        Which mode works for client depends on the client's choice.

        ext(6) Access to the port is denied until the port client is
        authenticated (by ext).
        "
    ::= { h3cDot11SrvPortSecurityEntry 2 }

h3cDot11SrvSecurityKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone(1) This means the key type is not set yet.

        userLoginTxKeyTypeDot11Key(2) This selects the 802.11 key type.

        userLoginTxKeyTypeRsaRC4Key(3) This selects the RC4 key for RSA RC4
        session encryption."
    ::= { h3cDot11SrvPortSecurityEntry 3 }

h3cDot11SrvSecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode. When input as pskKeyModePassPhrase,
        h3cDot11SrvSecurityPskKeyString must be 8 to 63 characters;
        when input as pskKeyModeRawKey, h3cDot11SrvSecurityPskKeyString
        must be 64 characters and each character must be '0'-'9', 'a'-'f' and
        'A'-'F'."
    ::= { h3cDot11SrvPortSecurityEntry 4 }

h3cDot11SrvSecurityPskKeyString OBJECT-TYPE
    SYNTAX      DisplayString(SIZE(0..64))
    MAX-ACCESS  read-write
    STATUS      current
    DESCRIPTION
        "This is the password string used for psk authentication."
    ::= { h3cDot11SrvPortSecurityEntry 5 }

-- *****************************************************************************
-- *  End of h3cDot11PortSecurityTable Definition
-- *****************************************************************************

-- *****************************************************************************
-- *  h3cDot11SrvPolicyExtendTable Definition
-- *****************************************************************************
h3cDot11SrvPolicyExtendTable OBJECT-TYPE
    SYNTAX      SEQUENCE OF H3cDot11SrvPolicyExtendEntry
    MAX-ACCESS  not-accessible
    STATUS      current
    DESCRIPTION
        "The table defines the parameters of each service policy."
    ::= { h3cDot11PolicyConfigGroup 6 }

h3cDot11SrvPolicyExtendEntry OBJECT-TYPE
    SYNTAX      H3cDot11SrvPolicyExtendEntry
    MAX-ACCESS  not-accessible
    STATUS      current
    DESCRIPTION
        "Each entry contains information of each service policy."
    INDEX
        {
            h3cDot11ServicePolicyID
        }
    ::= { h3cDot11SrvPolicyExtendTable 1 }

H3cDot11SrvPolicyExtendEntry ::= SEQUENCE
    {
        h3cDot11SPEnable              INTEGER
    }

h3cDot11SPEnable OBJECT-TYPE
    SYNTAX      INTEGER
    {
        enable(1),
        disable(2)
    }
    MAX-ACCESS  read-write
    STATUS      current
    DESCRIPTION
        "Represents whether the service policy is enabled."
    ::= { h3cDot11SrvPolicyExtendEntry 1 }

-- *****************************************************************************
-- *  End of h3cDot11ServicePolicyExtendTable Definition
-- *****************************************************************************

-- *****************************************************************************
-- *  h3cDot11APTemplateTable Definition
-- *****************************************************************************
h3cDot11APTemplateTable OBJECT-TYPE
    SYNTAX      SEQUENCE OF H3cDot11APTemplateEntry
    MAX-ACCESS  not-accessible
    STATUS      current
    DESCRIPTION
        "By AP template CLI, administrator will configure the parameters of AP
        by convenience.
        Before AP boot up and connect to AC by CAPWAP tunnel, administrator
        will create AP template for each AP. When AP connect to AC,
        AC will assign configuration to AP by h3cDot11APSerialID
        information in AP template."
    ::= { h3cDot11APConfigGroup 1 }

h3cDot11APTemplateEntry OBJECT-TYPE
    SYNTAX      H3cDot11APTemplateEntry
    MAX-ACCESS  not-accessible
    STATUS      current
    DESCRIPTION
        "Each entry contains configuration information for each AP."
    INDEX
        {
            h3cDot11APTemplateName
        }
    ::= { h3cDot11APTemplateTable 1 }

H3cDot11APTemplateEntry ::= SEQUENCE
    {
        h3cDot11APTemplateName             OCTET STRING,
        h3cDot11APSerialID                 OCTET STRING,
        h3cDot11TemplateAPModelAlias       OCTET STRING,
        h3cDot11Description                OCTET STRING,
        h3cDot11APWorkMode                 INTEGER,
        h3cDot11APTemplateRowStatus        RowStatus,
        h3cDot11APName                     OCTET STRING,
        h3cDot11StatisInterv               Integer32,
        h3cDot11APBroadcastProbeReply      TruthValue,
        h3cDot11StaIdleTimerInterv         Integer32,
        h3cDot11StaKeepAliveTimerInterv    Integer32,
        h3cDot11APCir                      Integer32,
        h3cDot11APCbs                      Integer32,
        h3cDot11APPriorityLevel            Integer32,
        h3cDot11APElementID                Integer32,
        h3cDot11APDevDetectEnable          TruthValue,
        h3cDot11APGetIPMethod              INTEGER,
        h3cDot11StatisIntervMode           INTEGER,
        h3cDot11ApTrapEnabled              TruthValue
    }

h3cDot11APTemplateName OBJECT-TYPE
    SYNTAX      OCTET STRING(SIZE(0..127))
    MAX-ACCESS  not-accessible
    STATUS      current
    DESCRIPTION
        "Represents the name of AP template."
    ::= { h3cDot11APTemplateEntry 1 }

h3cDot11APSerialID OBJECT-TYPE
    SYNTAX      OCTET STRING
    MAX-ACCESS  read-create
    STATUS      current
    DESCRIPTION
        "Represents AP serial id."
    ::= { h3cDot11APTemplateEntry 2 }

h3cDot11TemplateAPModelAlias OBJECT-TYPE
    SYNTAX      OCTET STRING
    MAX-ACCESS  read-create
    STATUS      current
    DESCRIPTION
        "Represents the alias of AP model name."
    ::= { h3cDot11APTemplateEntry 3 }

h3cDot11Description OBJECT-TYPE
    SYNTAX      OCTET STRING
    MAX-ACCESS  read-create
    STATUS      current
    DESCRIPTION
        "This attribute will give more information about AP.
        Administrator could suggest the location, owner or
        other information for each AP.
        If the value is set to NULL, the description will be removed."
    ::= { h3cDot11APTemplateEntry 4 }

h3cDot11APWorkMode OBJECT-TYPE
    SYNTAX      INTEGER
        {
            normal(1),
            monitor(2),
            hybrid(3)
        }
    MAX-ACCESS  read-create
    STATUS      current
    DESCRIPTION
        "Represents what work mode for AP.
        The following values are supported:
        normal      - AP will supply WLAN service.
        monitor     - AP will be a monitor to find attack.
        hybrid      - AP will supply WLAN service and Device detection is
        enabled."
    DEFVAL      { normal }
    ::= { h3cDot11APTemplateEntry 5 }

h3cDot11APTemplateRowStatus OBJECT-TYPE
    SYNTAX      RowStatus
    MAX-ACCESS  read-create
    STATUS      current
    DESCRIPTION
        "The status of this table entry."
    ::= { h3cDot11APTemplateEntry 6 }

h3cDot11APName OBJECT-TYPE
    SYNTAX      OCTET STRING
    MAX-ACCESS  read-create
    STATUS      current
    DESCRIPTION
        "Represents the AP name."
    ::= { h3cDot11APTemplateEntry 7 }

h3cDot11StatisInterv OBJECT-TYPE
    SYNTAX      Integer32
    UNITS       "second"
    MAX-ACCESS  read-create
    STATUS      current
    DESCRIPTION
        "Represents the interval of radio statistic."
    ::= { h3cDot11APTemplateEntry 8 }

h3cDot11APBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { h3cDot11APTemplateEntry 9 }

h3cDot11StaIdleTimerInterv OBJECT-TYPE
    SYNTAX      Integer32
    UNITS       "second"
    MAX-ACCESS  read-create
    STATUS      current
    DESCRIPTION
        "Represents the interval for which the link between AP and STA
        ( power-save or awake ) can be idle."
    ::= { h3cDot11APTemplateEntry 10 }

h3cDot11StaKeepAliveTimerInterv OBJECT-TYPE
    SYNTAX      Integer32
    UNITS       "second"
    MAX-ACCESS  read-create
    STATUS      current
    DESCRIPTION
        "Represents the interval of the keep alive requests sent between
        AP and STA."
    ::= { h3cDot11APTemplateEntry 11 }

h3cDot11APCir OBJECT-TYPE
    SYNTAX      Integer32
    UNITS       "Kbps"
    MAX-ACCESS  read-create
    STATUS      current
    DESCRIPTION
        "Represents the committed information rate between AP and AC."
    ::= { h3cDot11APTemplateEntry 12 }

h3cDot11APCbs OBJECT-TYPE
    SYNTAX      Integer32
    UNITS       "Bytes"
    MAX-ACCESS  read-create
    STATUS      current
    DESCRIPTION
        "Represents the committed burst size between AP and AC."
    ::= { h3cDot11APTemplateEntry 13 }

h3cDot11APPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { h3cDot11APTemplateEntry 14 }

h3cDot11APElementID OBJECT-TYPE
    SYNTAX      Integer32
    MAX-ACCESS  read-only
    STATUS      current
    DESCRIPTION
        "This object represents the AP element ID."
    ::= { h3cDot11APTemplateEntry 15 }

h3cDot11APDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services.  When an AP works
         in monitor mode, that is, the value of object h3cDot11APWorkMode is
         monitor, device detection can not be enabled with object
         h3cDot11APDevDetectEnable."
    DEFVAL      { false }
    ::= { h3cDot11APTemplateEntry 16 }

h3cDot11APGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { h3cDot11APTemplateEntry 17 }

h3cDot11StatisIntervMode OBJECT-TYPE
    SYNTAX      INTEGER
    {
        normal(1),
        realtime(2)
    }
    MAX-ACCESS  read-create
    STATUS      current
    DESCRIPTION
        "This object represents the mode of statics interval.
         normal    - statics interval value between 10s to 120s
         realtime  - statics interval value between 2s to 5s"
    DEFVAL      { normal }
    ::= { h3cDot11APTemplateEntry 18 }

h3cDot11ApTrapEnabled OBJECT-TYPE
    SYNTAX      TruthValue
    MAX-ACCESS  read-write
    STATUS      current
    DESCRIPTION
        "Represents whether the trap status is enabled or not.
        'true'  : Enable  the trap status;
        'false' : Disable the trap status."
    DEFVAL      { true }
    ::= { h3cDot11APTemplateEntry 19 }

-- *****************************************************************************
-- *  End of  h3cDot11APTemplateTable Definition
-- *****************************************************************************

-- *****************************************************************************
-- *  h3cDot11RadioToConfigTable Definition
-- *****************************************************************************
h3cDot11RadioToConfigTable OBJECT-TYPE
    SYNTAX      SEQUENCE OF H3cDot11RadioToConfigEntry
    MAX-ACCESS  not-accessible
    STATUS      current
    DESCRIPTION
        "Before AP connects to AC, administrator will configure radio
        parameter to each radio."
    ::= { h3cDot11APConfigGroup 2 }

h3cDot11RadioToConfigEntry OBJECT-TYPE
    SYNTAX      H3cDot11RadioToConfigEntry
    MAX-ACCESS  not-accessible
    STATUS      current
    DESCRIPTION
        "Each entry contains configuration information for each radio."
    INDEX
        {
            h3cDot11APTemplateNameCfg,
            h3cDot11CfgRadioID
        }
    ::= { h3cDot11RadioToConfigTable 1 }

H3cDot11RadioToConfigEntry ::= SEQUENCE
    {
        h3cDot11APTemplateNameCfg     OCTET STRING,
        h3cDot11CfgRadioID            H3cDot11RadioScopeType,
        h3cDot11CfgRadioPolicyName    OCTET STRING,
        h3cDot11CfgRadioType          H3cDot11RadioType,
        h3cDot11CfgChannel            H3cDot11ChannelScopeType,
        h3cDot11CfgMaxTxPowerLevel    H3cDot11TxPwrLevelScopeType,
        h3cDot11PreambleLen           H3cDot11PreambleType,
        h3cDot11CfgRadioStatus        TruthValue,
        h3cDot11CfgRdElementID        Unsigned32,
        h3cDot11CfgWorkMode           H3cDot11WorkMode,
        h3cDot11CfgPwrAttValue        Integer32,
        h3cDot11RadioTxArithmetic     INTEGER,
        h3cDot11CfgChannelLockStat    INTEGER,
        h3cDot11CfgPowerLockStat      INTEGER,
        h3cDot11CfgLBRdGroupId        Unsigned32,
        h3cDot11CfgRRMSDRdGroupId     Unsigned32,
        h3cDot11CfgRadioType2         H3cDot11RadioType2,
        h3cDot11CfgIDSEnable          TruthValue,
        h3cDot11CfgSaEnable           TruthValue,
        h3cDot11CfgSaCltRtFFTData     TruthValue,
        h3cDot11CfgSaBand             INTEGER
    }

h3cDot11APTemplateNameCfg OBJECT-TYPE
    SYNTAX      OCTET STRING(SIZE(0..127))
    MAX-ACCESS  not-accessible
    STATUS      current
    DESCRIPTION
        "Represents the name of AP template."
    ::= { h3cDot11RadioToConfigEntry 1 }

h3cDot11CfgRadioID OBJECT-TYPE
    SYNTAX      H3cDot11RadioScopeType
    MAX-ACCESS  not-accessible
    STATUS      current
    DESCRIPTION
        "Represents each radio."
    ::= { h3cDot11RadioToConfigEntry 2 }

h3cDot11CfgRadioPolicyName OBJECT-TYPE
    SYNTAX      OCTET STRING
    MAX-ACCESS  read-write
    STATUS      current
    DESCRIPTION
        "Represents the name of radio policy."
    ::= { h3cDot11RadioToConfigEntry 3 }

h3cDot11CfgRadioType OBJECT-TYPE
    SYNTAX      H3cDot11RadioType
    MAX-ACCESS  read-write
    STATUS      current
    DESCRIPTION
        "Represents the radio will work with which 802.11 radio type."
    ::= { h3cDot11RadioToConfigEntry 4 }

h3cDot11CfgChannel OBJECT-TYPE
    SYNTAX      H3cDot11ChannelScopeType
    MAX-ACCESS  read-write
    STATUS      current
    DESCRIPTION
        "Represents the channel allocation of radio."
    ::= { h3cDot11RadioToConfigEntry 5 }

h3cDot11CfgMaxTxPowerLevel OBJECT-TYPE
    SYNTAX      H3cDot11TxPwrLevelScopeType
    UNITS       "dbm"
    MAX-ACCESS  read-write
    STATUS      current
    DESCRIPTION
        "Represents the maximal transmit power scope for AP."
    ::= { h3cDot11RadioToConfigEntry 6 }

h3cDot11PreambleLen OBJECT-TYPE
    SYNTAX      H3cDot11PreambleType
    MAX-ACCESS  read-write
    STATUS      current
    DESCRIPTION
        "Represents whether use long or short preamble for 802.11 MAC
        frame.
        When h3cDot11CfgRadioType is either dot11b or dot11g,
        then value for h3cDot11PreambleLen will be valid.
        Othwise, the value for it will be invalid."
    DEFVAL      { short }
    ::= { h3cDot11RadioToConfigEntry 7 }

h3cDot11CfgRadioStatus OBJECT-TYPE
    SYNTAX      TruthValue
    MAX-ACCESS  read-write
    STATUS      current
    DESCRIPTION
        "Represents the radio admin status whether is enabled
        or disabled."
    ::= { h3cDot11RadioToConfigEntry 8 }

h3cDot11CfgRdElementID OBJECT-TYPE
    SYNTAX      Unsigned32
    MAX-ACCESS  read-only
    STATUS      current
    DESCRIPTION
        "Represents the element ID of this radio.  It comprises two parts.
        The highest 24 bits are AP element ID and the lowest 8 bits are
        radio ID."
    ::= { h3cDot11RadioToConfigEntry 9 }

h3cDot11CfgWorkMode OBJECT-TYPE
    SYNTAX      H3cDot11WorkMode
    MAX-ACCESS  read-write
    STATUS      current
    DESCRIPTION
        "Represents work mode of the radio."
    ::= { h3cDot11RadioToConfigEntry 10 }

h3cDot11CfgPwrAttValue OBJECT-TYPE
    SYNTAX      Integer32
    MAX-ACCESS  read-write
    STATUS      current
    DESCRIPTION
        "Represents the value of power attenuation."
    ::= { h3cDot11RadioToConfigEntry 11 }

h3cDot11RadioTxArithmetic OBJECT-TYPE
    SYNTAX      INTEGER
        {
            quality(1),
            bandwidth(2)
        }
    MAX-ACCESS  read-write
    STATUS      current
    DESCRIPTION
        "Represents the transmission arithmetic of the radio.
        The following values are supported:
        quality(1)  - Consider the quality first during the transmission.
        bandwidth(2) - Consider the bandwidth first during the transmission."
    DEFVAL      { quality }
    ::= { h3cDot11RadioToConfigEntry 12 }

h3cDot11CfgChannelLockStat OBJECT-TYPE
    SYNTAX      INTEGER
        {
            unlocked(1),
            locked(2)
        }
    MAX-ACCESS  read-write
    STATUS      current
    DESCRIPTION
        "Represents locked status of channel on the radio."
    DEFVAL      { unlocked }
    ::= { h3cDot11RadioToConfigEntry 13 }

h3cDot11CfgPowerLockStat OBJECT-TYPE
    SYNTAX      INTEGER
        {
            unlocked(1),
            locked(2)
        }
    MAX-ACCESS  read-write
    STATUS      current
    DESCRIPTION
        "Represents locked status of power on the radio."
    DEFVAL      { unlocked }
    ::= { h3cDot11RadioToConfigEntry 14 }

h3cDot11CfgLBRdGroupId OBJECT-TYPE
    SYNTAX      Unsigned32
    MAX-ACCESS  read-write
    STATUS      current
    DESCRIPTION
        "Represents the load balance group ID allocated for the radio."
    ::= { h3cDot11RadioToConfigEntry 15 }

h3cDot11CfgRRMSDRdGroupId OBJECT-TYPE
    SYNTAX      Unsigned32
    MAX-ACCESS  read-write
    STATUS      current
    DESCRIPTION
        "Represents the RRM self-decisive group ID allocated for the radio."
    ::= { h3cDot11RadioToConfigEntry 16 }

h3cDot11CfgRadioType2 OBJECT-TYPE
    SYNTAX      H3cDot11RadioType2
    MAX-ACCESS  read-write
    STATUS      current
    DESCRIPTION
        "Represents the radio will work with which 802.11 radio type."
    ::= { h3cDot11RadioToConfigEntry 17 }

h3cDot11CfgIDSEnable OBJECT-TYPE
    SYNTAX      TruthValue
    MAX-ACCESS  read-write
    STATUS      current
    DESCRIPTION
        "Represents whether intrusion detection is enabled for this radio."
    ::= { h3cDot11RadioToConfigEntry 18 }

h3cDot11CfgSaEnable OBJECT-TYPE
    SYNTAX      TruthValue
    MAX-ACCESS  read-write
    STATUS      current
    DESCRIPTION
        "Represents whether spectrum analysis is enabled."
    ::= { h3cDot11RadioToConfigEntry 19 }

h3cDot11CfgSaCltRtFFTData OBJECT-TYPE
    SYNTAX      TruthValue
    MAX-ACCESS  read-write
    STATUS      current
    DESCRIPTION
        "Represents whether to collect real-time FFT data for this radio."
    ::= { h3cDot11RadioToConfigEntry 20 }

h3cDot11CfgSaBand OBJECT-TYPE
    SYNTAX      INTEGER{
       dot11g(1),
       dot11aLower(2),
       dot11aMiddle(3),
       dot11aUpper(4)
    }
    MAX-ACCESS  read-write
    STATUS      current
    DESCRIPTION
        "Represents which band of channels will be monitored when collection
        real-time FFT data is enabled for this radio.  Detection of
        interference devices and air quality will also be affected.  Each band
        responds to the following channels.
         dot11g (Channels 1-14)
         dot11aLower (channels 36-64)
         dot11aMiddle (channels 100-140)
         dot11aUpper (channels 149-165)."
    ::= { h3cDot11RadioToConfigEntry 21 }

-- *****************************************************************************
-- *  End of  h3cDot11RadioToConfigTable Definition
-- *****************************************************************************

-- *****************************************************************************
-- *  h3cDot11APServiceSetTable Definition
-- *****************************************************************************
h3cDot11APServiceSetTable OBJECT-TYPE
    SYNTAX      SEQUENCE OF H3cDot11APServiceSetEntry
    MAX-ACCESS  not-accessible
    STATUS      current
    DESCRIPTION
        "For each radio, it could configure multiple service policies.
        The table describes the relationship between radio and
        service policies."
    ::= { h3cDot11APConfigGroup 3 }

h3cDot11APServiceSetEntry OBJECT-TYPE
    SYNTAX      H3cDot11APServiceSetEntry
    MAX-ACCESS  not-accessible
    STATUS      current
    DESCRIPTION
        "Each entry contains service policy information for each
        specific radio of AP."
    INDEX
        {
            h3cDot11APTemplateNameCfg,
            h3cDot11CfgRadioID,
            h3cDot11CfgServicePolicyID
        }
    ::= { h3cDot11APServiceSetTable 1 }

H3cDot11APServiceSetEntry ::= SEQUENCE
    {
        h3cDot11CfgServicePolicyID    H3cDot11ServicePolicyIDType,
        h3cDot11SrvSetRowStatus       RowStatus,
        h3cDot11ServiceSetVlanId      Integer32
    }

h3cDot11CfgServicePolicyID OBJECT-TYPE
    SYNTAX      H3cDot11ServicePolicyIDType
    MAX-ACCESS  not-accessible
    STATUS      current
    DESCRIPTION
        "Represents the ID of each service policy used by the AP."
    ::= { h3cDot11APServiceSetEntry 1 }

h3cDot11SrvSetRowStatus OBJECT-TYPE
    SYNTAX      RowStatus
    MAX-ACCESS  read-create
    STATUS      current
    DESCRIPTION
        "The status of this table entry."
    ::= { h3cDot11APServiceSetEntry 2 }

h3cDot11ServiceSetVlanId OBJECT-TYPE
    SYNTAX      Integer32(0..4094)
    MAX-ACCESS  read-create
    STATUS      current
    DESCRIPTION
        "Represents the Vlan ID of BSS which is generated when service policy
        is binded with the Radio."
    ::= { h3cDot11APServiceSetEntry 3 }
-- *****************************************************************************
-- * End of h3cDot11APServiceSetTable Definition
-- *****************************************************************************

-- *****************************************************************************
-- *  h3cDot11APSTVlanTable Definition
-- *****************************************************************************
h3cDot11APSTVlanTable OBJECT-TYPE
    SYNTAX      SEQUENCE OF H3cDot11APSTVlanEntry
    MAX-ACCESS  not-accessible
    STATUS      current
    DESCRIPTION
        "For each service policy, it could be bind to several VLANs.
        The table describes the relationship between VLAN and
        service policies."
    ::= { h3cDot11APConfigGroup 11 }

h3cDot11APSTVlanEntry OBJECT-TYPE
    SYNTAX      H3cDot11APSTVlanEntry
    MAX-ACCESS  not-accessible
    STATUS      current
    DESCRIPTION
        "Each entry contains VLAN and service policy information for each
        specific radio of AP."
    INDEX
        {
            h3cDot11SIDAPSerialID,
            h3cDot11CfgRadioID,
            h3cDot11CfgServicePolicyID
        }
    ::= { h3cDot11APSTVlanTable 1 }

H3cDot11APSTVlanEntry ::= SEQUENCE
    {
        h3cDot11CfgSTVLANID           Integer32,
        h3cDot11CfgSTNASPortID        OCTET STRING,
        h3cDot11CfgServiceSetRowStatus    RowStatus
    }

h3cDot11CfgSTVLANID OBJECT-TYPE
    SYNTAX      Integer32(0..4094)
    MAX-ACCESS  read-create
    STATUS      current
    DESCRIPTION
        "Represents the VLAN that current Service Policy have bind to."
    ::= { h3cDot11APSTVlanEntry 1 }

h3cDot11CfgSTNASPortID OBJECT-TYPE
    SYNTAX      OCTET STRING(SIZE(0..127))
    MAX-ACCESS  read-only
    STATUS      current
    DESCRIPTION
        "Represents the NAS Port ID of current Service Policy for each
        specific radio of AP."
    ::= { h3cDot11APSTVlanEntry 2 }

h3cDot11CfgServiceSetRowStatus OBJECT-TYPE
    SYNTAX      RowStatus
    MAX-ACCESS  read-create
    STATUS      current
    DESCRIPTION
        "The status of this table entry."
    ::= { h3cDot11APSTVlanEntry 3 }
-- *****************************************************************************
-- * End of h3cDot11APSTVlanTable Definition
-- *****************************************************************************

-- *****************************************************************************
-- *  h3cDot11APSysInfoSetTable Definition
-- *****************************************************************************
h3cDot11APSysInfoSetTable OBJECT-TYPE
    SYNTAX      SEQUENCE OF H3cDot11APSysInfoSetEntry
    MAX-ACCESS  not-accessible
    STATUS      current
    DESCRIPTION
        "The table of the system information for each AP."
    ::= { h3cDot11APConfigGroup 4 }

h3cDot11APSysInfoSetEntry OBJECT-TYPE
    SYNTAX      H3cDot11APSysInfoSetEntry
    MAX-ACCESS  not-accessible
    STATUS      current
    DESCRIPTION
        "The system information configuration for each AP."
    INDEX
        {
            h3cDot11SIDAPSerialID
        }
    ::= { h3cDot11APSysInfoSetTable 1 }

H3cDot11APSysInfoSetEntry ::= SEQUENCE
    {
        h3cDot11APSysNetID            OCTET STRING,
        h3cDot11APCpuUsageThreshold   Integer32,
        h3cDot11APMemUsageThreshold   Integer32
    }

h3cDot11APSysNetID OBJECT-TYPE
    SYNTAX      OCTET STRING(SIZE(0..127))
    MAX-ACCESS  read-write
    STATUS      current
    DESCRIPTION
        "Represents the system Net ID for AP."
    ::= { h3cDot11APSysInfoSetEntry 1 }

h3cDot11APCpuUsageThreshold OBJECT-TYPE
    SYNTAX      Integer32(0..100)
    UNITS       "onepercent"
    MAX-ACCESS  read-write
    STATUS      current
    DESCRIPTION
        "The CPU usage threshold for AP."
    ::= { h3cDot11APSysInfoSetEntry 2 }

h3cDot11APMemUsageThreshold OBJECT-TYPE
    SYNTAX      Integer32(0..100)
    UNITS       "onepercent"
    MAX-ACCESS  read-write
    STATUS      current
    DESCRIPTION
        "The memory usage threshold for AP."
    ::= { h3cDot11APSysInfoSetEntry 3 }

-- *****************************************************************************
-- * End of h3cDot11APSysInfoSetTable Definition
-- *****************************************************************************

-- *****************************************************************************
-- *  h3cDot11APLimitTable Definition
-- *****************************************************************************
h3cDot11APLimitTable OBJECT-TYPE
    SYNTAX      SEQUENCE OF H3cDot11APLimitEntry
    MAX-ACCESS  not-accessible
    STATUS      current
    DESCRIPTION
        "For each connected APs, administrator could configure a series of
        limits.  This table describes the limit information for AP(s)."
    ::= { h3cDot11APConfigGroup 5 }

h3cDot11APLimitEntry OBJECT-TYPE
    SYNTAX      H3cDot11APLimitEntry
    MAX-ACCESS  not-accessible
    STATUS      current
    DESCRIPTION
        "Each entry contains the limit information for each AP."
    INDEX
        {
            h3cDot11APElementIndex
        }
    ::= { h3cDot11APLimitTable 1 }

H3cDot11APLimitEntry ::= SEQUENCE
    {
        h3cDot11APSsidNumLimit     Integer32,
        h3cDot11APUserCntLimit     Integer32,
        h3cDot11APUserThreshold    Integer32
    }

h3cDot11APSsidNumLimit OBJECT-TYPE
    SYNTAX      Integer32(0..65535)
    MAX-ACCESS  read-write
    STATUS      current
    DESCRIPTION
        "Represents the upper limit of service template binded
        with this AP.  All radios of AP share this limit.
        Default value 0 : There is no upper limit of service template
        binded with this AP."
    DEFVAL      { 0 }
    ::= { h3cDot11APLimitEntry 1 }

h3cDot11APUserCntLimit OBJECT-TYPE
    SYNTAX      Integer32(0..65535)
    MAX-ACCESS  read-write
    STATUS      current
    DESCRIPTION
        "Represents the upper limit of user which has access to this AP.
        All BSSs binded with AP share this limit.
        Default value 0 : There is no upper limit of user which has access
        to this AP."
    DEFVAL      { 0 }
    ::= { h3cDot11APLimitEntry 2 }

h3cDot11APUserThreshold OBJECT-TYPE
    SYNTAX      Integer32(0..65535)
    MAX-ACCESS  read-write
    STATUS      current
    DESCRIPTION
        "Represents the threshold of user which has access to this
        AP.  All BSSs binded with AP share this limit.  If the user counter
        is overflow, the trap will be sent.
        Default value 0 : There is no threshold of user which has access
        to this AP."
    DEFVAL      { 0 }
    ::= { h3cDot11APLimitEntry 3 }
-- *****************************************************************************
-- * End of h3cDot11APLimitTable Definition
-- *****************************************************************************

-- *****************************************************************************
-- * h3cDot11APIfSetTable Definition
-- *****************************************************************************
h3cDot11APIfSetTable OBJECT-TYPE
    SYNTAX      SEQUENCE OF H3cDot11APIfSetEntry
    MAX-ACCESS  not-accessible
    STATUS      current
    DESCRIPTION
        "The table of the interface information for each AP."
    ::= { h3cDot11APConfigGroup 6 }

h3cDot11APIfSetEntry OBJECT-TYPE
    SYNTAX      H3cDot11APIfSetEntry
    MAX-ACCESS  not-accessible
    STATUS      current
    DESCRIPTION
        "The interface information configuration for each AP."
    INDEX
        {
            h3cDot11APElementIndex,
            h3cDot11APSetIfIndex
        }
    ::= { h3cDot11APIfSetTable 1 }

H3cDot11APIfSetEntry ::= SEQUENCE
    {
        h3cDot11APSetIfIndex      Integer32,
        h3cDot11APIfAlias         DisplayString
    }

h3cDot11APSetIfIndex OBJECT-TYPE
    SYNTAX      Integer32
    MAX-ACCESS  not-accessible
    STATUS      current
    DESCRIPTION
        "Represents the index for a interface."
    ::= { h3cDot11APIfSetEntry 1 }

h3cDot11APIfAlias OBJECT-TYPE
    SYNTAX      DisplayString
    MAX-ACCESS  read-write
    STATUS      current
    DESCRIPTION
        "This object is an 'alias' name for the interface as specified
        by a network manager for AP."
    ::= { h3cDot11APIfSetEntry 2 }

-- *****************************************************************************
-- * End of h3cDot11APIfSetTable Definition
-- *****************************************************************************

-- *****************************************************************************
-- *  h3cDot11APServiceVlanTable Definition
-- *****************************************************************************
h3cDot11APServiceVlanTable OBJECT-TYPE
    SYNTAX      SEQUENCE OF H3cDot11APServiceVlanEntry
    MAX-ACCESS  not-accessible
    STATUS      current
    DESCRIPTION
        "For all the radios on the AP, it could configure multiple service policies.
        The table describes the relationship between AP and
        service policies."
    ::= { h3cDot11APConfigGroup 7 }

h3cDot11APServiceVlanEntry OBJECT-TYPE
    SYNTAX      H3cDot11APServiceVlanEntry
    MAX-ACCESS  not-accessible
    STATUS      current
    DESCRIPTION
        "Each entry contains service policy information for each AP."
    INDEX
        {
            h3cDot11APServiceVlanSerialID,
            h3cDot11APServiceVlanSPID
        }
    ::= { h3cDot11APServiceVlanTable 1 }

H3cDot11APServiceVlanEntry ::= SEQUENCE
    {
        h3cDot11APServiceVlanSerialID          OCTET STRING,
        h3cDot11APServiceVlanSPID              H3cDot11ServicePolicyIDType,
        h3cDot11APServiceVlanId                Integer32,
        h3cDot11APServiceVlanRowStatus         RowStatus

    }

h3cDot11APServiceVlanSerialID OBJECT-TYPE
    SYNTAX      OCTET STRING
    MAX-ACCESS  not-accessible
    STATUS      current
    DESCRIPTION
        "This object represents AP serial id."
    ::= { h3cDot11APServiceVlanEntry 1 }

h3cDot11APServiceVlanSPID OBJECT-TYPE
    SYNTAX      H3cDot11ServicePolicyIDType
    MAX-ACCESS  not-accessible
    STATUS      current
    DESCRIPTION
        "This object represents the ID of each service policy used by the AP."
    ::= { h3cDot11APServiceVlanEntry 2 }

h3cDot11APServiceVlanId OBJECT-TYPE
    SYNTAX      Integer32(0..4094)
    MAX-ACCESS  read-create
    STATUS      current
    DESCRIPTION
        "This object represents the VLAN ID of BSS which is generated when the
         service policy is bound to the radio."
    ::= { h3cDot11APServiceVlanEntry 3 }

h3cDot11APServiceVlanRowStatus OBJECT-TYPE
    SYNTAX      RowStatus
    MAX-ACCESS  read-create
    STATUS      current
    DESCRIPTION
        "This object represents the status of this table entry."
    ::= { h3cDot11APServiceVlanEntry 4 }

-- *****************************************************************************
-- * End of h3cDot11APServiceSetTable Definition
-- *****************************************************************************

-- *****************************************************************************
-- *  h3cDot11RadioConfigTable Definition
-- *****************************************************************************
h3cDot11RadioConfigTable OBJECT-TYPE
    SYNTAX      SEQUENCE OF H3cDot11RadioConfigEntry
    MAX-ACCESS  not-accessible
    STATUS      current
    DESCRIPTION
        "Before AP connects to AC, administrator will configure radio
        parameter to each radio."
    ::= { h3cDot11APConfigGroup 8 }

h3cDot11RadioConfigEntry OBJECT-TYPE
    SYNTAX      H3cDot11RadioConfigEntry
    MAX-ACCESS  not-accessible
    STATUS      current
    DESCRIPTION
        "Each entry contains configuration information for each radio."
    INDEX
        {
            h3cDot11RCAPSerialID,
            h3cDot11RCRadioID
        }
    ::= { h3cDot11RadioConfigTable 1 }

H3cDot11RadioConfigEntry ::= SEQUENCE
    {
        h3cDot11RCAPSerialID               OCTET STRING,
        h3cDot11RCRadioID                  H3cDot11RadioScopeType,
        h3cDot11RCRadioType                H3cDot11RadioType,
        h3cDot11RCChannel                  H3cDot11ChannelScopeType,
        h3cDot11RCPreambleLen              H3cDot11PreambleType,
        h3cDot11RCPwrAttValue              Integer32,
        h3cDot11RCApPowerLevel             H3cDot11TxPwrLevelScopeType,
        h3cDot11RCDynamicChlState          TruthValue,
        h3cDot11RCDynamicPowerState        TruthValue,
        h3cDot11RCRadioStatus              TruthValue,
        h3cDot11RCRadioRate                OCTET STRING,
        h3cDot11RCPwrAdjustStepLength      Integer32,
        h3cDot11RCRadioType2               H3cDot11RadioType2
    }

h3cDot11RCAPSerialID OBJECT-TYPE
    SYNTAX      OCTET STRING(SIZE(0..127))
    MAX-ACCESS  not-accessible
    STATUS      current
    DESCRIPTION
        "This object represents the Serial ID of AP."
    ::= { h3cDot11RadioConfigEntry 1 }

h3cDot11RCRadioID OBJECT-TYPE
    SYNTAX      H3cDot11RadioScopeType
    MAX-ACCESS  not-accessible
    STATUS      current
    DESCRIPTION
        "This object represents each radio."
    ::= { h3cDot11RadioConfigEntry 2 }

h3cDot11RCRadioType OBJECT-TYPE
    SYNTAX      H3cDot11RadioType
    MAX-ACCESS  read-write
    STATUS      current
    DESCRIPTION
        "This object represents the radio will work with which 802.11 radio
         type."
    ::= { h3cDot11RadioConfigEntry 3 }

h3cDot11RCChannel OBJECT-TYPE
    SYNTAX      H3cDot11ChannelScopeType
    MAX-ACCESS  read-write
    STATUS      current
    DESCRIPTION
        "This object represents the channel allocation of radio."
    ::= { h3cDot11RadioConfigEntry 4 }

h3cDot11RCPreambleLen OBJECT-TYPE
    SYNTAX      H3cDot11PreambleType
    MAX-ACCESS  read-write
    STATUS      current
    DESCRIPTION
        "This object represents whether use long or short preamble for 802.11
         MAC frame.
        When h3cDot11CfgRadioType is either dot11b or dot11g,
        then value for h3cDot11PreambleLen will be valid.
        Otherwise, the value for it will be invalid."
    DEFVAL      { short }
    ::= { h3cDot11RadioConfigEntry 5 }

h3cDot11RCPwrAttValue OBJECT-TYPE
    SYNTAX      Integer32
    MAX-ACCESS  read-write
    STATUS      current
    DESCRIPTION
        "This object represents the value of power attenuation."
    ::= { h3cDot11RadioConfigEntry 6 }

h3cDot11RCApPowerLevel OBJECT-TYPE
    SYNTAX      H3cDot11TxPwrLevelScopeType
    UNITS       "dbm"
    MAX-ACCESS  read-write
    STATUS      current
    DESCRIPTION
        "Represents the maximal transmit power scope for AP."
    ::= { h3cDot11RadioConfigEntry 7 }

h3cDot11RCDynamicChlState OBJECT-TYPE
    SYNTAX      TruthValue
    MAX-ACCESS  read-write
    STATUS      current
    DESCRIPTION
        "Enable/Disable dynamic channel selection."
    ::= { h3cDot11RadioConfigEntry 8 }

h3cDot11RCDynamicPowerState OBJECT-TYPE
    SYNTAX      TruthValue
    MAX-ACCESS  read-write
    STATUS      current
    DESCRIPTION
        "Enable/Disable dynamic power selection for the band."
    ::= { h3cDot11RadioConfigEntry 9 }

h3cDot11RCRadioStatus OBJECT-TYPE
    SYNTAX      TruthValue
    MAX-ACCESS  read-write
    STATUS      current
    DESCRIPTION
        "Represents the radio admin status whether is enabled
        or disabled."
    ::= { h3cDot11RadioConfigEntry 10 }

h3cDot11RCRadioRate OBJECT-TYPE
    SYNTAX      OCTET STRING(SIZE(0..255))
    MAX-ACCESS  read-write
    STATUS      current
    DESCRIPTION
        "Set data transmit rates for the radio, in the format of 1,2,5.5...
        For 802.11n radios, the format can be MCS X. The data transmit rates
        between AP and STA must fall into the configured rates.
        (Note: For 802.11n radios, the first value will be treated as a mandatory rate,
        and the second value will be treated as a supported rate.
        If you configure more than two rates, the configuration cannot take effect.
        If you configure only one rate, it is considered as the mandatory rate by default.)"
    ::= { h3cDot11RadioConfigEntry 11 }

h3cDot11RCPwrAdjustStepLength OBJECT-TYPE
    SYNTAX      Integer32
    MAX-ACCESS  read-only
    STATUS      current
    DESCRIPTION
        "Power adjustment step-length in dBm."
    ::= { h3cDot11RadioConfigEntry 12 }

h3cDot11RCRadioType2 OBJECT-TYPE
    SYNTAX      H3cDot11RadioType2
    MAX-ACCESS  read-write
    STATUS      current
    DESCRIPTION
        "This object represents the radio will work with which 802.11 radio
         type."
    ::= { h3cDot11RadioConfigEntry 13 }

-- *****************************************************************************
-- * End of h3cDot11RadioConfigTable Definition
-- *****************************************************************************

h3cDot11RadioSSIDCfgTable OBJECT-TYPE
    SYNTAX      SEQUENCE OF H3cDot11RadioSSIDCfgEntry
    MAX-ACCESS  not-accessible
    STATUS      current
    DESCRIPTION
        "For each radio, it could configure multiple service policies.
        The table describes the relationship between radio and
        service policies."
    ::= { h3cDot11APConfigGroup 9 }

h3cDot11RadioSSIDCfgEntry OBJECT-TYPE
    SYNTAX      H3cDot11RadioSSIDCfgEntry
    MAX-ACCESS  not-accessible
    STATUS      current
    DESCRIPTION
        "Each entry contains SSID configuration information for each radio."
    INDEX
        {
            h3cDot11RadioSSIDSerialID,
            h3cDot11RadioSSIDRadioID,
            h3cDot11RadioSSIDWLANID
        }
    ::= { h3cDot11RadioSSIDCfgTable 1 }

H3cDot11RadioSSIDCfgEntry ::= SEQUENCE
    {
        h3cDot11RadioSSIDSerialID    H3cDot11ObjectIDType,
        h3cDot11RadioSSIDRadioID     H3cDot11RadioScopeType,
        h3cDot11RadioSSIDWLANID      Integer32,
        h3cDot11RadioSSIDIndex       H3cDot11ServicePolicyIDType,
        h3cDot11RadioBSSID           MacAddress,
        h3cDot11RadioSSIDRowStatus   RowStatus
    }

h3cDot11RadioSSIDSerialID OBJECT-TYPE
    SYNTAX      H3cDot11ObjectIDType
    MAX-ACCESS  not-accessible
    STATUS      current
    DESCRIPTION
        "This object represents the serial ID of AP."
    ::= { h3cDot11RadioSSIDCfgEntry 1 }

h3cDot11RadioSSIDRadioID OBJECT-TYPE
    SYNTAX      H3cDot11RadioScopeType
    MAX-ACCESS  not-accessible
    STATUS      current
    DESCRIPTION
        "This object represents each radio."
    ::= { h3cDot11RadioSSIDCfgEntry 2 }

h3cDot11RadioSSIDWLANID OBJECT-TYPE
    SYNTAX      Integer32
    MAX-ACCESS  not-accessible
    STATUS      current
    DESCRIPTION
        "This object represents the WLAN ID of the BSSID."
    ::= { h3cDot11RadioSSIDCfgEntry 3 }

h3cDot11RadioSSIDIndex OBJECT-TYPE
    SYNTAX      H3cDot11ServicePolicyIDType
    MAX-ACCESS  read-create
    STATUS      current
    DESCRIPTION
        "This object represents the ID of each service policy used by the
         radio."
    ::= { h3cDot11RadioSSIDCfgEntry 4 }

h3cDot11RadioBSSID OBJECT-TYPE
    SYNTAX      MacAddress
    MAX-ACCESS  read-only
    STATUS      current
    DESCRIPTION
        "As MAC address format, it is used to identify BSS."
    ::= { h3cDot11RadioSSIDCfgEntry 5 }

h3cDot11RadioSSIDRowStatus OBJECT-TYPE
    SYNTAX      RowStatus
    MAX-ACCESS  read-create
    STATUS      current
    DESCRIPTION
        "RowStatus."
    ::= { h3cDot11RadioSSIDCfgEntry 6 }

-- *****************************************************************************
-- *  h3cDot11APSerialIDTable Definition
-- *****************************************************************************

h3cDot11APSerialIDTable OBJECT-TYPE
    SYNTAX      SEQUENCE OF H3cDot11APSerialIDEntry
    MAX-ACCESS  not-accessible
    STATUS      current
    DESCRIPTION
        "The table will provide the general information about APs."
    ::= { h3cDot11APConfigGroup 10 }

h3cDot11APSerialIDEntry OBJECT-TYPE
    SYNTAX      H3cDot11APSerialIDEntry
    MAX-ACCESS  not-accessible
    STATUS      current
    DESCRIPTION
        "Each entry contains the general information of an AP."
    INDEX
        {
            h3cDot11SIDAPSerialID
        }
    ::= { h3cDot11APSerialIDTable 1 }

H3cDot11APSerialIDEntry ::= SEQUENCE
    {
        h3cDot11SIDAPSerialID               OCTET STRING,
        h3cDot11SIDAPWorkMode               INTEGER,
        h3cDot11SIDAPGetIPMethod            INTEGER,
        h3cDot11SIDAPTemplateName           OCTET STRING,
        h3cDot11SIDModelAlias               OCTET STRING,
        h3cDot11SIDAPDescription            OCTET STRING,
        h3cDot11SIDRowStatus                RowStatus,
        h3cDot11SIDAPName                   OCTET STRING,
        h3cDot11SIDStatisInterv             Integer32,
        h3cDot11SIDAPBroadcastProbeReply    TruthValue,
        h3cDot11SIDAPStaIdleTimerInterv     Integer32,
        h3cDot11SIDStaKeepAliveTimerInterv  Integer32,
        h3cDot11SIDAPCir                    Integer32,
        h3cDot11SIDAPCbs                    Integer32,
        h3cDot11SIDAPPriorityLevel          Integer32,
        h3cDot11SIDAPElementID              Integer32,
        h3cDot11SIDAPDevDetectEnable        TruthValue,
        h3cDot11SIDAPStatisIntervMode       INTEGER
    }

h3cDot11SIDAPSerialID OBJECT-TYPE
    SYNTAX      OCTET STRING
    MAX-ACCESS  not-accessible
    STATUS      current
    DESCRIPTION
        "Represents AP serial id."
    ::= { h3cDot11APSerialIDEntry 1 }

h3cDot11SIDAPWorkMode OBJECT-TYPE
    SYNTAX      INTEGER
        {
            normal(1),
            monitor(2),
            hybrid(3)
        }
    MAX-ACCESS  read-create
    STATUS      current
    DESCRIPTION
        "Represents what work mode for AP.
        The following values are supported:
        normal   - AP will supply WLAN service.
        monitor  - AP will be a monitor to find attack.
        hybrid   - AP will supply WLAN service and Device detection is
        enabled."
    DEFVAL      { normal }
    ::= { h3cDot11APSerialIDEntry 2 }

h3cDot11SIDAPGetIPMethod OBJECT-TYPE
    SYNTAX      INTEGER
    {
        dhcpAlloc(1),
        static(2)
    }
    MAX-ACCESS  read-create
    STATUS      current
    DESCRIPTION
        "This object represents the method how AP gets IP address."
    DEFVAL      { dhcpAlloc }
    ::= { h3cDot11APSerialIDEntry 3 }
h3cDot11SIDAPTemplateName OBJECT-TYPE
    SYNTAX      OCTET STRING
    MAX-ACCESS  read-create
    STATUS      current
    DESCRIPTION
        "Represents the name of AP template."
    ::= { h3cDot11APSerialIDEntry 4 }
h3cDot11SIDModelAlias OBJECT-TYPE
    SYNTAX      OCTET STRING
    MAX-ACCESS  read-create
    STATUS      current
    DESCRIPTION
        "Represents the alias of AP model name."
    ::= { h3cDot11APSerialIDEntry 5 }

h3cDot11SIDAPDescription OBJECT-TYPE
    SYNTAX      OCTET STRING
    MAX-ACCESS  read-create
    STATUS      current
    DESCRIPTION
        "This attribute will give more information about AP.
        Administrator could suggest the location, owner or
        other information for each AP.
        If the value is set to NULL, the description will be removed."
    ::= { h3cDot11APSerialIDEntry 6 }

h3cDot11SIDRowStatus OBJECT-TYPE
    SYNTAX      RowStatus
    MAX-ACCESS  read-create
    STATUS      current
    DESCRIPTION
        "The status of this table entry."
    ::= { h3cDot11APSerialIDEntry 7 }

h3cDot11SIDAPName OBJECT-TYPE
    SYNTAX      OCTET STRING
    MAX-ACCESS  read-create
    STATUS      current
    DESCRIPTION
        "Represents the AP name."
    ::= { h3cDot11APSerialIDEntry 8 }

h3cDot11SIDStatisInterv OBJECT-TYPE
    SYNTAX      Integer32
    UNITS       "second"
    MAX-ACCESS  read-create
    STATUS      current
    DESCRIPTION
        "Represents the interval of radio statistic."
    ::= { h3cDot11APSerialIDEntry 9 }

h3cDot11SIDAPBroadcastProbeReply OBJECT-TYPE
    SYNTAX      TruthValue
    MAX-ACCESS  read-create
    STATUS      current
    DESCRIPTION
        "Represents enable the AP to reply broadcast probe or not.
        'true' : The AP to reply broadcast probe is enabled.
        'false': The AP to reply broadcast probe is disabled"
    DEFVAL      { true }
    ::= { h3cDot11APSerialIDEntry 10 }

h3cDot11SIDAPStaIdleTimerInterv OBJECT-TYPE
    SYNTAX      Integer32
    UNITS       "second"
    MAX-ACCESS  read-create
    STATUS      current
    DESCRIPTION
        "Represents the interval for which the link between AP and STA
        ( power-save or awake ) can be idle."
    ::= { h3cDot11APSerialIDEntry 11 }

h3cDot11SIDStaKeepAliveTimerInterv OBJECT-TYPE
    SYNTAX      Integer32
    UNITS       "second"
    MAX-ACCESS  read-create
    STATUS      current
    DESCRIPTION
        "Represents the interval of the keep alive requests sent between
        AP and STA."
    ::= { h3cDot11APSerialIDEntry 12 }

h3cDot11SIDAPCir OBJECT-TYPE
    SYNTAX      Integer32
    UNITS       "Kbps"
    MAX-ACCESS  read-create
    STATUS      current
    DESCRIPTION
        "Represents the committed information rate between AP and AC."
    ::= { h3cDot11APSerialIDEntry 13 }

h3cDot11SIDAPCbs OBJECT-TYPE
    SYNTAX      Integer32
    UNITS       "Bytes"
    MAX-ACCESS  read-create
    STATUS      current
    DESCRIPTION
        "Represents the committed burst size between AP and AC."
    ::= { h3cDot11APSerialIDEntry 14 }

h3cDot11SIDAPPriorityLevel OBJECT-TYPE
    SYNTAX      Integer32 (0..7)
    MAX-ACCESS  read-create
    STATUS      current
    DESCRIPTION
        "This object represents the connection priority for the AP.
        If the connection priority is 7, the AC is considered as the
        primary AC for the AP."
    DEFVAL      { 4 }
    ::= { h3cDot11APSerialIDEntry 15 }

h3cDot11SIDAPElementID OBJECT-TYPE
    SYNTAX      Integer32
    MAX-ACCESS  read-only
    STATUS      current
    DESCRIPTION
        "This object represents the AP element ID."
    ::= { h3cDot11APSerialIDEntry 16 }

h3cDot11SIDAPDevDetectEnable OBJECT-TYPE
    SYNTAX      TruthValue
    MAX-ACCESS  read-create
    STATUS      current
    DESCRIPTION
        "Represents whether device detection is enabled or not.
         'true' : Device detection is enabled.
         'false': Device detection is disabled.
         If device detection is enabled, the AP will provide both device
         detection and WLAN data services.
         By default, the AP only provides WLAN data services.  When an AP works
         in monitor mode, that is, the value of object h3cDot11APWorkMode is
         monitor, device detection can not be enabled with object
         h3cDot11SIDAPDevDetectEnable."
    DEFVAL      { false }
    ::= { h3cDot11APSerialIDEntry 17 }

h3cDot11SIDAPStatisIntervMode OBJECT-TYPE
    SYNTAX      INTEGER
    {
        normal(1),
        realtime(2)
    }
    MAX-ACCESS  read-create
    STATUS      current
    DESCRIPTION
        "This object represents the mode of statics interval.
         normal    - statics interval value between 10s to 120s
         realtime  - statics interval value between 2s to 5s"
    DEFVAL      { normal }
    ::= { h3cDot11APSerialIDEntry 18 }

-- *****************************************************************************
-- *  h3cDot11RadioIntfConfigTable Definition
-- *****************************************************************************
h3cDot11RadioIntfConfigTable OBJECT-TYPE
    SYNTAX      SEQUENCE OF H3cDot11RadioIntfConfigEntry
    MAX-ACCESS  not-accessible
    STATUS      current
    DESCRIPTION
        "The table defines the parameters for radio in AP, as per
        radio."
    ::= { h3cDot11RadioIntfConfigGroup 1 }

h3cDot11RadioIntfConfigEntry OBJECT-TYPE
    SYNTAX      H3cDot11RadioIntfConfigEntry
    MAX-ACCESS  not-accessible
    STATUS      current
    DESCRIPTION
        "Each entry contains information of each radio in AP."
    INDEX
        {
            h3cDot11RadioIfIdx
        }
    ::= { h3cDot11RadioIntfConfigTable 1 }

H3cDot11RadioIntfConfigEntry ::= SEQUENCE
    {
        h3cDot11RadioIfIdx               Integer32,
        h3cDot11RadioCfgBeaconIntvl      Integer32,
        h3cDot11RadioCfgDtimIntvl        Integer32,
        h3cDot11RadioCfgRtsThreshold     Integer32,
        h3cDot11RadioCfgFragThreshold    Integer32,
        h3cDot11RadioCfgShtRetryThld     Integer32,
        h3cDot11RadioCfglongRtrThld      Integer32,
        h3cDot11RadioCfgMaxRxLifetime    Unsigned32,
        h3cDot11RadioCfgType             H3cDot11RadioType,
        h3cDot11RadioCfgChannel          H3cDot11ChannelScopeType,
        h3cDot11RadioCfgMaxTxPwrLvl      H3cDot11TxPwrLevelScopeType,
        h3cDot11RadioCfgPreambleLen      H3cDot11PreambleType,
        h3cDot11RadioCfgWorkMode         H3cDot11WorkMode,
        h3cDot11RadioCfgOnly11gEnable    TruthValue,
        h3cDot11RadioCfgType2            H3cDot11RadioType2
    }

h3cDot11RadioIfIdx OBJECT-TYPE
    SYNTAX      Integer32
    MAX-ACCESS  not-accessible
    STATUS      current
    DESCRIPTION
        "Represents the Radio IfIndex of radio in AP."
    ::= { h3cDot11RadioIntfConfigEntry 1 }

h3cDot11RadioCfgBeaconIntvl OBJECT-TYPE
    SYNTAX      Integer32
    UNITS       "TU"
    MAX-ACCESS  read-write
    STATUS      current
    DESCRIPTION
        "Represents the interval for Beacon management frame."
    DEFVAL { 100 }
    ::= { h3cDot11RadioIntfConfigEntry 2 }

h3cDot11RadioCfgDtimIntvl OBJECT-TYPE
    SYNTAX      Integer32
    MAX-ACCESS  read-write
    STATUS      current
    DESCRIPTION
        "Represents the number of beacon intervals that shall elapse
        between transmission of Beacons frames containing a Traffic
        Indication Map (TIM) element whose DTIM Count field is 0.
        This value is transmitted in the Delivery TIM (DTIM) Period
        field of Beacon frames."
    DEFVAL { 1 }
    ::= { h3cDot11RadioIntfConfigEntry 3 }

h3cDot11RadioCfgRtsThreshold OBJECT-TYPE
    SYNTAX      Integer32
    UNITS       "Byte"
    MAX-ACCESS  read-write
    STATUS      current
    DESCRIPTION
        "Represents the current minimum size,in octets,of the MAC
        protocol data unit (MPDU), below which a Request to send/Clear
        to send (RTS/CTS) handshake shall not be performed."
    DEFVAL { 2346 }
    ::= { h3cDot11RadioIntfConfigEntry 4 }

h3cDot11RadioCfgFragThreshold OBJECT-TYPE
    SYNTAX      Integer32
    UNITS       "Byte"
    MAX-ACCESS  read-write
    STATUS      current
    DESCRIPTION
        "Represents the current maximum size, in octets, of the MPDU that
        may be delivered to the PHY. A MSDU shall be broken into
        fragments if its size exceeds the value of this attribute after
        adding MAC headers and trailers."
    DEFVAL { 2346 }
    ::= { h3cDot11RadioIntfConfigEntry 5 }

h3cDot11RadioCfgShtRetryThld OBJECT-TYPE
    SYNTAX      Integer32
    MAX-ACCESS  read-write
    STATUS      current
    DESCRIPTION
        "Represents the maximum number of transmission attempts of a
        frame, the length of which is less than or equal to
        h3cDot11RadioRTSThreshold, that shall be made before a failure
        condition is indicated."
    DEFVAL { 5 }
    ::= { h3cDot11RadioIntfConfigEntry 6 }

h3cDot11RadioCfglongRtrThld OBJECT-TYPE
    SYNTAX      Integer32
    MAX-ACCESS  read-write
    STATUS      current
    DESCRIPTION
        "Represents the maximum number of transmission attempts of a
        frame, the length of which is longer than
        h3cDot11RadioRTSThreshold, that shall be made before a
        failure condition is indicated."
    DEFVAL { 5 }
    ::= { h3cDot11RadioIntfConfigEntry 7 }

h3cDot11RadioCfgMaxRxLifetime OBJECT-TYPE
    SYNTAX      Unsigned32
    UNITS       "millisecond"
    MAX-ACCESS  read-write
    STATUS      current
    DESCRIPTION
        "Represents the elapsed time. After the time specified by
        h3cDot11RadioCfgMaxRxLifetime, the further attempts to reassemble
        the MSDU shall be terminated."
    DEFVAL { 2000 }
    ::= { h3cDot11RadioIntfConfigEntry 8 }

h3cDot11RadioCfgType OBJECT-TYPE
    SYNTAX      H3cDot11RadioType
    MAX-ACCESS  read-write
    STATUS      current
    DESCRIPTION
        "Represents the radio will work with which 802.11 radio type."
    ::= { h3cDot11RadioIntfConfigEntry 9 }

h3cDot11RadioCfgChannel OBJECT-TYPE
    SYNTAX      H3cDot11ChannelScopeType
    MAX-ACCESS  read-write
    STATUS      current
    DESCRIPTION
        "Represents the channel allocation of radio."
    DEFVAL { 1 }
    ::= { h3cDot11RadioIntfConfigEntry 10 }

h3cDot11RadioCfgMaxTxPwrLvl OBJECT-TYPE
    SYNTAX      H3cDot11TxPwrLevelScopeType
    UNITS       "dbm"
    MAX-ACCESS  read-write
    STATUS      current
    DESCRIPTION
        "Represents the maximal transmit power scope for AP."
    ::= { h3cDot11RadioIntfConfigEntry 11 }

h3cDot11RadioCfgPreambleLen OBJECT-TYPE
    SYNTAX      H3cDot11PreambleType
    MAX-ACCESS  read-write
    STATUS      current
    DESCRIPTION
        "Represents whether use long or short preamble for 802.11 MAC
        frame."
    DEFVAL { short }
    ::= { h3cDot11RadioIntfConfigEntry 12 }

h3cDot11RadioCfgWorkMode OBJECT-TYPE
    SYNTAX      H3cDot11WorkMode
    MAX-ACCESS  read-write
    STATUS      current
    DESCRIPTION
        "Represents work mode of the radio."
    ::= { h3cDot11RadioIntfConfigEntry 13 }

h3cDot11RadioCfgOnly11gEnable OBJECT-TYPE
    SYNTAX      TruthValue
    MAX-ACCESS  read-write
    STATUS      current
    DESCRIPTION
        "Represents whether enable only 802.11g radio mode or not.
        'true' : Only 802.11g radio mode is enabled.
        'false': Only 802.11g radio mode is disabled."
    DEFVAL { false }
    ::= { h3cDot11RadioIntfConfigEntry 14 }

h3cDot11RadioCfgType2 OBJECT-TYPE
    SYNTAX      H3cDot11RadioType2
    MAX-ACCESS  read-write
    STATUS      current
    DESCRIPTION
        "Represents the radio will work with which 802.11 radio type."
    ::= { h3cDot11RadioIntfConfigEntry 15 }

-- *****************************************************************************
-- *  End of h3cDot11RadioIntfConfigTable Definition
-- *****************************************************************************

-- *****************************************************************************
-- *  h3cDot11RadioIntfBindTable Definition
-- *****************************************************************************
h3cDot11RadioIntfBindTable OBJECT-TYPE
    SYNTAX      SEQUENCE OF H3cDot11RadioIntfBindEntry
    MAX-ACCESS  not-accessible
    STATUS      current
    DESCRIPTION
        "The table defines the binding information for each radio in AP.
        "
    ::= { h3cDot11RadioIntfConfigGroup 2 }

h3cDot11RadioIntfBindEntry OBJECT-TYPE
    SYNTAX      H3cDot11RadioIntfBindEntry
    MAX-ACCESS  not-accessible
    STATUS      current
    DESCRIPTION
        "Each entry contains the radio interface binding information
        in AP."
    INDEX
        {
            h3cDot11RadioIfIdx,
            h3cDot11RadioIntfBindSvcPlcyID
        }
    ::= { h3cDot11RadioIntfBindTable 1 }

H3cDot11RadioIntfBindEntry ::= SEQUENCE
    {
        h3cDot11RadioIntfBindSvcPlcyID    H3cDot11ServicePolicyIDType,
        h3cDot11RadioIntfBindIfIdx        Unsigned32,
        h3cDot11RadioIntfBindRowStatus    RowStatus
    }

h3cDot11RadioIntfBindSvcPlcyID OBJECT-TYPE
    SYNTAX      H3cDot11ServicePolicyIDType
    MAX-ACCESS  not-accessible
    STATUS      current
    DESCRIPTION
        "Represents the ID of each service policy."
    ::= { h3cDot11RadioIntfBindEntry 1 }

h3cDot11RadioIntfBindIfIdx OBJECT-TYPE
    SYNTAX      Unsigned32
    MAX-ACCESS  read-create
    STATUS      current
    DESCRIPTION
        "Represents the Ifindex of interface which is binded to
        the radio."
    ::= { h3cDot11RadioIntfBindEntry 2 }

h3cDot11RadioIntfBindRowStatus OBJECT-TYPE
    SYNTAX      RowStatus
    MAX-ACCESS  read-create
    STATUS      current
    DESCRIPTION
        "The status of this table entry."
    ::= { h3cDot11RadioIntfBindEntry 3 }
-- *****************************************************************************
-- *  End of h3cDot11RadioIntfBindTable Definition
-- *****************************************************************************

-- *****************************************************************************
-- *  h3cDot11DataRateConfigTable Definition
-- *****************************************************************************
h3cDot11DataRateConfigTable OBJECT-TYPE
    SYNTAX      SEQUENCE OF H3cDot11DataRateConfigEntry
    MAX-ACCESS  not-accessible
    STATUS      current
    DESCRIPTION
        "Table will provide data rate configuration for a specific radio type."
    ::= { h3cDot11DataRateConfigGroup 1 }

h3cDot11DataRateConfigEntry OBJECT-TYPE
    SYNTAX      H3cDot11DataRateConfigEntry
    MAX-ACCESS  not-accessible
    STATUS      current
    DESCRIPTION
        "Each entry of the table will provide data rate configuration for a
        specific radio type."
    INDEX
        {
            h3cDot11RadioTypeID
        }
    ::= { h3cDot11DataRateConfigTable 1 }

H3cDot11DataRateConfigEntry ::= SEQUENCE
    {
        h3cDot11RadioTypeID         H3cDot11RadioType,
        h3cDot11SupportedRateSet    OCTET STRING,
        h3cDot11MandatoryRateSet    OCTET STRING,
        h3cDot11DisabledRateSet     OCTET STRING,
        h3cDot11SmartRateSet        OCTET STRING
    }

h3cDot11RadioTypeID OBJECT-TYPE
    SYNTAX      H3cDot11RadioType
    MAX-ACCESS  not-accessible
    STATUS      current
    DESCRIPTION
        "Represents the radio type."
    ::= { h3cDot11DataRateConfigEntry 1 }

h3cDot11SupportedRateSet OBJECT-TYPE
    SYNTAX      OCTET STRING(SIZE(0..255))
    MAX-ACCESS  read-write
    STATUS      current
    DESCRIPTION
        "Represents the supported rate set of a particular radio type."
    ::= { h3cDot11DataRateConfigEntry 2 }

h3cDot11MandatoryRateSet OBJECT-TYPE
    SYNTAX      OCTET STRING(SIZE(0..255))
    MAX-ACCESS  read-write
    STATUS      current
    DESCRIPTION
        "Represents the mandatory rate set of a particular radio type."
    ::= { h3cDot11DataRateConfigEntry 3 }

h3cDot11DisabledRateSet OBJECT-TYPE
    SYNTAX      OCTET STRING(SIZE(0..255))
    MAX-ACCESS  read-write
    STATUS      current
    DESCRIPTION
        "Represents the disabled rate set of a particular radio type."
    ::= { h3cDot11DataRateConfigEntry 4 }

h3cDot11SmartRateSet OBJECT-TYPE
    SYNTAX      OCTET STRING(SIZE(0..255))
    MAX-ACCESS  read-write
    STATUS      current
    DESCRIPTION
        "Represents the rate set of a particular radio type."
    ::= { h3cDot11DataRateConfigEntry 5 }
-- *****************************************************************************
-- *  End of h3cDot11DataRateConfigTable Definition
-- *****************************************************************************

-- *****************************************************************************
-- *  h3cDot11WlanEssIfTable Definition
-- *************************************************************************

h3cDot11WlanEssIfTable OBJECT-TYPE
    SYNTAX      SEQUENCE OF H3cDot11WlanEssIfEntry
    MAX-ACCESS  not-accessible
    STATUS      current
    DESCRIPTION
        "This table is used to configure WLAN ESS interface."
    ::= { h3cDot11InterfaceConfigGroup 1 }

h3cDot11WlanEssIfEntry OBJECT-TYPE
    SYNTAX      H3cDot11WlanEssIfEntry
    MAX-ACCESS  not-accessible
    STATUS      current
    DESCRIPTION
        "Each entry contains the WLAN ESS interface configuration."
    INDEX
        {
            h3cDot11WlanEssIfNumber
        }
    ::= { h3cDot11WlanEssIfTable 1 }

H3cDot11WlanEssIfEntry ::= SEQUENCE
    {
        h3cDot11WlanEssIfNumber      Integer32,
        h3cDot11WlanEssIfIndex       Integer32,
        h3cDot11WlanEssRowStatus     RowStatus
    }

h3cDot11WlanEssIfNumber OBJECT-TYPE
    SYNTAX      Integer32
    MAX-ACCESS  not-accessible
    STATUS      current
    DESCRIPTION
        "This node represents the WLAN ESS interface number."
    ::= { h3cDot11WlanEssIfEntry 1 }

h3cDot11WlanEssIfIndex OBJECT-TYPE
    SYNTAX      Integer32
    MAX-ACCESS  read-only
    STATUS      current
    DESCRIPTION
        "This node represents the ifIndex of WLAN-ESS interface."
    ::= { h3cDot11WlanEssIfEntry 2 }

h3cDot11WlanEssRowStatus OBJECT-TYPE
    SYNTAX      RowStatus
    MAX-ACCESS  read-create
    STATUS      current
    DESCRIPTION
        "This node represents the WLAN ESS interface row status."
    ::= { h3cDot11WlanEssIfEntry 3 }

-- *****************************************************************************
-- *  End of h3cDot11WlanEssIfTable  Definition
-- *****************************************************************************
-- *****************************************************************************
-- *  h3cDot11WlanBssIfTable Definition
-- *************************************************************************

h3cDot11WlanBssIfTable OBJECT-TYPE
    SYNTAX      SEQUENCE OF H3cDot11WlanBssIfEntry
    MAX-ACCESS  not-accessible
    STATUS      current
    DESCRIPTION
        "This table is used to configure WLAN BSS interface."
    ::= { h3cDot11InterfaceConfigGroup 2 }

h3cDot11WlanBssIfEntry OBJECT-TYPE
    SYNTAX      H3cDot11WlanBssIfEntry
    MAX-ACCESS  not-accessible
    STATUS      current
    DESCRIPTION
        "Each entry contains the WLAN BSS interface configuration."
    INDEX
        {
            h3cDot11WlanBssIfNumber
        }
    ::= { h3cDot11WlanBssIfTable 1 }

H3cDot11WlanBssIfEntry ::= SEQUENCE
    {
        h3cDot11WlanBssIfNumber     Integer32,
        h3cDot11WlanBssIfIndex      Integer32,
        h3cDot11WlanBssRowStatus    RowStatus
    }

h3cDot11WlanBssIfNumber OBJECT-TYPE
    SYNTAX      Integer32
    MAX-ACCESS  not-accessible
    STATUS      current
    DESCRIPTION
        "This node represents the WLAN BSS interface number."
    ::= { h3cDot11WlanBssIfEntry 1 }

h3cDot11WlanBssIfIndex OBJECT-TYPE
    SYNTAX      Integer32
    MAX-ACCESS  read-only
    STATUS      current
    DESCRIPTION
        "This node represents the ifIndex of WLAN-BSS interface."
    ::= { h3cDot11WlanBssIfEntry 2 }

h3cDot11WlanBssRowStatus OBJECT-TYPE
    SYNTAX      RowStatus
    MAX-ACCESS  read-create
    STATUS      current
    DESCRIPTION
        "This node represents the WLAN BSS interface row status."
    ::= { h3cDot11WlanBssIfEntry 3 }

-- *****************************************************************************
-- *  End of h3cDot11WlanBssIfTable Definition
-- *****************************************************************************
-- *****************************************************************************
-- *  h3cDot11WLANEthernetIfTable Definition
-- *************************************************************************

h3cDot11WLANEthernetIfTable OBJECT-TYPE
    SYNTAX      SEQUENCE OF H3cDot11WLANEthernetIfEntry
    MAX-ACCESS  not-accessible
    STATUS      current
    DESCRIPTION
        "This table is used to configure WLAN Ethernet interface."
    ::= { h3cDot11InterfaceConfigGroup 3 }

h3cDot11WLANEthernetIfEntry OBJECT-TYPE
    SYNTAX      H3cDot11WLANEthernetIfEntry
    MAX-ACCESS  not-accessible
    STATUS      current
    DESCRIPTION
        "Each entry contains the WLAN Ethernet interface configuration."
    INDEX
        {
            h3cDot11WlanEthernetIfNumber
        }
    ::= { h3cDot11WLANEthernetIfTable 1 }

H3cDot11WLANEthernetIfEntry ::= SEQUENCE
    {
        h3cDot11WlanEthernetIfNumber     Integer32,
        h3cDot11WLANEthernetIfIndex      Integer32,
        h3cDot11WlanEthernetRowStatus    RowStatus
    }

h3cDot11WlanEthernetIfNumber OBJECT-TYPE
    SYNTAX      Integer32
    MAX-ACCESS  not-accessible
    STATUS      current
    DESCRIPTION
        "This node represents the WLAN Ethernet interface number."
    ::= { h3cDot11WLANEthernetIfEntry 1 }

h3cDot11WLANEthernetIfIndex OBJECT-TYPE
    SYNTAX      Integer32
    MAX-ACCESS  read-only
    STATUS      current
    DESCRIPTION
        "This node represents the ifIndex of WLAN-Ethernet interface."
    ::= { h3cDot11WLANEthernetIfEntry 2 }

h3cDot11WlanEthernetRowStatus OBJECT-TYPE
    SYNTAX      RowStatus
    MAX-ACCESS  read-create
    STATUS      current
    DESCRIPTION
        "This node represents the Wlan Ethernet interface row status."
    ::= { h3cDot11WLANEthernetIfEntry 3 }

-- *****************************************************************************
-- *  End of h3cDot11DataRateConfigTable Definition
-- *****************************************************************************
-- *****************************************************************************
-- *  h3cDot11PortSecurityTable Definition
-- *****************************************************************************
h3cDot11PortSecurityTable OBJECT-TYPE
    SYNTAX      SEQUENCE OF H3cDot11PortSecurityEntry
    MAX-ACCESS  not-accessible
    STATUS      current
    DESCRIPTION
        "This table defines the WLAN security status for ESS, BSS, mesh and
        WLAN-Ethernet interface which binding the crypto service-template.
        Otherwise, when binding the clear service-template,
        h3cPortSecurityTables should be used to configure port security."
    ::= { h3cDot11InterfaceConfigGroup 4 }

h3cDot11PortSecurityEntry OBJECT-TYPE
    SYNTAX      H3cDot11PortSecurityEntry
    MAX-ACCESS  not-accessible
    STATUS      current
    DESCRIPTION
        "There is a row in this table for each ESS, BSS and WLAN-Ethernet
        interface.It is indexed using the object ifIndex in RFC1213-MIB."
    INDEX
        {
            ifIndex
        }
    ::= { h3cDot11PortSecurityTable 1 }

H3cDot11PortSecurityEntry ::= SEQUENCE
    {
        h3cDot11PortSecurityMode                 INTEGER,
        h3cDot11SecurityUserLoginTxKeyType       INTEGER,
        h3cDot11SecurityPskKeyMode               INTEGER,
        h3cDot11SecurityPskKeyString             DisplayString
    }

h3cDot11PortSecurityMode OBJECT-TYPE
    SYNTAX      INTEGER
        {
            noRestrictions(1),
            userLoginSecureExt(2),
            psk(3),
            macAddressAndPsk(4),
            userLoginSecureExtOrPsk(5),
            ext(6)
        }
    MAX-ACCESS  read-write
    STATUS      current
    DESCRIPTION
        "Determines the security modes of the WLAN port.

        noRestrictions(1)  The default value,no any security mode is set.

        userLoginSecureExt(2) Access to the port is denied until the port
        client is authorized (by 802.1X).

        psk(3) Access to the port is denied until the port client is
        authorized (by 802.1X key negotiation).

        macAddressAndPsk(4) The MAC address is first authenticated and only if
        this succeeds does the psk then attempt user authentication.

        userLoginSecureExtOrPsk(5) This selects both the userLoginSecureExt and
        psk modes together such that either is allowed to authorized access.
        Which mode works for client depends on the client's choice.

        ext(6) Access to the port is denied until the port client is
        authenticated (by ext).
        "
    ::= { h3cDot11PortSecurityEntry 1 }

h3cDot11SecurityUserLoginTxKeyType OBJECT-TYPE
    SYNTAX      INTEGER
        {
            userLoginTxKeyTypeNone(1),
            userLoginTxKeyTypeDot11Key(2),
            userLoginTxKeyTypeRsaRC4Key(3)
        }
    MAX-ACCESS  read-write
    STATUS      current
    DESCRIPTION
        "This indicates the key type in the 802.1X EAPOL_Key packet.

        userLoginTxKeyTypeNone(1) This means the key type is not set yet.

        userLoginTxKeyTypeDot11Key(2) This selects the 802.11 key type.

        userLoginTxKeyTypeRsaRC4Key(3) This selects the RC4 key for RSA RC4
        session encryption."
    ::= { h3cDot11PortSecurityEntry 2 }

h3cDot11SecurityPskKeyMode OBJECT-TYPE
    SYNTAX      INTEGER
        {
            pskKeyModeNone(1),
            pskKeyModePassPhrase(2),
            pskKeyModeRawKey(3)
        }
    MAX-ACCESS  read-write
    STATUS      current
    DESCRIPTION
        "This is the password input mode. When input as pskKeyModePassPhrase,
        h3cDot11SecurePskKeyString must be 8 to 63 characters; when input as
        pskKeyModeRawKey, h3cDot11SecurePskKeyString must be 64 characters and
        each character must be '0'-'9', 'a'-'f' and 'A'-'F'."
    ::= { h3cDot11PortSecurityEntry 3 }

h3cDot11SecurityPskKeyString OBJECT-TYPE
    SYNTAX      DisplayString
    MAX-ACCESS  read-write
    STATUS      current
    DESCRIPTION
        "This is the password string used for psk authentication."
    ::= { h3cDot11PortSecurityEntry 4 }

-- *****************************************************************************
-- *  End of h3cDot11PortSecurityTable Definition
-- *****************************************************************************
-- *****************************************************************************
-- *  h3cDot11WlanMeshIfTable Definition
-- *************************************************************************

h3cDot11WlanMeshIfTable OBJECT-TYPE
    SYNTAX      SEQUENCE OF H3cDot11WlanMeshIfEntry
    MAX-ACCESS  not-accessible
    STATUS      current
    DESCRIPTION
        "This table is used to configure WLAN mesh interface."
    ::= { h3cDot11InterfaceConfigGroup 5 }

h3cDot11WlanMeshIfEntry OBJECT-TYPE
    SYNTAX      H3cDot11WlanMeshIfEntry
    MAX-ACCESS  not-accessible
    STATUS      current
    DESCRIPTION
        "Each entry contains the WLAN mesh interface configuration."
    INDEX
        {
            h3cDot11WlanMeshIfNumber
        }
    ::= { h3cDot11WlanMeshIfTable 1 }

H3cDot11WlanMeshIfEntry ::= SEQUENCE
    {
        h3cDot11WlanMeshIfNumber    Integer32,
        h3cDot11WlanMeshIfIndex     Integer32,
        h3cDot11WlanMeshRowStatus   RowStatus
    }

h3cDot11WlanMeshIfNumber OBJECT-TYPE
    SYNTAX      Integer32
    MAX-ACCESS  not-accessible
    STATUS      current
    DESCRIPTION
        "This node represents the WLAN mesh interface number."
    ::= { h3cDot11WlanMeshIfEntry 1 }

h3cDot11WlanMeshIfIndex OBJECT-TYPE
    SYNTAX      Integer32
    MAX-ACCESS  read-only
    STATUS      current
    DESCRIPTION
        "This node represents the index of WLAN mesh interface."
    ::= { h3cDot11WlanMeshIfEntry 2 }

h3cDot11WlanMeshRowStatus OBJECT-TYPE
    SYNTAX      RowStatus
    MAX-ACCESS  read-create
    STATUS      current
    DESCRIPTION
        "This node represents the WLAN mesh interface row status."
    ::= { h3cDot11WlanMeshIfEntry 3 }

-- *****************************************************************************
-- *  End of h3cDot11WlanMeshIfTable Definition
-- *****************************************************************************

-- *****************************************************************************
-- *  h3cDot11ACBackupGroup Definition
-- *****************************************************************************
h3cDot11BackupACAdrssIP OBJECT-TYPE
    SYNTAX      InetAddress
    MAX-ACCESS  read-write
    STATUS      current
    DESCRIPTION
        "This object represents the backup AC IP address.
        If the backup AC IP address is not configured,
        the object value is 0.0.0.0."
    ::= { h3cDot11ACBackupGroup 1 }

h3cDot11BackupACAdrssIPv6 OBJECT-TYPE
    SYNTAX      InetAddress
    MAX-ACCESS  read-write
    STATUS      current
    DESCRIPTION
        "This object represents the backup AC IPv6 address.
         If the backup AC IPv6 address is not configured,
         the object value is 0::0."
    ::= { h3cDot11ACBackupGroup 2 }

-- *****************************************************************************
-- *  End of h3cDot11ACBackupGroup Definition
-- *****************************************************************************

-- *****************************************************************************
-- *  h3cDot11RadioElementConfigGroup Definition
-- *****************************************************************************

h3cDot11nRadioCfgTable OBJECT-TYPE
    SYNTAX SEQUENCE OF H3cDot11nRadioCfgEntry
    MAX-ACCESS not-accessible
    STATUS current
    DESCRIPTION
        "This table is used to configure dot11n on the radio."
    ::= { h3cDot11RadioElementConfigGroup 1 }

h3cDot11nRadioCfgEntry OBJECT-TYPE
    SYNTAX H3cDot11nRadioCfgEntry
    MAX-ACCESS not-accessible
    STATUS current
    DESCRIPTION
        "This entry contains the dot11n configuration on the radio."
    INDEX { h3cDot11nRadioCfgIndex }
    ::= { h3cDot11nRadioCfgTable 1 }

H3cDot11nRadioCfgEntry ::= SEQUENCE
    {
        h3cDot11nRadioCfgIndex       H3cDot11RadioElementIndex,
        h3cDot11nAMpduEnable         TruthValue,
        h3cDot11nAMsduEnable         TruthValue,
        h3cDot11nClientDot11nOnly    TruthValue,
        h3cDot11nChanelBand          INTEGER,
        h3cDot11nShortGiEnable       TruthValue
    }

h3cDot11nRadioCfgIndex OBJECT-TYPE
    SYNTAX H3cDot11RadioElementIndex
    MAX-ACCESS not-accessible
    STATUS current
    DESCRIPTION
        "Represents index of the radio."
    ::= { h3cDot11nRadioCfgEntry 1 }

h3cDot11nAMpduEnable OBJECT-TYPE
    SYNTAX TruthValue
    MAX-ACCESS read-write
    STATUS current
    DESCRIPTION
        "Enable the function of A-MPDU."
        DEFVAL { true }
    ::= { h3cDot11nRadioCfgEntry 2 }

h3cDot11nAMsduEnable OBJECT-TYPE
    SYNTAX TruthValue
    MAX-ACCESS read-write
    STATUS current
    DESCRIPTION
        "Enable the function of A-MSDU."
    DEFVAL { true }
    ::= { h3cDot11nRadioCfgEntry 3 }

h3cDot11nClientDot11nOnly OBJECT-TYPE
    SYNTAX TruthValue
    MAX-ACCESS read-write
    STATUS current
    DESCRIPTION
        "Only permit clients of 11n mode."
    DEFVAL { false }
    ::= { h3cDot11nRadioCfgEntry 4 }

h3cDot11nChanelBand OBJECT-TYPE
    SYNTAX INTEGER
        {
        mode20(1),
        mode40(2)
        }
    MAX-ACCESS read-write
    STATUS current
    DESCRIPTION
        "Specify the bandwidth mode."
    DEFVAL { mode40 }
    ::= { h3cDot11nRadioCfgEntry 5 }

h3cDot11nShortGiEnable OBJECT-TYPE
    SYNTAX TruthValue
    MAX-ACCESS read-write
    STATUS current
    DESCRIPTION
        "The function of Short GI."
    DEFVAL { true }
    ::= { h3cDot11nRadioCfgEntry 6 }


-- *****************************************************************************
-- *  End of h3cDot11RadioElementConfigGroup Definition
-- *****************************************************************************

-- *****************************************************************************
-- *  h3cDot11RadioWDSTable Definition
-- *****************************************************************************

h3cDot11RadioWDSTable OBJECT-TYPE
    SYNTAX      SEQUENCE OF H3cDot11RadioWDSEntry
    MAX-ACCESS  not-accessible
    STATUS      current
    DESCRIPTION
        "This table is used to configure WDS on the radio."
    ::= { h3cDot11RadioElementConfigGroup 2 }

h3cDot11RadioWDSEntry OBJECT-TYPE
    SYNTAX      H3cDot11RadioWDSEntry
    MAX-ACCESS  not-accessible
    STATUS      current
    DESCRIPTION
        "Each entry contains the WDS configuration on the radio."
    INDEX
        {
            h3cDot11RadioWDSIndex
        }
    ::= { h3cDot11RadioWDSTable 1 }

H3cDot11RadioWDSEntry ::= SEQUENCE
    {
        h3cDot11RadioWDSIndex            H3cDot11RadioElementIndex,
        h3cDot11RadioWDSMode             INTEGER,
        h3cDot11RadioWDSNetWorkID        OCTET STRING,
        h3cDot11WDSSecPskKeyMode         INTEGER,
        h3cDot11WDSSecPskKeyString       DisplayString
    }

h3cDot11RadioWDSIndex OBJECT-TYPE
    SYNTAX      H3cDot11RadioElementIndex
    MAX-ACCESS  not-accessible
    STATUS      current
    DESCRIPTION
        "Represents the element index of radio."
    ::= { h3cDot11RadioWDSEntry 1 }

h3cDot11RadioWDSMode OBJECT-TYPE
    SYNTAX      INTEGER
        {
            nowds(1),
            wds(2)
        }
    MAX-ACCESS  read-write
    STATUS      current
    DESCRIPTION
        "Represents enable the WDS mode or not.
        nowds: The WDS mode is disabled.
        wds  : The WDS mode is enabled"
    DEFVAL      { nowds }
    ::= { h3cDot11RadioWDSEntry 2 }

h3cDot11RadioWDSNetWorkID OBJECT-TYPE
    SYNTAX      OCTET STRING(SIZE(0..32))
    MAX-ACCESS  read-write
    STATUS      current
    DESCRIPTION
        "Represents the mesh ID of WDS."
    DEFVAL      { "" }
    ::= { h3cDot11RadioWDSEntry 3 }

h3cDot11WDSSecPskKeyMode OBJECT-TYPE
    SYNTAX      INTEGER
        {
          pskKeyModeNone(1),
          pskKeyModePassPhrase(2),
          pskKeyModeRawKey(3)
        }
    MAX-ACCESS  read-write
    STATUS      current
    DESCRIPTION
        "Represents the PSK mode of WDS."
    DEFVAL      { pskKeyModeNone }
    ::= { h3cDot11RadioWDSEntry 4 }

h3cDot11WDSSecPskKeyString OBJECT-TYPE
    SYNTAX      DisplayString
    MAX-ACCESS  read-write
    STATUS      current
    DESCRIPTION
        "Represents the PSK value of WDS."
    DEFVAL      { "" }
    ::= { h3cDot11RadioWDSEntry 5 }

-- *****************************************************************************
-- *  End of h3cDot11RadioWDSTable  Definition
-- *****************************************************************************

-- *****************************************************************************
-- *  h3cDot11nRadioCfg2Table Definition
-- *****************************************************************************

h3cDot11nRadioCfg2Table OBJECT-TYPE
    SYNTAX SEQUENCE OF H3cDot11nRadioCfg2Entry
    MAX-ACCESS not-accessible
    STATUS current
    DESCRIPTION
        "This table is used to configure dot11n on the radio."
    ::= { h3cDot11RadioElementConfigGroup 3 }

h3cDot11nRadioCfg2Entry OBJECT-TYPE
    SYNTAX H3cDot11nRadioCfg2Entry
    MAX-ACCESS not-accessible
    STATUS current
    DESCRIPTION
        "This entry contains the dot11n configuration on the radio."
    INDEX {
              h3cDot11nRadioCfg2APIDIndex,
              h3cDot11nRadioCfg2RadioIDIndex
          }
    ::= { h3cDot11nRadioCfg2Table 1 }

H3cDot11nRadioCfg2Entry ::= SEQUENCE
    {
        h3cDot11nRadioCfg2APIDIndex           H3cDot11ObjectIDType,
        h3cDot11nRadioCfg2RadioIDIndex        H3cDot11RadioScopeType,
        h3cDot11nRadioCfg2AMpduEnable         TruthValue,
        h3cDot11nRadioCfg2AMsduEnable         TruthValue,
        h3cDot11nRadioCfg2ClientDot11nOnly    TruthValue,
        h3cDot11nRadioCfg2ChannelBand          INTEGER,
        h3cDot11nRadioCfg2ShortGiEnable       TruthValue
    }

h3cDot11nRadioCfg2APIDIndex OBJECT-TYPE
    SYNTAX H3cDot11ObjectIDType
    MAX-ACCESS not-accessible
    STATUS current
    DESCRIPTION
        "Represents index of the AP."
    ::= { h3cDot11nRadioCfg2Entry 1 }

h3cDot11nRadioCfg2RadioIDIndex OBJECT-TYPE
    SYNTAX H3cDot11RadioScopeType
    MAX-ACCESS not-accessible
    STATUS current
    DESCRIPTION
        "Represents index of the radio."
    ::= { h3cDot11nRadioCfg2Entry 2 }

h3cDot11nRadioCfg2AMpduEnable OBJECT-TYPE
    SYNTAX TruthValue
    MAX-ACCESS read-write
    STATUS current
    DESCRIPTION
        "Enable the function of A-MPDU."
        DEFVAL { true }
    ::= { h3cDot11nRadioCfg2Entry 3 }

h3cDot11nRadioCfg2AMsduEnable OBJECT-TYPE
    SYNTAX TruthValue
    MAX-ACCESS read-write
    STATUS current
    DESCRIPTION
        "Enable the function of A-MSDU."
    DEFVAL { true }
    ::= { h3cDot11nRadioCfg2Entry 4 }

h3cDot11nRadioCfg2ClientDot11nOnly OBJECT-TYPE
    SYNTAX TruthValue
    MAX-ACCESS read-write
    STATUS current
    DESCRIPTION
        "Only permit clients of 11n mode."
    DEFVAL { false }
    ::= { h3cDot11nRadioCfg2Entry 5 }

h3cDot11nRadioCfg2ChannelBand OBJECT-TYPE
    SYNTAX INTEGER
        {
        mode20(1),
        mode40(2)
        }
    MAX-ACCESS read-write
    STATUS current
    DESCRIPTION
        "Specify the bandwidth mode."
    ::= { h3cDot11nRadioCfg2Entry 6 }

h3cDot11nRadioCfg2ShortGiEnable OBJECT-TYPE
    SYNTAX TruthValue
    MAX-ACCESS read-write
    STATUS current
    DESCRIPTION
        "Enable the function of Short GI."
    DEFVAL { true }
    ::= { h3cDot11nRadioCfg2Entry 7 }


-- *****************************************************************************
-- *  End of h3cDot11nRadioCfg2Table Definition
-- *****************************************************************************

-- *****************************************************************************
-- *  h3cDot11CfgNotifyGroup Definition
-- *****************************************************************************
h3cDot11CfgNotifications OBJECT IDENTIFIER ::= { h3cDot11CfgNotifyGroup 0 }

h3cDot11CfgCipherChange NOTIFICATION-TYPE
    OBJECTS
    {
        h3cDot11SSIDName,
        h3cDot11SecurityCiphers
    }
    STATUS      current
    DESCRIPTION
        "This notification is sent when cipher type of corresponding service
        template is changed."
    ::= { h3cDot11CfgNotifications 1 }

h3cDot11CfgPSKChange NOTIFICATION-TYPE
    OBJECTS
    {
        h3cDot11SSIDName
    }
    STATUS      current
    DESCRIPTION
        "This notification is sent when pre-shared key of corresponding
        service template is changed."
    ::= { h3cDot11CfgNotifications 2 }

h3cDot11SSIDWepIDConflictTrap NOTIFICATION-TYPE
    OBJECTS
    {
        h3cDot11PreConflictTemplateNum,
        h3cDot11CurrConflictTemplateNum,
        h3cDot11ConflictCipherIdx,
        h3cDot11ConfigureAPID,
        h3cDot11ConfigureRadioID
    }
    STATUS      current
    DESCRIPTION
        "This notification will be sent when the same wep ID is configured
         on two service policies."
    ::= { h3cDot11CfgNotifications 3 }

-- CFG Notification variable object

h3cDot11CfgTrapVarObjects OBJECT IDENTIFIER
    ::= { h3cDot11CfgNotifyGroup 1 }

h3cDot11PreConflictTemplateNum OBJECT-TYPE
    SYNTAX      Integer32 (1..1024)
    MAX-ACCESS  accessible-for-notify
    STATUS      current
    DESCRIPTION
        "Represents previous service policy ID when radio bind service policy
         and current service policy conflict with previous service policy
         in cipher configuration."
    ::= { h3cDot11CfgTrapVarObjects 1 }

h3cDot11CurrConflictTemplateNum OBJECT-TYPE
    SYNTAX      Integer32 (1..1024)
    MAX-ACCESS  accessible-for-notify
    STATUS      current
    DESCRIPTION
        "Represents current service policy ID when radio bind service policy
         and current service policy conflict with previous service policy
         in cipher configuration."
    ::= { h3cDot11CfgTrapVarObjects 2 }

h3cDot11ConflictCipherIdx OBJECT-TYPE
    SYNTAX      Integer32 (1..4)
    MAX-ACCESS  accessible-for-notify
    STATUS      current
    DESCRIPTION
        "Represents wep ID that conflicted with."
    ::= { h3cDot11CfgTrapVarObjects 3 }

h3cDot11ConfigureAPID OBJECT-TYPE
    SYNTAX      H3cDot11ObjectIDType
    MAX-ACCESS  accessible-for-notify
    STATUS      current
    DESCRIPTION
        "Represents which AP is configured."
    ::= { h3cDot11CfgTrapVarObjects 4 }

h3cDot11ConfigureRadioID OBJECT-TYPE
    SYNTAX      H3cDot11RadioScopeType
    MAX-ACCESS  accessible-for-notify
    STATUS      current
    DESCRIPTION
        "Represents which radio in AP is configured."
    ::= { h3cDot11CfgTrapVarObjects 5 }

-- *****************************************************************************
-- *  End of h3cDot11CfgNotifyGroup Definition
-- *****************************************************************************

END
