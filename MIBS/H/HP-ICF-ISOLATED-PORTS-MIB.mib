--**MOD+***********************************************************************
-- * Module:    hpicfIsolatedPorts.mib
-- *
-- * Copyright (C) 2014 Hewlett Packard Enterprise Development LP
-- * All Rights Reserved.
-- * 
-- * The contents of this software are proprietary and confidential
-- * to the Hewlett Packard Enterprise Development LP.  No part of this
-- * program may be photocopied, reproduced, or translated into another
-- * programming language without prior written consent of the
-- * Hewlett Packard Enterprise Development LP.
-- *
-- * Purpose:   Contains MIB Objects for Isolated Ports
-- *
-- **MOD-***********************************************************************/


-- HP Enterprise Isolated Ports MIB

HP-ICF-ISOLATED-PORTS-MIB DEFINITIONS ::= BEGIN

IMPORTS
    MODULE-IDENTITY, OBJECT-TYPE
        FROM SNMPv2-SMI
    PortList, dot1qVlanStaticEntry
            FROM Q-BRIDGE-MIB
    OBJECT-GROUP, MODULE-COMPLIANCE
        FROM SNMPv2-CONF
    hpSwitch
        FROM HP-ICF-OID;

    hpicfDot1qIsolatedPorts  MODULE-IDENTITY
        LAST-UPDATED "201404140000Z"
        ORGANIZATION "HP Networking"
        CONTACT-INFO 
            "Hewlett-Packard Company
             8000 Foothills Blvd.
             Roseville, CA 95747"
        DESCRIPTION 
        "This MIB module contains the HP proprietary objects for configuring and
         managing the isolated ports on the VLAN."
        REVISION "201404140000Z"       -- April 22, 2014 at 00:00 GMT
        DESCRIPTION
            "Initial Revision."
        ::= { hpSwitch 109 }

hpicfDot1qIsolatedPortConfigurationObjects    OBJECT IDENTIFIER ::= 
                                                 {hpicfDot1qIsolatedPorts 1}
hpicfDot1qIsolatedPortConformance	     OBJECT IDENTIFIER ::= 
                                                 {hpicfDot1qIsolatedPorts 2}  
--
--- Isolated Ports configuration Table
--
   hpicfDot1qIsolatedPortsTable OBJECT-TYPE
   SYNTAX      SEQUENCE OF HpicfDot1qIsolatedPortsEntry
   MAX-ACCESS  not-accessible
   STATUS      current
   DESCRIPTION "A table that contains the information about all the isolated
                ports of the VLANs on a device. Each VLAN can have a single
                isolate-list. The isolate-list holds a list of isolated ports
                that cannot forward the traffic to other isolated ports on the
                same VLAN."
   ::= { hpicfDot1qIsolatedPortConfigurationObjects 1 }

   hpicfDot1qIsolatedPortsEntry OBJECT-TYPE
   SYNTAX      HpicfDot1qIsolatedPortsEntry
   MAX-ACCESS  not-accessible
   STATUS      current
   DESCRIPTION "An entry in the table that contains the information about the
                isolated ports of a VLAN."
   AUGMENTS    { dot1qVlanStaticEntry }
   ::= { hpicfDot1qIsolatedPortsTable 1 }

   HpicfDot1qIsolatedPortsEntry ::=
   SEQUENCE {
            hpicfDot1qVlanStaticIsolatedPorts PortList
        }

   hpicfDot1qVlanStaticIsolatedPorts OBJECT-TYPE
    SYNTAX      PortList
    MAX-ACCESS  read-create
    STATUS      current
    DESCRIPTION "This object contains a list of isolated ports in the VLAN.
                 Traffic received on isolated ports will not be forwarded to
                 other isolated ports in the VLAN, only to non-isolated ports."
    ::= { hpicfDot1qIsolatedPortsEntry 1 }
  

-- Isolated Port - Conformance Information
-- =============================================================
    hpicfDot1qIsolatedPortCompliances
    OBJECT IDENTIFIER ::= { hpicfDot1qIsolatedPortConformance   1 }
    hpicfDot1qIsolatedPortGroups
    OBJECT IDENTIFIER ::= { hpicfDot1qIsolatedPortConformance   2 }

-- ============================================================

--  Isolated Ports - units of conformance
-- =============================================================
      
   hpicfDot1qIsolatedPortCompliance MODULE-COMPLIANCE
   STATUS  current
   DESCRIPTION
          "The compliance statement for the Isolated Ports."
   MODULE  -- this module
   MANDATORY-GROUPS { hpicfDot1qIsolatedPortGroup
                   }
   ::= { hpicfDot1qIsolatedPortCompliances 1 }
  
   hpicfDot1qIsolatedPortGroup OBJECT-GROUP
    OBJECTS  {
              hpicfDot1qVlanStaticIsolatedPorts
             }
    STATUS   current
    DESCRIPTION
        "The collection of objects that provides the information about the 
         isolated ports of the VLANs on a device."
      ::= { hpicfDot1qIsolatedPortGroups 1 }

END
