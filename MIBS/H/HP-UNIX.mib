HP-UNIX DEFINITIONS ::= BEGIN

--
--  Hewlett-Packard definitons for unix agents 
--  @(#) hp-unix $Date: 1998/07/30 18:52 UTC $ $Revision: /main/PULSAR/1 $
--

IMPORTS
        enterprises, NetworkAddress, IpAddress, Counter, Gauge,
		TimeTicks
            FROM RFC1155-SMI
	OBJECT-TYPE 				
	    FROM RFC-1212
	DisplayString 				
	    FROM RFC1213-MIB;

hp 		OBJECT IDENTIFIER ::= { enterprises 11 }
nm		OBJECT IDENTIFIER ::= { hp 2 }
system		OBJECT IDENTIFIER ::= { nm 3 }
interface	OBJECT IDENTIFIER ::= { nm 4 }
icmp		OBJECT IDENTIFIER ::= { nm 7 }
snmp		OBJECT IDENTIFIER ::= { nm 13 }
openView	OBJECT IDENTIFIER ::= { nm 17 }
general		OBJECT IDENTIFIER ::= { system 1 }
hpux		OBJECT IDENTIFIER ::= { system 2 }
hpsun		OBJECT IDENTIFIER ::= { system 10 }
sparc		OBJECT IDENTIFIER ::= { hpsun 1 }
computerSystem	OBJECT IDENTIFIER ::= { general 1 } 
fileSystem	OBJECT IDENTIFIER ::= { general 2 }
processes	OBJECT IDENTIFIER ::= { general 4 }
cluster		OBJECT IDENTIFIER ::= { general 5 }
ieee8023Mac	OBJECT IDENTIFIER ::= { interface 1 }
trap		OBJECT IDENTIFIER ::= { snmp 1 }
snmpdConf	OBJECT IDENTIFIER ::= { snmp 2 }
authfail	OBJECT IDENTIFIER ::= { snmp 4 }
openViewTrapVars OBJECT IDENTIFIER ::= { openView 2 }


-- sysObjectId definitions.  These values are returned in the
--    .iso.org.dod.internet.mgmt.mib-2.system.sysObjectID.0 variable

hp386		OBJECT IDENTIFIER ::= { system 8 }
hp9000s300	OBJECT IDENTIFIER ::= { hpux 2 }
hp9000s800	OBJECT IDENTIFIER ::= { hpux 3 }
hp9000s700	OBJECT IDENTIFIER ::= { hpux 5 }
hpOpenView	OBJECT IDENTIFIER ::= { openView 1 }
sun4		OBJECT IDENTIFIER ::= { sparc 1 }
sun5		OBJECT IDENTIFIER ::= { sparc 2 }

-- the ComputerSystem Group

computerSystemUpTime OBJECT-TYPE
	SYNTAX	TimeTicks
	ACCESS	read-only
	STATUS	mandatory
	DESCRIPTION
		"Time since the last boot."
	::= { computerSystem 1 }

computerSystemUsers OBJECT-TYPE
	SYNTAX 	Gauge
	ACCESS	read-only
	STATUS	mandatory
	DESCRIPTION
		"Number of users logged on to system."
	::= { computerSystem 2 }

computerSystemAvgJobs1 OBJECT-TYPE
	SYNTAX	Gauge
	ACCESS 	read-only
	STATUS	mandatory
	DESCRIPTION
		"Average number of jobs in the last 1 
		minute * 100."
	::= { computerSystem 3 }

computerSystemAvgJobs5 OBJECT-TYPE
	SYNTAX 	Gauge
	ACCESS 	read-only
	STATUS	mandatory
	DESCRIPTION
		"Average number of jobs in the last 5 
		minutes * 100."
	::= { computerSystem 4 }

computerSystemAvgJobs15 OBJECT-TYPE
	SYNTAX 	Gauge
	ACCESS 	read-only
	STATUS	mandatory
	DESCRIPTION
		"Average number of jobs in the last 15 
		minutes * 100."
	::= { computerSystem 5 }

computerSystemMaxProc OBJECT-TYPE
	SYNTAX 	INTEGER
	ACCESS 	read-only
	STATUS	mandatory
	DESCRIPTION
		"Maximum number of processes allowed in system.
		 Implemented with Extensible SNMP Agent."
	::= { computerSystem 6 }

computerSystemFreeMemory OBJECT-TYPE
	SYNTAX 	Gauge
	ACCESS 	read-only
	STATUS	mandatory
	DESCRIPTION
		"Free memory.  SunOS - not implemented.
		 Implemented with Extensible SNMP Agent."
	::= { computerSystem 7 }

computerSystemPhysMemory OBJECT-TYPE
	SYNTAX 	INTEGER
	ACCESS 	read-only
	STATUS	mandatory
	DESCRIPTION
		"Physical memory.  SunOS - not implemented.
		 Implemented with Extensible SNMP Agent."
	::= { computerSystem 8 }

computerSystemMaxUserMem OBJECT-TYPE
	SYNTAX 	Gauge
	ACCESS 	read-only
	STATUS	mandatory
	DESCRIPTION
		"Maximum user memory.  SunOS - not implemented.
		 Implemented with Extensible SNMP Agent."
	::= { computerSystem 9 }

computerSystemSwapConfig OBJECT-TYPE
	SYNTAX 	INTEGER
	ACCESS 	read-only
	STATUS	mandatory
	DESCRIPTION
		"Swap space configured.  SunOS - not implemented.
		 Implemented with Extensible SNMP Agent."
	::= { computerSystem 10 }

computerSystemEnabledSwap OBJECT-TYPE
	SYNTAX 	Gauge
	ACCESS 	read-only
	STATUS	mandatory
	DESCRIPTION
		"Enabled via swapon.  SunOS - not implemented.
		 Implemented with Extensible SNMP Agent."
	::= { computerSystem 11 }

computerSystemFreeSwap OBJECT-TYPE
	SYNTAX 	Gauge
	ACCESS 	read-only
	STATUS	mandatory
	DESCRIPTION
		"Currently free swap space.  SunOS - not implemented.
		 Implemented with Extensible SNMP Agent."
	::= { computerSystem 12 }

computerSystemUserCPU OBJECT-TYPE
	SYNTAX 	Counter
	ACCESS 	read-only
	STATUS	mandatory
	DESCRIPTION
		"CPU used by users.  SunOS - not implemented.
		 Implemented with Extensible SNMP Agent."
	::= { computerSystem 13 }

computerSystemSysCPU OBJECT-TYPE
	SYNTAX 	Counter
	ACCESS 	read-only
	STATUS	mandatory
	DESCRIPTION
		"CPU used by system.  SunOS - not implemented.
		 Implemented with Extensible SNMP Agent."
	::= { computerSystem 14 }

computerSystemIdleCPU OBJECT-TYPE
	SYNTAX 	Counter
	ACCESS 	read-only
	STATUS	mandatory
	DESCRIPTION
		"CPU idle.  SunOS - not implemented.
		 Implemented with Extensible SNMP Agent."
	::= { computerSystem 15 }

computerSystemNiceCPU OBJECT-TYPE
	SYNTAX 	Counter
	ACCESS 	read-only
	STATUS	mandatory
	DESCRIPTION
		"CPU nice.  SunOS - not implemented.
		 Implemented with Extensible SNMP Agent."
	::= { computerSystem 16 }

-- The FileSystem Group

fileSystemMounted OBJECT-TYPE
	SYNTAX 	Gauge
	ACCESS 	read-only
	STATUS	mandatory
	DESCRIPTION
		"The number of file systems mounted."
	::= { fileSystem 1 }

-- The FileSystem Table

fileSystemTable OBJECT-TYPE
	SYNTAX	SEQUENCE OF FileSystemEntry
	ACCESS 	not-accessible
	STATUS	mandatory
	DESCRIPTION
		"File system table."
	::= { fileSystem 2 }

fileSystemEntry OBJECT-TYPE
	SYNTAX	FileSystemEntry
	ACCESS 	not-accessible
	STATUS	mandatory
	DESCRIPTION
		"Each entry contains objects for a particular file 
		system."
	INDEX	{ fileSystemID1, fileSystemID2 }
	::= { fileSystemTable 1 }

FileSystemEntry ::= SEQUENCE {
    fileSystemID1
	INTEGER,
    fileSystemID2
	INTEGER,
    fileSystemName
	DisplayString,
    fileSystemBlock
	INTEGER,
    fileSystemBfree
	INTEGER,
    fileSystemBavail
	INTEGER,
    fileSystemBsize
	INTEGER,
    fileSystemFiles
	INTEGER,
    fileSystemFfree
	INTEGER,
    fileSystemDir
	DisplayString
}

fileSystemID1 OBJECT-TYPE
	SYNTAX	INTEGER (0..4294967295)
	ACCESS 	read-only
	STATUS	mandatory
	DESCRIPTION
		"First file system ID."
	::= { fileSystemEntry 1 }

fileSystemID2 OBJECT-TYPE
	SYNTAX	INTEGER (0..4294967295)
	ACCESS 	read-only
	STATUS	mandatory    
	DESCRIPTION
		"Second file system ID."
	::= { fileSystemEntry 2 }

fileSystemName OBJECT-TYPE
	SYNTAX	DisplayString
	ACCESS 	read-only
	STATUS	mandatory
	DESCRIPTION
		"Name of mounted file system."
	::= { fileSystemEntry 3 }

fileSystemBlock OBJECT-TYPE
	SYNTAX	INTEGER
	ACCESS 	read-only
	STATUS	mandatory
	DESCRIPTION
		"Total blocks in file system."
	::= { fileSystemEntry 4 }

fileSystemBfree OBJECT-TYPE
	SYNTAX	INTEGER
	ACCESS 	read-only
	STATUS	mandatory
	DESCRIPTION
		"Free blocks in file system."
	::= { fileSystemEntry 5 }

fileSystemBavail OBJECT-TYPE
	SYNTAX	INTEGER
	ACCESS 	read-only
	STATUS	mandatory
	DESCRIPTION
		"Free blocks avail to non-superuser."
	::= { fileSystemEntry 6 }

fileSystemBsize OBJECT-TYPE
	SYNTAX	INTEGER
	ACCESS 	read-only
	STATUS	mandatory
	DESCRIPTION
		"Fundamental file system block size."
	::= { fileSystemEntry 7 }

fileSystemFiles OBJECT-TYPE
	SYNTAX	INTEGER
	ACCESS 	read-only
	STATUS	mandatory
	DESCRIPTION
		"Total file nodes in file system."
	::= { fileSystemEntry 8 }

fileSystemFfree OBJECT-TYPE
	SYNTAX	INTEGER
	ACCESS 	read-only
	STATUS	mandatory
	DESCRIPTION
		"Free file nodes in file system."
	::= { fileSystemEntry 9 }

fileSystemDir OBJECT-TYPE
	SYNTAX	DisplayString
	ACCESS 	read-only
	STATUS	mandatory
	DESCRIPTION
		"File system path prefix."
	::= { fileSystemEntry 10 }

-- The Processes Group

processNum OBJECT-TYPE
	SYNTAX 	Gauge
	ACCESS 	read-only
	STATUS	mandatory
	DESCRIPTION
		"The number of processes running."
	::= { processes 1 }

-- The processes table

processTable OBJECT-TYPE
	SYNTAX	SEQUENCE OF ProcessEntry
	ACCESS 	not-accessible
	STATUS	mandatory
	DESCRIPTION
		"Processes Table.
		 Implemented with Extensible SNMP Agent."
	::= { processes 2 }

processEntry	OBJECT-TYPE
	SYNTAX	ProcessEntry
	ACCESS 	not-accessible
	STATUS	mandatory
	DESCRIPTION
		"Each entry contains information about a process
		running on the system."
	INDEX	{ processPID }
	::= { processTable 1 }

ProcessEntry ::= SEQUENCE {
    processPID
	INTEGER,
    processIdx
	INTEGER,
    processUID
	INTEGER,
    processPPID
	INTEGER,
    processDsize
	Gauge,
    processTsize
	Gauge,
    processSsize
	Gauge,
    processNice
	Gauge,
    processMajor
	INTEGER,
    processMinor
	INTEGER,
    processPgrp
	INTEGER,
    processPrio
	INTEGER,
    processAddr
	INTEGER,
    processCPU
	Gauge,
    processUtime
	TimeTicks,
    processStime
	TimeTicks,
    processStart
	TimeTicks,
    processFlags
	INTEGER,
    processStatus
	INTEGER,
    processWchan
	INTEGER,
    processProcNum
	INTEGER,
    processCmd
	DisplayString,
    processTime
	INTEGER,
    processCPUticks
	Counter,
    processCPUticksTotal
	Counter,
    processFss
	INTEGER,
    processPctCPU
	Gauge,
    processRssize
	Gauge,
    processSUID
	INTEGER,
    processUname
	DisplayString,
    processTTY
	DisplayString
}

processPID OBJECT-TYPE
	SYNTAX	INTEGER
	ACCESS	read-only
	STATUS	mandatory
	DESCRIPTION
		"The process ID (pid)."
	::= { processEntry 1 }

processIdx OBJECT-TYPE
	SYNTAX	INTEGER 
	ACCESS	read-only
	STATUS	mandatory
	DESCRIPTION
		"Index for pstat() requests.  SunOS - not implemented."
	::= { processEntry 2 }

processUID OBJECT-TYPE
	SYNTAX	INTEGER 
	ACCESS	read-only
	STATUS	mandatory
	DESCRIPTION
		"Process User ID."
	::= { processEntry 3 }

processPPID OBJECT-TYPE
	SYNTAX	INTEGER 
	ACCESS	read-only
	STATUS	mandatory
	DESCRIPTION
		"Parent process ID."
	::= { processEntry 4 }

processDsize OBJECT-TYPE
	SYNTAX	Gauge 
	ACCESS	read-only
	STATUS	mandatory
	DESCRIPTION
		"Process data size."
	::= { processEntry 5 }

processTsize OBJECT-TYPE
	SYNTAX	Gauge 
	ACCESS	read-only
	STATUS	mandatory
	DESCRIPTION
		"Process text size."
	::= { processEntry 6 }

processSsize OBJECT-TYPE
	SYNTAX	Gauge 
	ACCESS	read-only
	STATUS	mandatory
	DESCRIPTION
		"Process stack size."
	::= { processEntry 7 }

processNice OBJECT-TYPE
	SYNTAX	Gauge 
	ACCESS	read-only
	STATUS	mandatory
	DESCRIPTION
		"Process nice value."
	::= { processEntry 8 }

processMajor OBJECT-TYPE
	SYNTAX	INTEGER 
	ACCESS	read-only
	STATUS	mandatory
	DESCRIPTION
		"Process tty major number.  SunOS - not implemented."
	::= { processEntry 9 }

processMinor OBJECT-TYPE
	SYNTAX	INTEGER 
	ACCESS	read-only
	STATUS	mandatory
	DESCRIPTION
		"Process tty minor number.  SunOS - not implemented."
	::= { processEntry 10 }

processPgrp OBJECT-TYPE
	SYNTAX	INTEGER 
	ACCESS	read-only
	STATUS	mandatory
	DESCRIPTION
		"Process group of this process."
	::= { processEntry 11 }

processPrio OBJECT-TYPE
	SYNTAX	INTEGER 
	ACCESS	read-only
	STATUS	mandatory
	DESCRIPTION
		"Process priority."
	::= { processEntry 12 }

processAddr OBJECT-TYPE
	SYNTAX	INTEGER 
	ACCESS	read-only
	STATUS	mandatory
	DESCRIPTION
		"Address of process (in memory)."
	::= { processEntry 13 }

processCPU OBJECT-TYPE
	SYNTAX	Gauge 
	ACCESS	read-only
	STATUS	mandatory
	DESCRIPTION
		"Processor utilization for scheduling."
	::= { processEntry 14 }

processUtime OBJECT-TYPE
	SYNTAX	TimeTicks
	ACCESS	read-only
	STATUS	mandatory
	DESCRIPTION
		"User time spent executing."
	::= { processEntry 15 }

processStime OBJECT-TYPE
	SYNTAX	TimeTicks 
	ACCESS	read-only
	STATUS	mandatory
	DESCRIPTION
		"System time spent executing."
	::= { processEntry 16 }

processStart OBJECT-TYPE
	SYNTAX	TimeTicks 
	ACCESS	read-only
	STATUS	mandatory
	DESCRIPTION
		"Time Process started."
	::= { processEntry 17 }

processFlags OBJECT-TYPE
	SYNTAX	INTEGER {
		incore(1),
		sys(2),
		locked(4),
		trace(8),
		trace2(16)
		}
	ACCESS	read-only
	STATUS	mandatory
	DESCRIPTION
		"Flags associated with process.  SunOS - values found in
		/usr/include/sys/proc.h."
	::= { processEntry 18 }

processStatus OBJECT-TYPE
	SYNTAX	INTEGER {
		sleep(1),
		run(2),
		stop(3),
		zombie(4),
		other(5),
		idle(6)
		}
	ACCESS	read-only
	STATUS	mandatory
	DESCRIPTION
		"The process status.  SunOS - sleep(1), wait(2), run(3), 
		idle (4), zombie(5), stop(6)"
	::= { processEntry 19 }

processWchan OBJECT-TYPE
	SYNTAX	INTEGER
	ACCESS	read-only
	STATUS	mandatory
	DESCRIPTION
		"If processStatus is sleep, value sleeping on."
	::= { processEntry 20 }

processProcNum OBJECT-TYPE
	SYNTAX	INTEGER
	ACCESS	read-only
	STATUS	mandatory
	DESCRIPTION
		"Processor this process last run on.  SunOS - not
		implemented."
	::= { processEntry 21 }

processCmd OBJECT-TYPE
	SYNTAX	DisplayString
	ACCESS	read-only
	STATUS	mandatory
	DESCRIPTION
		"Command the process is running."
	::= { processEntry 22 }

processTime OBJECT-TYPE
	SYNTAX	INTEGER
	ACCESS	read-only
	STATUS	mandatory
	DESCRIPTION
		"Resident time for scheduling."
	::= { processEntry 23 }

processCPUticks OBJECT-TYPE
	SYNTAX	Counter
	ACCESS	read-only
	STATUS	mandatory
	DESCRIPTION
		"Ticks of cpu time."
	::= { processEntry 24 }

processCPUticksTotal OBJECT-TYPE
	SYNTAX	Counter
	ACCESS	read-only
	STATUS	mandatory
	DESCRIPTION
		"Total ticks for life of process.  SunOS - not
		implemented."
	::= { processEntry 25 }

processFss OBJECT-TYPE
	SYNTAX	INTEGER
	ACCESS	read-only
	STATUS	mandatory
	DESCRIPTION
		"Fair Share Schedular Group.  SunOS - not implemented."
	::= { processEntry 26 }

processPctCPU OBJECT-TYPE
	SYNTAX	Gauge
	ACCESS	read-only
	STATUS	mandatory
	DESCRIPTION
		"Percent CPU * 100 for this process."
	::= { processEntry 27 }

processRssize OBJECT-TYPE
	SYNTAX	Gauge
	ACCESS	read-only
	STATUS	mandatory
	DESCRIPTION
		"Resident Set Size for process (private pages)."
	::= { processEntry 28 }

processSUID OBJECT-TYPE
	SYNTAX	INTEGER
	ACCESS	read-only
	STATUS	mandatory
	DESCRIPTION
		"saved UID."
	::= { processEntry 29 }

processUname OBJECT-TYPE
	SYNTAX	DisplayString
	ACCESS	read-only
	STATUS	mandatory
	DESCRIPTION
		"User name."
	::= { processEntry 30 }

processTTY OBJECT-TYPE
	SYNTAX	DisplayString
	ACCESS	read-only
	STATUS	mandatory
	DESCRIPTION
		"Process TTY.  SunOS - not implemented."
	::= { processEntry 31 }

-- The Ieee8023Mac Group
-- 	This group is not implemented on Solaris.

-- The Ieee8023Mac Table

ieee8023MacTable OBJECT-TYPE
	SYNTAX	SEQUENCE OF Ieee8023MacEntry
	ACCESS 	not-accessible
	STATUS	mandatory
	DESCRIPTION
		"A list of IEEE 802.3 Interface entries."
	::= { ieee8023Mac 1 }

ieee8023MacEntry OBJECT-TYPE
	SYNTAX	Ieee8023MacEntry
	ACCESS 	not-accessible
	STATUS	mandatory
	DESCRIPTION
		"Each entry contains statistics for ieee 802.3
                interfaces."
	INDEX	{ ieee8023MacIndex }
	::= { ieee8023MacTable 1 }

Ieee8023MacEntry ::= SEQUENCE {
    ieee8023MacIndex
	INTEGER,
    ieee8023MacTransmitted
	Counter,
    ieee8023MacNotTransmitted
	Counter,
    ieee8023MacDeferred
	Counter,
    ieee8023MacCollisions
	Counter,
    ieee8023MacSingleCollisions
	Counter,
    ieee8023MacMultipleCollisions
	Counter,
    ieee8023MacExcessCollisions
	Counter,
    ieee8023MacLateCollisions
	Counter,
    ieee8023MacCarrierLostErrors
	Counter,
    ieee8023MacNoHeartBeatErrors
	Counter,
    ieee8023MacFramesReceived
	Counter,
    ieee8023MacUndeliverableFramesReceived
	Counter,
    ieee8023MacCRCErrors
	Counter,
    ieee8023MacAlignmentErrors
	Counter,
    ieee8023MacResourceErrors
	Counter,
    ieee8023MacControlFieldErrors
	Counter,
    ieee8023MacUnknownProtocolErrors
	Counter,
    ieee8023MacMulticastsAccepted
	Counter
}

ieee8023MacIndex OBJECT-TYPE
	SYNTAX	INTEGER
	ACCESS 	read-only
	STATUS  mandatory
	DESCRIPTION
		"The index value that uniquely identifies the
		interface to which this entry is applicable.  The
		interface identified by a particular value of this
		index is the same interface as identified by the
		same value of ifIndex."
	::= { ieee8023MacEntry 1 }

ieee8023MacTransmitted OBJECT-TYPE
	SYNTAX	Counter
	ACCESS 	read-only
	STATUS	mandatory
	DESCRIPTION
		"The number of frames successfully transmitted."
	::= { ieee8023MacEntry 2 }

ieee8023MacNotTransmitted OBJECT-TYPE
	SYNTAX	Counter
	ACCESS 	read-only
	STATUS	mandatory
	DESCRIPTION
		"The number of frames not transmitted."
	::= { ieee8023MacEntry 3 }

ieee8023MacDeferred OBJECT-TYPE
	SYNTAX	Counter
	ACCESS 	read-only
	STATUS	mandatory
	DESCRIPTION
		"The number of frames deferred because the medium
		was busy."
	::= { ieee8023MacEntry 4 }

ieee8023MacCollisions OBJECT-TYPE
	SYNTAX	Counter
	ACCESS 	read-only
	STATUS	mandatory
	DESCRIPTION
		"Total number of transmit attempts that were
		retransmitted due to collisions.  SunOS with Intel 82586
		Ethernet driver - total number of collisions."
	::= { ieee8023MacEntry 5 }

ieee8023MacSingleCollisions OBJECT-TYPE
	SYNTAX	Counter
	ACCESS 	read-only
	STATUS	mandatory
	DESCRIPTION
		"Number of transmit attempts that are involved in a
		single collision and are subsequently transmitted
		successfully.  SunOS - this is always 0."
	::= { ieee8023MacEntry 6 }

ieee8023MacMultipleCollisions OBJECT-TYPE
	SYNTAX	Counter
	ACCESS 	read-only
	STATUS	mandatory
	DESCRIPTION
		"Number of transmit attempts that are involved in
		between 2 and 15 collision attempts and are
		subsequently transmitted successfully.  SunOS with Intel
		82586 is always 0.  SunOS with AMD 7990 LANCE driver -
		number of transmit attempts that are involved in between
		1 and 15 collision attempts and are subsequently
		transmitted successfully."
	::= { ieee8023MacEntry 7 }

ieee8023MacExcessCollisions OBJECT-TYPE
	SYNTAX	Counter
	ACCESS 	read-only
	STATUS	mandatory
	DESCRIPTION
		"Number of transmit attempts that are involved in
		more than 15 collision attempts and are subsequently
		transmitted successfully.  SunOS with Intel 82586
		Ethernet driver - this is always 0."
	::= { ieee8023MacEntry 8 }

ieee8023MacLateCollisions OBJECT-TYPE
	SYNTAX	Counter
	ACCESS 	read-only
	STATUS	mandatory
	DESCRIPTION
		"Number of transmit attempts aborted because a
		collision occurred after the allotted channel time
		had elapsed."
	::= { ieee8023MacEntry 9 }

ieee8023MacCarrierLostErrors OBJECT-TYPE
	SYNTAX	Counter
	ACCESS 	read-only
	STATUS	mandatory
	DESCRIPTION
		"Number of times that carrier sense was lost when
		attempting to transmit."
	::= { ieee8023MacEntry 10 }

ieee8023MacNoHeartBeatErrors OBJECT-TYPE
	SYNTAX	Counter
	ACCESS 	read-only
	STATUS	mandatory
	DESCRIPTION
		"Number of times no heart beat was indicated after a
		transmission."
	::= { ieee8023MacEntry 11 }

ieee8023MacFramesReceived OBJECT-TYPE
	SYNTAX	Counter
	ACCESS 	read-only
	STATUS	mandatory
	DESCRIPTION
		"Number of frames successfully received."
	::= { ieee8023MacEntry 12 }

ieee8023MacUndeliverableFramesReceived OBJECT-TYPE
	SYNTAX	Counter
	ACCESS 	read-only
	STATUS	mandatory
	DESCRIPTION
		"Number of frames received that were not delivered
		because the software buffer was overrun when frames
		were sent faster than they could be received."
	::= { ieee8023MacEntry 13 }

ieee8023MacCRCErrors OBJECT-TYPE
	SYNTAX	Counter
	ACCESS 	read-only
	STATUS	mandatory
	DESCRIPTION
		"Number of Cyclical Redundancy Check (CRC) errors
		detected."
	::= { ieee8023MacEntry 14 }

ieee8023MacAlignmentErrors OBJECT-TYPE
	SYNTAX	Counter
	ACCESS 	read-only
	STATUS	mandatory
	DESCRIPTION
	        "Number of frames received that were both misaligned
		and had bad CRC."
	::= { ieee8023MacEntry 15 }

ieee8023MacResourceErrors OBJECT-TYPE
	SYNTAX	Counter
	ACCESS 	read-only
	STATUS	mandatory
	DESCRIPTION
		"Number of frames received that were lost due to lack
		of resources."
	::= { ieee8023MacEntry 16 }

ieee8023MacControlFieldErrors OBJECT-TYPE
	SYNTAX	Counter
	ACCESS 	read-only
	STATUS	mandatory
	DESCRIPTION
		"Number of frames received with errors in the control
		field.  SunOS - this is always 0."
	::= { ieee8023MacEntry 17 }

ieee8023MacUnknownProtocolErrors OBJECT-TYPE
	SYNTAX	Counter
	ACCESS 	read-only
	STATUS	mandatory
	DESCRIPTION
		"Number of frames dropped because the type field
		or sap field referenced an invalid protocol.  SunOS -
		this is always 0."
	::= { ieee8023MacEntry 18 }

ieee8023MacMulticastsAccepted OBJECT-TYPE
	SYNTAX	Counter
	ACCESS 	read-only
	STATUS	mandatory
	DESCRIPTION
		"Number of accepted muliticast addresses."
	::= { ieee8023MacEntry 19 }

-- The Icmp Group

icmpEchoReq OBJECT-TYPE
	SYNTAX	INTEGER
	ACCESS 	read-only
	STATUS	mandatory
	DESCRIPTION
		"The number of milliseconds it takes for an ICMP
		echo request to respond.  IcmpEchoReq is 
		    -1 if there is an internal error, 
		    -2 if the echo request timed out, 
		    -3 if the echo reply is not the correct reply,
		    -4 if the packet size is too large, and 
		    -5 if the timeout is invalid.

		To request the ICMP response time for IP address
		a1.a2.a3.a4 with a timeout of t and a packet size of s,
		send a request for icmpEchoReq.s.t.a1.a2.a3.a4.

		For example, suppose one wanted to find out the number
		of milliseconds it took to ping 15.2.112.113, with time
		out of 8 seconds, and packet size of 75.  Accordingly,
		icmpEchoReq.75.8.15.2.112.113 would identify the number
		of milliseconds.

		This MIB object is there only to provide for backward
		compatibility. A new MIB object is provided which does not
		violate the SNMP standards too,
		'icmp.icmpEchoReqTable.icmpEchoReqEntry.icmpEchoReqTime'.
		This new MIB object is recommended to be used to achieve the
		same funtionality as provided by this (icmp.icmpEchoReq)
		MIB object."
	::= { icmp 1 }

icmpEchoReqTable OBJECT-TYPE
    SYNTAX  SEQUENCE OF IcmpEchoReqEntry
    ACCESS  not-accessible
    STATUS  mandatory
    DESCRIPTION
        "A conceptual table holding the ICMP response times for
        various remote hosts. The table is a conceptual one in the
        sense that, the table actually contains no data. When a query
        for the table object icmpEchoReqTime is received by the agent
        an ICMP echo request is sent to the remote host, the ICMP
        echo reply is received, the elapsed time is calculated and
        is sent back as the response. Note that except the columnar
        object icmpEchoReqTime other objects in the table, viz.,
        icmpEchoReqPktSize, icmpEchoReqTimeout and icmpEchoReqHost,
        have ACCESS previlege as not-accessible, those variables
        cannot be queried for.

        The table entries have the objects icmpEchoReqPktSize,
        icmpEchoReqTimeout and icmpEchoReqHost as the indices, which
        is effectively a way of transfering these required details
        to the agent, so that the agent could do its function and
        respond appropriately."
    ::= { icmp 2 }

icmpEchoReqEntry OBJECT-TYPE
    SYNTAX  IcmpEchoReqEntry
    ACCESS  not-accessible
    STATUS  mandatory
    DESCRIPTION
        "Each entry in the table icmpEchoReqTable is a conceptual one.
        See description of icmpEchoReqTable for more details."
    INDEX { icmpEchoReqPktSize, icmpEchoReqTimeOut, icmpEchoReqHost }
    ::= { icmpEchoReqTable 1 }

IcmpEchoReqEntry ::=
    SEQUENCE {
        icmpEchoReqTime
            INTEGER,
        icmpEchoReqPktSize
            INTEGER,
        icmpEchoReqTimeOut
            INTEGER,
        icmpEchoReqHost
            IpAddress
    }

icmpEchoReqTime OBJECT-TYPE
    SYNTAX  INTEGER
    ACCESS  read-only
    STATUS  mandatory
    DESCRIPTION
        "The elapsed time between the time the ICMP echo request is
        sent to the host identified by the index object icmpEchoReqHost
        and the time the ICMP echo reply is received at the agent host.
        The ICMP packet size and the time out to be used for the
        ICMP echo request are identified by the indices
        icmpEchoReqPktSize and icmpEchoReqTimeOut. See description
        of icmpEchoReqTable for more details.

        In other words, the number of milliseconds it takes for
        an ICMP echo request to respond. Other return values:
            -1 if there is an internal error,
            -2 if the echo request timed out,
            -3 if the echo reply is not the correct reply,
            -4 if the packet size is too large, and
            -5 if the timeout is invalid.

        To request the ICMP response time for IP address
        a1.a2.a3.a4 with a timeout of t and a packet size of s,
        send a request for icmpEchoReqTime.s.t.a1.a2.a3.a4.

        For example, suppose one wanted to find out the number
        of milliseconds it took to ping 15.2.112.113, with time
        out of 8 seconds, and packet size of 75.  Accordingly,
        icmpEchoReqTime.75.8.15.2.112.113 would identify the
        number of milliseconds."
    ::= { icmpEchoReqEntry 1 }

icmpEchoReqPktSize OBJECT-TYPE
    SYNTAX  INTEGER
    ACCESS  not-accessible
    STATUS  mandatory
    DESCRIPTION
        "The packet size to be used for the ICMP echo request, see
        description of icmpEchoReqTable for more details.

        The object serves as the first index out of three indices
        used when the object icmpEchoReqTime is queried. Note that
        this object's value cannot be queried for, this object serves
        as an input to the agent itself and a query for this object
        makes no sense."
    ::= { icmpEchoReqEntry 2 }

icmpEchoReqTimeOut OBJECT-TYPE
    SYNTAX  INTEGER
    ACCESS  not-accessible
    STATUS  mandatory
    DESCRIPTION
        "The time period in seconds to wait for an ICMP echo reply
        message after an ICMP echo request is sent to the identified
        host, see description of icmpEchoReqTable for more details.

        The object serves as the second index out of three indices
        used when the object icmpEchoReqTime is queried. Note that
        this object's value cannot be queried for, this object serves
        as an input to the agent itself and a query for this object
        makes no sense."
    ::= { icmpEchoReqEntry 3 }

icmpEchoReqHost OBJECT-TYPE
    SYNTAX  IpAddress
    ACCESS  not-accessible
    STATUS  mandatory
    DESCRIPTION
        "The host to which the ICMP echo request is to be sent,
        the ping time between the host identified by this index
        object and the agent's host is what is queried for, see
        description of icmpEchoReqTable for more details.

        The object serves as the last index out of three indices
        used when the object icmpEchoReqTime is queried. Note that
        this object's value cannot be queried for, this object serves
        as an input to the agent itself and a query for this object
        makes no sense."
    ::= { icmpEchoReqEntry 4 }

-- The Trap Group

trapDestinationNum OBJECT-TYPE
	SYNTAX	Gauge
	ACCESS 	read-only
	STATUS	mandatory
	DESCRIPTION
		"The number of trap destinations."
	::= { trap 1 }

-- The Trap Destination Table

trapDestinationTable OBJECT-TYPE
	SYNTAX	SEQUENCE OF TrapDestinationEntry
	ACCESS 	not-accessible
	STATUS	mandatory
	DESCRIPTION
		"List of addresses to which the agent sends traps."
	::= { trap 2 }

trapDestinationEntry OBJECT-TYPE
	SYNTAX	TrapDestinationEntry
	ACCESS 	not-accessible
	STATUS	mandatory
	DESCRIPTION
		"Each entry contains the address of a management
		station."
	INDEX	{ trapDestination }
	::= { trapDestinationTable 1 }

TrapDestinationEntry ::= SEQUENCE {
    trapDestination
	IpAddress
}

trapDestination OBJECT-TYPE
	SYNTAX	IpAddress
	ACCESS 	read-write
	STATUS	mandatory
	DESCRIPTION
		"Address to which the agent sends traps."
    	::= { trapDestinationEntry 1 }

-- The SnmpdConf Group

snmpdConfRespond OBJECT-TYPE
	SYNTAX	INTEGER {
		    true(1),
		    false(2)
		}
	ACCESS 	read-write
	STATUS	mandatory
	DESCRIPTION
		"The SNMP agent was configured to respond to all
		objects if snmpdConfRespond is true.  HP-Internal
		use only."
	::= { snmpdConf 1 }

snmpdReConfigure OBJECT-TYPE
	SYNTAX	INTEGER {
		    reset(1)
		}
	ACCESS 	read-write
	STATUS	mandatory
	DESCRIPTION
		"The agent will re-configure itself if
		snmpdReConfigure is set to reset(1)"
	::= { snmpdConf 2 }

snmpdFlag OBJECT-TYPE
	SYNTAX	INTEGER {
		    removetrap(1),
		    netwareproxy(2)
		}
	ACCESS 	read-only
	STATUS	mandatory
	DESCRIPTION
		"Indicates the capability of the agent."
	::= { snmpdConf 3 }

snmpdLogMask	OBJECT-TYPE
	SYNTAX	INTEGER
	ACCESS 	read-write
	STATUS	mandatory
	DESCRIPTION
		"The agent's log mask."
	::= { snmpdConf 4 }

snmpdVersion	OBJECT-TYPE
	SYNTAX	INTEGER
	ACCESS 	read-only
	STATUS	mandatory
	DESCRIPTION
		"The agent's version number."
	::= { snmpdConf 5 }

snmpdStatus OBJECT-TYPE
	SYNTAX	INTEGER {
		    up(1),
		    down(2)
		}
	ACCESS 	read-write
	STATUS	mandatory
	DESCRIPTION
		"Indicates the status of the agent.  Setting 
		the agent to down will kill it."
	::= { snmpdConf 6 }

snmpdSize OBJECT-TYPE
	SYNTAX	INTEGER
	ACCESS 	read-only
	STATUS	mandatory
	DESCRIPTION
		"The amount of memory the agent has allocated."
	::= { snmpdConf 7 }

snmpdWhatString OBJECT-TYPE
	SYNTAX	DisplayString
	ACCESS 	read-only
	STATUS	mandatory
	DESCRIPTION
		"The what string of the agent."
	::= { snmpdConf 9 }

-- The Cluster Group
--
-- 	This group is not implemented on SunOS/Solaris.

isClustered	OBJECT-TYPE
	SYNTAX	INTEGER {
		standalone(1),
		rootserver(2),
		cnode(3)
	    }
	ACCESS read-only
	STATUS	mandatory
	DESCRIPTION
		"Describes whether machine is clustered or not."
	::= { cluster 1 }

clusterTable	OBJECT-TYPE
	SYNTAX	SEQUENCE OF ClusterEntry
	ACCESS	not-accessible
	STATUS	mandatory
	DESCRIPTION
		"List of nodes on the cluster."
	::= { cluster 2 }

clusterEntry OBJECT-TYPE
	SYNTAX	ClusterEntry
	ACCESS	not-accessible
	STATUS	mandatory
	DESCRIPTION
		"Each entry contains information about the clustered
		node."
	INDEX {clusterID }
	::= { clusterTable 1 }

ClusterEntry ::= SEQUENCE {
    clusterID
	INTEGER,
    clusterMachineID
	OCTET STRING,
    clusterType
	DisplayString,
    clusterCnodeName
	DisplayString,
    clusterSwapServingCnode
	INTEGER,
    clusterKcsp
	INTEGER,
    clusterCnodeAddress
	IpAddress
}

clusterID OBJECT-TYPE
	SYNTAX	INTEGER
	ACCESS 	read-only
	STATUS	mandatory
	DESCRIPTION
		"The cnode id."
    	::= { clusterEntry 1 }

clusterMachineID OBJECT-TYPE
	SYNTAX	OCTET STRING
	ACCESS 	read-only
	STATUS	mandatory
	DESCRIPTION
		"The cnode machine id."
    	::= { clusterEntry 2 }

clusterType OBJECT-TYPE
	SYNTAX	DisplayString
	ACCESS 	read-only
	STATUS	mandatory
	DESCRIPTION
		"The cnode type (r or c)."
    	::= { clusterEntry 3 }

clusterCnodeName OBJECT-TYPE
	SYNTAX	DisplayString
	ACCESS 	read-only
	STATUS	mandatory
	DESCRIPTION
		"The cnode name."
    	::= { clusterEntry 4 }

clusterSwapServingCnode OBJECT-TYPE
	SYNTAX	INTEGER
	ACCESS 	read-only
	STATUS	mandatory
	DESCRIPTION
		"The swap serving cnode."
    	::= { clusterEntry 5 }

clusterKcsp OBJECT-TYPE
	SYNTAX	INTEGER
	ACCESS 	read-only
	STATUS	mandatory
	DESCRIPTION
		"KCSP."
    	::= { clusterEntry 6 }

clusterCnodeAddress OBJECT-TYPE
	SYNTAX	IpAddress
	ACCESS 	read-only
	STATUS	mandatory
	DESCRIPTION
		"The cnode IP Address."
    	::= { clusterEntry 7 }

clusterCnodeID	OBJECT-TYPE
	SYNTAX	INTEGER
	ACCESS 	read-only
	STATUS	mandatory
	DESCRIPTION
		"The machine's cnodes id"
    	::= { cluster 3 }

-- The AuthFail Group

authFailTable OBJECT-TYPE
	SYNTAX	SEQUENCE OF AuthFailEntry
	ACCESS 	not-accessible
	STATUS	mandatory
	DESCRIPTION
		"List of managers that caused an authentication failure.
		This list has a maximum size."
	::= { authfail 1 }

authFailEntry OBJECT-TYPE
	SYNTAX	AuthFailEntry
	ACCESS 	not-accessible
	STATUS	mandatory
	DESCRIPTION
		"Each entry contains the ip address of the management
		station."
	INDEX	{ authIpAddress }
	::= { authFailTable 1 }

AuthFailEntry ::= SEQUENCE {
    authIpAddress
	NetworkAddress,
    authTime
	TimeTicks,
    authCommunityName 
	OCTET STRING
}

authIpAddress OBJECT-TYPE
	SYNTAX	NetworkAddress
	ACCESS 	read-only
	STATUS	mandatory
	DESCRIPTION
		"The ip address of the management station that sent a
		request to the agent with an incorrect community name."
    	::= { authFailEntry 1 }

authTime OBJECT-TYPE
	SYNTAX	TimeTicks
	ACCESS 	read-only
	STATUS	mandatory
	DESCRIPTION
		"The time since the agent received the un-authenticated 
		request."
    	::= { authFailEntry 2 }

authCommunityName OBJECT-TYPE
	SYNTAX	OCTET STRING
	ACCESS 	read-only
	STATUS	mandatory
	DESCRIPTION
		"The community name used in the request"
    	::= { authFailEntry 3 }

-- the OpenView trap variables Group
-- These object ID's cannot be retrieved from the SNMP Agent, but
--  instead document the objects sent with OpenView SNMP traps
 
openViewSourceId OBJECT-TYPE
	SYNTAX	INTEGER
	ACCESS	not-accessible
	STATUS	mandatory
	DESCRIPTION
		"The identifier of the software generating the trap/event.
		 This number is used by HP OpenView software when it sends
		 an event to the OpenView event system.  It identifies
		 which software component sent the event.
		 
		 This object cannot be retrieved from the SNMP agent."
	::= { openViewTrapVars 1 }

openViewSourceName OBJECT-TYPE
	SYNTAX	OCTET STRING
	ACCESS	not-accessible
	STATUS	mandatory
	DESCRIPTION
		"The source of the event (may not be the machine upon
		 which the event was generated).  This string is used
		 by HP OpenView software when it sends an event.  It
		 identifies for which source (node) the event is generated.

		 This object cannot be retrieved from the SNMP agent."
	::= { openViewTrapVars 2 }

openViewObjectId OBJECT-TYPE
	SYNTAX	OCTET STRING
	ACCESS	not-accessible
	STATUS	mandatory
	DESCRIPTION
		"The OpenView object identifier associated with the
		 source of the trap/event.

		 This object cannot be retrieved from the SNMP agent."
	::= { openViewTrapVars 3 }

openViewData OBJECT-TYPE
	SYNTAX	OCTET STRING
	ACCESS	not-accessible
	STATUS	mandatory
	DESCRIPTION
		"Any miscellaneous data sent with an OpenView trap/event.

		 This object cannot be retrieved from the SNMP agent."
	::= { openViewTrapVars 4 }

openViewSeverity OBJECT-TYPE
	SYNTAX	OCTET STRING
	ACCESS	not-accessible
	STATUS	mandatory
	DESCRIPTION
		"The OpenView event severity associated with the trap/event.

		 This object cannot be retrieved from the SNMP agent."
	::= { openViewTrapVars 5 }

openViewCategory OBJECT-TYPE
	SYNTAX	OCTET STRING
	ACCESS	not-accessible
	STATUS	mandatory
	DESCRIPTION
		"The OpenView event category associated with the trap/event.

		 This object cannot be retrieved from the SNMP agent."
	::= { openViewTrapVars 6 }

openViewFilter OBJECT-TYPE
	SYNTAX	OCTET STRING
	ACCESS	not-accessible
	STATUS	mandatory
	DESCRIPTION
		"The event filter for an application connecting to the
		 OpenView event system.

		 This object cannot be retrieved from the SNMP agent."
	::= { openViewTrapVars 7 }

openViewEntity OBJECT-TYPE
	SYNTAX	OCTET STRING
	ACCESS	not-accessible
	STATUS	mandatory
	DESCRIPTION
		"The entity (string name) of an application connecting
		 to the OpenView event system.

		 This object cannot be retrieved from the SNMP agent."
	::= { openViewTrapVars 8 }

openViewAddress OBJECT-TYPE
	SYNTAX	OCTET STRING
	ACCESS	not-accessible
	STATUS	mandatory
	DESCRIPTION
		"The IP address of the node from where an application
		 is connecting to the OpenView event system.

		 This object cannot be retrieved from the SNMP agent."
	::= { openViewTrapVars 9 }

openViewPid OBJECT-TYPE
	SYNTAX	OCTET STRING
	ACCESS	not-accessible
	STATUS	mandatory
	DESCRIPTION
		"The process ID of an application connecting to the
		 OpenView event system.

		 This object cannot be retrieved from the SNMP agent."
	::= { openViewTrapVars 10 }

END
