-- ===========================================================================================================
-- Copyright (c) 2004-2013 Hangzhou H3C Tech. Co., Ltd. All rights reserved.
--
-- Description: Mdc MIB
-- Reference:
-- Version: V1.0
-- History:
-- revision 1.0 2013-03-05 created by c08124
--
-- ============================================================================================================
H3C-MDC-MIB DEFINITIONS ::= BEGIN

IMPORTS
    entPhysicalIndex
        FROM ENTITY-MIB
    h3cCommon
        FROM HUAWEI-3COM-OID-MIB
    Integer32, Unsigned32, OBJECT-TYPE, MODULE-IDENTITY, NOTIFICATION-TYPE
        FROM SNMPv2-SMI
    DisplayString, RowStatus, TruthValue, TEXTUAL-CONVENTION
        FROM SNMPv2-TC;

h3cMDC MODULE-IDENTITY
    LAST-UPDATED "201303051448Z"
    ORGANIZATION
        "Hangzhou H3C Tech. Co., Ltd."
    CONTACT-INFO
        "Platform Team Hangzhou H3C Tech. Co., Ltd.
        Hai-Dian District Beijing P.R. China
        http://www.h3c.com
        Zip:100085"
    DESCRIPTION
        "This MIB contains objects to manage MDC (Multitenant Device Context) operations.

        Such as:
        1. Configure MDCs for a device and display MDCs and their status.
        2. Assign CPU, storage space, and memory space resources to the MDC, and display their status.
        3. Authorize the MDC to use the interface cards, and assign physical interfaces to an MDC.

        Default MDC: A device supporting MDCs is an MDC itself, and it is called the default MDC.
        From the default MDC, administrators can manage the entire physical device, create and delete non-default MDCs,
        and assign interfaces, CPU resources, storage space, and memory space to non-default MDCs.

        Non-default MDC: No MDCs can be created on a non-default MDC.
        Administrators of non-default MDCs can only manage and maintain their respective MDCs.
        A non-default MDC can use only the resources assigned to it."
    REVISION "201303051448Z"
    DESCRIPTION
        "The initial revision of this MIB module."
    ::= { h3cCommon 136 }


-- Scalar MIB objects, which are considered as global variables
-- Global Level Configuration
H3cMdcActionValue ::= TEXTUAL-CONVENTION
    STATUS current
    DESCRIPTION
        "start: start the MDC
         stop: stop the MDC"
    SYNTAX INTEGER
        {
            start(1),
            stop(2)
        }

H3cMdcRunStatus ::= TEXTUAL-CONVENTION
    STATUS current
    DESCRIPTION
        "Status of the MDC:
        inactive: The MDC is stopped or not started yet.
        starting: The device is executing the mdc start command to start the MDC.
        active: The MDC is operating properly.
        stopping: The device is executing the undo mdc start command to stop the MDC.
        updating: The device is executing the location command to authorize the MDC to use an interface card."
    SYNTAX INTEGER
        {
            inactive(1),
            starting(2),
            active(3),
            stopping(4),
            updating(5)
        }


-- Node definitions

h3cMDCScalarObjects OBJECT IDENTIFIER ::= { h3cMDC 1 }

h3cMDCMaxMDCNum OBJECT-TYPE
    SYNTAX Integer32
    MAX-ACCESS read-only
    STATUS current
    DESCRIPTION
        "The maximum number of MDCs which the system supported to create."
    ::= { h3cMDCScalarObjects 1 }


h3cMDCCurrentMDCNum OBJECT-TYPE
    SYNTAX Integer32
    MAX-ACCESS read-only
    STATUS current
    DESCRIPTION
        "The current number of MDCs which the system has created."
    ::= { h3cMDCScalarObjects 2 }

h3cMDCTables OBJECT IDENTIFIER ::= { h3cMDC 2 }

-- The operation and information for MDC.
h3cMDCControl OBJECT IDENTIFIER ::= { h3cMDCTables 1 }


h3cMDCControlTable OBJECT-TYPE
    SYNTAX SEQUENCE OF H3cMDCControlEntry
    MAX-ACCESS not-accessible
    STATUS current
    DESCRIPTION
        "This table is used to configure MDCs for a device and show MDC's status."
    ::= { h3cMDCControl 1 }


h3cMDCControlEntry OBJECT-TYPE
    SYNTAX H3cMDCControlEntry
    MAX-ACCESS not-accessible
    STATUS current
    DESCRIPTION
        "An entry of the h3cMDCControlTable, every entry is corresponding with an MDC."
    INDEX { h3cMDCIndex }
    ::= { h3cMDCControlTable 1 }


H3cMDCControlEntry ::=
    SEQUENCE
        {
            h3cMDCIndex
                Integer32,
            h3cMDCName
                DisplayString,
            h3cMDCAction
                H3cMdcActionValue,
            h3cMDCStatus
                H3cMdcRunStatus,
            h3cMDCRowStatus
                RowStatus
        }

h3cMDCIndex OBJECT-TYPE
    SYNTAX Integer32 (1..2147483647)
    MAX-ACCESS accessible-for-notify
    STATUS current
    DESCRIPTION
        "MDC ID is used as MDCIndex, the value range of MDC ID depends on the device model.
         MDCIndex cannot be modified after creation."
    ::= { h3cMDCControlEntry 1 }


h3cMDCName OBJECT-TYPE
    SYNTAX DisplayString (SIZE (1..15))
    MAX-ACCESS read-create
    STATUS current
    DESCRIPTION
        "Specifies the MDC name, a case-sensitive string of 1 to 15 characters.
        The MDC name cannot be modified after creation."
    ::= { h3cMDCControlEntry 2 }


h3cMDCAction OBJECT-TYPE
    SYNTAX H3cMdcActionValue
    MAX-ACCESS read-write
    STATUS current
    DESCRIPTION
        "State of MDC action: start/stop.
        After an MDC is started, administrators of the MDC can log in to
        the MDC for MDC configuration and maintenance.
        Stopping an MDC interrupts all services on the MDC and logs out
        all users of the MDC.

        Non-default MDC cannot operate."
    DEFVAL { stop }
    ::= { h3cMDCControlEntry 3 }


h3cMDCStatus OBJECT-TYPE
    SYNTAX H3cMdcRunStatus
    MAX-ACCESS read-only
    STATUS current
    DESCRIPTION
        "Status of MDCs."
    ::= { h3cMDCControlEntry 4 }


h3cMDCRowStatus OBJECT-TYPE
    SYNTAX RowStatus
    MAX-ACCESS read-create
    STATUS current
    DESCRIPTION
        "The status of this table entry.
        Only support active, createAndGo and destroy."
    ::= { h3cMDCControlEntry 5 }


h3cMDCResource OBJECT IDENTIFIER ::= { h3cMDCTables 2 }


h3cMDCDISKResourceTable OBJECT-TYPE
    SYNTAX SEQUENCE OF H3cMDCDISKResourceEntry
    MAX-ACCESS not-accessible
    STATUS current
    DESCRIPTION
        "This table is for disk resource management:
        Specify a disk space percentage for an MDC and display the disk space usage.

        Default: All MDCs share the disk space in the system,
        and an MDC can use all free disk space in the system.

        Non-default MDC can only query the disk space usage."
    ::= { h3cMDCResource 1 }


h3cMDCDISKResourceEntry OBJECT-TYPE
    SYNTAX H3cMDCDISKResourceEntry
    MAX-ACCESS not-accessible
    STATUS current
    DESCRIPTION
        "An entry of the h3cMDCDISKResourceTable, every entry is corresponding to
        disk resource of an MDC.

        Note that only entPhysicalIndex values that represent
        physical boards (i.e., associated entPhysicalClass value is
        'module(9)') are permitted to exist in this table."
    INDEX { entPhysicalIndex, h3cMDCIndex, h3cMDCDISKResourceInstance }
    ::= { h3cMDCDISKResourceTable 1 }


H3cMDCDISKResourceEntry ::=
    SEQUENCE {
        h3cMDCDISKResourceInstance
            Integer32,
        h3cMDCDISKResourceInstanceName
            DisplayString,
        h3cMDCDISKResourceMinLimit
            Integer32,
        h3cMDCDISKResourceMaxLimit
            Integer32,
        h3cMDCDISKResourceReserve
            Unsigned32,
        h3cMDCDISKResourceQuota
            Unsigned32,
        h3cMDCDISKResourceUsage
            Unsigned32,
        h3cMDCDISKResourceAvailable
            Unsigned32
     }

h3cMDCDISKResourceInstance OBJECT-TYPE
    SYNTAX Integer32 (1..2147483647)
    MAX-ACCESS not-accessible
    STATUS current
    DESCRIPTION
        "Instance index of disk resource.
         Different instances for disk: Flash, CF cards."
    ::= { h3cMDCDISKResourceEntry 1 }


h3cMDCDISKResourceInstanceName OBJECT-TYPE
    SYNTAX DisplayString (SIZE (1..32))
    MAX-ACCESS read-only
    STATUS current
    DESCRIPTION
        "Instance name of disk resource.

        Such as: Flash, CF cards."
    ::= { h3cMDCDISKResourceEntry 2 }


h3cMDCDISKResourceMinLimit OBJECT-TYPE
    SYNTAX Integer32 (0..100)
    UNITS       "percent"
    MAX-ACCESS read-write
    STATUS current
    DESCRIPTION
        "Limit minimum (reserve resources, must be all 0)."
    ::= { h3cMDCDISKResourceEntry 3 }


h3cMDCDISKResourceMaxLimit OBJECT-TYPE
    SYNTAX Integer32 (1..100)
    UNITS       "percent"
    MAX-ACCESS read-write
    STATUS current
    DESCRIPTION
        "Maximum of available resources of disk.
        Make sure the disk space amount assigned to an MDC is
        greater than the disk space amount the MDC is using.
        Non-default MDC cannot set"
    ::= { h3cMDCDISKResourceEntry 4 }

h3cMDCDISKResourceReserve OBJECT-TYPE
    SYNTAX Unsigned32
    UNITS       "KB"
    MAX-ACCESS read-only
    STATUS current
    DESCRIPTION
        "The reserve limit resources of disk."
    ::= { h3cMDCDISKResourceEntry 5 }

h3cMDCDISKResourceQuota OBJECT-TYPE
    SYNTAX Unsigned32
    UNITS       "KB"
    MAX-ACCESS read-only
    STATUS current
    DESCRIPTION
        "The total limit resources of disk according to h3cMDCDiskResourceMaxLimit."
    ::= { h3cMDCDISKResourceEntry 6 }


h3cMDCDISKResourceUsage OBJECT-TYPE
    SYNTAX Unsigned32
    UNITS       "KB"
    MAX-ACCESS read-only
    STATUS current
    DESCRIPTION
        "Current usage of disk resources."
    ::= { h3cMDCDISKResourceEntry 7 }


h3cMDCDISKResourceAvailable OBJECT-TYPE
    SYNTAX Unsigned32
    UNITS       "KB"
    MAX-ACCESS read-only
    STATUS current
    DESCRIPTION
        "Current available resources of disk."
    ::= { h3cMDCDISKResourceEntry 8 }

h3cMDCMemoryResourceTable OBJECT-TYPE
    SYNTAX SEQUENCE OF H3cMDCMemoryResourceEntry
    MAX-ACCESS not-accessible
    STATUS current
    DESCRIPTION
        "This table is for memory resource management:
         Specify a memory space percentage for an MDC and display the memory space usage.
         Default: All MDCs share the memory space in the system, and an MDC can use all free memory.

         Non-default MDC can only query resource message of memory."
    ::= { h3cMDCResource 2 }


h3cMDCMemoryResourceEntry OBJECT-TYPE
    SYNTAX H3cMDCMemoryResourceEntry
    MAX-ACCESS not-accessible
    STATUS current
    DESCRIPTION
        "An entry of the h3cMDCMemoryResourceTable, every entry is corresponding
        with memory resource of an MDC.

        Note that only entPhysicalIndex values that represent
        physical boards (i.e., associated entPhysicalClass value is
        'module(9)') are permitted to exist in this table."
    INDEX { entPhysicalIndex, h3cMDCIndex }
    ::= { h3cMDCMemoryResourceTable 1 }


H3cMDCMemoryResourceEntry ::=
    SEQUENCE {
        h3cMDCMemoryResourceMinLimit
            Integer32,
        h3cMDCMemoryResourceMaxLimit
            Integer32,
        h3cMDCMemoryResourceReserve
            Unsigned32,
        h3cMDCMemoryResourceQuota
            Unsigned32,
        h3cMDCMemoryResourceUsage
            Unsigned32,
        h3cMDCMemoryResourceAvailable
            Unsigned32
     }

h3cMDCMemoryResourceMinLimit OBJECT-TYPE
    SYNTAX Integer32 (0..100)
    UNITS       "percent"
    MAX-ACCESS read-write
    STATUS current
    DESCRIPTION
        "Limit minimum(reserve resources, must be all 0).

        Non-default MDC cannot set."
    ::= { h3cMDCMemoryResourceEntry 1 }


h3cMDCMemoryResourceMaxLimit OBJECT-TYPE
    SYNTAX Integer32 (1..100)
    UNITS       "percent"
    MAX-ACCESS read-write
    STATUS current
    DESCRIPTION
        "Maximum of available resources of memory,
        it specifies the ratio of the memory space that an MDC can use.
        Make sure this amount is sufficient for the MDC to operate properly.
        Non-default MDC cannot set."
    ::= { h3cMDCMemoryResourceEntry 2 }

h3cMDCMemoryResourceReserve OBJECT-TYPE
    SYNTAX Unsigned32
    UNITS       "KB"
    MAX-ACCESS read-only
    STATUS current
    DESCRIPTION
        "The reserve limit resources of memory."
    ::= { h3cMDCMemoryResourceEntry 3 }

h3cMDCMemoryResourceQuota OBJECT-TYPE
    SYNTAX Unsigned32
    UNITS       "KB"
    MAX-ACCESS read-only
    STATUS current
    DESCRIPTION
        "The total limit resources of memory."
    ::= { h3cMDCMemoryResourceEntry 4 }

h3cMDCMemoryResourceUsage OBJECT-TYPE
    SYNTAX Unsigned32
    UNITS       "KB"
    MAX-ACCESS read-only
    STATUS current
    DESCRIPTION
        "Current usage of memory resources."
    ::= { h3cMDCMemoryResourceEntry 5 }

h3cMDCMemoryResourceAvailable OBJECT-TYPE
    SYNTAX Unsigned32
    UNITS       "KB"
    MAX-ACCESS read-only
    STATUS current
    DESCRIPTION
        "Current available value of memory resources."
    ::= { h3cMDCMemoryResourceEntry 6 }

h3cMDCCPUResourceTable OBJECT-TYPE
    SYNTAX SEQUENCE OF H3cMDCCPUResourceEntry
    MAX-ACCESS not-accessible
    STATUS current
    DESCRIPTION
        "This table is for CPU resource management:
        Specify a CPU weight for an MDC and display the CPU usage.
        The amount of CPU resources an MDC can use depends on the CPU weight
        settings for all MDCs that share the same CPU.

        Non-default MDC can only query CPU resources."
    ::= { h3cMDCResource 3 }


h3cMDCCPUResourceEntry OBJECT-TYPE
    SYNTAX H3cMDCCPUResourceEntry
    MAX-ACCESS not-accessible
    STATUS current
    DESCRIPTION
        "An entry of the h3cMDCCPUResourceTable, every entry is corresponding
        with CPU resources of an MDC.

        Note that only entPhysicalIndex values that represent
        physical boards (i.e., associated entPhysicalClass value is
        'module(9)') are permitted to exist in this table."
    INDEX {entPhysicalIndex, h3cMDCIndex }
    ::= { h3cMDCCPUResourceTable 1 }


H3cMDCCPUResourceEntry ::=
    SEQUENCE {
        h3cMDCCPUResourceLimit
            Integer32,
        h3cMDCCPUResourceUsage
            Integer32
     }

h3cMDCCPUResourceLimit OBJECT-TYPE
    SYNTAX Integer32 (1..10)
    UNITS     "weight"
    MAX-ACCESS read-write
    STATUS current
    DESCRIPTION
        "CPU weight-maximum of available resources of CPU,
        this number specifies a CPU weight for an MDC.
        Non-default MDC cannot set."
    ::= { h3cMDCCPUResourceEntry 1 }


h3cMDCCPUResourceUsage OBJECT-TYPE
    SYNTAX Integer32 (0..100)
    UNITS    "percent"
    MAX-ACCESS read-only
    STATUS current
    DESCRIPTION
        "the CPU usage"
    ::= { h3cMDCCPUResourceEntry 2 }


-- The MDC location status.
h3cMDCLocation OBJECT IDENTIFIER ::= { h3cMDCTables 3 }

h3cMDCLocationTable OBJECT-TYPE
    SYNTAX SEQUENCE OF H3cMDCLocationEntry
    MAX-ACCESS not-accessible
    STATUS current
    DESCRIPTION
        "This table is for location management:
        Authorize an MDC to use an interface card and query state of location.
        To assign physical interfaces to an MDC, administrators must authorize the MDC
        to use the interface cards to which the physical interfaces belong.

        Default: All interface cards of the device belong to the default MDC,
        and a non-default MDC cannot use any interface card.
        Non-default MDC can only query location state."
    ::= { h3cMDCLocation 1 }


h3cMDCLocationEntry OBJECT-TYPE
    SYNTAX H3cMDCLocationEntry
    MAX-ACCESS not-accessible
    STATUS current
    DESCRIPTION
        "An entry of the h3cMDCLocationTable, every entry is the status
        whether an MDC has been Authorized to use the interface cards.

        Note that only entPhysicalIndex values that represent
        physical boards (i.e., associated entPhysicalClass value is
        'module(9)') are permitted to exist in this table."
    INDEX { entPhysicalIndex, h3cMDCIndex }
    ::= { h3cMDCLocationTable 1 }


H3cMDCLocationEntry ::=
    SEQUENCE {
        h3cMDCLocationStatus
            TruthValue
     }

h3cMDCLocationStatus OBJECT-TYPE
    SYNTAX TruthValue
    MAX-ACCESS read-write
    STATUS current
    DESCRIPTION
        "To authorize the MDC to use the interface cards, set the value
        of this object to 'true (1)'.  To cancel the authorization, set this
        value to 'false (2)'.

        Note that the return noError means the command is being executed.
        For the execution result, check h3cMDCLocationStatus."
    ::= { h3cMDCLocationEntry 1 }


-- The interfaces allocate information.
h3cMDCAllocate OBJECT IDENTIFIER ::= { h3cMDCTables 4 }

h3cMDCGroupIfTable OBJECT-TYPE
    SYNTAX SEQUENCE OF H3cMDCGroupIfEntry
    MAX-ACCESS not-accessible
    STATUS current
    DESCRIPTION
        "This table indication of relation between interfaces and groups,
        which helps to realize the allocation, together with h3cMDCAllocateTable.

        Non-default MDC cannot operate."
    ::= { h3cMDCAllocate 1 }


h3cMDCGroupIfEntry OBJECT-TYPE
    SYNTAX H3cMDCGroupIfEntry
    MAX-ACCESS not-accessible
    STATUS current
    DESCRIPTION
        "An entry of the h3cMDCGroupIfTable, every entry is the relationship
        between interfaces and groups.

        Due to hardware restrictions, the interfaces on some interface cards are grouped.
        The interfaces in a group must be assigned to the same MDC at the same time or
        removed from an MDC at the same time. Interface grouping depends on the device model.

        This table is used for h3cMDCAllocateTable to show interfae group lists.

        Note that only entPhysicalIndex values that represent
        physical ports (i.e., associated entPhysicalClass value is
        'port(10)') are permitted to exist in this table."
    INDEX { entPhysicalIndex }
    ::= { h3cMDCGroupIfTable 1 }


H3cMDCGroupIfEntry ::=
    SEQUENCE {
        h3cMDCGroupIdentity
            Integer32
     }

h3cMDCGroupIdentity OBJECT-TYPE
    SYNTAX Integer32
    MAX-ACCESS read-only
    STATUS current
    DESCRIPTION
        "The interface group ID. There are two parts for this id
         depicted as follows:

         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { h3cMDCGroupIfEntry 2 }

h3cMDCAllocateTable OBJECT-TYPE
    SYNTAX SEQUENCE OF H3cMDCAllocateEntry
    MAX-ACCESS not-accessible
    STATUS current
    DESCRIPTION
        "This table is used to assigning a physical interface to an MDC.
        It is allowed that allocate interfaces to a non-default MDC from the default MDC,
        and allocate interfaces back to the default MDC from a non-default MDC.

        All physical interfaces on the device belong to the default MDC,
        and a non-default MDC has no physical interfaces to use.
        Multiple physical interfaces can be assigned to a non-default MDC.
        A physical interface must meet the following conditions to be assigned to a non-default MDC:
        1. Belongs to the default MDC.
        2. Not the console or AUX port.
        3. Not the management Ethernet interface.
        4. Not in an interface group with an interface assigned to another MDC.
        5. The default MDC uses only the physical interfaces that are not assigned to a non-default MDC.

        Non-default MDC cannot set this table."
    ::= { h3cMDCAllocate 2 }


h3cMDCAllocateEntry OBJECT-TYPE
    SYNTAX H3cMDCAllocateEntry
    MAX-ACCESS not-accessible
    STATUS current
    DESCRIPTION
        "An entry of the h3cMDCAllocateTable, every entry is the status
        whether physical interfaces have been assigned to an MDC."
    INDEX { h3cMDCAllocateGroupIndex }
    ::= { h3cMDCAllocateTable 1 }


H3cMDCAllocateEntry ::=
    SEQUENCE {
        h3cMDCAllocateGroupIndex
            Integer32,
        h3cMDCAllocateGroupDescription
            DisplayString,
        h3cMDCAllocateMDCId
            Integer32
     }

h3cMDCAllocateGroupIndex OBJECT-TYPE
    SYNTAX Integer32 (1..2147483647)
    MAX-ACCESS not-accessible
    STATUS current
    DESCRIPTION
        "The interface group ID, the same as h3cMDCGroupIdentity.
         There are two parts for this id.

         depicted as follows:
         31                  7                  0
         +++++++++++++++++++++++++++++++++++++++++
         +   entity index    +    group index    +
         +   ( bit 8..31 )       ( bit 0..7 )    +
         +++++++++++++++++++++++++++++++++++++++++

         From bit0 to bit7 (one byte), it is interfaces group index.

         From bit8 to bit31 (three bytes), it is the physical index
         the same as the entPhysicalIndex specified in ENTITY-MIB.
         Note that only entPhysicalIndex values that represent
         physical boards (i.e., associated entPhysicalClass value is
         'module(9)') are permitted to exist in this table."
    ::= { h3cMDCAllocateEntry 1 }

h3cMDCAllocateGroupDescription OBJECT-TYPE
    SYNTAX DisplayString (SIZE (1..255))
    MAX-ACCESS read-only
    STATUS current
    DESCRIPTION
        "Interfaces list
        Such as:
        GigabitEthernet4/5/0/1 to GigabitEthernet4/5/0/24,
        GigabitEthernet4/5/0/48"
    ::= { h3cMDCAllocateEntry 2 }


h3cMDCAllocateMDCId OBJECT-TYPE
    SYNTAX Integer32 (1..2147483647)
    MAX-ACCESS read-write
    STATUS current
    DESCRIPTION
        "MDC ID is used as h3cMDCAllocateMDCId.
        Default MDC: It is allowed that allocate interfaces to non-default MDC from
        the default MDC, and allocate interfaces back to the default MDC from
        a non-default MDC.
        Non-default MDC cannot set allocation, can only query grouping of own MDC."
    ::= { h3cMDCAllocateEntry 3 }


h3cMDCNotification OBJECT IDENTIFIER ::= { h3cMDC 3 }

h3cMDCNotificationObjects OBJECT IDENTIFIER ::= { h3cMDCNotification 0 }

h3cMDCStateChangeToActive NOTIFICATION-TYPE
    OBJECTS {h3cMDCIndex, h3cMDCName}
    STATUS current
    DESCRIPTION
        "The h3cMDCStateChangeToActive trap indicates that the MDC status has changed to active."
    ::= { h3cMDCNotificationObjects 1 }

h3cMDCStateChangeToInactive NOTIFICATION-TYPE
    OBJECTS {h3cMDCIndex, h3cMDCName}
    STATUS current
    DESCRIPTION
        "The h3cMDCStateChangeToInactive trap indicates that the MDC status has changed to inactive."
    ::= { h3cMDCNotificationObjects 2 }

END
