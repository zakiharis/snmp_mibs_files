INFORMANT-HW DEFINITIONS ::= BEGIN

IMPORTS
    MODULE-IDENTITY, OBJECT-IDENTITY, OBJECT-TYPE, Gauge32, Integer32
        FROM SNMPv2-SMI
    DateAndTime, TruthValue, DisplayString
        FROM SNMPv2-TC
    informant
        FROM WTCS;

wmiHardware MODULE-IDENTITY
    LAST-UPDATED "200705242324Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant hardware WMI entities."
    REVISION      "200705242324Z"
    DESCRIPTION
            "Added Win32_Processor entries for L3CacheSize, 
             L3CacheSpeed, NumberOfCores, and NumberOfLogicalProcessors
             which are new for Windows Vista."
    REVISION      "200411032135Z"
    DESCRIPTION
            "The initial revision of this MIB module."
    ::= { informant 21 }

wmiCoolingDevice OBJECT-IDENTITY
    STATUS     current
    DESCRIPTION
        "The Cooling Devices subcategory groups classes that represent
        instrumentable fans, temperature probes, and refrigeration
        devices."
    ::= { wmiHardware 1 }

win32FanTable OBJECT-TYPE
    SYNTAX     SEQUENCE OF Win32FanEntry
    MAX-ACCESS not-accessible
    STATUS     current
    DESCRIPTION
        "The Win32_Fan WMI class represents the properties of a fan device
        in the computer system. For example, the CPU cooling fan."
    ::= { wmiCoolingDevice 1 }

win32FanEntry OBJECT-TYPE
    SYNTAX     Win32FanEntry
    MAX-ACCESS not-accessible
    STATUS     current
    DESCRIPTION
        "None"
    INDEX      { hwfanIndex }
    ::= { win32FanTable 1 }

Win32FanEntry ::= SEQUENCE {
    hwfanIndex Integer32,
    hwfanActiveCooling TruthValue,
    hwfanAvailability INTEGER,
    hwfanCaption DisplayString,
    hwfanConfigManagerErrorCode INTEGER,
    hwfanConfigManagerUserConfig TruthValue,
    hwfanCreationClassName DisplayString,
    hwfanDescription DisplayString,
    hwfanDesiredSpeed Gauge32,
    hwfanDeviceID DisplayString,
    hwfanErrorCleared TruthValue,
    hwfanErrorDescription DisplayString,
    hwfanInstallDate DateAndTime,
    hwfanLastErrorCode Gauge32,
    hwfanName DisplayString,
    hwfanPNPDeviceID DisplayString,
    hwfanPowerManagementCapabilities DisplayString,
    hwfanPowerManagementSupported TruthValue,
    hwfanStatus INTEGER,
    hwfanStatusInfo INTEGER,
    hwfanSystemCreationClassName DisplayString,
    hwfanSystemName DisplayString,
    hwfanVariableSpeed TruthValue
}

hwfanIndex OBJECT-TYPE
    SYNTAX     Integer32 (1..2147483647)
    MAX-ACCESS read-only
    STATUS     current
    DESCRIPTION
        "The value of this object uniquely identifies the instance entry
        for this class."
    ::= { win32FanEntry 1 }

hwfanActiveCooling OBJECT-TYPE
    SYNTAX     TruthValue
    MAX-ACCESS read-only
    STATUS     current
    DESCRIPTION
        "If TRUE, the cooling device provides active (as opposed to
        passive) cooling. This property is inherited from
        CIM_CoolingDevice."
    ::= { win32FanEntry 2 }

hwfanAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32FanEntry 3 }

hwfanCaption OBJECT-TYPE
    SYNTAX     DisplayString
    MAX-ACCESS read-only
    STATUS     current
    DESCRIPTION
        "Short description of the object a one-line string.
        This property is inherited from
        CIM_ManagedSystemElement."
    ::= { win32FanEntry 4 }

hwfanConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32FanEntry 5 }

hwfanConfigManagerUserConfig OBJECT-TYPE
    SYNTAX     TruthValue
    MAX-ACCESS read-only
    STATUS     current
    DESCRIPTION
        "If TRUE, the device is using a user-defined
        configuration. This property is inherited from
        CIM_LogicalDevice."
    ::= { win32FanEntry 6 }

hwfanCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be identified
        uniquely. This property is inherited from
        CIM_LogicalDevice."
    ::= { win32FanEntry 7 }

hwfanDescription OBJECT-TYPE
    SYNTAX     DisplayString
    MAX-ACCESS read-only
    STATUS     current
    DESCRIPTION
        "Description of the object. This property is
        inherited from CIM_ManagedSystemElement."
    ::= { win32FanEntry 8 }

hwfanDesiredSpeed OBJECT-TYPE
    SYNTAX     Gauge32
    MAX-ACCESS read-only
    STATUS     current
    DESCRIPTION
        "Currently requested fan speed, defined in
        revolutions per minute, when a variable speed fan
        is supported (VariableSpeed is TRUE). The current
        speed is determined by a sensor (CIM_Tachometer)
        that is associated with the fan using the
        CIM_AssociatedSensor relationship. This property is
        inherited from CIM_Fan."
    ::= { win32FanEntry 9 }

hwfanDeviceID OBJECT-TYPE
    SYNTAX     DisplayString
    MAX-ACCESS read-only
    STATUS     current
    DESCRIPTION
        "Identifies the fan device. This property is
        inherited from CIM_LogicalDevice."
    ::= { win32FanEntry 10 }

hwfanErrorCleared OBJECT-TYPE
    SYNTAX     TruthValue
    MAX-ACCESS read-only
    STATUS     current
    DESCRIPTION
        "If TRUE, the error reported in the LastErrorCode
        property is now cleared. This property is inherited
        from CIM_LogicalDevice."
    ::= { win32FanEntry 11 }

hwfanErrorDescription OBJECT-TYPE
    SYNTAX     DisplayString
    MAX-ACCESS read-only
    STATUS     current
    DESCRIPTION
        "Free-form string supplying more information about
        the error recorded in LastErrorCode property, and
        information on any corrective actions that may be
        taken. This property is inherited from
        CIM_LogicalDevice."
    ::= { win32FanEntry 12 }

hwfanInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32FanEntry 13 }

hwfanLastErrorCode OBJECT-TYPE
    SYNTAX     Gauge32
    MAX-ACCESS read-only
    STATUS     current
    DESCRIPTION
        "Last error code reported by the logical device.
        This property is inherited from CIM_LogicalDevice."
    ::= { win32FanEntry 14 }

hwfanName OBJECT-TYPE
    SYNTAX     DisplayString
    MAX-ACCESS read-only
    STATUS     current
    DESCRIPTION
        "Label by which the object is known. When
        subclassed, the property can be overridden to be a
        key property. This property is inherited from
        CIM_ManagedSystemElement."
    ::= { win32FanEntry 15 }

hwfanPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32FanEntry 16 }

hwfanPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32FanEntry 17 }

hwfanPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32FanEntry 18 }

hwfanStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32FanEntry 19 }

hwfanStatusInfo OBJECT-TYPE
    SYNTAX     INTEGER {
        other(1),
        unknown(2),
        enabled(3),
        disabled(4),
        notApplicable(5)
    }
    MAX-ACCESS read-only
    STATUS     current
    DESCRIPTION
        "State of the logical device. If the property does
        not apply to the logical device, the value 5 (Not
        Applicable) should be used. This property is
        inherited from CIM_LogicalDevice."
    ::= { win32FanEntry 20 }

hwfanSystemCreationClassName OBJECT-TYPE
    SYNTAX     DisplayString
    MAX-ACCESS read-only
    STATUS     current
    DESCRIPTION
        "Value of the scoping computer's CreationClassName
        property. This property is inherited from
        CIM_LogicalDevice."
    ::= { win32FanEntry 21 }

hwfanSystemName OBJECT-TYPE
    SYNTAX     DisplayString
    MAX-ACCESS read-only
    STATUS     current
    DESCRIPTION
        "Name of the scoping system. This property is
        inherited from CIM_LogicalDevice."
    ::= { win32FanEntry 22 }

hwfanVariableSpeed OBJECT-TYPE
    SYNTAX     TruthValue
    MAX-ACCESS read-only
    STATUS     current
    DESCRIPTION
        "If TRUE, the fan supports variable speeds. This
        property is inherited from CIM_Fan."
    ::= { win32FanEntry 23 }

win32HeatPipeTable OBJECT-TYPE
    SYNTAX     SEQUENCE OF Win32HeatPipeEntry
    MAX-ACCESS not-accessible
    STATUS     current
    DESCRIPTION
        "The Win32_HeatPipe WMI class represents the
        properties of a heat pipe cooling device."
    ::= { wmiCoolingDevice 2 }

win32HeatPipeEntry OBJECT-TYPE
    SYNTAX     Win32HeatPipeEntry
    MAX-ACCESS not-accessible
    STATUS     current
    DESCRIPTION
        "None"
    INDEX      { hwhpIndex }
    ::= { win32HeatPipeTable 1 }

Win32HeatPipeEntry ::= SEQUENCE {
    hwhpIndex Integer32,
    hwhpActiveCooling TruthValue,
    hwhpAvailability INTEGER,
    hwhpCaption DisplayString,
    hwhpConfigManagerErrorCode INTEGER,
    hwhpConfigManagerUserConfig TruthValue,
    hwhpCreationClassName DisplayString,
    hwhpDescription DisplayString,
    hwhpDeviceID DisplayString,
    hwhpErrorCleared TruthValue,
    hwhpErrorDescription DisplayString,
    hwhpInstallDate DateAndTime,
    hwhpLastErrorCode Gauge32,
    hwhpName DisplayString,
    hwhpPNPDeviceID DisplayString,
    hwhpPowerManagementCapabilities DisplayString,
    hwhpPowerManagementSupported TruthValue,
    hwhpStatus INTEGER,
    hwhpStatusInfo INTEGER,
    hwhpSystemCreationClassName DisplayString,
    hwhpSystemName DisplayString
}

hwhpIndex OBJECT-TYPE
    SYNTAX     Integer32 (1..2147483647)
    MAX-ACCESS read-only
    STATUS     current
    DESCRIPTION
        "The value of this object uniquely identifies the
        instance entry for this class."
    ::= { win32HeatPipeEntry 1 }

hwhpActiveCooling OBJECT-TYPE
    SYNTAX     TruthValue
    MAX-ACCESS read-only
    STATUS     current
    DESCRIPTION
        "If TRUE, the cooling device provides active
        cooling not passive. This property is inherited
        from CIM_CoolingDevice."
    ::= { win32HeatPipeEntry 2 }

hwhpAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32HeatPipeEntry 3 }

hwhpCaption OBJECT-TYPE
    SYNTAX     DisplayString
    MAX-ACCESS read-only
    STATUS     current
    DESCRIPTION
        "Short description of the object a one-line string.
        This property is inherited from
        CIM_ManagedSystemElement."
    ::= { win32HeatPipeEntry 4 }

hwhpConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32HeatPipeEntry 5 }

hwhpConfigManagerUserConfig OBJECT-TYPE
    SYNTAX     TruthValue
    MAX-ACCESS read-only
    STATUS     current
    DESCRIPTION
        "If TRUE, the device is using a user-defined
        configuration. This property is inherited from
        CIM_LogicalDevice."
    ::= { win32HeatPipeEntry 6 }

hwhpCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32HeatPipeEntry 7 }

hwhpDescription OBJECT-TYPE
    SYNTAX     DisplayString
    MAX-ACCESS read-only
    STATUS     current
    DESCRIPTION
        "Description of the object. This property is
        inherited from CIM_ManagedSystemElement."
    ::= { win32HeatPipeEntry 8 }

hwhpDeviceID OBJECT-TYPE
    SYNTAX     DisplayString
    MAX-ACCESS read-only
    STATUS     current
    DESCRIPTION
        "Unique identifier of the heat pipe. This property
        is inherited from CIM_LogicalDevice."
    ::= { win32HeatPipeEntry 9 }

hwhpErrorCleared OBJECT-TYPE
    SYNTAX     TruthValue
    MAX-ACCESS read-only
    STATUS     current
    DESCRIPTION
        "If TRUE, the error reported in LastErrorCode is
        now cleared. This property is inherited from
        CIM_LogicalDevice."
    ::= { win32HeatPipeEntry 10 }

hwhpErrorDescription OBJECT-TYPE
    SYNTAX     DisplayString
    MAX-ACCESS read-only
    STATUS     current
    DESCRIPTION
        "More information about the error that is recorded
        in LastErrorCode, and information about any
        corrective actions that may be taken. This property
        is inherited from CIM_LogicalDevice."
    ::= { win32HeatPipeEntry 11 }

hwhpInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32HeatPipeEntry 12 }

hwhpLastErrorCode OBJECT-TYPE
    SYNTAX     Gauge32
    MAX-ACCESS read-only
    STATUS     current
    DESCRIPTION
        "Last error code reported by the logical device.
        This property is inherited from CIM_LogicalDevice."
    ::= { win32HeatPipeEntry 13 }

hwhpName OBJECT-TYPE
    SYNTAX     DisplayString
    MAX-ACCESS read-only
    STATUS     current
    DESCRIPTION
        "Label by which the object is known. When
        subclassed, the property can be overridden to be a
        key property. This property is inherited from
        CIM_ManagedSystemElement."
    ::= { win32HeatPipeEntry 14 }

hwhpPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32HeatPipeEntry 15 }

hwhpPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32HeatPipeEntry 16 }

hwhpPowerManagementSupported OBJECT-TYPE
    SYNTAX     TruthValue
    MAX-ACCESS read-only
    STATUS     current
    DESCRIPTION
        "If TRUE, the device can be power-managed put into
        suspend mode, and so on. The property does not
        indicate that power management features are enabled
        currently, only that the logical device is capable
        of power management. This property is inherited
        from CIM_LogicalDevice."
    ::= { win32HeatPipeEntry 17 }

hwhpStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32HeatPipeEntry 18 }

hwhpStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32HeatPipeEntry 19 }

hwhpSystemCreationClassName OBJECT-TYPE
    SYNTAX     DisplayString
    MAX-ACCESS read-only
    STATUS     current
    DESCRIPTION
        "Value for the scoping computer's CreationClassName
        property. This property is inherited from
        CIM_LogicalDevice."
    ::= { win32HeatPipeEntry 20 }

hwhpSystemName OBJECT-TYPE
    SYNTAX     DisplayString
    MAX-ACCESS read-only
    STATUS     current
    DESCRIPTION
        "Name of the scoping system. This property is
        inherited from CIM_LogicalDevice."
    ::= { win32HeatPipeEntry 21 }

win32RefrigerationTable OBJECT-TYPE
    SYNTAX     SEQUENCE OF Win32RefrigerationEntry
    MAX-ACCESS not-accessible
    STATUS     current
    DESCRIPTION
        "The Win32_Refrigeration WMI class represents the
        properties of a refrigeration device."
    ::= { wmiCoolingDevice 3 }

win32RefrigerationEntry OBJECT-TYPE
    SYNTAX     Win32RefrigerationEntry
    MAX-ACCESS not-accessible
    STATUS     current
    DESCRIPTION
        "None"
    INDEX      { hwrfgIndex }
    ::= { win32RefrigerationTable 1 }

Win32RefrigerationEntry ::= SEQUENCE {
    hwrfgIndex Integer32,
    hwrfgActiveCooling TruthValue,
    hwrfgAvailability INTEGER,
    hwrfgCaption DisplayString,
    hwrfgConfigManagerErrorCode INTEGER,
    hwrfgConfigManagerUserConfig TruthValue,
    hwrfgCreationClassName DisplayString,
    hwrfgDescription DisplayString,
    hwrfgDeviceID DisplayString,
    hwrfgErrorCleared TruthValue,
    hwrfgErrorDescription DisplayString,
    hwrfgInstallDate DateAndTime,
    hwrfgLastErrorCode Gauge32,
    hwrfgName DisplayString,
    hwrfgPNPDeviceID DisplayString,
    hwrfgPowerManagementCapabilities DisplayString,
    hwrfgPowerManagementSupported TruthValue,
    hwrfgStatus INTEGER,
    hwrfgStatusInfo INTEGER,
    hwrfgSystemCreationClassName DisplayString,
    hwrfgSystemName DisplayString
}

hwrfgIndex OBJECT-TYPE
    SYNTAX     Integer32 (1..2147483647)
    MAX-ACCESS read-only
    STATUS     current
    DESCRIPTION
        "The value of this object uniquely identifies the
        instance entry for this class."
    ::= { win32RefrigerationEntry 1 }

hwrfgActiveCooling OBJECT-TYPE
    SYNTAX     TruthValue
    MAX-ACCESS read-only
    STATUS     current
    DESCRIPTION
        "If TRUE, the cooling device provides active
        cooling not passive cooling. This property is
        inherited from CIM_CoolingDevice."
    ::= { win32RefrigerationEntry 2 }

hwrfgAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32RefrigerationEntry 3 }

hwrfgCaption OBJECT-TYPE
    SYNTAX     DisplayString (SIZE (0..64))
    MAX-ACCESS read-only
    STATUS     current
    DESCRIPTION
        "Short description of the object a one-line string.
        This property is inherited from
        CIM_ManagedSystemElement."
    ::= { win32RefrigerationEntry 4 }

hwrfgConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32RefrigerationEntry 5 }

hwrfgConfigManagerUserConfig OBJECT-TYPE
    SYNTAX     TruthValue
    MAX-ACCESS read-only
    STATUS     current
    DESCRIPTION
        "If TRUE, the device is using a user-defined
        configuration. This property is inherited from
        CIM_LogicalDevice."
    ::= { win32RefrigerationEntry 6 }

hwrfgCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32RefrigerationEntry 7 }

hwrfgDescription OBJECT-TYPE
    SYNTAX     DisplayString
    MAX-ACCESS read-only
    STATUS     current
    DESCRIPTION
        "Description of the object. This property is
        inherited from CIM_ManagedSystemElement."
    ::= { win32RefrigerationEntry 8 }

hwrfgDeviceID OBJECT-TYPE
    SYNTAX     DisplayString
    MAX-ACCESS read-only
    STATUS     current
    DESCRIPTION
        "Unique identifier of the refrigeration device.
        This property is inherited from CIM_LogicalDevice."
    ::= { win32RefrigerationEntry 9 }

hwrfgErrorCleared OBJECT-TYPE
    SYNTAX     TruthValue
    MAX-ACCESS read-only
    STATUS     current
    DESCRIPTION
        "If TRUE, the error reported in LastErrorCode is
        now cleared. This property is inherited from
        CIM_LogicalDevice."
    ::= { win32RefrigerationEntry 10 }

hwrfgErrorDescription OBJECT-TYPE
    SYNTAX     DisplayString
    MAX-ACCESS read-only
    STATUS     current
    DESCRIPTION
        "More information about the error recorded in
        LastErrorCode, and any corrective actions that may
        be taken. This property is inherited from
        CIM_LogicalDevice."
    ::= { win32RefrigerationEntry 11 }

hwrfgInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32RefrigerationEntry 12 }

hwrfgLastErrorCode OBJECT-TYPE
    SYNTAX     Gauge32
    MAX-ACCESS read-only
    STATUS     current
    DESCRIPTION
        "Last error code reported by the logical device.
        This property is inherited from CIM_LogicalDevice."
    ::= { win32RefrigerationEntry 13 }

hwrfgName OBJECT-TYPE
    SYNTAX     DisplayString
    MAX-ACCESS read-only
    STATUS     current
    DESCRIPTION
        "Label by which the object is known. When
        subclassed, the property can be overridden to be a
        key property. This property is inherited from
        CIM_ManagedSystemElement."
    ::= { win32RefrigerationEntry 14 }

hwrfgPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32RefrigerationEntry 15 }

hwrfgPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32RefrigerationEntry 16 }

hwrfgPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32RefrigerationEntry 17 }

hwrfgStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32RefrigerationEntry 18 }

hwrfgStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32RefrigerationEntry 19 }

hwrfgSystemCreationClassName OBJECT-TYPE
    SYNTAX     DisplayString
    MAX-ACCESS read-only
    STATUS     current
    DESCRIPTION
        "Value for the scoping computer's CreationClassName
        property. This property is inherited from
        CIM_LogicalDevice."
    ::= { win32RefrigerationEntry 20 }

hwrfgSystemName OBJECT-TYPE
    SYNTAX     DisplayString
    MAX-ACCESS read-only
    STATUS     current
    DESCRIPTION
        "Name of the scoping system. This property is
        inherited from CIM_LogicalDevice."
    ::= { win32RefrigerationEntry 21 }

win32TemperatureProbeTable OBJECT-TYPE
    SYNTAX     SEQUENCE OF Win32TemperatureProbeEntry
    MAX-ACCESS not-accessible
    STATUS     current
    DESCRIPTION
        "The Win32_TemperatureProbe WMI class represents
        the properties of a temperature sensor (electronic
        thermometer)."
    ::= { wmiCoolingDevice 4 }

win32TemperatureProbeEntry OBJECT-TYPE
    SYNTAX     Win32TemperatureProbeEntry
    MAX-ACCESS not-accessible
    STATUS     current
    DESCRIPTION
        "None"
    INDEX      { hwtmpIndex }
    ::= { win32TemperatureProbeTable 1 }

Win32TemperatureProbeEntry ::= SEQUENCE {
    hwtmpIndex Integer32,
    hwtmpAccuracy Integer32,
    hwtmpAvailability INTEGER,
    hwtmpCaption DisplayString,
    hwtmpConfigManagerErrorCode INTEGER,
    hwtmpConfigManagerUserConfig TruthValue,
    hwtmpCreationClassName DisplayString,
    hwtmpCurrentReading Integer32,
    hwtmpDescription DisplayString,
    hwtmpDeviceID DisplayString,
    hwtmpErrorCleared TruthValue,
    hwtmpErrorDescription DisplayString,
    hwtmpInstallDate DateAndTime,
    hwtmpIsLinear TruthValue,
    hwtmpLastErrorCode Gauge32,
    hwtmpLowerThresholdCritical Integer32,
    hwtmpLowerThresholdFatal Integer32,
    hwtmpLowerThresholdNonCritical Integer32,
    hwtmpMaxReadable Integer32,
    hwtmpMinReadable Integer32,
    hwtmpName DisplayString,
    hwtmpNominalReading Integer32,
    hwtmpNormalMax Integer32,
    hwtmpNormalMin Integer32,
    hwtmpPNPDeviceID DisplayString,
    hwtmpPowerManagementCapabilities DisplayString,
    hwtmpPowerManagementSupported TruthValue,
    hwtmpResolution Gauge32,
    hwtmpStatus INTEGER,
    hwtmpStatusInfo INTEGER,
    hwtmpSystemCreationClassName DisplayString,
    hwtmpSystemName DisplayString,
    hwtmpTolerance Integer32,
    hwtmpUpperThresholdCritical Integer32,
    hwtmpUpperThresholdFatal Integer32,
    hwtmpUpperThresholdNonCritical Integer32
}

hwtmpIndex OBJECT-TYPE
    SYNTAX     Integer32 (1..2147483647)
    MAX-ACCESS read-only
    STATUS     current
    DESCRIPTION
        "The value of this object uniquely identifies the
        instance entry for this class."
    ::= { win32TemperatureProbeEntry 1 }

hwtmpAccuracy OBJECT-TYPE
    SYNTAX     Integer32
    UNITS "Hundredths of Percent"
    MAX-ACCESS read-only
    STATUS     current
    DESCRIPTION
        "Accuracy of the sensor for the measured property.
        Its value is recorded as plus or minus hundredths
        of a percent. Accuracy, and resolution and
        tolerance are used to calculate the actual value of
        the measured physical property. Accuracy may vary
        and depends on whether or not the device is linear
        over its dynamic range. This property is inherited
        from CIM_NumericSensor."
    ::= { win32TemperatureProbeEntry 2 }

hwtmpAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32TemperatureProbeEntry 3 }

hwtmpCaption OBJECT-TYPE
    SYNTAX     DisplayString (SIZE (0..64))
    MAX-ACCESS read-only
    STATUS     current
    DESCRIPTION
        "Short description of an object a one-line string.
        This property is inherited from
        CIM_ManagedSystemElement."
    ::= { win32TemperatureProbeEntry 4 }

hwtmpConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32TemperatureProbeEntry 5 }

hwtmpConfigManagerUserConfig OBJECT-TYPE
    SYNTAX     TruthValue
    MAX-ACCESS read-only
    STATUS     current
    DESCRIPTION
        "If TRUE, the device is using a user-defined
        configuration. This property is inherited from
        CIM_LogicalDevice."
    ::= { win32TemperatureProbeEntry 6 }

hwtmpCreationClassName OBJECT-TYPE
    SYNTAX     DisplayString
    MAX-ACCESS read-only
    STATUS     current
    DESCRIPTION
        "Name of the first concrete class that appears in
        the inheritance chain used in the creation of an
        instance. When used with the other key properties
        of a class, the property allows all instances of
        the class and its subclasses to be identified
        uniquely. This property is inherited from
        CIM_LogicalDevice."
    ::= { win32TemperatureProbeEntry 7 }

hwtmpCurrentReading OBJECT-TYPE
    SYNTAX     Integer32
    UNITS "Tenths of degrees centigrade"
    MAX-ACCESS read-only
    STATUS     current
    DESCRIPTION
        "Current value indicated by the sensor. This
        property is inherited from CIM_NumericSensor."
    ::= { win32TemperatureProbeEntry 8 }

hwtmpDescription OBJECT-TYPE
    SYNTAX     DisplayString
    MAX-ACCESS read-only
    STATUS     current
    DESCRIPTION
        "Description of the object. This property is
        inherited from CIM_ManagedSystemElement."
    ::= { win32TemperatureProbeEntry 9 }

hwtmpDeviceID OBJECT-TYPE
    SYNTAX     DisplayString
    MAX-ACCESS read-only
    STATUS     current
    DESCRIPTION
        "Unique identifier of the current probe. This
        property is inherited from CIM_LogicalDevice."
    ::= { win32TemperatureProbeEntry 10 }

hwtmpErrorCleared OBJECT-TYPE
    SYNTAX     TruthValue
    MAX-ACCESS read-only
    STATUS     current
    DESCRIPTION
        "If TRUE, the error reported in LastErrorCode is
        now cleared. This property is inherited from
        CIM_LogicalDevice."
    ::= { win32TemperatureProbeEntry 11 }

hwtmpErrorDescription OBJECT-TYPE
    SYNTAX     DisplayString
    MAX-ACCESS read-only
    STATUS     current
    DESCRIPTION
        "More information about the error recorded in
        LastErrorCode, and information about any corrective
        actions that you can take. This property is
        inherited from CIM_LogicalDevice."
    ::= { win32TemperatureProbeEntry 12 }

hwtmpInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32TemperatureProbeEntry 13 }

hwtmpIsLinear OBJECT-TYPE
    SYNTAX     TruthValue
    MAX-ACCESS read-only
    STATUS     current
    DESCRIPTION
        "If TRUE, the sensor is linear over its dynamic
        range. This property is inherited from
        CIM_NumericSensor."
    ::= { win32TemperatureProbeEntry 14 }

hwtmpLastErrorCode OBJECT-TYPE
    SYNTAX     Gauge32
    MAX-ACCESS read-only
    STATUS     current
    DESCRIPTION
        "Last error code reported by the logical device.
        This property is inherited from CIM_LogicalDevice."
    ::= { win32TemperatureProbeEntry 15 }

hwtmpLowerThresholdCritical OBJECT-TYPE
    SYNTAX     Integer32
    UNITS "Tenths of degrees Centigrade"
    MAX-ACCESS read-only
    STATUS     current
    DESCRIPTION
        "Sensor threshold value to specify the ranges
        (minimum and maximum values) that identify the
        sensor operating conditions, which can be normal,
        non-critical, critical, or fatal conditions. If
        CurrentReading is between LowerThresholdCritical
        and LowerThresholdFatal, the current state is
        critical. This property is inherited from
        CIM_NumericSensor."
    ::= { win32TemperatureProbeEntry 16 }

hwtmpLowerThresholdFatal OBJECT-TYPE
    SYNTAX     Integer32
    UNITS "Tenths of degrees Centigrade"
    MAX-ACCESS read-only
    STATUS     current
    DESCRIPTION
        "Sensor threshold value to specify the ranges
        (minimum and maximum values) that identify the
        sensor operating conditions, which can be normal,
        non-critical, critical, or fatal conditions. If
        CurrentReading is below LowerThresholdFatal, the
        current state is fatal. This property is inherited
        from CIM_NumericSensor."
    ::= { win32TemperatureProbeEntry 17 }

hwtmpLowerThresholdNonCritical OBJECT-TYPE
    SYNTAX     Integer32
    UNITS "Tenths of degrees Centigrade"
    MAX-ACCESS read-only
    STATUS     current
    DESCRIPTION
        "Sensor threshold value to specify the ranges
        (minimum and maximum values) that identify the
        sensor operating conditions, which can be normal,
        non-critical, critical, or fatal conditions. If
        CurrentReading is between LowerThresholdNonCritical
        and UpperThresholdNonCritical, the sensor is
        reporting a normal value. If CurrentReading is
        between LowerThresholdNonCritical and
        LowerThresholdCritical, the current state is
        non-critical. This property is inherited from
        CIM_NumericSensor."
    ::= { win32TemperatureProbeEntry 18 }

hwtmpMaxReadable OBJECT-TYPE
    SYNTAX     Integer32
    UNITS "Tenths of degrees Centigrade"
    MAX-ACCESS read-only
    STATUS     current
    DESCRIPTION
        "Largest value of the measured property that can be
        read by the numeric sensor. This property is
        inherited from CIM_NumericSensor."
    ::= { win32TemperatureProbeEntry 19 }

hwtmpMinReadable OBJECT-TYPE
    SYNTAX     Integer32
    UNITS "Tenths of degrees Centigrade"
    MAX-ACCESS read-only
    STATUS     current
    DESCRIPTION
        "Smallest value of the measured property that can
        be read by the numeric sensor. This property is
        inherited from CIM_NumericSensor."
    ::= { win32TemperatureProbeEntry 20 }

hwtmpName OBJECT-TYPE
    SYNTAX     DisplayString
    MAX-ACCESS read-only
    STATUS     current
    DESCRIPTION
        "Label for the object. When subclassed, the
        property can be overridden to be a key property.
        This property is inherited from
        CIM_ManagedSystemElement."
    ::= { win32TemperatureProbeEntry 21 }

hwtmpNominalReading OBJECT-TYPE
    SYNTAX     Integer32
    UNITS "Tenths of degrees Centigrade"
    MAX-ACCESS read-only
    STATUS     current
    DESCRIPTION
        "Normal or expected value for the numeric sensor.
        This property is inherited from CIM_NumericSensor."
    ::= { win32TemperatureProbeEntry 22 }

hwtmpNormalMax OBJECT-TYPE
    SYNTAX     Integer32
    UNITS "Tenths of degrees Centigrade"
    MAX-ACCESS read-only
    STATUS     current
    DESCRIPTION
        "Normal or expected value for the numeric sensor.
        This property is inherited from CIM_NumericSensor."
    ::= { win32TemperatureProbeEntry 23 }

hwtmpNormalMin OBJECT-TYPE
    SYNTAX     Integer32
    UNITS "Tenths of degrees Centigrade"
    MAX-ACCESS read-only
    STATUS     current
    DESCRIPTION
        "Guidance for the user as to the normal minimum
        range for the numeric sensor. This property is
        inherited from CIM_NumericSensor."
    ::= { win32TemperatureProbeEntry 24 }

hwtmpPNPDeviceID OBJECT-TYPE
    SYNTAX     DisplayString
    MAX-ACCESS read-only
    STATUS     current
    DESCRIPTION
        "Windows plug and play device identifier of the
        logical device. This property is inherited from
        CIM_LogicalDevice.
        Example: '*PNP030b'"
    ::= { win32TemperatureProbeEntry 25 }

hwtmpPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32TemperatureProbeEntry 26 }

hwtmpPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32TemperatureProbeEntry 27 }

hwtmpResolution OBJECT-TYPE
    SYNTAX     Gauge32
    UNITS "Hundredths of degrees Centigrade"
    MAX-ACCESS read-only
    STATUS     current
    DESCRIPTION
        "Ability of the sensor to resolve differences in
        the measured property. This value may vary
        depending on whether the device is linear over its
        dynamic range. This property is inherited from
        CIM_NumericSensor."
    ::= { win32TemperatureProbeEntry 28 }

hwtmpStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32TemperatureProbeEntry 29 }

hwtmpStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32TemperatureProbeEntry 30 }

hwtmpSystemCreationClassName OBJECT-TYPE
    SYNTAX     DisplayString
    MAX-ACCESS read-only
    STATUS     current
    DESCRIPTION
        "Value for the scoping computer's CreationClassName
        property. This property is inherited from
        CIM_LogicalDevice."
    ::= { win32TemperatureProbeEntry 31 }

hwtmpSystemName OBJECT-TYPE
    SYNTAX     DisplayString
    MAX-ACCESS read-only
    STATUS     current
    DESCRIPTION
        "Name of the scoping system. This property is
        inherited from CIM_LogicalDevice."
    ::= { win32TemperatureProbeEntry 32 }

hwtmpTolerance OBJECT-TYPE
    SYNTAX     Integer32
    UNITS "Tenths of degrees Centigrade"
    MAX-ACCESS read-only
    STATUS     current
    DESCRIPTION
        "Tolerance of the sensor for the measured property.
        Tolerance, along with resolution and accuracy, is
        used to calculate the actual value of the measured
        physical property. Tolerance may vary depending on
        whether the device is linear over its dynamic
        range. This property is inherited from
        CIM_NumericSensor."
    ::= { win32TemperatureProbeEntry 33 }

hwtmpUpperThresholdCritical OBJECT-TYPE
    SYNTAX     Integer32
    UNITS "Tenths of degrees Centigrade"
    MAX-ACCESS read-only
    STATUS     current
    DESCRIPTION
        "Sensor's threshold values specify the ranges
        (minimum and maximum values) that identify the
        sensor operating conditions, which can be normal,
        non-critical, critical, or fatal conditions. If
        CurrentReading is between UpperThresholdCritical
        and UpperThresholdFatal, the current state is
        critical. This property is inherited from
        CIM_NumericSensor."
    ::= { win32TemperatureProbeEntry 34 }

hwtmpUpperThresholdFatal OBJECT-TYPE
    SYNTAX     Integer32
    UNITS "Tenths of degrees Centigrade"
    MAX-ACCESS read-only
    STATUS     current
    DESCRIPTION
        "Sensor's threshold values specify the ranges
        (minimum and maximum values) that identify the
        sensor operating conditions, which can be normal,
        non-critical, critical, or fatal conditions. If
        CurrentReading is above UpperThresholdFatal, the
        current state is fatal. This property is inherited
        from CIM_NumericSensor."
    ::= { win32TemperatureProbeEntry 35 }

hwtmpUpperThresholdNonCritical OBJECT-TYPE
    SYNTAX     Integer32
    UNITS "Tenths of degrees Centigrade"
    MAX-ACCESS read-only
    STATUS     current
    DESCRIPTION
        "Sensor's threshold values specify the ranges
        (minimum and maximum values) that identify the
        sensor operating conditions, which can be normal,
        non-critical, critical, or fatal conditions. If
        CurrentReading is between LowerThresholdNonCritical
        and UpperThresholdNonCritical, the sensor is
        reporting a normal value. If CurrentReading is
        between UpperThresholdNonCritical and
        UpperThresholdCritical, the current state is
        non-critical. This property is inherited from
        CIM_NumericSensor."
    ::= { win32TemperatureProbeEntry 36 }

wmiInputDevice OBJECT-IDENTITY
    STATUS     current
    DESCRIPTION
        "The Input Devices subcategory groups classes that
        represent keyboards and pointing devices."
    ::= { wmiHardware 2 }

win32KeyboardTable OBJECT-TYPE
    SYNTAX     SEQUENCE OF Win32KeyboardEntry
    MAX-ACCESS not-accessible
    STATUS     current
    DESCRIPTION
        "The Win32_Keyboard WMI class represents a keyboard
        installed on a Windows system."
    ::= { wmiInputDevice 1 }

win32KeyboardEntry OBJECT-TYPE
    SYNTAX     Win32KeyboardEntry
    MAX-ACCESS not-accessible
    STATUS     current
    DESCRIPTION
        "None"
    INDEX      { hwkbIndex }
    ::= { win32KeyboardTable 1 }

Win32KeyboardEntry ::= SEQUENCE {
    hwkbIndex Integer32,
    hwkbAvailability INTEGER,
    hwkbCaption DisplayString,
    hwkbConfigManagerErrorCode INTEGER,
    hwkbConfigManagerUserConfig TruthValue,
    hwkbCreationClassName DisplayString,
    hwkbDescription DisplayString,
    hwkbDeviceID DisplayString,
    hwkbErrorCleared TruthValue,
    hwkbErrorDescription DisplayString,
    hwkbInstallDate DateAndTime,
    hwkbIsLocked TruthValue,
    hwkbLastErrorCode Gauge32,
    hwkbLayout DisplayString,
    hwkbName DisplayString,
    hwkbNumberOfFunctionKeys Integer32,
    hwkbPassword INTEGER,
    hwkbPNPDeviceID DisplayString,
    hwkbPowerManagementCapabilities DisplayString,
    hwkbPowerManagementSupported TruthValue,
    hwkbStatus INTEGER,
    hwkbStatusInfo INTEGER,
    hwkbSystemCreationClassName DisplayString,
    hwkbSystemName DisplayString
}

hwkbIndex OBJECT-TYPE
    SYNTAX     Integer32 (1..2147483647)
    MAX-ACCESS read-only
    STATUS     current
    DESCRIPTION
        "The value of this object uniquely identifies the
        instance entry for this class."
    ::= { win32KeyboardEntry 1 }

hwkbAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32KeyboardEntry 2 }

hwkbCaption OBJECT-TYPE
    SYNTAX     DisplayString
    MAX-ACCESS read-only
    STATUS     current
    DESCRIPTION
        "Short description of the object a one-line string.
        This property is inherited from
        CIM_ManagedSystemElement."
    ::= { win32KeyboardEntry 3 }

hwkbConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32KeyboardEntry 4 }

hwkbConfigManagerUserConfig OBJECT-TYPE
    SYNTAX     TruthValue
    MAX-ACCESS read-only
    STATUS     current
    DESCRIPTION
        "If TRUE, the device is using a user-defined
        configuration. This property is inherited from
        CIM_LogicalDevice."
    ::= { win32KeyboardEntry 5 }

hwkbCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32KeyboardEntry 6 }

hwkbDescription OBJECT-TYPE
    SYNTAX     DisplayString
    MAX-ACCESS read-only
    STATUS     current
    DESCRIPTION
        "Description of the object. This property is
        inherited from CIM_ManagedSystemElement."
    ::= { win32KeyboardEntry 7 }

hwkbDeviceID OBJECT-TYPE
    SYNTAX     DisplayString
    MAX-ACCESS read-only
    STATUS     current
    DESCRIPTION
        "Address or other identifying information to
        uniquely name the logical device. This property is
        inherited from CIM_LogicalDevice."
    ::= { win32KeyboardEntry 8 }

hwkbErrorCleared OBJECT-TYPE
    SYNTAX     TruthValue
    MAX-ACCESS read-only
    STATUS     current
    DESCRIPTION
        "If TRUE, the error reported in LastErrorCode is
        now cleared. This property is inherited from
        CIM_LogicalDevice."
    ::= { win32KeyboardEntry 9 }

hwkbErrorDescription OBJECT-TYPE
    SYNTAX     DisplayString
    MAX-ACCESS read-only
    STATUS     current
    DESCRIPTION
        "More information about the error recorded in
        LastErrorCode, and corrective actions that may be
        taken. This property is inherited from
        CIM_LogicalDevice."
    ::= { win32KeyboardEntry 10 }

hwkbInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32KeyboardEntry 11 }

hwkbIsLocked OBJECT-TYPE
    SYNTAX     TruthValue
    MAX-ACCESS read-only
    STATUS     current
    DESCRIPTION
        "If TRUE, the device is locked, preventing user
        input or output. This property is inherited from
        CIM_UserDevice."
    ::= { win32KeyboardEntry 12 }

hwkbLastErrorCode OBJECT-TYPE
    SYNTAX     Gauge32
    MAX-ACCESS read-only
    STATUS     current
    DESCRIPTION
        "Last error code reported by the logical device.
        This property is inherited from CIM_LogicalDevice."
    ::= { win32KeyboardEntry 13 }

hwkbLayout OBJECT-TYPE
    SYNTAX     DisplayString
    MAX-ACCESS read-only
    STATUS     current
    DESCRIPTION
        "Free-form string indicating the layout of the
        keyboard. This property is inherited from
        CIM_Keyboard."
    ::= { win32KeyboardEntry 14 }

hwkbName OBJECT-TYPE
    SYNTAX     DisplayString
    MAX-ACCESS read-only
    STATUS     current
    DESCRIPTION
        "Label by which the object is known. When
        subclassed, the property can be overridden to be a
        key property. This property is inherited from
        CIM_ManagedSystemElement."
    ::= { win32KeyboardEntry 15 }

hwkbNumberOfFunctionKeys OBJECT-TYPE
    SYNTAX     Integer32
    MAX-ACCESS read-only
    STATUS     current
    DESCRIPTION
        "Number of function keys on the keyboard. This
        property is inherited from CIM_Keyboard."
    ::= { win32KeyboardEntry 16 }

hwkbPassword OBJECT-TYPE
    SYNTAX     INTEGER {
        other(1),
        unknown(2),
        disabled(3),
        enabled(4),
        notImplemented(5)
    }
    MAX-ACCESS read-only
    STATUS     current
    DESCRIPTION
        "Status of hardware-level password enabled at the
        keyboard (value=4), preventing local input. This
        property is inherited from CIM_Keyboard."
    ::= { win32KeyboardEntry 17 }

hwkbPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32KeyboardEntry 18 }

hwkbPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32KeyboardEntry 19 }

hwkbPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32KeyboardEntry 20 }

hwkbStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32KeyboardEntry 21 }

hwkbStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32KeyboardEntry 22 }

hwkbSystemCreationClassName OBJECT-TYPE
    SYNTAX     DisplayString
    MAX-ACCESS read-only
    STATUS     current
    DESCRIPTION
        "Value of the scoping computer's CreationClassName
        property. This property is inherited from
        CIM_LogicalDevice."
    ::= { win32KeyboardEntry 23 }

hwkbSystemName OBJECT-TYPE
    SYNTAX     DisplayString
    MAX-ACCESS read-only
    STATUS     current
    DESCRIPTION
        "Name of the scoping system. This property is
        inherited from CIM_LogicalDevice."
    ::= { win32KeyboardEntry 24 }

win32PointingDeviceTable OBJECT-TYPE
    SYNTAX     SEQUENCE OF Win32PointingDeviceEntry
    MAX-ACCESS not-accessible
    STATUS     current
    DESCRIPTION
        "The Win32_PointingDevice WMI class represents an
        input device used to point to and select regions on
        the display of a Windows computer system. Any
        device used to manipulate a pointer, or point to
        the display on a Windows computer system is a
        member of this class."
    ::= { wmiInputDevice 2 }

win32PointingDeviceEntry OBJECT-TYPE
    SYNTAX     Win32PointingDeviceEntry
    MAX-ACCESS not-accessible
    STATUS     current
    DESCRIPTION
        "None"
    INDEX      { hwptIndex }
    ::= { win32PointingDeviceTable 1 }

Win32PointingDeviceEntry ::= SEQUENCE {
    hwptIndex Integer32,
    hwptAvailability INTEGER,
    hwptCaption DisplayString,
    hwptConfigManagerErrorCode INTEGER,
    hwptConfigManagerUserConfig TruthValue,
    hwptCreationClassName DisplayString,
    hwptDescription DisplayString,
    hwptDeviceID DisplayString,
    hwptDeviceInterface INTEGER,
    hwptDoubleSpeedThreshold Gauge32,
    hwptErrorCleared TruthValue,
    hwptErrorDescription DisplayString,
    hwptHandedness INTEGER,
    hwptHardwareType DisplayString,
    hwptInfFileName DisplayString,
    hwptInfSection DisplayString,
    hwptInstallDate DateAndTime,
    hwptIsLocked TruthValue,
    hwptLastErrorCode Gauge32,
    hwptManufacturer DisplayString,
    hwptName DisplayString,
    hwptNumberOfButtons Integer32,
    hwptPNPDeviceID DisplayString,
    hwptPointingType INTEGER,
    hwptPowerManagementCapabilities DisplayString,
    hwptPowerManagementSupported TruthValue,
    hwptQuadSpeedThreshold Gauge32,
    hwptResolution Gauge32,
    hwptSampleRate Gauge32,
    hwptStatus INTEGER,
    hwptStatusInfo INTEGER,
    hwptSynch Gauge32,
    hwptSystemCreationClassName DisplayString,
    hwptSystemName DisplayString
}

hwptIndex OBJECT-TYPE
    SYNTAX     Integer32 (1..2147483647)
    MAX-ACCESS read-only
    STATUS     current
    DESCRIPTION
        "The value of this object uniquely identifies the
        instance entry for this class."
    ::= { win32PointingDeviceEntry 1 }

hwptAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32PointingDeviceEntry 2 }

hwptCaption OBJECT-TYPE
    SYNTAX     DisplayString
    MAX-ACCESS read-only
    STATUS     current
    DESCRIPTION
        "Short description (one-line string) of the object.
        This property is inherited from
        CIM_ManagedSystemElement."
    ::= { win32PointingDeviceEntry 3 }

hwptConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. . This
        property is inherited from CIM_LogicalDevice."
    ::= { win32PointingDeviceEntry 4 }

hwptConfigManagerUserConfig OBJECT-TYPE
    SYNTAX     TruthValue
    MAX-ACCESS read-only
    STATUS     current
    DESCRIPTION
        "If TRUE, the device is using a user-defined
        configuration. This property is inherited from
        CIM_LogicalDevice."
    ::= { win32PointingDeviceEntry 5 }

hwptCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32PointingDeviceEntry 6 }

hwptDescription OBJECT-TYPE
    SYNTAX     DisplayString
    MAX-ACCESS read-only
    STATUS     current
    DESCRIPTION
        "Description of the object. This property is
        inherited from CIM_ManagedSystemElement."
    ::= { win32PointingDeviceEntry 7 }

hwptDeviceID OBJECT-TYPE
    SYNTAX     DisplayString
    MAX-ACCESS read-only
    STATUS     current
    DESCRIPTION
        "Unique identifier of the pointing device with
        other devices on the system. This property is
        inherited from CIM_LogicalDevice."
    ::= { win32PointingDeviceEntry 8 }

hwptDeviceInterface OBJECT-TYPE
    SYNTAX     INTEGER {
        other(1),
        unknown(2),
        serial(3),
        ps2(4),
        infrared(5),
        hpHIL(6),
        busMouse(7),
        appleDesktopBus(8),
        busMouseDB9(160),
        busMouseMicroDIN(161),
        usb(162)
    }
    MAX-ACCESS read-only
    STATUS     current
    DESCRIPTION
        "Type of interface used for the pointing device."
    ::= { win32PointingDeviceEntry 9 }

hwptDoubleSpeedThreshold OBJECT-TYPE
    SYNTAX     Gauge32
    UNITS "Mickeys"
    MAX-ACCESS read-only
    STATUS     current
    DESCRIPTION
        "One of two acceleration values. The sensitivity of
        the pointing device doubles (toggles from the first
        to the second value) when the pointing device moves
        a distance greater than this threshold value."
    ::= { win32PointingDeviceEntry 10 }

hwptErrorCleared OBJECT-TYPE
    SYNTAX     TruthValue
    MAX-ACCESS read-only
    STATUS     current
    DESCRIPTION
        "If TRUE, the error reported in LastErrorCode is
        now cleared. This property is inherited from
        CIM_LogicalDevice."
    ::= { win32PointingDeviceEntry 11 }

hwptErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32PointingDeviceEntry 12 }

hwptHandedness OBJECT-TYPE
    SYNTAX     INTEGER {
        unknown(0),
        notApplicable(1),
        rightHandedOperation(2),
        leftHandedOperation(3)
    }
    MAX-ACCESS read-only
    STATUS     current
    DESCRIPTION
        "Configuration of the pointing device for left or
        right-hand operation. This property is inherited
        from CIM_PointingDevice."
    ::= { win32PointingDeviceEntry 13 }

hwptHardwareType OBJECT-TYPE
    SYNTAX     DisplayString
    MAX-ACCESS read-only
    STATUS     current
    DESCRIPTION
        "Type of hardware used for the Windows pointing
        device.
        Example: 'MICROSOFT PS2 MOUSE'"
    ::= { win32PointingDeviceEntry 14 }

hwptInfFileName OBJECT-TYPE
    SYNTAX     DisplayString
    MAX-ACCESS read-only
    STATUS     current
    DESCRIPTION
        "Name of the .inf file for the Windows pointing
        device.
        Example: 'ab.inf'"
    ::= { win32PointingDeviceEntry 15 }

hwptInfSection OBJECT-TYPE
    SYNTAX     DisplayString
    MAX-ACCESS read-only
    STATUS     current
    DESCRIPTION
        "Section of the .inf file that holds configuration
        information for the Windows pointing device."
    ::= { win32PointingDeviceEntry 16 }

hwptInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32PointingDeviceEntry 17 }

hwptIsLocked OBJECT-TYPE
    SYNTAX     TruthValue
    MAX-ACCESS read-only
    STATUS     current
    DESCRIPTION
        "If TRUE, the device is locked, preventing user
        input or output. This property is inherited from
        CIM_UserDevice."
    ::= { win32PointingDeviceEntry 18 }

hwptLastErrorCode OBJECT-TYPE
    SYNTAX     Gauge32
    MAX-ACCESS read-only
    STATUS     current
    DESCRIPTION
        "Last error code reported by the logical device.
        This property is inherited from CIM_LogicalDevice."
    ::= { win32PointingDeviceEntry 19 }

hwptManufacturer OBJECT-TYPE
    SYNTAX     DisplayString
    MAX-ACCESS read-only
    STATUS     current
    DESCRIPTION
        "Name of the processor's manufacturer.
        Example: 'GenuineSilicon'"
    ::= { win32PointingDeviceEntry 20 }

hwptName OBJECT-TYPE
    SYNTAX     DisplayString
    MAX-ACCESS read-only
    STATUS     current
    DESCRIPTION
        "Label by which the object is known. When
        subclassed, the property can be overridden to be a
        key property. This property is inherited from
        CIM_ManagedSystemElement."
    ::= { win32PointingDeviceEntry 21 }

hwptNumberOfButtons OBJECT-TYPE
    SYNTAX     Integer32 (0..255)
    MAX-ACCESS read-only
    STATUS     current
    DESCRIPTION
        "Number of buttons on the pointing device. This
        property is inherited from CIM_PointingDevice.
        Example: 2"
    ::= { win32PointingDeviceEntry 22 }

hwptPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32PointingDeviceEntry 23 }

hwptPointingType OBJECT-TYPE
    SYNTAX     INTEGER {
        other(1),
        unknown(2),
        mouse(3),
        trackBall(4),
        trackPoint(5),
        glidePoint(6),
        touchPad(7),
        touchScreen(8),
        mouseOpticalSensor(9)
    }
    MAX-ACCESS read-only
    STATUS     current
    DESCRIPTION
        "Type of pointing device. This property is
        inherited from CIM_PointingDevice."
    ::= { win32PointingDeviceEntry 24 }

hwptPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32PointingDeviceEntry 25 }

hwptPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32PointingDeviceEntry 26 }

hwptQuadSpeedThreshold OBJECT-TYPE
    SYNTAX     Gauge32
    UNITS "Mickeys"
    MAX-ACCESS read-only
    STATUS     current
    DESCRIPTION
        "One of two acceleration threshold values. The
        system doubles the speed of the pointer movement
        when the pointer device moves a distance greater
        than this value. Because this speed increase occurs
        after the DoubleSpeedThreshold value has been met,
        the pointer effectively moves at four times its
        original speed."
    ::= { win32PointingDeviceEntry 27 }

hwptResolution OBJECT-TYPE
    SYNTAX     Gauge32
    MAX-ACCESS read-only
    STATUS     current
    DESCRIPTION
        "Tracking resolution. This property is inherited
        from CIM_PointingDevice.
        Example: 0"
    ::= { win32PointingDeviceEntry 28 }

hwptSampleRate OBJECT-TYPE
    SYNTAX     Gauge32
    UNITS "Hertz"
    MAX-ACCESS read-only
    STATUS     current
    DESCRIPTION
        "Rate at which the pointing device is polled for
        input information."
    ::= { win32PointingDeviceEntry 29 }

hwptStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PointingDeviceEntry 30 }

hwptStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32PointingDeviceEntry 31 }

hwptSynch OBJECT-TYPE
    SYNTAX     Gauge32
    UNITS "100 Nanoseconds"
    MAX-ACCESS read-only
    STATUS     current
    DESCRIPTION
        "Length of time after which the next interrupt is
        assumed to indicate the start of a new device
        packet (partial packets are discarded). In the
        event that an interrupt is lost, this allows the
        pointing device driver to synchronize its
        internalrepresentation of the packet state with the
        hardware state."
    ::= { win32PointingDeviceEntry 32 }

hwptSystemCreationClassName OBJECT-TYPE
    SYNTAX     DisplayString
    MAX-ACCESS read-only
    STATUS     current
    DESCRIPTION
        "Value of the scoping computer's CreationClassName
        property. This property is inherited from
        CIM_LogicalDevice."
    ::= { win32PointingDeviceEntry 33 }

hwptSystemName OBJECT-TYPE
    SYNTAX     DisplayString
    MAX-ACCESS read-only
    STATUS     current
    DESCRIPTION
        "Name of the scoping system. This property is
        inherited from CIM_LogicalDevice."
    ::= { win32PointingDeviceEntry 34 }

wmiMassStorage OBJECT-IDENTITY
    STATUS     current
    DESCRIPTION
        "Classes in the Mass Storage subcategory represent
        storage devices such as hard disk drives, CD-ROM
        drives, and tape drives."
    ::= { wmiHardware 3 }

win32AutochkSettingTable OBJECT-TYPE
    SYNTAX     SEQUENCE OF Win32AutochkSettingEntry
    MAX-ACCESS not-accessible
    STATUS     current
    DESCRIPTION
        "The Win32_AutochkSetting WMI class represents the
        settings for the autocheck operation of a disk."
    ::= { wmiMassStorage 2 }

win32AutochkSettingEntry OBJECT-TYPE
    SYNTAX     Win32AutochkSettingEntry
    MAX-ACCESS not-accessible
    STATUS     current
    DESCRIPTION
        "None"
    INDEX      { hwasIndex }
    ::= { win32AutochkSettingTable 1 }

Win32AutochkSettingEntry ::= SEQUENCE {
    hwasIndex Integer32,
    hwasCaption DisplayString,
    hwasDescription DisplayString,
    hwasSettingID DisplayString,
    hwasUserInputDelay Gauge32
}

hwasIndex OBJECT-TYPE
    SYNTAX     Integer32 (1..2147483647)
    MAX-ACCESS read-only
    STATUS     current
    DESCRIPTION
        "The value of this object uniquely identifies the
        instance entry for this class."
    ::= { win32AutochkSettingEntry 1 }

hwasCaption OBJECT-TYPE
    SYNTAX     DisplayString (SIZE (0..64))
    MAX-ACCESS read-only
    STATUS     current
    DESCRIPTION
        "Short description (one-line string) of the object.
        This property is inherited from CIM_Setting."
    ::= { win32AutochkSettingEntry 2 }

hwasDescription OBJECT-TYPE
    SYNTAX     DisplayString
    MAX-ACCESS read-only
    STATUS     current
    DESCRIPTION
        "Description of the autocheck setting. This
        property is inherited from CIM_Setting."
    ::= { win32AutochkSettingEntry 3 }

hwasSettingID OBJECT-TYPE
    SYNTAX     DisplayString (SIZE (0..256))
    MAX-ACCESS read-only
    STATUS     current
    DESCRIPTION
        "Date and time when the object was installed. This
        property does not need a value to indicate that the
        object is installed. This property is inherited
        from CIM_Setting."
    ::= { win32AutochkSettingEntry 4 }

hwasUserInputDelay OBJECT-TYPE
    SYNTAX     Gauge32
    UNITS "Seconds"
    MAX-ACCESS read-only
    STATUS     current
    DESCRIPTION
        "User input delay for autocheck."
    ::= { win32AutochkSettingEntry 5 }

win32CDROMDriveTable OBJECT-TYPE
    SYNTAX     SEQUENCE OF Win32CDROMDriveEntry
    MAX-ACCESS not-accessible
    STATUS     current
    DESCRIPTION
        "The Win32_CDROMDrive WMI class represents a CD-ROM
        drive on a Windows computer system. Note that the
        name of the drive does not correspond to the
        logical drive letter assigned to the device."
    ::= { wmiMassStorage 8 }

win32CDROMDriveEntry OBJECT-TYPE
    SYNTAX     Win32CDROMDriveEntry
    MAX-ACCESS not-accessible
    STATUS     current
    DESCRIPTION
        "None"
    INDEX      { hwcdIndex }
    ::= { win32CDROMDriveTable 1 }

Win32CDROMDriveEntry ::= SEQUENCE {
    hwcdIndex Integer32,
    hwcdAvailability INTEGER,
    hwcdCapabilities DisplayString,
    hwcdCapabilityDescriptions DisplayString,
    hwcdCaption DisplayString,
    hwcdCompressionMethod DisplayString,
    hwcdConfigManagerErrorCode INTEGER,
    hwcdConfigManagerUserConfig TruthValue,
    hwcdCreationClassName DisplayString,
    hwcdDefaultBlockSize Gauge32,
    hwcdDescription DisplayString,
    hwcdDeviceID DisplayString,
    hwcdDrive DisplayString,
    hwcdDriveIntegrity TruthValue,
    hwcdErrorCleared TruthValue,
    hwcdErrorDescription DisplayString,
    hwcdErrorMethodology DisplayString,
    hwcdFileSystemFlags Integer32,
    hwcdFileSystemFlagsEx INTEGER,
    hwcdId DisplayString,
    hwcdInstallDate DateAndTime,
    hwcdLastErrorCode Gauge32,
    hwcdManufacturer DisplayString,
    hwcdMaxBlockSize Gauge32,
    hwcdMaximumComponentLength Gauge32,
    hwcdMaxMediaSize Gauge32,
    hwcdMediaLoaded TruthValue,
    hwcdMediaType INTEGER,
    hwcdMfrAssignedRevisionLevel DisplayString,
    hwcdMinBlockSize Gauge32,
    hwcdName DisplayString,
    hwcdNeedsCleaning TruthValue,
    hwcdNumberOfMediaSupported Gauge32,
    hwcdPNPDeviceID DisplayString,
    hwcdPowerManagementCapabilities DisplayString,
    hwcdPowerManagementSupported TruthValue,
    hwcdRevisionLevel DisplayString,
    hwcdSCSIBus Gauge32,
    hwcdSCSILogicalUnit Integer32,
    hwcdSCSIPort Integer32,
    hwcdSCSITargetId Integer32,
    hwcdSize Gauge32,
    hwcdStatus INTEGER,
    hwcdStatusInfo INTEGER,
    hwcdSystemCreationClassName DisplayString,
    hwcdSystemName DisplayString,
    hwcdTransferRate Integer32,
    hwcdVolumeName DisplayString,
    hwcdVolumeSerialNumber DisplayString
}

hwcdIndex OBJECT-TYPE
    SYNTAX     Integer32 (1..2147483647)
    MAX-ACCESS read-only
    STATUS     current
    DESCRIPTION
        "The value of this object uniquely identifies the
        instance entry for this class."
    ::= { win32CDROMDriveEntry 1 }

hwcdAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32CDROMDriveEntry 2 }

hwcdCapabilities OBJECT-TYPE
    SYNTAX     DisplayString
    MAX-ACCESS read-only
    STATUS     current
    DESCRIPTION
        "Array of capabilities of the media access device.
        For example, the device may support random access
        (3), removable media (7), and automatic cleaning
        (9). This property is inherited from
        CIM_MediaAccessDevice.
        Value Meaning 
        0 Unknown 
        1 Other 
        2 Sequential Access 
        3 Random Access 
        4 Supports Writing 
        5 Encryption 
        6 Compression 
        7 Supports Removable Media 
        8 Manual Cleaning 
        9 Automatic Cleaning 
        10 SMART Notification 
        11 Supports Dual-sided Media 
        12 Predismount Eject Not Required "
    ::= { win32CDROMDriveEntry 3 }

hwcdCapabilityDescriptions OBJECT-TYPE
    SYNTAX     DisplayString
    MAX-ACCESS read-only
    STATUS     current
    DESCRIPTION
        "Array of more detailed explanations for any of the
        access device features indicated in the
        Capabilities array. Each entry of this array is
        related to the entry in the Capabilities array that
        is located at the same index. This property is
        inherited from CIM_MediaAccessDevice."
    ::= { win32CDROMDriveEntry 4 }

hwcdCaption OBJECT-TYPE
    SYNTAX     DisplayString
    MAX-ACCESS read-only
    STATUS     current
    DESCRIPTION
        "Short description of the object a one-line string.
        This property is inherited from
        CIM_ManagedSystemElement."
    ::= { win32CDROMDriveEntry 5 }

hwcdCompressionMethod OBJECT-TYPE
    SYNTAX     DisplayString
    MAX-ACCESS read-only
    STATUS     current
    DESCRIPTION
        "Algorithm or tool used by the device to support
        compression. If it is not possible or not desired
        to describe the compression scheme (perhaps because
        it is not known), use the following words:
        'Unknown' to represent that it is not known whether
        the device supports compression capabilities;
        'Compressed' to represent that the device supports
        compression capabilities but either its compression
        scheme is not known or not disclosed; and 'Not
        Compressed' to represent that the device does not
        support compression capabilities. This property is
        inherited from CIM_MediaAccessDevice."
    ::= { win32CDROMDriveEntry 6 }

hwcdConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32CDROMDriveEntry 7 }

hwcdConfigManagerUserConfig OBJECT-TYPE
    SYNTAX     TruthValue
    MAX-ACCESS read-only
    STATUS     current
    DESCRIPTION
        "If TRUE, the device is using a user-defined
        configuration. This property is inherited from
        CIM_LogicalDevice."
    ::= { win32CDROMDriveEntry 8 }

hwcdCreationClassName OBJECT-TYPE
    SYNTAX     DisplayString
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32CDROMDriveEntry 9 }

hwcdDefaultBlockSize OBJECT-TYPE
    SYNTAX     Gauge32
    MAX-ACCESS read-only
    STATUS     current
    DESCRIPTION
        "Default block size, in bytes, for this device.
        This property is inherited from
        CIM_MediaAccessDevice."
    ::= { win32CDROMDriveEntry 10 }

hwcdDescription OBJECT-TYPE
    SYNTAX     DisplayString
    MAX-ACCESS read-only
    STATUS     current
    DESCRIPTION
        "Description of the object. This property is
        inherited from CIM_ManagedSystemElement."
    ::= { win32CDROMDriveEntry 11 }

hwcdDeviceID OBJECT-TYPE
    SYNTAX     DisplayString
    MAX-ACCESS read-only
    STATUS     current
    DESCRIPTION
        "Unique identifier for a CD-ROM drive. This
        property is inherited from CIM_LogicalDevice."
    ::= { win32CDROMDriveEntry 12 }

hwcdDrive OBJECT-TYPE
    SYNTAX     DisplayString
    MAX-ACCESS read-only
    STATUS     current
    DESCRIPTION
        "Drive letter of the CD-ROM drive.
        Example: 'd:\'"
    ::= { win32CDROMDriveEntry 13 }

hwcdDriveIntegrity OBJECT-TYPE
    SYNTAX     TruthValue
    MAX-ACCESS read-only
    STATUS     current
    DESCRIPTION
        "If TRUE, files can be accurately read from the CD
        device. This is achieved by reading a block of data
        twice and comparing the data against itself."
    ::= { win32CDROMDriveEntry 14 }

hwcdErrorCleared OBJECT-TYPE
    SYNTAX     TruthValue
    MAX-ACCESS read-only
    STATUS     current
    DESCRIPTION
        "If TRUE, the error reported in LastErrorCode is
        now cleared."
    ::= { win32CDROMDriveEntry 15 }

hwcdErrorDescription OBJECT-TYPE
    SYNTAX     DisplayString
    MAX-ACCESS read-only
    STATUS     current
    DESCRIPTION
        "More information about the error recorded in
        LastErrorCode, and information about corrective
        actions that can be taken."
    ::= { win32CDROMDriveEntry 16 }

hwcdErrorMethodology OBJECT-TYPE
    SYNTAX     DisplayString
    MAX-ACCESS read-only
    STATUS     current
    DESCRIPTION
        "Type of error detection and correction supported
        by this device. This property is inherited from
        CIM_MediaAccessDevice."
    ::= { win32CDROMDriveEntry 17 }

hwcdFileSystemFlags OBJECT-TYPE
    SYNTAX     Integer32
    MAX-ACCESS read-only
    STATUS     current
    DESCRIPTION
        "This property is obsolete. In place of this
        property, use FileSystemFlagsEx."
    ::= { win32CDROMDriveEntry 18 }

hwcdFileSystemFlagsEx OBJECT-TYPE
    SYNTAX     INTEGER {
        caseSENSITIVESEARCH(1),
        casePRESERVEDNAMES(2),
        unicodeONDISK(4),
        persistentACLS(8),
        fileCOMPRESSION(16),
        volumeQUOTAS(32),
        supportsSPARSEFILES(64),
        supportsREPARSEPOINTS(128),
        supportsREMOTESTORAGE(256),
        supportsLONGNAMES(16384),
        volumeISCOMPRESSED(32768),
        supportsOBJECTIDS(65536),
        supportsENCRYPTION(131072),
        supportsNAMEDSTREAMS(262144)
    }
    MAX-ACCESS read-only
    STATUS     current
    DESCRIPTION
        "File system flags associated with the Windows
        CD-ROM drive. This parameter can be any combination
        of flags, but FS_FILE_COMPRESSION and
        FS_VOL_IS_COMPRESSED are mutually exclusive."
    ::= { win32CDROMDriveEntry 19 }

hwcdId OBJECT-TYPE
    SYNTAX     DisplayString
    MAX-ACCESS read-only
    STATUS     current
    DESCRIPTION
        "Drive letter uniquely identifying this CD-ROM
        drive.
        Example: 'd:\'"
    ::= { win32CDROMDriveEntry 20 }

hwcdInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32CDROMDriveEntry 21 }

hwcdLastErrorCode OBJECT-TYPE
    SYNTAX     Gauge32
    MAX-ACCESS read-only
    STATUS     current
    DESCRIPTION
        "Last error code reported by the logical device."
    ::= { win32CDROMDriveEntry 22 }

hwcdManufacturer OBJECT-TYPE
    SYNTAX     DisplayString
    MAX-ACCESS read-only
    STATUS     current
    DESCRIPTION
        "Manufacturer of the Windows CD-ROM drive.
        Example: 'PLEXTOR'"
    ::= { win32CDROMDriveEntry 23 }

hwcdMaxBlockSize OBJECT-TYPE
    SYNTAX     Gauge32
    MAX-ACCESS read-only
    STATUS     current
    DESCRIPTION
        "Maximum block size, in bytes, for media accessed
        by this device. This property is inherited from
        CIM_MediaAccessDevice."
    ::= { win32CDROMDriveEntry 24 }

hwcdMaximumComponentLength OBJECT-TYPE
    SYNTAX     Gauge32
    MAX-ACCESS read-only
    STATUS     current
    DESCRIPTION
        "Maximum length of a filename component supported
        by the Windows CD-ROM drive. A file name component
        the portion of a file name between backslashes. The
        value can be used to indicate that long names are
        supported by the specified file system. For
        example, for a FAT file system supporting long
        names, the function stores the value 255, rather
        than the previous 8.3 indicator. Long names can
        also be supported on systems that use the NTFS file
        system.
        Example: 255"
    ::= { win32CDROMDriveEntry 25 }

hwcdMaxMediaSize OBJECT-TYPE
    SYNTAX     Gauge32
    MAX-ACCESS read-only
    STATUS     current
    DESCRIPTION
        "Maximum size, in kilobytes, of media supported by
        this device. This property is inherited from
        CIM_MediaAccessDevice."
    ::= { win32CDROMDriveEntry 26 }

hwcdMediaLoaded OBJECT-TYPE
    SYNTAX     TruthValue
    MAX-ACCESS read-only
    STATUS     current
    DESCRIPTION
        "If TRUE, a CD-ROM is in the drive."
    ::= { win32CDROMDriveEntry 27 }

hwcdMediaType OBJECT-TYPE
    SYNTAX     INTEGER {
        randomAccess(1),
        supportsWriting(2),
        removableMedia(3),
        cdrom(4)
    }
    MAX-ACCESS read-only
    STATUS     current
    DESCRIPTION
        "Type of media used or accessed by this device. In
        this class, the value is always 'CD-ROM'."
    ::= { win32CDROMDriveEntry 28 }

hwcdMfrAssignedRevisionLevel OBJECT-TYPE
    SYNTAX     DisplayString
    MAX-ACCESS read-only
    STATUS     current
    DESCRIPTION
        "Windows XP and Windows Server 2003:  Manufacturer
        assigned firmware revision level of the CD-ROM
        drive. "
    ::= { win32CDROMDriveEntry 29 }

hwcdMinBlockSize OBJECT-TYPE
    SYNTAX     Gauge32
    MAX-ACCESS read-only
    STATUS     current
    DESCRIPTION
        "Minimum block size, in bytes, for media accessed
        by this device. This property is inherited from
        CIM_MediaAccessDevice."
    ::= { win32CDROMDriveEntry 30 }

hwcdName OBJECT-TYPE
    SYNTAX     DisplayString
    MAX-ACCESS read-only
    STATUS     current
    DESCRIPTION
        "Label for the object. When subclassed, the
        property can be overridden to be a key property.
        This property is inherited from
        CIM_ManagedSystemElement."
    ::= { win32CDROMDriveEntry 31 }

hwcdNeedsCleaning OBJECT-TYPE
    SYNTAX     TruthValue
    MAX-ACCESS read-only
    STATUS     current
    DESCRIPTION
        "If TRUE, the media access device needs cleaning.
        Whether manual or automatic cleaning is possible is
        indicated in the Capabilities property. This
        property is inherited from CIM_MediaAccessDevice."
    ::= { win32CDROMDriveEntry 32 }

hwcdNumberOfMediaSupported OBJECT-TYPE
    SYNTAX     Gauge32
    MAX-ACCESS read-only
    STATUS     current
    DESCRIPTION
        "Maximum number of media that can be supported or
        inserted, when the media access device supports
        multiple individual media. This property is
        inherited from CIM_MediaAccessDevice."
    ::= { win32CDROMDriveEntry 33 }

hwcdPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32CDROMDriveEntry 34 }

hwcdPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32CDROMDriveEntry 35 }

hwcdPowerManagementSupported OBJECT-TYPE
    SYNTAX     TruthValue
    MAX-ACCESS read-only
    STATUS     current
    DESCRIPTION
        "If TRUE, the device can be power-managed, which
        means that it can be put into suspend mode, and so
        on. The property does not indicate that power
        management features are currently enabled, only
        that the logical device is capable of power
        management. This property is inherited from
        CIM_LogicalDevice."
    ::= { win32CDROMDriveEntry 36 }

hwcdRevisionLevel OBJECT-TYPE
    SYNTAX     DisplayString
    MAX-ACCESS read-only
    STATUS     current
    DESCRIPTION
        "Firmware revision level of the Windows CD-ROM
        drive."
    ::= { win32CDROMDriveEntry 37 }

hwcdSCSIBus OBJECT-TYPE
    SYNTAX     Gauge32
    MAX-ACCESS read-only
    STATUS     current
    DESCRIPTION
        "SCSI bus number for the disk drive.
        Example: 0"
    ::= { win32CDROMDriveEntry 38 }

hwcdSCSILogicalUnit OBJECT-TYPE
    SYNTAX     Integer32
    MAX-ACCESS read-only
    STATUS     current
    DESCRIPTION
        "SCSI logical unit number (LUN) of the disk drive.
        The LUN is used to designate which SCSI controller
        is being accessed in a system with more than one
        controller being used. The SCSI device identifier
        is similar, but is the designation for multiple
        devices on one controller.
        Example: 0"
    ::= { win32CDROMDriveEntry 39 }

hwcdSCSIPort OBJECT-TYPE
    SYNTAX     Integer32
    MAX-ACCESS read-only
    STATUS     current
    DESCRIPTION
        "SCSI port number of the disk drive.
        Example: 1"
    ::= { win32CDROMDriveEntry 40 }

hwcdSCSITargetId OBJECT-TYPE
    SYNTAX     Integer32
    MAX-ACCESS read-only
    STATUS     current
    DESCRIPTION
        "SCSI identifier number of the Windows CD-ROM
        drive.
        Example: 0"
    ::= { win32CDROMDriveEntry 41 }

hwcdSize OBJECT-TYPE
    SYNTAX     Gauge32
    UNITS "Bytes"
    MAX-ACCESS read-only
    STATUS     current
    DESCRIPTION
        "Size of the disk drive."
    ::= { win32CDROMDriveEntry 42 }

hwcdStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32CDROMDriveEntry 43 }

hwcdStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used."
    ::= { win32CDROMDriveEntry 44 }

hwcdSystemCreationClassName OBJECT-TYPE
    SYNTAX     DisplayString
    MAX-ACCESS read-only
    STATUS     current
    DESCRIPTION
        "Value of the scoping computer's CreationClassName
        property."
    ::= { win32CDROMDriveEntry 45 }

hwcdSystemName OBJECT-TYPE
    SYNTAX     DisplayString
    MAX-ACCESS read-only
    STATUS     current
    DESCRIPTION
        "Name of the scoping system."
    ::= { win32CDROMDriveEntry 46 }

hwcdTransferRate OBJECT-TYPE
    SYNTAX     Integer32
    UNITS "KiloBytes per Second"
    MAX-ACCESS read-only
    STATUS     current
    DESCRIPTION
        "Transfer rate of the CD-ROM drive. A value of -1
        indicates that the rate cannot be determined. This
        might happen if the CD is not in the drive."
    ::= { win32CDROMDriveEntry 47 }

hwcdVolumeName OBJECT-TYPE
    SYNTAX     DisplayString
    MAX-ACCESS read-only
    STATUS     current
    DESCRIPTION
        "Volume name of the Windows CD-ROM drive."
    ::= { win32CDROMDriveEntry 48 }

hwcdVolumeSerialNumber OBJECT-TYPE
    SYNTAX     DisplayString
    MAX-ACCESS read-only
    STATUS     current
    DESCRIPTION
        "Volume serial number of the media in the CD-ROM
        drive.
        Example: A8C3-D032"
    ::= { win32CDROMDriveEntry 49 }

win32DiskDriveTable OBJECT-TYPE
    SYNTAX     SEQUENCE OF Win32DiskDriveEntry
    MAX-ACCESS not-accessible
    STATUS     current
    DESCRIPTION
        "The Win32_DiskDrive WMI class represents a
        physical disk drive as seen by a computer running
        the Windows operating system. Any interface to a
        Windows physical disk drive is a descendent (or
        member) of this class. The features of the disk
        drive seen through this object correspond to the
        logical and management characteristics of the
        drive. In some cases, this may not reflect the
        actual physical characteristics of the device. Any
        object based on another logical device would not be
        a member of this class."
    ::= { wmiMassStorage 12 }

win32DiskDriveEntry OBJECT-TYPE
    SYNTAX     Win32DiskDriveEntry
    MAX-ACCESS not-accessible
    STATUS     current
    DESCRIPTION
        "None"
    INDEX      { hwddIndex }
    ::= { win32DiskDriveTable 1 }

Win32DiskDriveEntry ::= SEQUENCE {
    hwddIndex Integer32,
    hwddAvailability INTEGER,
    hwddBytesPerSector Gauge32,
    hwddCapabilities DisplayString,
    hwddCapabilityDescriptions DisplayString,
    hwddCaption DisplayString,
    hwddCompressionMethod DisplayString,
    hwddConfigManagerErrorCode INTEGER,
    hwddConfigManagerUserConfig TruthValue,
    hwddCreationClassName DisplayString,
    hwddDefaultBlockSize Gauge32,
    hwddDescription DisplayString,
    hwddDeviceID DisplayString,
    hwddErrorCleared TruthValue,
    hwddErrorDescription DisplayString,
    hwddErrorMethodology DisplayString,
    hwddPhysicalIndex Gauge32,
    hwddInstallDate DateAndTime,
    hwddInterfaceType DisplayString,
    hwddLastErrorCode Gauge32,
    hwddManufacturer DisplayString,
    hwddMaxBlockSize Gauge32,
    hwddMaxMediaSize Gauge32,
    hwddMediaLoaded TruthValue,
    hwddMediaType DisplayString,
    hwddMinBlockSize Gauge32,
    hwddModel DisplayString,
    hwddName DisplayString,
    hwddNeedsCleaning TruthValue,
    hwddNumberOfMediaSupported Gauge32,
    hwddPartitions Gauge32,
    hwddPNPDeviceID DisplayString,
    hwddPowerManagementCapabilities DisplayString,
    hwddPowerManagementSupported TruthValue,
    hwddSCSIBus Gauge32,
    hwddSCSILogicalUnit Integer32,
    hwddSCSIPort Integer32,
    hwddSCSITargetId Integer32,
    hwddSectorsPerTrack Gauge32,
    hwddSignature Gauge32,
    hwddSize DisplayString,
    hwddStatus INTEGER,
    hwddStatusInfo INTEGER,
    hwddSystemCreationClassName DisplayString,
    hwddSystemName DisplayString,
    hwddTotalCylinders Gauge32,
    hwddTotalHeads Gauge32,
    hwddTotalSectors Gauge32,
    hwddTotalTracks Gauge32,
    hwddTracksPerCylinder Gauge32
}

hwddIndex OBJECT-TYPE
    SYNTAX     Integer32 (1..2147483647)
    MAX-ACCESS read-only
    STATUS     current
    DESCRIPTION
        "The value of this object uniquely identifies the
        instance entry for this class."
    ::= { win32DiskDriveEntry 1 }

hwddAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32DiskDriveEntry 2 }

hwddBytesPerSector OBJECT-TYPE
    SYNTAX     Gauge32
    UNITS "Bytes"
    MAX-ACCESS read-only
    STATUS     current
    DESCRIPTION
        "Number of bytes in each sector for the physical
        disk drive.
        Example: 512"
    ::= { win32DiskDriveEntry 3 }

hwddCapabilities OBJECT-TYPE
    SYNTAX     DisplayString
    MAX-ACCESS read-only
    STATUS     current
    DESCRIPTION
        "Array of capabilities of the media access device.
        For example, the device may support random access
        (3), removable media (7) and automatic cleaning
        (9). This property is inherited from
        CIM_MediaAccessDevice.
        Value Meaning 
        0 Unknown 
        1 Other 
        2 Sequential Access 
        3 Random Access 
        4 Supports Writing 
        5 Encryption 
        6 Compression 
        7 Supports Removable Media 
        8 Manual Cleaning 
        9 Automatic Cleaning 
        10 SMART Notification 
        11 Supports Dual Sided Media 
        12 Ejection Prior to Drive Dismount Not Required "
    ::= { win32DiskDriveEntry 4 }

hwddCapabilityDescriptions OBJECT-TYPE
    SYNTAX     DisplayString
    MAX-ACCESS read-only
    STATUS     current
    DESCRIPTION
        "List of more detailed explanations for any of the
        access device features indicated in the
        Capabilities array. Note, each entry of this array
        is related to the entry in the Capabilities array
        that is located at the same index. This property is
        inherited from CIM_MediaAccessDevice."
    ::= { win32DiskDriveEntry 5 }

hwddCaption OBJECT-TYPE
    SYNTAX     DisplayString
    MAX-ACCESS read-only
    STATUS     current
    DESCRIPTION
        "Short description (one-line string) of the object.
        This property is inherited from
        CIM_ManagedSystemElement."
    ::= { win32DiskDriveEntry 6 }

hwddCompressionMethod OBJECT-TYPE
    SYNTAX     DisplayString
    MAX-ACCESS read-only
    STATUS     current
    DESCRIPTION
        "Algorithm or tool used by the device to support
        compression. If it is not possible or not desired
        to describe the compression scheme (perhaps because
        it is not known), use the following words:
        'Unknown' to represent that it is not known whether
        the device supports compression capabilities or
        not; 'Compressed' to represent that the device
        supports compression capabilities but either its
        compression scheme is not known or not disclosed;
        and 'Not Compressed' to represent that the device
        does not support compression capabilities. This
        property is inherited from CIM_MediaAccessDevice."
    ::= { win32DiskDriveEntry 7 }

hwddConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32DiskDriveEntry 8 }

hwddConfigManagerUserConfig OBJECT-TYPE
    SYNTAX     TruthValue
    MAX-ACCESS read-only
    STATUS     current
    DESCRIPTION
        "If TRUE, the device is using a user-defined
        configuration. This property is inherited from
        CIM_LogicalDevice."
    ::= { win32DiskDriveEntry 9 }

hwddCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32DiskDriveEntry 10 }

hwddDefaultBlockSize OBJECT-TYPE
    SYNTAX     Gauge32
    MAX-ACCESS read-only
    STATUS     current
    DESCRIPTION
        "Default block size, in bytes, for this device.
        This property is inherited from
        CIM_MediaAccessDevice."
    ::= { win32DiskDriveEntry 11 }

hwddDescription OBJECT-TYPE
    SYNTAX     DisplayString
    MAX-ACCESS read-only
    STATUS     current
    DESCRIPTION
        "Description of the object. This property is
        inherited from CIM_ManagedSystemElement."
    ::= { win32DiskDriveEntry 12 }

hwddDeviceID OBJECT-TYPE
    SYNTAX     DisplayString
    MAX-ACCESS read-only
    STATUS     current
    DESCRIPTION
        "Unique identifier of the disk drive with other
        devices on the system. This property is inherited
        from CIM_LogicalDevice."
    ::= { win32DiskDriveEntry 13 }

hwddErrorCleared OBJECT-TYPE
    SYNTAX     TruthValue
    MAX-ACCESS read-only
    STATUS     current
    DESCRIPTION
        "If TRUE, the error reported in LastErrorCode is
        now cleared. This property is inherited from
        CIM_LogicalDevice."
    ::= { win32DiskDriveEntry 14 }

hwddErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32DiskDriveEntry 15 }

hwddErrorMethodology OBJECT-TYPE
    SYNTAX     DisplayString
    MAX-ACCESS read-only
    STATUS     current
    DESCRIPTION
        "Type of error detection and correction supported
        by this device. This property is inherited from
        CIM_MediaAccessDevice."
    ::= { win32DiskDriveEntry 16 }

hwddPhysicalIndex OBJECT-TYPE
    SYNTAX     Gauge32
    MAX-ACCESS read-only
    STATUS     current
    DESCRIPTION
        "Physical drive number of the given drive. This
        property is filled by the GetDriveMapInfo method. A
        value of 0xFF indicates that the given drive does
        not map to a physical drive.
        Example: 1"
    ::= { win32DiskDriveEntry 17 }

hwddInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32DiskDriveEntry 18 }

hwddInterfaceType OBJECT-TYPE
    SYNTAX     DisplayString
    MAX-ACCESS read-only
    STATUS     current
    DESCRIPTION
        "Interface type of physical disk drive.
        Example: 'SCSI'"
    ::= { win32DiskDriveEntry 19 }

hwddLastErrorCode OBJECT-TYPE
    SYNTAX     Gauge32
    MAX-ACCESS read-only
    STATUS     current
    DESCRIPTION
        "Last error code reported by the logical device.
        This property is inherited from CIM_LogicalDevice."
    ::= { win32DiskDriveEntry 20 }

hwddManufacturer OBJECT-TYPE
    SYNTAX     DisplayString
    MAX-ACCESS read-only
    STATUS     current
    DESCRIPTION
        "Name of the disk drive manufacturer.
        Example: 'Seagate'"
    ::= { win32DiskDriveEntry 21 }

hwddMaxBlockSize OBJECT-TYPE
    SYNTAX     Gauge32
    MAX-ACCESS read-only
    STATUS     current
    DESCRIPTION
        "Maximum block size, in bytes, for media accessed
        by this device. This property is inherited from
        CIM_MediaAccessDevice."
    ::= { win32DiskDriveEntry 22 }

hwddMaxMediaSize OBJECT-TYPE
    SYNTAX     Gauge32
    MAX-ACCESS read-only
    STATUS     current
    DESCRIPTION
        "Maximum media size, in kilobytes, of media
        supported by this device. This property is
        inherited from CIM_MediaAccessDevice."
    ::= { win32DiskDriveEntry 23 }

hwddMediaLoaded OBJECT-TYPE
    SYNTAX     TruthValue
    MAX-ACCESS read-only
    STATUS     current
    DESCRIPTION
        "If TRUE, the media for a disk drive is loaded. For
        fixed disk drives, this property will always be
        TRUE"
    ::= { win32DiskDriveEntry 24 }

hwddMediaType OBJECT-TYPE
    SYNTAX     DisplayString
    MAX-ACCESS read-only
    STATUS     current
    DESCRIPTION
        "Type of media used or accessed by this device."
    ::= { win32DiskDriveEntry 25 }

hwddMinBlockSize OBJECT-TYPE
    SYNTAX     Gauge32
    MAX-ACCESS read-only
    STATUS     current
    DESCRIPTION
        "Minimum block size, in bytes, for media accessed
        by this device. This property is inherited from
        CIM_MediaAccessDevice."
    ::= { win32DiskDriveEntry 26 }

hwddModel OBJECT-TYPE
    SYNTAX     DisplayString
    MAX-ACCESS read-only
    STATUS     current
    DESCRIPTION
        "Manufacturer's model number of the disk drive.
        Example: 'ST32171W'"
    ::= { win32DiskDriveEntry 27 }

hwddName OBJECT-TYPE
    SYNTAX     DisplayString
    MAX-ACCESS read-only
    STATUS     current
    DESCRIPTION
        "Label by which the object is known. When
        subclassed, the property can be overridden to be a
        key property. This property is inherited from
        CIM_ManagedSystemElement."
    ::= { win32DiskDriveEntry 28 }

hwddNeedsCleaning OBJECT-TYPE
    SYNTAX     TruthValue
    MAX-ACCESS read-only
    STATUS     current
    DESCRIPTION
        "If TRUE, the media access device needs cleaning.
        Whether manual or automatic cleaning is possible is
        indicated in the Capabilities property. This
        property is inherited from CIM_MediaAccessDevice."
    ::= { win32DiskDriveEntry 29 }

hwddNumberOfMediaSupported OBJECT-TYPE
    SYNTAX     Gauge32
    MAX-ACCESS read-only
    STATUS     current
    DESCRIPTION
        "Maximum number of media which can be supported or
        inserted (when the media access device supports
        multiple individual media). This property is
        inherited from CIM_MediaAccessDevice."
    ::= { win32DiskDriveEntry 30 }

hwddPartitions OBJECT-TYPE
    SYNTAX     Gauge32
    MAX-ACCESS read-only
    STATUS     current
    DESCRIPTION
        "Number of partitions on this physical disk drive
        that are recognized by the operating system.
        Example: 2"
    ::= { win32DiskDriveEntry 31 }

hwddPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32DiskDriveEntry 32 }

hwddPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32DiskDriveEntry 33 }

hwddPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32DiskDriveEntry 34 }

hwddSCSIBus OBJECT-TYPE
    SYNTAX     Gauge32
    MAX-ACCESS read-only
    STATUS     current
    DESCRIPTION
        "SCSI bus number of the disk drive.
        Example: 0"
    ::= { win32DiskDriveEntry 35 }

hwddSCSILogicalUnit OBJECT-TYPE
    SYNTAX     Integer32
    MAX-ACCESS read-only
    STATUS     current
    DESCRIPTION
        "SCSI logical unit number (LUN) of the disk drive.
        Example: 0"
    ::= { win32DiskDriveEntry 36 }

hwddSCSIPort OBJECT-TYPE
    SYNTAX     Integer32
    MAX-ACCESS read-only
    STATUS     current
    DESCRIPTION
        "SCSI port number of the disk drive.
        Example: 0"
    ::= { win32DiskDriveEntry 37 }

hwddSCSITargetId OBJECT-TYPE
    SYNTAX     Integer32
    MAX-ACCESS read-only
    STATUS     current
    DESCRIPTION
        "SCSI identifier number of the disk drive.
        Example: 0"
    ::= { win32DiskDriveEntry 38 }

hwddSectorsPerTrack OBJECT-TYPE
    SYNTAX     Gauge32
    MAX-ACCESS read-only
    STATUS     current
    DESCRIPTION
        "Number of sectors in each track for this physical
        disk drive.
        Example: 63"
    ::= { win32DiskDriveEntry 39 }

hwddSignature OBJECT-TYPE
    SYNTAX     Gauge32
    MAX-ACCESS read-only
    STATUS     current
    DESCRIPTION
        "Disk identification. This property can be used to
        identify a shared resource. This property has been
        added for Windows XP."
    ::= { win32DiskDriveEntry 40 }

hwddSize OBJECT-TYPE
    SYNTAX     DisplayString
    UNITS "Bytes"
    MAX-ACCESS read-only
    STATUS     current
    DESCRIPTION
        "Size of the disk drive. It is calculated by
        multiplying the total number of cylinders, tracks
        in each cylinder, sectors in each track, and bytes
        in each sector."
    ::= { win32DiskDriveEntry 41 }

hwddStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32DiskDriveEntry 42 }

hwddStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32DiskDriveEntry 43 }

hwddSystemCreationClassName OBJECT-TYPE
    SYNTAX     DisplayString
    MAX-ACCESS read-only
    STATUS     current
    DESCRIPTION
        "Value of the scoping computer's CreationClassName
        property. This property is inherited from
        CIM_LogicalDevice."
    ::= { win32DiskDriveEntry 44 }

hwddSystemName OBJECT-TYPE
    SYNTAX     DisplayString
    MAX-ACCESS read-only
    STATUS     current
    DESCRIPTION
        "Name of the scoping system. This property is
        inherited from CIM_LogicalDevice."
    ::= { win32DiskDriveEntry 45 }

hwddTotalCylinders OBJECT-TYPE
    SYNTAX     Gauge32
    MAX-ACCESS read-only
    STATUS     current
    DESCRIPTION
        "Total number of cylinders on the physical disk
        drive. Note: the value for this property is
        obtained through extended functions of BIOS
        interrupt 13h. The value may be inaccurate if the
        drive uses a translation scheme to support high
        capacity disk sizes. Consult the manufacturer for
        accurate drive specifications.
        Example: 657"
    ::= { win32DiskDriveEntry 46 }

hwddTotalHeads OBJECT-TYPE
    SYNTAX     Gauge32
    MAX-ACCESS read-only
    STATUS     current
    DESCRIPTION
        "Total number of heads on the disk drive. Note: the
        value for this property is obtained through
        extended functions of BIOS interrupt 13h. The value
        may be inaccurate if the drive uses a translation
        scheme to support high capacity disk sizes. Consult
        the manufacturer for accurate drive
        specifications."
    ::= { win32DiskDriveEntry 47 }

hwddTotalSectors OBJECT-TYPE
    SYNTAX     Gauge32
    MAX-ACCESS read-only
    STATUS     current
    DESCRIPTION
        "Total number of sectors on the physical disk
        drive. Note: the value for this property is
        obtained through extended functions of BIOS
        interrupt 13h. The value may be inaccurate if the
        drive uses a translation scheme to support high
        capacity disk sizes. Consult the manufacturer for
        accurate drive specifications.
        Example: 2649024"
    ::= { win32DiskDriveEntry 48 }

hwddTotalTracks OBJECT-TYPE
    SYNTAX     Gauge32
    MAX-ACCESS read-only
    STATUS     current
    DESCRIPTION
        "Total number of tracks on the physical disk drive.
        Note: the value for this property is obtained
        through extended functions of BIOS interrupt 13h.
        The value may be inaccurate if the drive uses a
        translation scheme to support high capacity disk
        sizes. Consult the manufacturer for accurate drive
        specifications.
        Example: 42048"
    ::= { win32DiskDriveEntry 49 }

hwddTracksPerCylinder OBJECT-TYPE
    SYNTAX     Gauge32
    MAX-ACCESS read-only
    STATUS     current
    DESCRIPTION
        "Number of tracks in each cylinder on the physical
        disk drive. Note: the value for this property is
        obtained through extended functions of BIOS
        interrupt 13h. The value may be inaccurate if the
        drive uses a translation scheme to support high
        capacity disk sizes. Consult the manufacturer for
        accurate drive specifications.
        Example: 64"
    ::= { win32DiskDriveEntry 50 }

win32FloppyDriveTable OBJECT-TYPE
    SYNTAX     SEQUENCE OF Win32FloppyDriveEntry
    MAX-ACCESS not-accessible
    STATUS     current
    DESCRIPTION
        "The Win32_FloppyDrive WMI class manages the
        capabilities of a floppy disk drive."
    ::= { wmiMassStorage 18 }

win32FloppyDriveEntry OBJECT-TYPE
    SYNTAX     Win32FloppyDriveEntry
    MAX-ACCESS not-accessible
    STATUS     current
    DESCRIPTION
        "None"
    INDEX      { hwfdIndex }
    ::= { win32FloppyDriveTable 1 }

Win32FloppyDriveEntry ::= SEQUENCE {
    hwfdIndex Integer32,
    hwfdAvailability INTEGER,
    hwfdCapabilities DisplayString,
    hwfdCapabilityDescriptions DisplayString,
    hwfdCaption DisplayString,
    hwfdCompressionMethod DisplayString,
    hwfdConfigManagerErrorCode INTEGER,
    hwfdConfigManagerUserConfig TruthValue,
    hwfdCreationClassName DisplayString,
    hwfdDefaultBlockSize Gauge32,
    hwfdDescription DisplayString,
    hwfdDeviceID DisplayString,
    hwfdErrorCleared TruthValue,
    hwfdErrorDescription DisplayString,
    hwfdErrorMethodology DisplayString,
    hwfdInstallDate DateAndTime,
    hwfdLastErrorCode Gauge32,
    hwfdManufacturer DisplayString,
    hwfdMaxBlockSize Gauge32,
    hwfdMaxMediaSize Gauge32,
    hwfdMinBlockSize Gauge32,
    hwfdName DisplayString,
    hwfdNeedsCleaning TruthValue,
    hwfdNumberOfMediaSupported Gauge32,
    hwfdPNPDeviceID DisplayString,
    hwfdPowerManagementCapabilities DisplayString,
    hwfdPowerManagementSupported TruthValue,
    hwfdStatus INTEGER,
    hwfdStatusInfo INTEGER,
    hwfdSystemCreationClassName DisplayString,
    hwfdSystemName DisplayString
}

hwfdIndex OBJECT-TYPE
    SYNTAX     Integer32 (1..2147483647)
    MAX-ACCESS read-only
    STATUS     current
    DESCRIPTION
        "The value of this object uniquely identifies the
        instance entry for this class."
    ::= { win32FloppyDriveEntry 1 }

hwfdAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32FloppyDriveEntry 2 }

hwfdCapabilities OBJECT-TYPE
    SYNTAX     DisplayString
    MAX-ACCESS read-only
    STATUS     current
    DESCRIPTION
        "Array of capabilities of the media access device.
        For example, the device may support Random Access,
        removable media and Automatic Cleaning. In this
        case, the values 3, 7 and 9 would be written to the
        array. This property is inherited from
        CIM_MediaAccessDevice.
        Value Meaning 
        0 Unknown 
        1 Other 
        2 Sequential Access 
        3 Random Access 
        4 Supports Writing 
        5 Encryption 
        6 Compression 
        7 Supports Removable Media 
        8 Manual Cleaning 
        9 Automatic Cleaning 
        10 SMART Notification 
        11 Supports Dual Sided Media 
        12 Predismount Eject Not Required "
    ::= { win32FloppyDriveEntry 3 }

hwfdCapabilityDescriptions OBJECT-TYPE
    SYNTAX     DisplayString
    MAX-ACCESS read-only
    STATUS     current
    DESCRIPTION
        "Array of free-form strings providing more detailed
        explanations for any of the serial controller
        features indicated in the Capabilities array. Note,
        each entry of this array is related to the entry in
        the Capabilities array that is located at the same
        index. This property is inherited from
        CIM_MediaAccessDevice."
    ::= { win32FloppyDriveEntry 4 }

hwfdCaption OBJECT-TYPE
    SYNTAX     DisplayString
    MAX-ACCESS read-only
    STATUS     current
    DESCRIPTION
        "Short description (one-line string) of the object.
        This property is inherited from
        CIM_ManagedSystemElement."
    ::= { win32FloppyDriveEntry 5 }

hwfdCompressionMethod OBJECT-TYPE
    SYNTAX     DisplayString
    MAX-ACCESS read-only
    STATUS     current
    DESCRIPTION
        "Free form string indicating the algorithm or tool
        used by the device to support compression. If it is
        not possible or not desired to describe the
        compression scheme (perhaps because it is not
        known), we recommend using the following words:
        'Unknown' to represent that it is not known whether
        the device supports compression capabilities or
        not; 'Compressed' to represent that the device
        supports compression capabilities but either its
        compression scheme is not known or not disclosed;
        and 'Not Compressed' to represent that the device
        does not support compression capabilities. This
        property is inherited from CIM_MediaAccessDevice."
    ::= { win32FloppyDriveEntry 6 }

hwfdConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32FloppyDriveEntry 7 }

hwfdConfigManagerUserConfig OBJECT-TYPE
    SYNTAX     TruthValue
    MAX-ACCESS read-only
    STATUS     current
    DESCRIPTION
        "If TRUE, the device is using a user-defined
        configuration. This property is inherited from
        CIM_LogicalDevice."
    ::= { win32FloppyDriveEntry 8 }

hwfdCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32FloppyDriveEntry 9 }

hwfdDefaultBlockSize OBJECT-TYPE
    SYNTAX     Gauge32
    MAX-ACCESS read-only
    STATUS     current
    DESCRIPTION
        "Default block size, in bytes, for this device.
        This property is inherited from
        CIM_MediaAccessDevice."
    ::= { win32FloppyDriveEntry 10 }

hwfdDescription OBJECT-TYPE
    SYNTAX     DisplayString
    MAX-ACCESS read-only
    STATUS     current
    DESCRIPTION
        "Description of the object. This property is
        inherited from CIM_ManagedSystemElement."
    ::= { win32FloppyDriveEntry 11 }

hwfdDeviceID OBJECT-TYPE
    SYNTAX     DisplayString
    MAX-ACCESS read-only
    STATUS     current
    DESCRIPTION
        "Unique identifier of the floppy disk drive with
        other devices on the system. This property is
        inherited from CIM_LogicalDevice."
    ::= { win32FloppyDriveEntry 12 }

hwfdErrorCleared OBJECT-TYPE
    SYNTAX     TruthValue
    MAX-ACCESS read-only
    STATUS     current
    DESCRIPTION
        "If TRUE, the error reported in LastErrorCode is
        now cleared. This property is inherited from
        CIM_LogicalDevice."
    ::= { win32FloppyDriveEntry 13 }

hwfdErrorDescription OBJECT-TYPE
    SYNTAX     DisplayString
    MAX-ACCESS read-only
    STATUS     current
    DESCRIPTION
        "Free-form string supplying more information about
        the error recorded in LastErrorCode, and
        information on any corrective actions that may be
        taken. This property is inherited from
        CIM_LogicalDevice."
    ::= { win32FloppyDriveEntry 14 }

hwfdErrorMethodology OBJECT-TYPE
    SYNTAX     DisplayString
    MAX-ACCESS read-only
    STATUS     current
    DESCRIPTION
        "Free-form string describing the type of error
        detection and correction supported by this device.
        This property is inherited from
        CIM_MediaAccessDevice."
    ::= { win32FloppyDriveEntry 15 }

hwfdInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32FloppyDriveEntry 16 }

hwfdLastErrorCode OBJECT-TYPE
    SYNTAX     Gauge32
    MAX-ACCESS read-only
    STATUS     current
    DESCRIPTION
        "Last error code reported by the logical device.
        This property is inherited from CIM_LogicalDevice."
    ::= { win32FloppyDriveEntry 17 }

hwfdManufacturer OBJECT-TYPE
    SYNTAX     DisplayString
    MAX-ACCESS read-only
    STATUS     current
    DESCRIPTION
        "Name of the manufacturer of the floppy disk drive.
        Example: 'Acme'"
    ::= { win32FloppyDriveEntry 18 }

hwfdMaxBlockSize OBJECT-TYPE
    SYNTAX     Gauge32
    MAX-ACCESS read-only
    STATUS     current
    DESCRIPTION
        "Maximum block size, in bytes, for media accessed
        by this device. This property is inherited from
        CIM_MediaAccessDevice."
    ::= { win32FloppyDriveEntry 19 }

hwfdMaxMediaSize OBJECT-TYPE
    SYNTAX     Gauge32
    MAX-ACCESS read-only
    STATUS     current
    DESCRIPTION
        "Maximum size, in kilobytes, of media supported by
        this device. This property is inherited from
        CIM_MediaAccessDevice."
    ::= { win32FloppyDriveEntry 20 }

hwfdMinBlockSize OBJECT-TYPE
    SYNTAX     Gauge32
    MAX-ACCESS read-only
    STATUS     current
    DESCRIPTION
        "Minimum block size, in bytes, for media accessed
        by this device. This property is inherited from
        CIM_MediaAccessDevice."
    ::= { win32FloppyDriveEntry 21 }

hwfdName OBJECT-TYPE
    SYNTAX     DisplayString
    MAX-ACCESS read-only
    STATUS     current
    DESCRIPTION
        "Label by which the object is known. When
        subclassed, the property can be overridden to be a
        key property. This property is inherited from
        CIM_ManagedSystemElement."
    ::= { win32FloppyDriveEntry 22 }

hwfdNeedsCleaning OBJECT-TYPE
    SYNTAX     TruthValue
    MAX-ACCESS read-only
    STATUS     current
    DESCRIPTION
        "If TRUE, the media access device needs cleaning.
        Whether manual or automatic cleaning is possible is
        indicated in the Capabilities property. This
        property is inherited from CIM_MediaAccessDevice."
    ::= { win32FloppyDriveEntry 23 }

hwfdNumberOfMediaSupported OBJECT-TYPE
    SYNTAX     Gauge32
    MAX-ACCESS read-only
    STATUS     current
    DESCRIPTION
        "Maximum number of individual media which can be
        supported or inserted in the media access device
        (when supported). This property is inherited from
        CIM_MediaAccessDevice."
    ::= { win32FloppyDriveEntry 24 }

hwfdPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32FloppyDriveEntry 25 }

hwfdPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32FloppyDriveEntry 26 }

hwfdPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32FloppyDriveEntry 27 }

hwfdStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32FloppyDriveEntry 28 }

hwfdStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32FloppyDriveEntry 29 }

hwfdSystemCreationClassName OBJECT-TYPE
    SYNTAX     DisplayString
    MAX-ACCESS read-only
    STATUS     current
    DESCRIPTION
        "Value of the scoping computer's CreationClassName
        property. This property is inherited from
        CIM_LogicalDevice."
    ::= { win32FloppyDriveEntry 30 }

hwfdSystemName OBJECT-TYPE
    SYNTAX     DisplayString
    MAX-ACCESS read-only
    STATUS     current
    DESCRIPTION
        "Name of the scoping system. This property is
        inherited from CIM_LogicalDevice."
    ::= { win32FloppyDriveEntry 31 }

win32PhysicalMediaTable OBJECT-TYPE
    SYNTAX     SEQUENCE OF Win32PhysicalMediaEntry
    MAX-ACCESS not-accessible
    STATUS     current
    DESCRIPTION
        "The Win32_PhysicalMedia class represents any type
        of documentation or storage medium, such as tapes,
        CD ROMs and so on. To obtain the characteristics of
        the media in a CD drive, such as whether it is
        writeable, use Win32_CDROMDrive and the
        Capabilities property"
    ::= { wmiMassStorage 32 }

win32PhysicalMediaEntry OBJECT-TYPE
    SYNTAX     Win32PhysicalMediaEntry
    MAX-ACCESS not-accessible
    STATUS     current
    DESCRIPTION
        "None"
    INDEX      { hwpmdIndex }
    ::= { win32PhysicalMediaTable 1 }

Win32PhysicalMediaEntry ::= SEQUENCE {
    hwpmdIndex Integer32,
    hwpmdCapacity Gauge32,
    hwpmdCaption DisplayString,
    hwpmdCleanerMedia TruthValue,
    hwpmdCreationClassName DisplayString,
    hwpmdDescription DisplayString,
    hwpmdHotSwappable TruthValue,
    hwpmdInstallDate DateAndTime,
    hwpmdManufacturer DisplayString,
    hwpmdMediaDescription DisplayString,
    hwpmdMediaType INTEGER,
    hwpmdModel DisplayString,
    hwpmdName DisplayString,
    hwpmdOtherIdentifyingInfo DisplayString,
    hwpmdPartNumber DisplayString,
    hwpmdPoweredOn TruthValue,
    hwpmdRemovable TruthValue,
    hwpmdReplaceable TruthValue,
    hwpmdSerialNumber DisplayString,
    hwpmdSKU DisplayString,
    hwpmdStatus INTEGER,
    hwpmdTag DisplayString,
    hwpmdVersion DisplayString,
    hwpmdWriteProtectOn TruthValue
}

hwpmdIndex OBJECT-TYPE
    SYNTAX     Integer32 (1..2147483647)
    MAX-ACCESS read-only
    STATUS     current
    DESCRIPTION
        "The value of this object uniquely identifies the
        instance entry for this class."
    ::= { win32PhysicalMediaEntry 1 }

hwpmdCapacity OBJECT-TYPE
    SYNTAX     Gauge32
    MAX-ACCESS read-only
    STATUS     current
    DESCRIPTION
        "Number of bytes that can be read from or written
        to this physical media component. This property
        does not apply to 'Hard Copy' or cleaner media.
        Data compression should not be assumed as it would
        increase the value of this property. For tapes, it
        should be assumed that no filemarks or blank space
        areas are recorded on the media."
    ::= { win32PhysicalMediaEntry 2 }

hwpmdCaption OBJECT-TYPE
    SYNTAX     DisplayString
    MAX-ACCESS read-only
    STATUS     current
    DESCRIPTION
        "Short, one line textual description of the
        object."
    ::= { win32PhysicalMediaEntry 3 }

hwpmdCleanerMedia OBJECT-TYPE
    SYNTAX     TruthValue
    MAX-ACCESS read-only
    STATUS     current
    DESCRIPTION
        "If true the physical media is used for cleaning
        purposes and not data storage."
    ::= { win32PhysicalMediaEntry 4 }

hwpmdCreationClassName OBJECT-TYPE
    SYNTAX     DisplayString
    MAX-ACCESS read-only
    STATUS     current
    DESCRIPTION
        "Name of the class or subclass used in the creation
        of an instance. When used with other key properties
        of this class, CreationClassName allows all
        instances of this class and its subclasses to be
        uniquely identified."
    ::= { win32PhysicalMediaEntry 5 }

hwpmdDescription OBJECT-TYPE
    SYNTAX     DisplayString
    MAX-ACCESS read-only
    STATUS     current
    DESCRIPTION
        "Textual description of the object."
    ::= { win32PhysicalMediaEntry 6 }

hwpmdHotSwappable OBJECT-TYPE
    SYNTAX     TruthValue
    MAX-ACCESS read-only
    STATUS     current
    DESCRIPTION
        "If true this physical media component can be
        replaced with a physically different but equivalent
        one while the containing package has the power
        applied. For example, a fan component may be
        designed to be hot swapped. All components that can
        be hot swapped are inherently removable and
        replaceable."
    ::= { win32PhysicalMediaEntry 7 }

hwpmdInstallDate OBJECT-TYPE
    SYNTAX     DateAndTime
    MAX-ACCESS read-only
    STATUS     current
    DESCRIPTION
        "When the object was installed. This property does
        not need a value to indicate that the object is
        installed."
    ::= { win32PhysicalMediaEntry 8 }

hwpmdManufacturer OBJECT-TYPE
    SYNTAX     DisplayString
    MAX-ACCESS read-only
    STATUS     current
    DESCRIPTION
        "Name of the organization responsible for producing
        the physical element. This may be the entity from
        whom the element is purchased, but this is not
        necessarily the case as this information is
        contained in the Vendor property."
    ::= { win32PhysicalMediaEntry 9 }

hwpmdMediaDescription OBJECT-TYPE
    SYNTAX     DisplayString
    MAX-ACCESS read-only
    STATUS     current
    DESCRIPTION
        "Additional detail related to the MediaType
        property. For example, if MediaType has the value 3
        (QIC Cartridge) the MediaDescription property could
        indicate whether the tape is wide or quarter inch."
    ::= { win32PhysicalMediaEntry 10 }

hwpmdMediaType OBJECT-TYPE
    SYNTAX     INTEGER {
        unknown(0),
        other(1),
        tapeCartridge(2),
        qicCartridge(3),
        aitCartridge(4),
        dtfCartridge(5),
        datCartridge(6),
        n8mmTapeCartridge(7),
        n19mmTapeCartridge(8),
        dltCartridge(9),
        halfInchMagneticTapeCartridge(10),
        cartridgeDisk(11),
        jazDisk(12),
        zipDisk(13),
        syQuestDisk(14),
        winchesterRemovableDisk(15),
        cdROM(16),
        cdROMXA(17),
        cdI(18),
        cdRecordable(19),
        worm(20),
        magnetoOptical(21),
        dvd(22),
        dvdRWplus(23),
        dvdRAM(24),
        dvdROM(25),
        dvdVideo(26),
        divx(27),
        floppyDiskette(28),
        hardDisk(29),
        memoryCard(30),
        hardCopy(31),
        clikDisk(32),
        cdRW(33),
        cdDA(34),
        cd(35),
        dvdRecordable(36),
        dvdRWminus(37),
        dvdAudio(38),
        dvd5(39),
        dvd9(40),
        dvd10(41),
        dvd18(42),
        magnetoOpticalRewriteable(43),
        magnetoOpticalWriteOnce(44),
        magnetoOpticalRewriteableLIMDOW(45),
        phaseChangeWriteOnce(46),
        phaseChangeRewriteable(47),
        phaseChangeDualRewriteable(48),
        ablativeWriteOnce(49),
        nearFieldRecording(50),
        miniQic(51),
        travan(52),
        n8mmMetalParticle(53),
        n8mmAdvancedMetalEvaporate(54),
        nctp(55),
        ltoUltrium(56),
        ltoAccelis(57),
        n9TrackeTape(58),
        n18TrackTape(59),
        n36TrackTape(60),
        magstar3590(61),
        magstarMP(62),
        d2Tape(63),
        tapeDSTSmall(64),
        tapeDSTMedium(65),
        tapeDSTLarge(66)
    }
    MAX-ACCESS read-only
    STATUS     current
    DESCRIPTION
        "The type of the media, as an enumerated integer.
        The MediaDescription property provides a more
        explicit definition of the media type."
    ::= { win32PhysicalMediaEntry 11 }

hwpmdModel OBJECT-TYPE
    SYNTAX     DisplayString
    MAX-ACCESS read-only
    STATUS     current
    DESCRIPTION
        "Name by which the physical element is generally
        known."
    ::= { win32PhysicalMediaEntry 12 }

hwpmdName OBJECT-TYPE
    SYNTAX     DisplayString
    MAX-ACCESS read-only
    STATUS     current
    DESCRIPTION
        "Label by which the object is known. When
        subclassed, the Name property can be overridden to
        be a Key property."
    ::= { win32PhysicalMediaEntry 13 }

hwpmdOtherIdentifyingInfo OBJECT-TYPE
    SYNTAX     DisplayString
    MAX-ACCESS read-only
    STATUS     current
    DESCRIPTION
        "Additional data, beyond asset tag information,
        that could be used to identify a physical element.
        One example is bar code data associated with an
        element that also has an asset tag. Note that if
        only bar code data is available and is unique and
        it can be used as an element key, this property is
        NULL and the bar code data used is the class key in
        the Tag property."
    ::= { win32PhysicalMediaEntry 14 }

hwpmdPartNumber OBJECT-TYPE
    SYNTAX     DisplayString
    MAX-ACCESS read-only
    STATUS     current
    DESCRIPTION
        "Part number assigned by the manufacturer of the
        physical element."
    ::= { win32PhysicalMediaEntry 15 }

hwpmdPoweredOn OBJECT-TYPE
    SYNTAX     TruthValue
    MAX-ACCESS read-only
    STATUS     current
    DESCRIPTION
        "If true the physical element is powered on."
    ::= { win32PhysicalMediaEntry 16 }

hwpmdRemovable OBJECT-TYPE
    SYNTAX     TruthValue
    MAX-ACCESS read-only
    STATUS     current
    DESCRIPTION
        "If true the physical component is designed to be
        taken in and out of the physical container in which
        it is normally found, without impairing the
        function of the overall packaging. A component can
        still be removable if the power must be 'off' in
        order to perform the removal. If power can be 'on'
        and the component removed, the element is removable
        and can be hot swapped. "
    ::= { win32PhysicalMediaEntry 17 }

hwpmdReplaceable OBJECT-TYPE
    SYNTAX     TruthValue
    MAX-ACCESS read-only
    STATUS     current
    DESCRIPTION
        "If true this physical media component can be
        replaced with a physically different one. For
        example, some computer systems allow the main
        processor chip to be upgraded to one of a higher
        clock rating. In this case, the processor is said
        to be replaceable. All removable components are
        inherently replaceable."
    ::= { win32PhysicalMediaEntry 18 }

hwpmdSerialNumber OBJECT-TYPE
    SYNTAX     DisplayString
    MAX-ACCESS read-only
    STATUS     current
    DESCRIPTION
        "Manufacturer-allocated number used to identify the
        physical media.
        Example: WD-WM3493798728"
    ::= { win32PhysicalMediaEntry 19 }

hwpmdSKU OBJECT-TYPE
    SYNTAX     DisplayString
    MAX-ACCESS read-only
    STATUS     current
    DESCRIPTION
        "Stock keeping unit number for this physical
        element."
    ::= { win32PhysicalMediaEntry 20 }

hwpmdStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses are 'OK', 'Degraded', and
        'Pred Fail'. 'Pred Fail' indicates that an element
        may function properly at the present, but predicts
        a failure in the near future. For example, a
        SMART-enabled hard drive. Non-operational statuses
        can also be specified. These are, 'Error',
        'Starting', 'Stopping' and 'Service'. The 'Service'
        status applies to administrative work, such as
        mirror-resilvering of a disk or reload of a user
        permissions list. Not all such work is online, yet
        the managed element is neither 'OK' nor in one of
        the other states."
    ::= { win32PhysicalMediaEntry 21 }

hwpmdTag OBJECT-TYPE
    SYNTAX     DisplayString (SIZE (0..256))
    MAX-ACCESS read-only
    STATUS     current
    DESCRIPTION
        "Uniquely identifies the physical media in the
        system.
        Example: PHYSICALDRIVE0"
    ::= { win32PhysicalMediaEntry 22 }

hwpmdVersion OBJECT-TYPE
    SYNTAX     DisplayString
    MAX-ACCESS read-only
    STATUS     current
    DESCRIPTION
        "Version of the physical element."
    ::= { win32PhysicalMediaEntry 23 }

hwpmdWriteProtectOn OBJECT-TYPE
    SYNTAX     TruthValue
    MAX-ACCESS read-only
    STATUS     current
    DESCRIPTION
        "If true the media is currently write protected by
        some kind of physical mechanism, such as a protect
        tab on a floppy diskette."
    ::= { win32PhysicalMediaEntry 24 }

win32TapeDriveTable OBJECT-TYPE
    SYNTAX     SEQUENCE OF Win32TapeDriveEntry
    MAX-ACCESS not-accessible
    STATUS     current
    DESCRIPTION
        "The Win32_TapeDrive WMI class represents a tape
        drive on a Windows computer. Tape drives are
        primarily distinguished by the fact that they can
        be accessed only sequentially."
    ::= { wmiMassStorage 56 }

win32TapeDriveEntry OBJECT-TYPE
    SYNTAX     Win32TapeDriveEntry
    MAX-ACCESS not-accessible
    STATUS     current
    DESCRIPTION
        "None"
    INDEX      { hwtdIndex }
    ::= { win32TapeDriveTable 1 }

Win32TapeDriveEntry ::= SEQUENCE {
    hwtdIndex Integer32,
    hwtdAvailability INTEGER,
    hwtdCapabilities DisplayString,
    hwtdCapabilityDescriptions DisplayString,
    hwtdCaption DisplayString,
    hwtdCompression INTEGER,
    hwtdCompressionMethod DisplayString,
    hwtdConfigManagerErrorCode INTEGER,
    hwtdConfigManagerUserConfig TruthValue,
    hwtdCreationClassName DisplayString,
    hwtdDefaultBlockSize Gauge32,
    hwtdDescription DisplayString,
    hwtdDeviceID DisplayString,
    hwtdECC INTEGER,
    hwtdEOTWarningZoneSize Gauge32,
    hwtdErrorCleared TruthValue,
    hwtdErrorDescription DisplayString,
    hwtdErrorMethodology DisplayString,
    hwtdFeaturesHigh Gauge32,
    hwtdFeaturesLow Gauge32,
    hwtdId DisplayString,
    hwtdInstallDate DateAndTime,
    hwtdLastErrorCode Gauge32,
    hwtdManufacturer DisplayString,
    hwtdMaxBlockSize Gauge32,
    hwtdMaxMediaSize Gauge32,
    hwtdMaxPartitionCount Gauge32,
    hwtdMediaType DisplayString,
    hwtdMinBlockSize Gauge32,
    hwtdName DisplayString,
    hwtdNeedsCleaning TruthValue,
    hwtdNumberOfMediaSupported Gauge32,
    hwtdPadding Gauge32,
    hwtdPNPDeviceID DisplayString,
    hwtdPowerManagementCapabilities DisplayString,
    hwtdPowerManagementSupported TruthValue,
    hwtdReportSetMarks INTEGER,
    hwtdStatus INTEGER,
    hwtdStatusInfo INTEGER,
    hwtdSystemCreationClassName DisplayString,
    hwtdSystemName DisplayString
}

hwtdIndex OBJECT-TYPE
    SYNTAX     Integer32 (1..2147483647)
    MAX-ACCESS read-only
    STATUS     current
    DESCRIPTION
        "The value of this object uniquely identifies the
        instance entry for this class."
    ::= { win32TapeDriveEntry 1 }

hwtdAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32TapeDriveEntry 2 }

hwtdCapabilities OBJECT-TYPE
    SYNTAX     DisplayString
    MAX-ACCESS read-only
    STATUS     current
    DESCRIPTION
        "Array of capabilities of the media access device.
        For example, the device may support Random Access,
        removable media and Automatic Cleaning. In this
        case, the values 3, 7, and 9 would be written to
        the array. This property is inherited from
        CIM_MediaAccessDevice.
        Value Meaning 
        0 Unknown 
        1 Other 
        2 Sequential Access 
        3 Random Access 
        4 Supports Writing 
        5 Encryption 
        6 Compression 
        7 Supports Removable Media 
        8 Manual Cleaning 
        9 Automatic Cleaning 
        10 SMART Notification 
        11 Supports Dual Sided Media 
        12 Predismount Eject Not Required "
    ::= { win32TapeDriveEntry 3 }

hwtdCapabilityDescriptions OBJECT-TYPE
    SYNTAX     DisplayString
    MAX-ACCESS read-only
    STATUS     current
    DESCRIPTION
        "Array of free-form strings providing more detailed
        explanations for any of the access device features
        indicated in the Capabilities array. Note that each
        entry of this array is related to the entry in the
        Capabilities array that is located at the same
        index. This property is inherited from
        CIM_MediaAccessDevice."
    ::= { win32TapeDriveEntry 4 }

hwtdCaption OBJECT-TYPE
    SYNTAX     DisplayString (SIZE (0..64))
    MAX-ACCESS read-only
    STATUS     current
    DESCRIPTION
        "Short description (one-line string) of the object.
        This property is inherited from
        CIM_ManagedSystemElement."
    ::= { win32TapeDriveEntry 5 }

hwtdCompression OBJECT-TYPE
    SYNTAX     INTEGER {
        false(0),
        true(1)
    }
    MAX-ACCESS read-only
    STATUS     current
    DESCRIPTION
        "If TRUE, hardware data compression is enabled."
    ::= { win32TapeDriveEntry 6 }

hwtdCompressionMethod OBJECT-TYPE
    SYNTAX     DisplayString
    MAX-ACCESS read-only
    STATUS     current
    DESCRIPTION
        "Free form string indicating the algorithm or tool
        used by the device to support compression. If it is
        not possible or not desired to describe the
        compression scheme (perhaps because it is not
        known), we recommend using the following words:
        'Unknown' to represent that it is not known whether
        the device supports compression capabilities or
        not; 'Compressed' to represent that the device
        supports compression capabilities but either its
        compression scheme is not known or not disclosed;
        and 'Not Compressed' to represent that the device
        does not support compression capabilities. This
        property is inherited from CIM_MediaAccessDevice."
    ::= { win32TapeDriveEntry 7 }

hwtdConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32TapeDriveEntry 8 }

hwtdConfigManagerUserConfig OBJECT-TYPE
    SYNTAX     TruthValue
    MAX-ACCESS read-only
    STATUS     current
    DESCRIPTION
        "If TRUE, the device is using a user-defined
        configuration. This property is inherited from
        CIM_LogicalDevice."
    ::= { win32TapeDriveEntry 9 }

hwtdCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32TapeDriveEntry 10 }

hwtdDefaultBlockSize OBJECT-TYPE
    SYNTAX     Gauge32
    MAX-ACCESS read-only
    STATUS     current
    DESCRIPTION
        "Default block size, in bytes, for this device.
        This property is inherited from
        CIM_MediaAccessDevice."
    ::= { win32TapeDriveEntry 11 }

hwtdDescription OBJECT-TYPE
    SYNTAX     DisplayString
    MAX-ACCESS read-only
    STATUS     current
    DESCRIPTION
        "Description of the object. This property is
        inherited from CIM_ManagedSystemElement."
    ::= { win32TapeDriveEntry 12 }

hwtdDeviceID OBJECT-TYPE
    SYNTAX     DisplayString
    MAX-ACCESS read-only
    STATUS     current
    DESCRIPTION
        "Unique identifier of the tape drive with other
        devices on the system. This property is inherited
        from CIM_LogicalDevice."
    ::= { win32TapeDriveEntry 13 }

hwtdECC OBJECT-TYPE
    SYNTAX     INTEGER {
        false(0),
        true(1)
    }
    MAX-ACCESS read-only
    STATUS     current
    DESCRIPTION
        "If TRUE, the device supports hardware error
        correction."
    ::= { win32TapeDriveEntry 14 }

hwtdEOTWarningZoneSize OBJECT-TYPE
    SYNTAX     Gauge32
    MAX-ACCESS read-only
    STATUS     current
    DESCRIPTION
        "Zone size for the End Of Tape (EOT) warning. This
        property is inherited from CIM_TapeDrive."
    ::= { win32TapeDriveEntry 15 }

hwtdErrorCleared OBJECT-TYPE
    SYNTAX     TruthValue
    MAX-ACCESS read-only
    STATUS     current
    DESCRIPTION
        "If TRUE, the error reported in LastErrorCode is
        now cleared. This property is inherited from
        CIM_LogicalDevice."
    ::= { win32TapeDriveEntry 16 }

hwtdErrorDescription OBJECT-TYPE
    SYNTAX     DisplayString
    MAX-ACCESS read-only
    STATUS     current
    DESCRIPTION
        "Free-form string supplying more information about
        the error recorded in LastErrorCode, and
        information on any corrective actions that may be
        taken. This property is inherited from
        CIM_LogicalDevice."
    ::= { win32TapeDriveEntry 17 }

hwtdErrorMethodology OBJECT-TYPE
    SYNTAX     DisplayString
    MAX-ACCESS read-only
    STATUS     current
    DESCRIPTION
        "Free-form string describing the type of error
        detection and correction supported by this device.
        This property is inherited from
        CIM_MediaAccessDevice."
    ::= { win32TapeDriveEntry 18 }

hwtdFeaturesHigh OBJECT-TYPE
    SYNTAX     Gauge32
    MAX-ACCESS read-only
    STATUS     current
    DESCRIPTION
        "High-order 32 bits of the device features flag."
    ::= { win32TapeDriveEntry 19 }

hwtdFeaturesLow OBJECT-TYPE
    SYNTAX     Gauge32
    MAX-ACCESS read-only
    STATUS     current
    DESCRIPTION
        "Low-order 32 bits of the device features flag."
    ::= { win32TapeDriveEntry 20 }

hwtdId OBJECT-TYPE
    SYNTAX     DisplayString
    MAX-ACCESS read-only
    STATUS     current
    DESCRIPTION
        "Manufacturer's identifying name of the Windows CD
        ROM drive.
        Example: 'PLEXTOR CD-ROM PX-12CS 1.01'"
    ::= { win32TapeDriveEntry 21 }

hwtdInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32TapeDriveEntry 22 }

hwtdLastErrorCode OBJECT-TYPE
    SYNTAX     Gauge32
    MAX-ACCESS read-only
    STATUS     current
    DESCRIPTION
        "Last error code reported by the logical device.
        This property is inherited from CIM_LogicalDevice."
    ::= { win32TapeDriveEntry 23 }

hwtdManufacturer OBJECT-TYPE
    SYNTAX     DisplayString
    MAX-ACCESS read-only
    STATUS     current
    DESCRIPTION
        "Manufacturer of the Windows CD-ROM drive.
        Example: 'PLEXTOR'"
    ::= { win32TapeDriveEntry 24 }

hwtdMaxBlockSize OBJECT-TYPE
    SYNTAX     Gauge32
    MAX-ACCESS read-only
    STATUS     current
    DESCRIPTION
        "Maximum block size, in bytes, for media accessed
        by this device. This property is inherited from
        CIM_MediaAccessDevice."
    ::= { win32TapeDriveEntry 25 }

hwtdMaxMediaSize OBJECT-TYPE
    SYNTAX     Gauge32
    MAX-ACCESS read-only
    STATUS     current
    DESCRIPTION
        "Maximum size, in kilobytes, of media supported by
        this device. This property is inherited from
        CIM_MediaAccessDevice."
    ::= { win32TapeDriveEntry 26 }

hwtdMaxPartitionCount OBJECT-TYPE
    SYNTAX     Gauge32
    MAX-ACCESS read-only
    STATUS     current
    DESCRIPTION
        "Maximum partition count for the tape drive. This
        property is inherited from CIM_TapeDrive."
    ::= { win32TapeDriveEntry 27 }

hwtdMediaType OBJECT-TYPE
    SYNTAX     DisplayString
    MAX-ACCESS read-only
    STATUS     current
    DESCRIPTION
        "Media type used by (or accessed by) this device.
        In this case, it is set to 'Tape Drive'."
    ::= { win32TapeDriveEntry 28 }

hwtdMinBlockSize OBJECT-TYPE
    SYNTAX     Gauge32
    MAX-ACCESS read-only
    STATUS     current
    DESCRIPTION
        "Minimum block size, in bytes, for media accessed
        by this device. This property is inherited from
        CIM_MediaAccessDevice."
    ::= { win32TapeDriveEntry 29 }

hwtdName OBJECT-TYPE
    SYNTAX     DisplayString
    MAX-ACCESS read-only
    STATUS     current
    DESCRIPTION
        "Label by which the object is known. When
        subclassed, the property can be overridden to be a
        key property. This property is inherited from
        CIM_ManagedSystemElement."
    ::= { win32TapeDriveEntry 30 }

hwtdNeedsCleaning OBJECT-TYPE
    SYNTAX     TruthValue
    MAX-ACCESS read-only
    STATUS     current
    DESCRIPTION
        "If TRUE, the media access device needs cleaning.
        Whether manual or automatic cleaning is possible is
        indicated in the Capabilities property. This
        property is inherited from CIM_MediaAccessDevice."
    ::= { win32TapeDriveEntry 31 }

hwtdNumberOfMediaSupported OBJECT-TYPE
    SYNTAX     Gauge32
    MAX-ACCESS read-only
    STATUS     current
    DESCRIPTION
        "Maximum number of individual media which can be
        supported or inserted in the media access device
        (when supported). This property is inherited from
        CIM_MediaAccessDevice."
    ::= { win32TapeDriveEntry 32 }

hwtdPadding OBJECT-TYPE
    SYNTAX     Gauge32
    UNITS "Bytes"
    MAX-ACCESS read-only
    STATUS     current
    DESCRIPTION
        "Number of bytes inserted between blocks on a tape
        media. This property is inherited from
        CIM_TapeDrive."
    ::= { win32TapeDriveEntry 33 }

hwtdPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32TapeDriveEntry 34 }

hwtdPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32TapeDriveEntry 35 }

hwtdPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32TapeDriveEntry 36 }

hwtdReportSetMarks OBJECT-TYPE
    SYNTAX     INTEGER {
        false(0),
        true(1)
    }
    MAX-ACCESS read-only
    STATUS     current
    DESCRIPTION
        "If TRUE, setmark reporting is enabled. Setmark
        reporting makes use of a specialized recorded
        element that does not contain user data. This
        recorded element is used to provide a segmentation
        scheme that is hierarchically superior to
        filemarks. Setmarks provide faster positioning on
        high-capacity tapes."
    ::= { win32TapeDriveEntry 37 }

hwtdStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32TapeDriveEntry 38 }

hwtdStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32TapeDriveEntry 39 }

hwtdSystemCreationClassName OBJECT-TYPE
    SYNTAX     DisplayString
    MAX-ACCESS read-only
    STATUS     current
    DESCRIPTION
        "Value of the scoping computer's CreationClassName
        property. This property is inherited from
        CIM_LogicalDevice."
    ::= { win32TapeDriveEntry 40 }

hwtdSystemName OBJECT-TYPE
    SYNTAX     DisplayString
    MAX-ACCESS read-only
    STATUS     current
    DESCRIPTION
        "Name of the scoping system. This property is
        inherited from CIM_LogicalDevice."
    ::= { win32TapeDriveEntry 41 }

wmiMotherboardControllerPort OBJECT-IDENTITY
    STATUS     current
    DESCRIPTION
        "The Motherboard, Controllers, and Ports
        subcategory groups classes that represent system
        devices. Examples include system memory, cache
        memory, and controllers."
    ::= { wmiHardware 4 }

win321394ControllerTable OBJECT-TYPE
    SYNTAX     SEQUENCE OF Win321394ControllerEntry
    MAX-ACCESS not-accessible
    STATUS     current
    DESCRIPTION
        "The Win32_1394Controller WMI class represents the
        capabilities and management of a 1394 controller.
        IEEE 1394 is a specification for a high speed
        serial bus."
    ::= { wmiMotherboardControllerPort 1 }

win321394ControllerEntry OBJECT-TYPE
    SYNTAX     Win321394ControllerEntry
    MAX-ACCESS not-accessible
    STATUS     current
    DESCRIPTION
        "None"
    INDEX      { hw1394Index }
    ::= { win321394ControllerTable 1 }

Win321394ControllerEntry ::= SEQUENCE {
    hw1394Index Integer32,
    hw1394Availability INTEGER,
    hw1394Caption DisplayString,
    hw1394ConfigManagerErrorCode INTEGER,
    hw1394ConfigManagerUserConfig TruthValue,
    hw1394CreationClassName DisplayString,
    hw1394Description DisplayString,
    hw1394DeviceID DisplayString,
    hw1394ErrorCleared TruthValue,
    hw1394ErrorDescription DisplayString,
    hw1394InstallDate DateAndTime,
    hw1394LastErrorCode Gauge32,
    hw1394Manufacturer DisplayString,
    hw1394MaxNumberControlled Gauge32,
    hw1394Name DisplayString,
    hw1394PNPDeviceID DisplayString,
    hw1394PowerManagementCapability DisplayString,
    hw1394PowerManagementSupported TruthValue,
    hw1394ProtocolSupported INTEGER,
    hw1394Status INTEGER,
    hw1394StatusInfo INTEGER,
    hw1394SystemCreationClassName DisplayString,
    hw1394SystemName DisplayString,
    hw1394TimeOfLastReset DateAndTime
}

hw1394Index OBJECT-TYPE
    SYNTAX     Integer32 (1..2147483647)
    MAX-ACCESS read-only
    STATUS     current
    DESCRIPTION
        "The value of this object uniquely identifies the
        instance entry for this class."
    ::= { win321394ControllerEntry 1 }

hw1394Availability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. Inherited from CIM_LogicalDevice."
    ::= { win321394ControllerEntry 2 }

hw1394Caption OBJECT-TYPE
    SYNTAX     DisplayString
    MAX-ACCESS read-only
    STATUS     current
    DESCRIPTION
        "Short description (one-line string) of the object.
        This property is inherited from
        CIM_ManagedSystemElement."
    ::= { win321394ControllerEntry 3 }

hw1394ConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win321394ControllerEntry 4 }

hw1394ConfigManagerUserConfig OBJECT-TYPE
    SYNTAX     TruthValue
    MAX-ACCESS read-only
    STATUS     current
    DESCRIPTION
        "If TRUE, the device is using a user-defined
        configuration. This property is inherited from
        CIM_LogicalDevice."
    ::= { win321394ControllerEntry 5 }

hw1394CreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win321394ControllerEntry 6 }

hw1394Description OBJECT-TYPE
    SYNTAX     DisplayString
    MAX-ACCESS read-only
    STATUS     current
    DESCRIPTION
        "Description of the object. This property is
        inherited from CIM_ManagedSystemElement."
    ::= { win321394ControllerEntry 7 }

hw1394DeviceID OBJECT-TYPE
    SYNTAX     DisplayString
    MAX-ACCESS read-only
    STATUS     current
    DESCRIPTION
        "Unique identifier of this controller. This
        property is inherited from CIM_LogicalDevice."
    ::= { win321394ControllerEntry 8 }

hw1394ErrorCleared OBJECT-TYPE
    SYNTAX     TruthValue
    MAX-ACCESS read-only
    STATUS     current
    DESCRIPTION
        "If TRUE, the error reported in LastErrorCode is
        now cleared. This property is inherited from
        CIM_LogicalDevice."
    ::= { win321394ControllerEntry 9 }

hw1394ErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win321394ControllerEntry 10 }

hw1394InstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win321394ControllerEntry 11 }

hw1394LastErrorCode OBJECT-TYPE
    SYNTAX     Gauge32
    MAX-ACCESS read-only
    STATUS     current
    DESCRIPTION
        "Last error code reported by the logical device.
        This property is inherited from CIM_LogicalDevice."
    ::= { win321394ControllerEntry 12 }

hw1394Manufacturer OBJECT-TYPE
    SYNTAX     DisplayString
    MAX-ACCESS read-only
    STATUS     current
    DESCRIPTION
        "Manufacturer of the controller."
    ::= { win321394ControllerEntry 13 }

hw1394MaxNumberControlled OBJECT-TYPE
    SYNTAX     Gauge32
    MAX-ACCESS read-only
    STATUS     current
    DESCRIPTION
        "Maximum number of directly addressable entities
        supportable by this controller. A value of 0 should
        be used if the number is unknown. This property is
        inherited from CIM_Controller."
    ::= { win321394ControllerEntry 14 }

hw1394Name OBJECT-TYPE
    SYNTAX     DisplayString
    MAX-ACCESS read-only
    STATUS     current
    DESCRIPTION
        "Label by which the object is known. When
        subclassed, the property can be overridden to be a
        key property. This property is inherited from
        CIM_ManagedSystemElement."
    ::= { win321394ControllerEntry 15 }

hw1394PNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win321394ControllerEntry 16 }

hw1394PowerManagementCapability OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. This method is
        found on the parent CIM_LogicalDevice class and can
        be implemented. For more information, see Extending
        Your Management Capabilities. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win321394ControllerEntry 17 }

hw1394PowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win321394ControllerEntry 18 }

hw1394ProtocolSupported OBJECT-TYPE
    SYNTAX     INTEGER {
        other(1),
        unknown(2),
        eisa(3),
        isa(4),
        pci(5),
        ataATAPI(6),
        flexibleDiskette(7),
        n1496(8),
        scsiParallelInterface(9),
        scsiFibreChannelProtocol(10),
        scsiSerialBusProtocol(11),
        scsiSerialBusProtocol2(12),
        scsiSerialStorageArchitecture(13),
        vesa(14),
        pcmcia(15),
        universalSerialBus(16),
        parallelProtocol(17),
        escon(18),
        diagnostic(19),
        i2C(20),
        power(21),
        hippi(22),
        multiBus(23),
        vme(24),
        ipi(25),
        ieee488(26),
        rs232(27),
        ieee802310BASE5(28),
        ieee802310BASE2(29),
        ieee80231BASE5(30),
        ieee802310BROAD36(31),
        ieee8023100BASEVG(32),
        ieee8025TokenRing(33),
        ansiX3T95FDDI(34),
        mca(35),
        esdi(36),
        ide(37),
        cmd(38),
        st506(39),
        dssi(40),
        qic2(41),
        enhancedATAIDE(42),
        agp(43),
        twoWayInfrared(44),
        fastInfrared(45),
        serialInfrared(46),
        irBus(47)
    }
    MAX-ACCESS read-only
    STATUS     current
    DESCRIPTION
        "Protocol used by the controller to access
        'controlled' devices. This property is inherited
        from CIM_Controller."
    ::= { win321394ControllerEntry 19 }

hw1394Status OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win321394ControllerEntry 20 }

hw1394StatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win321394ControllerEntry 21 }

hw1394SystemCreationClassName OBJECT-TYPE
    SYNTAX     DisplayString
    MAX-ACCESS read-only
    STATUS     current
    DESCRIPTION
        "Value for the scoping computer's CreationClassName
        property. This property is inherited from
        CIM_LogicalDevice."
    ::= { win321394ControllerEntry 22 }

hw1394SystemName OBJECT-TYPE
    SYNTAX     DisplayString
    MAX-ACCESS read-only
    STATUS     current
    DESCRIPTION
        "Name of the scoping system. This property is
        inherited from CIM_LogicalDevice."
    ::= { win321394ControllerEntry 23 }

hw1394TimeOfLastReset OBJECT-TYPE
    SYNTAX     DateAndTime
    MAX-ACCESS read-only
    STATUS     current
    DESCRIPTION
        "Date and time controller was last reset. This
        could mean the controller was powered down, or
        reinitialized. This property is inherited from
        CIM_Controller."
    ::= { win321394ControllerEntry 24 }

win32BaseBoardTable OBJECT-TYPE
    SYNTAX     SEQUENCE OF Win32BaseBoardEntry
    MAX-ACCESS not-accessible
    STATUS     current
    DESCRIPTION
        "The Win32_BaseBoard WMI class represents a
        baseboard, which is also known as a motherboard or
        system board."
    ::= { wmiMotherboardControllerPort 2 }

win32BaseBoardEntry OBJECT-TYPE
    SYNTAX     Win32BaseBoardEntry
    MAX-ACCESS not-accessible
    STATUS     current
    DESCRIPTION
        "None"
    INDEX      { hwbbIndex }
    ::= { win32BaseBoardTable 1 }

Win32BaseBoardEntry ::= SEQUENCE {
    hwbbIndex Integer32,
    hwbbCaption DisplayString,
    hwbbConfigOptions DisplayString,
    hwbbCreationClassName DisplayString,
    hwbbDepth Integer32,
    hwbbDescription DisplayString,
    hwbbHeight Integer32,
    hwbbHostingBoard TruthValue,
    hwbbHotSwappable TruthValue,
    hwbbInstallDate DateAndTime,
    hwbbManufacturer DisplayString,
    hwbbModel DisplayString,
    hwbbName DisplayString,
    hwbbOtherIdentifyingInfo DisplayString,
    hwbbPartNumber DisplayString,
    hwbbPoweredOn TruthValue,
    hwbbProduct DisplayString,
    hwbbRemovable TruthValue,
    hwbbReplaceable TruthValue,
    hwbbRequirementsDescription DisplayString,
    hwbbRequiresDaughterBoard TruthValue,
    hwbbSerialNumber DisplayString,
    hwbbSKU DisplayString,
    hwbbSlotLayout DisplayString,
    hwbbSpecialRequirements TruthValue,
    hwbbStatus INTEGER,
    hwbbTag DisplayString,
    hwbbVersion DisplayString,
    hwbbWeight Integer32,
    hwbbWidth Integer32
}

hwbbIndex OBJECT-TYPE
    SYNTAX     Integer32 (1..2147483647)
    MAX-ACCESS read-only
    STATUS     current
    DESCRIPTION
        "The value of this object uniquely identifies the
        instance entry for this class."
    ::= { win32BaseBoardEntry 1 }

hwbbCaption OBJECT-TYPE
    SYNTAX     DisplayString
    MAX-ACCESS read-only
    STATUS     current
    DESCRIPTION
        "Short description of the object a one-line string.
        This property is inherited from
        CIM_ManagedSystemElement."
    ::= { win32BaseBoardEntry 2 }

hwbbConfigOptions OBJECT-TYPE
    SYNTAX     DisplayString
    MAX-ACCESS read-only
    STATUS     current
    DESCRIPTION
        "Array that represents the configuration of the
        jumpers and switches located on the base board.
        Example: 'JP2: 1-2 Cache Size is 256K, 2-3 Cache
        Size is 512K, SW1-1: Close to Disable On Board
        Video'"
    ::= { win32BaseBoardEntry 3 }

hwbbCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_PhysicalElement."
    ::= { win32BaseBoardEntry 4 }

hwbbDepth OBJECT-TYPE
    SYNTAX     Integer32
    MAX-ACCESS read-only
    STATUS     current
    DESCRIPTION
        "Depth of the physical package in inches. This
        property is inherited from CIM_PhysicalPackage."
    ::= { win32BaseBoardEntry 5 }

hwbbDescription OBJECT-TYPE
    SYNTAX     DisplayString
    MAX-ACCESS read-only
    STATUS     current
    DESCRIPTION
        "Description of the object. This property is
        inherited from CIM_ManagedSystemElement."
    ::= { win32BaseBoardEntry 6 }

hwbbHeight OBJECT-TYPE
    SYNTAX     Integer32
    MAX-ACCESS read-only
    STATUS     current
    DESCRIPTION
        "Height of the physical package in inches. This
        property is inherited from CIM_PhysicalPackage."
    ::= { win32BaseBoardEntry 7 }

hwbbHostingBoard OBJECT-TYPE
    SYNTAX     TruthValue
    MAX-ACCESS read-only
    STATUS     current
    DESCRIPTION
        "If TRUE, the card is a motherboard, or a baseboard
        in a chassis. This property is inherited from
        CIM_Card."
    ::= { win32BaseBoardEntry 8 }

hwbbHotSwappable OBJECT-TYPE
    SYNTAX     TruthValue
    MAX-ACCESS read-only
    STATUS     current
    DESCRIPTION
        "If TRUE, the package can be hot-swapped. A
        physical package can be hot-swapped if it is
        possible to replace the element with a physically
        different but equivalent oelement while the
        containing package has power applied to it that is,
        while it is ON. For example, a disk drive package
        inserted using SCA connectors is removable and can
        be hot-swapped. All packages that can be
        hot-swapped are inherently removable and
        replaceable. This property is inherited from
        CIM_PhysicalPackage."
    ::= { win32BaseBoardEntry 9 }

hwbbInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32BaseBoardEntry 10 }

hwbbManufacturer OBJECT-TYPE
    SYNTAX     DisplayString
    MAX-ACCESS read-only
    STATUS     current
    DESCRIPTION
        "Name of the organization responsible for producing
        the physical element. This property is inherited
        from CIM_PhysicalElement."
    ::= { win32BaseBoardEntry 11 }

hwbbModel OBJECT-TYPE
    SYNTAX     DisplayString
    MAX-ACCESS read-only
    STATUS     current
    DESCRIPTION
        "Name by which the physical element is known. This
        property is inherited from CIM_PhysicalElement."
    ::= { win32BaseBoardEntry 12 }

hwbbName OBJECT-TYPE
    SYNTAX     DisplayString
    MAX-ACCESS read-only
    STATUS     current
    DESCRIPTION
        "Label by which the object is known. When
        subclassed, the property can be overridden to be a
        key property. This property is inherited from
        CIM_ManagedSystemElement."
    ::= { win32BaseBoardEntry 13 }

hwbbOtherIdentifyingInfo OBJECT-TYPE
    SYNTAX     DisplayString
    MAX-ACCESS read-only
    STATUS     current
    DESCRIPTION
        "Captures additional data, beyond asset tag
        information, that can be used to identify a
        physical element. One example is bar code data that
        is associated with an element that also has an
        asset tag. Note that if only bar code data is
        available and unique or able to be used as an
        element key, the property value would be NULL and
        the bar code data used as the class key, in the tag
        property. This property is inherited from
        CIM_PhysicalElement."
    ::= { win32BaseBoardEntry 14 }

hwbbPartNumber OBJECT-TYPE
    SYNTAX     DisplayString
    MAX-ACCESS read-only
    STATUS     current
    DESCRIPTION
        "Part number assigned by the organization
        responsible for producing or manufacturing the
        physical element. This property is inherited from
        CIM_PhysicalElement."
    ::= { win32BaseBoardEntry 15 }

hwbbPoweredOn OBJECT-TYPE
    SYNTAX     TruthValue
    MAX-ACCESS read-only
    STATUS     current
    DESCRIPTION
        "If TRUE, the physical element is powered ON. This
        property is inherited from CIM_PhysicalElement."
    ::= { win32BaseBoardEntry 16 }

hwbbProduct OBJECT-TYPE
    SYNTAX     DisplayString
    MAX-ACCESS read-only
    STATUS     current
    DESCRIPTION
        "Baseboard part number defined by the
        manufacturer."
    ::= { win32BaseBoardEntry 17 }

hwbbRemovable OBJECT-TYPE
    SYNTAX     TruthValue
    MAX-ACCESS read-only
    STATUS     current
    DESCRIPTION
        "If TRUE, a package is removable. A physical
        package is removable if it is designed to be taken
        in and out of the physical container in which it is
        normally found without impairing the function of
        the overall packaging. A package can still be
        removable if power must be OFF in order to perform
        the removal. If power can be ON and the package
        removed, then the element is removable and can be
        hot-swapped. For example, an extra battery in a
        laptop is removable, as is a disk drive package
        inserted using SCA connectors. However, the latter
        can also be hot-swapped. A laptop's display is not
        removable, nor is a non-redundant power supply.
        Removing these components would impact the function
        of the overall packaging, or is impossible due to
        the tight integration of the package. This property
        is inherited from CIM_PhysicalPackage."
    ::= { win32BaseBoardEntry 18 }

hwbbReplaceable OBJECT-TYPE
    SYNTAX     TruthValue
    MAX-ACCESS read-only
    STATUS     current
    DESCRIPTION
        "If TRUE, a package is replaceable. A physical
        package is replaceable if it is possible to replace
        (FRU or upgrade) the element with a physically
        different one. For example, some computer systems
        allow the main processor chip to be upgraded to one
        of a higher clock rating. In this case, the
        processor is said to be replaceable. Another
        example is a power supply package mounted on
        sliding rails. All removable packages are
        inherently replaceable. This property is inherited
        from CIM_PhysicalPackage."
    ::= { win32BaseBoardEntry 19 }

hwbbRequirementsDescription OBJECT-TYPE
    SYNTAX     DisplayString
    MAX-ACCESS read-only
    STATUS     current
    DESCRIPTION
        "Free-form string that describes the way in which
        this card is physically unique from other cards.
        The property only has meaning when the
        corresponding Boolean property SpecialRequirements
        is set to TRUE. This property is inherited from
        CIM_Card."
    ::= { win32BaseBoardEntry 20 }

hwbbRequiresDaughterBoard OBJECT-TYPE
    SYNTAX     TruthValue
    MAX-ACCESS read-only
    STATUS     current
    DESCRIPTION
        "If TRUE, at least one daughterboard or auxiliary
        card is required to function properly. This
        property is inherited from CIM_Card."
    ::= { win32BaseBoardEntry 21 }

hwbbSerialNumber OBJECT-TYPE
    SYNTAX     DisplayString
    MAX-ACCESS read-only
    STATUS     current
    DESCRIPTION
        "Manufacturer-allocated number used to identify the
        physical element. This property is inherited from
        CIM_PhysicalElement."
    ::= { win32BaseBoardEntry 22 }

hwbbSKU OBJECT-TYPE
    SYNTAX     DisplayString
    MAX-ACCESS read-only
    STATUS     current
    DESCRIPTION
        "Stock-keeping unit number for the physical
        element. This property is inherited from
        CIM_PhysicalElement."
    ::= { win32BaseBoardEntry 23 }

hwbbSlotLayout OBJECT-TYPE
    SYNTAX     DisplayString
    MAX-ACCESS read-only
    STATUS     current
    DESCRIPTION
        "Free-form string that describes the slot position,
        typical usage, restrictions, individual slot
        spacing or any other pertinent information for the
        slots on a card. This property is inherited from
        CIM_Card."
    ::= { win32BaseBoardEntry 24 }

hwbbSpecialRequirements OBJECT-TYPE
    SYNTAX     TruthValue
    MAX-ACCESS read-only
    STATUS     current
    DESCRIPTION
        "If TRUE, this card is physically unique from other
        cards of the same type and therefore requires a
        special slot. For example, a double-wide card
        requires two slots. Another example is where a
        certain card may be used for the same general
        function as other cards but requires a special slot
        (for example, extra long), whereas the other cards
        can be placed in any available slot. If set to
        TRUE, then the corresponding property,
        RequirementsDescription, should specify the nature
        of the uniqueness or purpose of the card. This
        property is inherited from CIM_Card."
    ::= { win32BaseBoardEntry 25 }

hwbbStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32BaseBoardEntry 26 }

hwbbTag OBJECT-TYPE
    SYNTAX     DisplayString (SIZE (0..256))
    MAX-ACCESS read-only
    STATUS     current
    DESCRIPTION
        "Unique identifier of the baseboard of the system.
        This property is inherited from
        CIM_PhysicalElement.
        Example: 'Base Board'"
    ::= { win32BaseBoardEntry 27 }

hwbbVersion OBJECT-TYPE
    SYNTAX     DisplayString
    MAX-ACCESS read-only
    STATUS     current
    DESCRIPTION
        "Version of the physical element. This property is
        inherited from CIM_PhysicalElement."
    ::= { win32BaseBoardEntry 28 }

hwbbWeight OBJECT-TYPE
    SYNTAX     Integer32
    MAX-ACCESS read-only
    STATUS     current
    DESCRIPTION
        "Weight of the physical package in pounds. This
        property is inherited from CIM_PhysicalPackage."
    ::= { win32BaseBoardEntry 29 }

hwbbWidth OBJECT-TYPE
    SYNTAX     Integer32
    MAX-ACCESS read-only
    STATUS     current
    DESCRIPTION
        "Width of the physical package in inches. This
        property is inherited from CIM_PhysicalPackage."
    ::= { win32BaseBoardEntry 30 }

win32BIOSTable OBJECT-TYPE
    SYNTAX     SEQUENCE OF Win32BIOSEntry
    MAX-ACCESS not-accessible
    STATUS     current
    DESCRIPTION
        "The Win32_BIOS WMI class represents the attributes
        of the computer system's basic input/output
        services (BIOS) that are installed on a computer."
    ::= { wmiMotherboardControllerPort 3 }

win32BIOSEntry OBJECT-TYPE
    SYNTAX     Win32BIOSEntry
    MAX-ACCESS not-accessible
    STATUS     current
    DESCRIPTION
        "None"
    INDEX      { hwbiIndex }
    ::= { win32BIOSTable 1 }

Win32BIOSEntry ::= SEQUENCE {
    hwbiIndex Integer32,
    hwbiBiosCharacteristics DisplayString,
    hwbiBIOSVersion DisplayString,
    hwbiBuildNumber DisplayString,
    hwbiCaption DisplayString,
    hwbiCodeSet DisplayString,
    hwbiCurrentLanguage DisplayString,
    hwbiDescription DisplayString,
    hwbiIdentificationCode DisplayString,
    hwbiInstallableLanguages Integer32,
    hwbiInstallDate DateAndTime,
    hwbiLanguageEdition DisplayString,
    hwbiListOfLanguages DisplayString,
    hwbiManufacturer DisplayString,
    hwbiName DisplayString,
    hwbiOtherTargetOS DisplayString,
    hwbiPrimaryBIOS TruthValue,
    hwbiReleaseDate DateAndTime,
    hwbiSerialNumber DisplayString,
    hwbiSMBIOSBIOSVersion DisplayString,
    hwbiSMBIOSMajorVersion Integer32,
    hwbiSMBIOSMinorVersion Integer32,
    hwbiSMBIOSPresent TruthValue,
    hwbiSoftwareElementID DisplayString,
    hwbiSoftwareElementState INTEGER,
    hwbiStatus INTEGER,
    hwbiTargetOperatingSystem INTEGER,
    hwbiVersion DisplayString
}

hwbiIndex OBJECT-TYPE
    SYNTAX     Integer32 (1..2147483647)
    MAX-ACCESS read-only
    STATUS     current
    DESCRIPTION
        "The value of this object uniquely identifies the
        instance entry for this class."
    ::= { win32BIOSEntry 1 }

hwbiBiosCharacteristics OBJECT-TYPE
    SYNTAX     DisplayString
    MAX-ACCESS read-only
    STATUS     current
    DESCRIPTION
        "Array of BIOS characteristics supported by the
        system as defined by the System Management BIOS
        Reference Specification.
        Value Meaning 
        0 Reserved 
        1 Reserved 
        2 Unknown 
        3 BIOS Characteristics Not Supported 
        4 ISA is supported 
        5 MCA is supported 
        6 EISA is supported 
        7 PCI is supported 
        8 PC Card (PCMCIA) is supported 
        9 Plug and Play is supported 
        10 APM is supported 
        11 BIOS is Upgradable (Flash) 
        12 BIOS shadowing is allowed 
        13 VL-VESA is supported 
        14 ESCD support is available 
        15 Boot from CD is supported 
        16 Selectable Boot is supported 
        17 BIOS ROM is socketed 
        18 Boot From PC Card (PCMCIA) is supported 
        19 EDD (Enhanced Disk Drive) Specification is
        supported 
        20 Int 13h - Japanese Floppy for NEC 9800 1.2mb
        (3.5, 1k Bytes/Sector, 360 RPM) is supported 
        21 Int 13h - Japanese Floppy for Toshiba 1.2mb
        (3.5, 360 RPM) is supported 
        22 Int 13h - 5.25 / 360 KB Floppy Services are
        supported 
        23 Int 13h - 5.25 /1.2MB Floppy Services are
        supported 
        24 Int 13h - 3.5 / 720 KB Floppy Services are
        supported 
        25 Int 13h - 3.5 / 2.88 MB Floppy Services are
        supported 
        26 Int 5h, Print Screen Service is supported 
        27 Int 9h, 8042 Keyboard services are supported 
        28 Int 14h, Serial Services are supported 
        29 Int 17h, printer services are supported 
        30 Int 10h, CGA/Mono Video Services are supported 
        31 NEC PC-98 
        32 ACPI supported 
        33 USB Legacy is supported 
        34 AGP is supported 
        35 I2O boot is supported 
        36 LS-120 boot is supported 
        37 ATAPI ZIP Drive boot is supported 
        38 1394 boot is supported 
        39 Smart Battery supported "
    ::= { win32BIOSEntry 2 }

hwbiBIOSVersion OBJECT-TYPE
    SYNTAX     DisplayString
    MAX-ACCESS read-only
    STATUS     current
    DESCRIPTION
        "Windows Server 2003 and Windows XP:  Array of the
        complete system BIOS information. In many computers
        there can be several version strings that are
        stored in the registry, and represent the system
        BIOS information. "
    ::= { win32BIOSEntry 3 }

hwbiBuildNumber OBJECT-TYPE
    SYNTAX     DisplayString
    MAX-ACCESS read-only
    STATUS     current
    DESCRIPTION
        "Internal identifier for this compilation of this
        software element. This property is inherited from
        CIM_SoftwareElement. "
    ::= { win32BIOSEntry 4 }

hwbiCaption OBJECT-TYPE
    SYNTAX     DisplayString
    MAX-ACCESS read-only
    STATUS     current
    DESCRIPTION
        "Short description of the object a one-line string.
        This property is inherited from
        CIM_ManagedSystemElement."
    ::= { win32BIOSEntry 5 }

hwbiCodeSet OBJECT-TYPE
    SYNTAX     DisplayString (SIZE (0..64))
    MAX-ACCESS read-only
    STATUS     current
    DESCRIPTION
        "Code set used by this software element. This
        property is inherited from CIM_SoftwareElement."
    ::= { win32BIOSEntry 6 }

hwbiCurrentLanguage OBJECT-TYPE
    SYNTAX     DisplayString
    MAX-ACCESS read-only
    STATUS     current
    DESCRIPTION
        "Name of the current BIOS language."
    ::= { win32BIOSEntry 7 }

hwbiDescription OBJECT-TYPE
    SYNTAX     DisplayString
    MAX-ACCESS read-only
    STATUS     current
    DESCRIPTION
        "Description of the object. This property is
        inherited from CIM_ManagedSystemElement."
    ::= { win32BIOSEntry 8 }

hwbiIdentificationCode OBJECT-TYPE
    SYNTAX     DisplayString (SIZE (0..64))
    MAX-ACCESS read-only
    STATUS     current
    DESCRIPTION
        "Manufacturer's identifier for this software
        element. Often this will be a stock keeping unit
        (SKU) or a part number. This property is inherited
        from CIM_SoftwareElement."
    ::= { win32BIOSEntry 9 }

hwbiInstallableLanguages OBJECT-TYPE
    SYNTAX     Integer32
    MAX-ACCESS read-only
    STATUS     current
    DESCRIPTION
        "Number of languages available for installation on
        this system. Language may determine properties such
        as the need for Unicode and bi-directional text."
    ::= { win32BIOSEntry 10 }

hwbiInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32BIOSEntry 11 }

hwbiLanguageEdition OBJECT-TYPE
    SYNTAX     DisplayString (SIZE (0..32))
    MAX-ACCESS read-only
    STATUS     current
    DESCRIPTION
        "Language edition of this software element. The
        language codes defined in ISO 639 should be used.
        Where the software element represents multilingual
        or international version of a product, the string
        'multilingual' should be used. This property is
        inherited from CIM_SoftwareElement."
    ::= { win32BIOSEntry 12 }

hwbiListOfLanguages OBJECT-TYPE
    SYNTAX     DisplayString
    MAX-ACCESS read-only
    STATUS     current
    DESCRIPTION
        "Array of names of available BIOS-installable
        languages."
    ::= { win32BIOSEntry 13 }

hwbiManufacturer OBJECT-TYPE
    SYNTAX     DisplayString
    MAX-ACCESS read-only
    STATUS     current
    DESCRIPTION
        "Manufacturer of this software element. This
        property is inherited from CIM_SoftwareElement."
    ::= { win32BIOSEntry 14 }

hwbiName OBJECT-TYPE
    SYNTAX     DisplayString (SIZE (0..256))
    MAX-ACCESS read-only
    STATUS     current
    DESCRIPTION
        "Name used to identify this software element. This
        property is inherited from
        CIM_ManagedSystemElement."
    ::= { win32BIOSEntry 15 }

hwbiOtherTargetOS OBJECT-TYPE
    SYNTAX     DisplayString (SIZE (0..64))
    MAX-ACCESS read-only
    STATUS     current
    DESCRIPTION
        "Records the manufacturer and operating system type
        for a software element when the
        TargetOperatingSystem property has a value of 1
        (Other). When TargetOperatingSystem has a value of
        1, OtherTargetOS must have a non-null value. For
        all other values of TargetOperatingSystem,
        OtherTargetOS is NULL. This property is inherited
        from CIM_SoftwareElement."
    ::= { win32BIOSEntry 16 }

hwbiPrimaryBIOS OBJECT-TYPE
    SYNTAX     TruthValue
    MAX-ACCESS read-only
    STATUS     current
    DESCRIPTION
        "If TRUE, this is the primary BIOS of the computer
        system. This property is inherited from
        CIM_BIOSElement."
    ::= { win32BIOSEntry 17 }

hwbiReleaseDate OBJECT-TYPE
    SYNTAX     DateAndTime
    MAX-ACCESS read-only
    STATUS     current
    DESCRIPTION
        "Release date of the Windows BIOS in the
        Coordinated Universal Time (UTC) format of
        YYYYMMDDHHMMSS.MMMMMM(+-)OOO."
    ::= { win32BIOSEntry 18 }

hwbiSerialNumber OBJECT-TYPE
    SYNTAX     DisplayString
    MAX-ACCESS read-only
    STATUS     current
    DESCRIPTION
        "Assigned serial number of the software element.
        This property is inherited from
        CIM_SoftwareElement."
    ::= { win32BIOSEntry 19 }

hwbiSMBIOSBIOSVersion OBJECT-TYPE
    SYNTAX     DisplayString
    MAX-ACCESS read-only
    STATUS     current
    DESCRIPTION
        "BIOS version as reported by SMBIOS."
    ::= { win32BIOSEntry 20 }

hwbiSMBIOSMajorVersion OBJECT-TYPE
    SYNTAX     Integer32
    MAX-ACCESS read-only
    STATUS     current
    DESCRIPTION
        "Major SMBIOS version number. This property is NULL
        if SMBIOS is not found."
    ::= { win32BIOSEntry 21 }

hwbiSMBIOSMinorVersion OBJECT-TYPE
    SYNTAX     Integer32
    MAX-ACCESS read-only
    STATUS     current
    DESCRIPTION
        "Minor SMBIOS version number. This property is NULL
        if SMBIOS is not found."
    ::= { win32BIOSEntry 22 }

hwbiSMBIOSPresent OBJECT-TYPE
    SYNTAX     TruthValue
    MAX-ACCESS read-only
    STATUS     current
    DESCRIPTION
        "If true, the SMBIOS is available on this computer
        system."
    ::= { win32BIOSEntry 23 }

hwbiSoftwareElementID OBJECT-TYPE
    SYNTAX     DisplayString
    MAX-ACCESS read-only
    STATUS     current
    DESCRIPTION
        "Identifier for this software element; designed to
        be used in conjunction with other keys to create a
        unique representation of this CIM_SoftwareElement
        instance. This property is inherited from
        CIM_SoftwareElement."
    ::= { win32BIOSEntry 24 }

hwbiSoftwareElementState OBJECT-TYPE
    SYNTAX     INTEGER {
        deployable(0),
        installable(1),
        executable(2),
        running(3)
    }
    MAX-ACCESS read-only
    STATUS     current
    DESCRIPTION
        "State of a software element. This property is
        inherited from CIM_SoftwareElement."
    ::= { win32BIOSEntry 25 }

hwbiStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32BIOSEntry 26 }

hwbiTargetOperatingSystem OBJECT-TYPE
    SYNTAX     INTEGER {
        unknown(0),
        other(1),
        macos(2),
        attunix(3),
        dgux(4),
        decnt(5),
        digitalUnix(6),
        openVMS(7),
        hpux(8),
        aix(9),
        mvs(10),
        os400(11),
        os2(12),
        javaVM(13),
        msdos(14),
        win3x(15),
        win95(16),
        win98(17),
        winnt(18),
        wince(19),
        ncr3000(20),
        netWare(21),
        osf(22),
        dcOS(23),
        reliantUNIX(24),
        scoUnixWare(25),
        scoOpenServer(26),
        sequent(27),
        irix(28),
        solaris(29),
        sunOS(30),
        u6000(31),
        aseries(32),
        tandemNSK(33),
        tandemNT(34),
        bs2000(35),
        linux(36),
        lynx(37),
        xenix(38),
        vmESA(39),
        interactiveUNIX(40),
        bsdunix(41),
        freeBSD(42),
        netBSD(43),
        gnuHurd(44),
        os9(45),
        machKernel(46),
        inferno(47),
        qnx(48),
        epoc(49),
        ixWorks(50),
        vxWorks(51),
        miNT(52),
        beOS(53),
        hpMPE(54),
        nextStep(55),
        palmPilot(56),
        rhapsody(57),
        windows2000(58),
        dedicated(59),
        vse(60),
        tpf(61)
    }
    MAX-ACCESS read-only
    STATUS     current
    DESCRIPTION
        "Target operating system of the owning software
        element. This property is inherited from
        CIM_SoftwareElement."
    ::= { win32BIOSEntry 27 }

hwbiVersion OBJECT-TYPE
    SYNTAX     DisplayString (SIZE (0..64))
    MAX-ACCESS read-only
    STATUS     current
    DESCRIPTION
        "Version of the BIOS. This string is created by the
        BIOS manufacturer. This property is inherited from
        CIM_SoftwareElement."
    ::= { win32BIOSEntry 28 }

win32BusTable OBJECT-TYPE
    SYNTAX     SEQUENCE OF Win32BusEntry
    MAX-ACCESS not-accessible
    STATUS     current
    DESCRIPTION
        "The Win32_Bus WMI class represents a physical bus
        as seen by a Windows operating system. Any instance
        of a Windows bus is a descendent (or member) of
        this class."
    ::= { wmiMotherboardControllerPort 4 }

win32BusEntry OBJECT-TYPE
    SYNTAX     Win32BusEntry
    MAX-ACCESS not-accessible
    STATUS     current
    DESCRIPTION
        "None"
    INDEX      { hwbuIndex }
    ::= { win32BusTable 1 }

Win32BusEntry ::= SEQUENCE {
    hwbuIndex Integer32,
    hwbuAvailability INTEGER,
    hwbuBusNum Gauge32,
    hwbuBusType INTEGER,
    hwbuCaption DisplayString,
    hwbuConfigManagerErrorCode INTEGER,
    hwbuConfigManagerUserConfig TruthValue,
    hwbuCreationClassName DisplayString,
    hwbuDescription DisplayString,
    hwbuDeviceID DisplayString,
    hwbuErrorCleared TruthValue,
    hwbuErrorDescription DisplayString,
    hwbuInstallDate DateAndTime,
    hwbuLastErrorCode Gauge32,
    hwbuName DisplayString,
    hwbuPNPDeviceID DisplayString,
    hwbuPowerManagementCapabilities DisplayString,
    hwbuPowerManagementSupported TruthValue,
    hwbuStatus INTEGER,
    hwbuStatusInfo INTEGER,
    hwbuSystemCreationClassName DisplayString,
    hwbuSystemName DisplayString
}

hwbuIndex OBJECT-TYPE
    SYNTAX     Integer32 (1..2147483647)
    MAX-ACCESS read-only
    STATUS     current
    DESCRIPTION
        "The value of this object uniquely identifies the
        instance entry for this class."
    ::= { win32BusEntry 1 }

hwbuAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32BusEntry 2 }

hwbuBusNum OBJECT-TYPE
    SYNTAX     Gauge32
    MAX-ACCESS read-only
    STATUS     current
    DESCRIPTION
        "Logical number assigned to the physical bus.
        Example: 1"
    ::= { win32BusEntry 3 }

hwbuBusType OBJECT-TYPE
    SYNTAX     INTEGER {
        internal(0),
        isa(1),
        eisa(2),
        microChannel(3),
        turboChannel(4),
        pciBus(5),
        vmeBus(6),
        nuBus(7),
        pcmciaBus(8),
        cBus(9),
        mpiBus(10),
        mpsaBus(11),
        internalProcessor(12),
        internalPowerBus(13),
        pnpISABus(14),
        pnpBus(15),
        maximumInterfaceType(16)
    }
    MAX-ACCESS read-only
    STATUS     current
    DESCRIPTION
        "Type of the physical bus. This value will be one
        of the values in the INTERFACE_TYPE enumeration
        defined in Bus.h."
    ::= { win32BusEntry 4 }

hwbuCaption OBJECT-TYPE
    SYNTAX     DisplayString
    MAX-ACCESS read-only
    STATUS     current
    DESCRIPTION
        "Short description of the object a one-line string.
        This property is inherited from
        CIM_ManagedSystemElement."
    ::= { win32BusEntry 5 }

hwbuConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32BusEntry 6 }

hwbuConfigManagerUserConfig OBJECT-TYPE
    SYNTAX     TruthValue
    MAX-ACCESS read-only
    STATUS     current
    DESCRIPTION
        "If TRUE, the device is using a user-defined
        configuration. This property is inherited from
        CIM_LogicalDevice."
    ::= { win32BusEntry 7 }

hwbuCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32BusEntry 8 }

hwbuDescription OBJECT-TYPE
    SYNTAX     DisplayString
    MAX-ACCESS read-only
    STATUS     current
    DESCRIPTION
        "Description of the object. This property is
        inherited from CIM_ManagedSystemElement."
    ::= { win32BusEntry 9 }

hwbuDeviceID OBJECT-TYPE
    SYNTAX     DisplayString
    MAX-ACCESS read-only
    STATUS     current
    DESCRIPTION
        "Unique name that identifies the bus. This property
        is inherited from CIM_LogicalDevice."
    ::= { win32BusEntry 10 }

hwbuErrorCleared OBJECT-TYPE
    SYNTAX     TruthValue
    MAX-ACCESS read-only
    STATUS     current
    DESCRIPTION
        "If TRUE, the error reported in LastErrorCode is
        now cleared. This property is inherited from
        CIM_LogicalDevice."
    ::= { win32BusEntry 11 }

hwbuErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32BusEntry 12 }

hwbuInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32BusEntry 13 }

hwbuLastErrorCode OBJECT-TYPE
    SYNTAX     Gauge32
    MAX-ACCESS read-only
    STATUS     current
    DESCRIPTION
        "Last error code reported by the logical device.
        This property is inherited from CIM_LogicalDevice."
    ::= { win32BusEntry 14 }

hwbuName OBJECT-TYPE
    SYNTAX     DisplayString
    MAX-ACCESS read-only
    STATUS     current
    DESCRIPTION
        "Label by which the object is known. When
        subclassed, this property can be overridden to be a
        key property. This property is inherited from
        CIM_ManagedSystemElement."
    ::= { win32BusEntry 15 }

hwbuPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32BusEntry 16 }

hwbuPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32BusEntry 17 }

hwbuPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32BusEntry 18 }

hwbuStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32BusEntry 19 }

hwbuStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32BusEntry 20 }

hwbuSystemCreationClassName OBJECT-TYPE
    SYNTAX     DisplayString
    MAX-ACCESS read-only
    STATUS     current
    DESCRIPTION
        "Value of the scoping computer's CreationClassName
        property. This property is inherited from
        CIM_LogicalDevice."
    ::= { win32BusEntry 21 }

hwbuSystemName OBJECT-TYPE
    SYNTAX     DisplayString
    MAX-ACCESS read-only
    STATUS     current
    DESCRIPTION
        "Name of the scoping system. This property is
        inherited from CIM_LogicalDevice."
    ::= { win32BusEntry 22 }

win32CacheMemoryTable OBJECT-TYPE
    SYNTAX     SEQUENCE OF Win32CacheMemoryEntry
    MAX-ACCESS not-accessible
    STATUS     current
    DESCRIPTION
        "The Win32_CacheMemory WMI class represents
        internal and external cache memory on a computer
        system."
    ::= { wmiMotherboardControllerPort 5 }

win32CacheMemoryEntry OBJECT-TYPE
    SYNTAX     Win32CacheMemoryEntry
    MAX-ACCESS not-accessible
    STATUS     current
    DESCRIPTION
        "None"
    INDEX      { hwcmIndex }
    ::= { win32CacheMemoryTable 1 }

Win32CacheMemoryEntry ::= SEQUENCE {
    hwcmIndex Integer32,
    hwcmAccess INTEGER,
    hwcmAdditionalErrorData DisplayString,
    hwcmAssociativity INTEGER,
    hwcmAvailability INTEGER,
    hwcmBlockSize Gauge32,
    hwcmCacheSpeed Gauge32,
    hwcmCacheType INTEGER,
    hwcmCaption DisplayString,
    hwcmConfigManagerErrorCode INTEGER,
    hwcmConfigManagerUserConfig TruthValue,
    hwcmCorrectableError TruthValue,
    hwcmCreationClassName DisplayString,
    hwcmCurrentSRAM DisplayString,
    hwcmDescription DisplayString,
    hwcmDeviceID DisplayString,
    hwcmEndingAddress Gauge32,
    hwcmErrorAccess INTEGER,
    hwcmErrorAddress Gauge32,
    hwcmErrorCleared TruthValue,
    hwcmErrorCorrectType INTEGER,
    hwcmErrorData DisplayString,
    hwcmErrorDataOrder INTEGER,
    hwcmErrorDescription DisplayString,
    hwcmErrorInfo INTEGER,
    hwcmErrorMethodology DisplayString,
    hwcmErrorResolution Gauge32,
    hwcmErrorTime DateAndTime,
    hwcmErrorTransferSize Gauge32,
    hwcmFlushTimer Gauge32,
    hwcmInstallDate DateAndTime,
    hwcmInstalledSize Gauge32,
    hwcmLastErrorCode Gauge32,
    hwcmLevel INTEGER,
    hwcmLineSize Gauge32,
    hwcmLocation INTEGER,
    hwcmMaxCacheSize Gauge32,
    hwcmName DisplayString,
    hwcmNumberOfBlocks Gauge32,
    hwcmOtherErrorDescription DisplayString,
    hwcmPNPDeviceID DisplayString,
    hwcmPowerManagementCapabilities DisplayString,
    hwcmPowerManagementSupported TruthValue,
    hwcmPurpose DisplayString,
    hwcmReadPolicy INTEGER,
    hwcmReplacementPolicy INTEGER,
    hwcmStartingAddress Gauge32,
    hwcmStatus INTEGER,
    hwcmStatusInfo INTEGER,
    hwcmSupportedSRAM DisplayString,
    hwcmSystemCreationClassName DisplayString,
    hwcmSystemLevelAddress TruthValue,
    hwcmSystemName DisplayString,
    hwcmWritePolicy INTEGER
}

hwcmIndex OBJECT-TYPE
    SYNTAX     Integer32 (1..2147483647)
    MAX-ACCESS read-only
    STATUS     current
    DESCRIPTION
        "The value of this object uniquely identifies the
        instance entry for this class."
    ::= { win32CacheMemoryEntry 1 }

hwcmAccess OBJECT-TYPE
    SYNTAX     INTEGER {
        unknown(0),
        readable(1),
        writable(2),
        readWriteSupported(3),
        writeOnce(4)
    }
    MAX-ACCESS read-only
    STATUS     current
    DESCRIPTION
        "Type of access. This property is inherited from
        CIM_StorageExtent."
    ::= { win32CacheMemoryEntry 2 }

hwcmAdditionalErrorData OBJECT-TYPE
    SYNTAX     DisplayString
    MAX-ACCESS read-only
    STATUS     current
    DESCRIPTION
        "Array of octets that hold additional error
        information. An example is ECC Syndrome or the
        return of the check bits if a CRC-based error
        methodology is used. In the latter case, if a
        single bit error is recognized and the CRC
        algorithm is known, it is possible to determine the
        exact bit that failed. This type of data (ECC
        Syndrome, Check Bit, Parity Bit data, or other
        vendor supplied information) is included in this
        field. If the ErrorInfo property is equal to 3
        (OK), then this property has no meaning. This
        property is inherited from CIM_Memory."
    ::= { win32CacheMemoryEntry 3 }

hwcmAssociativity OBJECT-TYPE
    SYNTAX     INTEGER {
        other(1),
        unknown(2),
        directMapped(3),
        n2waySetAssociative(4),
        n4waySetAssociative(5),
        fullyAssociative(6),
        n8waySetAssociative(7),
        n16waySetAssociative(8)
    }
    MAX-ACCESS read-only
    STATUS     current
    DESCRIPTION
        "An integer enumeration that defines the system
        cache associativity. This property is inherited
        from CIM_CacheMemory."
    ::= { win32CacheMemoryEntry 4 }

hwcmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32CacheMemoryEntry 5 }

hwcmBlockSize OBJECT-TYPE
    SYNTAX     Gauge32
    MAX-ACCESS read-only
    STATUS     current
    DESCRIPTION
        "Size in bytes of the blocks that form this storage
        extent. If unknown or if a block concept is not
        valid (for example, for aggregate extents, memory
        or logical disks), enter a 1. This property is
        inherited from CIM_StorageExtent."
    ::= { win32CacheMemoryEntry 6 }

hwcmCacheSpeed OBJECT-TYPE
    SYNTAX     Gauge32
    UNITS "NanoSeconds"
    MAX-ACCESS read-only
    STATUS     current
    DESCRIPTION
        "Speed of the cache."
    ::= { win32CacheMemoryEntry 7 }

hwcmCacheType OBJECT-TYPE
    SYNTAX     INTEGER {
        other(1),
        unknown(2),
        instruction(3),
        data(4),
        unified(5)
    }
    MAX-ACCESS read-only
    STATUS     current
    DESCRIPTION
        "Type of cache. This property is inherited from
        CIM_CacheMemory."
    ::= { win32CacheMemoryEntry 8 }

hwcmCaption OBJECT-TYPE
    SYNTAX     DisplayString
    MAX-ACCESS read-only
    STATUS     current
    DESCRIPTION
        "Short description of the object a one-line string.
        This property is inherited from
        CIM_ManagedSystemElement."
    ::= { win32CacheMemoryEntry 9 }

hwcmConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32CacheMemoryEntry 10 }

hwcmConfigManagerUserConfig OBJECT-TYPE
    SYNTAX     TruthValue
    MAX-ACCESS read-only
    STATUS     current
    DESCRIPTION
        "If TRUE, the device is using a user-defined
        configuration. This property is inherited from
        CIM_LogicalDevice."
    ::= { win32CacheMemoryEntry 11 }

hwcmCorrectableError OBJECT-TYPE
    SYNTAX     TruthValue
    MAX-ACCESS read-only
    STATUS     current
    DESCRIPTION
        "If TRUE, the most recent error was correctable. If
        the ErrorInfo property is equal to 3 (OK), then
        this property has no meaning. This property is
        inherited from CIM_Memory."
    ::= { win32CacheMemoryEntry 12 }

hwcmCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32CacheMemoryEntry 13 }

hwcmCurrentSRAM OBJECT-TYPE
    SYNTAX     DisplayString
    MAX-ACCESS read-only
    STATUS     current
    DESCRIPTION
        "Array of types of Static Random Access Memory
        (SRAM) being used for the cache memory.
        Value Meaning 
        0 Other 
        1 Unknown 
        2 Non-Burst 
        3 Burst 
        4 Pipeline Burst 
        5 Synchronous 
        6 Asynchronous "
    ::= { win32CacheMemoryEntry 14 }

hwcmDescription OBJECT-TYPE
    SYNTAX     DisplayString
    MAX-ACCESS read-only
    STATUS     current
    DESCRIPTION
        "Description of the object. This property is
        inherited from CIM_ManagedSystemElement."
    ::= { win32CacheMemoryEntry 15 }

hwcmDeviceID OBJECT-TYPE
    SYNTAX     DisplayString
    MAX-ACCESS read-only
    STATUS     current
    DESCRIPTION
        "Unique identifier of the cache represented by an
        instance of Win32_CacheMemory. This property is
        inherited from CIM_LogicalDevice.
        Example: 'Cache Memory 1'"
    ::= { win32CacheMemoryEntry 16 }

hwcmEndingAddress OBJECT-TYPE
    SYNTAX     Gauge32
    MAX-ACCESS read-only
    STATUS     current
    DESCRIPTION
        "Ending address, referenced by an application or
        operating system and mapped by a memory controller,
        for this memory object. The ending address is
        specified in kilobytes. This property is inherited
        from CIM_Memory."
    ::= { win32CacheMemoryEntry 17 }

hwcmErrorAccess OBJECT-TYPE
    SYNTAX     INTEGER {
        other(1),
        unknown(2),
        read(3),
        write(4),
        partialWrite(5)
    }
    MAX-ACCESS read-only
    STATUS     current
    DESCRIPTION
        "Memory access operation that caused the last
        error. The type of error is described by the
        ErrorInfo property. If ErrorInfo is equal to 3
        (OK), then this property has no meaning. This
        property is inherited from CIM_Memory."
    ::= { win32CacheMemoryEntry 18 }

hwcmErrorAddress OBJECT-TYPE
    SYNTAX     Gauge32
    MAX-ACCESS read-only
    STATUS     current
    DESCRIPTION
        "Address of the last memory error. The type of
        error is described by the ErrorInfo property. If
        ErrorInfo is equal to 3 (OK), then this property
        has no meaning. This property is inherited from
        CIM_Memory."
    ::= { win32CacheMemoryEntry 19 }

hwcmErrorCleared OBJECT-TYPE
    SYNTAX     TruthValue
    MAX-ACCESS read-only
    STATUS     current
    DESCRIPTION
        "If TRUE, the error reported in LastErrorCode is
        now cleared. This property is inherited from
        CIM_LogicalDevice."
    ::= { win32CacheMemoryEntry 20 }

hwcmErrorCorrectType OBJECT-TYPE
    SYNTAX     INTEGER {
        reserved(0),
        other(1),
        unknown(2),
        none(3),
        parity(4),
        singlebitECC(5),
        multibitECC(6)
    }
    MAX-ACCESS read-only
    STATUS     current
    DESCRIPTION
        "Error correction method used by the cache memory."
    ::= { win32CacheMemoryEntry 21 }

hwcmErrorData OBJECT-TYPE
    SYNTAX     DisplayString
    MAX-ACCESS read-only
    STATUS     current
    DESCRIPTION
        "Array of data captured during the last erroneous
        memory access. The data occupies the first n octets
        of the array necessary to hold the number of bits
        specified by the ErrorTransferSize property. If
        ErrorTransferSize is 0, then this property has no
        meaning. This property is inherited from
        CIM_Memory."
    ::= { win32CacheMemoryEntry 22 }

hwcmErrorDataOrder OBJECT-TYPE
    SYNTAX     INTEGER {
        unknown(0),
        leastSignificantByteFirst(1),
        mostSignificantByteFirst(2)
    }
    MAX-ACCESS read-only
    STATUS     current
    DESCRIPTION
        "Ordering for data stored in the ErrorData
        property. If ErrorTransferSize is 0, then this
        property has no meaning. This property is inherited
        from CIM_Memory."
    ::= { win32CacheMemoryEntry 23 }

hwcmErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32CacheMemoryEntry 24 }

hwcmErrorInfo OBJECT-TYPE
    SYNTAX     INTEGER {
        other(1),
        unknown(2),
        ok(3),
        badRead(4),
        parityError(5),
        singleBitError(6),
        doubleBitError(7),
        multiBitError(8),
        nibbleError(9),
        checksumError(10),
        crcError(11)
    }
    MAX-ACCESS read-only
    STATUS     current
    DESCRIPTION
        "Type of error that occurred most recently. The
        values 12-14 are undefined in the CIM schema
        because in DMI they mix the semantics of the type
        of error and whether it was correctable or not. The
        latter is indicated in the property
        CorrectableError. This property is inherited from
        CIM_Memory."
    ::= { win32CacheMemoryEntry 25 }

hwcmErrorMethodology OBJECT-TYPE
    SYNTAX     DisplayString
    MAX-ACCESS read-only
    STATUS     current
    DESCRIPTION
        "Details on the parity or CRC algorithms, ECC, or
        other mechanisms used. This property is inherited
        from CIM_Memory."
    ::= { win32CacheMemoryEntry 26 }

hwcmErrorResolution OBJECT-TYPE
    SYNTAX     Gauge32
    MAX-ACCESS read-only
    STATUS     current
    DESCRIPTION
        "Range, in bytes, to which the last error can be
        resolved. For example, if error addresses are
        resolved to bit 11 (that is, on a typical page
        basis), then errors can be resolved to 4K
        boundaries and this property is set to 4000. If the
        ErrorInfo property is equal to 3 (OK), then this
        property has no meaning. This property is inherited
        from CIM_Memory."
    ::= { win32CacheMemoryEntry 27 }

hwcmErrorTime OBJECT-TYPE
    SYNTAX     DateAndTime
    MAX-ACCESS read-only
    STATUS     current
    DESCRIPTION
        "Time that the last memory error occurred. The type
        of error is described by the ErrorInfo property. If
        the ErrorInfo property is equal to 3 (OK), then
        this property has no meaning. This property is
        inherited from CIM_Memory."
    ::= { win32CacheMemoryEntry 28 }

hwcmErrorTransferSize OBJECT-TYPE
    SYNTAX     Gauge32
    MAX-ACCESS read-only
    STATUS     current
    DESCRIPTION
        "Size of the data transfer in bits that caused the
        last error. 0 indicates no error. If the ErrorInfo
        property is equal to 3 (OK), then this property
        should be set to 0. This property is inherited from
        CIM_Memory."
    ::= { win32CacheMemoryEntry 29 }

hwcmFlushTimer OBJECT-TYPE
    SYNTAX     Gauge32
    MAX-ACCESS read-only
    STATUS     current
    DESCRIPTION
        "Maximum amount of time, in seconds, dirty lines or
        buckets may remain in the cache before they are
        flushed. A value of 0 indicated that a cache flush
        is not controlled by a flushing timer. This
        property is inherited from CIM_CacheMemory."
    ::= { win32CacheMemoryEntry 30 }

hwcmInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32CacheMemoryEntry 31 }

hwcmInstalledSize OBJECT-TYPE
    SYNTAX     Gauge32
    UNITS "Kilobytes"
    MAX-ACCESS read-only
    STATUS     current
    DESCRIPTION
        "Current size of the installed cache memory."
    ::= { win32CacheMemoryEntry 32 }

hwcmLastErrorCode OBJECT-TYPE
    SYNTAX     Gauge32
    MAX-ACCESS read-only
    STATUS     current
    DESCRIPTION
        "Last error code reported by the logical device.
        This property is inherited from CIM_LogicalDevice."
    ::= { win32CacheMemoryEntry 33 }

hwcmLevel OBJECT-TYPE
    SYNTAX     INTEGER {
        other(1),
        unknown(2),
        primary(3),
        secondary(4),
        tertiary(5),
        notApplicable(6)
    }
    MAX-ACCESS read-only
    STATUS     current
    DESCRIPTION
        "Level of the cache. This property is inherited
        from CIM_CacheMemory."
    ::= { win32CacheMemoryEntry 34 }

hwcmLineSize OBJECT-TYPE
    SYNTAX     Gauge32
    MAX-ACCESS read-only
    STATUS     current
    DESCRIPTION
        "Size, in bytes, of a single cache bucket or line.
        This property is inherited from CIM_CacheMemory."
    ::= { win32CacheMemoryEntry 35 }

hwcmLocation OBJECT-TYPE
    SYNTAX     INTEGER {
        internal(0),
        external(1),
        reserved(2),
        unknown(3)
    }
    MAX-ACCESS read-only
    STATUS     current
    DESCRIPTION
        "Physical location of the cache memory."
    ::= { win32CacheMemoryEntry 36 }

hwcmMaxCacheSize OBJECT-TYPE
    SYNTAX     Gauge32
    UNITS "Kilobytes"
    MAX-ACCESS read-only
    STATUS     current
    DESCRIPTION
        "Maximum cache size installable to this particular
        cache memory."
    ::= { win32CacheMemoryEntry 37 }

hwcmName OBJECT-TYPE
    SYNTAX     DisplayString
    MAX-ACCESS read-only
    STATUS     current
    DESCRIPTION
        "Label by which the object is known. When
        subclassed, the property can be overridden to be a
        key property. This property is inherited from
        CIM_ManagedSystemElement."
    ::= { win32CacheMemoryEntry 38 }

hwcmNumberOfBlocks OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent. This property is inherited from
        CIM_StorageExtent."
    ::= { win32CacheMemoryEntry 39 }

hwcmOtherErrorDescription OBJECT-TYPE
    SYNTAX     DisplayString
    MAX-ACCESS read-only
    STATUS     current
    DESCRIPTION
        "Free-form string providing more information if the
        ErrorType property is set to 1, Other. Otherwise,
        this string has no meaning. This property is
        inherited from CIM_Memory."
    ::= { win32CacheMemoryEntry 40 }

hwcmPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32CacheMemoryEntry 41 }

hwcmPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32CacheMemoryEntry 42 }

hwcmPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32CacheMemoryEntry 43 }

hwcmPurpose OBJECT-TYPE
    SYNTAX     DisplayString
    MAX-ACCESS read-only
    STATUS     current
    DESCRIPTION
        "Free-form string describing the media and/or its
        use. This property is inherited from
        CIM_StorageExtent."
    ::= { win32CacheMemoryEntry 44 }

hwcmReadPolicy OBJECT-TYPE
    SYNTAX     INTEGER {
        other(1),
        unknown(2),
        read(3),
        readAhead(4),
        readAndReadAhead(5),
        determinationPerIO(6)
    }
    MAX-ACCESS read-only
    STATUS     current
    DESCRIPTION
        "Policy that shall be employed by the cache for
        handling read requests. This property is inherited
        from CIM_CacheMemory."
    ::= { win32CacheMemoryEntry 45 }

hwcmReplacementPolicy OBJECT-TYPE
    SYNTAX     INTEGER {
        other(1),
        unknown(2),
        leastRecentlyUsed(3),
        firstInFirstOut(4),
        lastInFirstOut(5),
        leastFrequentlyUsed(6),
        mostFrequentlyUsed(7),
        osDependentAlgorithms(8)
    }
    MAX-ACCESS read-only
    STATUS     current
    DESCRIPTION
        "Algorithm to determine which cache lines or
        buckets should be re-used. This property is
        inherited from CIM_CacheMemory."
    ::= { win32CacheMemoryEntry 46 }

hwcmStartingAddress OBJECT-TYPE
    SYNTAX     Gauge32
    MAX-ACCESS read-only
    STATUS     current
    DESCRIPTION
        "Beginning address, referenced by an application or
        operating system and mapped by a memory controller,
        for this memory object. The starting address is
        specified in kilobytes. This property is inherited
        from CIM_Memory."
    ::= { win32CacheMemoryEntry 47 }

hwcmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32CacheMemoryEntry 48 }

hwcmStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32CacheMemoryEntry 49 }

hwcmSupportedSRAM OBJECT-TYPE
    SYNTAX     DisplayString
    MAX-ACCESS read-only
    STATUS     current
    DESCRIPTION
        "Array of supported types of Static Random Access
        Memory (SRAM) that can be used for the cache
        memory.
        Value Meaning 
        0 Other 
        1 Unknown 
        2 Non-Burst 
        3 Burst 
        4 Pipeline Burst 
        5 Synchronous 
        6 Asynchronous "
    ::= { win32CacheMemoryEntry 50 }

hwcmSystemCreationClassName OBJECT-TYPE
    SYNTAX     DisplayString
    MAX-ACCESS read-only
    STATUS     current
    DESCRIPTION
        "Value of the scoping computer's CreationClassName
        property. This property is inherited from
        CIM_LogicalDevice."
    ::= { win32CacheMemoryEntry 51 }

hwcmSystemLevelAddress OBJECT-TYPE
    SYNTAX     TruthValue
    MAX-ACCESS read-only
    STATUS     current
    DESCRIPTION
        "If TRUE, the address information in the property
        ErrorAddress is a system-level address. If FALSE,
        it is a physical address. If the ErrorInfo property
        is equal to 3, then this property has no meaning.
        This property is inherited from CIM_Memory."
    ::= { win32CacheMemoryEntry 52 }

hwcmSystemName OBJECT-TYPE
    SYNTAX     DisplayString
    MAX-ACCESS read-only
    STATUS     current
    DESCRIPTION
        "Name of the scoping system. This property is
        inherited from CIM_LogicalDevice."
    ::= { win32CacheMemoryEntry 53 }

hwcmWritePolicy OBJECT-TYPE
    SYNTAX     INTEGER {
        other(1),
        unknown(2),
        writeBack(3),
        writeThrough(4),
        variesWithAddress(5),
        determinationPerIO(6)
    }
    MAX-ACCESS read-only
    STATUS     current
    DESCRIPTION
        "Write policy definition. This property is
        inherited from CIM_CacheMemory."
    ::= { win32CacheMemoryEntry 54 }

win32DeviceMemoryAddressTable OBJECT-TYPE
    SYNTAX     SEQUENCE OF Win32DeviceMemoryAddressEntry
    MAX-ACCESS not-accessible
    STATUS     current
    DESCRIPTION
        "The Win32_DeviceMemoryAddress WMI class represents
        a device memory address on a Windows system."
    ::= { wmiMotherboardControllerPort 6 }

win32DeviceMemoryAddressEntry OBJECT-TYPE
    SYNTAX     Win32DeviceMemoryAddressEntry
    MAX-ACCESS not-accessible
    STATUS     current
    DESCRIPTION
        "None"
    INDEX      { hwdaIndex }
    ::= { win32DeviceMemoryAddressTable 1 }

Win32DeviceMemoryAddressEntry ::= SEQUENCE {
    hwdaIndex Integer32,
    hwdaCaption DisplayString,
    hwdaCreationClassName DisplayString,
    hwdaCSCreationClassName DisplayString,
    hwdaCSName DisplayString,
    hwdaDescription DisplayString,
    hwdaEndingAddress Gauge32,
    hwdaInstallDate DateAndTime,
    hwdaMemoryType INTEGER,
    hwdaName DisplayString,
    hwdaStartingAddress Gauge32,
    hwdaStatus INTEGER
}

hwdaIndex OBJECT-TYPE
    SYNTAX     Integer32 (1..2147483647)
    MAX-ACCESS read-only
    STATUS     current
    DESCRIPTION
        "The value of this object uniquely identifies the
        instance entry for this class."
    ::= { win32DeviceMemoryAddressEntry 1 }

hwdaCaption OBJECT-TYPE
    SYNTAX     DisplayString
    MAX-ACCESS read-only
    STATUS     current
    DESCRIPTION
        "Short description of the object a one-line string.
        This property is inherited from
        CIM_ManagedSystemElement."
    ::= { win32DeviceMemoryAddressEntry 2 }

hwdaCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_MemoryMappedIO."
    ::= { win32DeviceMemoryAddressEntry 3 }

hwdaCSCreationClassName OBJECT-TYPE
    SYNTAX     DisplayString
    MAX-ACCESS read-only
    STATUS     current
    DESCRIPTION
        "Name of the scoping computer system creation
        class. This property is inherited from
        CIM_MemoryMappedIO."
    ::= { win32DeviceMemoryAddressEntry 4 }

hwdaCSName OBJECT-TYPE
    SYNTAX     DisplayString
    MAX-ACCESS read-only
    STATUS     current
    DESCRIPTION
        "Name of the scoping computer system. This property
        is inherited from CIM_MemoryMappedIO."
    ::= { win32DeviceMemoryAddressEntry 5 }

hwdaDescription OBJECT-TYPE
    SYNTAX     DisplayString
    MAX-ACCESS read-only
    STATUS     current
    DESCRIPTION
        "Description of the object. This property is
        inherited from CIM_ManagedSystemElement."
    ::= { win32DeviceMemoryAddressEntry 6 }

hwdaEndingAddress OBJECT-TYPE
    SYNTAX     Gauge32
    MAX-ACCESS read-only
    STATUS     current
    DESCRIPTION
        "Ending address of memory-mapped I/O. This property
        is inherited from CIM_MemoryMappedIO."
    ::= { win32DeviceMemoryAddressEntry 7 }

hwdaInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32DeviceMemoryAddressEntry 8 }

hwdaMemoryType OBJECT-TYPE
    SYNTAX     INTEGER {
        readWrite(1),
        readOnly(2),
        writeOnly(3),
        prefetchable(4)
    }
    MAX-ACCESS read-only
    STATUS     current
    DESCRIPTION
        "Characteristics of the memory resource on the
        Windows system."
    ::= { win32DeviceMemoryAddressEntry 9 }

hwdaName OBJECT-TYPE
    SYNTAX     DisplayString
    MAX-ACCESS read-only
    STATUS     current
    DESCRIPTION
        "Label by which the object is known. When
        subclassed, the property can be overridden to be a
        key property. This property is inherited from
        CIM_ManagedSystemElement."
    ::= { win32DeviceMemoryAddressEntry 10 }

hwdaStartingAddress OBJECT-TYPE
    SYNTAX     Gauge32
    MAX-ACCESS read-only
    STATUS     current
    DESCRIPTION
        "Starting address of memory-mapped I/O. The
        hardware resource identifier property should be set
        to this value to construct the mapped I/O resource
        key. This property is inherited from
        CIM_MemoryMappedIO."
    ::= { win32DeviceMemoryAddressEntry 11 }

hwdaStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32DeviceMemoryAddressEntry 12 }

win32DMAChannelTable OBJECT-TYPE
    SYNTAX     SEQUENCE OF Win32DMAChannelEntry
    MAX-ACCESS not-accessible
    STATUS     current
    DESCRIPTION
        "The Win32_DMAChannel WMI class represents a direct
        memory access (DMA) channel on a Windows computer
        system. DMA is a method of moving data from a
        device to memory (or vice versa) without the help
        of the microprocessor. The system board uses a DMA
        controller to handle a fixed number of channels,
        each of which can be used by one (and only one)
        device at a time."
    ::= { wmiMotherboardControllerPort 7 }

win32DMAChannelEntry OBJECT-TYPE
    SYNTAX     Win32DMAChannelEntry
    MAX-ACCESS not-accessible
    STATUS     current
    DESCRIPTION
        "None"
    INDEX      { hwdmaIndex }
    ::= { win32DMAChannelTable 1 }

Win32DMAChannelEntry ::= SEQUENCE {
    hwdmaIndex Integer32,
    hwdmaAddressSize Integer32,
    hwdmaAvailability INTEGER,
    hwdmaBurstMode TruthValue,
    hwdmaByteMode INTEGER,
    hwdmaCaption DisplayString,
    hwdmaChannelTiming INTEGER,
    hwdmaCreationClassName DisplayString,
    hwdmaCSCreationClassName DisplayString,
    hwdmaCSName DisplayString,
    hwdmaDescription DisplayString,
    hwdmaDMAChannel Gauge32,
    hwdmaInstallDate DateAndTime,
    hwdmaMaxTransferSize Gauge32,
    hwdmaName DisplayString,
    hwdmaPort Gauge32,
    hwdmaStatus INTEGER,
    hwdmaTransferWidths DisplayString,
    hwdmaTypeCTiming INTEGER,
    hwdmaWordMode INTEGER
}

hwdmaIndex OBJECT-TYPE
    SYNTAX     Integer32 (1..2147483647)
    MAX-ACCESS read-only
    STATUS     current
    DESCRIPTION
        "The value of this object uniquely identifies the
        instance entry for this class."
    ::= { win32DMAChannelEntry 1 }

hwdmaAddressSize OBJECT-TYPE
    SYNTAX     Integer32
    MAX-ACCESS read-only
    STATUS     current
    DESCRIPTION
        "DMA channel address size in bits. Permissible
        values are 8, 16, 32 or 64 bits. If unknown, enter
        0 (zero). This property is inherited from CIM_DMA."
    ::= { win32DMAChannelEntry 2 }

hwdmaAvailability OBJECT-TYPE
    SYNTAX     INTEGER {
        other(1),
        unknown(2),
        available(3),
        inUseNotAvailable(4),
        inUseAndAvailableShareable(5)
    }
    MAX-ACCESS read-only
    STATUS     current
    DESCRIPTION
        "Availability of the DMA. This property is
        inherited from CIM_DMA."
    ::= { win32DMAChannelEntry 3 }

hwdmaBurstMode OBJECT-TYPE
    SYNTAX     TruthValue
    MAX-ACCESS read-only
    STATUS     current
    DESCRIPTION
        "Indicates whether or not the DMA channel supports
        burst mode. This property is inherited from
        CIM_DMA."
    ::= { win32DMAChannelEntry 4 }

hwdmaByteMode OBJECT-TYPE
    SYNTAX     INTEGER {
        other(1),
        unknown(2),
        doesNotExecuteIncountByByteMode(3),
        executeIncountByByteMode(4)
    }
    MAX-ACCESS read-only
    STATUS     current
    DESCRIPTION
        "DMA execution mode. This property is inherited
        from CIM_DMA."
    ::= { win32DMAChannelEntry 5 }

hwdmaCaption OBJECT-TYPE
    SYNTAX     DisplayString
    MAX-ACCESS read-only
    STATUS     current
    DESCRIPTION
        "Short description of the object a one-line string.
        This property is inherited from
        CIM_ManagedSystemElement."
    ::= { win32DMAChannelEntry 6 }

hwdmaChannelTiming OBJECT-TYPE
    SYNTAX     INTEGER {
        other(1),
        unknown(2),
        isaCompatible(3),
        typeA(4),
        typeB(5),
        typeF(6)
    }
    MAX-ACCESS read-only
    STATUS     current
    DESCRIPTION
        "DMA channel timing. This property is inherited
        from CIM_DMA."
    ::= { win32DMAChannelEntry 7 }

hwdmaCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_DMA."
    ::= { win32DMAChannelEntry 8 }

hwdmaCSCreationClassName OBJECT-TYPE
    SYNTAX     DisplayString
    MAX-ACCESS read-only
    STATUS     current
    DESCRIPTION
        "Name of the scoping computer system creation
        class. This property is inherited from CIM_DMA."
    ::= { win32DMAChannelEntry 9 }

hwdmaCSName OBJECT-TYPE
    SYNTAX     DisplayString
    MAX-ACCESS read-only
    STATUS     current
    DESCRIPTION
        "Name of the scoping computer system. This property
        is inherited from CIM_DMA."
    ::= { win32DMAChannelEntry 10 }

hwdmaDescription OBJECT-TYPE
    SYNTAX     DisplayString
    MAX-ACCESS read-only
    STATUS     current
    DESCRIPTION
        "Description of the object. This property is
        inherited from CIM_ManagedSystemElement."
    ::= { win32DMAChannelEntry 11 }

hwdmaDMAChannel OBJECT-TYPE
    SYNTAX     Gauge32
    MAX-ACCESS read-only
    STATUS     current
    DESCRIPTION
        "DMA channel number, part of the object's key
        value. This property is inherited from CIM_DMA."
    ::= { win32DMAChannelEntry 12 }

hwdmaInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32DMAChannelEntry 13 }

hwdmaMaxTransferSize OBJECT-TYPE
    SYNTAX     Gauge32
    MAX-ACCESS read-only
    STATUS     current
    DESCRIPTION
        "Maximum number of bytes that can be transferred by
        this DMA channel. If unknown, enter 0 (zero). This
        property is inherited from CIM_DMA."
    ::= { win32DMAChannelEntry 14 }

hwdmaName OBJECT-TYPE
    SYNTAX     DisplayString
    MAX-ACCESS read-only
    STATUS     current
    DESCRIPTION
        "Label by which the object is known. When
        subclassed, the property can be overridden to be a
        key property. This property is inherited from
        CIM_ManagedSystemElement."
    ::= { win32DMAChannelEntry 15 }

hwdmaPort OBJECT-TYPE
    SYNTAX     Gauge32
    MAX-ACCESS read-only
    STATUS     current
    DESCRIPTION
        "DMA port used by the host bus adapter. This is
        meaningful for MCA-type buses.
        Example: 12"
    ::= { win32DMAChannelEntry 16 }

hwdmaStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32DMAChannelEntry 17 }

hwdmaTransferWidths OBJECT-TYPE
    SYNTAX     DisplayString
    MAX-ACCESS read-only
    STATUS     current
    DESCRIPTION
        "Array of all the transfer widths (in bits)
        supported by this DMA channel. If unknown, enter 0
        (zero). This property is inherited from CIM_DMA."
    ::= { win32DMAChannelEntry 18 }

hwdmaTypeCTiming OBJECT-TYPE
    SYNTAX     INTEGER {
        other(1),
        unknown(2),
        isaCompatible(3),
        notSupported(4),
        supported(5)
    }
    MAX-ACCESS read-only
    STATUS     current
    DESCRIPTION
        "Support for C type (burst) timing. This property
        is inherited from CIM_DMA."
    ::= { win32DMAChannelEntry 19 }

hwdmaWordMode OBJECT-TYPE
    SYNTAX     INTEGER {
        other(1),
        unknown(2),
        doesNotExecuteIncountByWordMode(3),
        executeIncountByWordMode(4)
    }
    MAX-ACCESS read-only
    STATUS     current
    DESCRIPTION
        "DMA execution mode. This property is inherited
        from CIM_DMA."
    ::= { win32DMAChannelEntry 20 }

win32FloppyControllerTable OBJECT-TYPE
    SYNTAX     SEQUENCE OF Win32FloppyControllerEntry
    MAX-ACCESS not-accessible
    STATUS     current
    DESCRIPTION
        "The Win32_FloppyController WMI class represents
        the capabilities and management capacity of a
        floppy disk drive controller."
    ::= { wmiMotherboardControllerPort 8 }

win32FloppyControllerEntry OBJECT-TYPE
    SYNTAX     Win32FloppyControllerEntry
    MAX-ACCESS not-accessible
    STATUS     current
    DESCRIPTION
        "None"
    INDEX      { hwfcIndex }
    ::= { win32FloppyControllerTable 1 }

Win32FloppyControllerEntry ::= SEQUENCE {
    hwfcIndex Integer32,
    hwfcAvailability INTEGER,
    hwfcCaption DisplayString,
    hwfcConfigManagerErrorCode INTEGER,
    hwfcConfigManagerUserConfig TruthValue,
    hwfcCreationClassName DisplayString,
    hwfcDescription DisplayString,
    hwfcDeviceID DisplayString,
    hwfcErrorCleared TruthValue,
    hwfcErrorDescription DisplayString,
    hwfcInstallDate DateAndTime,
    hwfcLastErrorCode Gauge32,
    hwfcManufacturer DisplayString,
    hwfcMaxNumberControlled Gauge32,
    hwfcName DisplayString,
    hwfcPNPDeviceID DisplayString,
    hwfcPowerManagementCapabilities DisplayString,
    hwfcPowerManagementSupported TruthValue,
    hwfcProtocolSupported INTEGER,
    hwfcStatus INTEGER,
    hwfcStatusInfo INTEGER,
    hwfcSystemCreationClassName DisplayString,
    hwfcSystemName DisplayString,
    hwfcTimeOfLastReset DateAndTime
}

hwfcIndex OBJECT-TYPE
    SYNTAX     Integer32 (1..2147483647)
    MAX-ACCESS read-only
    STATUS     current
    DESCRIPTION
        "The value of this object uniquely identifies the
        instance entry for this class."
    ::= { win32FloppyControllerEntry 1 }

hwfcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32FloppyControllerEntry 2 }

hwfcCaption OBJECT-TYPE
    SYNTAX     DisplayString
    MAX-ACCESS read-only
    STATUS     current
    DESCRIPTION
        "Short description of the object a one-line string.
        This property is inherited from
        CIM_ManagedSystemElement."
    ::= { win32FloppyControllerEntry 3 }

hwfcConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32FloppyControllerEntry 4 }

hwfcConfigManagerUserConfig OBJECT-TYPE
    SYNTAX     TruthValue
    MAX-ACCESS read-only
    STATUS     current
    DESCRIPTION
        "If TRUE, the device is using a user-defined
        configuration. This property is inherited from
        CIM_LogicalDevice."
    ::= { win32FloppyControllerEntry 5 }

hwfcCreationClassName OBJECT-TYPE
    SYNTAX     DisplayString
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32FloppyControllerEntry 6 }

hwfcDescription OBJECT-TYPE
    SYNTAX     DisplayString
    MAX-ACCESS read-only
    STATUS     current
    DESCRIPTION
        "Description of the object. This property is
        inherited from CIM_ManagedSystemElement."
    ::= { win32FloppyControllerEntry 7 }

hwfcDeviceID OBJECT-TYPE
    SYNTAX     DisplayString
    MAX-ACCESS read-only
    STATUS     current
    DESCRIPTION
        "Unique identifier of the floppy controller. This
        property is inherited from CIM_LogicalDevice."
    ::= { win32FloppyControllerEntry 8 }

hwfcErrorCleared OBJECT-TYPE
    SYNTAX     TruthValue
    MAX-ACCESS read-only
    STATUS     current
    DESCRIPTION
        "If TRUE, the error reported in LastErrorCode is
        now cleared. This property is inherited from
        CIM_LogicalDevice."
    ::= { win32FloppyControllerEntry 9 }

hwfcErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32FloppyControllerEntry 10 }

hwfcInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32FloppyControllerEntry 11 }

hwfcLastErrorCode OBJECT-TYPE
    SYNTAX     Gauge32
    MAX-ACCESS read-only
    STATUS     current
    DESCRIPTION
        "Last error code reported by the logical device.
        This property is inherited from CIM_LogicalDevice."
    ::= { win32FloppyControllerEntry 12 }

hwfcManufacturer OBJECT-TYPE
    SYNTAX     DisplayString
    MAX-ACCESS read-only
    STATUS     current
    DESCRIPTION
        "Name of the floppy controller manufacturer.
        Example: 'Microsoft'"
    ::= { win32FloppyControllerEntry 13 }

hwfcMaxNumberControlled OBJECT-TYPE
    SYNTAX     Gauge32
    MAX-ACCESS read-only
    STATUS     current
    DESCRIPTION
        "Maximum number of directly addressable entities
        that this controller supports. A value of 0 (zero)
        should be used if the number is unknown. This
        property is inherited from CIM_Controller."
    ::= { win32FloppyControllerEntry 14 }

hwfcName OBJECT-TYPE
    SYNTAX     DisplayString
    MAX-ACCESS read-only
    STATUS     current
    DESCRIPTION
        "Label for the object. When subclassed, the
        property can be overridden to be a key property.
        This property is inherited from
        CIM_ManagedSystemElement."
    ::= { win32FloppyControllerEntry 15 }

hwfcPNPDeviceID OBJECT-TYPE
    SYNTAX     DisplayString
    MAX-ACCESS read-only
    STATUS     current
    DESCRIPTION
        "Windows Plug and Play device identifier for the
        logical device. This property is inherited from
        CIM_LogicalDevice.
        Example: '*PNP030b'"
    ::= { win32FloppyControllerEntry 16 }

hwfcPowerManagementCapabilities OBJECT-TYPE
    SYNTAX     DisplayString
    MAX-ACCESS read-only
    STATUS     current
    DESCRIPTION
        "Array of the specific power-related capabilities
        of a logical device. The Enabled value indicates
        that the power management features are currently
        enabled, but the exact feature set is unknown or
        the information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32FloppyControllerEntry 17 }

hwfcPowerManagementSupported OBJECT-TYPE
    SYNTAX     TruthValue
    MAX-ACCESS read-only
    STATUS     current
    DESCRIPTION
        "If TRUE, the device can be power-managed, which
        means that it can be put into suspend mode, and so
        on. The property does not indicate that power
        management features are currently enabled, only
        that the logical device is capable of power
        management. This property is inherited from
        CIM_LogicalDevice."
    ::= { win32FloppyControllerEntry 18 }

hwfcProtocolSupported OBJECT-TYPE
    SYNTAX     INTEGER {
        other(1),
        unknown(2),
        eisa(3),
        isa(4),
        pci(5),
        ataATAPI(6),
        flexibleDiskette(7),
        n1496(8),
        scsiParallelInterface(9),
        scsiFibreChannelProtocol(10),
        scsiSerialBusProtocol(11),
        scsiSerialBusProtocol2(12),
        scsiSerialStorageArchitecture(13),
        vesa(14),
        pcmcia(15),
        universalSerialBus(16),
        parallelProtocol(17),
        escon(18),
        diagnostic(19),
        i2C(20),
        power(21),
        hippi(22),
        multiBus(23),
        vme(24),
        ipi(25),
        ieee488(26),
        rs232(27),
        ieee802310BASE5(28),
        ieee802310BASE2(29),
        ieee80231BASES(30),
        ieee802310BROAD36(31),
        ieee8023100BASEVG(32),
        ieee8025TokenRing(33),
        ansiX3T95FDDI(34),
        mca(35),
        esdi(36),
        ide(37),
        cmd(38),
        st506(39),
        dssi(40),
        qic2(41),
        enhancedATAIDE(42),
        agp(43),
        twowayInfrared(44),
        fastInfrared(45),
        serialInfrared(46),
        irBus(47)
    }
    MAX-ACCESS read-only
    STATUS     current
    DESCRIPTION
        "Protocol that the controller uses to access
        controlled devices. This property is inherited from
        CIM_Controller."
    ::= { win32FloppyControllerEntry 19 }

hwfcStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32FloppyControllerEntry 20 }

hwfcStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32FloppyControllerEntry 21 }

hwfcSystemCreationClassName OBJECT-TYPE
    SYNTAX     DisplayString
    MAX-ACCESS read-only
    STATUS     current
    DESCRIPTION
        "Value of the scoping computer's CreationClassName
        property. This property is inherited from
        CIM_LogicalDevice."
    ::= { win32FloppyControllerEntry 22 }

hwfcSystemName OBJECT-TYPE
    SYNTAX     DisplayString
    MAX-ACCESS read-only
    STATUS     current
    DESCRIPTION
        "Name of the scoping system. This property is
        inherited from CIM_LogicalDevice."
    ::= { win32FloppyControllerEntry 23 }

hwfcTimeOfLastReset OBJECT-TYPE
    SYNTAX     DateAndTime
    MAX-ACCESS read-only
    STATUS     current
    DESCRIPTION
        "Date and time the controller was last reset. This
        could mean the controller was powered down or
        reinitialized. This property is inherited from
        CIM_Controller."
    ::= { win32FloppyControllerEntry 24 }

win32IDEControllerTable OBJECT-TYPE
    SYNTAX     SEQUENCE OF Win32IDEControllerEntry
    MAX-ACCESS not-accessible
    STATUS     current
    DESCRIPTION
        "The Win32_IDEController  WMI class manages the
        capabilities of an integrated device electronics
        (IDE) controller device."
    ::= { wmiMotherboardControllerPort 9 }

win32IDEControllerEntry OBJECT-TYPE
    SYNTAX     Win32IDEControllerEntry
    MAX-ACCESS not-accessible
    STATUS     current
    DESCRIPTION
        "None"
    INDEX      { hwideIndex }
    ::= { win32IDEControllerTable 1 }

Win32IDEControllerEntry ::= SEQUENCE {
    hwideIndex Integer32,
    hwideAvailability INTEGER,
    hwideCaption DisplayString,
    hwideConfigManagerErrorCode INTEGER,
    hwideConfigManagerUserConfig TruthValue,
    hwideCreationClassName DisplayString,
    hwideDescription DisplayString,
    hwideDeviceID DisplayString,
    hwideErrorCleared TruthValue,
    hwideErrorDescription DisplayString,
    hwideInstallDate DateAndTime,
    hwideLastErrorCode Gauge32,
    hwideManufacturer DisplayString,
    hwideMaxNumberControlled Gauge32,
    hwideName DisplayString,
    hwidePNPDeviceID DisplayString,
    hwidePowerManagementCapabilities DisplayString,
    hwidePowerManagementSupported TruthValue,
    hwideProtocolSupported INTEGER,
    hwideStatus INTEGER,
    hwideStatusInfo INTEGER,
    hwideSystemCreationClassName DisplayString,
    hwideSystemName DisplayString,
    hwideTimeOfLastReset DateAndTime
}

hwideIndex OBJECT-TYPE
    SYNTAX     Integer32 (1..2147483647)
    MAX-ACCESS read-only
    STATUS     current
    DESCRIPTION
        "The value of this object uniquely identifies the
        instance entry for this class."
    ::= { win32IDEControllerEntry 1 }

hwideAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32IDEControllerEntry 2 }

hwideCaption OBJECT-TYPE
    SYNTAX     DisplayString
    MAX-ACCESS read-only
    STATUS     current
    DESCRIPTION
        "Short description of the object a one-line string.
        This property is inherited from
        CIM_ManagedSystemElement."
    ::= { win32IDEControllerEntry 3 }

hwideConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32IDEControllerEntry 4 }

hwideConfigManagerUserConfig OBJECT-TYPE
    SYNTAX     TruthValue
    MAX-ACCESS read-only
    STATUS     current
    DESCRIPTION
        "If TRUE, the device is using a user-defined
        configuration. This property is inherited from
        CIM_LogicalDevice."
    ::= { win32IDEControllerEntry 5 }

hwideCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32IDEControllerEntry 6 }

hwideDescription OBJECT-TYPE
    SYNTAX     DisplayString
    MAX-ACCESS read-only
    STATUS     current
    DESCRIPTION
        "Description of the object. This property is
        inherited from CIM_ManagedSystemElement."
    ::= { win32IDEControllerEntry 7 }

hwideDeviceID OBJECT-TYPE
    SYNTAX     DisplayString
    MAX-ACCESS read-only
    STATUS     current
    DESCRIPTION
        "Unique identifier of the IDE controller with other
        devices on the system. This property is inherited
        from CIM_LogicalDevice. "
    ::= { win32IDEControllerEntry 8 }

hwideErrorCleared OBJECT-TYPE
    SYNTAX     TruthValue
    MAX-ACCESS read-only
    STATUS     current
    DESCRIPTION
        "If TRUE, the error reported in LastErrorCode is
        now cleared. This property is inherited from
        CIM_LogicalDevice."
    ::= { win32IDEControllerEntry 9 }

hwideErrorDescription OBJECT-TYPE
    SYNTAX     DisplayString
    MAX-ACCESS read-only
    STATUS     current
    DESCRIPTION
        "More information about the error recorded in
        LastErrorCode property, and information about any
        corrective actions that may be taken. This property
        is inherited from CIM_LogicalDevice. "
    ::= { win32IDEControllerEntry 10 }

hwideInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32IDEControllerEntry 11 }

hwideLastErrorCode OBJECT-TYPE
    SYNTAX     Gauge32
    MAX-ACCESS read-only
    STATUS     current
    DESCRIPTION
        "Last error code reported by the logical device.
        This property is inherited from CIM_LogicalDevice."
    ::= { win32IDEControllerEntry 12 }

hwideManufacturer OBJECT-TYPE
    SYNTAX     DisplayString
    MAX-ACCESS read-only
    STATUS     current
    DESCRIPTION
        "Manufacturer of the IDE controller device. "
    ::= { win32IDEControllerEntry 13 }

hwideMaxNumberControlled OBJECT-TYPE
    SYNTAX     Gauge32
    MAX-ACCESS read-only
    STATUS     current
    DESCRIPTION
        "Maximum number of directly addressable entities
        supportable by this controller. A value of 0 (zero)
        should be used if the number is unknown. This
        property is inherited from CIM_Controller. "
    ::= { win32IDEControllerEntry 14 }

hwideName OBJECT-TYPE
    SYNTAX     DisplayString
    MAX-ACCESS read-only
    STATUS     current
    DESCRIPTION
        "Label by which the object is known. When
        subclassed, the property can be overridden to be a
        key property. This property is inherited from
        CIM_ManagedSystemElement."
    ::= { win32IDEControllerEntry 15 }

hwidePNPDeviceID OBJECT-TYPE
    SYNTAX     DisplayString
    MAX-ACCESS read-only
    STATUS     current
    DESCRIPTION
        "Windows plug and play device ID of the logical
        device. This property is inherited from
        CIM_LogicalDevice.
        Example: *PNP030b"
    ::= { win32IDEControllerEntry 16 }

hwidePowerManagementCapabilities OBJECT-TYPE
    SYNTAX     DisplayString
    MAX-ACCESS read-only
    STATUS     current
    DESCRIPTION
        "Array of the specific power-related capabilities
        of a logical device. The Enabled value indicates
        that the power management features are currently
        enabled, but the exact feature set is unknown or
        the information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle),
        and Time set to a specific date and time or
        interval for power-on. This property is inherited
        from CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32IDEControllerEntry 17 }

hwidePowerManagementSupported OBJECT-TYPE
    SYNTAX     TruthValue
    MAX-ACCESS read-only
    STATUS     current
    DESCRIPTION
        "If TRUE, the device can be power-managed put into
        suspend mode, and so on. The property does not
        indicate that power management features are
        currently enabled, only that the logical device is
        capable of power management. This property is
        inherited from CIM_LogicalDevice."
    ::= { win32IDEControllerEntry 18 }

hwideProtocolSupported OBJECT-TYPE
    SYNTAX     INTEGER {
        other(1),
        unknown(2),
        eisa(3),
        isa(4),
        pci(5),
        ataATAPI(6),
        flexibleDiskette(7),
        n1496(8),
        scsiParallelInterface(9),
        scsiFibreChannelProtocol(10),
        scsiSerialBusProtocol(11),
        scsiSerialBusProtocol1394(12),
        scsiSerialStorageArchitecture(13),
        vesa(14),
        pcmcia(15),
        universalSerialBus(16),
        parallelProtocol(17),
        escon(18),
        diagnostic(19),
        i2C(20),
        power(21),
        hippi(22),
        multiBus(23),
        vme(24),
        ipi(25),
        ieee488(26),
        rs232(27),
        ieee802310BASE5(28),
        ieee802310BASE2(29),
        ieee80231BASE5(30),
        ieee802310BROAD36(31),
        ieee8023100BASEVG(32),
        ieee8025TokenRing(33),
        ansiX3T95FDDI(34),
        mca(35),
        esdi(36),
        ide(37),
        cmd(38),
        st506(39),
        dssi(40),
        qic2(41),
        enhancedATAIDE(42),
        agp(43),
        twowayInfrared(44),
        fastInfrared(45),
        serialInfrared(46),
        irBus(47)
    }
    MAX-ACCESS read-only
    STATUS     current
    DESCRIPTION
        "Protocol used by the controller to access
        controlled devices. This property is inherited from
        CIM_Controller."
    ::= { win32IDEControllerEntry 19 }

hwideStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32IDEControllerEntry 20 }

hwideStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32IDEControllerEntry 21 }

hwideSystemCreationClassName OBJECT-TYPE
    SYNTAX     DisplayString
    MAX-ACCESS read-only
    STATUS     current
    DESCRIPTION
        "Value for the scoping computer's CreationClassName
        property. This property is inherited from
        CIM_LogicalDevice."
    ::= { win32IDEControllerEntry 22 }

hwideSystemName OBJECT-TYPE
    SYNTAX     DisplayString
    MAX-ACCESS read-only
    STATUS     current
    DESCRIPTION
        "Name of the scoping system. This property is
        inherited from CIM_LogicalDevice."
    ::= { win32IDEControllerEntry 23 }

hwideTimeOfLastReset OBJECT-TYPE
    SYNTAX     DateAndTime
    MAX-ACCESS read-only
    STATUS     current
    DESCRIPTION
        "Date and time this controller was last reset. This
        could mean the controller was powered down or
        reinitialized. This property is inherited from
        CIM_Controller."
    ::= { win32IDEControllerEntry 24 }

win32InfraredDeviceTable OBJECT-TYPE
    SYNTAX     SEQUENCE OF Win32InfraredDeviceEntry
    MAX-ACCESS not-accessible
    STATUS     current
    DESCRIPTION
        "The Win32_InfraredDevice WMI class represents the
        capabilities and management of an infrared device."
    ::= { wmiMotherboardControllerPort 10 }

win32InfraredDeviceEntry OBJECT-TYPE
    SYNTAX     Win32InfraredDeviceEntry
    MAX-ACCESS not-accessible
    STATUS     current
    DESCRIPTION
        "None"
    INDEX      { hwidIndex }
    ::= { win32InfraredDeviceTable 1 }

Win32InfraredDeviceEntry ::= SEQUENCE {
    hwidIndex Integer32,
    hwidAvailability INTEGER,
    hwidCaption DisplayString,
    hwidConfigManagerErrorCode INTEGER,
    hwidConfigManagerUserConfig TruthValue,
    hwidCreationClassName DisplayString,
    hwidDescription DisplayString,
    hwidDeviceID DisplayString,
    hwidErrorCleared TruthValue,
    hwidErrorDescription DisplayString,
    hwidInstallDate DateAndTime,
    hwidLastErrorCode Gauge32,
    hwidManufacturer DisplayString,
    hwidMaxNumberControlled Gauge32,
    hwidName DisplayString,
    hwidPNPDeviceID DisplayString,
    hwidPowerManagementCapabilities DisplayString,
    hwidPowerManagementSupported TruthValue,
    hwidProtocolSupported INTEGER,
    hwidStatus INTEGER,
    hwidStatusInfo INTEGER,
    hwidSystemCreationClassName DisplayString,
    hwidSystemName DisplayString,
    hwidTimeOfLastReset DateAndTime
}

hwidIndex OBJECT-TYPE
    SYNTAX     Integer32 (1..2147483647)
    MAX-ACCESS read-only
    STATUS     current
    DESCRIPTION
        "The value of this object uniquely identifies the
        instance entry for this class."
    ::= { win32InfraredDeviceEntry 1 }

hwidAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32InfraredDeviceEntry 2 }

hwidCaption OBJECT-TYPE
    SYNTAX     DisplayString
    MAX-ACCESS read-only
    STATUS     current
    DESCRIPTION
        "Short description of the object a one-line string.
        This property is inherited from
        CIM_ManagedSystemElement."
    ::= { win32InfraredDeviceEntry 3 }

hwidConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32InfraredDeviceEntry 4 }

hwidConfigManagerUserConfig OBJECT-TYPE
    SYNTAX     TruthValue
    MAX-ACCESS read-only
    STATUS     current
    DESCRIPTION
        "If TRUE, the device is using a user-defined
        configuration. This property is inherited from
        CIM_LogicalDevice."
    ::= { win32InfraredDeviceEntry 5 }

hwidCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32InfraredDeviceEntry 6 }

hwidDescription OBJECT-TYPE
    SYNTAX     DisplayString
    MAX-ACCESS read-only
    STATUS     current
    DESCRIPTION
        "Description of the object. This property is
        inherited from CIM_ManagedSystemElement."
    ::= { win32InfraredDeviceEntry 7 }

hwidDeviceID OBJECT-TYPE
    SYNTAX     DisplayString
    MAX-ACCESS read-only
    STATUS     current
    DESCRIPTION
        "Unique identifier of the infrared device. This
        property is inherited from CIM_LogicalDevice."
    ::= { win32InfraredDeviceEntry 8 }

hwidErrorCleared OBJECT-TYPE
    SYNTAX     TruthValue
    MAX-ACCESS read-only
    STATUS     current
    DESCRIPTION
        "If TRUE, the error reported in LastErrorCode is
        now cleared. This property is inherited from
        CIM_LogicalDevice."
    ::= { win32InfraredDeviceEntry 9 }

hwidErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32InfraredDeviceEntry 10 }

hwidInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32InfraredDeviceEntry 11 }

hwidLastErrorCode OBJECT-TYPE
    SYNTAX     Gauge32
    MAX-ACCESS read-only
    STATUS     current
    DESCRIPTION
        "Last error code reported by the logical device.
        This property is inherited from CIM_LogicalDevice."
    ::= { win32InfraredDeviceEntry 12 }

hwidManufacturer OBJECT-TYPE
    SYNTAX     DisplayString
    MAX-ACCESS read-only
    STATUS     current
    DESCRIPTION
        "Manufacturer of the device."
    ::= { win32InfraredDeviceEntry 13 }

hwidMaxNumberControlled OBJECT-TYPE
    SYNTAX     Gauge32
    MAX-ACCESS read-only
    STATUS     current
    DESCRIPTION
        "Maximum number of directly addressable entities
        supportable by this device. A value of 0 (zero)
        should be used if the number is unknown. This
        property is inherited from CIM_Controller."
    ::= { win32InfraredDeviceEntry 14 }

hwidName OBJECT-TYPE
    SYNTAX     DisplayString
    MAX-ACCESS read-only
    STATUS     current
    DESCRIPTION
        "Label by which the object is known. When
        subclassed, the property can be overridden to be a
        key property. This property is inherited from
        CIM_ManagedSystemElement."
    ::= { win32InfraredDeviceEntry 15 }

hwidPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32InfraredDeviceEntry 16 }

hwidPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32InfraredDeviceEntry 17 }

hwidPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32InfraredDeviceEntry 18 }

hwidProtocolSupported OBJECT-TYPE
    SYNTAX     INTEGER {
        other(1),
        unknown(2),
        eisa(3),
        isa(4),
        pci(5),
        ataATAPI(6),
        flexibleDiskette(7),
        n1496(8),
        scsiParallelInterface(9),
        scsiFibreChannelProtocol(10),
        scsiSerialBusProtocol(11),
        scsiSerialBusProtocol1394(12),
        scsiSerialStorageArchitecture(13),
        vesa(14),
        pcmcia(15),
        universalSerialBus(16),
        parallelProtocol(17),
        escon(18),
        diagnostic(19),
        i2C(20),
        power(21),
        hippi(22),
        multiBus(23),
        vme(24),
        ipi(25),
        ieee488(26),
        rs232(27),
        ieee802310BASE5(28),
        ieee802310BASE2(29),
        ieee80231BASE5(30),
        ieee802310BROAD36(31),
        ieee8023100BASEVG(32),
        ieee8025TokenRing(33),
        ansiX3T95FDDI(34),
        mca(35),
        esdi(36),
        ide(37),
        cmd(38),
        st506(39),
        dssi(40),
        qic2(41),
        enhancedATAIDE(42),
        agp(43),
        twowayInfrared(44),
        fastInfrared(45),
        serialInfrared(46),
        irBus(47)
    }
    MAX-ACCESS read-only
    STATUS     current
    DESCRIPTION
        "Protocol used by the controller to access
        controlled devices. This property is inherited from
        CIM_Controller."
    ::= { win32InfraredDeviceEntry 19 }

hwidStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32InfraredDeviceEntry 20 }

hwidStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32InfraredDeviceEntry 21 }

hwidSystemCreationClassName OBJECT-TYPE
    SYNTAX     DisplayString
    MAX-ACCESS read-only
    STATUS     current
    DESCRIPTION
        "Value for the scoping computer's CreationClassName
        property. This property is inherited from
        CIM_LogicalDevice."
    ::= { win32InfraredDeviceEntry 22 }

hwidSystemName OBJECT-TYPE
    SYNTAX     DisplayString
    MAX-ACCESS read-only
    STATUS     current
    DESCRIPTION
        "Name of the scoping system. This property is
        inherited from CIM_LogicalDevice."
    ::= { win32InfraredDeviceEntry 23 }

hwidTimeOfLastReset OBJECT-TYPE
    SYNTAX     DateAndTime
    MAX-ACCESS read-only
    STATUS     current
    DESCRIPTION
        "Date and time the controller was last reset. This
        could mean the controller was powered down, or
        reinitialized. This property is inherited from
        CIM_Controller."
    ::= { win32InfraredDeviceEntry 24 }

win32IRQResourceTable OBJECT-TYPE
    SYNTAX     SEQUENCE OF Win32IRQResourceEntry
    MAX-ACCESS not-accessible
    STATUS     current
    DESCRIPTION
        "The Win32_IRQResource  WMI class represents an
        interrupt request line (IRQ) number on a Windows
        computer system. An interrupt request is a signal
        sent to the CPU by a device or program for time
        critical events. IRQ can be hardware or
        software-based."
    ::= { wmiMotherboardControllerPort 11 }

win32IRQResourceEntry OBJECT-TYPE
    SYNTAX     Win32IRQResourceEntry
    MAX-ACCESS not-accessible
    STATUS     current
    DESCRIPTION
        "None"
    INDEX      { hwirqIndex }
    ::= { win32IRQResourceTable 1 }

Win32IRQResourceEntry ::= SEQUENCE {
    hwirqIndex Integer32,
    hwirqAvailability INTEGER,
    hwirqCaption DisplayString,
    hwirqCreationClassName DisplayString,
    hwirqCSCreationClassName DisplayString,
    hwirqCSName DisplayString,
    hwirqDescription DisplayString,
    hwirqHardware TruthValue,
    hwirqInstallDate DateAndTime,
    hwirqIRQNumber Gauge32,
    hwirqName DisplayString,
    hwirqShareable TruthValue,
    hwirqStatus INTEGER,
    hwirqTriggerLevel INTEGER,
    hwirqTriggerType INTEGER,
    hwirqVector Gauge32
}

hwirqIndex OBJECT-TYPE
    SYNTAX     Integer32 (1..2147483647)
    MAX-ACCESS read-only
    STATUS     current
    DESCRIPTION
        "The value of this object uniquely identifies the
        instance entry for this class."
    ::= { win32IRQResourceEntry 1 }

hwirqAvailability OBJECT-TYPE
    SYNTAX     INTEGER {
        other(0),
        unknown(1),
        available(2),
        inUseNotAvailable(3),
        inUseAndAvailableShareable(4)
    }
    MAX-ACCESS read-only
    STATUS     current
    DESCRIPTION
        "Availability of the IRQ. This property is
        inherited from CIM_IRQ."
    ::= { win32IRQResourceEntry 2 }

hwirqCaption OBJECT-TYPE
    SYNTAX     DisplayString
    MAX-ACCESS read-only
    STATUS     current
    DESCRIPTION
        "Short description of the object a one-line string.
        This property is inherited from
        CIM_ManagedSystemElement."
    ::= { win32IRQResourceEntry 3 }

hwirqCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_IRQ."
    ::= { win32IRQResourceEntry 4 }

hwirqCSCreationClassName OBJECT-TYPE
    SYNTAX     DisplayString
    MAX-ACCESS read-only
    STATUS     current
    DESCRIPTION
        "Name of the scoping computer system creation
        class. This property is inherited from CIM_IRQ."
    ::= { win32IRQResourceEntry 5 }

hwirqCSName OBJECT-TYPE
    SYNTAX     DisplayString
    MAX-ACCESS read-only
    STATUS     current
    DESCRIPTION
        "Name of the scoping computer system. This property
        is inherited from CIM_IRQ."
    ::= { win32IRQResourceEntry 6 }

hwirqDescription OBJECT-TYPE
    SYNTAX     DisplayString
    MAX-ACCESS read-only
    STATUS     current
    DESCRIPTION
        "Textual description of the object. This property
        is inherited from CIM_ManagedSystemElement."
    ::= { win32IRQResourceEntry 7 }

hwirqHardware OBJECT-TYPE
    SYNTAX     TruthValue
    MAX-ACCESS read-only
    STATUS     current
    DESCRIPTION
        "If TRUE, the interrupt is hardware or software
        based. A hardware IRQ is a physical wire from the
        peripheral to the programmable interrupt controller
        (PIC) chip through which the CPU can be notified of
        time-critical events. Some IRQ lines are reserved
        for standard devices such as the keyboard, floppy
        disk drives, and the system clock. A software
        interrupt allows applications to get the attention
        of the processor."
    ::= { win32IRQResourceEntry 8 }

hwirqInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32IRQResourceEntry 9 }

hwirqIRQNumber OBJECT-TYPE
    SYNTAX     Gauge32
    MAX-ACCESS read-only
    STATUS     current
    DESCRIPTION
        "Part of the object's key value. This property is
        inherited from CIM_IRQ."
    ::= { win32IRQResourceEntry 10 }

hwirqName OBJECT-TYPE
    SYNTAX     DisplayString
    MAX-ACCESS read-only
    STATUS     current
    DESCRIPTION
        "Label by which the object is known. When
        subclassed, the property can be overridden to be a
        key property. This property is inherited from
        CIM_ManagedSystemElement."
    ::= { win32IRQResourceEntry 11 }

hwirqShareable OBJECT-TYPE
    SYNTAX     TruthValue
    MAX-ACCESS read-only
    STATUS     current
    DESCRIPTION
        "If TRUE, the IRQ can be shared. This property is
        inherited from CIM_IRQ."
    ::= { win32IRQResourceEntry 12 }

hwirqStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32IRQResourceEntry 13 }

hwirqTriggerLevel OBJECT-TYPE
    SYNTAX     INTEGER {
        other(1),
        unknown(2),
        activeLow(3),
        activeHigh(4)
    }
    MAX-ACCESS read-only
    STATUS     current
    DESCRIPTION
        "IRQ trigger level indicating whether the interrupt
        is triggered by the hardware signal going high (4)
        or low (3). This property is inherited from
        CIM_IRQ."
    ::= { win32IRQResourceEntry 14 }

hwirqTriggerType OBJECT-TYPE
    SYNTAX     INTEGER {
        other(1),
        unknown(2),
        level(3),
        edge(4)
    }
    MAX-ACCESS read-only
    STATUS     current
    DESCRIPTION
        "IRQ trigger type indicating whether edge- (4) or
        level-triggered (3) interrupts occur. This property
        is inherited from CIM_IRQ."
    ::= { win32IRQResourceEntry 15 }

hwirqVector OBJECT-TYPE
    SYNTAX     Gauge32
    MAX-ACCESS read-only
    STATUS     current
    DESCRIPTION
        "Vector of the Windows IRQ resource. A vector
        contains the memory address to the function that
        will execute once the interrupt request is
        acknowledged by the CPU."
    ::= { win32IRQResourceEntry 16 }

win32MemoryArrayTable OBJECT-TYPE
    SYNTAX     SEQUENCE OF Win32MemoryArrayEntry
    MAX-ACCESS not-accessible
    STATUS     current
    DESCRIPTION
        "The Win32_MemoryArray WMI class represents the
        properties of the computer system memory array and
        mapped addresses."
    ::= { wmiMotherboardControllerPort 12 }

win32MemoryArrayEntry OBJECT-TYPE
    SYNTAX     Win32MemoryArrayEntry
    MAX-ACCESS not-accessible
    STATUS     current
    DESCRIPTION
        "None"
    INDEX      { hwmaIndex }
    ::= { win32MemoryArrayTable 1 }

Win32MemoryArrayEntry ::= SEQUENCE {
    hwmaIndex Integer32,
    hwmaAccess INTEGER,
    hwmaAdditionalErrorData DisplayString,
    hwmaAvailability INTEGER,
    hwmaBlockSize Gauge32,
    hwmaCaption DisplayString,
    hwmaConfigManagerErrorCode INTEGER,
    hwmaConfigManagerUserConfig TruthValue,
    hwmaCorrectableError TruthValue,
    hwmaCreationClassName DisplayString,
    hwmaDescription DisplayString,
    hwmaDeviceID DisplayString,
    hwmaEndingAddress Gauge32,
    hwmaErrorAccess INTEGER,
    hwmaErrorAddress Gauge32,
    hwmaErrorCleared TruthValue,
    hwmaErrorData DisplayString,
    hwmaErrorDataOrder INTEGER,
    hwmaErrorDescription DisplayString,
    hwmaErrorGranularity INTEGER,
    hwmaErrorInfo INTEGER,
    hwmaErrorMethodology INTEGER,
    hwmaErrorResolution Gauge32,
    hwmaErrorTime DateAndTime,
    hwmaErrorTransferSize Gauge32,
    hwmaInstallDate DateAndTime,
    hwmaLastErrorCode Gauge32,
    hwmaName DisplayString,
    hwmaNumberOfBlocks Gauge32,
    hwmaOtherErrorDescription DisplayString,
    hwmaPNPDeviceID DisplayString,
    hwmaPowerManagementCapabilities DisplayString,
    hwmaPowerManagementSupported TruthValue,
    hwmaPurpose DisplayString,
    hwmaStartingAddress Gauge32,
    hwmaStatus INTEGER,
    hwmaStatusInfo INTEGER,
    hwmaSystemCreationClassName DisplayString,
    hwmaSystemLevelAddress TruthValue,
    hwmaSystemName DisplayString
}

hwmaIndex OBJECT-TYPE
    SYNTAX     Integer32 (1..2147483647)
    MAX-ACCESS read-only
    STATUS     current
    DESCRIPTION
        "The value of this object uniquely identifies the
        instance entry for this class."
    ::= { win32MemoryArrayEntry 1 }

hwmaAccess OBJECT-TYPE
    SYNTAX     INTEGER {
        unknown(0),
        readable(1),
        writable(2),
        readWriteSupported(3),
        writeOnce(4)
    }
    MAX-ACCESS read-only
    STATUS     current
    DESCRIPTION
        "Type of media access available. This property is
        inherited from CIM_StorageExtent."
    ::= { win32MemoryArrayEntry 2 }

hwmaAdditionalErrorData OBJECT-TYPE
    SYNTAX     DisplayString
    MAX-ACCESS read-only
    STATUS     current
    DESCRIPTION
        "Array of additional error information. An example
        is Error Checking and Correcting (ECC) Syndrome, or
        the return of the check bits if a cyclical
        redundancy check (CRC) based ErrorMethodology value
        is used. In the latter case, if a single bit error
        is recognized and the CRC algorithm is known, it is
        possible to determine the exact bit that failed.
        This type of data (ECC Syndrome, Check Bit, Parity
        Bit data, or other vendor-supplied information) is
        included in this field. This property is used only
        when the ErrorInfo property is not equal to 3. This
        property is inherited from Win32_SMBIOSMemory."
    ::= { win32MemoryArrayEntry 3 }

hwmaAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32MemoryArrayEntry 4 }

hwmaBlockSize OBJECT-TYPE
    SYNTAX     Gauge32
    MAX-ACCESS read-only
    STATUS     current
    DESCRIPTION
        "Size in bytes of the blocks that form this storage
        extent. If unknown or if a block concept is not
        valid (for example, for aggregate extents, memory
        or logical disks), enter a 1. This property is
        inherited from CIM_StorageExtent."
    ::= { win32MemoryArrayEntry 5 }

hwmaCaption OBJECT-TYPE
    SYNTAX     DisplayString
    MAX-ACCESS read-only
    STATUS     current
    DESCRIPTION
        "Short description of the object a one-line string.
        This property is inherited from
        CIM_ManagedSystemElement."
    ::= { win32MemoryArrayEntry 6 }

hwmaConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32MemoryArrayEntry 7 }

hwmaConfigManagerUserConfig OBJECT-TYPE
    SYNTAX     TruthValue
    MAX-ACCESS read-only
    STATUS     current
    DESCRIPTION
        "If TRUE, the device is using a user-defined
        configuration. This property is inherited from
        CIM_LogicalDevice."
    ::= { win32MemoryArrayEntry 8 }

hwmaCorrectableError OBJECT-TYPE
    SYNTAX     TruthValue
    MAX-ACCESS read-only
    STATUS     current
    DESCRIPTION
        "If TRUE, the most recent error was correctable.
        This property is not used if ErrorInfo is set to 3.
        This property is inherited from
        Win32_SMBIOSMemory."
    ::= { win32MemoryArrayEntry 9 }

hwmaCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32MemoryArrayEntry 10 }

hwmaDescription OBJECT-TYPE
    SYNTAX     DisplayString
    MAX-ACCESS read-only
    STATUS     current
    DESCRIPTION
        "Description of the object. This property is
        inherited from CIM_ManagedSystemElement."
    ::= { win32MemoryArrayEntry 11 }

hwmaDeviceID OBJECT-TYPE
    SYNTAX     DisplayString
    MAX-ACCESS read-only
    STATUS     current
    DESCRIPTION
        "Unique identifier of the memory array. This
        property is inherited from CIM_LogicalDevice.
        Example: 'Memory Array 1'"
    ::= { win32MemoryArrayEntry 12 }

hwmaEndingAddress OBJECT-TYPE
    SYNTAX     Gauge32
    MAX-ACCESS read-only
    STATUS     current
    DESCRIPTION
        "Ending address referenced by an application or
        operating system. This memory address is mapped by
        a memory controller for this memory object. This
        property is inherited from Win32_SMBIOSMemory."
    ::= { win32MemoryArrayEntry 13 }

hwmaErrorAccess OBJECT-TYPE
    SYNTAX     INTEGER {
        other(1),
        unknown(2),
        read(3),
        write(4),
        partialWrite(5)
    }
    MAX-ACCESS read-only
    STATUS     current
    DESCRIPTION
        "Type of memory access operation that caused the
        last error. This property is valid only when
        ErrorInfo is not set to 3. This property is
        inherited from Win32_SMBIOSMemory."
    ::= { win32MemoryArrayEntry 14 }

hwmaErrorAddress OBJECT-TYPE
    SYNTAX     Gauge32
    MAX-ACCESS read-only
    STATUS     current
    DESCRIPTION
        "Address of the last memory error. This property is
        used only when ErrorInfo is not set to 3. This
        property is inherited from Win32_SMBIOSMemory."
    ::= { win32MemoryArrayEntry 15 }

hwmaErrorCleared OBJECT-TYPE
    SYNTAX     TruthValue
    MAX-ACCESS read-only
    STATUS     current
    DESCRIPTION
        "If TRUE, the error reported in LastErrorCode is
        now cleared. This property is inherited from
        CIM_LogicalDevice."
    ::= { win32MemoryArrayEntry 16 }

hwmaErrorData OBJECT-TYPE
    SYNTAX     DisplayString
    MAX-ACCESS read-only
    STATUS     current
    DESCRIPTION
        "Array of data captured from the last memory access
        with an error. The data occupies the first n octets
        of the array necessary to hold the number of bits
        specified by the ErrorTransferSize property. If
        ErrorTransferSize is 0 (zero), then this property
        is not used. This property is inherited from
        Win32_SMBIOSMemory."
    ::= { win32MemoryArrayEntry 17 }

hwmaErrorDataOrder OBJECT-TYPE
    SYNTAX     INTEGER {
        unknown(0),
        leastSignificantByteFirst(1),
        mostSignificantByteFirst(2)
    }
    MAX-ACCESS read-only
    STATUS     current
    DESCRIPTION
        "Ordering for data stored in the ErrorData
        property. This property is used only when
        ErrorTransferSize is 0 (zero). This property is
        inherited from Win32_SMBIOSMemory."
    ::= { win32MemoryArrayEntry 18 }

hwmaErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32MemoryArrayEntry 19 }

hwmaErrorGranularity OBJECT-TYPE
    SYNTAX     INTEGER {
        other(1),
        unknown(2),
        deviceLevel(3),
        memoryPartitionLevel(4)
    }
    MAX-ACCESS read-only
    STATUS     current
    DESCRIPTION
        "Level where the error can be resolved."
    ::= { win32MemoryArrayEntry 20 }

hwmaErrorInfo OBJECT-TYPE
    SYNTAX     INTEGER {
        other(1),
        unknown(2),
        ok(3),
        badRead(4),
        parityError(5),
        singleBitError(6),
        doubleBitError(7),
        multiBitError(8),
        nibbleError(9),
        checksumError(10),
        crcError(11),
        correctedSinglebitError(12),
        correctedError(13),
        uncorrectableError(14)
    }
    MAX-ACCESS read-only
    STATUS     current
    DESCRIPTION
        "Type of error that occurred most recently. The
        values 12-14, which indicate whether an error is
        correctable, are not used with this property but
        this information is found in the CorrectableError
        property. This property is inherited from
        Win32_SMBIOSMemory."
    ::= { win32MemoryArrayEntry 21 }

hwmaErrorMethodology OBJECT-TYPE
    SYNTAX     INTEGER {
        other(1),
        unknown(2),
        none(3),
        parity(4),
        singleBitECC(5),
        multiBitECC(6),
        crc(7)
    }
    MAX-ACCESS read-only
    STATUS     current
    DESCRIPTION
        "Types of error checking used by the memory
        hardware. This property is inherited from
        CIM_StorageExtent."
    ::= { win32MemoryArrayEntry 22 }

hwmaErrorResolution OBJECT-TYPE
    SYNTAX     Gauge32
    MAX-ACCESS read-only
    STATUS     current
    DESCRIPTION
        "Amount of data actually determined to cause the
        error. This property is unused when the ErrorInfo
        property is set to 3. This property is inherited
        from Win32_SMBIOSMemory."
    ::= { win32MemoryArrayEntry 23 }

hwmaErrorTime OBJECT-TYPE
    SYNTAX     DateAndTime
    MAX-ACCESS read-only
    STATUS     current
    DESCRIPTION
        "Time that the last memory error occurred. This
        property is valid only when ErrorInfo is not set to
        3. This property is inherited from
        Win32_SMBIOSMemory."
    ::= { win32MemoryArrayEntry 24 }

hwmaErrorTransferSize OBJECT-TYPE
    SYNTAX     Gauge32
    MAX-ACCESS read-only
    STATUS     current
    DESCRIPTION
        "Size of the data (containing the last error) being
        transferred. This property is set to 0 (zero) if
        there is no error. This property is inherited from
        Win32_SMBIOSMemory."
    ::= { win32MemoryArrayEntry 25 }

hwmaInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32MemoryArrayEntry 26 }

hwmaLastErrorCode OBJECT-TYPE
    SYNTAX     Gauge32
    MAX-ACCESS read-only
    STATUS     current
    DESCRIPTION
        "Last error code reported by the logical device.
        This property is inherited from CIM_LogicalDevice."
    ::= { win32MemoryArrayEntry 27 }

hwmaName OBJECT-TYPE
    SYNTAX     DisplayString
    MAX-ACCESS read-only
    STATUS     current
    DESCRIPTION
        "Label by which the object is known. When
        subclassed, the property can be overridden to be a
        key property. This property is inherited from
        CIM_ManagedSystemElement."
    ::= { win32MemoryArrayEntry 28 }

hwmaNumberOfBlocks OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent. This property is inherited from
        CIM_StorageExtent."
    ::= { win32MemoryArrayEntry 29 }

hwmaOtherErrorDescription OBJECT-TYPE
    SYNTAX     DisplayString
    MAX-ACCESS read-only
    STATUS     current
    DESCRIPTION
        "More information when the ErrorInfo property is
        set to 1. This property is inherited from
        Win32_SMBIOSMemory."
    ::= { win32MemoryArrayEntry 30 }

hwmaPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32MemoryArrayEntry 31 }

hwmaPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32MemoryArrayEntry 32 }

hwmaPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32MemoryArrayEntry 33 }

hwmaPurpose OBJECT-TYPE
    SYNTAX     DisplayString
    MAX-ACCESS read-only
    STATUS     current
    DESCRIPTION
        "Free-form string describing the media and/or its
        use. This property is inherited from
        CIM_StorageExtent."
    ::= { win32MemoryArrayEntry 34 }

hwmaStartingAddress OBJECT-TYPE
    SYNTAX     Gauge32
    MAX-ACCESS read-only
    STATUS     current
    DESCRIPTION
        "Beginning address referenced by an application or
        the operating system. This memory address is mapped
        by a memory controller for this memory object. This
        property is inherited from Win32_SMBIOSMemory."
    ::= { win32MemoryArrayEntry 35 }

hwmaStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32MemoryArrayEntry 36 }

hwmaStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32MemoryArrayEntry 37 }

hwmaSystemCreationClassName OBJECT-TYPE
    SYNTAX     DisplayString
    MAX-ACCESS read-only
    STATUS     current
    DESCRIPTION
        "Value of the scoping computer's CreationClassName
        property. This property is inherited from
        CIM_LogicalDevice."
    ::= { win32MemoryArrayEntry 38 }

hwmaSystemLevelAddress OBJECT-TYPE
    SYNTAX     TruthValue
    MAX-ACCESS read-only
    STATUS     current
    DESCRIPTION
        "If TRUE, the address information in the
        ErrorAddress property is a system-level address. If
        FALSE, it is a physical address. This property is
        used only when ErrorInfo is not set to 3. This
        property is inherited from Win32_SMBIOSMemory."
    ::= { win32MemoryArrayEntry 39 }

hwmaSystemName OBJECT-TYPE
    SYNTAX     DisplayString
    MAX-ACCESS read-only
    STATUS     current
    DESCRIPTION
        "Name of the scoping system. This property is
        inherited from CIM_LogicalDevice."
    ::= { win32MemoryArrayEntry 40 }

win32MemoryDeviceTable OBJECT-TYPE
    SYNTAX     SEQUENCE OF Win32MemoryDeviceEntry
    MAX-ACCESS not-accessible
    STATUS     current
    DESCRIPTION
        "The Win32_MemoryDevice WMI class represents the
        properties of a computer system memory device and
        its associated mapped addresses."
    ::= { wmiMotherboardControllerPort 13 }

win32MemoryDeviceEntry OBJECT-TYPE
    SYNTAX     Win32MemoryDeviceEntry
    MAX-ACCESS not-accessible
    STATUS     current
    DESCRIPTION
        "None"
    INDEX      { hwmmIndex }
    ::= { win32MemoryDeviceTable 1 }

Win32MemoryDeviceEntry ::= SEQUENCE {
    hwmmIndex Integer32,
    hwmmAccess INTEGER,
    hwmmAdditionalErrorData DisplayString,
    hwmmAvailability INTEGER,
    hwmmBlockSize Gauge32,
    hwmmCaption DisplayString,
    hwmmConfigManagerErrorCode INTEGER,
    hwmmConfigManagerUserConfig TruthValue,
    hwmmCorrectableError TruthValue,
    hwmmCreationClassName DisplayString,
    hwmmDescription DisplayString,
    hwmmDeviceID DisplayString,
    hwmmEndingAddress Gauge32,
    hwmmErrorAccess INTEGER,
    hwmmErrorAddress Gauge32,
    hwmmErrorCleared TruthValue,
    hwmmErrorData DisplayString,
    hwmmErrorDataOrder INTEGER,
    hwmmErrorDescription DisplayString,
    hwmmErrorGranularity INTEGER,
    hwmmErrorInfo INTEGER,
    hwmmErrorMethodology INTEGER,
    hwmmErrorResolution Gauge32,
    hwmmErrorTime DateAndTime,
    hwmmErrorTransferSize Gauge32,
    hwmmInstallDate DateAndTime,
    hwmmLastErrorCode Gauge32,
    hwmmName DisplayString,
    hwmmNumberOfBlocks Gauge32,
    hwmmOtherErrorDescription DisplayString,
    hwmmPNPDeviceID DisplayString,
    hwmmPowerManagementCapabilities DisplayString,
    hwmmPowerManagementSupported TruthValue,
    hwmmPurpose DisplayString,
    hwmmStartingAddress Gauge32,
    hwmmStatus INTEGER,
    hwmmStatusInfo INTEGER,
    hwmmSystemCreationClassName DisplayString,
    hwmmSystemLevelAddress TruthValue,
    hwmmSystemName DisplayString
}

hwmmIndex OBJECT-TYPE
    SYNTAX     Integer32 (1..2147483647)
    MAX-ACCESS read-only
    STATUS     current
    DESCRIPTION
        "The value of this object uniquely identifies the
        instance entry for this class."
    ::= { win32MemoryDeviceEntry 1 }

hwmmAccess OBJECT-TYPE
    SYNTAX     INTEGER {
        unknown(0),
        readable(1),
        writable(2),
        readWriteSupported(3),
        writeOnce(4)
    }
    MAX-ACCESS read-only
    STATUS     current
    DESCRIPTION
        "Media access available. This property is inherited
        from CIM_StorageExtent."
    ::= { win32MemoryDeviceEntry 2 }

hwmmAdditionalErrorData OBJECT-TYPE
    SYNTAX     DisplayString
    MAX-ACCESS read-only
    STATUS     current
    DESCRIPTION
        "Array of additional error information. An example
        is Error Checking and Correcting (ECC) Syndrome, or
        the return of the check bits if a cyclical
        redundancy check (CRC) based error methodology is
        used. In the latter case, if a single bit error is
        recognized and the CRC algorithm is known, it is
        possible to determine the exact bit that failed.
        This type of data (ECC Syndrome, Check Bit, Parity
        Bit data, or other vendor-supplied information) is
        included in this field. This property is used only
        when the ErrorInfo property is not equal to 3. This
        property is inherited from Win32_SMBIOSMemory."
    ::= { win32MemoryDeviceEntry 3 }

hwmmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32MemoryDeviceEntry 4 }

hwmmBlockSize OBJECT-TYPE
    SYNTAX     Gauge32
    MAX-ACCESS read-only
    STATUS     current
    DESCRIPTION
        "Size in bytes of the blocks that form this storage
        extent. If unknown or if a block concept is not
        valid (for example, for aggregate extents, memory
        or logical disks), enter a 1. This property is
        inherited from CIM_StorageExtent."
    ::= { win32MemoryDeviceEntry 5 }

hwmmCaption OBJECT-TYPE
    SYNTAX     DisplayString
    MAX-ACCESS read-only
    STATUS     current
    DESCRIPTION
        "Short description of the object a one-line string.
        This property is inherited from
        CIM_ManagedSystemElement."
    ::= { win32MemoryDeviceEntry 6 }

hwmmConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32MemoryDeviceEntry 7 }

hwmmConfigManagerUserConfig OBJECT-TYPE
    SYNTAX     TruthValue
    MAX-ACCESS read-only
    STATUS     current
    DESCRIPTION
        "If TRUE, the device is using a user-defined
        configuration. This property is inherited from
        CIM_LogicalDevice."
    ::= { win32MemoryDeviceEntry 8 }

hwmmCorrectableError OBJECT-TYPE
    SYNTAX     TruthValue
    MAX-ACCESS read-only
    STATUS     current
    DESCRIPTION
        "If TRUE, the most recent error was correctable.
        This property is not used if ErrorInfo is set to 3.
        This property is inherited from
        Win32_SMBIOSMemory."
    ::= { win32MemoryDeviceEntry 9 }

hwmmCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32MemoryDeviceEntry 10 }

hwmmDescription OBJECT-TYPE
    SYNTAX     DisplayString
    MAX-ACCESS read-only
    STATUS     current
    DESCRIPTION
        "Description of the object. This property is
        inherited from CIM_ManagedSystemElement."
    ::= { win32MemoryDeviceEntry 11 }

hwmmDeviceID OBJECT-TYPE
    SYNTAX     DisplayString
    MAX-ACCESS read-only
    STATUS     current
    DESCRIPTION
        "Unique identifier of the memory device. This
        property is inherited from CIM_LogicalDevice.
        Example: 'Memory Device 1'"
    ::= { win32MemoryDeviceEntry 12 }

hwmmEndingAddress OBJECT-TYPE
    SYNTAX     Gauge32
    MAX-ACCESS read-only
    STATUS     current
    DESCRIPTION
        "Ending address referenced by an application or
        operating system. This memory address is mapped by
        a memory controller for this memory object. This
        property is inherited from Win32_SMBIOSMemory."
    ::= { win32MemoryDeviceEntry 13 }

hwmmErrorAccess OBJECT-TYPE
    SYNTAX     INTEGER {
        other(1),
        unknown(2),
        read(3),
        write(4),
        partialWrite(5)
    }
    MAX-ACCESS read-only
    STATUS     current
    DESCRIPTION
        "Type of memory access operation that caused the
        last error. This property is valid only when
        ErrorInfo is not set to 3. This property is
        inherited from Win32_SMBIOSMemory."
    ::= { win32MemoryDeviceEntry 14 }

hwmmErrorAddress OBJECT-TYPE
    SYNTAX     Gauge32
    MAX-ACCESS read-only
    STATUS     current
    DESCRIPTION
        "Address of the last memory error. This property is
        used only when ErrorInfo is not set to 3. This
        property is inherited from Win32_SMBIOSMemory."
    ::= { win32MemoryDeviceEntry 15 }

hwmmErrorCleared OBJECT-TYPE
    SYNTAX     TruthValue
    MAX-ACCESS read-only
    STATUS     current
    DESCRIPTION
        "If TRUE, the error reported in LastErrorCode is
        now cleared. This property is inherited from
        CIM_LogicalDevice."
    ::= { win32MemoryDeviceEntry 16 }

hwmmErrorData OBJECT-TYPE
    SYNTAX     DisplayString
    MAX-ACCESS read-only
    STATUS     current
    DESCRIPTION
        "Array of data captured from the last memory access
        with an error. The data occupies the first n octets
        of the array necessary to hold the number of bits
        specified by the ErrorTransferSize property. If
        ErrorTransferSize is 0 (zero), then this property
        is not used. This property is inherited from
        Win32_SMBIOSMemory."
    ::= { win32MemoryDeviceEntry 17 }

hwmmErrorDataOrder OBJECT-TYPE
    SYNTAX     INTEGER {
        unknown(0),
        leastSignificantByteFirst(1),
        mostSignificantByteFirst(2)
    }
    MAX-ACCESS read-only
    STATUS     current
    DESCRIPTION
        "Ordering for data stored in the ErrorData
        property. This property is used only when
        ErrorTransferSize is 0 (zero). This property is
        inherited from Win32_SMBIOSMemory."
    ::= { win32MemoryDeviceEntry 18 }

hwmmErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32MemoryDeviceEntry 19 }

hwmmErrorGranularity OBJECT-TYPE
    SYNTAX     INTEGER {
        other(1),
        unknown(2),
        deviceLevel(3),
        memoryPartitionLevel(4)
    }
    MAX-ACCESS read-only
    STATUS     current
    DESCRIPTION
        "Level where the error can be resolved."
    ::= { win32MemoryDeviceEntry 20 }

hwmmErrorInfo OBJECT-TYPE
    SYNTAX     INTEGER {
        other(1),
        unknown(2),
        ok(3),
        badRead(4),
        parityError(5),
        singleBitError(6),
        doubleBitError(7),
        multiBitError(8),
        nibbleError(9),
        checksumError(10),
        crcError(11),
        correctedSinglebitError(12),
        correctedError(13),
        uncorrectableError(14)
    }
    MAX-ACCESS read-only
    STATUS     current
    DESCRIPTION
        "Type of error that occurred most recently. The
        values 12-14, indicating whether an error is
        correctable, are not used with this property but
        this information is found in the CorrectableError
        property. This property is inherited from
        Win32_SMBIOSMemory."
    ::= { win32MemoryDeviceEntry 21 }

hwmmErrorMethodology OBJECT-TYPE
    SYNTAX     INTEGER {
        other(1),
        unknown(2),
        name(3),
        parity(4),
        singleBitECC(5),
        multiBitECC(6),
        crc(7)
    }
    MAX-ACCESS read-only
    STATUS     current
    DESCRIPTION
        "Types of error checking used by the memory
        hardware. This property is inherited from
        CIM_StorageExtent."
    ::= { win32MemoryDeviceEntry 22 }

hwmmErrorResolution OBJECT-TYPE
    SYNTAX     Gauge32
    MAX-ACCESS read-only
    STATUS     current
    DESCRIPTION
        "Amount of data actually determined to cause the
        error. This property is unused when the ErrorInfo
        property is set to 3. This property is inherited
        from Win32_SMBIOSMemory."
    ::= { win32MemoryDeviceEntry 23 }

hwmmErrorTime OBJECT-TYPE
    SYNTAX     DateAndTime
    MAX-ACCESS read-only
    STATUS     current
    DESCRIPTION
        "Time that the last memory error occurred. This
        property is valid only when ErrorInfo is not set to
        3. This property is inherited from
        Win32_SMBIOSMemory."
    ::= { win32MemoryDeviceEntry 24 }

hwmmErrorTransferSize OBJECT-TYPE
    SYNTAX     Gauge32
    MAX-ACCESS read-only
    STATUS     current
    DESCRIPTION
        "Size of the data (containing the last error) being
        transferred. This property is set to 0 (zero) if
        there is no error. This property is inherited from
        Win32_SMBIOSMemory."
    ::= { win32MemoryDeviceEntry 25 }

hwmmInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32MemoryDeviceEntry 26 }

hwmmLastErrorCode OBJECT-TYPE
    SYNTAX     Gauge32
    MAX-ACCESS read-only
    STATUS     current
    DESCRIPTION
        "Last error code reported by the logical device.
        This property is inherited from CIM_LogicalDevice."
    ::= { win32MemoryDeviceEntry 27 }

hwmmName OBJECT-TYPE
    SYNTAX     DisplayString
    MAX-ACCESS read-only
    STATUS     current
    DESCRIPTION
        "Label by which the object is known. When
        subclassed, the property can be overridden to be a
        key property. This property is inherited from
        CIM_ManagedSystemElement."
    ::= { win32MemoryDeviceEntry 28 }

hwmmNumberOfBlocks OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent. This property is inherited from
        CIM_StorageExtent."
    ::= { win32MemoryDeviceEntry 29 }

hwmmOtherErrorDescription OBJECT-TYPE
    SYNTAX     DisplayString
    MAX-ACCESS read-only
    STATUS     current
    DESCRIPTION
        "More information when the ErrorInfo property is
        set to 1. This property is inherited from
        Win32_SMBIOSMemory."
    ::= { win32MemoryDeviceEntry 30 }

hwmmPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32MemoryDeviceEntry 31 }

hwmmPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32MemoryDeviceEntry 32 }

hwmmPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32MemoryDeviceEntry 33 }

hwmmPurpose OBJECT-TYPE
    SYNTAX     DisplayString
    MAX-ACCESS read-only
    STATUS     current
    DESCRIPTION
        "Free-form string describing the media and/or its
        use. This property is inherited from
        CIM_StorageExtent."
    ::= { win32MemoryDeviceEntry 34 }

hwmmStartingAddress OBJECT-TYPE
    SYNTAX     Gauge32
    MAX-ACCESS read-only
    STATUS     current
    DESCRIPTION
        "Beginning address referenced by an application or
        the operating system. This memory address is mapped
        by a memory controller for this memory object. This
        property is inherited from Win32_SMBIOSMemory."
    ::= { win32MemoryDeviceEntry 35 }

hwmmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32MemoryDeviceEntry 36 }

hwmmStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32MemoryDeviceEntry 37 }

hwmmSystemCreationClassName OBJECT-TYPE
    SYNTAX     DisplayString
    MAX-ACCESS read-only
    STATUS     current
    DESCRIPTION
        "Value of the scoping computer's CreationClassName
        property. This property is inherited from
        CIM_LogicalDevice."
    ::= { win32MemoryDeviceEntry 38 }

hwmmSystemLevelAddress OBJECT-TYPE
    SYNTAX     TruthValue
    MAX-ACCESS read-only
    STATUS     current
    DESCRIPTION
        "If TRUE, the address information in the
        ErrorAddress property is a system-level address. If
        FALSE, it is a physical address. This property is
        used only when ErrorInfo is not set to 3. This
        property is inherited from Win32_SMBIOSMemory."
    ::= { win32MemoryDeviceEntry 39 }

hwmmSystemName OBJECT-TYPE
    SYNTAX     DisplayString
    MAX-ACCESS read-only
    STATUS     current
    DESCRIPTION
        "Name of the scoping system. This property is
        inherited from CIM_LogicalDevice."
    ::= { win32MemoryDeviceEntry 40 }

win32MotherboardDeviceTable OBJECT-TYPE
    SYNTAX     SEQUENCE OF Win32MotherboardDeviceEntry
    MAX-ACCESS not-accessible
    STATUS     current
    DESCRIPTION
        "The Win32_MotherboardDevice WMI class represents a
        device that contains the central components of the
        Windows computer system."
    ::= { wmiMotherboardControllerPort 14 }

win32MotherboardDeviceEntry OBJECT-TYPE
    SYNTAX     Win32MotherboardDeviceEntry
    MAX-ACCESS not-accessible
    STATUS     current
    DESCRIPTION
        "None"
    INDEX      { hwmbIndex }
    ::= { win32MotherboardDeviceTable 1 }

Win32MotherboardDeviceEntry ::= SEQUENCE {
    hwmbIndex Integer32,
    hwmbAvailability INTEGER,
    hwmbCaption DisplayString,
    hwmbConfigManagerErrorCode INTEGER,
    hwmbConfigManagerUserConfig TruthValue,
    hwmbCreationClassName DisplayString,
    hwmbDescription DisplayString,
    hwmbDeviceID DisplayString,
    hwmbErrorCleared TruthValue,
    hwmbErrorDescription DisplayString,
    hwmbInstallDate DateAndTime,
    hwmbLastErrorCode Gauge32,
    hwmbName DisplayString,
    hwmbPNPDeviceID DisplayString,
    hwmbPowerManagementCapabilities DisplayString,
    hwmbPowerManagementSupported TruthValue,
    hwmbPrimaryBusType DisplayString,
    hwmbRevisionNumber DisplayString,
    hwmbSecondaryBusType DisplayString,
    hwmbStatus INTEGER,
    hwmbStatusInfo INTEGER,
    hwmbSystemCreationClassName DisplayString,
    hwmbSystemName DisplayString
}

hwmbIndex OBJECT-TYPE
    SYNTAX     Integer32 (1..2147483647)
    MAX-ACCESS read-only
    STATUS     current
    DESCRIPTION
        "The value of this object uniquely identifies the
        instance entry for this class."
    ::= { win32MotherboardDeviceEntry 1 }

hwmbAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32MotherboardDeviceEntry 2 }

hwmbCaption OBJECT-TYPE
    SYNTAX     DisplayString
    MAX-ACCESS read-only
    STATUS     current
    DESCRIPTION
        "Short description of the object a one-line string.
        This property is inherited from
        CIM_ManagedSystemElement."
    ::= { win32MotherboardDeviceEntry 3 }

hwmbConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32MotherboardDeviceEntry 4 }

hwmbConfigManagerUserConfig OBJECT-TYPE
    SYNTAX     TruthValue
    MAX-ACCESS read-only
    STATUS     current
    DESCRIPTION
        "If TRUE, the device is using a user-defined
        configuration. This property is inherited from
        CIM_LogicalDevice."
    ::= { win32MotherboardDeviceEntry 5 }

hwmbCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32MotherboardDeviceEntry 6 }

hwmbDescription OBJECT-TYPE
    SYNTAX     DisplayString
    MAX-ACCESS read-only
    STATUS     current
    DESCRIPTION
        "Description of the object. This property is
        inherited from CIM_ManagedSystemElement."
    ::= { win32MotherboardDeviceEntry 7 }

hwmbDeviceID OBJECT-TYPE
    SYNTAX     DisplayString
    MAX-ACCESS read-only
    STATUS     current
    DESCRIPTION
        "Unique identifier of this motherboard. This
        property is inherited from CIM_LogicalDevice."
    ::= { win32MotherboardDeviceEntry 8 }

hwmbErrorCleared OBJECT-TYPE
    SYNTAX     TruthValue
    MAX-ACCESS read-only
    STATUS     current
    DESCRIPTION
        "If TRUE, the error reported in LastErrorCode is
        now cleared. This property is inherited from
        CIM_LogicalDevice."
    ::= { win32MotherboardDeviceEntry 9 }

hwmbErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32MotherboardDeviceEntry 10 }

hwmbInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32MotherboardDeviceEntry 11 }

hwmbLastErrorCode OBJECT-TYPE
    SYNTAX     Gauge32
    MAX-ACCESS read-only
    STATUS     current
    DESCRIPTION
        "Last error code reported by the logical device.
        This property is inherited from CIM_LogicalDevice."
    ::= { win32MotherboardDeviceEntry 12 }

hwmbName OBJECT-TYPE
    SYNTAX     DisplayString
    MAX-ACCESS read-only
    STATUS     current
    DESCRIPTION
        "Label by which the object is known. When
        subclassed, the property can be overridden to be a
        key property. This property is inherited from
        CIM_ManagedSystemElement."
    ::= { win32MotherboardDeviceEntry 13 }

hwmbPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32MotherboardDeviceEntry 14 }

hwmbPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32MotherboardDeviceEntry 15 }

hwmbPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32MotherboardDeviceEntry 16 }

hwmbPrimaryBusType OBJECT-TYPE
    SYNTAX     DisplayString
    MAX-ACCESS read-only
    STATUS     current
    DESCRIPTION
        "Primary bus type of the motherboard.
        Example: 'PCI'"
    ::= { win32MotherboardDeviceEntry 17 }

hwmbRevisionNumber OBJECT-TYPE
    SYNTAX     DisplayString
    MAX-ACCESS read-only
    STATUS     current
    DESCRIPTION
        "Revision number of the motherboard.
        Example: '00'"
    ::= { win32MotherboardDeviceEntry 18 }

hwmbSecondaryBusType OBJECT-TYPE
    SYNTAX     DisplayString
    MAX-ACCESS read-only
    STATUS     current
    DESCRIPTION
        "Secondary bus type of the motherboard.
        Example: 'ISA'"
    ::= { win32MotherboardDeviceEntry 19 }

hwmbStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32MotherboardDeviceEntry 20 }

hwmbStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32MotherboardDeviceEntry 21 }

hwmbSystemCreationClassName OBJECT-TYPE
    SYNTAX     DisplayString
    MAX-ACCESS read-only
    STATUS     current
    DESCRIPTION
        "Value of the scoping computer's CreationClassName
        property. This property is inherited from
        CIM_LogicalDevice."
    ::= { win32MotherboardDeviceEntry 22 }

hwmbSystemName OBJECT-TYPE
    SYNTAX     DisplayString
    MAX-ACCESS read-only
    STATUS     current
    DESCRIPTION
        "Name of the scoping system. This property is
        inherited from CIM_LogicalDevice."
    ::= { win32MotherboardDeviceEntry 23 }

win32OnBoardDeviceTable OBJECT-TYPE
    SYNTAX     SEQUENCE OF Win32OnBoardDeviceEntry
    MAX-ACCESS not-accessible
    STATUS     current
    DESCRIPTION
        "The Win32_OnBoardDevice WMI class represents
        common adapter devices built into the motherboard
        (system board)."
    ::= { wmiMotherboardControllerPort 15 }

win32OnBoardDeviceEntry OBJECT-TYPE
    SYNTAX     Win32OnBoardDeviceEntry
    MAX-ACCESS not-accessible
    STATUS     current
    DESCRIPTION
        "None"
    INDEX      { hwobIndex }
    ::= { win32OnBoardDeviceTable 1 }

Win32OnBoardDeviceEntry ::= SEQUENCE {
    hwobIndex Integer32,
    hwobCaption DisplayString,
    hwobCreationClassName DisplayString,
    hwobDescription DisplayString,
    hwobDeviceType INTEGER,
    hwobEnabled TruthValue,
    hwobHotSwappable TruthValue,
    hwobInstallDate DateAndTime,
    hwobManufacturer DisplayString,
    hwobModel DisplayString,
    hwobName DisplayString,
    hwobOtherIdentifyingInfo DisplayString,
    hwobPartNumber DisplayString,
    hwobPoweredOn TruthValue,
    hwobRemovable TruthValue,
    hwobReplaceable TruthValue,
    hwobSerialNumber DisplayString,
    hwobSKU DisplayString,
    hwobStatus INTEGER,
    hwobTag DisplayString,
    hwobVersion DisplayString
}

hwobIndex OBJECT-TYPE
    SYNTAX     Integer32 (1..2147483647)
    MAX-ACCESS read-only
    STATUS     current
    DESCRIPTION
        "The value of this object uniquely identifies the
        instance entry for this class."
    ::= { win32OnBoardDeviceEntry 1 }

hwobCaption OBJECT-TYPE
    SYNTAX     DisplayString
    MAX-ACCESS read-only
    STATUS     current
    DESCRIPTION
        "Short description (one-line string) of the object.
        This property is inherited from
        CIM_ManagedSystemElement."
    ::= { win32OnBoardDeviceEntry 2 }

hwobCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_PhysicalElement."
    ::= { win32OnBoardDeviceEntry 3 }

hwobDescription OBJECT-TYPE
    SYNTAX     DisplayString
    MAX-ACCESS read-only
    STATUS     current
    DESCRIPTION
        "Description of the object. This property is
        inherited from CIM_ManagedSystemElement."
    ::= { win32OnBoardDeviceEntry 4 }

hwobDeviceType OBJECT-TYPE
    SYNTAX     INTEGER {
        other(1),
        unknown(2),
        video(3),
        scsiController(4),
        ethernet(5),
        tokenRing(6),
        sound(7)
    }
    MAX-ACCESS read-only
    STATUS     current
    DESCRIPTION
        "Type of device being represented."
    ::= { win32OnBoardDeviceEntry 5 }

hwobEnabled OBJECT-TYPE
    SYNTAX     TruthValue
    MAX-ACCESS read-only
    STATUS     current
    DESCRIPTION
        "If TRUE, the on-board device is available for use.
        "
    ::= { win32OnBoardDeviceEntry 6 }

hwobHotSwappable OBJECT-TYPE
    SYNTAX     TruthValue
    MAX-ACCESS read-only
    STATUS     current
    DESCRIPTION
        "If TRUE, a physical package can be hot-swapped (if
        it is possible to replace the element with a
        physically different but equivalent one while the
        containing package has power applied to it). For
        example, a disk drive package inserted using SCA
        connectors is removable and can be hot-swapped. All
        packages that can be hot-swapped are inherently
        removable and replaceable. This property is
        inherited from CIM_PhysicalComponent."
    ::= { win32OnBoardDeviceEntry 7 }

hwobInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32OnBoardDeviceEntry 8 }

hwobManufacturer OBJECT-TYPE
    SYNTAX     DisplayString
    MAX-ACCESS read-only
    STATUS     current
    DESCRIPTION
        "Name of the organization responsible for producing
        the physical element. This property is inherited
        from CIM_PhysicalElement."
    ::= { win32OnBoardDeviceEntry 9 }

hwobModel OBJECT-TYPE
    SYNTAX     DisplayString
    MAX-ACCESS read-only
    STATUS     current
    DESCRIPTION
        "Name by which the physical element is generally
        known. This property is inherited from
        CIM_PhysicalElement."
    ::= { win32OnBoardDeviceEntry 10 }

hwobName OBJECT-TYPE
    SYNTAX     DisplayString
    MAX-ACCESS read-only
    STATUS     current
    DESCRIPTION
        "Label by which the object is known. When
        subclassed, the property can be overridden to be a
        key property. This property is inherited from
        CIM_ManagedSystemElement."
    ::= { win32OnBoardDeviceEntry 11 }

hwobOtherIdentifyingInfo OBJECT-TYPE
    SYNTAX     DisplayString
    MAX-ACCESS read-only
    STATUS     current
    DESCRIPTION
        "Additional data, beyond asset tag information,
        that could be used to identify a physical element.
        One example is bar code data associated with an
        element that also has an asset tag. Note that if
        only bar code data is available and is unique/able
        to be used as an element key, this property would
        be NULL and the bar code data used as the class
        key, in the tag property. This property is
        inherited from CIM_PhysicalElement."
    ::= { win32OnBoardDeviceEntry 12 }

hwobPartNumber OBJECT-TYPE
    SYNTAX     DisplayString
    MAX-ACCESS read-only
    STATUS     current
    DESCRIPTION
        "Part number assigned by the organization
        responsible for producing or manufacturing the
        physical element. This property is inherited from
        CIM_PhysicalElement."
    ::= { win32OnBoardDeviceEntry 13 }

hwobPoweredOn OBJECT-TYPE
    SYNTAX     TruthValue
    MAX-ACCESS read-only
    STATUS     current
    DESCRIPTION
        "If TRUE, the physical element is powered on. This
        property is inherited from CIM_PhysicalElement."
    ::= { win32OnBoardDeviceEntry 14 }

hwobRemovable OBJECT-TYPE
    SYNTAX     TruthValue
    MAX-ACCESS read-only
    STATUS     current
    DESCRIPTION
        "If TRUE, a physical package is removable (if it is
        designed to be taken in and out of the physical
        container in which it is normally found, without
        impairing the function of the overall packaging). A
        package can still be removable if power must be
        'off' to perform the removal. If power can be 'on'
        and the package removed, then the element is
        removable and can be hot-swapped. For example, an
        extra battery in a laptop is removable, as is a
        disk drive package inserted using SCA connectors.
        However, the latter can be hot-swapped. A laptop's
        display is not removable, nor is a non-redundant
        power supply. Removing these components would
        affect the function of the overall packaging or is
        impossible due to the tight integration of the
        package. This property is inherited from
        CIM_PhysicalComponent."
    ::= { win32OnBoardDeviceEntry 15 }

hwobReplaceable OBJECT-TYPE
    SYNTAX     TruthValue
    MAX-ACCESS read-only
    STATUS     current
    DESCRIPTION
        "If TRUE, a physical package is replaceable (if it
        is possible to replace, FRU or upgrade, the element
        with a physically different one). For example, some
        computer systems allow the main processor chip to
        be upgraded to one of a higher clock rating. In
        this case, the processor is said to be replaceable.
        Another example is a power supply package mounted
        on sliding rails. All removable packages are
        inherently replaceable. This property is inherited
        from CIM_PhysicalComponent."
    ::= { win32OnBoardDeviceEntry 16 }

hwobSerialNumber OBJECT-TYPE
    SYNTAX     DisplayString
    MAX-ACCESS read-only
    STATUS     current
    DESCRIPTION
        "Manufacturer-allocated number used to identify the
        physical element. This property is inherited from
        CIM_PhysicalElement."
    ::= { win32OnBoardDeviceEntry 17 }

hwobSKU OBJECT-TYPE
    SYNTAX     DisplayString
    MAX-ACCESS read-only
    STATUS     current
    DESCRIPTION
        "Stock-keeping unit number for the physical
        element. This property is inherited from
        CIM_PhysicalElement."
    ::= { win32OnBoardDeviceEntry 18 }

hwobStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32OnBoardDeviceEntry 19 }

hwobTag OBJECT-TYPE
    SYNTAX     DisplayString (SIZE (0..256))
    MAX-ACCESS read-only
    STATUS     current
    DESCRIPTION
        "Unique identifier of the on-board device connected
        to the system. This property is inherited from
        CIM_PhysicalElement.
        Example: 'On Board Device 1'"
    ::= { win32OnBoardDeviceEntry 20 }

hwobVersion OBJECT-TYPE
    SYNTAX     DisplayString
    MAX-ACCESS read-only
    STATUS     current
    DESCRIPTION
        "Version of the physical element. This property is
        inherited from CIM_PhysicalElement."
    ::= { win32OnBoardDeviceEntry 21 }

win32ParallelPortTable OBJECT-TYPE
    SYNTAX     SEQUENCE OF Win32ParallelPortEntry
    MAX-ACCESS not-accessible
    STATUS     current
    DESCRIPTION
        "The Win32_ParallelPort WMI class represents the
        properties of a parallel port on a Windows computer
        system."
    ::= { wmiMotherboardControllerPort 16 }

win32ParallelPortEntry OBJECT-TYPE
    SYNTAX     Win32ParallelPortEntry
    MAX-ACCESS not-accessible
    STATUS     current
    DESCRIPTION
        "None"
    INDEX      { hwppIndex }
    ::= { win32ParallelPortTable 1 }

Win32ParallelPortEntry ::= SEQUENCE {
    hwppIndex Integer32,
    hwppAvailability INTEGER,
    hwppCapabilities DisplayString,
    hwppCapabilityDescriptions DisplayString,
    hwppCaption DisplayString,
    hwppConfigManagerErrorCode INTEGER,
    hwppConfigManagerUserConfig TruthValue,
    hwppCreationClassName DisplayString,
    hwppDescription DisplayString,
    hwppDeviceID DisplayString,
    hwppDMASupport TruthValue,
    hwppErrorCleared TruthValue,
    hwppErrorDescription DisplayString,
    hwppInstallDate DateAndTime,
    hwppLastErrorCode Gauge32,
    hwppMaxNumberControlled Gauge32,
    hwppName DisplayString,
    hwppOSAutoDiscovered TruthValue,
    hwppPNPDeviceID DisplayString,
    hwppPowerManagementCapabilities DisplayString,
    hwppPowerManagementSupported TruthValue,
    hwppProtocolSupported INTEGER,
    hwppStatus INTEGER,
    hwppStatusInfo INTEGER,
    hwppSystemCreationClassName DisplayString,
    hwppSystemName DisplayString,
    hwppTimeOfLastReset DateAndTime
}

hwppIndex OBJECT-TYPE
    SYNTAX     Integer32 (1..2147483647)
    MAX-ACCESS read-only
    STATUS     current
    DESCRIPTION
        "The value of this object uniquely identifies the
        instance entry for this class."
    ::= { win32ParallelPortEntry 1 }

hwppAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32ParallelPortEntry 2 }

hwppCapabilities OBJECT-TYPE
    SYNTAX     DisplayString
    MAX-ACCESS read-only
    STATUS     current
    DESCRIPTION
        "Array of the capabilities of the parallel
        controller. This property is inherited from
        CIM_ParallelController.
        Value (dec/hex) Meaning 
        1
        0x1 Unknown 
        2
        0x2 Other 
        3
        0x3 XT/AT Compatible 
        4
        0x4 PS/2 Compatible 
        5
        0x5 ECP 
        6
        0x6 EPP 
        7
        0x7 PC-98 
        8
        0x8 PC-98-Hireso 
        9
        0x9 PC-H98 "
    ::= { win32ParallelPortEntry 3 }

hwppCapabilityDescriptions OBJECT-TYPE
    SYNTAX     DisplayString
    MAX-ACCESS read-only
    STATUS     current
    DESCRIPTION
        "Array of more detailed explanations for any of the
        parallel controller features indicated in the
        Capabilities array. Each entry of this array is
        related to the entry in the Capabilities array that
        is located at the same index. This property is
        inherited from CIM_ParallelController."
    ::= { win32ParallelPortEntry 4 }

hwppCaption OBJECT-TYPE
    SYNTAX     DisplayString
    MAX-ACCESS read-only
    STATUS     current
    DESCRIPTION
        "Short description of the object a one-line string.
        This property is inherited from
        CIM_ManagedSystemElement."
    ::= { win32ParallelPortEntry 5 }

hwppConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32ParallelPortEntry 6 }

hwppConfigManagerUserConfig OBJECT-TYPE
    SYNTAX     TruthValue
    MAX-ACCESS read-only
    STATUS     current
    DESCRIPTION
        "If TRUE, the device is using a user-defined
        configuration. This property is inherited from
        CIM_LogicalDevice."
    ::= { win32ParallelPortEntry 7 }

hwppCreationClassName OBJECT-TYPE
    SYNTAX     DisplayString
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32ParallelPortEntry 8 }

hwppDescription OBJECT-TYPE
    SYNTAX     DisplayString
    MAX-ACCESS read-only
    STATUS     current
    DESCRIPTION
        "Description of the object. This property is
        inherited from CIM_ManagedSystemElement."
    ::= { win32ParallelPortEntry 9 }

hwppDeviceID OBJECT-TYPE
    SYNTAX     DisplayString
    MAX-ACCESS read-only
    STATUS     current
    DESCRIPTION
        "Identifier of the parallel port. This property is
        inherited from CIM_LogicalDevice."
    ::= { win32ParallelPortEntry 10 }

hwppDMASupport OBJECT-TYPE
    SYNTAX     TruthValue
    MAX-ACCESS read-only
    STATUS     current
    DESCRIPTION
        "If TRUE, the parallel port supports DMA. This
        property is inherited from CIM_ParallelController."
    ::= { win32ParallelPortEntry 11 }

hwppErrorCleared OBJECT-TYPE
    SYNTAX     TruthValue
    MAX-ACCESS read-only
    STATUS     current
    DESCRIPTION
        "If TRUE, the error reported in LastErrorCode is
        cleared. This property is inherited from
        CIM_LogicalDevice."
    ::= { win32ParallelPortEntry 12 }

hwppErrorDescription OBJECT-TYPE
    SYNTAX     DisplayString
    MAX-ACCESS read-only
    STATUS     current
    DESCRIPTION
        "More information about the error recorded in
        LastErrorCode, and information about corrective
        actions that might be taken. This property is
        inherited from CIM_LogicalDevice."
    ::= { win32ParallelPortEntry 13 }

hwppInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32ParallelPortEntry 14 }

hwppLastErrorCode OBJECT-TYPE
    SYNTAX     Gauge32
    MAX-ACCESS read-only
    STATUS     current
    DESCRIPTION
        "Last error code reported by the logical device.
        This property is inherited from CIM_LogicalDevice."
    ::= { win32ParallelPortEntry 15 }

hwppMaxNumberControlled OBJECT-TYPE
    SYNTAX     Gauge32
    MAX-ACCESS read-only
    STATUS     current
    DESCRIPTION
        "Maximum number of directly addressable entities
        supportable by this controller. A value of 0 (zero)
        should be used if the number is unknown. This
        property is inherited from CIM_Controller."
    ::= { win32ParallelPortEntry 16 }

hwppName OBJECT-TYPE
    SYNTAX     DisplayString
    MAX-ACCESS read-only
    STATUS     current
    DESCRIPTION
        "Label by which the object is known. When
        subclassed, the property can be overridden to be a
        key property. This property is inherited from
        CIM_ManagedSystemElement."
    ::= { win32ParallelPortEntry 17 }

hwppOSAutoDiscovered OBJECT-TYPE
    SYNTAX     TruthValue
    MAX-ACCESS read-only
    STATUS     current
    DESCRIPTION
        "If TRUE, the parallel port was automatically
        detected by the operating system. If FALSE, the
        port was detected by other means (such as being
        manually added through the Control Panel)."
    ::= { win32ParallelPortEntry 18 }

hwppPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32ParallelPortEntry 19 }

hwppPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value (dec/hex) Meaning 
        0
        0x0 Unknown 
        1
        0x1 Not Supported 
        2
        0x2 Disabled 
        3
        0x3 Enabled 
        4
        0x4 Power Saving Modes Entered Automatically 
        5
        0x5 Power State Settable 
        6
        0x6 Power Cycling Supported 
        7
        0x7 Timed Power On Supported "
    ::= { win32ParallelPortEntry 20 }

hwppPowerManagementSupported OBJECT-TYPE
    SYNTAX     TruthValue
    MAX-ACCESS read-only
    STATUS     current
    DESCRIPTION
        "If TRUE, the device can be power-managed, which
        means that it can be put into suspend mode, and so
        on. The property does not indicate that power
        management features are currently enabled, only
        that the logical device is capable of power
        management. This property is inherited from
        CIM_LogicalDevice."
    ::= { win32ParallelPortEntry 21 }

hwppProtocolSupported OBJECT-TYPE
    SYNTAX     INTEGER {
        other(1),
        unknown(2),
        eisa(3),
        isa(4),
        pci(5),
        ataATAPI(6),
        flexibleDiskette(7),
        n1496(8),
        scsiParallelInterface(9),
        scsiFibreChannelProtocol(10),
        scsiSerialBusProtocol(11),
        scsiSerialBusProtocol1394(12),
        scsiSerialStorageArchitecture(13),
        vesa(14),
        pcmcia(15),
        universalSerialBus(16),
        parallelProtocol(17),
        escon(18),
        diagnostic(19),
        i2C(20),
        power(21),
        hippi(22),
        multiBus(23),
        vme(24),
        ipi(25),
        ieee488(26),
        rs232(27),
        ieee802310BASE5(28),
        ieee802310BASE2(29),
        ieee80231BASES(30),
        ieee802310BROAD36(31),
        ieee8023100BASEVG(32),
        ieee8025TokenRing(33),
        ansiX3T95FDDI(34),
        mca(35),
        esdi(36),
        ide(37),
        cmd(38),
        st506(39),
        dssi(40),
        qic2(41),
        enhancedATAIDE(42),
        agp(43),
        twowayInfrared(44),
        fastInfrared(45),
        serialInfrared(46),
        irBus(47)
    }
    MAX-ACCESS read-only
    STATUS     current
    DESCRIPTION
        "Protocol used by the controller to access
        controlled devices. This property is inherited from
        CIM_Controller."
    ::= { win32ParallelPortEntry 22 }

hwppStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32ParallelPortEntry 23 }

hwppStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32ParallelPortEntry 24 }

hwppSystemCreationClassName OBJECT-TYPE
    SYNTAX     DisplayString
    MAX-ACCESS read-only
    STATUS     current
    DESCRIPTION
        "Value of the scoping computer's CreationClassName
        property. This property is inherited from
        CIM_LogicalDevice."
    ::= { win32ParallelPortEntry 25 }

hwppSystemName OBJECT-TYPE
    SYNTAX     DisplayString
    MAX-ACCESS read-only
    STATUS     current
    DESCRIPTION
        "Name of the scoping system. This property is
        inherited from CIM_LogicalDevice."
    ::= { win32ParallelPortEntry 26 }

hwppTimeOfLastReset OBJECT-TYPE
    SYNTAX     DateAndTime
    MAX-ACCESS read-only
    STATUS     current
    DESCRIPTION
        "Date and time the controller was last reset. This
        could mean the controller was powered down, or
        reinitialized. This property is inherited from
        CIM_Controller."
    ::= { win32ParallelPortEntry 27 }

win32PCMCIAControllerTable OBJECT-TYPE
    SYNTAX     SEQUENCE OF Win32PCMCIAControllerEntry
    MAX-ACCESS not-accessible
    STATUS     current
    DESCRIPTION
        "The Win32_PCMCIAController WMI class manages the
        capabilities of a Personal Computer Memory Card
        Interface Adapter (PCMCIA of PC card) controller
        device."
    ::= { wmiMotherboardControllerPort 17 }

win32PCMCIAControllerEntry OBJECT-TYPE
    SYNTAX     Win32PCMCIAControllerEntry
    MAX-ACCESS not-accessible
    STATUS     current
    DESCRIPTION
        "None"
    INDEX      { hwpcmIndex }
    ::= { win32PCMCIAControllerTable 1 }

Win32PCMCIAControllerEntry ::= SEQUENCE {
    hwpcmIndex Integer32,
    hwpcmAvailability INTEGER,
    hwpcmCaption DisplayString,
    hwpcmConfigManagerErrorCode INTEGER,
    hwpcmConfigManagerUserConfig TruthValue,
    hwpcmCreationClassName DisplayString,
    hwpcmDescription DisplayString,
    hwpcmDeviceID DisplayString,
    hwpcmErrorCleared TruthValue,
    hwpcmErrorDescription DisplayString,
    hwpcmInstallDate DateAndTime,
    hwpcmLastErrorCode Gauge32,
    hwpcmManufacturer DisplayString,
    hwpcmMaxNumberControlled Gauge32,
    hwpcmName DisplayString,
    hwpcmPNPDeviceID DisplayString,
    hwpcmPowerManagementCapabilities DisplayString,
    hwpcmPowerManagementSupported TruthValue,
    hwpcmProtocolSupported INTEGER,
    hwpcmStatus INTEGER,
    hwpcmStatusInfo INTEGER,
    hwpcmSystemCreationClassName DisplayString,
    hwpcmSystemName DisplayString,
    hwpcmTimeOfLastReset DateAndTime
}

hwpcmIndex OBJECT-TYPE
    SYNTAX     Integer32 (1..2147483647)
    MAX-ACCESS read-only
    STATUS     current
    DESCRIPTION
        "The value of this object uniquely identifies the
        instance entry for this class."
    ::= { win32PCMCIAControllerEntry 1 }

hwpcmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32PCMCIAControllerEntry 2 }

hwpcmCaption OBJECT-TYPE
    SYNTAX     DisplayString
    MAX-ACCESS read-only
    STATUS     current
    DESCRIPTION
        "Short description (one-line string) of the object.
        This property is inherited from
        CIM_ManagedSystemElement."
    ::= { win32PCMCIAControllerEntry 3 }

hwpcmConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32PCMCIAControllerEntry 4 }

hwpcmConfigManagerUserConfig OBJECT-TYPE
    SYNTAX     TruthValue
    MAX-ACCESS read-only
    STATUS     current
    DESCRIPTION
        "If TRUE, the device is using a user-defined
        configuration. This property is inherited from
        CIM_LogicalDevice."
    ::= { win32PCMCIAControllerEntry 5 }

hwpcmCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32PCMCIAControllerEntry 6 }

hwpcmDescription OBJECT-TYPE
    SYNTAX     DisplayString
    MAX-ACCESS read-only
    STATUS     current
    DESCRIPTION
        "Description of the object. This property is
        inherited from CIM_ManagedSystemElement."
    ::= { win32PCMCIAControllerEntry 7 }

hwpcmDeviceID OBJECT-TYPE
    SYNTAX     DisplayString
    MAX-ACCESS read-only
    STATUS     current
    DESCRIPTION
        "Unique identifier of this device with other
        peripherals using the Plug and Play BIOS. This
        property is derived from CIM_LogicalDevice."
    ::= { win32PCMCIAControllerEntry 8 }

hwpcmErrorCleared OBJECT-TYPE
    SYNTAX     TruthValue
    MAX-ACCESS read-only
    STATUS     current
    DESCRIPTION
        "If TRUE, the error reported in LastErrorCode is
        now cleared. This property is inherited from
        CIM_LogicalDevice."
    ::= { win32PCMCIAControllerEntry 9 }

hwpcmErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32PCMCIAControllerEntry 10 }

hwpcmInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32PCMCIAControllerEntry 11 }

hwpcmLastErrorCode OBJECT-TYPE
    SYNTAX     Gauge32
    MAX-ACCESS read-only
    STATUS     current
    DESCRIPTION
        "Last error code reported by the logical device.
        This property is inherited from CIM_LogicalDevice."
    ::= { win32PCMCIAControllerEntry 12 }

hwpcmManufacturer OBJECT-TYPE
    SYNTAX     DisplayString
    MAX-ACCESS read-only
    STATUS     current
    DESCRIPTION
        "Name of the PCMCIA controller manufacturer. This
        property is inherited from CIM_PCMCIAController.
        Example: 'Acme'"
    ::= { win32PCMCIAControllerEntry 13 }

hwpcmMaxNumberControlled OBJECT-TYPE
    SYNTAX     Gauge32
    MAX-ACCESS read-only
    STATUS     current
    DESCRIPTION
        "Maximum number of directly addressable entities
        supportable by this controller. A value of 0 should
        be used if the number is unknown. This property is
        inherited from CIM_Controller."
    ::= { win32PCMCIAControllerEntry 14 }

hwpcmName OBJECT-TYPE
    SYNTAX     DisplayString
    MAX-ACCESS read-only
    STATUS     current
    DESCRIPTION
        "Label by which the object is known. When
        subclassed, the property can be overridden to be a
        key property. This property is inherited from
        CIM_ManagedSystemElement."
    ::= { win32PCMCIAControllerEntry 15 }

hwpcmPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32PCMCIAControllerEntry 16 }

hwpcmPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32PCMCIAControllerEntry 17 }

hwpcmPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32PCMCIAControllerEntry 18 }

hwpcmProtocolSupported OBJECT-TYPE
    SYNTAX     INTEGER {
        other(1),
        unknown(2),
        eisa(3),
        isa(4),
        pci(5),
        ataATAPI(6),
        flexibleDiskette(7),
        n1496(8),
        scsiParallelInterface(9),
        scsiFibreChannelProtocol(10),
        scsiSerialBusProtocol(11),
        scsiSerialBusProtocol1394(12),
        scsiSerialStorageArchitecture(13),
        vesa(14),
        pcmcia(15),
        universalSerialBus(16),
        parallelProtocol(17),
        escon(18),
        diagnostic(19),
        i2C(20),
        power(21),
        hippi(22),
        multiBus(23),
        vme(24),
        ipi(25),
        ieee488(26),
        rs232(27),
        ieee802310BASE5(28),
        ieee802310BASE2(29),
        ieee80231BASE5(30),
        ieee802310BROAD36(31),
        ieee8023100BASEVG(32),
        ieee8025TokenRing(33),
        ansiX3T95FDDI(34),
        mca(35),
        esdi(36),
        ide(37),
        cmd(38),
        st506(39),
        dssi(40),
        qic2(41),
        enhancedATAIDE(42),
        agp(43),
        twoWayInfrared(44),
        fastInfrared(45),
        serialInfrared(46),
        irBus(47)
    }
    MAX-ACCESS read-only
    STATUS     current
    DESCRIPTION
        "Protocol used by the controller to access
        'controlled' devices. This property is inherited
        from CIM_Controller."
    ::= { win32PCMCIAControllerEntry 19 }

hwpcmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PCMCIAControllerEntry 20 }

hwpcmStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32PCMCIAControllerEntry 21 }

hwpcmSystemCreationClassName OBJECT-TYPE
    SYNTAX     DisplayString
    MAX-ACCESS read-only
    STATUS     current
    DESCRIPTION
        "Value of the scoping computer's CreationClassName
        property. This property is inherited from
        CIM_LogicalDevice."
    ::= { win32PCMCIAControllerEntry 22 }

hwpcmSystemName OBJECT-TYPE
    SYNTAX     DisplayString
    MAX-ACCESS read-only
    STATUS     current
    DESCRIPTION
        "Name of the scoping system. This property is
        inherited from CIM_LogicalDevice."
    ::= { win32PCMCIAControllerEntry 23 }

hwpcmTimeOfLastReset OBJECT-TYPE
    SYNTAX     DateAndTime
    MAX-ACCESS read-only
    STATUS     current
    DESCRIPTION
        "Date and time the controller was last reset. This
        could mean the controller was powered down, or
        reinitialized. This property is inherited from
        CIM_Controller."
    ::= { win32PCMCIAControllerEntry 24 }

win32PhysicalMemoryTable OBJECT-TYPE
    SYNTAX     SEQUENCE OF Win32PhysicalMemoryEntry
    MAX-ACCESS not-accessible
    STATUS     current
    DESCRIPTION
        "The Win32_PhysicalMemory WMI class represents a
        physical memory device located on a computer system
        and available to the operating system."
    ::= { wmiMotherboardControllerPort 18 }

win32PhysicalMemoryEntry OBJECT-TYPE
    SYNTAX     Win32PhysicalMemoryEntry
    MAX-ACCESS not-accessible
    STATUS     current
    DESCRIPTION
        "None"
    INDEX      { hwpmmIndex }
    ::= { win32PhysicalMemoryTable 1 }

Win32PhysicalMemoryEntry ::= SEQUENCE {
    hwpmmIndex Integer32,
    hwpmmBankLabel DisplayString,
    hwpmmCapacity Gauge32,
    hwpmmCaption DisplayString,
    hwpmmCreationClassName DisplayString,
    hwpmmDataWidth Integer32,
    hwpmmDescription DisplayString,
    hwpmmDeviceLocator DisplayString,
    hwpmmFormFactor INTEGER,
    hwpmmHotSwappable TruthValue,
    hwpmmInstallDate DateAndTime,
    hwpmmInterleaveDataDepth Integer32,
    hwpmmInterleavePosition INTEGER,
    hwpmmManufacturer DisplayString,
    hwpmmMemoryType INTEGER,
    hwpmmModel DisplayString,
    hwpmmName DisplayString,
    hwpmmOtherIdentifyingInfo DisplayString,
    hwpmmPartNumber DisplayString,
    hwpmmPositionInRow Gauge32,
    hwpmmPoweredOn TruthValue,
    hwpmmRemovable TruthValue,
    hwpmmReplaceable TruthValue,
    hwpmmSerialNumber DisplayString,
    hwpmmSKU DisplayString,
    hwpmmSpeed Gauge32,
    hwpmmStatus INTEGER,
    hwpmmTag DisplayString,
    hwpmmTotalWidth Integer32,
    hwpmmTypeDetail INTEGER,
    hwpmmVersion DisplayString
}

hwpmmIndex OBJECT-TYPE
    SYNTAX     Integer32 (1..2147483647)
    MAX-ACCESS read-only
    STATUS     current
    DESCRIPTION
        "The value of this object uniquely identifies the
        instance entry for this class."
    ::= { win32PhysicalMemoryEntry 1 }

hwpmmBankLabel OBJECT-TYPE
    SYNTAX     DisplayString
    MAX-ACCESS read-only
    STATUS     current
    DESCRIPTION
        "Physically-labeled bank where the memory is
        located. This property is inherited from
        CIM_PhysicalMemory.
        Examples: 'Bank 0', 'Bank A'"
    ::= { win32PhysicalMemoryEntry 2 }

hwpmmCapacity OBJECT-TYPE
    SYNTAX     Gauge32
    MAX-ACCESS read-only
    STATUS     current
    DESCRIPTION
        "Total capacity of the physical memory in bytes.
        This property is inherited from
        CIM_PhysicalMemory."
    ::= { win32PhysicalMemoryEntry 3 }

hwpmmCaption OBJECT-TYPE
    SYNTAX     DisplayString
    MAX-ACCESS read-only
    STATUS     current
    DESCRIPTION
        "Short description of the object a one-line string.
        This property is inherited from
        CIM_ManagedSystemElement."
    ::= { win32PhysicalMemoryEntry 4 }

hwpmmCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_PhysicalElement."
    ::= { win32PhysicalMemoryEntry 5 }

hwpmmDataWidth OBJECT-TYPE
    SYNTAX     Integer32
    MAX-ACCESS read-only
    STATUS     current
    DESCRIPTION
        "Data width of the physical memory in bits. A data
        width of 0 (zero) and a total width of 8 indicates
        that the memory is used solely to provide error
        correction bits. This property is inherited from
        CIM_PhysicalMemory."
    ::= { win32PhysicalMemoryEntry 6 }

hwpmmDescription OBJECT-TYPE
    SYNTAX     DisplayString
    MAX-ACCESS read-only
    STATUS     current
    DESCRIPTION
        "Description of an object. This property is
        inherited from CIM_ManagedSystemElement."
    ::= { win32PhysicalMemoryEntry 7 }

hwpmmDeviceLocator OBJECT-TYPE
    SYNTAX     DisplayString
    MAX-ACCESS read-only
    STATUS     current
    DESCRIPTION
        "Label of the socket or circuit board that holds
        the memory.
        Example: 'SIMM 3'"
    ::= { win32PhysicalMemoryEntry 8 }

hwpmmFormFactor OBJECT-TYPE
    SYNTAX     INTEGER {
        unknown(0),
        other(1),
        sip(2),
        dip(3),
        zip(4),
        soj(5),
        proprietary(6),
        simm(7),
        dimm(8),
        tsop(9),
        pga(10),
        rimm(11),
        sodimm(12),
        srimm(13),
        smd(14),
        ssmp(15),
        qfp(16),
        tqfp(17),
        soic(18),
        lcc(19),
        plcc(20),
        bga(21),
        fpbga(22),
        lga(23)
    }
    MAX-ACCESS read-only
    STATUS     current
    DESCRIPTION
        "Implementation form factor for the chip. This
        property is inherited from CIM_Chip."
    ::= { win32PhysicalMemoryEntry 9 }

hwpmmHotSwappable OBJECT-TYPE
    SYNTAX     TruthValue
    MAX-ACCESS read-only
    STATUS     current
    DESCRIPTION
        "If TRUE, a physical component can be hot-swapped
        if it is possible to replace the element with a
        physically different but equivalent one while the
        containing package has power applied to it, is
        'on'. For example, a fan component may be designed
        to be hot-swapped. All components that can be
        hot-swapped are inherently removable and
        replaceable. This property is inherited from
        CIM_PhysicalComponent."
    ::= { win32PhysicalMemoryEntry 10 }

hwpmmInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32PhysicalMemoryEntry 11 }

hwpmmInterleaveDataDepth OBJECT-TYPE
    SYNTAX     Integer32
    MAX-ACCESS read-only
    STATUS     current
    DESCRIPTION
        "Unsigned 16-bit integer maximum number of
        consecutive rows of data that are accessed in a
        single interleaved transfer from the memory device.
        If the value is 0 (zero), the memory is not
        interleaved."
    ::= { win32PhysicalMemoryEntry 12 }

hwpmmInterleavePosition OBJECT-TYPE
    SYNTAX     INTEGER {
        noninterleaved(0),
        firstPosition(1),
        secondPosition(2)
    }
    MAX-ACCESS read-only
    STATUS     current
    DESCRIPTION
        "Position of the physical memory in an interleave.
        For example, in a 2:1 interleave, a value of '1'
        indicates that the memory is in the 'even'
        position. This property is inherited from
        CIM_PhysicalMemory. "
    ::= { win32PhysicalMemoryEntry 13 }

hwpmmManufacturer OBJECT-TYPE
    SYNTAX     DisplayString
    MAX-ACCESS read-only
    STATUS     current
    DESCRIPTION
        "Name of the organization responsible for producing
        the physical element. This property is inherited
        from CIM_PhysicalElement."
    ::= { win32PhysicalMemoryEntry 14 }

hwpmmMemoryType OBJECT-TYPE
    SYNTAX     INTEGER {
        unknown(0),
        other(1),
        dram(2),
        synchronousDRAM(3),
        cacheDRAM(4),
        edo(5),
        edram(6),
        vram(7),
        sram(8),
        ram(9),
        rom(10),
        flash(11),
        eeprom(12),
        feprom(13),
        eprom(14),
        cdram(15),
        n3DRAM(16),
        sdram(17),
        sgram(18),
        rdram(19),
        ddr(20)
    }
    MAX-ACCESS read-only
    STATUS     current
    DESCRIPTION
        "Type of physical memory. This property is
        inherited from CIM_PhysicalMemory."
    ::= { win32PhysicalMemoryEntry 15 }

hwpmmModel OBJECT-TYPE
    SYNTAX     DisplayString
    MAX-ACCESS read-only
    STATUS     current
    DESCRIPTION
        "Name for the physical element. This property is
        inherited from CIM_PhysicalElement."
    ::= { win32PhysicalMemoryEntry 16 }

hwpmmName OBJECT-TYPE
    SYNTAX     DisplayString
    MAX-ACCESS read-only
    STATUS     current
    DESCRIPTION
        "Label for the object. When subclassed, the
        property can be overridden to be a key property.
        This property is inherited from
        CIM_ManagedSystemElement."
    ::= { win32PhysicalMemoryEntry 17 }

hwpmmOtherIdentifyingInfo OBJECT-TYPE
    SYNTAX     DisplayString
    MAX-ACCESS read-only
    STATUS     current
    DESCRIPTION
        "Additional data, beyond asset tag information,
        that can be used to identify a physical element.
        One example is bar code data associated with an
        element that also has an asset tag. If only bar
        code data is available and unique or able to be
        used as an element key, this property is be NULL
        and the bar code data is used as the class key in
        the tag property. This property is inherited from
        CIM_PhysicalElement."
    ::= { win32PhysicalMemoryEntry 18 }

hwpmmPartNumber OBJECT-TYPE
    SYNTAX     DisplayString
    MAX-ACCESS read-only
    STATUS     current
    DESCRIPTION
        "Part number assigned by the organization
        responsible for producing or manufacturing the
        physical element. This property is inherited from
        CIM_PhysicalElement."
    ::= { win32PhysicalMemoryEntry 19 }

hwpmmPositionInRow OBJECT-TYPE
    SYNTAX     Gauge32
    MAX-ACCESS read-only
    STATUS     current
    DESCRIPTION
        "Position of the physical memory in a row. For
        example, if it takes two 8-bit memory devices to
        form a 16-bit row, then a value of 2 means that
        this memory is the second device 0 (zero) is an
        invalid value for this property. This property is
        inherited from CIM_PhysicalMemory."
    ::= { win32PhysicalMemoryEntry 20 }

hwpmmPoweredOn OBJECT-TYPE
    SYNTAX     TruthValue
    MAX-ACCESS read-only
    STATUS     current
    DESCRIPTION
        "If TRUE, the physical element is powered on. This
        property is inherited from CIM_PhysicalElement."
    ::= { win32PhysicalMemoryEntry 21 }

hwpmmRemovable OBJECT-TYPE
    SYNTAX     TruthValue
    MAX-ACCESS read-only
    STATUS     current
    DESCRIPTION
        "If TRUE, a physical component is removable (if it
        is designed to be taken in and out of the physical
        container in which it is normally found, without
        impairing the function of the overall packaging). A
        component can still be removable if power must be
        'off' in order to perform the removal. If power can
        be 'on' and the component removed, then the element
        is removable and can be hot-swapped. For example,
        an upgradable processor chip is removable. This
        property is inherited from CIM_PhysicalComponent."
    ::= { win32PhysicalMemoryEntry 22 }

hwpmmReplaceable OBJECT-TYPE
    SYNTAX     TruthValue
    MAX-ACCESS read-only
    STATUS     current
    DESCRIPTION
        "If TRUE, a physical component is replaceable (if
        it is possible to replace, FRU or upgrade, the
        element with a physically different one). For
        example, some computer systems allow the main
        processor chip to be upgraded to one of a higher
        clock rating. In this case, the processor is said
        to be replaceable. All removable components are
        inherently replaceable. This property is inherited
        from CIM_PhysicalComponent."
    ::= { win32PhysicalMemoryEntry 23 }

hwpmmSerialNumber OBJECT-TYPE
    SYNTAX     DisplayString
    MAX-ACCESS read-only
    STATUS     current
    DESCRIPTION
        "Manufacturer-allocated number to identify the
        physical element. This property is inherited from
        CIM_PhysicalElement."
    ::= { win32PhysicalMemoryEntry 24 }

hwpmmSKU OBJECT-TYPE
    SYNTAX     DisplayString
    MAX-ACCESS read-only
    STATUS     current
    DESCRIPTION
        "Stock-keeping unit number for the physical
        element. This property is inherited from
        CIM_PhysicalElement."
    ::= { win32PhysicalMemoryEntry 25 }

hwpmmSpeed OBJECT-TYPE
    SYNTAX     Gauge32
    MAX-ACCESS read-only
    STATUS     current
    DESCRIPTION
        "Speed of the physical memory in nanoseconds. This
        property is inherited from CIM_PhysicalMemory."
    ::= { win32PhysicalMemoryEntry 26 }

hwpmmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PhysicalMemoryEntry 27 }

hwpmmTag OBJECT-TYPE
    SYNTAX     DisplayString (SIZE (0..256))
    MAX-ACCESS read-only
    STATUS     current
    DESCRIPTION
        "Unique identifier for the physical memory device
        that is represented by an instance of
        Win32_PhysicalMemory. This property is inherited
        from CIM_PhysicalElement.
        Example: 'Physical Memory 1'"
    ::= { win32PhysicalMemoryEntry 28 }

hwpmmTotalWidth OBJECT-TYPE
    SYNTAX     Integer32
    MAX-ACCESS read-only
    STATUS     current
    DESCRIPTION
        "Total width, in bits, of the physical memory,
        including check or error correction bits. If there
        are no error correction bits, the value in this
        property should match what is specified for the
        DataWidth property. This property is inherited from
        CIM_PhysicalMemory."
    ::= { win32PhysicalMemoryEntry 29 }

hwpmmTypeDetail OBJECT-TYPE
    SYNTAX     INTEGER {
        reserved(1),
        other(2),
        unknown(4),
        fastpaged(8),
        staticColumn(16),
        pseudostatic(32),
        rambus(64),
        synchronous(128),
        cmos(256),
        edo(512),
        windowDRAM(1024),
        cacheDRAM(2048),
        nonvolatile(4096)
    }
    MAX-ACCESS read-only
    STATUS     current
    DESCRIPTION
        "Type of physical memory represented."
    ::= { win32PhysicalMemoryEntry 30 }

hwpmmVersion OBJECT-TYPE
    SYNTAX     DisplayString
    MAX-ACCESS read-only
    STATUS     current
    DESCRIPTION
        "Version of the physical element. This property is
        inherited from CIM_PhysicalElement."
    ::= { win32PhysicalMemoryEntry 31 }

win32PhysicalMemoryArrayTable OBJECT-TYPE
    SYNTAX     SEQUENCE OF Win32PhysicalMemoryArrayEntry
    MAX-ACCESS not-accessible
    STATUS     current
    DESCRIPTION
        "The Win32_PhysicalMemoryArray WMI class represents
        details about the computer system physical memory.
        This includes the number of memory devices, memory
        capacity available, and memory type for example,
        system or video memory."
    ::= { wmiMotherboardControllerPort 19 }

win32PhysicalMemoryArrayEntry OBJECT-TYPE
    SYNTAX     Win32PhysicalMemoryArrayEntry
    MAX-ACCESS not-accessible
    STATUS     current
    DESCRIPTION
        "None"
    INDEX      { hwpmaIndex }
    ::= { win32PhysicalMemoryArrayTable 1 }

Win32PhysicalMemoryArrayEntry ::= SEQUENCE {
    hwpmaIndex Integer32,
    hwpmaCaption DisplayString,
    hwpmaCreationClassName DisplayString,
    hwpmaDepth Integer32,
    hwpmaDescription DisplayString,
    hwpmaHeight Integer32,
    hwpmaHotSwappable TruthValue,
    hwpmaInstallDate DateAndTime,
    hwpmaLocation INTEGER,
    hwpmaManufacturer DisplayString,
    hwpmaMaxCapacity Gauge32,
    hwpmaMemoryDevices Integer32,
    hwpmaMemoryErrorCorrection INTEGER,
    hwpmaModel DisplayString,
    hwpmaName DisplayString,
    hwpmaOtherIdentifyingInfo DisplayString,
    hwpmaPartNumber DisplayString,
    hwpmaPoweredOn TruthValue,
    hwpmaRemovable TruthValue,
    hwpmaReplaceable TruthValue,
    hwpmaSerialNumber DisplayString,
    hwpmaSKU DisplayString,
    hwpmaStatus INTEGER,
    hwpmaTag DisplayString,
    hwpmaUse INTEGER,
    hwpmaVersion DisplayString,
    hwpmaWeight Integer32,
    hwpmaWidth Integer32
}

hwpmaIndex OBJECT-TYPE
    SYNTAX     Integer32 (1..2147483647)
    MAX-ACCESS read-only
    STATUS     current
    DESCRIPTION
        "The value of this object uniquely identifies the
        instance entry for this class."
    ::= { win32PhysicalMemoryArrayEntry 1 }

hwpmaCaption OBJECT-TYPE
    SYNTAX     DisplayString
    MAX-ACCESS read-only
    STATUS     current
    DESCRIPTION
        "Short description of the object a one-line string.
        This property is inherited from
        CIM_ManagedSystemElement."
    ::= { win32PhysicalMemoryArrayEntry 2 }

hwpmaCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_PhysicalElement."
    ::= { win32PhysicalMemoryArrayEntry 3 }

hwpmaDepth OBJECT-TYPE
    SYNTAX     Integer32
    MAX-ACCESS read-only
    STATUS     current
    DESCRIPTION
        "Depth of the physical package in inches. This
        property is inherited from CIM_PhysicalPackage."
    ::= { win32PhysicalMemoryArrayEntry 4 }

hwpmaDescription OBJECT-TYPE
    SYNTAX     DisplayString
    MAX-ACCESS read-only
    STATUS     current
    DESCRIPTION
        "Description of the object. This property is
        inherited from CIM_ManagedSystemElement."
    ::= { win32PhysicalMemoryArrayEntry 5 }

hwpmaHeight OBJECT-TYPE
    SYNTAX     Integer32
    MAX-ACCESS read-only
    STATUS     current
    DESCRIPTION
        "Height of the physical package in inches. This
        property is inherited from CIM_PhysicalPackage."
    ::= { win32PhysicalMemoryArrayEntry 6 }

hwpmaHotSwappable OBJECT-TYPE
    SYNTAX     TruthValue
    MAX-ACCESS read-only
    STATUS     current
    DESCRIPTION
        "If TRUE, a physical package can be hot-swapped (if
        it is possible to replace the element with a
        physically different but equivalent one while the
        containing package has power applied to it, is
        'on'). For example, a disk drive package inserted
        using SCA connectors is removable and can be
        hot-swapped. All packages that can be hot-swapped
        are inherently removable and replaceable. This
        property is inherited from CIM_PhysicalPackage."
    ::= { win32PhysicalMemoryArrayEntry 7 }

hwpmaInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32PhysicalMemoryArrayEntry 8 }

hwpmaLocation OBJECT-TYPE
    SYNTAX     INTEGER {
        reserved(0),
        other(1),
        unknown(2),
        systemBoardOrMotherboard(3),
        isaAddonCard(4),
        eisaAddonCard(5),
        pciAddonCard(6),
        mcaAddonCard(7),
        pcmciaAddonCard(8),
        proprietaryAddonCard(9),
        nuBus(10),
        pc98C20AddonCard(11),
        pc98C24AddonCard(12),
        pc98EAddonCard(13),
        pc98LocalBusAddonCard(14)
    }
    MAX-ACCESS read-only
    STATUS     current
    DESCRIPTION
        "Physical location of the memory array."
    ::= { win32PhysicalMemoryArrayEntry 9 }

hwpmaManufacturer OBJECT-TYPE
    SYNTAX     DisplayString
    MAX-ACCESS read-only
    STATUS     current
    DESCRIPTION
        "Name of the organization responsible for producing
        the physical element. This property is inherited
        from CIM_PhysicalElement."
    ::= { win32PhysicalMemoryArrayEntry 10 }

hwpmaMaxCapacity OBJECT-TYPE
    SYNTAX     Gauge32
    UNITS "Kilobytes"
    MAX-ACCESS read-only
    STATUS     current
    DESCRIPTION
        "Maximum memory size (in bytes) installable for
        this particular memory array. If the size is
        unknown, the property is given a value of 0
        (zero)."
    ::= { win32PhysicalMemoryArrayEntry 11 }

hwpmaMemoryDevices OBJECT-TYPE
    SYNTAX     Integer32
    MAX-ACCESS read-only
    STATUS     current
    DESCRIPTION
        "Number of physical slots or sockets available in
        this memory array."
    ::= { win32PhysicalMemoryArrayEntry 12 }

hwpmaMemoryErrorCorrection OBJECT-TYPE
    SYNTAX     INTEGER {
        reserved(0),
        other(1),
        unknown(2),
        none(3),
        parity(4),
        singlebitECC(5),
        multibitECC(6),
        crc(7)
    }
    MAX-ACCESS read-only
    STATUS     current
    DESCRIPTION
        "Type of error correction used by the memory
        array."
    ::= { win32PhysicalMemoryArrayEntry 13 }

hwpmaModel OBJECT-TYPE
    SYNTAX     DisplayString
    MAX-ACCESS read-only
    STATUS     current
    DESCRIPTION
        "Name by which the physical element is generally
        known. This property is inherited from
        CIM_PhysicalElement."
    ::= { win32PhysicalMemoryArrayEntry 14 }

hwpmaName OBJECT-TYPE
    SYNTAX     DisplayString
    MAX-ACCESS read-only
    STATUS     current
    DESCRIPTION
        "Label by which the object is known. When
        subclassed, the property can be overridden to be a
        key property. This property is inherited from
        CIM_ManagedSystemElement."
    ::= { win32PhysicalMemoryArrayEntry 15 }

hwpmaOtherIdentifyingInfo OBJECT-TYPE
    SYNTAX     DisplayString
    MAX-ACCESS read-only
    STATUS     current
    DESCRIPTION
        "Additional data, beyond asset tag information,
        that could be used to identify a physical element.
        One example is bar code data associated with an
        element that also has an asset tag. Note that if
        only bar code data is available and is unique/able
        to be used as an element key, this property would
        be NULL and the bar code data used as the class
        key, in the tag property. This property is
        inherited from CIM_PhysicalElement."
    ::= { win32PhysicalMemoryArrayEntry 16 }

hwpmaPartNumber OBJECT-TYPE
    SYNTAX     DisplayString
    MAX-ACCESS read-only
    STATUS     current
    DESCRIPTION
        "Part number assigned by the organization
        responsible for producing or manufacturing the
        physical element. This property is inherited from
        CIM_PhysicalElement."
    ::= { win32PhysicalMemoryArrayEntry 17 }

hwpmaPoweredOn OBJECT-TYPE
    SYNTAX     TruthValue
    MAX-ACCESS read-only
    STATUS     current
    DESCRIPTION
        "If TRUE, the physical element is powered on. This
        property is inherited from CIM_PhysicalElement."
    ::= { win32PhysicalMemoryArrayEntry 18 }

hwpmaRemovable OBJECT-TYPE
    SYNTAX     TruthValue
    MAX-ACCESS read-only
    STATUS     current
    DESCRIPTION
        "If TRUE, a physical package is removable (if it is
        designed to be taken in and out of the physical
        container in which it is normally found, without
        impairing the function of the overall packaging). A
        package can still be removable if power must be
        'off' in order to perform the removal. If power can
        be 'on' and the package removed, then the element
        is removable and can be hot-swapped. For example,
        an extra battery in a laptop is removable, as is a
        disk drive package inserted using SCA connectors.
        However, the latter can be hot-swapped. A laptop's
        display is not removable, nor is a non-redundant
        power supply. Removing these components would
        affect the function of the overall packaging or is
        impossible due to the tight integration of the
        package. This property is inherited from
        CIM_PhysicalPackage."
    ::= { win32PhysicalMemoryArrayEntry 19 }

hwpmaReplaceable OBJECT-TYPE
    SYNTAX     TruthValue
    MAX-ACCESS read-only
    STATUS     current
    DESCRIPTION
        "If TRUE, a physical package is replaceable (if it
        is possible to replace, FRU or upgrade, the element
        with a physically different one). For example, some
        computer systems allow the main processor chip to
        be upgraded to one of a higher clock rating. In
        this case, the processor is said to be replaceable.
        Another example is a power supply package mounted
        on sliding rails. All removable packages are
        inherently replaceable. This property is inherited
        from CIM_PhysicalPackage."
    ::= { win32PhysicalMemoryArrayEntry 20 }

hwpmaSerialNumber OBJECT-TYPE
    SYNTAX     DisplayString
    MAX-ACCESS read-only
    STATUS     current
    DESCRIPTION
        "Manufacturer-allocated number used to identify the
        physical element. This property is inherited from
        CIM_PhysicalElement."
    ::= { win32PhysicalMemoryArrayEntry 21 }

hwpmaSKU OBJECT-TYPE
    SYNTAX     DisplayString
    MAX-ACCESS read-only
    STATUS     current
    DESCRIPTION
        "Stockkeeping unit number for the physical element.
        This property is inherited from
        CIM_PhysicalElement."
    ::= { win32PhysicalMemoryArrayEntry 22 }

hwpmaStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement"
    ::= { win32PhysicalMemoryArrayEntry 23 }

hwpmaTag OBJECT-TYPE
    SYNTAX     DisplayString (SIZE (0..256))
    MAX-ACCESS read-only
    STATUS     current
    DESCRIPTION
        "Unique identifier of the physical memory array.
        This property is inherited from
        CIM_PhysicalElement.
        Example: 'Physical Memory Array 1'"
    ::= { win32PhysicalMemoryArrayEntry 24 }

hwpmaUse OBJECT-TYPE
    SYNTAX     INTEGER {
        reserved(0),
        other(1),
        unknown(2),
        systemMemory(3),
        videoMemory(4),
        flashMemory(5),
        nonvolatileRAM(6),
        cacheMemory(7)
    }
    MAX-ACCESS read-only
    STATUS     current
    DESCRIPTION
        "How memory is used in the computer system."
    ::= { win32PhysicalMemoryArrayEntry 25 }

hwpmaVersion OBJECT-TYPE
    SYNTAX     DisplayString
    MAX-ACCESS read-only
    STATUS     current
    DESCRIPTION
        "Version of the physical element. This property is
        inherited from CIM_PhysicalElement."
    ::= { win32PhysicalMemoryArrayEntry 26 }

hwpmaWeight OBJECT-TYPE
    SYNTAX     Integer32
    MAX-ACCESS read-only
    STATUS     current
    DESCRIPTION
        "Weight of the physical package in pounds. This
        property is inherited from CIM_PhysicalPackage."
    ::= { win32PhysicalMemoryArrayEntry 27 }

hwpmaWidth OBJECT-TYPE
    SYNTAX     Integer32
    MAX-ACCESS read-only
    STATUS     current
    DESCRIPTION
        "Width of the physical package in inches. This
        property is inherited from CIM_PhysicalPackage."
    ::= { win32PhysicalMemoryArrayEntry 28 }

win32PnPEntityTable OBJECT-TYPE
    SYNTAX     SEQUENCE OF Win32PnPEntityEntry
    MAX-ACCESS not-accessible
    STATUS     current
    DESCRIPTION
        "The Win32_PnPEntity WMI class represents the
        properties of a Plug and Play device. Plug and Play
        entities are shown as entries in the Device Manager
        located in Control Panel."
    ::= { wmiMotherboardControllerPort 20 }

win32PnPEntityEntry OBJECT-TYPE
    SYNTAX     Win32PnPEntityEntry
    MAX-ACCESS not-accessible
    STATUS     current
    DESCRIPTION
        "None"
    INDEX      { hwpnpIndex }
    ::= { win32PnPEntityTable 1 }

Win32PnPEntityEntry ::= SEQUENCE {
    hwpnpIndex Integer32,
    hwpnpAvailability INTEGER,
    hwpnpCaption DisplayString,
    hwpnpClassGuid DisplayString,
    hwpnpConfigManagerErrorCode INTEGER,
    hwpnpConfigManagerUserConfig TruthValue,
    hwpnpCreationClassName DisplayString,
    hwpnpDescription DisplayString,
    hwpnpDeviceID DisplayString,
    hwpnpErrorCleared TruthValue,
    hwpnpErrorDescription DisplayString,
    hwpnpInstallDate DateAndTime,
    hwpnpLastErrorCode Gauge32,
    hwpnpManufacturer DisplayString,
    hwpnpName DisplayString,
    hwpnpPNPDeviceID DisplayString,
    hwpnpPowerManagementCapabilities DisplayString,
    hwpnpPowerManagementSupported TruthValue,
    hwpnpService DisplayString,
    hwpnpStatus INTEGER,
    hwpnpStatusInfo INTEGER,
    hwpnpSystemCreationClassName DisplayString,
    hwpnpSystemName DisplayString
}

hwpnpIndex OBJECT-TYPE
    SYNTAX     Integer32 (1..2147483647)
    MAX-ACCESS read-only
    STATUS     current
    DESCRIPTION
        "The value of this object uniquely identifies the
        instance entry for this class."
    ::= { win32PnPEntityEntry 1 }

hwpnpAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32PnPEntityEntry 2 }

hwpnpCaption OBJECT-TYPE
    SYNTAX     DisplayString
    MAX-ACCESS read-only
    STATUS     current
    DESCRIPTION
        "Short description (one-line string) of the object.
        This property is inherited from
        CIM_ManagedSystemElement."
    ::= { win32PnPEntityEntry 3 }

hwpnpClassGuid OBJECT-TYPE
    SYNTAX     DisplayString
    MAX-ACCESS read-only
    STATUS     current
    DESCRIPTION
        "Globally unique identifier (GUID) of this Plug and
        Play device."
    ::= { win32PnPEntityEntry 4 }

hwpnpConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32PnPEntityEntry 5 }

hwpnpConfigManagerUserConfig OBJECT-TYPE
    SYNTAX     TruthValue
    MAX-ACCESS read-only
    STATUS     current
    DESCRIPTION
        "If TRUE, the device is using a user-defined
        configuration. This property is inherited from
        CIM_LogicalDevice."
    ::= { win32PnPEntityEntry 6 }

hwpnpCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32PnPEntityEntry 7 }

hwpnpDescription OBJECT-TYPE
    SYNTAX     DisplayString
    MAX-ACCESS read-only
    STATUS     current
    DESCRIPTION
        "Description of the object. This property is
        inherited from CIM_ManagedSystemElement."
    ::= { win32PnPEntityEntry 8 }

hwpnpDeviceID OBJECT-TYPE
    SYNTAX     DisplayString
    MAX-ACCESS read-only
    STATUS     current
    DESCRIPTION
        "Identifier of the Plug and Play device. This
        property is inherited from CIM_LogicalDevice."
    ::= { win32PnPEntityEntry 9 }

hwpnpErrorCleared OBJECT-TYPE
    SYNTAX     TruthValue
    MAX-ACCESS read-only
    STATUS     current
    DESCRIPTION
        "If TRUE, the error reported in LastErrorCode is
        now cleared. This property is inherited from
        CIM_LogicalDevice."
    ::= { win32PnPEntityEntry 10 }

hwpnpErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32PnPEntityEntry 11 }

hwpnpInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32PnPEntityEntry 12 }

hwpnpLastErrorCode OBJECT-TYPE
    SYNTAX     Gauge32
    MAX-ACCESS read-only
    STATUS     current
    DESCRIPTION
        "Last error code reported by the logical device.
        This property is inherited from CIM_LogicalDevice."
    ::= { win32PnPEntityEntry 13 }

hwpnpManufacturer OBJECT-TYPE
    SYNTAX     DisplayString
    MAX-ACCESS read-only
    STATUS     current
    DESCRIPTION
        "Name of the manufacturer of the Plug and Play
        device.
        Example: 'Acme'"
    ::= { win32PnPEntityEntry 14 }

hwpnpName OBJECT-TYPE
    SYNTAX     DisplayString
    MAX-ACCESS read-only
    STATUS     current
    DESCRIPTION
        "Label by which the object is known. When
        subclassed, the property can be overridden to be a
        key property. This property is inherited from
        CIM_ManagedSystemElement."
    ::= { win32PnPEntityEntry 15 }

hwpnpPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32PnPEntityEntry 16 }

hwpnpPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32PnPEntityEntry 17 }

hwpnpPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32PnPEntityEntry 18 }

hwpnpService OBJECT-TYPE
    SYNTAX     DisplayString
    MAX-ACCESS read-only
    STATUS     current
    DESCRIPTION
        "Name of the service that supports this Plug and
        Play device. For more information, see
        Win32_SystemDriverPnPEntity.
        Example: 'atapi'"
    ::= { win32PnPEntityEntry 19 }

hwpnpStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PnPEntityEntry 20 }

hwpnpStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32PnPEntityEntry 21 }

hwpnpSystemCreationClassName OBJECT-TYPE
    SYNTAX     DisplayString
    MAX-ACCESS read-only
    STATUS     current
    DESCRIPTION
        "Value of the scoping computer's CreationClassName
        property. This property is inherited from
        CIM_LogicalDevice."
    ::= { win32PnPEntityEntry 22 }

hwpnpSystemName OBJECT-TYPE
    SYNTAX     DisplayString
    MAX-ACCESS read-only
    STATUS     current
    DESCRIPTION
        "Name of the scoping system. This property is
        inherited from CIM_LogicalDevice."
    ::= { win32PnPEntityEntry 23 }

win32PnPSignedDriverTable OBJECT-TYPE
    SYNTAX     SEQUENCE OF Win32PnPSignedDriverEntry
    MAX-ACCESS not-accessible
    STATUS     current
    DESCRIPTION
        "The Win32_PnPSignedDriver WMI class provides
        digital signature information about drivers."
    ::= { wmiMotherboardControllerPort 21 }

win32PnPSignedDriverEntry OBJECT-TYPE
    SYNTAX     Win32PnPSignedDriverEntry
    MAX-ACCESS not-accessible
    STATUS     current
    DESCRIPTION
        "None"
    INDEX      { hwpsdIndex }
    ::= { win32PnPSignedDriverTable 1 }

Win32PnPSignedDriverEntry ::= SEQUENCE {
    hwpsdIndex Integer32,
    hwpsdClassGuid DisplayString,
    hwpsdCompatID DisplayString,
    hwpsdDescription DisplayString,
    hwpsdDeviceClass DisplayString,
    hwpsdDeviceID DisplayString,
    hwpsdDeviceName DisplayString,
    hwpsdDevLoader DisplayString,
    hwpsdDriverDate DisplayString,
    hwpsdDriverName DisplayString,
    hwpsdDriverVersion DisplayString,
    hwpsdFriendlyName DisplayString,
    hwpsdHardWareID DisplayString,
    hwpsdInfName DisplayString,
    hwpsdInstallDate DateAndTime,
    hwpsdIsSigned TruthValue,
    hwpsdLocation DisplayString,
    hwpsdManufacturer DisplayString,
    hwpsdName DisplayString,
    hwpsdPDO DisplayString,
    hwpsdProviderName DisplayString,
    hwpsdSigner DisplayString,
    hwpsdStarted TruthValue,
    hwpsdStartMode DisplayString,
    hwpsdStatus INTEGER,
    hwpsdSystemCreationClassName DisplayString,
    hwpsdSystemName DisplayString
}

hwpsdIndex OBJECT-TYPE
    SYNTAX     Integer32 (1..2147483647)
    MAX-ACCESS read-only
    STATUS     current
    DESCRIPTION
        "The value of this object uniquely identifies the
        instance entry for this class."
    ::= { win32PnPSignedDriverEntry 1 }

hwpsdClassGuid OBJECT-TYPE
    SYNTAX     DisplayString
    MAX-ACCESS read-only
    STATUS     current
    DESCRIPTION
        "GUID of the device class. Example:
        '{71A27CDD-11D0-BEC7-08002BE2092F}'"
    ::= { win32PnPSignedDriverEntry 2 }

hwpsdCompatID OBJECT-TYPE
    SYNTAX     DisplayString
    MAX-ACCESS read-only
    STATUS     current
    DESCRIPTION
        "Compatibility identifier for the driver. Example:
        'DETECTEDInternal\ftdisk'"
    ::= { win32PnPSignedDriverEntry 3 }

hwpsdDescription OBJECT-TYPE
    SYNTAX     DisplayString
    MAX-ACCESS read-only
    STATUS     current
    DESCRIPTION
        "Description of the driver."
    ::= { win32PnPSignedDriverEntry 4 }

hwpsdDeviceClass OBJECT-TYPE
    SYNTAX     DisplayString
    MAX-ACCESS read-only
    STATUS     current
    DESCRIPTION
        "Device class of the driver. Example: 'SYSTEM'"
    ::= { win32PnPSignedDriverEntry 5 }

hwpsdDeviceID OBJECT-TYPE
    SYNTAX     DisplayString
    MAX-ACCESS read-only
    STATUS     current
    DESCRIPTION
        "Device identifier of the device. Example:
        'ROOT\FTDISK\0000'"
    ::= { win32PnPSignedDriverEntry 6 }

hwpsdDeviceName OBJECT-TYPE
    SYNTAX     DisplayString
    MAX-ACCESS read-only
    STATUS     current
    DESCRIPTION
        "Name of the device."
    ::= { win32PnPSignedDriverEntry 7 }

hwpsdDevLoader OBJECT-TYPE
    SYNTAX     DisplayString
    MAX-ACCESS read-only
    STATUS     current
    DESCRIPTION
        "Device loader for the device."
    ::= { win32PnPSignedDriverEntry 8 }

hwpsdDriverDate OBJECT-TYPE
    SYNTAX     DisplayString
    MAX-ACCESS read-only
    STATUS     current
    DESCRIPTION
        "Build date of the driver (from the manufacturer).
        Example: '1-25-2001'"
    ::= { win32PnPSignedDriverEntry 9 }

hwpsdDriverName OBJECT-TYPE
    SYNTAX     DisplayString
    MAX-ACCESS read-only
    STATUS     current
    DESCRIPTION
        "Name of the driver."
    ::= { win32PnPSignedDriverEntry 10 }

hwpsdDriverVersion OBJECT-TYPE
    SYNTAX     DisplayString
    MAX-ACCESS read-only
    STATUS     current
    DESCRIPTION
        "Version of the driver. Example: '5.1.2427.1'"
    ::= { win32PnPSignedDriverEntry 11 }

hwpsdFriendlyName OBJECT-TYPE
    SYNTAX     DisplayString
    MAX-ACCESS read-only
    STATUS     current
    DESCRIPTION
        "Friendly name of the driver. Example:
        'Communications Port (COM2)'"
    ::= { win32PnPSignedDriverEntry 12 }

hwpsdHardWareID OBJECT-TYPE
    SYNTAX     DisplayString
    MAX-ACCESS read-only
    STATUS     current
    DESCRIPTION
        "Hardware identifier for the driver. Example:
        'ROOT\FTDISK'"
    ::= { win32PnPSignedDriverEntry 13 }

hwpsdInfName OBJECT-TYPE
    SYNTAX     DisplayString
    MAX-ACCESS read-only
    STATUS     current
    DESCRIPTION
        "Name of the .inf file which installed the device.
        Example: 'machine.inf'"
    ::= { win32PnPSignedDriverEntry 14 }

hwpsdInstallDate OBJECT-TYPE
    SYNTAX     DateAndTime
    MAX-ACCESS read-only
    STATUS     current
    DESCRIPTION
        "Date the driver was installed. Lack of value does
        not indicate that the driver is not installed. This
        property is inherited from
        CIM_ManagedSystemElement."
    ::= { win32PnPSignedDriverEntry 15 }

hwpsdIsSigned OBJECT-TYPE
    SYNTAX     TruthValue
    MAX-ACCESS read-only
    STATUS     current
    DESCRIPTION
        "If TRUE, the driver is signed."
    ::= { win32PnPSignedDriverEntry 16 }

hwpsdLocation OBJECT-TYPE
    SYNTAX     DisplayString
    MAX-ACCESS read-only
    STATUS     current
    DESCRIPTION
        "Location of the driver."
    ::= { win32PnPSignedDriverEntry 17 }

hwpsdManufacturer OBJECT-TYPE
    SYNTAX     DisplayString
    MAX-ACCESS read-only
    STATUS     current
    DESCRIPTION
        "Manufacturer of the driver. Example: 'Microsoft'"
    ::= { win32PnPSignedDriverEntry 18 }

hwpsdName OBJECT-TYPE
    SYNTAX     DisplayString
    MAX-ACCESS read-only
    STATUS     current
    DESCRIPTION
        "Name of the driver. This property is inherited
        from CIM_ManagedSystemElement."
    ::= { win32PnPSignedDriverEntry 19 }

hwpsdPDO OBJECT-TYPE
    SYNTAX     DisplayString
    MAX-ACCESS read-only
    STATUS     current
    DESCRIPTION
        "Physical device object (PDO). PDOs represent
        individual devices on a bus. Other drivers for the
        device attach on top of the PDO. It is always at
        the bottom of the device stack. Example:
        '\Device\00000002'"
    ::= { win32PnPSignedDriverEntry 20 }

hwpsdProviderName OBJECT-TYPE
    SYNTAX     DisplayString
    MAX-ACCESS read-only
    STATUS     current
    DESCRIPTION
        "Provider of the driver. Example: 'Microsoft'"
    ::= { win32PnPSignedDriverEntry 21 }

hwpsdSigner OBJECT-TYPE
    SYNTAX     DisplayString
    MAX-ACCESS read-only
    STATUS     current
    DESCRIPTION
        "Signer of driver, if it is signed. Example:
        'ntbuild'"
    ::= { win32PnPSignedDriverEntry 22 }

hwpsdStarted OBJECT-TYPE
    SYNTAX     TruthValue
    MAX-ACCESS read-only
    STATUS     current
    DESCRIPTION
        "If TRUE, the driver is started. This property is
        inherited from CIM_Service."
    ::= { win32PnPSignedDriverEntry 23 }

hwpsdStartMode OBJECT-TYPE
    SYNTAX     DisplayString
    MAX-ACCESS read-only
    STATUS     current
    DESCRIPTION
        "Start mode of the driver. This property is
        inherited from CIM_Service."
    ::= { win32PnPSignedDriverEntry 24 }

hwpsdStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PnPSignedDriverEntry 25 }

hwpsdSystemCreationClassName OBJECT-TYPE
    SYNTAX     DisplayString
    MAX-ACCESS read-only
    STATUS     current
    DESCRIPTION
        "Value of the scoping computer's CreationClassName
        property. This property is inherited from
        CIM_Service."
    ::= { win32PnPSignedDriverEntry 26 }

hwpsdSystemName OBJECT-TYPE
    SYNTAX     DisplayString
    MAX-ACCESS read-only
    STATUS     current
    DESCRIPTION
        "System name. This property is inherited from
        CIM_Service."
    ::= { win32PnPSignedDriverEntry 27 }

win32PortConnectorTable OBJECT-TYPE
    SYNTAX     SEQUENCE OF Win32PortConnectorEntry
    MAX-ACCESS not-accessible
    STATUS     current
    DESCRIPTION
        "The Win32_PortConnector WMI class represents
        physical connection ports, such as DB-25 pin male,
        Centronics, or PS/2."
    ::= { wmiMotherboardControllerPort 22 }

win32PortConnectorEntry OBJECT-TYPE
    SYNTAX     Win32PortConnectorEntry
    MAX-ACCESS not-accessible
    STATUS     current
    DESCRIPTION
        "None"
    INDEX      { hwpcIndex }
    ::= { win32PortConnectorTable 1 }

Win32PortConnectorEntry ::= SEQUENCE {
    hwpcIndex Integer32,
    hwpcCaption DisplayString,
    hwpcConnectorPinout DisplayString,
    hwpcConnectorType DisplayString,
    hwpcCreationClassName DisplayString,
    hwpcDescription DisplayString,
    hwpcExternalReferenceDesignator DisplayString,
    hwpcInstallDate DateAndTime,
    hwpcInternalReferenceDesignator DisplayString,
    hwpcManufacturer DisplayString,
    hwpcModel DisplayString,
    hwpcName DisplayString,
    hwpcOtherIdentifyingInfo DisplayString,
    hwpcPartNumber DisplayString,
    hwpcPortType INTEGER,
    hwpcPoweredOn TruthValue,
    hwpcSerialNumber DisplayString,
    hwpcSKU DisplayString,
    hwpcStatus INTEGER,
    hwpcTag DisplayString,
    hwpcVersion DisplayString
}

hwpcIndex OBJECT-TYPE
    SYNTAX     Integer32 (1..2147483647)
    MAX-ACCESS read-only
    STATUS     current
    DESCRIPTION
        "The value of this object uniquely identifies the
        instance entry for this class."
    ::= { win32PortConnectorEntry 1 }

hwpcCaption OBJECT-TYPE
    SYNTAX     DisplayString
    MAX-ACCESS read-only
    STATUS     current
    DESCRIPTION
        "Short description of the object a one-line string.
        This property is inherited from
        CIM_ManagedSystemElement."
    ::= { win32PortConnectorEntry 2 }

hwpcConnectorPinout OBJECT-TYPE
    SYNTAX     DisplayString
    MAX-ACCESS read-only
    STATUS     current
    DESCRIPTION
        "Pin configuration and signal usage of a physical
        connector. This property is inherited from
        CIM_PhysicalConnector."
    ::= { win32PortConnectorEntry 3 }

hwpcConnectorType OBJECT-TYPE
    SYNTAX     DisplayString
    MAX-ACCESS read-only
    STATUS     current
    DESCRIPTION
        "Array of physical attributes of the connector used
        by this port. This property is inherited from
        CIM_PhysicalConnector. Values are the following:
        Value Meaning 
        0 Unknown 
        1 Other 
        2 Male 
        3 Female 
        4 Shielded 
        5 Unshielded 
        6 SCSI (A) High-Density (50 pins) 
        7 SCSI (A) Low-Density (50 pins) 
        8 SCSI (P) High-Density (68 pins) 
        9 SCSI SCA-I (80 pins) 
        10 SCSI SCA-II (80 pins) 
        11 SCSI Fibre Channel (DB-9, Copper) 
        12 SCSI Fibre Channel (Fibre) 
        13 SCSI Fibre Channel SCA-II (40 pins) 
        14 SCSI Fibre Channel SCA-II (20 pins) 
        15 SCSI Fibre Channel BNC 
        16 ATA 3-1/2 Inch (40 pins) 
        17 ATA 2-1/2 Inch (44 pins) 
        18 ATA-2 
        19 ATA-3 
        20 ATA/66 
        21 DB-9 
        22 DB-15 
        23 DB-25 
        24 DB-36 
        25 RS-232C 
        26 RS-422 
        27 RS-423 
        28 RS-485 
        29 RS-449 
        30 V.35 
        31 X.21 
        32 IEEE-488 
        33 AUI 
        34 UTP Category 3 
        35 UTP Category 4 
        36 UTP Category 5 
        37 BNC 
        38 RJ11 
        39 RJ45 
        40 Fiber MIC 
        41 Apple AUI 
        42 Apple GeoPort 
        43 PCI 
        44 ISA 
        45 EISA 
        46 VESA 
        47 PCMCIA 
        48 PCMCIA Type I 
        49 PCMCIA Type II 
        50 PCMCIA Type III 
        51 ZV Port 
        52 CardBus 
        53 USB 
        54 IEEE 1394 
        55 HIPPI 
        56 HSSDC (6 pins) 
        57 GBIC 
        58 DIN 
        59 Mini-DIN 
        60 Micro-DIN 
        61 PS/2 
        62 Infrared 
        63 HP-HIL 
        64 Access.bus 
        65 NuBus 
        66 Centronics 
        67 Mini-Centronics 
        68 Mini-Centronics Type-14 
        69 Mini-Centronics Type-20 
        70 Mini-Centronics Type-26 
        71 Bus Mouse 
        72 ADB 
        73 AGP 
        74 VME Bus 
        75 VME64 
        76 Proprietary 
        77 Proprietary Processor Card Slot 
        78 Proprietary Memory Card Slot 
        79 Proprietary I/O Riser Slot 
        80 PCI-66MHZ 
        81 AGP2X 
        82 AGP4X 
        83 PC-98 
        84 PC-98-Hireso 
        85 PC-H98 
        86 PC-98Note 
        87 PC-98Full 
        88 SSA SCSI 
        89 Circular 
        90 On Board IDE Connector 
        91 On Board Floppy Connector 
        92 9 Pin Dual Inline 
        93 25 Pin Dual Inline 
        94 50 Pin Dual Inline 
        95 68 Pin Dual Inline 
        96 On Board Sound Connector 
        97 Mini-jack 
        98 PCI-X 
        99 Sbus IEEE 1396-1993 32 bit 
        100 Sbus IEEE 1396-1993 64 bit 
        101 MCA 
        102 GIO 
        103 XIO 
        104 HIO 
        105 NGIO 
        106 PMC 
        107 MTRJ 
        108 VF-45 
        109 Future I/O 
        110 SC 
        111 SG 
        112 Electrical 
        113 Optical 
        114 Ribbon 
        115 GLM 
        116 1x9 
        117 Mini SG 
        118 LC 
        119 HSSC 
        120 VHDCI Shielded (68 pins) 
        121 InfiniBand "
    ::= { win32PortConnectorEntry 4 }

hwpcCreationClassName OBJECT-TYPE
    SYNTAX     DisplayString
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_PhysicalElement."
    ::= { win32PortConnectorEntry 5 }

hwpcDescription OBJECT-TYPE
    SYNTAX     DisplayString
    MAX-ACCESS read-only
    STATUS     current
    DESCRIPTION
        "Description of the object. This property is
        inherited from CIM_ManagedSystemElement."
    ::= { win32PortConnectorEntry 6 }

hwpcExternalReferenceDesignator OBJECT-TYPE
    SYNTAX     DisplayString
    MAX-ACCESS read-only
    STATUS     current
    DESCRIPTION
        "External reference designator of the port.
        External reference designators are identifiers that
        determine the type and use of the port.
        Example: 'COM1'"
    ::= { win32PortConnectorEntry 7 }

hwpcInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32PortConnectorEntry 8 }

hwpcInternalReferenceDesignator OBJECT-TYPE
    SYNTAX     DisplayString
    MAX-ACCESS read-only
    STATUS     current
    DESCRIPTION
        "Internal reference designator of the port.
        Internal reference designators are specific to the
        manufacturer, and identify the circuit board
        location or use of the port.
        Example: 'J101'"
    ::= { win32PortConnectorEntry 9 }

hwpcManufacturer OBJECT-TYPE
    SYNTAX     DisplayString
    MAX-ACCESS read-only
    STATUS     current
    DESCRIPTION
        "Name of the organization responsible for producing
        the physical element. This property is inherited
        from CIM_PhysicalElement."
    ::= { win32PortConnectorEntry 10 }

hwpcModel OBJECT-TYPE
    SYNTAX     DisplayString
    MAX-ACCESS read-only
    STATUS     current
    DESCRIPTION
        "Name for the physical element. This property is
        inherited from CIM_PhysicalElement."
    ::= { win32PortConnectorEntry 11 }

hwpcName OBJECT-TYPE
    SYNTAX     DisplayString
    MAX-ACCESS read-only
    STATUS     current
    DESCRIPTION
        "Label for the object. When subclassed, the
        property can be overridden to be a key property.
        This property is inherited from
        CIM_ManagedSystemElement."
    ::= { win32PortConnectorEntry 12 }

hwpcOtherIdentifyingInfo OBJECT-TYPE
    SYNTAX     DisplayString
    MAX-ACCESS read-only
    STATUS     current
    DESCRIPTION
        "Additional data, beyond asset tag information,
        that can be used to identify a physical element.
        One example is bar code data associated with an
        element that also has an asset tag. If only bar
        code data is available and unique or able to be
        used as an element key, this property is NULL and
        the bar code data is used as the class key in the
        tag property. This property is inherited from
        CIM_PhysicalElement."
    ::= { win32PortConnectorEntry 13 }

hwpcPartNumber OBJECT-TYPE
    SYNTAX     DisplayString
    MAX-ACCESS read-only
    STATUS     current
    DESCRIPTION
        "Part number assigned by the organization
        responsible for producing or manufacturing the
        physical element. This property is inherited from
        CIM_PhysicalElement."
    ::= { win32PortConnectorEntry 14 }

hwpcPortType OBJECT-TYPE
    SYNTAX     INTEGER {
        none(0),
        parallelPortXTATCompatible(1),
        parallelPortPS2(2),
        parallelPortECP(3),
        parallelPortEPP(4),
        parallelPortECPEPP(5),
        serialPortXTATCompatible(6),
        serialPort16450Compatible(7),
        serialPort16550Compatible(8),
        serialPort16550ACompatible(9),
        scsiPort(10),
        midiPort(11),
        joyStickPort(12),
        keyboardPort(13),
        mousePort(14),
        ssaSCSI(15),
        usb(16),
        fireWire(17),
        pcmciaTypeII(18),
        pcmciaTypeII2(19),
        cardbus(20),
        accessBusPort(21),
        scsiII(22),
        scsiWide(23),
        pc98(24),
        pc98Hireso(25),
        pcH98(26),
        audioPort(27),
        modemPort(28),
        networkPort(29),
        n8251Compatible(30),
        n8251FIFOCompatible(31)
    }
    MAX-ACCESS read-only
    STATUS     current
    DESCRIPTION
        "Function of the port."
    ::= { win32PortConnectorEntry 15 }

hwpcPoweredOn OBJECT-TYPE
    SYNTAX     TruthValue
    MAX-ACCESS read-only
    STATUS     current
    DESCRIPTION
        "If TRUE, the physical element is powered on. This
        property is inherited from CIM_PhysicalElement."
    ::= { win32PortConnectorEntry 16 }

hwpcSerialNumber OBJECT-TYPE
    SYNTAX     DisplayString
    MAX-ACCESS read-only
    STATUS     current
    DESCRIPTION
        "Manufacturer-allocated number used to identify a
        physical element. This property is inherited from
        CIM_PhysicalElement."
    ::= { win32PortConnectorEntry 17 }

hwpcSKU OBJECT-TYPE
    SYNTAX     DisplayString
    MAX-ACCESS read-only
    STATUS     current
    DESCRIPTION
        "Stock-keeping unit number for a physical element.
        This property is inherited from
        CIM_PhysicalElement."
    ::= { win32PortConnectorEntry 18 }

hwpcStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PortConnectorEntry 19 }

hwpcTag OBJECT-TYPE
    SYNTAX     DisplayString (SIZE (0..256))
    MAX-ACCESS read-only
    STATUS     current
    DESCRIPTION
        "Unique identifier of a port connection on the
        computer system. This property is inherited from
        CIM_PhysicalElement.
        Example: 'Port Connector 1'"
    ::= { win32PortConnectorEntry 20 }

hwpcVersion OBJECT-TYPE
    SYNTAX     DisplayString
    MAX-ACCESS read-only
    STATUS     current
    DESCRIPTION
        "Version of the physical element. This property is
        inherited from CIM_PhysicalElement."
    ::= { win32PortConnectorEntry 21 }

win32PortResourceTable OBJECT-TYPE
    SYNTAX     SEQUENCE OF Win32PortResourceEntry
    MAX-ACCESS not-accessible
    STATUS     current
    DESCRIPTION
        "The Win32_PortResource WMI class represents an I/O
        port on a Windows computer system."
    ::= { wmiMotherboardControllerPort 23 }

win32PortResourceEntry OBJECT-TYPE
    SYNTAX     Win32PortResourceEntry
    MAX-ACCESS not-accessible
    STATUS     current
    DESCRIPTION
        "None"
    INDEX      { hwpreIndex }
    ::= { win32PortResourceTable 1 }

Win32PortResourceEntry ::= SEQUENCE {
    hwpreIndex Integer32,
    hwpreAlias TruthValue,
    hwpreCaption DisplayString,
    hwpreCreationClassName DisplayString,
    hwpreCSCreationClassName DisplayString,
    hwpreCSName DisplayString,
    hwpreDescription DisplayString,
    hwpreEndingAddress Gauge32,
    hwpreInstallDate DateAndTime,
    hwpreName DisplayString,
    hwpreStartingAddress Gauge32,
    hwpreStatus INTEGER
}

hwpreIndex OBJECT-TYPE
    SYNTAX     Integer32 (1..2147483647)
    MAX-ACCESS read-only
    STATUS     current
    DESCRIPTION
        "The value of this object uniquely identifies the
        instance entry for this class."
    ::= { win32PortResourceEntry 1 }

hwpreAlias OBJECT-TYPE
    SYNTAX     TruthValue
    MAX-ACCESS read-only
    STATUS     current
    DESCRIPTION
        "If TRUE, this instance represents one of the
        ranges with an alias. If FALSE, the instance
        represents a base port address. A base port address
        is a predetermined port address dedicated to a
        specific service or device. A port alias address is
        one that a device responds to as if it were the
        actual address of an I/O port."
    ::= { win32PortResourceEntry 2 }

hwpreCaption OBJECT-TYPE
    SYNTAX     DisplayString
    MAX-ACCESS read-only
    STATUS     current
    DESCRIPTION
        "Short description (one-line string) of the object.
        This property is inherited from
        CIM_ManagedSystemElement."
    ::= { win32PortResourceEntry 3 }

hwpreCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_MemoryMappedIO."
    ::= { win32PortResourceEntry 4 }

hwpreCSCreationClassName OBJECT-TYPE
    SYNTAX     DisplayString
    MAX-ACCESS read-only
    STATUS     current
    DESCRIPTION
        "Creation class name of the scoping computer
        system. This property is inherited from
        CIM_MemoryMappedIO."
    ::= { win32PortResourceEntry 5 }

hwpreCSName OBJECT-TYPE
    SYNTAX     DisplayString
    MAX-ACCESS read-only
    STATUS     current
    DESCRIPTION
        "Name of the scoping computer system. This property
        is inherited from CIM_MemoryMappedIO."
    ::= { win32PortResourceEntry 6 }

hwpreDescription OBJECT-TYPE
    SYNTAX     DisplayString
    MAX-ACCESS read-only
    STATUS     current
    DESCRIPTION
        "Description of the object. This property is
        inherited from CIM_ManagedSystemElement."
    ::= { win32PortResourceEntry 7 }

hwpreEndingAddress OBJECT-TYPE
    SYNTAX     Gauge32
    MAX-ACCESS read-only
    STATUS     current
    DESCRIPTION
        "Ending address of memory mapped I/O. This property
        is inherited from CIM_MemoryMappedIO."
    ::= { win32PortResourceEntry 8 }

hwpreInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32PortResourceEntry 9 }

hwpreName OBJECT-TYPE
    SYNTAX     DisplayString
    MAX-ACCESS read-only
    STATUS     current
    DESCRIPTION
        "Label by which the object is known. When
        subclassed, the property can be overridden to be a
        key property. This property is inherited from
        CIM_ManagedSystemElement."
    ::= { win32PortResourceEntry 10 }

hwpreStartingAddress OBJECT-TYPE
    SYNTAX     Gauge32
    MAX-ACCESS read-only
    STATUS     current
    DESCRIPTION
        "Starting address of memory mapped I/O. The
        hardware resource identifier property should be set
        to this value to construct the mapped I/O resource
        key. This property is inherited from
        CIM_MemoryMappedIO."
    ::= { win32PortResourceEntry 11 }

hwpreStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PortResourceEntry 12 }

win32ProcessorTable OBJECT-TYPE
    SYNTAX     SEQUENCE OF Win32ProcessorEntry
    MAX-ACCESS not-accessible
    STATUS     current
    DESCRIPTION
        "The Win32_Processor WMI class represents a device
        that can interpret a sequence of machine
        instructions on a computer running a Windows
        operating system. On a multiprocessor machine, one
        instance of the Win32_Processor class exists for
        each processor."
    ::= { wmiMotherboardControllerPort 24 }

win32ProcessorEntry OBJECT-TYPE
    SYNTAX     Win32ProcessorEntry
    MAX-ACCESS not-accessible
    STATUS     current
    DESCRIPTION
        "None"
    INDEX      { hwcpuIndex }
    ::= { win32ProcessorTable 1 }

Win32ProcessorEntry ::= SEQUENCE {
    hwcpuIndex Integer32,
    hwcpuAddressWidth Integer32,
    hwcpuArchitecture INTEGER,
    hwcpuAvailability INTEGER,
    hwcpuCaption DisplayString,
    hwcpuConfigManagerErrorCode INTEGER,
    hwcpuConfigManagerUserConfig TruthValue,
    hwcpuCpuStatus INTEGER,
    hwcpuCreationClassName DisplayString,
    hwcpuCurrentClockSpeed Gauge32,
    hwcpuCurrentVoltage Integer32,
    hwcpuDataWidth Integer32,
    hwcpuDescription DisplayString,
    hwcpuDeviceID DisplayString,
    hwcpuErrorCleared TruthValue,
    hwcpuErrorDescription DisplayString,
    hwcpuExtClock Gauge32,
    hwcpuFamily INTEGER,
    hwcpuInstallDate DateAndTime,
    hwcpuL2CacheSize Gauge32,
    hwcpuL2CacheSpeed Gauge32,
    hwcpuLastErrorCode Gauge32,
    hwcpuLevel Integer32,
    hwcpuLoadPercentage Integer32,
    hwcpuManufacturer DisplayString,
    hwcpuMaxClockSpeed Gauge32,
    hwcpuName DisplayString,
    hwcpuOtherFamilyDescription DisplayString,
    hwcpuPNPDeviceID DisplayString,
    hwcpuPowerManagementCapabilities DisplayString,
    hwcpuPowerManagementSupported TruthValue,
    hwcpuProcessorId DisplayString,
    hwcpuProcessorType INTEGER,
    hwcpuRevision Integer32,
    hwcpuRole DisplayString,
    hwcpuSocketDesignation DisplayString,
    hwcpuStatus INTEGER,
    hwcpuStatusInfo INTEGER,
    hwcpuStepping DisplayString,
    hwcpuSystemCreationClassName DisplayString,
    hwcpuSystemName DisplayString,
    hwcpuUniqueId DisplayString,
    hwcpuUpgradeMethod INTEGER,
    hwcpuVersion DisplayString,
    hwcpuVoltageCaps INTEGER,
    hwcpuL3CacheSize Gauge32,
    hwcpuL3CacheSpeed Gauge32,
    hwcpuNumberOfCores Gauge32,
    hwcpuNumberOfLogicalProcessors Gauge32
}

hwcpuIndex OBJECT-TYPE
    SYNTAX     Integer32 (1..2147483647)
    MAX-ACCESS read-only
    STATUS     current
    DESCRIPTION
        "The value of this object uniquely identifies the
        instance entry for this class."
    ::= { win32ProcessorEntry 1 }

hwcpuAddressWidth OBJECT-TYPE
    SYNTAX     Integer32
    MAX-ACCESS read-only
    STATUS     current
    DESCRIPTION
        "Processor address width in bits. This property is
        inherited from CIM_Processor."
    ::= { win32ProcessorEntry 2 }

hwcpuArchitecture OBJECT-TYPE
    SYNTAX     INTEGER {
        x86(0),
        mips(1),
        alpha(2),
        powerPC(3),
        ia64(6)
    }
    MAX-ACCESS read-only
    STATUS     current
    DESCRIPTION
        "Processor architecture that the platform uses."
    ::= { win32ProcessorEntry 3 }

hwcpuAvailability OBJECT-TYPE
    SYNTAX     INTEGER {
        other(1),
        unknown(2),
        runningOrFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of a device. Power Save -
        Unknown indicates that a device is in a power save
        mode, but the status is unknown; Power Save - Low
        Power Mode indicates that a device is in a power
        save mode, but still functioning in a degraded
        performance state; Power Save - Standby indicates
        that a device is not functioning, but can be
        brought to full power quickly; and Power Save -
        Warning indicates that a device is in a warning and
        power save mode. This property is inherited from
        CIM_LogicalDevice."
    ::= { win32ProcessorEntry 4 }

hwcpuCaption OBJECT-TYPE
    SYNTAX     DisplayString
    MAX-ACCESS read-only
    STATUS     current
    DESCRIPTION
        "Qualifier: MaxLen(64)
        Short description of an object a one-line string.
        This property is inherited from
        CIM_ManagedSystemElement."
    ::= { win32ProcessorEntry 5 }

hwcpuConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Error code for the Windows Configuration Manager.
        This property is inherited from CIM_LogicalDevice."
    ::= { win32ProcessorEntry 6 }

hwcpuConfigManagerUserConfig OBJECT-TYPE
    SYNTAX     TruthValue
    MAX-ACCESS read-only
    STATUS     current
    DESCRIPTION
        "If TRUE, the device is using a configuration that
        the user defines. This property is inherited from
        CIM_LogicalDevice."
    ::= { win32ProcessorEntry 7 }

hwcpuCpuStatus OBJECT-TYPE
    SYNTAX     INTEGER {
        unknown(0),
        cpuEnabled(1),
        cpuDisabledByUserViaBIOSSetup(2),
        cpuDisabledByBIOS(3),
        cpuIsIdle(4),
        reserved(5),
        reserved2(6),
        other(7)
    }
    MAX-ACCESS read-only
    STATUS     current
    DESCRIPTION
        "Current status of the processor. Status changes
        indicate processor usage, not the physical
        condition of the processor."
    ::= { win32ProcessorEntry 8 }

hwcpuCreationClassName OBJECT-TYPE
    SYNTAX     DisplayString (SIZE (0..256))
    MAX-ACCESS read-only
    STATUS     current
    DESCRIPTION
        "Name of the first concrete class that appears in
        the inheritance chain used to create an instance.
        When used with the other key properties of the
        class, the property allows all instances of this
        class and its subclasses to be identified uniquely.
        This property is inherited from CIM_LogicalDevice."
    ::= { win32ProcessorEntry 9 }

hwcpuCurrentClockSpeed OBJECT-TYPE
    SYNTAX     Gauge32
    UNITS "MegaHertz"
    MAX-ACCESS read-only
    STATUS     current
    DESCRIPTION
        "Current speed of the processor in MHz. This
        property is inherited from CIM_Processor."
    ::= { win32ProcessorEntry 10 }

hwcpuCurrentVoltage OBJECT-TYPE
    SYNTAX     Integer32
    UNITS "tenth-Volts"
    MAX-ACCESS read-only
    STATUS     current
    DESCRIPTION
        "Voltage of the processor. Bits 0-6 of the field
        contain the current voltage of the processor times
        10. This value is only set when SMBIOS designates a
        voltage value. For specific values, see
        VoltageCaps.
        Example: field value for a processor voltage of 1.8
        volts is 92h = 80h + (1.8 x 10) = 80h + 18 = 80h +
        12h"
    ::= { win32ProcessorEntry 11 }

hwcpuDataWidth OBJECT-TYPE
    SYNTAX     Integer32
    MAX-ACCESS read-only
    STATUS     current
    DESCRIPTION
        "Processor data width in bits. This property is
        inherited from CIM_Processor."
    ::= { win32ProcessorEntry 12 }

hwcpuDescription OBJECT-TYPE
    SYNTAX     DisplayString
    MAX-ACCESS read-only
    STATUS     current
    DESCRIPTION
        "Description of the object. This property is
        inherited from CIM_ManagedSystemElement."
    ::= { win32ProcessorEntry 13 }

hwcpuDeviceID OBJECT-TYPE
    SYNTAX     DisplayString
    MAX-ACCESS read-only
    STATUS     current
    DESCRIPTION
        "Unique identifier of a processor on the system.
        This property is inherited from CIM_LogicalDevice."
    ::= { win32ProcessorEntry 14 }

hwcpuErrorCleared OBJECT-TYPE
    SYNTAX     TruthValue
    MAX-ACCESS read-only
    STATUS     current
    DESCRIPTION
        "If TRUE, the error reported in LastErrorCode is
        clear. This property is inherited from
        CIM_LogicalDevice."
    ::= { win32ProcessorEntry 15 }

hwcpuErrorDescription OBJECT-TYPE
    SYNTAX     DisplayString
    MAX-ACCESS read-only
    STATUS     current
    DESCRIPTION
        "More information about the error recorded in
        LastErrorCode, and information about corrective
        actions that can be taken. This property is
        inherited from CIM_LogicalDevice."
    ::= { win32ProcessorEntry 16 }

hwcpuExtClock OBJECT-TYPE
    SYNTAX     Gauge32
    UNITS "MegaHertz"
    MAX-ACCESS read-only
    STATUS     current
    DESCRIPTION
        "External clock frequency in MHz. If the frequency
        is unknown, this property is set to NULL."
    ::= { win32ProcessorEntry 17 }

hwcpuFamily OBJECT-TYPE
    SYNTAX     INTEGER {
        other(1),
        unknown(2),
        n8086(3),
        n80286(4),
        n80386(5),
        n80486(6),
        n8087(7),
        n80287(8),
        n80387(9),
        n80487(10),
        pentiumBrand(11),
        pentiumPro(12),
        pentiumII(13),
        pentiumProcessorMMX(14),
        celeron(15),
        pentiumIIXeon(16),
        pentiumIII(17),
        m1Family(18),
        m2Family(19),
        k5Family(24),
        k6Family(25),
        k62(26),
        k63(27),
        amdAthlonProcessorFamily(28),
        amdDuronProcessor(29),
        amd2900Family(30),
        k62plus(31),
        powerPCFamily(32),
        powerPC601(33),
        powerPC603(34),
        powerPC603plus(35),
        powerPC604(36),
        powerPC620(37),
        powerPCX704(38),
        powerPC750(39),
        alphaFamily(48),
        alpha21064(49),
        alpha21066(50),
        alpha21164(51),
        alpha21164PC(52),
        alpha21164a(53),
        alpha21264(54),
        alpha21364(55),
        mipsFamily(64),
        mipsR4000(65),
        mipsR4200(66),
        mipsR4400(67),
        mipsR4600(68),
        mipsR10000(69),
        sparcFamily(80),
        superSPARC(81),
        microSPARCII(82),
        microSPARCIIep(83),
        ultraSPARC(84),
        ultraSPARCII(85),
        ultraSPARCIIi(86),
        ultraSPARCIII(87),
        ultraSPARCIIIi(88),
        n68040(96),
        n68xxxFamily(97),
        n68000(98),
        n68010(99),
        n68020(100),
        n68030(101),
        hobbitFamily(112),
        crusoeTM5000Family(120),
        crusoeTM3000Family(121),
        weitek(128),
        itaniumProcessor(130),
        paRISCFamily(144),
        paRISC8500(145),
        paRISC8000(146),
        paRISC7300LC(147),
        paRISC7200(148),
        paRISC7100LC(149),
        paRISC7100(150),
        v30Family(160),
        pentiumIIIXeon(176),
        pentiumIIIProcessorSpeedStep(177),
        pentium4(178),
        intelXeon(179),
        as400Family(180),
        intelXeonProcessorMP(181),
        amdAthlonXPFamily(182),
        amdAthlonMPFamily(183),
        intelItanium2(184),
        amdOpteronFamily(185),
        k7(190),
        ibm390Family(200),
        g4(201),
        g5(202),
        i860(250),
        i960(251),
        sh3(260),
        sh4(261),
        arm(280),
        strongARM(281),
        n6x86(300),
        mediaGX(301),
        mii(302),
        winChip(320),
        dsp(350),
        videoProcessor(500)
    }
    MAX-ACCESS read-only
    STATUS     current
    DESCRIPTION
        "Processor family type. This property is inherited
        from CIM_Processor. "
    ::= { win32ProcessorEntry 18 }

hwcpuInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32ProcessorEntry 19 }

hwcpuL2CacheSize OBJECT-TYPE
    SYNTAX     Gauge32
    UNITS "Kilobytes"
    MAX-ACCESS read-only
    STATUS     current
    DESCRIPTION
        "Size of the Level 2 processor cache. A Level 2
        cache is an external memory area that has a faster
        access time than the main RAM memory."
    ::= { win32ProcessorEntry 20 }

hwcpuL2CacheSpeed OBJECT-TYPE
    SYNTAX     Gauge32
    UNITS "MegaHertz"
    MAX-ACCESS read-only
    STATUS     current
    DESCRIPTION
        "Clock speed of the Level 2 processor cache. A
        Level 2 cache is an external memory area that has a
        faster access time than the main RAM memory."
    ::= { win32ProcessorEntry 21 }

hwcpuLastErrorCode OBJECT-TYPE
    SYNTAX     Gauge32
    MAX-ACCESS read-only
    STATUS     current
    DESCRIPTION
        "Last error code reported by the logical device.
        This property is inherited from CIM_LogicalDevice."
    ::= { win32ProcessorEntry 22 }

hwcpuLevel OBJECT-TYPE
    SYNTAX     Integer32
    MAX-ACCESS read-only
    STATUS     current
    DESCRIPTION
        "Definition of the processor type. The value
        depends on the architecture of the processor."
    ::= { win32ProcessorEntry 23 }

hwcpuLoadPercentage OBJECT-TYPE
    SYNTAX     Integer32
    UNITS "Percent"
    MAX-ACCESS read-only
    STATUS     current
    DESCRIPTION
        "Load capacity of each processor, averaged to the
        last second. Processor loading refers to the total
        computing burden for each processor at one time.
        This property is inherited from CIM_Processor."
    ::= { win32ProcessorEntry 24 }

hwcpuManufacturer OBJECT-TYPE
    SYNTAX     DisplayString
    MAX-ACCESS read-only
    STATUS     current
    DESCRIPTION
        "Name of the processor manufacturer.
        Example: A. Datum Corporation"
    ::= { win32ProcessorEntry 25 }

hwcpuMaxClockSpeed OBJECT-TYPE
    SYNTAX     Gauge32
    UNITS "MegaHertz"
    MAX-ACCESS read-only
    STATUS     current
    DESCRIPTION
        "Maximum speed of the processor in MHz. This
        property is inherited from CIM_Processor."
    ::= { win32ProcessorEntry 26 }

hwcpuName OBJECT-TYPE
    SYNTAX     DisplayString
    MAX-ACCESS read-only
    STATUS     current
    DESCRIPTION
        "Label by which the object is known. When this
        property is a subclass, it can be overridden to be
        a key property. This property is inherited from
        CIM_ManagedSystemElement."
    ::= { win32ProcessorEntry 27 }

hwcpuOtherFamilyDescription OBJECT-TYPE
    SYNTAX     DisplayString (SIZE (0..64))
    MAX-ACCESS read-only
    STATUS     current
    DESCRIPTION
        "Processor family type. Used when the Family
        property is set to 1, which means Other. This
        string should be set to NULL when the Family
        property is a value that is not 1. This property is
        inherited from CIM_Processor."
    ::= { win32ProcessorEntry 28 }

hwcpuPNPDeviceID OBJECT-TYPE
    SYNTAX     DisplayString
    MAX-ACCESS read-only
    STATUS     current
    DESCRIPTION
        "Windows Plug and Play device identifier of the
        logical device. This property is inherited from
        CIM_LogicalDevice.
        Example: *PNP030b"
    ::= { win32ProcessorEntry 29 }

hwcpuPowerManagementCapabilities OBJECT-TYPE
    SYNTAX     DisplayString
    MAX-ACCESS read-only
    STATUS     current
    DESCRIPTION
        "Specific power capabilities of a logical device.
        The Enabled value indicates that the power
        management features are currently enabled, but the
        exact setting is unknown or the information is
        unavailable. Power Saving Modes Entered
        Automatically indicates that a device can change
        its power state based on usage or other criteria.
        Power State Settable indicates that the
        SetPowerState method is supported. Power Cycling
        Supported indicates that the SetPowerState method
        can be invoked with the PowerState parameter set to
        5. Timed Power On Supported indicates that the
        SetPowerState method can be invoked with the
        PowerState parameter set to 5 and Time set to a
        specific date and time, or interval to power ON.
        This property is inherited from
        CIM_UnitaryComputerSystem.
        Value Meaning 
        0 Unknown 
        1 Not Supported 
        2 Disabled 
        3 Enabled 
        4 Power Saving Modes Entered Automatically 
        5 Power State Settable 
        6 Power Cycling Supported 
        7 Timed Power On Supported "
    ::= { win32ProcessorEntry 30 }

hwcpuPowerManagementSupported OBJECT-TYPE
    SYNTAX     TruthValue
    MAX-ACCESS read-only
    STATUS     current
    DESCRIPTION
        "If TRUE, the power of the device can be managed,
        which means that it can be put into suspend mode,
        and so on. The property does not indicate that
        power management features are enabled, but it does
        indicate that the logical device power can be
        managed. This property is inherited from
        CIM_LogicalDevice."
    ::= { win32ProcessorEntry 31 }

hwcpuProcessorId OBJECT-TYPE
    SYNTAX     DisplayString
    MAX-ACCESS read-only
    STATUS     current
    DESCRIPTION
        "Processor information that describes the processor
        features. For an x86 class CPU, the field format
        depends on the processor support of the CPUID
        instruction. If the instruction is supported, the
        property contains 2 (two) DWORD formatted values.
        The first is an offset of 08h-0Bh, which is the EAX
        value that a CPUID instruction returns with input
        EAX set to 1. The second is an offset of 0Ch-0Fh,
        which is the EDX value that the instruction
        returns. Only the first two bytes of the property
        are significant and contain the contents of the DX
        register at CPU reset all others are set to 0
        (zero), and the contents are in DWORD format."
    ::= { win32ProcessorEntry 32 }

hwcpuProcessorType OBJECT-TYPE
    SYNTAX     INTEGER {
        other(1),
        unknown(2),
        centralProcessor(3),
        mathProcessor(4),
        dspProcessor(5),
        videoProcessor(6)
    }
    MAX-ACCESS read-only
    STATUS     current
    DESCRIPTION
        "Primary function of the processor."
    ::= { win32ProcessorEntry 33 }

hwcpuRevision OBJECT-TYPE
    SYNTAX     Integer32
    MAX-ACCESS read-only
    STATUS     current
    DESCRIPTION
        "System revision level that depends on the
        architecture. The system revision level contains
        the same values as the Version property, but in a
        numerical format."
    ::= { win32ProcessorEntry 34 }

hwcpuRole OBJECT-TYPE
    SYNTAX     DisplayString
    MAX-ACCESS read-only
    STATUS     current
    DESCRIPTION
        "Role of the processor. This property is inherited
        from CIM_Processor.
        Examples: Central Processor or Math Processor"
    ::= { win32ProcessorEntry 35 }

hwcpuSocketDesignation OBJECT-TYPE
    SYNTAX     DisplayString
    MAX-ACCESS read-only
    STATUS     current
    DESCRIPTION
        "Type of chip socket used on the circuit.
        Example: J202"
    ::= { win32ProcessorEntry 36 }

hwcpuStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of an object. Various operational
        and non-operational statuses can be defined.
        Operational statuses include: OK, Degraded, and
        Pred Fail, which is an element such as a
        SMART-enabled hard drive that may be functioning
        properly, but predicts a failure in the near
        future. Non-operational statuses include: Error,
        Starting, Stopping, and Service, which can apply
        during mirror resilvering of a disk, reloading a
        user permissions list, or other administrative
        work. Not all status work is online, but the
        managed element is not OK or in one of the other
        states. This property is inherited from
        CIM_ManagedSystemElement."
    ::= { win32ProcessorEntry 37 }

hwcpuStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, use the value 5,
        which means Not Applicable. This property is
        inherited from CIM_LogicalDevice."
    ::= { win32ProcessorEntry 38 }

hwcpuStepping OBJECT-TYPE
    SYNTAX     DisplayString
    MAX-ACCESS read-only
    STATUS     current
    DESCRIPTION
        "Revision level of the processor in the processor
        family. This property is inherited from
        CIM_Processor."
    ::= { win32ProcessorEntry 39 }

hwcpuSystemCreationClassName OBJECT-TYPE
    SYNTAX     DisplayString
    MAX-ACCESS read-only
    STATUS     current
    DESCRIPTION
        "Value of the CreationClassName property for the
        scoping computer. This property is inherited from
        CIM_LogicalDevice."
    ::= { win32ProcessorEntry 40 }

hwcpuSystemName OBJECT-TYPE
    SYNTAX     DisplayString
    MAX-ACCESS read-only
    STATUS     current
    DESCRIPTION
        "Name of the scoping system. This property is
        inherited from CIM_LogicalDevice."
    ::= { win32ProcessorEntry 41 }

hwcpuUniqueId OBJECT-TYPE
    SYNTAX     DisplayString
    MAX-ACCESS read-only
    STATUS     current
    DESCRIPTION
        "Globally unique identifier for the processor. This
        identifier may only be unique within a processor
        family. This property is inherited from
        CIM_Processor."
    ::= { win32ProcessorEntry 42 }

hwcpuUpgradeMethod OBJECT-TYPE
    SYNTAX     INTEGER {
        other(1),
        unknown(2),
        daughterBoard(3),
        zifSocket(4),
        replacementPiggyBack(5),
        none(6),
        lifSocket(7),
        slot1(8),
        slot2(9),
        n370PinSocket(10),
        slotA(11),
        slotM(12)
    }
    MAX-ACCESS read-only
    STATUS     current
    DESCRIPTION
        "Method by which this processor can be upgraded, if
        upgrades are supported. This property is an integer
        enumeration. This property is inherited from
        CIM_Processor."
    ::= { win32ProcessorEntry 43 }

hwcpuVersion OBJECT-TYPE
    SYNTAX     DisplayString
    MAX-ACCESS read-only
    STATUS     current
    DESCRIPTION
        "Processor revision number that depends on the
        architecture. This property is not used in Windows
        95.
        Example: Model 2, Stepping 12"
    ::= { win32ProcessorEntry 44 }

hwcpuVoltageCaps OBJECT-TYPE
    SYNTAX     INTEGER {
        n5(1),
        n33(2),
        n29(4)
    }
    UNITS "Volts"
    MAX-ACCESS read-only
    STATUS     current
    DESCRIPTION
        "Voltage capabilities of the processor. Bits 0-3 of
        the field represent specific voltages that the
        processor socket can accept. All other bits should
        be set to 0 (zero). The socket is configurable if
        multiple bits are set. For a range of voltages, see
        CurrentVoltage. If the property is NULL, then the
        voltage capabilities are unknown."
    ::= { win32ProcessorEntry 45 }

hwcpuL3CacheSize OBJECT-TYPE
    SYNTAX     Gauge32
    UNITS "Kilobytes"
    MAX-ACCESS read-only
    STATUS     current
    DESCRIPTION
        "Size of the Level 3 processor cache. A Level 3
        cache is an external memory area that has a faster
        access time than the main RAM memory."
    ::= { win32ProcessorEntry 46 }

hwcpuL3CacheSpeed OBJECT-TYPE
    SYNTAX     Gauge32
    UNITS "MegaHertz"
    MAX-ACCESS read-only
    STATUS     current
    DESCRIPTION
        "Clockspeed of the Level 3 property cache. A Level
        3 cache is an external memory area that has a
        faster access time than the main RAM memory."
    ::= { win32ProcessorEntry 47 }

hwcpuNumberOfCores OBJECT-TYPE
    SYNTAX     Gauge32
    MAX-ACCESS read-only
    STATUS     current
    DESCRIPTION
        "Number of cores for the current instance of the
        processor. A core is a physical processor on the
        integrated circuit. For example, in a dual-core
        processor this property has a value of 2.
        
        To determine if hyperthreading is enabled for the
        processor, compare NumberOfLogicalProcessors and
        NumberOfCores. If hyperthreading is enabled in the
        BIOS for the processor, then NumberOfCores is less
        than NumberOfLogicalProcessors. For example, a dual
        processor system that contains two processors
        enabled for hyperthreading can run four threads or
        programs or simultaneously. In this case,
        NumberOfCores is 2 and NumberOfLogicalProcessors is
        4."
    ::= { win32ProcessorEntry 48 }

hwcpuNumberOfLogicalProcessors OBJECT-TYPE
    SYNTAX     Gauge32
    MAX-ACCESS read-only
    STATUS     current
    DESCRIPTION
        "Number of logical processors for the current
        instance of the processor. For processors capable
        of hyperthreading, this value includes only the
        processors which have hyperthreading enabled.
        
        To determine if hyperthreading is enabled for the
        processor, compare NumberOfLogicalProcessors and
        NumberOfCores. If hyperthreading is enabled in the
        BIOS for the processor, then NumberOfCores is less
        than NumberOfLogicalProcessors. For example, a dual
        processor system that contains two processors
        enabled for hyperthreading can run four threads or
        programs or simultaneously. In this case,
        NumberOfCores is 2 and NumberOfLogicalProcessors is
        4."
    ::= { win32ProcessorEntry 49 }

win32SCSIControllerTable OBJECT-TYPE
    SYNTAX     SEQUENCE OF Win32SCSIControllerEntry
    MAX-ACCESS not-accessible
    STATUS     current
    DESCRIPTION
        "The Win32_SCSIController WMI class represents a
        SCSI controller on a Windows system."
    ::= { wmiMotherboardControllerPort 25 }

win32SCSIControllerEntry OBJECT-TYPE
    SYNTAX     Win32SCSIControllerEntry
    MAX-ACCESS not-accessible
    STATUS     current
    DESCRIPTION
        "None"
    INDEX      { hwscsiIndex }
    ::= { win32SCSIControllerTable 1 }

Win32SCSIControllerEntry ::= SEQUENCE {
    hwscsiIndex Integer32,
    hwscsiAvailability INTEGER,
    hwscsiCaption DisplayString,
    hwscsiConfigManagerErrorCode INTEGER,
    hwscsiConfigManagerUserConfig TruthValue,
    hwscsiControllerTimeouts Gauge32,
    hwscsiCreationClassName DisplayString,
    hwscsiDescription DisplayString,
    hwscsiDeviceID DisplayString,
    hwscsiDeviceMap DisplayString,
    hwscsiDriverName DisplayString,
    hwscsiErrorCleared TruthValue,
    hwscsiErrorDescription DisplayString,
    hwscsiHardwareVersion DisplayString,
    hwscsiRegistryIndex Gauge32,
    hwscsiInstallDate DateAndTime,
    hwscsiLastErrorCode Gauge32,
    hwscsiManufacturer DisplayString,
    hwscsiMaxDataWidth Gauge32,
    hwscsiMaxNumberControlled Gauge32,
    hwscsiMaxTransferRate Gauge32,
    hwscsiName DisplayString,
    hwscsiPNPDeviceID DisplayString,
    hwscsiPowerManagementCapability DisplayString,
    hwscsiPowerManagementSupported TruthValue,
    hwscsiProtectionManagement INTEGER,
    hwscsiProtocolSupported INTEGER,
    hwscsiStatus INTEGER,
    hwscsiStatusInfo INTEGER,
    hwscsiSystemCreationClassName DisplayString,
    hwscsiSystemName DisplayString,
    hwscsiTimeOfLastReset DateAndTime
}

hwscsiIndex OBJECT-TYPE
    SYNTAX     Integer32 (1..2147483647)
    MAX-ACCESS read-only
    STATUS     current
    DESCRIPTION
        "The value of this object uniquely identifies the
        instance entry for this class."
    ::= { win32SCSIControllerEntry 1 }

hwscsiAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32SCSIControllerEntry 2 }

hwscsiCaption OBJECT-TYPE
    SYNTAX     DisplayString (SIZE (0..64))
    MAX-ACCESS read-only
    STATUS     current
    DESCRIPTION
        "Short description (one-line string) of the object.
        This property is inherited from
        CIM_ManagedSystemElement."
    ::= { win32SCSIControllerEntry 3 }

hwscsiConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. . This
        property is inherited from CIM_LogicalDevice."
    ::= { win32SCSIControllerEntry 4 }

hwscsiConfigManagerUserConfig OBJECT-TYPE
    SYNTAX     TruthValue
    MAX-ACCESS read-only
    STATUS     current
    DESCRIPTION
        "If TRUE, the device is using a user-defined
        configuration. This property is inherited from
        CIM_LogicalDevice."
    ::= { win32SCSIControllerEntry 5 }

hwscsiControllerTimeouts OBJECT-TYPE
    SYNTAX     Gauge32
    MAX-ACCESS read-only
    STATUS     current
    DESCRIPTION
        "Number of timeouts that have occurred after the
        TimeOfLastReset value. This property is inherited
        from CIM_SCSIController."
    ::= { win32SCSIControllerEntry 6 }

hwscsiCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32SCSIControllerEntry 7 }

hwscsiDescription OBJECT-TYPE
    SYNTAX     DisplayString
    MAX-ACCESS read-only
    STATUS     current
    DESCRIPTION
        "Description of the object. This property is
        inherited from CIM_ManagedSystemElement."
    ::= { win32SCSIControllerEntry 8 }

hwscsiDeviceID OBJECT-TYPE
    SYNTAX     DisplayString
    MAX-ACCESS read-only
    STATUS     current
    DESCRIPTION
        "Unique identifier of the SCSI controller with
        other devices on the system. This property is
        inherited from CIM_LogicalDevice."
    ::= { win32SCSIControllerEntry 9 }

hwscsiDeviceMap OBJECT-TYPE
    SYNTAX     DisplayString
    MAX-ACCESS read-only
    STATUS     current
    DESCRIPTION
        "Order in which devices are listed with this SCSI
        controller."
    ::= { win32SCSIControllerEntry 10 }

hwscsiDriverName OBJECT-TYPE
    SYNTAX     DisplayString
    MAX-ACCESS read-only
    STATUS     current
    DESCRIPTION
        "Driver file name of the SCSI controller.
        Example: 'Adaptec'"
    ::= { win32SCSIControllerEntry 11 }

hwscsiErrorCleared OBJECT-TYPE
    SYNTAX     TruthValue
    MAX-ACCESS read-only
    STATUS     current
    DESCRIPTION
        "If TRUE, the error reported in LastErrorCode is
        now cleared. This property is inherited from
        CIM_LogicalDevice."
    ::= { win32SCSIControllerEntry 12 }

hwscsiErrorDescription OBJECT-TYPE
    SYNTAX     DisplayString
    MAX-ACCESS read-only
    STATUS     current
    DESCRIPTION
        "Free-form string supplying more information about
        the error recorded in LastErrorCode, and
        information on any corrective actions that may be
        taken. This property is inherited from
        CIM_LogicalDevice."
    ::= { win32SCSIControllerEntry 13 }

hwscsiHardwareVersion OBJECT-TYPE
    SYNTAX     DisplayString
    MAX-ACCESS read-only
    STATUS     current
    DESCRIPTION
        "Hardware version number of the SCSI controller.
        Example: '1.25'"
    ::= { win32SCSIControllerEntry 14 }

hwscsiRegistryIndex OBJECT-TYPE
    SYNTAX     Gauge32
    MAX-ACCESS read-only
    STATUS     current
    DESCRIPTION
        "Index number of the SCSI controller in the system
        registry.
        Example: 0"
    ::= { win32SCSIControllerEntry 15 }

hwscsiInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32SCSIControllerEntry 16 }

hwscsiLastErrorCode OBJECT-TYPE
    SYNTAX     Gauge32
    MAX-ACCESS read-only
    STATUS     current
    DESCRIPTION
        "Last error code reported by the logical device.
        This property is inherited from CIM_LogicalDevice."
    ::= { win32SCSIControllerEntry 17 }

hwscsiManufacturer OBJECT-TYPE
    SYNTAX     DisplayString
    MAX-ACCESS read-only
    STATUS     current
    DESCRIPTION
        "Name of the SCSI controller manufacturer.
        Example: 'Adaptec'"
    ::= { win32SCSIControllerEntry 18 }

hwscsiMaxDataWidth OBJECT-TYPE
    SYNTAX     Gauge32
    MAX-ACCESS read-only
    STATUS     current
    DESCRIPTION
        "Maximum data width (in bits) supported by the SCSI
        controller. This property is inherited from
        CIM_SCSIController."
    ::= { win32SCSIControllerEntry 19 }

hwscsiMaxNumberControlled OBJECT-TYPE
    SYNTAX     Gauge32
    MAX-ACCESS read-only
    STATUS     current
    DESCRIPTION
        "Maximum number of directly addressable entities
        supportable by this controller. A value of 0 should
        be used if the number is unknown. This property is
        inherited from CIM_Controller."
    ::= { win32SCSIControllerEntry 20 }

hwscsiMaxTransferRate OBJECT-TYPE
    SYNTAX     Gauge32
    MAX-ACCESS read-only
    STATUS     current
    DESCRIPTION
        "Maximum transfer rate (in bits per second)
        supported by the SCSI controller. This property is
        inherited from CIM_SCSIController."
    ::= { win32SCSIControllerEntry 21 }

hwscsiName OBJECT-TYPE
    SYNTAX     DisplayString
    MAX-ACCESS read-only
    STATUS     current
    DESCRIPTION
        "Label by which the object is known. When
        subclassed, the property can be overridden to be a
        key property. This property is inherited from
        CIM_ManagedSystemElement."
    ::= { win32SCSIControllerEntry 22 }

hwscsiPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32SCSIControllerEntry 23 }

hwscsiPowerManagementCapability OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32SCSIControllerEntry 24 }

hwscsiPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32SCSIControllerEntry 25 }

hwscsiProtectionManagement OBJECT-TYPE
    SYNTAX     INTEGER {
        other(1),
        unknown(2),
        unprotected(3),
        protected(4),
        protectedThroughSCC(5),
        protectedThroughSCC2(6)
    }
    MAX-ACCESS read-only
    STATUS     current
    DESCRIPTION
        "Support of the SCSI controller for redundancy or
        protection against device failures. This property
        is inherited from CIM_SCSIController."
    ::= { win32SCSIControllerEntry 26 }

hwscsiProtocolSupported OBJECT-TYPE
    SYNTAX     INTEGER {
        other(0),
        unknown(1),
        eisa(2),
        isa(3),
        pci(4),
        ataATAPI(5),
        flexibleDiskette(6),
        n1496(7),
        scsiParallelInterface(8),
        scsiFibreChannelProtocol(9),
        scsiSerialBusProtocol(10),
        scsiSerialBusProtocol1394(11),
        scsiSerialStorageArchitecture(12),
        vesa(13),
        pcmcia(14),
        universalSerialBus(15),
        parallelProtocol(16),
        escon(17),
        diagnostic(18),
        i2C(19),
        power(20),
        hippi(21),
        multiBus(22),
        vme(23),
        ipi(24),
        ieee488(25),
        rs232(26),
        ieee802310BASE5(27),
        ieee802310BASE2(28),
        ieee80231BASE5(29),
        ieee802310BROAD36(30),
        ieee8023100BASEVG(31),
        ieee8025TokenRing(32),
        ansiX3T95FDDI(33),
        mca(34),
        esdi(35),
        ide(36),
        cmd(37),
        st506(38),
        dssi(39),
        qic2(40),
        enhancedATAIDE(41),
        agp(42),
        twowayInfrared(43),
        fastInfrared(44),
        serialInfrared(45),
        irBus(46)
    }
    MAX-ACCESS read-only
    STATUS     current
    DESCRIPTION
        "Protocol used by the controller to access
        'controlled' devices. This property is inherited
        from CIM_Controller."
    ::= { win32SCSIControllerEntry 27 }

hwscsiStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SCSIControllerEntry 28 }

hwscsiStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32SCSIControllerEntry 29 }

hwscsiSystemCreationClassName OBJECT-TYPE
    SYNTAX     DisplayString
    MAX-ACCESS read-only
    STATUS     current
    DESCRIPTION
        "Value of the scoping computer's CreationClassName
        property. This property is inherited from
        CIM_LogicalDevice."
    ::= { win32SCSIControllerEntry 30 }

hwscsiSystemName OBJECT-TYPE
    SYNTAX     DisplayString
    MAX-ACCESS read-only
    STATUS     current
    DESCRIPTION
        "Name of the scoping system. This property is
        inherited from CIM_LogicalDevice."
    ::= { win32SCSIControllerEntry 31 }

hwscsiTimeOfLastReset OBJECT-TYPE
    SYNTAX     DateAndTime
    MAX-ACCESS read-only
    STATUS     current
    DESCRIPTION
        "Date and time this controller was last reset. This
        could mean the controller was powered down, or
        reinitialized. This property is inherited from
        CIM_Controller."
    ::= { win32SCSIControllerEntry 32 }

win32SerialPortTable OBJECT-TYPE
    SYNTAX     SEQUENCE OF Win32SerialPortEntry
    MAX-ACCESS not-accessible
    STATUS     current
    DESCRIPTION
        "The Win32_SerialPort WMI class represents a serial
        port on a Windows system."
    ::= { wmiMotherboardControllerPort 26 }

win32SerialPortEntry OBJECT-TYPE
    SYNTAX     Win32SerialPortEntry
    MAX-ACCESS not-accessible
    STATUS     current
    DESCRIPTION
        "None"
    INDEX      { hwspIndex }
    ::= { win32SerialPortTable 1 }

Win32SerialPortEntry ::= SEQUENCE {
    hwspIndex Integer32,
    hwspAvailability INTEGER,
    hwspBinary TruthValue,
    hwspCapabilities DisplayString,
    hwspCapabilityDescriptions DisplayString,
    hwspCaption DisplayString,
    hwspConfigManagerErrorCode INTEGER,
    hwspConfigManagerUserConfig TruthValue,
    hwspCreationClassName DisplayString,
    hwspDescription DisplayString,
    hwspDeviceID DisplayString,
    hwspErrorCleared TruthValue,
    hwspErrorDescription DisplayString,
    hwspInstallDate DateAndTime,
    hwspLastErrorCode Gauge32,
    hwspMaxBaudRate Gauge32,
    hwspMaximumInputBufferSize Gauge32,
    hwspMaximumOutputBufferSize Gauge32,
    hwspMaxNumberControlled Gauge32,
    hwspName DisplayString,
    hwspOSAutoDiscovered TruthValue,
    hwspPNPDeviceID DisplayString,
    hwspPowerManagementCapabilities DisplayString,
    hwspPowerManagementSupported TruthValue,
    hwspProtocolSupported INTEGER,
    hwspProviderType DisplayString,
    hwspSettableBaudRate TruthValue,
    hwspSettableDataBits TruthValue,
    hwspSettableFlowControl TruthValue,
    hwspSettableParity TruthValue,
    hwspSettableParityCheck TruthValue,
    hwspSettableRLSD TruthValue,
    hwspSettableStopBits TruthValue,
    hwspStatus INTEGER,
    hwspStatusInfo INTEGER,
    hwspSupports16BitMode TruthValue,
    hwspSupportsDTRDSR TruthValue,
    hwspSupportsElapsedTimeouts TruthValue,
    hwspSupportsIntTimeouts TruthValue,
    hwspSupportsParityCheck TruthValue,
    hwspSupportsRLSD TruthValue,
    hwspSupportsRTSCTS TruthValue,
    hwspSupportsSpecialCharacters TruthValue,
    hwspSupportsXOnXOff TruthValue,
    hwspSupportsXOnXOffSet TruthValue,
    hwspSystemCreationClassName DisplayString,
    hwspSystemName DisplayString,
    hwspTimeOfLastReset DateAndTime
}

hwspIndex OBJECT-TYPE
    SYNTAX     Integer32 (1..2147483647)
    MAX-ACCESS read-only
    STATUS     current
    DESCRIPTION
        "The value of this object uniquely identifies the
        instance entry for this class."
    ::= { win32SerialPortEntry 1 }

hwspAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32SerialPortEntry 2 }

hwspBinary OBJECT-TYPE
    SYNTAX     TruthValue
    MAX-ACCESS read-only
    STATUS     current
    DESCRIPTION
        "If TRUE, the serial port is configured for binary
        data transfer. Because the Windows API does not
        support non-binary mode transfers, this property
        must be TRUE."
    ::= { win32SerialPortEntry 3 }

hwspCapabilities OBJECT-TYPE
    SYNTAX     DisplayString
    MAX-ACCESS read-only
    STATUS     current
    DESCRIPTION
        "Array of chip-level compatibility for the serial
        controller. This property describes the buffering
        and other capabilities of the serial controller
        that may be inherent in the chip hardware. The
        property is an enumerated integer. This property is
        inherited from CIM_SerialController.
        Value Meaning 
        1 Other 
        2 Unknown 
        3 XT/AT Compatible 
        4 16450 Compatible 
        5 16550 Compatible 
        6 16550A Compatible 
        160 8251 Compatible 
        161 8251FIFO Compatible "
    ::= { win32SerialPortEntry 4 }

hwspCapabilityDescriptions OBJECT-TYPE
    SYNTAX     DisplayString
    MAX-ACCESS read-only
    STATUS     current
    DESCRIPTION
        "Array of free-form strings providing more detailed
        explanations for any of the serial controller
        features indicated in the Capabilities array. Note,
        each entry of this array is related to the entry in
        the Capabilities array that is located at the same
        index. This property is inherited from
        CIM_SerialController."
    ::= { win32SerialPortEntry 5 }

hwspCaption OBJECT-TYPE
    SYNTAX     DisplayString (SIZE (0..64))
    MAX-ACCESS read-only
    STATUS     current
    DESCRIPTION
        "Short description (one-line string) of the object.
        This property is inherited from
        CIM_ManagedSystemElement."
    ::= { win32SerialPortEntry 6 }

hwspConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. . This
        property is inherited from CIM_LogicalDevice."
    ::= { win32SerialPortEntry 7 }

hwspConfigManagerUserConfig OBJECT-TYPE
    SYNTAX     TruthValue
    MAX-ACCESS read-only
    STATUS     current
    DESCRIPTION
        "If TRUE, the device is using a user-defined
        configuration. This property is inherited from
        CIM_LogicalDevice."
    ::= { win32SerialPortEntry 8 }

hwspCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32SerialPortEntry 9 }

hwspDescription OBJECT-TYPE
    SYNTAX     DisplayString
    MAX-ACCESS read-only
    STATUS     current
    DESCRIPTION
        "Description of the object. This property is
        inherited from CIM_ManagedSystemElement."
    ::= { win32SerialPortEntry 10 }

hwspDeviceID OBJECT-TYPE
    SYNTAX     DisplayString
    MAX-ACCESS read-only
    STATUS     current
    DESCRIPTION
        "Unique identifier of the serial port with other
        devices on the system. This property is inherited
        from CIM_LogicalDevice."
    ::= { win32SerialPortEntry 11 }

hwspErrorCleared OBJECT-TYPE
    SYNTAX     TruthValue
    MAX-ACCESS read-only
    STATUS     current
    DESCRIPTION
        "If TRUE, the error reported in LastErrorCode is
        now cleared. This property is inherited from
        CIM_LogicalDevice."
    ::= { win32SerialPortEntry 12 }

hwspErrorDescription OBJECT-TYPE
    SYNTAX     DisplayString
    MAX-ACCESS read-only
    STATUS     current
    DESCRIPTION
        "Free-form string supplying more information about
        the error recorded in LastErrorCode, and
        information on any corrective actions that may be
        taken. This property is inherited from
        CIM_LogicalDevice."
    ::= { win32SerialPortEntry 13 }

hwspInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32SerialPortEntry 14 }

hwspLastErrorCode OBJECT-TYPE
    SYNTAX     Gauge32
    MAX-ACCESS read-only
    STATUS     current
    DESCRIPTION
        "Last error code reported by the logical device.
        This property is inherited from CIM_LogicalDevice."
    ::= { win32SerialPortEntry 15 }

hwspMaxBaudRate OBJECT-TYPE
    SYNTAX     Gauge32
    UNITS "Bits per second"
    MAX-ACCESS read-only
    STATUS     current
    DESCRIPTION
        "Maximum baud rate (in bits per second) supported
        by the serial controller. This property is
        inherited from CIM_SerialController."
    ::= { win32SerialPortEntry 16 }

hwspMaximumInputBufferSize OBJECT-TYPE
    SYNTAX     Gauge32
    UNITS "Bytes"
    MAX-ACCESS read-only
    STATUS     current
    DESCRIPTION
        "Maximum size of the serial port driver's internal
        input buffer. A value of 0 indicates that no
        maximum value is imposed by the serial provider."
    ::= { win32SerialPortEntry 17 }

hwspMaximumOutputBufferSize OBJECT-TYPE
    SYNTAX     Gauge32
    UNITS "Bytes"
    MAX-ACCESS read-only
    STATUS     current
    DESCRIPTION
        "Maximum size of the serial port driver's internal
        output buffer. A value of 0 indicates that no
        maximum value is imposed by the serial provider."
    ::= { win32SerialPortEntry 18 }

hwspMaxNumberControlled OBJECT-TYPE
    SYNTAX     Gauge32
    MAX-ACCESS read-only
    STATUS     current
    DESCRIPTION
        "Maximum number of directly addressable entities
        supportable by this controller. A value of 0 should
        be used if the number is unknown. This property is
        inherited from CIM_Controller."
    ::= { win32SerialPortEntry 19 }

hwspName OBJECT-TYPE
    SYNTAX     DisplayString
    MAX-ACCESS read-only
    STATUS     current
    DESCRIPTION
        "Label by which the object is known. When
        subclassed, the property can be overridden to be a
        key property. This property is inherited from
        CIM_ManagedSystemElement."
    ::= { win32SerialPortEntry 20 }

hwspOSAutoDiscovered OBJECT-TYPE
    SYNTAX     TruthValue
    MAX-ACCESS read-only
    STATUS     current
    DESCRIPTION
        "If TRUE, the instances of this class were
        automatically discovered by the operating system.
        If, for example, hardware was added through the
        Control Panel, the operating system finds instances
        of this class by querying hardware from the
        instances of this class."
    ::= { win32SerialPortEntry 21 }

hwspPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32SerialPortEntry 22 }

hwspPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32SerialPortEntry 23 }

hwspPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management."
    ::= { win32SerialPortEntry 24 }

hwspProtocolSupported OBJECT-TYPE
    SYNTAX     INTEGER {
        other(0),
        unknown(1),
        eisa(2),
        isa(3),
        pci(4),
        ataATAPI(5),
        flexibleDiskette(6),
        n1496(7),
        scsiParallelInterface(8),
        scsiFibreChannelProtocol(9),
        scsiSerialBusProtocol(10),
        scsiSerialBusProtocol1394(11),
        scsiSerialStorageArchitecture(12),
        vesa(13),
        pcmcia(14),
        universalSerialBus(15),
        parallelProtocol(16),
        escon(17),
        diagnostic(18),
        i2C(19),
        power(20),
        hippi(21),
        multiBus(22),
        vme(23),
        ipi(24),
        ieee488(25),
        rs232(26),
        ieee802310BASE5(27),
        ieee802310BASE2(28),
        ieee80231BASE5(29),
        ieee802310BROAD36(30),
        ieee8023100BASEVG(31),
        ieee8025TokenRing(32),
        ansiX3T95FDDI(33),
        mca(34),
        esdi(35),
        ide(36),
        cmd(37),
        st506(38),
        dssi(39),
        qic2(40),
        enhancedATAIDE(41),
        agp(42),
        twowayInfrared(43),
        fastInfrared(44),
        serialInfrared(45),
        irBus(46)
    }
    MAX-ACCESS read-only
    STATUS     current
    DESCRIPTION
        "Protocol used by the controller to access
        'controlled' devices. This property is inherited
        from CIM_Controller."
    ::= { win32SerialPortEntry 25 }

hwspProviderType OBJECT-TYPE
    SYNTAX     DisplayString
    MAX-ACCESS read-only
    STATUS     current
    DESCRIPTION
        "Communications provider type. Values are:
        'FAX Device'
        'LAT Protocol'
        'Modem Device'
        'Network Bridge'
        'Parallel Port'
        'RS232 Serial Port'
        'RS422 Port'
        'RS423 Port'
        'RS449 Port'
        'Scanner Device'
        'TCP/IP TelNet'
        'X.25'
        'Unspecified'"
    ::= { win32SerialPortEntry 26 }

hwspSettableBaudRate OBJECT-TYPE
    SYNTAX     TruthValue
    MAX-ACCESS read-only
    STATUS     current
    DESCRIPTION
        "If TRUE, the baud rate can be changed for this
        serial port."
    ::= { win32SerialPortEntry 27 }

hwspSettableDataBits OBJECT-TYPE
    SYNTAX     TruthValue
    MAX-ACCESS read-only
    STATUS     current
    DESCRIPTION
        "If TRUE, data bits can be set for this serial
        port."
    ::= { win32SerialPortEntry 28 }

hwspSettableFlowControl OBJECT-TYPE
    SYNTAX     TruthValue
    MAX-ACCESS read-only
    STATUS     current
    DESCRIPTION
        "If TRUE, flow control can be set for this serial
        port."
    ::= { win32SerialPortEntry 29 }

hwspSettableParity OBJECT-TYPE
    SYNTAX     TruthValue
    MAX-ACCESS read-only
    STATUS     current
    DESCRIPTION
        "If TRUE, parity can be set for this serial port."
    ::= { win32SerialPortEntry 30 }

hwspSettableParityCheck OBJECT-TYPE
    SYNTAX     TruthValue
    MAX-ACCESS read-only
    STATUS     current
    DESCRIPTION
        "If TRUE, parity checking can be set for this
        serial port (if parity checking is supported)."
    ::= { win32SerialPortEntry 31 }

hwspSettableRLSD OBJECT-TYPE
    SYNTAX     TruthValue
    MAX-ACCESS read-only
    STATUS     current
    DESCRIPTION
        "If TRUE, Received Line Signal Detect (RLSD) can be
        set for this serial port (if RLSD is supported)."
    ::= { win32SerialPortEntry 32 }

hwspSettableStopBits OBJECT-TYPE
    SYNTAX     TruthValue
    MAX-ACCESS read-only
    STATUS     current
    DESCRIPTION
        "If TRUE, stop bits can be set for this serial
        port."
    ::= { win32SerialPortEntry 33 }

hwspStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SerialPortEntry 34 }

hwspStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32SerialPortEntry 35 }

hwspSupports16BitMode OBJECT-TYPE
    SYNTAX     TruthValue
    MAX-ACCESS read-only
    STATUS     current
    DESCRIPTION
        "If TRUE, 16-bit mode is supported on this serial
        port."
    ::= { win32SerialPortEntry 36 }

hwspSupportsDTRDSR OBJECT-TYPE
    SYNTAX     TruthValue
    MAX-ACCESS read-only
    STATUS     current
    DESCRIPTION
        "If TRUE, Data Terminal Ready (DTR) and Data Set
        Ready (DSR) signals are supported on this serial
        port."
    ::= { win32SerialPortEntry 37 }

hwspSupportsElapsedTimeouts OBJECT-TYPE
    SYNTAX     TruthValue
    MAX-ACCESS read-only
    STATUS     current
    DESCRIPTION
        "If TRUE, elapsed timeouts are supported on this
        serial port. Elapsed timeouts track the total
        amount of time between data transmissions."
    ::= { win32SerialPortEntry 38 }

hwspSupportsIntTimeouts OBJECT-TYPE
    SYNTAX     TruthValue
    MAX-ACCESS read-only
    STATUS     current
    DESCRIPTION
        "If TRUE, interval timeouts are supported. An
        interval timeout is the amount of time allowed to
        elapse between the arrival of each piece of data."
    ::= { win32SerialPortEntry 39 }

hwspSupportsParityCheck OBJECT-TYPE
    SYNTAX     TruthValue
    MAX-ACCESS read-only
    STATUS     current
    DESCRIPTION
        "If TRUE, parity checking is supported on this
        serial port."
    ::= { win32SerialPortEntry 40 }

hwspSupportsRLSD OBJECT-TYPE
    SYNTAX     TruthValue
    MAX-ACCESS read-only
    STATUS     current
    DESCRIPTION
        "If TRUE, Received Line Signal Detect (RLSD) is
        supported on this serial port."
    ::= { win32SerialPortEntry 41 }

hwspSupportsRTSCTS OBJECT-TYPE
    SYNTAX     TruthValue
    MAX-ACCESS read-only
    STATUS     current
    DESCRIPTION
        "If TRUE, Ready To Send (RTS) and Clear To Send
        (CTS) signals are supported on this serial port."
    ::= { win32SerialPortEntry 42 }

hwspSupportsSpecialCharacters OBJECT-TYPE
    SYNTAX     TruthValue
    MAX-ACCESS read-only
    STATUS     current
    DESCRIPTION
        "If TRUE, serial port control characters are
        supported. These characters signal events rather
        than data. These characters are not displayable and
        are set by the driver. They include EofChar,
        ErrorChar, BreakChar, EventChar, XonChar, and
        XoffChar."
    ::= { win32SerialPortEntry 43 }

hwspSupportsXOnXOff OBJECT-TYPE
    SYNTAX     TruthValue
    MAX-ACCESS read-only
    STATUS     current
    DESCRIPTION
        "If TRUE, XON/XOFF flow control is supported on
        this serial port."
    ::= { win32SerialPortEntry 44 }

hwspSupportsXOnXOffSet OBJECT-TYPE
    SYNTAX     TruthValue
    MAX-ACCESS read-only
    STATUS     current
    DESCRIPTION
        "If TRUE, the communications provider supports
        configuration of the XON/XOFF flow control
        setting."
    ::= { win32SerialPortEntry 45 }

hwspSystemCreationClassName OBJECT-TYPE
    SYNTAX     DisplayString
    MAX-ACCESS read-only
    STATUS     current
    DESCRIPTION
        "Value of the scoping computer's CreationClassName
        property. This property is inherited from
        CIM_LogicalDevice."
    ::= { win32SerialPortEntry 46 }

hwspSystemName OBJECT-TYPE
    SYNTAX     DisplayString
    MAX-ACCESS read-only
    STATUS     current
    DESCRIPTION
        "Name of the scoping system. This property is
        inherited from CIM_LogicalDevice."
    ::= { win32SerialPortEntry 47 }

hwspTimeOfLastReset OBJECT-TYPE
    SYNTAX     DateAndTime
    MAX-ACCESS read-only
    STATUS     current
    DESCRIPTION
        "Date and time this controller was last reset. This
        could mean the controller was powered down, or
        reinitialized. This property is inherited from
        CIM_Controller."
    ::= { win32SerialPortEntry 48 }

win32SerialPortConfigTable OBJECT-TYPE
    SYNTAX     SEQUENCE OF Win32SerialPortConfigEntry
    MAX-ACCESS not-accessible
    STATUS     current
    DESCRIPTION
        "The Win32_SerialPortConfiguration WMI class
        represents the settings for data transmission on a
        Windows serial port. This includes configurations
        for establishing a connection and error checking."
    ::= { wmiMotherboardControllerPort 27 }

win32SerialPortConfigEntry OBJECT-TYPE
    SYNTAX     Win32SerialPortConfigEntry
    MAX-ACCESS not-accessible
    STATUS     current
    DESCRIPTION
        "None"
    INDEX      { hwspcIndex }
    ::= { win32SerialPortConfigTable 1 }

Win32SerialPortConfigEntry ::= SEQUENCE {
    hwspcIndex Integer32,
    hwspcAbortReadWriteOnError TruthValue,
    hwspcBaudRate Gauge32,
    hwspcBinaryModeEnabled TruthValue,
    hwspcBitsPerByte Gauge32,
    hwspcCaption DisplayString,
    hwspcContinueXMitOnXOff TruthValue,
    hwspcCTSOutflowControl TruthValue,
    hwspcDescription DisplayString,
    hwspcDiscardNULLBytes TruthValue,
    hwspcDSROutflowControl TruthValue,
    hwspcDSRSensitivity TruthValue,
    hwspcDTRFlowControlType INTEGER,
    hwspcEOFCharacter Gauge32,
    hwspcErrorReplaceCharacter Gauge32,
    hwspcErrorReplacementEnabled TruthValue,
    hwspcEventCharacter Gauge32,
    hwspcIsBusy TruthValue,
    hwspcName DisplayString,
    hwspcParity DisplayString,
    hwspcParityCheckEnabled TruthValue,
    hwspcRTSFlowControlType DisplayString,
    hwspcSettingID DisplayString,
    hwspcStopBits DisplayString,
    hwspcXOffCharacter Gauge32,
    hwspcXOffXMitThreshold Gauge32,
    hwspcXOnCharacter Gauge32,
    hwspcXOnXMitThreshold Gauge32,
    hwspcXOnXOffInFlowControl INTEGER,
    hwspcXOnXOffOutFlowControl Gauge32
}

hwspcIndex OBJECT-TYPE
    SYNTAX     Integer32 (1..2147483647)
    MAX-ACCESS read-only
    STATUS     current
    DESCRIPTION
        "The value of this object uniquely identifies the
        instance entry for this class."
    ::= { win32SerialPortConfigEntry 1 }

hwspcAbortReadWriteOnError OBJECT-TYPE
    SYNTAX     TruthValue
    MAX-ACCESS read-only
    STATUS     current
    DESCRIPTION
        "If TRUE, read and write operations are terminated
        if an error occurs. If TRUE, the driver terminates
        all read and write operations with an error status
        if an error occurs. The driver will not accept any
        further communications operations until the
        application acknowledges the error."
    ::= { win32SerialPortConfigEntry 2 }

hwspcBaudRate OBJECT-TYPE
    SYNTAX     Gauge32
    MAX-ACCESS read-only
    STATUS     current
    DESCRIPTION
        "Baud (bits per second) rate at which the
        communications device operates.
        Example: 9600"
    ::= { win32SerialPortConfigEntry 3 }

hwspcBinaryModeEnabled OBJECT-TYPE
    SYNTAX     TruthValue
    MAX-ACCESS read-only
    STATUS     current
    DESCRIPTION
        "If TRUE, binary-mode data transfers are enabled
        for the serial port. Windows systems only allow
        binary transfers through serial ports, so this
        value is always TRUE."
    ::= { win32SerialPortConfigEntry 4 }

hwspcBitsPerByte OBJECT-TYPE
    SYNTAX     Gauge32
    MAX-ACCESS read-only
    STATUS     current
    DESCRIPTION
        "Number of bits transmitted and received for each
        byte of data for the Windows serial port. The
        number may vary with control and error correction
        bits, such as parity bits.
        Example: 8"
    ::= { win32SerialPortConfigEntry 5 }

hwspcCaption OBJECT-TYPE
    SYNTAX     DisplayString (SIZE (0..64))
    MAX-ACCESS read-only
    STATUS     current
    DESCRIPTION
        "Short description (one-line string) of the
        CIM_Setting object. This property is inherited from
        CIM_Setting."
    ::= { win32SerialPortConfigEntry 6 }

hwspcContinueXMitOnXOff OBJECT-TYPE
    SYNTAX     TruthValue
    MAX-ACCESS read-only
    STATUS     current
    DESCRIPTION
        "If TRUE, data transmissions continue when the
        input buffer has come within XOffXMitThreshold
        bytes of being full and the driver has transmitted
        the XOffChararcter value to stop receiving bytes.
        If FALSE, transmission does not continue until the
        input buffer is within XOnXMitThreshold bytes of
        being empty and the driver has transmitted the
        XOnCharacter value to resume reception."
    ::= { win32SerialPortConfigEntry 7 }

hwspcCTSOutflowControl OBJECT-TYPE
    SYNTAX     TruthValue
    MAX-ACCESS read-only
    STATUS     current
    DESCRIPTION
        "If TRUE, the Clear To Send (CTS) signal is checked
        before transmitting data. CTS signals that both
        devices on the serial connection are ready to
        transfer data. Data transmission is suspended until
        the CTS signal is given."
    ::= { win32SerialPortConfigEntry 8 }

hwspcDescription OBJECT-TYPE
    SYNTAX     DisplayString
    MAX-ACCESS read-only
    STATUS     current
    DESCRIPTION
        "Description of the CIM_Setting object. This
        property is inherited from CIM_Setting."
    ::= { win32SerialPortConfigEntry 9 }

hwspcDiscardNULLBytes OBJECT-TYPE
    SYNTAX     TruthValue
    MAX-ACCESS read-only
    STATUS     current
    DESCRIPTION
        "If TRUE, NULL bytes (characters) are discarded
        when they are received."
    ::= { win32SerialPortConfigEntry 10 }

hwspcDSROutflowControl OBJECT-TYPE
    SYNTAX     TruthValue
    MAX-ACCESS read-only
    STATUS     current
    DESCRIPTION
        "If TRUE, data outflow control is enabled when
        there is a Data Set Ready (DSR) condition. DSR
        signals that the connection has been established by
        the devices on the serial connection. DSR data
        transmission is suspended until DSR signal is
        given."
    ::= { win32SerialPortConfigEntry 11 }

hwspcDSRSensitivity OBJECT-TYPE
    SYNTAX     TruthValue
    MAX-ACCESS read-only
    STATUS     current
    DESCRIPTION
        "If TRUE, the communications driver is sensitive to
        the state of the DSR signal. The driver ignores any
        bytes received, unless the DSR modem input line is
        high."
    ::= { win32SerialPortConfigEntry 12 }

hwspcDTRFlowControlType OBJECT-TYPE
    SYNTAX     INTEGER {
        enable(1),
        disable(2),
        handshake(3)
    }
    MAX-ACCESS read-only
    STATUS     current
    DESCRIPTION
        "Use of the data-terminal-ready (DTR) flow control
        after a connection has been established."
    ::= { win32SerialPortConfigEntry 13 }

hwspcEOFCharacter OBJECT-TYPE
    SYNTAX     Gauge32
    MAX-ACCESS read-only
    STATUS     current
    DESCRIPTION
        "Value of the character used to signal the end of
        data.
        Example: ^Z"
    ::= { win32SerialPortConfigEntry 14 }

hwspcErrorReplaceCharacter OBJECT-TYPE
    SYNTAX     Gauge32
    MAX-ACCESS read-only
    STATUS     current
    DESCRIPTION
        "Value of the character used to replace bytes
        received with a parity error.
        Example: ^C"
    ::= { win32SerialPortConfigEntry 15 }

hwspcErrorReplacementEnabled OBJECT-TYPE
    SYNTAX     TruthValue
    MAX-ACCESS read-only
    STATUS     current
    DESCRIPTION
        "If TRUE, bytes received with parity errors are
        replaced with the ErrorReplaceCharacter value.
        Characters with parity errors are only replaced if
        this property is TRUE and the parity is enabled."
    ::= { win32SerialPortConfigEntry 16 }

hwspcEventCharacter OBJECT-TYPE
    SYNTAX     Gauge32
    MAX-ACCESS read-only
    STATUS     current
    DESCRIPTION
        "Value of the control character that is used to
        signal an event, such as end of file.
        Example: ^e"
    ::= { win32SerialPortConfigEntry 17 }

hwspcIsBusy OBJECT-TYPE
    SYNTAX     TruthValue
    MAX-ACCESS read-only
    STATUS     current
    DESCRIPTION
        "If TRUE, the serial port is busy."
    ::= { win32SerialPortConfigEntry 18 }

hwspcName OBJECT-TYPE
    SYNTAX     DisplayString (SIZE (0..256))
    MAX-ACCESS read-only
    STATUS     current
    DESCRIPTION
        "Name of the Windows serial port.
        Example: 'COM1'"
    ::= { win32SerialPortConfigEntry 19 }

hwspcParity OBJECT-TYPE
    SYNTAX     DisplayString
    MAX-ACCESS read-only
    STATUS     current
    DESCRIPTION
        "Method of parity checking to be used. Parity is
        used as an error checking technique where an extra
        parity bit is included with every unit of data. The
        receiver can then verify the validity of the data
        by counting the bits that are set.
        
        Value Meaning 
        'None' Parity checking not used 
        'Odd' Sets the parity bit so that the count of bits
        set is an odd number 
        'Even' Sets the parity bit so that the count of
        bits set is an even number 
        'Mark' Leaves the parity bit set to 1 
        'Space' Leaves the parity bit set to 0"
    ::= { win32SerialPortConfigEntry 20 }

hwspcParityCheckEnabled OBJECT-TYPE
    SYNTAX     TruthValue
    MAX-ACCESS read-only
    STATUS     current
    DESCRIPTION
        "If TRUE, parity checking is enabled."
    ::= { win32SerialPortConfigEntry 21 }

hwspcRTSFlowControlType OBJECT-TYPE
    SYNTAX     DisplayString
    MAX-ACCESS read-only
    STATUS     current
    DESCRIPTION
        "Request-to-send (RTS) flow control. RTS is used to
        signal that data is available for transmission.
        
        Value Meaning 
        'Enable' RTS is left on for the data transfer
        session 
        'Disable' RTS is ignored after the first RTS signal
        is received 
        'Handshake' RTS is turned off if the transmission
        buffer is more than three-quarters full, and RTS is
        turned on when the buffer is less than one-half
        full 
        'Toggle' RTS is turned on if there is any data
        buffered for transmission"
    ::= { win32SerialPortConfigEntry 22 }

hwspcSettingID OBJECT-TYPE
    SYNTAX     DisplayString (SIZE (0..256))
    MAX-ACCESS read-only
    STATUS     current
    DESCRIPTION
        "Identifier by which the CIM_Setting instance is
        known. This property is inherited from
        CIM_Setting."
    ::= { win32SerialPortConfigEntry 23 }

hwspcStopBits OBJECT-TYPE
    SYNTAX     DisplayString
    MAX-ACCESS read-only
    STATUS     current
    DESCRIPTION
        "Number of stop bits to be used. Stop bits separate
        each unit of data on an asynchronous serial
        connection. They are also sent continuously when no
        data is available for transmission. Values are:
        '1'
        '1.5'
        '2'"
    ::= { win32SerialPortConfigEntry 24 }

hwspcXOffCharacter OBJECT-TYPE
    SYNTAX     Gauge32
    MAX-ACCESS read-only
    STATUS     current
    DESCRIPTION
        "Value of the XOFF character for both transmission
        and reception. XOFF is a software control to stop
        the transmission of data (whereas RTS and CTS are
        hardware controls). XON resumes the transmission."
    ::= { win32SerialPortConfigEntry 25 }

hwspcXOffXMitThreshold OBJECT-TYPE
    SYNTAX     Gauge32
    MAX-ACCESS read-only
    STATUS     current
    DESCRIPTION
        "Maximum number of bytes allowed in the input
        buffer before the XOFF character is sent."
    ::= { win32SerialPortConfigEntry 26 }

hwspcXOnCharacter OBJECT-TYPE
    SYNTAX     Gauge32
    MAX-ACCESS read-only
    STATUS     current
    DESCRIPTION
        "Value of the XON character for both transmission
        and reception. XON is a software control to resume
        the transmission of data (whereas RTS and CTS are
        hardware controls). XOFF stops the transmission."
    ::= { win32SerialPortConfigEntry 27 }

hwspcXOnXMitThreshold OBJECT-TYPE
    SYNTAX     Gauge32
    MAX-ACCESS read-only
    STATUS     current
    DESCRIPTION
        "Minimum number of bytes allowed in the input
        buffer before the XON character is sent. This
        property works in conjunction with
        XOffXMitThreshold to regulate the rate at which
        data is transferred."
    ::= { win32SerialPortConfigEntry 28 }

hwspcXOnXOffInFlowControl OBJECT-TYPE
    SYNTAX     INTEGER {
        false(0),
        true(1)
    }
    MAX-ACCESS read-only
    STATUS     current
    DESCRIPTION
        "If TRUE, XON/XOFF flow control is used during
        reception. If TRUE, the XOffCharacter value is sent
        when the input buffer comes within
        XOffXMitThreshold bytes of being full, and the
        XOnCharacter value is sent when the input buffer
        comes within XOnXMitThreshold bytes of being
        empty."
    ::= { win32SerialPortConfigEntry 29 }

hwspcXOnXOffOutFlowControl OBJECT-TYPE
    SYNTAX     Gauge32
    MAX-ACCESS read-only
    STATUS     current
    DESCRIPTION
        "The XOnXOffOutFlowControl specifies whether
        XON/XOFF flow control is used during transmission.
        If TRUE, transmission stops when the XOffCharacter
        value is received and starts again when the
        XOnCharacter value is received."
    ::= { win32SerialPortConfigEntry 30 }

win32SMBIOSMemoryTable OBJECT-TYPE
    SYNTAX     SEQUENCE OF Win32SMBIOSMemoryEntry
    MAX-ACCESS not-accessible
    STATUS     current
    DESCRIPTION
        "The Win32_SMBIOSMemory abstract WMI class
        represents the properties of a computer system
        memory as seen through the System Management BIOS
        (SMBIOS) interface. The SMBIOS interface does not
        distinguish between non-volatile, volatile, and
        flash memories. The CIM_Memory class is the parent
        class of all types of memory."
    ::= { wmiMotherboardControllerPort 28 }

win32SMBIOSMemoryEntry OBJECT-TYPE
    SYNTAX     Win32SMBIOSMemoryEntry
    MAX-ACCESS not-accessible
    STATUS     current
    DESCRIPTION
        "None"
    INDEX      { hwsbmIndex }
    ::= { win32SMBIOSMemoryTable 1 }

Win32SMBIOSMemoryEntry ::= SEQUENCE {
    hwsbmIndex Integer32,
    hwsbmAccess INTEGER,
    hwsbmAdditionalErrorData DisplayString,
    hwsbmAvailability INTEGER,
    hwsbmBlockSize Gauge32,
    hwsbmCaption DisplayString,
    hwsbmConfigManagerErrorCode INTEGER,
    hwsbmConfigManagerUserConfig TruthValue,
    hwsbmCorrectableError TruthValue,
    hwsbmCreationClassName DisplayString,
    hwsbmDescription DisplayString,
    hwsbmDeviceID DisplayString,
    hwsbmEndingAddress Gauge32,
    hwsbmErrorAccess INTEGER,
    hwsbmErrorAddress Gauge32,
    hwsbmErrorCleared TruthValue,
    hwsbmErrorData DisplayString,
    hwsbmErrorDataOrder INTEGER,
    hwsbmErrorDescription DisplayString,
    hwsbmErrorInfo INTEGER,
    hwsbmErrorMethodology INTEGER,
    hwsbmErrorResolution Gauge32,
    hwsbmErrorTime DateAndTime,
    hwsbmErrorTransferSize Gauge32,
    hwsbmInstallDate DateAndTime,
    hwsbmLastErrorCode Gauge32,
    hwsbmName DisplayString,
    hwsbmNumberOfBlocks Gauge32,
    hwsbmOtherErrorDescription DisplayString,
    hwsbmPNPDeviceID DisplayString,
    hwsbmPowerManagementCapabilities DisplayString,
    hwsbmPowerManagementSupported TruthValue,
    hwsbmPurpose DisplayString,
    hwsbmStartingAddress Gauge32,
    hwsbmStatus INTEGER,
    hwsbmStatusInfo INTEGER,
    hwsbmSystemCreationClassName DisplayString,
    hwsbmSystemLevelAddress TruthValue,
    hwsbmSystemName DisplayString
}

hwsbmIndex OBJECT-TYPE
    SYNTAX     Integer32 (1..2147483647)
    MAX-ACCESS read-only
    STATUS     current
    DESCRIPTION
        "The value of this object uniquely identifies the
        instance entry for this class."
    ::= { win32SMBIOSMemoryEntry 1 }

hwsbmAccess OBJECT-TYPE
    SYNTAX     INTEGER {
        unknown(0),
        readable(1),
        writable(2),
        readWriteSupported(3),
        writeOnce(4)
    }
    MAX-ACCESS read-only
    STATUS     current
    DESCRIPTION
        "Type of access. This property is inherited from
        CIM_StorageExtent."
    ::= { win32SMBIOSMemoryEntry 2 }

hwsbmAdditionalErrorData OBJECT-TYPE
    SYNTAX     DisplayString
    MAX-ACCESS read-only
    STATUS     current
    DESCRIPTION
        "Array of octets that hold additional error
        information. An example is Error Checking and
        Correcting (ECC) Syndrome, or the return of the
        check bits if a CRC-based error methodology is
        used. In the latter case, if a single bit error is
        recognized and the cyclical redundancy check (CRC)
        algorithm is known, it is possible to determine the
        exact bit that failed. This type of data (ECC
        Syndrome, Check Bit or Parity Bit data, or other
        vendor supplied information) is included in this
        field. If the ErrorInfo property is equal to 3
        (OK), then this property has no meaning."
    ::= { win32SMBIOSMemoryEntry 3 }

hwsbmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. This
        property is inherited from CIM_LogicalDevice."
    ::= { win32SMBIOSMemoryEntry 4 }

hwsbmBlockSize OBJECT-TYPE
    SYNTAX     Gauge32
    MAX-ACCESS read-only
    STATUS     current
    DESCRIPTION
        "Size in bytes of the blocks that form this storage
        extent. If unknown or if a block concept is not
        valid (for example, for aggregate extents, memory
        or logical disks), enter a 1. This property is
        inherited from CIM_StorageExtent."
    ::= { win32SMBIOSMemoryEntry 5 }

hwsbmCaption OBJECT-TYPE
    SYNTAX     DisplayString (SIZE (0..64))
    MAX-ACCESS read-only
    STATUS     current
    DESCRIPTION
        "Short description of the object a one-line string.
        This property is inherited from
        CIM_ManagedSystemElement."
    ::= { win32SMBIOSMemoryEntry 6 }

hwsbmConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32SMBIOSMemoryEntry 7 }

hwsbmConfigManagerUserConfig OBJECT-TYPE
    SYNTAX     TruthValue
    MAX-ACCESS read-only
    STATUS     current
    DESCRIPTION
        "If TRUE, the device is using a user-defined
        configuration. This property is inherited from
        CIM_LogicalDevice."
    ::= { win32SMBIOSMemoryEntry 8 }

hwsbmCorrectableError OBJECT-TYPE
    SYNTAX     TruthValue
    MAX-ACCESS read-only
    STATUS     current
    DESCRIPTION
        "If TRUE, the most recent error was correctable. If
        the ErrorInfo property is equal to 3 (OK), then
        this property has no meaning."
    ::= { win32SMBIOSMemoryEntry 9 }

hwsbmCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32SMBIOSMemoryEntry 10 }

hwsbmDescription OBJECT-TYPE
    SYNTAX     DisplayString
    MAX-ACCESS read-only
    STATUS     current
    DESCRIPTION
        "Description of the object. This property is
        inherited from CIM_ManagedSystemElement."
    ::= { win32SMBIOSMemoryEntry 11 }

hwsbmDeviceID OBJECT-TYPE
    SYNTAX     DisplayString
    MAX-ACCESS read-only
    STATUS     current
    DESCRIPTION
        "Unique identifier of the logical device. This
        property is inherited from CIM_LogicalDevice."
    ::= { win32SMBIOSMemoryEntry 12 }

hwsbmEndingAddress OBJECT-TYPE
    SYNTAX     Gauge32
    MAX-ACCESS read-only
    STATUS     current
    DESCRIPTION
        "Ending address, referenced by an application or
        operating system and mapped by a memory controller
        for this memory object. The ending address is
        specified in kilobytes."
    ::= { win32SMBIOSMemoryEntry 13 }

hwsbmErrorAccess OBJECT-TYPE
    SYNTAX     INTEGER {
        other(1),
        unknown(2),
        read(3),
        write(4),
        partialWrite(5)
    }
    MAX-ACCESS read-only
    STATUS     current
    DESCRIPTION
        "Memory access operation that caused the last
        error. The type of error is described by the
        ErrorInfo property. If ErrorInfo is equal to 3
        (OK), then this property has no meaning."
    ::= { win32SMBIOSMemoryEntry 14 }

hwsbmErrorAddress OBJECT-TYPE
    SYNTAX     Gauge32
    MAX-ACCESS read-only
    STATUS     current
    DESCRIPTION
        "Address of the last memory error. The type of
        error is described by the ErrorInfo property. If
        ErrorInfo is equal to 3 (OK), then this property
        has no meaning."
    ::= { win32SMBIOSMemoryEntry 15 }

hwsbmErrorCleared OBJECT-TYPE
    SYNTAX     TruthValue
    MAX-ACCESS read-only
    STATUS     current
    DESCRIPTION
        "If TRUE, the error reported in LastErrorCode is
        now cleared. This property is inherited from
        CIM_LogicalDevice."
    ::= { win32SMBIOSMemoryEntry 16 }

hwsbmErrorData OBJECT-TYPE
    SYNTAX     DisplayString
    MAX-ACCESS read-only
    STATUS     current
    DESCRIPTION
        "Array of data captured during the last erroneous
        memory access. The data occupies the first n octets
        of the array necessary to hold the number of bits
        specified by the ErrorTransferSize property. If
        ErrorTransferSize is 0 (zero), then this property
        has no meaning."
    ::= { win32SMBIOSMemoryEntry 17 }

hwsbmErrorDataOrder OBJECT-TYPE
    SYNTAX     INTEGER {
        unknown(0),
        leastSignificantByteFirst(1),
        mostSignificantByteFirst(2)
    }
    MAX-ACCESS read-only
    STATUS     current
    DESCRIPTION
        "Ordering for data stored in the ErrorData
        property. If ErrorTransferSize is 0 (zero), then
        this property has no meaning."
    ::= { win32SMBIOSMemoryEntry 18 }

hwsbmErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32SMBIOSMemoryEntry 19 }

hwsbmErrorInfo OBJECT-TYPE
    SYNTAX     INTEGER {
        other(1),
        unknown(2),
        ok(3),
        badRead(4),
        parityError(5),
        singleBitError(6),
        doubleBitError(7),
        multiBitError(8),
        nibbleError(9),
        checksumError(10),
        crcError(11),
        correctedSinglebitError(12),
        correctedError(13),
        uncorrectableError(14)
    }
    MAX-ACCESS read-only
    STATUS     current
    DESCRIPTION
        "Type of error that occurred most recently. The
        values 12 through 14 are unused. The ability to be
        corrected is indicated in the property
        CorrectableError."
    ::= { win32SMBIOSMemoryEntry 20 }

hwsbmErrorMethodology OBJECT-TYPE
    SYNTAX     INTEGER {
        other(1),
        unknown(2),
        none(3),
        parity(4),
        singleBitECC(5),
        multiBitECC(6),
        crc(7)
    }
    MAX-ACCESS read-only
    STATUS     current
    DESCRIPTION
        "Details on the parity or CRC algorithms, ECC or
        other mechanisms used. This property is inherited
        from CIM_StorageExtent."
    ::= { win32SMBIOSMemoryEntry 21 }

hwsbmErrorResolution OBJECT-TYPE
    SYNTAX     Gauge32
    MAX-ACCESS read-only
    STATUS     current
    DESCRIPTION
        "Range, in bytes, to which the last error can be
        resolved. For example, if error addresses are
        resolved to bit 11 (that is, on a typical page
        basis), then errors can be resolved to 4 KB
        boundaries and this property is set to 4000. If the
        ErrorInfo property is equal to 3 (OK), then this
        property has no meaning."
    ::= { win32SMBIOSMemoryEntry 22 }

hwsbmErrorTime OBJECT-TYPE
    SYNTAX     DateAndTime
    MAX-ACCESS read-only
    STATUS     current
    DESCRIPTION
        "Time that the last memory error occurred. The type
        of error is described by the ErrorInfo property. If
        the ErrorInfo property is equal to 3 (OK), then
        this property has no meaning."
    ::= { win32SMBIOSMemoryEntry 23 }

hwsbmErrorTransferSize OBJECT-TYPE
    SYNTAX     Gauge32
    MAX-ACCESS read-only
    STATUS     current
    DESCRIPTION
        "Size of the data transfer in bits that caused the
        last error 0 (zero) indicates no error. If the
        ErrorInfo property is equal to 3 (OK), then this
        property should be set to 0 (zero)."
    ::= { win32SMBIOSMemoryEntry 24 }

hwsbmInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32SMBIOSMemoryEntry 25 }

hwsbmLastErrorCode OBJECT-TYPE
    SYNTAX     Gauge32
    MAX-ACCESS read-only
    STATUS     current
    DESCRIPTION
        "Last error code reported by the logical device.
        This property is inherited from CIM_LogicalDevice."
    ::= { win32SMBIOSMemoryEntry 26 }

hwsbmName OBJECT-TYPE
    SYNTAX     DisplayString
    MAX-ACCESS read-only
    STATUS     current
    DESCRIPTION
        "Label by which the object is known. When
        subclassed, the property can be overridden to be a
        key property. This property is inherited from
        CIM_ManagedSystemElement."
    ::= { win32SMBIOSMemoryEntry 27 }

hwsbmNumberOfBlocks OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent. This property is inherited from
        CIM_StorageExtent."
    ::= { win32SMBIOSMemoryEntry 28 }

hwsbmOtherErrorDescription OBJECT-TYPE
    SYNTAX     DisplayString
    MAX-ACCESS read-only
    STATUS     current
    DESCRIPTION
        "Free-form string that provides more information if
        the ErrorType property is set to 1; otherwise, this
        string has no meaning."
    ::= { win32SMBIOSMemoryEntry 29 }

hwsbmPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32SMBIOSMemoryEntry 30 }

hwsbmPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32SMBIOSMemoryEntry 31 }

hwsbmPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32SMBIOSMemoryEntry 32 }

hwsbmPurpose OBJECT-TYPE
    SYNTAX     DisplayString
    MAX-ACCESS read-only
    STATUS     current
    DESCRIPTION
        "Free-form string describing the media and/or its
        use. This property is inherited from
        CIM_StorageExtent."
    ::= { win32SMBIOSMemoryEntry 33 }

hwsbmStartingAddress OBJECT-TYPE
    SYNTAX     Gauge32
    MAX-ACCESS read-only
    STATUS     current
    DESCRIPTION
        "Beginning address that is referenced by an
        application or operating system, and mapped by a
        memory controller for this memory object. The
        starting address is specified in kilobytes."
    ::= { win32SMBIOSMemoryEntry 34 }

hwsbmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SMBIOSMemoryEntry 35 }

hwsbmStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32SMBIOSMemoryEntry 36 }

hwsbmSystemCreationClassName OBJECT-TYPE
    SYNTAX     DisplayString
    MAX-ACCESS read-only
    STATUS     current
    DESCRIPTION
        "Value of the scoping computer's CreationClassName
        property. This property is inherited from
        CIM_LogicalDevice."
    ::= { win32SMBIOSMemoryEntry 37 }

hwsbmSystemLevelAddress OBJECT-TYPE
    SYNTAX     TruthValue
    MAX-ACCESS read-only
    STATUS     current
    DESCRIPTION
        "If TRUE, the address information in the
        ErrorAddress property is a system-level address. If
        FALSE, it is a physical address. If the ErrorInfo
        property is equal to 3 (OK), then this property has
        no meaning."
    ::= { win32SMBIOSMemoryEntry 38 }

hwsbmSystemName OBJECT-TYPE
    SYNTAX     DisplayString
    MAX-ACCESS read-only
    STATUS     current
    DESCRIPTION
        "Name of the scoping system. This property is
        inherited from CIM_LogicalDevice."
    ::= { win32SMBIOSMemoryEntry 39 }

win32SoundDeviceTable OBJECT-TYPE
    SYNTAX     SEQUENCE OF Win32SoundDeviceEntry
    MAX-ACCESS not-accessible
    STATUS     current
    DESCRIPTION
        "The Win32_SoundDevice WMI class represents the
        properties of a sound device on a Windows computer
        system."
    ::= { wmiMotherboardControllerPort 29 }

win32SoundDeviceEntry OBJECT-TYPE
    SYNTAX     Win32SoundDeviceEntry
    MAX-ACCESS not-accessible
    STATUS     current
    DESCRIPTION
        "None"
    INDEX      { hwsndIndex }
    ::= { win32SoundDeviceTable 1 }

Win32SoundDeviceEntry ::= SEQUENCE {
    hwsndIndex Integer32,
    hwsndAvailability INTEGER,
    hwsndCaption DisplayString,
    hwsndConfigManagerErrorCode INTEGER,
    hwsndConfigManagerUserConfig TruthValue,
    hwsndCreationClassName DisplayString,
    hwsndDescription DisplayString,
    hwsndDeviceID DisplayString,
    hwsndDMABufferSize Integer32,
    hwsndErrorCleared TruthValue,
    hwsndErrorDescription DisplayString,
    hwsndInstallDate DateAndTime,
    hwsndLastErrorCode Gauge32,
    hwsndManufacturer DisplayString,
    hwsndMPU401Address Gauge32,
    hwsndName DisplayString,
    hwsndPNPDeviceID DisplayString,
    hwsndPowerManagementCapabilities DisplayString,
    hwsndPowerManagementSupported TruthValue,
    hwsndProductName DisplayString,
    hwsndStatus INTEGER,
    hwsndStatusInfo INTEGER,
    hwsndSystemCreationClassName DisplayString,
    hwsndSystemName DisplayString
}

hwsndIndex OBJECT-TYPE
    SYNTAX     Integer32 (1..2147483647)
    MAX-ACCESS read-only
    STATUS     current
    DESCRIPTION
        "The value of this object uniquely identifies the
        instance entry for this class."
    ::= { win32SoundDeviceEntry 1 }

hwsndAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32SoundDeviceEntry 2 }

hwsndCaption OBJECT-TYPE
    SYNTAX     DisplayString (SIZE (0..64))
    MAX-ACCESS read-only
    STATUS     current
    DESCRIPTION
        "Short description (one-line string) of the object.
        This property is inherited from
        CIM_ManagedSystemElement."
    ::= { win32SoundDeviceEntry 3 }

hwsndConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. . This
        property is inherited from CIM_LogicalDevice."
    ::= { win32SoundDeviceEntry 4 }

hwsndConfigManagerUserConfig OBJECT-TYPE
    SYNTAX     TruthValue
    MAX-ACCESS read-only
    STATUS     current
    DESCRIPTION
        "If TRUE, the device is using a user-defined
        configuration. This property is inherited from
        CIM_LogicalDevice."
    ::= { win32SoundDeviceEntry 5 }

hwsndCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32SoundDeviceEntry 6 }

hwsndDescription OBJECT-TYPE
    SYNTAX     DisplayString
    MAX-ACCESS read-only
    STATUS     current
    DESCRIPTION
        "Description of the object. This property is
        inherited from CIM_ManagedSystemElement."
    ::= { win32SoundDeviceEntry 7 }

hwsndDeviceID OBJECT-TYPE
    SYNTAX     DisplayString (SIZE (0..260))
    MAX-ACCESS read-only
    STATUS     current
    DESCRIPTION
        "Unique identifier of the sound device. This
        property is inherited from CIM_LogicalDevice."
    ::= { win32SoundDeviceEntry 8 }

hwsndDMABufferSize OBJECT-TYPE
    SYNTAX     Integer32
    UNITS "Kilobytes"
    MAX-ACCESS read-only
    STATUS     current
    DESCRIPTION
        "Size of the Direct Memory Access buffer.
        Example: 4"
    ::= { win32SoundDeviceEntry 9 }

hwsndErrorCleared OBJECT-TYPE
    SYNTAX     TruthValue
    MAX-ACCESS read-only
    STATUS     current
    DESCRIPTION
        "If TRUE, the error reported in LastErrorCode is
        now cleared. This property is inherited from
        CIM_LogicalDevice."
    ::= { win32SoundDeviceEntry 10 }

hwsndErrorDescription OBJECT-TYPE
    SYNTAX     DisplayString
    MAX-ACCESS read-only
    STATUS     current
    DESCRIPTION
        "Free-form string supplying more information about
        the error recorded in LastErrorCode, and
        information on any corrective actions that may be
        taken. This property is inherited from
        CIM_LogicalDevice."
    ::= { win32SoundDeviceEntry 11 }

hwsndInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32SoundDeviceEntry 12 }

hwsndLastErrorCode OBJECT-TYPE
    SYNTAX     Gauge32
    MAX-ACCESS read-only
    STATUS     current
    DESCRIPTION
        "Last error code reported by the logical device.
        This property is inherited from CIM_LogicalDevice."
    ::= { win32SoundDeviceEntry 13 }

hwsndManufacturer OBJECT-TYPE
    SYNTAX     DisplayString
    MAX-ACCESS read-only
    STATUS     current
    DESCRIPTION
        "Manufacturer of the sound device.
        Example: 'Creative Labs'"
    ::= { win32SoundDeviceEntry 14 }

hwsndMPU401Address OBJECT-TYPE
    SYNTAX     Gauge32
    MAX-ACCESS read-only
    STATUS     current
    DESCRIPTION
        "Starting I/O address assigned to the MPU-401 port
        of the sound device.
        Example: 300"
    ::= { win32SoundDeviceEntry 15 }

hwsndName OBJECT-TYPE
    SYNTAX     DisplayString
    MAX-ACCESS read-only
    STATUS     current
    DESCRIPTION
        "Label by which the object is known. When
        subclassed, the property can be overridden to be a
        key property. This property is inherited from
        CIM_ManagedSystemElement."
    ::= { win32SoundDeviceEntry 16 }

hwsndPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32SoundDeviceEntry 17 }

hwsndPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32SoundDeviceEntry 18 }

hwsndPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32SoundDeviceEntry 19 }

hwsndProductName OBJECT-TYPE
    SYNTAX     DisplayString
    MAX-ACCESS read-only
    STATUS     current
    DESCRIPTION
        "Product name of the sound device.
        Example: 'Creative Labs SoundBlaster AWE64PNP'"
    ::= { win32SoundDeviceEntry 20 }

hwsndStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SoundDeviceEntry 21 }

hwsndStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32SoundDeviceEntry 22 }

hwsndSystemCreationClassName OBJECT-TYPE
    SYNTAX     DisplayString
    MAX-ACCESS read-only
    STATUS     current
    DESCRIPTION
        "Value of the scoping computer's CreationClassName
        property. This property is inherited from
        CIM_LogicalDevice."
    ::= { win32SoundDeviceEntry 23 }

hwsndSystemName OBJECT-TYPE
    SYNTAX     DisplayString
    MAX-ACCESS read-only
    STATUS     current
    DESCRIPTION
        "Name of the scoping system. This property is
        inherited from CIM_LogicalDevice."
    ::= { win32SoundDeviceEntry 24 }

win32SystemEnclosureTable OBJECT-TYPE
    SYNTAX     SEQUENCE OF Win32SystemEnclosureEntry
    MAX-ACCESS not-accessible
    STATUS     current
    DESCRIPTION
        "The Win32_SystemEnclosure WMI class represents the
        properties associated with a physical system
        enclosure."
    ::= { wmiMotherboardControllerPort 30 }

win32SystemEnclosureEntry OBJECT-TYPE
    SYNTAX     Win32SystemEnclosureEntry
    MAX-ACCESS not-accessible
    STATUS     current
    DESCRIPTION
        "None"
    INDEX      { hwseIndex }
    ::= { win32SystemEnclosureTable 1 }

Win32SystemEnclosureEntry ::= SEQUENCE {
    hwseIndex Integer32,
    hwseAudibleAlarm TruthValue,
    hwseBreachDescription DisplayString,
    hwseCableManagementStrategy DisplayString,
    hwseCaption DisplayString,
    hwseChassisTypes DisplayString,
    hwseCreationClassName DisplayString,
    hwseCurrentRequiredOrProduced Integer32,
    hwseDepth Integer32,
    hwseDescription DisplayString,
    hwseHeatGeneration Integer32,
    hwseHeight Integer32,
    hwseHotSwappable TruthValue,
    hwseInstallDate DateAndTime,
    hwseLockPresent TruthValue,
    hwseManufacturer DisplayString,
    hwseModel DisplayString,
    hwseName DisplayString,
    hwseNumberOfPowerCords Integer32,
    hwseOtherIdentifyingInfo DisplayString,
    hwsePartNumber DisplayString,
    hwsePoweredOn TruthValue,
    hwseRemovable TruthValue,
    hwseReplaceable TruthValue,
    hwseSecurityBreach INTEGER,
    hwseSecurityStatus INTEGER,
    hwseSerialNumber DisplayString,
    hwseServiceDescriptions DisplayString,
    hwseServicePhilosophy DisplayString,
    hwseSKU DisplayString,
    hwseSMBIOSAssetTag DisplayString,
    hwseStatus INTEGER,
    hwseTag DisplayString,
    hwseTypeDescriptions DisplayString,
    hwseVersion DisplayString,
    hwseVisibleAlarm TruthValue,
    hwseWeight Integer32,
    hwseWidth Integer32
}

hwseIndex OBJECT-TYPE
    SYNTAX     Integer32 (1..2147483647)
    MAX-ACCESS read-only
    STATUS     current
    DESCRIPTION
        "The value of this object uniquely identifies the
        instance entry for this class."
    ::= { win32SystemEnclosureEntry 1 }

hwseAudibleAlarm OBJECT-TYPE
    SYNTAX     TruthValue
    MAX-ACCESS read-only
    STATUS     current
    DESCRIPTION
        "If TRUE, the frame is equipped with an audible
        alarm. This property is inherited from
        CIM_PhysicalFrame."
    ::= { win32SystemEnclosureEntry 2 }

hwseBreachDescription OBJECT-TYPE
    SYNTAX     DisplayString
    MAX-ACCESS read-only
    STATUS     current
    DESCRIPTION
        "Free-form string that provides more information if
        the SecurityBreach property indicates that a breach
        or some other security-related event occurred. This
        property is inherited from CIM_PhysicalFrame."
    ::= { win32SystemEnclosureEntry 3 }

hwseCableManagementStrategy OBJECT-TYPE
    SYNTAX     DisplayString
    MAX-ACCESS read-only
    STATUS     current
    DESCRIPTION
        "Free-form string that contains information about
        how the various cables are connected and bundled
        for the frame. With many networking,
        storage-related, and power cables, cable management
        can be a complex and challenging endeavor. The
        property contains information to aid in assembly
        and service of the frame. This property is
        inherited from CIM_PhysicalFrame."
    ::= { win32SystemEnclosureEntry 4 }

hwseCaption OBJECT-TYPE
    SYNTAX     DisplayString (SIZE (0..64))
    MAX-ACCESS read-only
    STATUS     current
    DESCRIPTION
        "Short description of the object a one-line string.
        This property is inherited from
        CIM_ManagedSystemElement."
    ::= { win32SystemEnclosureEntry 5 }

hwseChassisTypes OBJECT-TYPE
    SYNTAX     DisplayString
    MAX-ACCESS read-only
    STATUS     current
    DESCRIPTION
        "Array of chassis types. This property is inherited
        from CIM_Chassis.
        Value Meaning 
        1 Other 
        2 Unknown 
        3 Desktop 
        4 Low Profile Desktop 
        5 Pizza Box  
        6 Mini Tower 
        7 Tower 
        8 Portable 
        9 Laptop 
        10 Notebook 
        11 Hand Held 
        12 Docking Station 
        13 All in One 
        14 Sub Notebook 
        15 Space-Saving 
        16 Lunch Box  
        17 Main System Chassis 
        18 Expansion Chassis 
        19 SubChassis 
        20 Bus Expansion Chassis 
        21 Peripheral Chassis 
        22 Storage Chassis 
        23 Rack Mount Chassis 
        24 Sealed-Case PC "
    ::= { win32SystemEnclosureEntry 6 }

hwseCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_PhysicalElement."
    ::= { win32SystemEnclosureEntry 7 }

hwseCurrentRequiredOrProduced OBJECT-TYPE
    SYNTAX     Integer32
    UNITS "Amps at 120 Volts"
    MAX-ACCESS read-only
    STATUS     current
    DESCRIPTION
        "Current required by the chassis at 120V. If power
        is provided by the chassis as in the case of an
        uninterruptible power supply (UPS) this property
        may indicate the amperage produced (as a negative
        number). This property is inherited from
        CIM_Chassis."
    ::= { win32SystemEnclosureEntry 8 }

hwseDepth OBJECT-TYPE
    SYNTAX     Integer32
    MAX-ACCESS read-only
    STATUS     current
    DESCRIPTION
        "Depth of the physical package in inches. This
        property is inherited from CIM_PhysicalPackage."
    ::= { win32SystemEnclosureEntry 9 }

hwseDescription OBJECT-TYPE
    SYNTAX     DisplayString
    MAX-ACCESS read-only
    STATUS     current
    DESCRIPTION
        "Description of the object. This property is
        inherited from CIM_ManagedSystemElement."
    ::= { win32SystemEnclosureEntry 10 }

hwseHeatGeneration OBJECT-TYPE
    SYNTAX     Integer32
    MAX-ACCESS read-only
    STATUS     current
    DESCRIPTION
        "Amount of heat generated by the chassis in
        BTU/hour. This property is inherited from
        CIM_Chassis."
    ::= { win32SystemEnclosureEntry 11 }

hwseHeight OBJECT-TYPE
    SYNTAX     Integer32
    MAX-ACCESS read-only
    STATUS     current
    DESCRIPTION
        "Height of the physical package in inches. This
        property is inherited from CIM_PhysicalPackage."
    ::= { win32SystemEnclosureEntry 12 }

hwseHotSwappable OBJECT-TYPE
    SYNTAX     TruthValue
    MAX-ACCESS read-only
    STATUS     current
    DESCRIPTION
        "If TRUE, a physical package can be hot-swapped (if
        it is possible to replace the element with a
        physically different but equivalent one while the
        containing package has power applied to it). For
        example, a disk drive package inserted using SCA
        connectors is removable and can be hot-swapped. All
        packages that can be hot-swapped are inherently
        removable and replaceable. This property is
        inherited from CIM_PhysicalPackage."
    ::= { win32SystemEnclosureEntry 13 }

hwseInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32SystemEnclosureEntry 14 }

hwseLockPresent OBJECT-TYPE
    SYNTAX     TruthValue
    MAX-ACCESS read-only
    STATUS     current
    DESCRIPTION
        "If TRUE, the frame is protected with a lock. This
        property is inherited from CIM_PhysicalFrame."
    ::= { win32SystemEnclosureEntry 15 }

hwseManufacturer OBJECT-TYPE
    SYNTAX     DisplayString (SIZE (0..256))
    MAX-ACCESS read-only
    STATUS     current
    DESCRIPTION
        "Name of the organization responsible for producing
        the physical element. This property is inherited
        from CIM_PhysicalElement."
    ::= { win32SystemEnclosureEntry 16 }

hwseModel OBJECT-TYPE
    SYNTAX     DisplayString (SIZE (0..64))
    MAX-ACCESS read-only
    STATUS     current
    DESCRIPTION
        "Name by which the physical element is generally
        known. This property is inherited from
        CIM_PhysicalElement."
    ::= { win32SystemEnclosureEntry 17 }

hwseName OBJECT-TYPE
    SYNTAX     DisplayString
    MAX-ACCESS read-only
    STATUS     current
    DESCRIPTION
        "Label by which the object is known. When
        subclassed, the property can be overridden to be a
        key property. This property is inherited from
        CIM_ManagedSystemElement."
    ::= { win32SystemEnclosureEntry 18 }

hwseNumberOfPowerCords OBJECT-TYPE
    SYNTAX     Integer32
    MAX-ACCESS read-only
    STATUS     current
    DESCRIPTION
        "Number of power cords that must be connected to
        the chassis for all the components to operate. This
        property is inherited from CIM_Chassis."
    ::= { win32SystemEnclosureEntry 19 }

hwseOtherIdentifyingInfo OBJECT-TYPE
    SYNTAX     DisplayString
    MAX-ACCESS read-only
    STATUS     current
    DESCRIPTION
        "Additional data, beyond asset tag information,
        that can be used to identify a physical element.
        One example is bar code data associated with an
        element that also has an asset tag. Note that if
        only bar code data is available and is unique/able
        to be used as an element key, this property would
        be NULL and the bar code data used as the class
        key, in the tag property. This property is
        inherited from CIM_PhysicalElement."
    ::= { win32SystemEnclosureEntry 20 }

hwsePartNumber OBJECT-TYPE
    SYNTAX     DisplayString (SIZE (0..256))
    MAX-ACCESS read-only
    STATUS     current
    DESCRIPTION
        "Part number assigned by the organization
        responsible for producing or manufacturing the
        physical element. This property is inherited from
        CIM_PhysicalElement."
    ::= { win32SystemEnclosureEntry 21 }

hwsePoweredOn OBJECT-TYPE
    SYNTAX     TruthValue
    MAX-ACCESS read-only
    STATUS     current
    DESCRIPTION
        "If TRUE, the physical element is powered ON. This
        property is inherited from CIM_PhysicalElement."
    ::= { win32SystemEnclosureEntry 22 }

hwseRemovable OBJECT-TYPE
    SYNTAX     TruthValue
    MAX-ACCESS read-only
    STATUS     current
    DESCRIPTION
        "If TRUE, a physical package is removable (if it is
        designed to be taken in and out of the physical
        container in which it is normally found, without
        impairing the function of the overall packaging). A
        package can still be removable if power must be
        'off' in order to perform the removal. If power can
        be ON and the package removed, then the element is
        removable and can be hot-swapped. For example, an
        extra battery in a laptop is removable, as is a
        disk drive package inserted using SCA connectors.
        However, the latter can be hot swapped. A laptop's
        display is not removable, nor is a non-redundant
        power supply. Removing these components would
        affect the function of the overall packaging or is
        impossible due to the tight integration of the
        package. This property is inherited from
        CIM_PhysicalPackage."
    ::= { win32SystemEnclosureEntry 23 }

hwseReplaceable OBJECT-TYPE
    SYNTAX     TruthValue
    MAX-ACCESS read-only
    STATUS     current
    DESCRIPTION
        "If TRUE, a physical package is replaceable (if it
        is possible to replace field replaceable unit (FRU)
        or upgrade the element with a physically different
        one). For example, some computer systems allow the
        main processor chip to be upgraded to one of a
        higher clock rating. In this case, the processor is
        replaceable. Another example is a power supply
        package mounted on sliding rails. All removable
        packages are inherently replaceable. This property
        is inherited from CIM_PhysicalPackage."
    ::= { win32SystemEnclosureEntry 24 }

hwseSecurityBreach OBJECT-TYPE
    SYNTAX     INTEGER {
        other(1),
        unknown(2),
        noBreach(3),
        breachAttempted(4),
        breachSuccessful(5)
    }
    MAX-ACCESS read-only
    STATUS     current
    DESCRIPTION
        "Status of a physical breach of the frame. This
        property is inherited from CIM_PhysicalFrame."
    ::= { win32SystemEnclosureEntry 25 }

hwseSecurityStatus OBJECT-TYPE
    SYNTAX     INTEGER {
        other(1),
        unknown(2),
        none(3),
        externalInterfaceLockedOut(4),
        externalInterfaceEnabled(5)
    }
    MAX-ACCESS read-only
    STATUS     current
    DESCRIPTION
        "Security setting for external input for example, a
        keyboard to this computer."
    ::= { win32SystemEnclosureEntry 26 }

hwseSerialNumber OBJECT-TYPE
    SYNTAX     DisplayString (SIZE (0..64))
    MAX-ACCESS read-only
    STATUS     current
    DESCRIPTION
        "Manufacturer-allocated number used to identify the
        physical element. This property is inherited from
        CIM_PhysicalElement."
    ::= { win32SystemEnclosureEntry 27 }

hwseServiceDescriptions OBJECT-TYPE
    SYNTAX     DisplayString
    MAX-ACCESS read-only
    STATUS     current
    DESCRIPTION
        "Array of more detailed explanations for any of the
        entries in the ServicePhilosophy array. Note that
        each entry of this array is related to the entry in
        ServicePhilosophy that is located at the same
        index. This property is inherited from
        CIM_PhysicalFrame."
    ::= { win32SystemEnclosureEntry 28 }

hwseServicePhilosophy OBJECT-TYPE
    SYNTAX     DisplayString
    MAX-ACCESS read-only
    STATUS     current
    DESCRIPTION
        "Array that includes whether the frame is serviced
        from the top, front, back, or side; whether the
        frame has sliding trays or removable sides; and
        whether the frame is moveable for example, having
        rollers. This property is inherited from
        CIM_PhysicalFrame.
        Value Meaning 
        0 Unknown 
        1 Other 
        2 Service From Top 
        3 Service From Front 
        4 Service From Back 
        5 Service From Side 
        6 Sliding Trays 
        7 Removable Sides 
        8 Moveable "
    ::= { win32SystemEnclosureEntry 29 }

hwseSKU OBJECT-TYPE
    SYNTAX     DisplayString (SIZE (0..64))
    MAX-ACCESS read-only
    STATUS     current
    DESCRIPTION
        "Stock keeping unit number for the physical
        element. This property is inherited from
        CIM_PhysicalElement."
    ::= { win32SystemEnclosureEntry 30 }

hwseSMBIOSAssetTag OBJECT-TYPE
    SYNTAX     DisplayString
    MAX-ACCESS read-only
    STATUS     current
    DESCRIPTION
        "Asset tag number of the system enclosure."
    ::= { win32SystemEnclosureEntry 31 }

hwseStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SystemEnclosureEntry 32 }

hwseTag OBJECT-TYPE
    SYNTAX     DisplayString (SIZE (0..256))
    MAX-ACCESS read-only
    STATUS     current
    DESCRIPTION
        "Unique identifier of the system enclosure. This
        property is inherited from CIM_PhysicalElement.
        Example: 'System Enclosure 1'"
    ::= { win32SystemEnclosureEntry 33 }

hwseTypeDescriptions OBJECT-TYPE
    SYNTAX     DisplayString
    MAX-ACCESS read-only
    STATUS     current
    DESCRIPTION
        "Array of more information about the ChassisTypes
        array entries. Note that each entry of this array
        is related to the entry in ChassisTypes that is
        located at the same index. This property is
        inherited from CIM_Chassis."
    ::= { win32SystemEnclosureEntry 34 }

hwseVersion OBJECT-TYPE
    SYNTAX     DisplayString (SIZE (0..64))
    MAX-ACCESS read-only
    STATUS     current
    DESCRIPTION
        "Version of the physical element. This property is
        inherited from CIM_PhysicalElement."
    ::= { win32SystemEnclosureEntry 35 }

hwseVisibleAlarm OBJECT-TYPE
    SYNTAX     TruthValue
    MAX-ACCESS read-only
    STATUS     current
    DESCRIPTION
        "If TRUE, the equipment includes a visible alarm.
        This property is inherited from CIM_PhysicalFrame."
    ::= { win32SystemEnclosureEntry 36 }

hwseWeight OBJECT-TYPE
    SYNTAX     Integer32
    MAX-ACCESS read-only
    STATUS     current
    DESCRIPTION
        "Weight of the physical package in pounds. This
        property is inherited from CIM_PhysicalPackage."
    ::= { win32SystemEnclosureEntry 37 }

hwseWidth OBJECT-TYPE
    SYNTAX     Integer32
    MAX-ACCESS read-only
    STATUS     current
    DESCRIPTION
        "Width of the physical package in inches. This
        property is inherited from CIM_PhysicalPackage."
    ::= { win32SystemEnclosureEntry 38 }

win32SystemMemoryResourceTable OBJECT-TYPE
    SYNTAX     SEQUENCE OF Win32SystemMemoryResourceEntry
    MAX-ACCESS not-accessible
    STATUS     current
    DESCRIPTION
        "The Win32_SystemMemoryResource abstract WMI class
        represents a system memory resource on a Windows
        operating system."
    ::= { wmiMotherboardControllerPort 31 }

win32SystemMemoryResourceEntry OBJECT-TYPE
    SYNTAX     Win32SystemMemoryResourceEntry
    MAX-ACCESS not-accessible
    STATUS     current
    DESCRIPTION
        "None"
    INDEX      { hwsmrIndex }
    ::= { win32SystemMemoryResourceTable 1 }

Win32SystemMemoryResourceEntry ::= SEQUENCE {
    hwsmrIndex Integer32,
    hwsmrCaption DisplayString,
    hwsmrCreationClassName DisplayString,
    hwsmrCSCreationClassName DisplayString,
    hwsmrCSName DisplayString,
    hwsmrDescription DisplayString,
    hwsmrEndingAddress Gauge32,
    hwsmrInstallDate DateAndTime,
    hwsmrName DisplayString,
    hwsmrStartingAddress Gauge32,
    hwsmrStatus INTEGER
}

hwsmrIndex OBJECT-TYPE
    SYNTAX     Integer32 (1..2147483647)
    MAX-ACCESS read-only
    STATUS     current
    DESCRIPTION
        "The value of this object uniquely identifies the
        instance entry for this class."
    ::= { win32SystemMemoryResourceEntry 1 }

hwsmrCaption OBJECT-TYPE
    SYNTAX     DisplayString (SIZE (0..64))
    MAX-ACCESS read-only
    STATUS     current
    DESCRIPTION
        "Short description of an object a one-line string.
        This property is inherited from
        CIM_ManagedSystemElement."
    ::= { win32SystemMemoryResourceEntry 2 }

hwsmrCreationClassName OBJECT-TYPE
    SYNTAX     DisplayString (SIZE (0..256))
    MAX-ACCESS read-only
    STATUS     current
    DESCRIPTION
        "Name of the first concrete class that appears in
        the inheritance chain used in the creation of an
        instance. When used with other key properties of a
        class, the property allows all instances of the
        class and its subclasses to be identified uniquely.
        This property is inherited from
        CIM_MemoryMappedIO."
    ::= { win32SystemMemoryResourceEntry 3 }

hwsmrCSCreationClassName OBJECT-TYPE
    SYNTAX     DisplayString (SIZE (0..64))
    MAX-ACCESS read-only
    STATUS     current
    DESCRIPTION
        "Creation class name of the scoping computer
        system. This property is inherited from
        CIM_MemoryMappedIO."
    ::= { win32SystemMemoryResourceEntry 4 }

hwsmrCSName OBJECT-TYPE
    SYNTAX     DisplayString (SIZE (0..256))
    MAX-ACCESS read-only
    STATUS     current
    DESCRIPTION
        "Name of the scoping computer system. This property
        is inherited from CIM_MemoryMappedIO."
    ::= { win32SystemMemoryResourceEntry 5 }

hwsmrDescription OBJECT-TYPE
    SYNTAX     DisplayString
    MAX-ACCESS read-only
    STATUS     current
    DESCRIPTION
        "Description of the object. This property is
        inherited from CIM_ManagedSystemElement."
    ::= { win32SystemMemoryResourceEntry 6 }

hwsmrEndingAddress OBJECT-TYPE
    SYNTAX     Gauge32
    MAX-ACCESS read-only
    STATUS     current
    DESCRIPTION
        "Ending address of memory mapped I/O. This property
        is inherited from CIM_MemoryMappedIO."
    ::= { win32SystemMemoryResourceEntry 7 }

hwsmrInstallDate OBJECT-TYPE
    SYNTAX     DateAndTime
    MAX-ACCESS read-only
    STATUS     current
    DESCRIPTION
        "Date and time an object is installed. This
        property does not need a value to indicate that the
        object is installed. This property is inherited
        from CIM_ManagedSystemElement."
    ::= { win32SystemMemoryResourceEntry 8 }

hwsmrName OBJECT-TYPE
    SYNTAX     DisplayString
    MAX-ACCESS read-only
    STATUS     current
    DESCRIPTION
        "Label for the object. When subclassed, the
        property can be overridden to be a key property.
        This property is inherited from
        CIM_ManagedSystemElement."
    ::= { win32SystemMemoryResourceEntry 9 }

hwsmrStartingAddress OBJECT-TYPE
    SYNTAX     Gauge32
    MAX-ACCESS read-only
    STATUS     current
    DESCRIPTION
        "Starting address of memory mapped I/O. The
        hardware resource identifier property should be set
        to this value to construct the mapped I/O resource
        key. This property is inherited from
        CIM_MemoryMappedIO."
    ::= { win32SystemMemoryResourceEntry 10 }

hwsmrStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SystemMemoryResourceEntry 11 }

win32SystemSlotTable OBJECT-TYPE
    SYNTAX     SEQUENCE OF Win32SystemSlotEntry
    MAX-ACCESS not-accessible
    STATUS     current
    DESCRIPTION
        "The Win32_SystemSlot WMI class represents physical
        connection points including ports, motherboard
        slots and peripherals, and proprietary connection
        points."
    ::= { wmiMotherboardControllerPort 32 }

win32SystemSlotEntry OBJECT-TYPE
    SYNTAX     Win32SystemSlotEntry
    MAX-ACCESS not-accessible
    STATUS     current
    DESCRIPTION
        "None"
    INDEX      { hwssIndex }
    ::= { win32SystemSlotTable 1 }

Win32SystemSlotEntry ::= SEQUENCE {
    hwssIndex Integer32,
    hwssCaption DisplayString,
    hwssConnectorPinout DisplayString,
    hwssConnectorType DisplayString,
    hwssCreationClassName DisplayString,
    hwssCurrentUsage INTEGER,
    hwssDescription DisplayString,
    hwssHeightAllowed Integer32,
    hwssInstallDate DateAndTime,
    hwssLengthAllowed Integer32,
    hwssManufacturer DisplayString,
    hwssMaxDataWidth Integer32,
    hwssModel DisplayString,
    hwssName DisplayString,
    hwssNumber Integer32,
    hwssOtherIdentifyingInfo DisplayString,
    hwssPartNumber DisplayString,
    hwssPMESignal TruthValue,
    hwssPoweredOn TruthValue,
    hwssPurposeDescription DisplayString,
    hwssSerialNumber DisplayString,
    hwssShared TruthValue,
    hwssSKU DisplayString,
    hwssSlotDesignation DisplayString,
    hwssSpecialPurpose TruthValue,
    hwssStatus INTEGER,
    hwssSupportsHotPlug TruthValue,
    hwssTag DisplayString,
    hwssThermalRating Gauge32,
    hwssVccMixedVoltageSupport DisplayString,
    hwssVersion DisplayString,
    hwssVppMixedVoltageSupport DisplayString
}

hwssIndex OBJECT-TYPE
    SYNTAX     Integer32 (1..2147483647)
    MAX-ACCESS read-only
    STATUS     current
    DESCRIPTION
        "The value of this object uniquely identifies the
        instance entry for this class."
    ::= { win32SystemSlotEntry 1 }

hwssCaption OBJECT-TYPE
    SYNTAX     DisplayString (SIZE (0..64))
    MAX-ACCESS read-only
    STATUS     current
    DESCRIPTION
        "Short description of an object a one-line string.
        This property is inherited from
        CIM_ManagedSystemElement."
    ::= { win32SystemSlotEntry 2 }

hwssConnectorPinout OBJECT-TYPE
    SYNTAX     DisplayString
    MAX-ACCESS read-only
    STATUS     current
    DESCRIPTION
        "Free-form string that describes the pin
        configuration and signal usage of a physical
        connector. This property is inherited from
        CIM_PhysicalConnector."
    ::= { win32SystemSlotEntry 3 }

hwssConnectorType OBJECT-TYPE
    SYNTAX     DisplayString
    MAX-ACCESS read-only
    STATUS     current
    DESCRIPTION
        "Array of physical attributes of the connector that
        this slot uses. This property is inherited from
        CIM_PhysicalConnector.
        Value Meaning 
        0 Unknown 
        1 Other 
        2 Male 
        3 Female 
        4 Shielded 
        5 Unshielded 
        6 SCSI (A) High-Density (50 pins) 
        7 SCSI (A) Low-Density (50 pins) 
        8 SCSI (P) High-Density (68 pins) 
        9 SCSI SCA-I (80 pins) 
        10 SCSI SCA-II (80 pins) 
        11 SCSI Fibre Channel (DB-9, Copper) 
        12 SCSI Fibre Channel (Fibre) 
        13 SCSI Fibre Channel SCA-II (40 pins) 
        14 SCSI Fibre Channel SCA-II (20 pins) 
        15 SCSI Fibre Channel BNC 
        16 ATA 3-1/2 Inch (40 pins) 
        17 ATA 2-1/2 Inch (44 pins) 
        18 ATA-2 
        19 ATA-3 
        20 ATA/66 
        21 DB-9 
        22 DB-15 
        23 DB-25 
        24 DB-36 
        25 RS-232C 
        26 RS-422 
        27 RS-423 
        28 RS-485 
        29 RS-449 
        30 V.35 
        31 X.21 
        32 IEEE-488 
        33 AUI 
        34 UTP Category 3 
        35 UTP Category 4 
        36 UTP Category 5 
        37 BNC 
        38 RJ11 
        39 RJ45 
        40 Fiber MIC 
        41 Apple AUI 
        42 Apple GeoPort 
        43 PCI 
        44 ISA 
        45 EISA 
        46 VESA 
        47 PCMCIA 
        48 PCMCIA Type I 
        49 PCMCIA Type II 
        50 PCMCIA Type III 
        51 ZV Port 
        52 CardBus 
        53 USB 
        54 IEEE 1394 
        55 HIPPI 
        56 HSSDC (6 pins) 
        57 GBIC 
        58 DIN 
        59 Mini-DIN 
        60 Micro-DIN 
        61 PS/2 
        62 Infrared 
        63 HP-HIL 
        64 Access.bus 
        65 NuBus 
        66 Centronics 
        67 Mini-Centronics 
        68 Mini-Centronics Type-14 
        69 Mini-Centronics Type-20 
        70 Mini-Centronics Type-26 
        71 Bus Mouse 
        72 ADB 
        73 AGP 
        74 VME Bus 
        75 VME64 
        76 Proprietary 
        77 Proprietary Processor Card Slot 
        78 Proprietary Memory Card Slot 
        79 Proprietary I/O Riser Slot 
        80 PCI-66MHZ 
        81 AGP2X 
        82 AGP4X 
        83 PC-98 
        84 PC-98-Hireso 
        85 PC-H98 
        86 PC-98Note 
        87 PC-98Full 
        88 SSA SCSI 
        89 Circular 
        90 On Board IDE Connector 
        91 On Board Floppy Connector 
        92 9 Pin Dual Inline 
        93 25 Pin Dual Inline 
        94 50 Pin Dual Inline 
        95 68 Pin Dual Inline 
        96 On Board Sound Connector 
        97 Mini-jack 
        98 PCI-X 
        99 Sbus IEEE 1396-1993 32 bit 
        100 Sbus IEEE 1396-1993 64 bit 
        101 MCA 
        102 GIO 
        103 XIO 
        104 HIO 
        105 NGIO 
        106 PMC 
        107 MTRJ 
        108 VF-45 
        109 Future I/O 
        110 SC 
        111 SG 
        112 Electrical 
        113 Optical 
        114 Ribbon 
        115 GLM 
        116 1x9 
        117 Mini SG 
        118 LC 
        119 HSSC 
        120 VHDCI Shielded (68 pins) 
        121 InfiniBand "
    ::= { win32SystemSlotEntry 4 }

hwssCreationClassName OBJECT-TYPE
    SYNTAX     DisplayString (SIZE (0..256))
    MAX-ACCESS read-only
    STATUS     current
    DESCRIPTION
        "Name of the first concrete class that appears in
        the inheritance chain used in the creation of an
        instance. When used with the other key properties
        of a class, the property allows all instances of
        this class and its subclasses to be identified
        uniquely. This property is inherited from
        CIM_PhysicalElement."
    ::= { win32SystemSlotEntry 5 }

hwssCurrentUsage OBJECT-TYPE
    SYNTAX     INTEGER {
        reserved(0),
        other(1),
        unknown(2),
        available(3),
        inUse(4)
    }
    MAX-ACCESS read-only
    STATUS     current
    DESCRIPTION
        "Status of system slot use."
    ::= { win32SystemSlotEntry 6 }

hwssDescription OBJECT-TYPE
    SYNTAX     DisplayString
    MAX-ACCESS read-only
    STATUS     current
    DESCRIPTION
        "Description of the object. This property is
        inherited from CIM_ManagedSystemElement."
    ::= { win32SystemSlotEntry 7 }

hwssHeightAllowed OBJECT-TYPE
    SYNTAX     Integer32
    MAX-ACCESS read-only
    STATUS     current
    DESCRIPTION
        "Maximum height of an adapter card that can be
        inserted into the slot in inches. This property is
        inherited from CIM_Slot."
    ::= { win32SystemSlotEntry 8 }

hwssInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32SystemSlotEntry 9 }

hwssLengthAllowed OBJECT-TYPE
    SYNTAX     Integer32
    MAX-ACCESS read-only
    STATUS     current
    DESCRIPTION
        "Maximum length of an adapter card that can be
        inserted into the slot in inches. This property is
        inherited from CIM_Slot."
    ::= { win32SystemSlotEntry 10 }

hwssManufacturer OBJECT-TYPE
    SYNTAX     DisplayString (SIZE (0..256))
    MAX-ACCESS read-only
    STATUS     current
    DESCRIPTION
        "Name of the organization that produces the
        physical element. This property is inherited from
        CIM_PhysicalElement."
    ::= { win32SystemSlotEntry 11 }

hwssMaxDataWidth OBJECT-TYPE
    SYNTAX     Integer32
    MAX-ACCESS read-only
    STATUS     current
    DESCRIPTION
        "Maximum bus width of adapter cards that can be
        inserted into this slot in bits. This property is
        inherited from CIM_Slot.
        Value Maximun data widith (bits) 
        0 8 
        1 16 
        2 32 
        3 64 
        4 128 "
    ::= { win32SystemSlotEntry 12 }

hwssModel OBJECT-TYPE
    SYNTAX     DisplayString (SIZE (0..64))
    MAX-ACCESS read-only
    STATUS     current
    DESCRIPTION
        "Name for the physical element. This property is
        inherited from CIM_PhysicalElement."
    ::= { win32SystemSlotEntry 13 }

hwssName OBJECT-TYPE
    SYNTAX     DisplayString
    MAX-ACCESS read-only
    STATUS     current
    DESCRIPTION
        "Label for the object. When subclassed, the
        property can be overridden to be a key property.
        This property is inherited from
        CIM_ManagedSystemElement."
    ::= { win32SystemSlotEntry 14 }

hwssNumber OBJECT-TYPE
    SYNTAX     Integer32
    MAX-ACCESS read-only
    STATUS     current
    DESCRIPTION
        "Physical slot number that can be used as an index
        into a system slot table, whether or not that slot
        is physically occupied. This property is inherited
        from CIM_Slot."
    ::= { win32SystemSlotEntry 15 }

hwssOtherIdentifyingInfo OBJECT-TYPE
    SYNTAX     DisplayString
    MAX-ACCESS read-only
    STATUS     current
    DESCRIPTION
        "Additional data (that is, more than asset tag
        information), that can be used to identify a
        physical element. One example is bar code data
        associated with an element that also has an asset
        tag. Note that if only bar code data is available,
        and it is unique or can be used as an element key,
        this property is NULL, and the bar code data is
        used as the class key in the Tag property. This
        property is inherited from CIM_PhysicalElement."
    ::= { win32SystemSlotEntry 16 }

hwssPartNumber OBJECT-TYPE
    SYNTAX     DisplayString (SIZE (0..256))
    MAX-ACCESS read-only
    STATUS     current
    DESCRIPTION
        "Part number that the producer or manufacturer
        assigns to the physical element. This property is
        inherited from CIM_PhysicalElement."
    ::= { win32SystemSlotEntry 17 }

hwssPMESignal OBJECT-TYPE
    SYNTAX     TruthValue
    MAX-ACCESS read-only
    STATUS     current
    DESCRIPTION
        "If TRUE, the PCI bus Power Management Enabled
        (PME) signal is supported by this slot."
    ::= { win32SystemSlotEntry 18 }

hwssPoweredOn OBJECT-TYPE
    SYNTAX     TruthValue
    MAX-ACCESS read-only
    STATUS     current
    DESCRIPTION
        "If TRUE, the physical element is powered on. This
        property is inherited from CIM_PhysicalElement."
    ::= { win32SystemSlotEntry 19 }

hwssPurposeDescription OBJECT-TYPE
    SYNTAX     DisplayString
    MAX-ACCESS read-only
    STATUS     current
    DESCRIPTION
        "Free-form string that describes how this slot is
        physically unique and may hold special types of
        hardware. This property only has meaning when the
        corresponding property SpecialPurpose is TRUE. This
        property is inherited from CIM_Slot."
    ::= { win32SystemSlotEntry 20 }

hwssSerialNumber OBJECT-TYPE
    SYNTAX     DisplayString (SIZE (0..64))
    MAX-ACCESS read-only
    STATUS     current
    DESCRIPTION
        "Manufacturer-allocated number used to identify the
        physical element. This property is inherited from
        CIM_PhysicalElement."
    ::= { win32SystemSlotEntry 21 }

hwssShared OBJECT-TYPE
    SYNTAX     TruthValue
    MAX-ACCESS read-only
    STATUS     current
    DESCRIPTION
        "If TRUE, two or more slots share a location on the
        baseboard, such as a PCI/EISA shared slot."
    ::= { win32SystemSlotEntry 22 }

hwssSKU OBJECT-TYPE
    SYNTAX     DisplayString (SIZE (0..64))
    MAX-ACCESS read-only
    STATUS     current
    DESCRIPTION
        "Stockkeeping unit number for the physical element.
        This property is inherited from
        CIM_PhysicalElement."
    ::= { win32SystemSlotEntry 23 }

hwssSlotDesignation OBJECT-TYPE
    SYNTAX     DisplayString
    MAX-ACCESS read-only
    STATUS     current
    DESCRIPTION
        "SMBIOS string that identifies the system slot
        designation of the slot on the motherboard.
        Example: 'PCI-1'"
    ::= { win32SystemSlotEntry 24 }

hwssSpecialPurpose OBJECT-TYPE
    SYNTAX     TruthValue
    MAX-ACCESS read-only
    STATUS     current
    DESCRIPTION
        "If TRUE, this slot is physically unique and may
        hold special types of hardware, such as a graphics
        processor slot. If TRUE, then PurposeDescription
        should specify the nature of the uniqueness or
        purpose of the slot. This property is inherited
        from CIM_Slot."
    ::= { win32SystemSlotEntry 25 }

hwssStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32SystemSlotEntry 26 }

hwssSupportsHotPlug OBJECT-TYPE
    SYNTAX     TruthValue
    MAX-ACCESS read-only
    STATUS     current
    DESCRIPTION
        "If TRUE, the slot supports hot-plugging of adapter
        cards. This property is inherited from CIM_Slot."
    ::= { win32SystemSlotEntry 27 }

hwssTag OBJECT-TYPE
    SYNTAX     DisplayString (SIZE (0..256))
    MAX-ACCESS read-only
    STATUS     current
    DESCRIPTION
        "System slot represented by an instance of this
        class. This property is inherited from
        CIM_PhysicalElement.
        Example: 'System Slot 1'"
    ::= { win32SystemSlotEntry 28 }

hwssThermalRating OBJECT-TYPE
    SYNTAX     Gauge32
    MAX-ACCESS read-only
    STATUS     current
    DESCRIPTION
        "Maximum thermal dissipation of the slot in
        milliwatts. This property is inherited from
        CIM_Slot."
    ::= { win32SystemSlotEntry 29 }

hwssVccMixedVoltageSupport OBJECT-TYPE
    SYNTAX     DisplayString
    MAX-ACCESS read-only
    STATUS     current
    DESCRIPTION
        "Array of enumerated integers indicating the Vcc
        voltage supported by this slot. This property is
        inherited from CIM_Slot.
        Value Meaning 
        0 Unknown 
        1 Other 
        2 3.3V 
        3 5V "
    ::= { win32SystemSlotEntry 30 }

hwssVersion OBJECT-TYPE
    SYNTAX     DisplayString (SIZE (0..64))
    MAX-ACCESS read-only
    STATUS     current
    DESCRIPTION
        "Version of the physical element. This property is
        inherited from CIM_PhysicalElement."
    ::= { win32SystemSlotEntry 31 }

hwssVppMixedVoltageSupport OBJECT-TYPE
    SYNTAX     DisplayString
    MAX-ACCESS read-only
    STATUS     current
    DESCRIPTION
        "Array of enumerated integers indicating the Vpp
        voltage supported by this slot. This property is
        inherited from CIM_Slot.
        Value Meaning 
        0 Unknown 
        1 Other 
        2 3.3V 
        3 5V 
        4 12V "
    ::= { win32SystemSlotEntry 32 }

win32USBControllerTable OBJECT-TYPE
    SYNTAX     SEQUENCE OF Win32USBControllerEntry
    MAX-ACCESS not-accessible
    STATUS     current
    DESCRIPTION
        "The Win32_USBController WMI class manages the
        capabilities of a Universal Serial Bus (USB)
        controller."
    ::= { wmiMotherboardControllerPort 33 }

win32USBControllerEntry OBJECT-TYPE
    SYNTAX     Win32USBControllerEntry
    MAX-ACCESS not-accessible
    STATUS     current
    DESCRIPTION
        "None"
    INDEX      { hwucIndex }
    ::= { win32USBControllerTable 1 }

Win32USBControllerEntry ::= SEQUENCE {
    hwucIndex Integer32,
    hwucAvailability INTEGER,
    hwucCaption DisplayString,
    hwucConfigManagerErrorCode INTEGER,
    hwucConfigManagerUserConfig TruthValue,
    hwucCreationClassName DisplayString,
    hwucDescription DisplayString,
    hwucDeviceID DisplayString,
    hwucErrorCleared TruthValue,
    hwucErrorDescription DisplayString,
    hwucInstallDate DateAndTime,
    hwucLastErrorCode Gauge32,
    hwucManufacturer DisplayString,
    hwucMaxNumberControlled Gauge32,
    hwucName DisplayString,
    hwucPNPDeviceID DisplayString,
    hwucPowerManagementCapabilities DisplayString,
    hwucPowerManagementSupported TruthValue,
    hwucProtocolSupported INTEGER,
    hwucStatus INTEGER,
    hwucStatusInfo INTEGER,
    hwucSystemCreationClassName DisplayString,
    hwucSystemName DisplayString,
    hwucTimeOfLastReset DateAndTime
}

hwucIndex OBJECT-TYPE
    SYNTAX     Integer32 (1..2147483647)
    MAX-ACCESS read-only
    STATUS     current
    DESCRIPTION
        "The value of this object uniquely identifies the
        instance entry for this class."
    ::= { win32USBControllerEntry 1 }

hwucAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32USBControllerEntry 2 }

hwucCaption OBJECT-TYPE
    SYNTAX     DisplayString (SIZE (0..64))
    MAX-ACCESS read-only
    STATUS     current
    DESCRIPTION
        "Short description (one-line string) of the object.
        This property is inherited from
        CIM_ManagedSystemElement."
    ::= { win32USBControllerEntry 3 }

hwucConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32USBControllerEntry 4 }

hwucConfigManagerUserConfig OBJECT-TYPE
    SYNTAX     TruthValue
    MAX-ACCESS read-only
    STATUS     current
    DESCRIPTION
        "If TRUE, the device is using a user-defined
        configuration. This property is inherited from
        CIM_LogicalDevice."
    ::= { win32USBControllerEntry 5 }

hwucCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32USBControllerEntry 6 }

hwucDescription OBJECT-TYPE
    SYNTAX     DisplayString
    MAX-ACCESS read-only
    STATUS     current
    DESCRIPTION
        "Description of the object. This property is
        inherited from CIM_ManagedSystemElement."
    ::= { win32USBControllerEntry 7 }

hwucDeviceID OBJECT-TYPE
    SYNTAX     DisplayString
    MAX-ACCESS read-only
    STATUS     current
    DESCRIPTION
        "Unique identifier of the USB controller. This
        property is inherited from CIM_LogicalDevice."
    ::= { win32USBControllerEntry 8 }

hwucErrorCleared OBJECT-TYPE
    SYNTAX     TruthValue
    MAX-ACCESS read-only
    STATUS     current
    DESCRIPTION
        "If TRUE, the error reported in LastErrorCode is
        now cleared. This property is inherited from
        CIM_LogicalDevice."
    ::= { win32USBControllerEntry 9 }

hwucErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32USBControllerEntry 10 }

hwucInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32USBControllerEntry 11 }

hwucLastErrorCode OBJECT-TYPE
    SYNTAX     Gauge32
    MAX-ACCESS read-only
    STATUS     current
    DESCRIPTION
        "Last error code reported by the logical device.
        This property is inherited from CIM_LogicalDevice."
    ::= { win32USBControllerEntry 12 }

hwucManufacturer OBJECT-TYPE
    SYNTAX     DisplayString
    MAX-ACCESS read-only
    STATUS     current
    DESCRIPTION
        "Manufacturer of the controller. This property is
        inherited from CIM_USBController."
    ::= { win32USBControllerEntry 13 }

hwucMaxNumberControlled OBJECT-TYPE
    SYNTAX     Gauge32
    MAX-ACCESS read-only
    STATUS     current
    DESCRIPTION
        "Maximum number of directly addressable entities
        supportable by this controller. A value of 0 should
        be used if the number is unknown. This property is
        inherited from CIM_Controller."
    ::= { win32USBControllerEntry 14 }

hwucName OBJECT-TYPE
    SYNTAX     DisplayString
    MAX-ACCESS read-only
    STATUS     current
    DESCRIPTION
        "Label by which the object is known. When
        subclassed, the property can be overridden to be a
        key property. This property is inherited from
        CIM_ManagedSystemElement."
    ::= { win32USBControllerEntry 15 }

hwucPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32USBControllerEntry 16 }

hwucPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32USBControllerEntry 17 }

hwucPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32USBControllerEntry 18 }

hwucProtocolSupported OBJECT-TYPE
    SYNTAX     INTEGER {
        other(0),
        unknown(1),
        eisa(2),
        isa(3),
        pci(4),
        ataATAPI(5),
        flexibleDiskette(6),
        n1496(7),
        scsiParallelInterface(8),
        scsiFibreChannelProtocol(9),
        scsiSerialBusProtocol(10),
        scsiSerialBusProtocol1394(11),
        scsiSerialStorageArchitecture(12),
        vesa(13),
        pcmcia(14),
        universalSerialBus(15),
        parallelProtocol(16),
        escon(17),
        diagnostic(18),
        i2C(19),
        power(20),
        hippi(21),
        multiBus(22),
        vme(23),
        ipi(24),
        ieee488(25),
        rs232(26),
        ieee802310BASE5(27),
        ieee802310BASE2(28),
        ieee80231BASE5(29),
        ieee802310BROAD36(30),
        ieee8023100BASEVG(31),
        ieee8025TokenRing(32),
        ansiX3T95FDDI(33),
        mca(34),
        esdi(35),
        ide(36),
        cmd(37),
        st506(38),
        dssi(39),
        qic2(40),
        enhancedATAIDE(41),
        agp(42),
        twowayInfrared(43),
        fastInfrared(44),
        serialInfrared(45),
        irBus(46)
    }
    MAX-ACCESS read-only
    STATUS     current
    DESCRIPTION
        "Protocol used by the controller to access
        'controlled' devices. This property is inherited
        from CIM_Controller."
    ::= { win32USBControllerEntry 19 }

hwucStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32USBControllerEntry 20 }

hwucStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32USBControllerEntry 21 }

hwucSystemCreationClassName OBJECT-TYPE
    SYNTAX     DisplayString
    MAX-ACCESS read-only
    STATUS     current
    DESCRIPTION
        "Value for the scoping computer's CreationClassName
        property. This property is inherited from
        CIM_LogicalDevice."
    ::= { win32USBControllerEntry 22 }

hwucSystemName OBJECT-TYPE
    SYNTAX     DisplayString
    MAX-ACCESS read-only
    STATUS     current
    DESCRIPTION
        "Name of the scoping system. This property is
        inherited from CIM_LogicalDevice."
    ::= { win32USBControllerEntry 23 }

hwucTimeOfLastReset OBJECT-TYPE
    SYNTAX     DateAndTime
    MAX-ACCESS read-only
    STATUS     current
    DESCRIPTION
        "Date and time the controller was last reset. This
        could mean the controller was powered down, or
        reinitialized. This property is inherited from
        CIM_Controller."
    ::= { win32USBControllerEntry 24 }

win32USBHubTable OBJECT-TYPE
    SYNTAX     SEQUENCE OF Win32USBHubEntry
    MAX-ACCESS not-accessible
    STATUS     current
    DESCRIPTION
        "The Win32_USBHub WMI class represents the
        management characteristics of a USB hub."
    ::= { wmiMotherboardControllerPort 34 }

win32USBHubEntry OBJECT-TYPE
    SYNTAX     Win32USBHubEntry
    MAX-ACCESS not-accessible
    STATUS     current
    DESCRIPTION
        "None"
    INDEX      { hwuhIndex }
    ::= { win32USBHubTable 1 }

Win32USBHubEntry ::= SEQUENCE {
    hwuhIndex Integer32,
    hwuhAvailability INTEGER,
    hwuhCaption DisplayString,
    hwuhClassCode Integer32,
    hwuhConfigManagerErrorCode INTEGER,
    hwuhConfigManagerUserCode TruthValue,
    hwuhCreationClassName DisplayString,
    hwuhCurrentAlternativeSettings Integer32,
    hwuhCurrentConfigValue Integer32,
    hwuhDescription DisplayString,
    hwuhDeviceID DisplayString,
    hwuhErrorCleared TruthValue,
    hwuhErrorDescription DisplayString,
    hwuhGangSwitched TruthValue,
    hwuhInstallDate DateAndTime,
    hwuhLastErrorCode Gauge32,
    hwuhName DisplayString,
    hwuhNumberOfConfigs Integer32,
    hwuhNumberOfPorts Integer32,
    hwuhPNPDeviceID DisplayString,
    hwuhPowerManagementCapabilities DisplayString,
    hwuhPowerManagementSupported TruthValue,
    hwuhProtocolCode Integer32,
    hwuhStatus INTEGER,
    hwuhStatusInfo INTEGER,
    hwuhSubclassCode Integer32,
    hwuhSystemCreationClassName DisplayString,
    hwuhSystemName DisplayString,
    hwuhUSBVersion Integer32
}

hwuhIndex OBJECT-TYPE
    SYNTAX     Integer32 (1..2147483647)
    MAX-ACCESS read-only
    STATUS     current
    DESCRIPTION
        "The value of this object uniquely identifies the
        instance entry for this class."
    ::= { win32USBHubEntry 1 }

hwuhAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32USBHubEntry 2 }

hwuhCaption OBJECT-TYPE
    SYNTAX     DisplayString (SIZE (0..64))
    MAX-ACCESS read-only
    STATUS     current
    DESCRIPTION
        "Short description (one-line string) of the
        CIM_Setting object. This property is inherited from
        CIM_Setting."
    ::= { win32USBHubEntry 3 }

hwuhClassCode OBJECT-TYPE
    SYNTAX     Integer32 (0..255)
    MAX-ACCESS read-only
    STATUS     current
    DESCRIPTION
        "USB class code. This property is inherited from
        CIM_USBHub."
    ::= { win32USBHubEntry 4 }

hwuhConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32USBHubEntry 5 }

hwuhConfigManagerUserCode OBJECT-TYPE
    SYNTAX     TruthValue
    MAX-ACCESS read-only
    STATUS     current
    DESCRIPTION
        "If TRUE, the device is using a user-defined
        configuration. This property is inherited from
        CIM_LogicalDevice."
    ::= { win32USBHubEntry 6 }

hwuhCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32USBHubEntry 7 }

hwuhCurrentAlternativeSettings OBJECT-TYPE
    SYNTAX     Integer32 (0..255)
    MAX-ACCESS read-only
    STATUS     current
    DESCRIPTION
        "Array of USB alternate settings for each interface
        in the currently selected configuration (indicated
        by the CurrentConfigValue property). This array has
        one entry for each interface in the configuration.
        If the property, CurrentConfigValue is 0
        (indicating that the device is not configured), the
        array is undefined. To understand how to parse this
        octet string, refer to the USB specification. This
        property is inherited from CIM_LogicalDevice."
    ::= { win32USBHubEntry 8 }

hwuhCurrentConfigValue OBJECT-TYPE
    SYNTAX     Integer32 (0..255)
    MAX-ACCESS read-only
    STATUS     current
    DESCRIPTION
        "Configuration currently configured for this
        device. If this value is 0, the device is not
        configured. This property is inherited from
        CIM_USBDevice."
    ::= { win32USBHubEntry 9 }

hwuhDescription OBJECT-TYPE
    SYNTAX     DisplayString
    MAX-ACCESS read-only
    STATUS     current
    DESCRIPTION
        "Textual description of the object. This property
        is inherited from CIM_ManagedSystemElement."
    ::= { win32USBHubEntry 10 }

hwuhDeviceID OBJECT-TYPE
    SYNTAX     DisplayString
    MAX-ACCESS read-only
    STATUS     current
    DESCRIPTION
        "Address or other identifying information to name
        the logical device uniquely. This property is
        inherited from CIM_LogicalDevice."
    ::= { win32USBHubEntry 11 }

hwuhErrorCleared OBJECT-TYPE
    SYNTAX     TruthValue
    MAX-ACCESS read-only
    STATUS     current
    DESCRIPTION
        "Indicates that the error reported in the
        LastErrorCode property is now cleared. This
        property is inherited from CIM_LogicalDevice."
    ::= { win32USBHubEntry 12 }

hwuhErrorDescription OBJECT-TYPE
    SYNTAX     DisplayString
    MAX-ACCESS read-only
    STATUS     current
    DESCRIPTION
        "Free-form string supplying more information about
        the error recorded in LastErrorCode property, and
        information on any corrective actions that may be
        taken. This property is inherited from
        CIM_LogicalDevice."
    ::= { win32USBHubEntry 13 }

hwuhGangSwitched OBJECT-TYPE
    SYNTAX     TruthValue
    MAX-ACCESS read-only
    STATUS     current
    DESCRIPTION
        "If TRUE, power is switched to all ports on the HUB
        at one time. If FALSE, power is switched
        individually for each port. This property is
        inherited from CIM_USBHub."
    ::= { win32USBHubEntry 14 }

hwuhInstallDate OBJECT-TYPE
    SYNTAX     DateAndTime
    MAX-ACCESS read-only
    STATUS     current
    DESCRIPTION
        "Date the object was installed. This property does
        not need a value to indicate that the object is
        installed. This property is inherited from
        CIM_ManagedSystemElement."
    ::= { win32USBHubEntry 15 }

hwuhLastErrorCode OBJECT-TYPE
    SYNTAX     Gauge32
    MAX-ACCESS read-only
    STATUS     current
    DESCRIPTION
        "Last error code reported by the logical device.
        This property is inherited from CIM_LogicalDevice."
    ::= { win32USBHubEntry 16 }

hwuhName OBJECT-TYPE
    SYNTAX     DisplayString
    MAX-ACCESS read-only
    STATUS     current
    DESCRIPTION
        "Name of the USB hub. This property is inherited
        from CIM_ManagedSystemElement."
    ::= { win32USBHubEntry 17 }

hwuhNumberOfConfigs OBJECT-TYPE
    SYNTAX     Integer32 (0..255)
    MAX-ACCESS read-only
    STATUS     current
    DESCRIPTION
        "Number of defined device configurations. This
        property is inherited from CIM_USBDevice."
    ::= { win32USBHubEntry 18 }

hwuhNumberOfPorts OBJECT-TYPE
    SYNTAX     Integer32 (0..255)
    MAX-ACCESS read-only
    STATUS     current
    DESCRIPTION
        "Number of downstream ports on the hub, including
        those embedded in the hub's silicon. This property
        is inherited from CIM_USBHub."
    ::= { win32USBHubEntry 19 }

hwuhPNPDeviceID OBJECT-TYPE
    SYNTAX     DisplayString
    MAX-ACCESS read-only
    STATUS     current
    DESCRIPTION
        "Windows Plug and Play device identifier of the
        logical device. Example: *PNP030b. This property is
        inherited from CIM_LogicalDevice."
    ::= { win32USBHubEntry 20 }

hwuhPowerManagementCapabilities OBJECT-TYPE
    SYNTAX     DisplayString
    MAX-ACCESS read-only
    STATUS     current
    DESCRIPTION
        "Specific power-related capabilities of the logical
        device. This property is inherited from CIM_USBHub.
        Value Meaning 
        0 Unknown 
        1 Not Supported 
        2 Disabled 
        3 Enabled 
        4 Power Saving Modes Entered Automatically 
        5 Power State Settable 
        6 Power Cycling Supported 
        7 Timed Power On Supported "
    ::= { win32USBHubEntry 21 }

hwuhPowerManagementSupported OBJECT-TYPE
    SYNTAX     TruthValue
    MAX-ACCESS read-only
    STATUS     current
    DESCRIPTION
        "If TRUE, the device can be power managed; that is,
        put into a power save state. This Boolean value
        does not indicate that power management features
        are currently enabled, or if enabled, what features
        are supported. For more information, see the
        PowerManagementCapabilities array for this
        information. If FALSE, the integer value 1, for the
        string 'Not Supported', should be the only entry in
        the PowerManagementCapabilities array. This
        property is inherited from CIM_LogicalDevice."
    ::= { win32USBHubEntry 22 }

hwuhProtocolCode OBJECT-TYPE
    SYNTAX     Integer32 (0..255)
    MAX-ACCESS read-only
    STATUS     current
    DESCRIPTION
        "USB protocol code. This property is inherited from
        CIM_USBDevice."
    ::= { win32USBHubEntry 23 }

hwuhStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32USBHubEntry 24 }

hwuhStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32USBHubEntry 25 }

hwuhSubclassCode OBJECT-TYPE
    SYNTAX     Integer32 (0..255)
    MAX-ACCESS read-only
    STATUS     current
    DESCRIPTION
        "USB subclass code. This property is inherited from
        CIM_USBDevice."
    ::= { win32USBHubEntry 26 }

hwuhSystemCreationClassName OBJECT-TYPE
    SYNTAX     DisplayString
    MAX-ACCESS read-only
    STATUS     current
    DESCRIPTION
        "Creation class name for the scoping system. This
        property is inherited from CIM_LogicalDevice."
    ::= { win32USBHubEntry 27 }

hwuhSystemName OBJECT-TYPE
    SYNTAX     DisplayString
    MAX-ACCESS read-only
    STATUS     current
    DESCRIPTION
        "Name of the scoping system. This property is
        inherited from CIM_LogicalDevice."
    ::= { win32USBHubEntry 28 }

hwuhUSBVersion OBJECT-TYPE
    SYNTAX     Integer32
    MAX-ACCESS read-only
    STATUS     current
    DESCRIPTION
        "Latest USB version supported by the USB device.
        The property is expressed as a binary-coded decimal
        (BCD), where a decimal point is implied between the
        second and third digits. For example, a value of
        0x201 indicates that version 2.01 is supported.
        This property is inherited from CIM_USBDevice."
    ::= { win32USBHubEntry 29 }

wmiNetworkingDevice OBJECT-IDENTITY
    STATUS     current
    DESCRIPTION
        "The Networking Devices subcategory groups classes
        that represent the network interface controller,
        its configurations, and its settings."
    ::= { wmiHardware 5 }

win32NetworkAdapterTable OBJECT-TYPE
    SYNTAX     SEQUENCE OF Win32NetworkAdapterEntry
    MAX-ACCESS not-accessible
    STATUS     current
    DESCRIPTION
        "The Win32_NetworkAdapter WMI class represents a
        network adapter on a Windows operating system."
    ::= { wmiNetworkingDevice 1 }

win32NetworkAdapterEntry OBJECT-TYPE
    SYNTAX     Win32NetworkAdapterEntry
    MAX-ACCESS not-accessible
    STATUS     current
    DESCRIPTION
        "None"
    INDEX      { hwnaIndex }
    ::= { win32NetworkAdapterTable 1 }

Win32NetworkAdapterEntry ::= SEQUENCE {
    hwnaIndex Integer32,
    hwnaAdapterType DisplayString,
    hwnaAdapterTypeID INTEGER,
    hwnaAutoSense TruthValue,
    hwnaAvailability INTEGER,
    hwnaCaption DisplayString,
    hwnaConfigManagerErrorCode INTEGER,
    hwnaConfigManagerUserConfig TruthValue,
    hwnaCreationClassName DisplayString,
    hwnaDescription DisplayString,
    hwnaDeviceID DisplayString,
    hwnaErrorCleared TruthValue,
    hwnaErrorDescription DisplayString,
    hwnaRegistryIndex Gauge32,
    hwnaInstallDate DateAndTime,
    hwnaInstalled TruthValue,
    hwnaInterfaceIndex Gauge32,
    hwnaLastErrorCode Gauge32,
    hwnaMACAddress DisplayString,
    hwnaManufacturer DisplayString,
    hwnaMaxNumberControlled Gauge32,
    hwnaMaxSpeed Gauge32,
    hwnaName DisplayString,
    hwnaNetConnectionID DisplayString,
    hwnaNetConnectionStatus INTEGER,
    hwnaNetworkAddresses DisplayString,
    hwnaPermanentAddress DisplayString,
    hwnaPNPDeviceID DisplayString,
    hwnaPowerManagementCapabilities DisplayString,
    hwnaPowerManagementSupported TruthValue,
    hwnaProductName DisplayString,
    hwnaServiceName DisplayString,
    hwnaSpeed Gauge32,
    hwnaStatus INTEGER,
    hwnaStatusInfo INTEGER,
    hwnaSystemCreationClassName DisplayString,
    hwnaSystemName DisplayString,
    hwnaTimeOfLastReset DateAndTime
}

hwnaIndex OBJECT-TYPE
    SYNTAX     Integer32 (1..2147483647)
    MAX-ACCESS read-only
    STATUS     current
    DESCRIPTION
        "The value of this object uniquely identifies the
        instance entry for this class."
    ::= { win32NetworkAdapterEntry 1 }

hwnaAdapterType OBJECT-TYPE
    SYNTAX     DisplayString
    MAX-ACCESS read-only
    STATUS     current
    DESCRIPTION
        "Network medium in use. This property may not be
        applicable to all types of network adapters listed
        within this class Windows NT only. 
        'Ethernet 802.3'
        'Token Ring 802.5'
        'Fiber Distributed Data Interface (FDDI)'
        'Wide Area Network (WAN)'
        'LocalTalk'
        'Ethernet using DIX header format'
        'ARCNET'
        'ARCNET (878.2)'
        'ATM'
        'Wireless'
        'Infrared Wireless'
        'Bpc'
        'CoWan'
        '1394'"
    ::= { win32NetworkAdapterEntry 2 }

hwnaAdapterTypeID OBJECT-TYPE
    SYNTAX     INTEGER {
        ethernet8023(0),
        tokenRing8025(1),
        fiberDistributedDataInterface(2),
        wideAreaNetwork(3),
        localTalk(4),
        ethernetUsingDIXHeaderFormat(5),
        arcnet(6),
        arcnet8782(7),
        atm(8),
        wireless(9),
        infraredWireless(10),
        bpc(11),
        coWan(12),
        n1394(13)
    }
    MAX-ACCESS read-only
    STATUS     current
    DESCRIPTION
        "Network medium in use. Gives the same information
        as the AdapterType property, except that the
        information is in the form of an integer. This
        property may not be applicable to all types of
        network adapters listed Windows NT only. This
        property is new for Windows XP."
    ::= { win32NetworkAdapterEntry 3 }

hwnaAutoSense OBJECT-TYPE
    SYNTAX     TruthValue
    MAX-ACCESS read-only
    STATUS     current
    DESCRIPTION
        "If TRUE, the network adapter is capable of
        automatically determining the speed of the
        attached/network media. This property is inherited
        from CIM_NetworkAdapter. "
    ::= { win32NetworkAdapterEntry 4 }

hwnaAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32NetworkAdapterEntry 5 }

hwnaCaption OBJECT-TYPE
    SYNTAX     DisplayString
    MAX-ACCESS read-only
    STATUS     current
    DESCRIPTION
        "Short description of the object a one-line string.
        This property is inherited from
        CIM_ManagedSystemElement. "
    ::= { win32NetworkAdapterEntry 6 }

hwnaConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32NetworkAdapterEntry 7 }

hwnaConfigManagerUserConfig OBJECT-TYPE
    SYNTAX     TruthValue
    MAX-ACCESS read-only
    STATUS     current
    DESCRIPTION
        "If TRUE, the device is using a user-defined
        configuration. This property is inherited from
        CIM_LogicalDevice."
    ::= { win32NetworkAdapterEntry 8 }

hwnaCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32NetworkAdapterEntry 9 }

hwnaDescription OBJECT-TYPE
    SYNTAX     DisplayString
    MAX-ACCESS read-only
    STATUS     current
    DESCRIPTION
        "Description of the object. This property is
        inherited from CIM_ManagedSystemElement."
    ::= { win32NetworkAdapterEntry 10 }

hwnaDeviceID OBJECT-TYPE
    SYNTAX     DisplayString
    MAX-ACCESS read-only
    STATUS     current
    DESCRIPTION
        "Unique identifier of the network adapter from
        other devices on the system. This property is
        inherited from CIM_LogicalDevice."
    ::= { win32NetworkAdapterEntry 11 }

hwnaErrorCleared OBJECT-TYPE
    SYNTAX     TruthValue
    MAX-ACCESS read-only
    STATUS     current
    DESCRIPTION
        "If TRUE, the error reported in LastErrorCode is
        now cleared. This property is inherited from
        CIM_LogicalDevice."
    ::= { win32NetworkAdapterEntry 12 }

hwnaErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32NetworkAdapterEntry 13 }

hwnaRegistryIndex OBJECT-TYPE
    SYNTAX     Gauge32
    MAX-ACCESS read-only
    STATUS     current
    DESCRIPTION
        "Index number of the network adapter, stored in the
        system registry.
        Example: 0"
    ::= { win32NetworkAdapterEntry 14 }

hwnaInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32NetworkAdapterEntry 15 }

hwnaInstalled OBJECT-TYPE
    SYNTAX     TruthValue
    MAX-ACCESS read-only
    STATUS     current
    DESCRIPTION
        "If TRUE, the network adapter is installed in the
        system."
    ::= { win32NetworkAdapterEntry 16 }

hwnaInterfaceIndex OBJECT-TYPE
    SYNTAX     Gauge32
    MAX-ACCESS read-only
    STATUS     current
    DESCRIPTION
        "Index value that uniquely identifies the local
        network interface. The value in this property is
        the same as the value in the InterfaceIndex
        property in the instance of Win32_IP4RouteTable
        that represents the network interface in the route
        table.
        Windows XP and earlier:   The InterfaceIndex
        property is not available."
    ::= { win32NetworkAdapterEntry 17 }

hwnaLastErrorCode OBJECT-TYPE
    SYNTAX     Gauge32
    MAX-ACCESS read-only
    STATUS     current
    DESCRIPTION
        "Last error code reported by the logical device.
        This property is inherited from CIM_LogicalDevice."
    ::= { win32NetworkAdapterEntry 18 }

hwnaMACAddress OBJECT-TYPE
    SYNTAX     DisplayString
    MAX-ACCESS read-only
    STATUS     current
    DESCRIPTION
        "Media access control address for this network
        adapter. A MAC address is a unique 48-bit number
        assigned to the network adapter by the
        manufacturer. It uniquely identifies this network
        adapter and is used for mapping TCP/IP network
        communications."
    ::= { win32NetworkAdapterEntry 19 }

hwnaManufacturer OBJECT-TYPE
    SYNTAX     DisplayString
    MAX-ACCESS read-only
    STATUS     current
    DESCRIPTION
        "Name of the network adapter's manufacturer.
        Example: '3COM'"
    ::= { win32NetworkAdapterEntry 20 }

hwnaMaxNumberControlled OBJECT-TYPE
    SYNTAX     Gauge32
    MAX-ACCESS read-only
    STATUS     current
    DESCRIPTION
        "Maximum number of directly addressable ports
        supported by this network adapter. A value of 0
        should be used if the number is unknown."
    ::= { win32NetworkAdapterEntry 21 }

hwnaMaxSpeed OBJECT-TYPE
    SYNTAX     Gauge32
    MAX-ACCESS read-only
    STATUS     current
    DESCRIPTION
        "Maximum speed, in bits per second, for the network
        adapter. This property is inherited from
        CIM_NetworkAdapter."
    ::= { win32NetworkAdapterEntry 22 }

hwnaName OBJECT-TYPE
    SYNTAX     DisplayString
    MAX-ACCESS read-only
    STATUS     current
    DESCRIPTION
        "Label by which the object is known. When
        subclassed, the property can be overridden to be a
        key property. This property is inherited from
        CIM_ManagedSystemElement."
    ::= { win32NetworkAdapterEntry 23 }

hwnaNetConnectionID OBJECT-TYPE
    SYNTAX     DisplayString
    MAX-ACCESS read-only
    STATUS     current
    DESCRIPTION
        "Name of the network connection as it appears in
        the Network Connections Control Panel program. This
        property is new for Windows XP."
    ::= { win32NetworkAdapterEntry 24 }

hwnaNetConnectionStatus OBJECT-TYPE
    SYNTAX     INTEGER {
        disconnected(0),
        connecting(1),
        connected(2),
        disconnecting(3),
        hardwareNotPresent(4),
        hardwareDisabled(5),
        hardwareMalfunction(6),
        mediaDisconnected(7),
        authenticating(8),
        authenticationSucceeded(9),
        authenticationFailed(10)
    }
    MAX-ACCESS read-only
    STATUS     current
    DESCRIPTION
        "State of the network adapter's connection to the
        network. This property is new for Windows XP."
    ::= { win32NetworkAdapterEntry 25 }

hwnaNetworkAddresses OBJECT-TYPE
    SYNTAX     DisplayString
    MAX-ACCESS read-only
    STATUS     current
    DESCRIPTION
        "Array of network addresses for an adapter. This
        property is inherited from CIM_NetworkAdapter."
    ::= { win32NetworkAdapterEntry 26 }

hwnaPermanentAddress OBJECT-TYPE
    SYNTAX     DisplayString
    MAX-ACCESS read-only
    STATUS     current
    DESCRIPTION
        "Network address hard-coded into an adapter. This
        hard-coded address may be changed by firmware
        upgrade or software configuration. If so, this
        field should be updated when the change is made.
        The property should be left blank if no hard-coded
        address exists for the network adapter. This
        property is inherited from CIM_NetworkAdapter."
    ::= { win32NetworkAdapterEntry 27 }

hwnaPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32NetworkAdapterEntry 28 }

hwnaPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32NetworkAdapterEntry 29 }

hwnaPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32NetworkAdapterEntry 30 }

hwnaProductName OBJECT-TYPE
    SYNTAX     DisplayString
    MAX-ACCESS read-only
    STATUS     current
    DESCRIPTION
        "Product name of the network adapter.
        Example: 'Fast EtherLink XL'"
    ::= { win32NetworkAdapterEntry 31 }

hwnaServiceName OBJECT-TYPE
    SYNTAX     DisplayString
    MAX-ACCESS read-only
    STATUS     current
    DESCRIPTION
        "Service name of the network adapter. This name is
        usually shorter than the full product name.
        Example: 'Elnkii'"
    ::= { win32NetworkAdapterEntry 32 }

hwnaSpeed OBJECT-TYPE
    SYNTAX     Gauge32
    MAX-ACCESS read-only
    STATUS     current
    DESCRIPTION
        "Estimate of the current bandwidth in bits per
        second. For endpoints which vary in bandwidth or
        for those where no accurate estimation can be made,
        this property should contain the nominal bandwidth.
        This property is inherited from
        CIM_NetworkAdapter."
    ::= { win32NetworkAdapterEntry 33 }

hwnaStatus OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32NetworkAdapterEntry 34 }

hwnaStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32NetworkAdapterEntry 35 }

hwnaSystemCreationClassName OBJECT-TYPE
    SYNTAX     DisplayString
    MAX-ACCESS read-only
    STATUS     current
    DESCRIPTION
        "Value of the scoping computer's CreationClassName
        property. This property is inherited from
        CIM_LogicalDevice."
    ::= { win32NetworkAdapterEntry 36 }

hwnaSystemName OBJECT-TYPE
    SYNTAX     DisplayString
    MAX-ACCESS read-only
    STATUS     current
    DESCRIPTION
        "Name of the scoping system. This property is
        inherited from CIM_LogicalDevice."
    ::= { win32NetworkAdapterEntry 37 }

hwnaTimeOfLastReset OBJECT-TYPE
    SYNTAX     DateAndTime
    MAX-ACCESS read-only
    STATUS     current
    DESCRIPTION
        "Date and time the network adapter was last reset."
    ::= { win32NetworkAdapterEntry 38 }

win32NetworkAdapterConfigTable OBJECT-TYPE
    SYNTAX     SEQUENCE OF Win32NetworkAdapterConfigEntry
    MAX-ACCESS not-accessible
    STATUS     current
    DESCRIPTION
        "The Win32_NetworkAdapterConfiguration WMI class
        represents the attributes and behaviors of a
        network adapter. This class includes extra
        properties and methods that support the management
        of the TCP/IP and Internetworking Packet Exchange
        (IPX) protocols that are independent from the
        network adapter."
    ::= { wmiNetworkingDevice 2 }

win32NetworkAdapterConfigEntry OBJECT-TYPE
    SYNTAX     Win32NetworkAdapterConfigEntry
    MAX-ACCESS not-accessible
    STATUS     current
    DESCRIPTION
        "None"
    INDEX      { hwnacIndex }
    ::= { win32NetworkAdapterConfigTable 1 }

Win32NetworkAdapterConfigEntry ::= SEQUENCE {
    hwnacIndex Integer32,
    hwnacArpAlwaysSourceRoute TruthValue,
    hwnacArpUseEtherSNAP TruthValue,
    hwnacCaption DisplayString,
    hwnacDatabasePath DisplayString,
    hwnacDeadGWDetectEnabled TruthValue,
    hwnacDefaultIPGateway DisplayString,
    hwnacDefaultTOS Integer32,
    hwnacDefaultTTL Integer32,
    hwnacDescription DisplayString,
    hwnacDHCPEnabled TruthValue,
    hwnacDHCPLeaseExpires DateAndTime,
    hwnacDHCPLeaseObtained DateAndTime,
    hwnacDHCPServer DisplayString,
    hwnacDNSDomain DisplayString,
    hwnacDNSDomainSuffixSearchOrder DisplayString,
    hwnacDNSEnabledForWINSResolution TruthValue,
    hwnacDNSHostName DisplayString,
    hwnacDNSServerSearchOrder DisplayString,
    hwnacDomainDNSRegistrationEnable TruthValue,
    hwnacForwardBufferMemory Gauge32,
    hwnacFullDNSRegistrationEnabled TruthValue,
    hwnacGatewayCostMetric DisplayString,
    hwnacIGMPLevel INTEGER,
    hwnacConfigurationIndex Gauge32,
    hwnacInterfaceIndex Gauge32,
    hwnacIPAddress DisplayString,
    hwnacIPConnectionMetric Gauge32,
    hwnacIPEnabled TruthValue,
    hwnacIPFilterSecurityEnabled TruthValue,
    hwnacIPPortSecurityEnabled TruthValue,
    hwnacIPSecPermitIPProtocols DisplayString,
    hwnacIPSecPermitTCPPorts DisplayString,
    hwnacIPSecPermitUDPPorts DisplayString,
    hwnacIPSubnet DisplayString,
    hwnacIPUseZeroBroadcast TruthValue,
    hwnacIPXAddress DisplayString,
    hwnacIPXEnabled TruthValue,
    hwnacIPXFrameType DisplayString,
    hwnacIPXMediaType INTEGER,
    hwnacIPXNetworkNumber DisplayString,
    hwnacIPXVirtualNetNumber DisplayString,
    hwnacKeepAliveInterval Gauge32,
    hwnacKeepAliveTime Gauge32,
    hwnacMACAddress DisplayString,
    hwnacMTU Gauge32,
    hwnacNumForwardPackets Gauge32,
    hwnacPMTUBHDetectEnabled TruthValue,
    hwnacPMTUDiscoveryEnabled TruthValue,
    hwnacServiceName DisplayString,
    hwnacSettingID DisplayString,
    hwnacTcpipNetbiosOptions INTEGER,
    hwnacTcpMaxConnectRetransmission Gauge32,
    hwnacTcpMaxDataRetransmissions Gauge32,
    hwnacTcpNumConnections Gauge32,
    hwnacTcpUseRFC1122UrgentPointer TruthValue,
    hwnacTcpWindowSize Integer32,
    hwnacWINSEnableLMHostsLookup TruthValue,
    hwnacWINSHostLookupFile DisplayString,
    hwnacWINSPrimaryServer DisplayString,
    hwnacWINSScopeID DisplayString,
    hwnacWINSSecondaryServer DisplayString
}

hwnacIndex OBJECT-TYPE
    SYNTAX     Integer32 (1..2147483647)
    MAX-ACCESS read-only
    STATUS     current
    DESCRIPTION
        "The value of this object uniquely identifies the
        instance entry for this class."
    ::= { win32NetworkAdapterConfigEntry 1 }

hwnacArpAlwaysSourceRoute OBJECT-TYPE
    SYNTAX     TruthValue
    MAX-ACCESS read-only
    STATUS     current
    DESCRIPTION
        "If TRUE, TCP/IP transmits Address Resolution
        Protocol (ARP) queries with source routing enabled
        on Token Ring networks. By default (FALSE), ARP
        first queries without source routing, and then
        retries with source routing enabled if no reply is
        received. Source routing allows the routing of
        network packets across different types of
        networks."
    ::= { win32NetworkAdapterConfigEntry 2 }

hwnacArpUseEtherSNAP OBJECT-TYPE
    SYNTAX     TruthValue
    MAX-ACCESS read-only
    STATUS     current
    DESCRIPTION
        "If TRUE, Ethernet packets follow the IEEE 802.3
        Sub-Network Access Protocol (SNAP) encoding.
        Setting this parameter to 1 forces TCP/IP to
        transmit Ethernet packets by using 802.3 SNAP
        encoding. By default (FALSE), the stack transmits
        packets in DIX Ethernet format. Windows NT/Windows
        2000 systems can receive both formats."
    ::= { win32NetworkAdapterConfigEntry 3 }

hwnacCaption OBJECT-TYPE
    SYNTAX     DisplayString
    MAX-ACCESS read-only
    STATUS     current
    DESCRIPTION
        "Description of the CIM_Setting object a one-line
        string. This property is inherited from
        CIM_Setting."
    ::= { win32NetworkAdapterConfigEntry 4 }

hwnacDatabasePath OBJECT-TYPE
    SYNTAX     DisplayString
    MAX-ACCESS read-only
    STATUS     current
    DESCRIPTION
        "Valid Windows file path to standard Internet
        database files (HOSTS, LMHOSTS, NETWORKS,
        PROTOCOLS). The file path is used by the Windows
        Sockets interface. This property is only available
        on Windows NT/Windows 2000 systems."
    ::= { win32NetworkAdapterConfigEntry 5 }

hwnacDeadGWDetectEnabled OBJECT-TYPE
    SYNTAX     TruthValue
    MAX-ACCESS read-only
    STATUS     current
    DESCRIPTION
        "If TRUE, dead gateway detection occurs. With this
        feature enabled, Transmission Control Protocol
        (TCP) asks Internet Protocol (IP) to change to a
        backup gateway if it re-transmits a segment several
        times without receiving a response."
    ::= { win32NetworkAdapterConfigEntry 6 }

hwnacDefaultIPGateway OBJECT-TYPE
    SYNTAX     DisplayString
    MAX-ACCESS read-only
    STATUS     current
    DESCRIPTION
        "Array of IP addresses of default gateways that the
        computer system uses.
        Example: '192.168.12.1 192.168.46.1'"
    ::= { win32NetworkAdapterConfigEntry 7 }

hwnacDefaultTOS OBJECT-TYPE
    SYNTAX     Integer32 (0..255)
    MAX-ACCESS read-only
    STATUS     current
    DESCRIPTION
        "Default Type Of Service (TOS) value set in the
        header of outgoing IP packets. Request for Comments
        (RFC) 791 defines the values. Default: 0, Valid
        Range: 0 - 255."
    ::= { win32NetworkAdapterConfigEntry 8 }

hwnacDefaultTTL OBJECT-TYPE
    SYNTAX     Integer32 (0..255)
    MAX-ACCESS read-only
    STATUS     current
    DESCRIPTION
        "Default Time To Live (TTL) value set in the header
        of outgoing IP packets. The TTL specifies the
        number of routers an IP packet can pass through to
        reach its destination before being discarded. Each
        router decrements by one the TTL count of a packet
        as it passes through and discards the packets if
        the TTL is 0 (zero). Default: 32, Valid Range: 1 -
        255."
    ::= { win32NetworkAdapterConfigEntry 9 }

hwnacDescription OBJECT-TYPE
    SYNTAX     DisplayString
    MAX-ACCESS read-only
    STATUS     current
    DESCRIPTION
        "Description of the CIM_Setting object. This
        property is inherited from CIM_Setting."
    ::= { win32NetworkAdapterConfigEntry 10 }

hwnacDHCPEnabled OBJECT-TYPE
    SYNTAX     TruthValue
    MAX-ACCESS read-only
    STATUS     current
    DESCRIPTION
        "If TRUE, the dynamic host configuration protocol
        (DHCP) server automatically assigns an IP address
        to the computer system when establishing a network
        connection."
    ::= { win32NetworkAdapterConfigEntry 11 }

hwnacDHCPLeaseExpires OBJECT-TYPE
    SYNTAX     DateAndTime
    MAX-ACCESS read-only
    STATUS     current
    DESCRIPTION
        "Expiration date and time for a leased IP address
        that was assigned to the computer by the dynamic
        host configuration protocol (DHCP) server.
        Example: 20521201000230.000000000"
    ::= { win32NetworkAdapterConfigEntry 12 }

hwnacDHCPLeaseObtained OBJECT-TYPE
    SYNTAX     DateAndTime
    MAX-ACCESS read-only
    STATUS     current
    DESCRIPTION
        "Date and time the lease was obtained for the IP
        address assigned to the computer by the dynamic
        host configuration protocol (DHCP) server.
        Example: 19521201000230.000000000"
    ::= { win32NetworkAdapterConfigEntry 13 }

hwnacDHCPServer OBJECT-TYPE
    SYNTAX     DisplayString
    MAX-ACCESS read-only
    STATUS     current
    DESCRIPTION
        "IP address of the dynamic host configuration
        protocol (DHCP) server.
        Example: '10.55.34'"
    ::= { win32NetworkAdapterConfigEntry 14 }

hwnacDNSDomain OBJECT-TYPE
    SYNTAX     DisplayString
    MAX-ACCESS read-only
    STATUS     current
    DESCRIPTION
        "Organization name followed by a period and an
        extension that indicates the type of organization,
        such as microsoft.com. The name can be any
        combination of the letters A through Z, the
        numerals 0 through 9, and the hyphen (-), plus the
        period (.) character used as a separator.
        Example: 'microsoft.com'"
    ::= { win32NetworkAdapterConfigEntry 15 }

hwnacDNSDomainSuffixSearchOrder OBJECT-TYPE
    SYNTAX     DisplayString
    MAX-ACCESS read-only
    STATUS     current
    DESCRIPTION
        "Array of DNS domain suffixes to be appended to the
        end of host names during name resolution. When
        attempting to resolve a fully-qualified domain name
        (FQDN) from a host only name, the system will first
        append the local domain name. If this is not
        successful, the system will use the domain suffix
        list to create additional FQDNs in the order listed
        and query DNS servers for each
        Example: 'samples.microsoft.com
        example.microsoft.com'"
    ::= { win32NetworkAdapterConfigEntry 16 }

hwnacDNSEnabledForWINSResolution OBJECT-TYPE
    SYNTAX     TruthValue
    MAX-ACCESS read-only
    STATUS     current
    DESCRIPTION
        "If TRUE, the Domain Name System (DNS) is enabled
        for name resolution over Windows Internet Naming
        Service (WINS) resolution. If the name cannot be
        resolved using DNS, the name request is forwarded
        to WINS for resolution."
    ::= { win32NetworkAdapterConfigEntry 17 }

hwnacDNSHostName OBJECT-TYPE
    SYNTAX     DisplayString
    MAX-ACCESS read-only
    STATUS     current
    DESCRIPTION
        "Host name used to identify the local computer for
        authentication by some utilities. Other
        TCP/IP-based utilities can use this value to
        acquire the name of the local computer. Host names
        are stored on DNS servers in a table that maps
        names to IP addresses for use by DNS. The name can
        be any combination of the letters A through Z, the
        numerals 0 through 9, and the hyphen (-), plus the
        period (.) character used as a separator. By
        default, this value is the Microsoft networking
        computer name, but the network administrator can
        assign another host name without affecting the
        computer name.
        Example: 'corpdns'"
    ::= { win32NetworkAdapterConfigEntry 18 }

hwnacDNSServerSearchOrder OBJECT-TYPE
    SYNTAX     DisplayString
    MAX-ACCESS read-only
    STATUS     current
    DESCRIPTION
        "Array of server IP addresses to be used in
        querying for DNS servers."
    ::= { win32NetworkAdapterConfigEntry 19 }

hwnacDomainDNSRegistrationEnable OBJECT-TYPE
    SYNTAX     TruthValue
    MAX-ACCESS read-only
    STATUS     current
    DESCRIPTION
        "If TRUE, the IP addresses for this connection are
        registered in DNS under the domain name of this
        connection in addition to being registered under
        the computer's full DNS name. The domain name of
        this connection is either set using the
        SetDNSDomain() method or assigned by DSCP. The
        registered name is the host name of the computer
        with the domain name appended. This property is new
        for Windows XP."
    ::= { win32NetworkAdapterConfigEntry 20 }

hwnacForwardBufferMemory OBJECT-TYPE
    SYNTAX     Gauge32
    UNITS "Bytes"
    MAX-ACCESS read-only
    STATUS     current
    DESCRIPTION
        "Memory allocated by IP to store packet data in the
        router packet queue. When this buffer space is
        filled, the router begins discarding packets at
        random from its queue. Packet queue data buffers
        are 256 bytes in length, so the value of this
        parameter should be a multiple of 256. Multiple
        buffers are chained together for larger packets.
        The IP header for a packet is stored separately.
        This parameter is ignored and no buffers are
        allocated if the IP router is not enabled. The
        buffer size can range from the network MTU to the a
        value smaller than 0xFFFFFFFF. Default: 74240
        (fifty 1480-byte packets, rounded to a multiple of
        256)."
    ::= { win32NetworkAdapterConfigEntry 21 }

hwnacFullDNSRegistrationEnabled OBJECT-TYPE
    SYNTAX     TruthValue
    MAX-ACCESS read-only
    STATUS     current
    DESCRIPTION
        "If TRUE, the IP addresses for this connection are
        registered in DNS under the computer's full DNS
        name. The full DNS name of the computer is
        displayed on the Network Identification tab in the
        System application in Control Panel. This property
        is new for Windows XP."
    ::= { win32NetworkAdapterConfigEntry 22 }

hwnacGatewayCostMetric OBJECT-TYPE
    SYNTAX     DisplayString
    MAX-ACCESS read-only
    STATUS     current
    DESCRIPTION
        "Array of integer cost metric values (ranging from
        1 to 9999) to be used in calculating the fastest,
        most reliable, or least expensive routes. This
        argument has a one-to-one correspondence with the
        DefaultIPGateway property. Windows 2000 only."
    ::= { win32NetworkAdapterConfigEntry 23 }

hwnacIGMPLevel OBJECT-TYPE
    SYNTAX     INTEGER {
        noMulticast(0),
        ipMulticast(1),
        ipIGMPMulticast(2)
    }
    MAX-ACCESS read-only
    STATUS     current
    DESCRIPTION
        "Extent to which the system supports IP multicast
        and participates in the Internet Group Management
        Protocol. At level 0 (zero), the system provides no
        multicast support. At level 1, the system may only
        send IP multicast packets. At level 2, the system
        may send IP multicast packets and fully participate
        in IGMP to receive multicast packets."
    ::= { win32NetworkAdapterConfigEntry 24 }

hwnacConfigurationIndex OBJECT-TYPE
    SYNTAX     Gauge32
    MAX-ACCESS read-only
    STATUS     current
    DESCRIPTION
        "Index number of the Windows network adapter
        configuration. The index number is used when there
        is more than one configuration available."
    ::= { win32NetworkAdapterConfigEntry 25 }

hwnacInterfaceIndex OBJECT-TYPE
    SYNTAX     Gauge32
    MAX-ACCESS read-only
    STATUS     current
    DESCRIPTION
        "Index value that uniquely identifies a local
        network interface. The value in this property is
        the same as the value in the InterfaceIndex
        property in the instance of Win32_IP4RouteTable
        that represents the network interface in the route
        table.
        Windows XP and earlier:  The InterfaceIndex
        property is not available."
    ::= { win32NetworkAdapterConfigEntry 26 }

hwnacIPAddress OBJECT-TYPE
    SYNTAX     DisplayString
    MAX-ACCESS read-only
    STATUS     current
    DESCRIPTION
        "Array of all of the IP addresses associated with
        the current network adapter.
        Example: '172.16.22.0'"
    ::= { win32NetworkAdapterConfigEntry 27 }

hwnacIPConnectionMetric OBJECT-TYPE
    SYNTAX     Gauge32
    MAX-ACCESS read-only
    STATUS     current
    DESCRIPTION
        "Cost of using the configured routes for the IP
        bound adapter and is the weighted value for those
        routes in the IP routing table. If there are
        multiple routes to a destination in the IP routing
        table, the route with the lowest metric is used.
        The default value is 1. This property is new for
        Windows XP."
    ::= { win32NetworkAdapterConfigEntry 28 }

hwnacIPEnabled OBJECT-TYPE
    SYNTAX     TruthValue
    MAX-ACCESS read-only
    STATUS     current
    DESCRIPTION
        "If TRUE, TCP/IP is bound and enabled on this
        network adapter."
    ::= { win32NetworkAdapterConfigEntry 29 }

hwnacIPFilterSecurityEnabled OBJECT-TYPE
    SYNTAX     TruthValue
    MAX-ACCESS read-only
    STATUS     current
    DESCRIPTION
        "If TRUE, IP port security is enabled globally
        across all IP-bound network adapters and the
        security values associated with individual network
        adapters are in effect. This property is used in
        conjunction with IPSecPermitTCPPorts,
        IPSecPermitUDPPorts, and IPSecPermitIPProtocols. If
        FALSE, IP filter security is disabled across all
        network adapters and allows all port and protocol
        traffic to flow unfiltered."
    ::= { win32NetworkAdapterConfigEntry 30 }

hwnacIPPortSecurityEnabled OBJECT-TYPE
    SYNTAX     TruthValue
    MAX-ACCESS read-only
    STATUS     current
    DESCRIPTION
        "If TRUE, IP port security is enabled globally
        across all IP-bound network adapters. This property
        is obsolete. In place of this property, you should
        use IPFilterSecurityEnabled."
    ::= { win32NetworkAdapterConfigEntry 31 }

hwnacIPSecPermitIPProtocols OBJECT-TYPE
    SYNTAX     DisplayString
    MAX-ACCESS read-only
    STATUS     current
    DESCRIPTION
        "Array of the protocols permitted to run over the
        IP. The list of protocols is defined using the
        EnableIPSec method. The list will either be empty
        or contain numeric values. A numeric value of 0
        (zero) indicates access permission is granted for
        all protocols. An empty string indicates that no
        protocols are permitted to run when
        IPFilterSecurityEnabled is TRUE."
    ::= { win32NetworkAdapterConfigEntry 32 }

hwnacIPSecPermitTCPPorts OBJECT-TYPE
    SYNTAX     DisplayString
    MAX-ACCESS read-only
    STATUS     current
    DESCRIPTION
        "Array of the ports that will be granted access
        permission for TCP. The list of protocols is
        defined using the EnableIPSec method. The list will
        either be empty or contain numeric values. A
        numeric value of 0 (zero)indicates access
        permission is granted for all ports. An empty
        string indicates that no ports are granted access
        permission when IPFilterSecurityEnabled is TRUE."
    ::= { win32NetworkAdapterConfigEntry 33 }

hwnacIPSecPermitUDPPorts OBJECT-TYPE
    SYNTAX     DisplayString
    MAX-ACCESS read-only
    STATUS     current
    DESCRIPTION
        "Array of the ports that will be granted User
        Datagram Protocol (UDP) access permission. The list
        of protocols is defined using the EnableIPSec
        method. The list will either be empty or contain
        numeric values. A numeric value of 0 (zero)
        indicates access permission is granted for all
        ports. An empty string indicates that no ports are
        granted access permission when
        IPFilterSecurityEnabled is TRUE."
    ::= { win32NetworkAdapterConfigEntry 34 }

hwnacIPSubnet OBJECT-TYPE
    SYNTAX     DisplayString
    MAX-ACCESS read-only
    STATUS     current
    DESCRIPTION
        "Array of all the subnet masks associated with the
        current network adapter.
        Example: '255.255.0'"
    ::= { win32NetworkAdapterConfigEntry 35 }

hwnacIPUseZeroBroadcast OBJECT-TYPE
    SYNTAX     TruthValue
    MAX-ACCESS read-only
    STATUS     current
    DESCRIPTION
        "If TRUE, IP zeros-broadcasts are used (0.0.0.0),
        and the system uses ones-broadcasts
        (255.255.255.255). Computer systems generally use
        ones-broadcasts, but those derived from BSD
        implementations use zeros-broadcasts. Systems that
        do not use that same broadcasts will not
        interoperate on the same network. The default is
        FALSE."
    ::= { win32NetworkAdapterConfigEntry 36 }

hwnacIPXAddress OBJECT-TYPE
    SYNTAX     DisplayString
    MAX-ACCESS read-only
    STATUS     current
    DESCRIPTION
        "Internetworking Packet Exchange (IPX) address of
        the network adapter. The IPX address identifies a
        computer system on a network using the IPX
        protocol."
    ::= { win32NetworkAdapterConfigEntry 37 }

hwnacIPXEnabled OBJECT-TYPE
    SYNTAX     TruthValue
    MAX-ACCESS read-only
    STATUS     current
    DESCRIPTION
        "If TRUE, the or Internetwork Packet Exchange (IPX)
        protocol is bound and enabled for this adapter."
    ::= { win32NetworkAdapterConfigEntry 38 }

hwnacIPXFrameType OBJECT-TYPE
    SYNTAX     DisplayString
    MAX-ACCESS read-only
    STATUS     current
    DESCRIPTION
        "Array of frame type identifiers. The values in
        this array correspond to the elements in
        IPXNetworkNumber.
        Value Meaning 
        0 Ethernet II 
        1 Ethernet 802.3 
        2 Ethernet 802.2 
        3 Ethernet SNAP 
        255 AUTO "
    ::= { win32NetworkAdapterConfigEntry 39 }

hwnacIPXMediaType OBJECT-TYPE
    SYNTAX     INTEGER {
        ethernet(1),
        tokenRing(2),
        fddi(3),
        arcnet(8)
    }
    MAX-ACCESS read-only
    STATUS     current
    DESCRIPTION
        "Internetworking Packet Exchange (IPX) media type
        identifier."
    ::= { win32NetworkAdapterConfigEntry 40 }

hwnacIPXNetworkNumber OBJECT-TYPE
    SYNTAX     DisplayString
    MAX-ACCESS read-only
    STATUS     current
    DESCRIPTION
        "Array of characters that uniquely identifies a
        frame/network adapter combination on the computer
        system. The NetWare Link (NWLink)
        IPX/SPX-compatible transport in Windows 2000 and
        Windows NT 4.0 and later use two distinctly
        different types of network numbers. This number is
        sometimes referred to as the external network
        number. It must be unique for each network segment.
        The order in this string list will correspond
        item-for-item with the elements in the IPXFrameType
        property."
    ::= { win32NetworkAdapterConfigEntry 41 }

hwnacIPXVirtualNetNumber OBJECT-TYPE
    SYNTAX     DisplayString
    MAX-ACCESS read-only
    STATUS     current
    DESCRIPTION
        "Unique identifier of the computer system on the
        network. It is represented in the form of an
        eight-character hexadecimal digit. Windows
        NT/Windows 2000 uses the virtual network number
        (also known as an internal network number) for
        internal routing."
    ::= { win32NetworkAdapterConfigEntry 42 }

hwnacKeepAliveInterval OBJECT-TYPE
    SYNTAX     Gauge32
    UNITS "Milliseconds"
    MAX-ACCESS read-only
    STATUS     current
    DESCRIPTION
        "Interval separating Keep Alive Retransmissions
        until a response is received. After a response is
        received, the delay until the next Keep Alive
        Transmission is again controlled by the value of
        KeepAliveTime. The connection will be aborted after
        the number of retransmissions specified by
        TcpMaxDataRetransmissions have gone unanswered.
        Default: 1000, Valid Range: 1 - 0xFFFFFFFF."
    ::= { win32NetworkAdapterConfigEntry 43 }

hwnacKeepAliveTime OBJECT-TYPE
    SYNTAX     Gauge32
    UNITS "Milliseconds"
    MAX-ACCESS read-only
    STATUS     current
    DESCRIPTION
        "The KeepAliveTime property indicates how often the
        TCP attempts to verify that an idle connection is
        still intact by sending a Keep Alive Packet. A
        remote system that is reachable will acknowledge
        the keep alive transmission. Keep Alive packets are
        not sent by default. This feature may be enabled in
        a connection by an application. Default: 7,200,000
        (two hours)"
    ::= { win32NetworkAdapterConfigEntry 44 }

hwnacMACAddress OBJECT-TYPE
    SYNTAX     DisplayString
    MAX-ACCESS read-only
    STATUS     current
    DESCRIPTION
        "Media Access Control (MAC) address of the network
        adapter. A MAC address is assigned by the
        manufacturer to uniquely identify the network
        adapter.
        Example: '00:80:C7:8F:6C:96'"
    ::= { win32NetworkAdapterConfigEntry 45 }

hwnacMTU OBJECT-TYPE
    SYNTAX     Gauge32
    UNITS "Bytes"
    MAX-ACCESS read-only
    STATUS     current
    DESCRIPTION
        "Overrides the default Maximum Transmission Unit
        (MTU) for a network interface. The MTU is the
        maximum packet size (including the transport
        header) that the transport will transmit over the
        underlying network. The IP datagram can span
        multiple packets. The range of this value spans the
        minimum packet size (68) to the MTU supported by
        the underlying network."
    ::= { win32NetworkAdapterConfigEntry 46 }

hwnacNumForwardPackets OBJECT-TYPE
    SYNTAX     Gauge32
    MAX-ACCESS read-only
    STATUS     current
    DESCRIPTION
        "Number of IP packet headers allocated for the
        router packet queue. When all headers are in use,
        the router will begin to discard packets from the
        queue at random. This value should be at least as
        large as the ForwardBufferMemory value divided by
        the maximum IP data size of the networks connected
        to the router. It should be no larger than the
        ForwardBufferMemory value divided by 256, since at
        least 256 bytes of forward buffer memory are used
        for each packet. The optimal number of forward
        packets for a given ForwardBufferMemory size
        depends on the type of traffic on the network. It
        will be somewhere between these two values. If the
        router is not enabled, this parameter is ignored
        and no headers are allocated. Default: 50, Valid
        Range: 1 - 0xFFFFFFFE"
    ::= { win32NetworkAdapterConfigEntry 47 }

hwnacPMTUBHDetectEnabled OBJECT-TYPE
    SYNTAX     TruthValue
    MAX-ACCESS read-only
    STATUS     current
    DESCRIPTION
        "If TRUE, detection of black hole routers occurs
        while TCP discovers the path of the Maximum
        Transmission Unit. A black hole router does not
        return ICMP Destination Unreachable messages when
        it needs to fragment an IP datagram with the Don't
        Fragment bit set. TCP depends on receiving these
        messages to perform Path MTU Discovery. With this
        feature enabled, TCP will try to send segments
        without the Don't Fragment bit set if several
        retransmissions of a segment go unacknowledged. If
        the segment is acknowledged as a result, the MSS
        will be decreased and the Don't Fragment bit will
        be set in future packets on the connection.
        Enabling black hole detection increases the maximum
        number of retransmissions performed for a given
        segment. The default value of this property is
        FALSE."
    ::= { win32NetworkAdapterConfigEntry 48 }

hwnacPMTUDiscoveryEnabled OBJECT-TYPE
    SYNTAX     TruthValue
    MAX-ACCESS read-only
    STATUS     current
    DESCRIPTION
        "If TRUE, the Maximum Transmission Unit (MTU) path
        is discovered over the path to a remote host. By
        discovering the MTU path and limiting TCP segments
        to this size, TCP can eliminate fragmentation at
        routers along the path that connect networks with
        different MTUs. Fragmentation adversely affects TCP
        throughput and network congestion. Setting this
        parameter to FALSE causes an MTU of 576 bytes to be
        used for all connections that are not to machines
        on the local subnet. The default is TRUE."
    ::= { win32NetworkAdapterConfigEntry 49 }

hwnacServiceName OBJECT-TYPE
    SYNTAX     DisplayString
    MAX-ACCESS read-only
    STATUS     current
    DESCRIPTION
        "Service name of the network adapter. This name is
        usually shorter than the full product name.
        Example: 'Elnkii'"
    ::= { win32NetworkAdapterConfigEntry 50 }

hwnacSettingID OBJECT-TYPE
    SYNTAX     DisplayString
    MAX-ACCESS read-only
    STATUS     current
    DESCRIPTION
        "Identifier by which the CIM_Setting object is
        known. This property is inherited from
        CIM_Setting."
    ::= { win32NetworkAdapterConfigEntry 51 }

hwnacTcpipNetbiosOptions OBJECT-TYPE
    SYNTAX     INTEGER {
        n0x0EnableNetbiosViaDhcp(0),
        n0x1EnableNetbios(1),
        n0x2DisableNetbios(2)
    }
    MAX-ACCESS read-only
    STATUS     current
    DESCRIPTION
        "Bitmap of the possible settings related to
        NetBIOSover TCP/IP. This property is new for
        Windows XP."
    ::= { win32NetworkAdapterConfigEntry 52 }

hwnacTcpMaxConnectRetransmission OBJECT-TYPE
    SYNTAX     Gauge32
    MAX-ACCESS read-only
    STATUS     current
    DESCRIPTION
        "Number of times TCP attempts to retransmit a
        Connect Request before terminating the connection.
        The initial retransmission timeout is 3 seconds.
        The retransmission timeout doubles for each
        attempt. Default: 3, Valid Range: 0 - 0xFFFFFFFF."
    ::= { win32NetworkAdapterConfigEntry 53 }

hwnacTcpMaxDataRetransmissions OBJECT-TYPE
    SYNTAX     Gauge32
    MAX-ACCESS read-only
    STATUS     current
    DESCRIPTION
        "Number of times TCP re-transmits an individual
        data segment (non-connect segment) before
        terminating the connection. The retransmission
        time-out doubles with each successive
        retransmission on a connection. Default: 5, Valid
        Range: 0 - 0xFFFFFFFF."
    ::= { win32NetworkAdapterConfigEntry 54 }

hwnacTcpNumConnections OBJECT-TYPE
    SYNTAX     Gauge32
    MAX-ACCESS read-only
    STATUS     current
    DESCRIPTION
        "Maximum number of connections that TCP can have
        open simultaneously. Default: 0xFFFFFE, Valid
        Range: 0 - 0xFFFFFE."
    ::= { win32NetworkAdapterConfigEntry 55 }

hwnacTcpUseRFC1122UrgentPointer OBJECT-TYPE
    SYNTAX     TruthValue
    MAX-ACCESS read-only
    STATUS     current
    DESCRIPTION
        "If TRUE, TCP uses the RFC 1122 specification for
        urgent data. If FALSE (default), TCP uses the mode
        used by Berkeley Software Design (BSD) derived
        systems. The two mechanisms interpret the urgent
        pointer differently and are not interoperable.
        Windows 2000 and Windows NT version 3.51 and later
        default to BSD mode."
    ::= { win32NetworkAdapterConfigEntry 56 }

hwnacTcpWindowSize OBJECT-TYPE
    SYNTAX     Integer32
    UNITS "Bytes"
    MAX-ACCESS read-only
    STATUS     current
    DESCRIPTION
        "Maximum TCP Receive Window size offered by the
        system. The Receive Window specifies the number of
        bytes a sender may transmit without receiving an
        acknowledgment. In general, larger receiving
        windows will improve performance over high delay
        and high bandwidth networks. For efficiency, the
        receiving window should be an even multiple of the
        TCP Maximum Segment Size (MSS). Default: Four times
        the maximum TCP data size or an even multiple of
        TCP data size rounded up to the nearest multiple of
        8192. Ethernet networks default to 8760. Valid
        range: 0 - 65535."
    ::= { win32NetworkAdapterConfigEntry 57 }

hwnacWINSEnableLMHostsLookup OBJECT-TYPE
    SYNTAX     TruthValue
    MAX-ACCESS read-only
    STATUS     current
    DESCRIPTION
        "If TRUE, local lookup files are used. Lookup files
        will contain a map of IP addresses to host names.
        If they exist on the local system, they will be
        found in %SystemRoot%\system32\drivers\etc."
    ::= { win32NetworkAdapterConfigEntry 58 }

hwnacWINSHostLookupFile OBJECT-TYPE
    SYNTAX     DisplayString
    MAX-ACCESS read-only
    STATUS     current
    DESCRIPTION
        "Path to a WINS lookup file on the local system.
        This file will contain a map of IP addresses to
        host names. If the file specified in this property
        is found, it will be copied to the
        %SystemRoot%\system32\drivers\etc folder of the
        local system. Valid only if the
        WINSEnableLMHostsLookup property is TRUE."
    ::= { win32NetworkAdapterConfigEntry 59 }

hwnacWINSPrimaryServer OBJECT-TYPE
    SYNTAX     DisplayString
    MAX-ACCESS read-only
    STATUS     current
    DESCRIPTION
        "IP address for the primary WINS server."
    ::= { win32NetworkAdapterConfigEntry 60 }

hwnacWINSScopeID OBJECT-TYPE
    SYNTAX     DisplayString
    MAX-ACCESS read-only
    STATUS     current
    DESCRIPTION
        "Value appended to the end of the NetBIOS name that
        isolates a group of computer systems communicating
        with only each other. It is used for all NetBIOS
        transactions over TCP/IP communications from that
        computer system. Computers configured with
        identical scope identifiers are able to communicate
        with this computer. TCP/IP clients with different
        scope identifiers disregard packets from computers
        with this scope identifier. Valid only when the
        EnableWINS method executes successfully."
    ::= { win32NetworkAdapterConfigEntry 61 }

hwnacWINSSecondaryServer OBJECT-TYPE
    SYNTAX     DisplayString
    MAX-ACCESS read-only
    STATUS     current
    DESCRIPTION
        "IP address for the secondary WINS server."
    ::= { win32NetworkAdapterConfigEntry 62 }

wmiPower OBJECT-IDENTITY
    STATUS     current
    DESCRIPTION
        "The Power subcategory groups classes that
        represent power supplies, batteries, and events
        related to these devices."
    ::= { wmiHardware 6 }

win32BatteryTable OBJECT-TYPE
    SYNTAX     SEQUENCE OF Win32BatteryEntry
    MAX-ACCESS not-accessible
    STATUS     current
    DESCRIPTION
        "The Win32_Battery WMI class represents a battery
        connected to the computer system. Windows 2000 and
        Windows 98 do not report instances of Win32_Battery
        unless Advanced Power Management (APM) is enabled
        on the system, and a battery is present."
    ::= { wmiPower 1 }

win32BatteryEntry OBJECT-TYPE
    SYNTAX     Win32BatteryEntry
    MAX-ACCESS not-accessible
    STATUS     current
    DESCRIPTION
        "None"
    INDEX      { hwbaIndex }
    ::= { win32BatteryTable 1 }

Win32BatteryEntry ::= SEQUENCE {
    hwbaIndex Integer32,
    hwbaAvailability INTEGER,
    hwbaBatteryRechargeTime Gauge32,
    hwbaBatteryStatus INTEGER,
    hwbaCaption DisplayString,
    hwbaChemistry INTEGER,
    hwbaConfigManagerErrorCode INTEGER,
    hwbaConfigManagerUserConfig TruthValue,
    hwbaCreationClassName DisplayString,
    hwbaDescription DisplayString,
    hwbaDesignCapacity Gauge32,
    hwbaDesignVoltage Gauge32,
    hwbaDeviceID DisplayString,
    hwbaErrorCleared TruthValue,
    hwbaErrorDescription DisplayString,
    hwbaEstimatedChargeRemaining Integer32,
    hwbaEstimatedRunTime Gauge32,
    hwbaExpectedBatteryLife Gauge32,
    hwbaExpectedLife Gauge32,
    hwbaFullChargeCapacity Gauge32,
    hwbaInstallDate DateAndTime,
    hwbaLastErrorCode Gauge32,
    hwbaMaxRechargeTime Gauge32,
    hwbaName DisplayString,
    hwbaPNPDeviceID DisplayString,
    hwbaPowerManagementCapabilities DisplayString,
    hwbaPowerManagementSupported TruthValue,
    hwbaSmartBatteryVersion DisplayString,
    hwbaStatus INTEGER,
    hwbaStatusInfo INTEGER,
    hwbaSystemCreationClassName DisplayString,
    hwbaSystemName DisplayString,
    hwbaTimeOnBattery Gauge32,
    hwbaTimeToFullCharge Gauge32
}

hwbaIndex OBJECT-TYPE
    SYNTAX     Integer32 (1..2147483647)
    MAX-ACCESS read-only
    STATUS     current
    DESCRIPTION
        "The value of this object uniquely identifies the
        instance entry for this class."
    ::= { win32BatteryEntry 1 }

hwbaAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32BatteryEntry 2 }

hwbaBatteryRechargeTime OBJECT-TYPE
    SYNTAX     Gauge32
    UNITS "Minutes"
    MAX-ACCESS read-only
    STATUS     current
    DESCRIPTION
        "Time required to fully charge the battery. This
        property is not supported. BatteryRechargeTime does
        not have a replacement property, and is now
        considered obsolete."
    ::= { win32BatteryEntry 3 }

hwbaBatteryStatus OBJECT-TYPE
    SYNTAX     INTEGER {
        other(1),
        unknown(2),
        fullyCharged(3),
        low(4),
        critical(5),
        charging(6),
        chargingAndHigh(7),
        chargingAndLow(8),
        chargingAndCritical(9),
        undefined(10),
        partiallyCharged(11)
    }
    MAX-ACCESS read-only
    STATUS     current
    DESCRIPTION
        "Status of the battery. The value 10 (Undefined) is
        not valid in the CIM schema because in DMI it
        represents that no battery is installed. In this
        case, the object should not be instantiated. This
        property is inherited from CIM_Battery."
    ::= { win32BatteryEntry 4 }

hwbaCaption OBJECT-TYPE
    SYNTAX     DisplayString
    MAX-ACCESS read-only
    STATUS     current
    DESCRIPTION
        "Short description of the object a one-line string.
        This property is inherited from
        CIM_ManagedSystemElement."
    ::= { win32BatteryEntry 5 }

hwbaChemistry OBJECT-TYPE
    SYNTAX     INTEGER {
        other(1),
        unknown(2),
        leadAcid(3),
        nickelCadmium(4),
        nickelMetalHydride(5),
        lithiumion(6),
        zincAir(7),
        lithiumPolymer(8)
    }
    MAX-ACCESS read-only
    STATUS     current
    DESCRIPTION
        "Enumeration that describes the battery's
        chemistry. This property is inherited from
        CIM_Battery."
    ::= { win32BatteryEntry 6 }

hwbaConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. For more
        information, see the Remarks section of this topic.
        This property is inherited from CIM_LogicalDevice."
    ::= { win32BatteryEntry 7 }

hwbaConfigManagerUserConfig OBJECT-TYPE
    SYNTAX     TruthValue
    MAX-ACCESS read-only
    STATUS     current
    DESCRIPTION
        "If true, the device is using a user-defined
        configuration. This property is inherited from
        CIM_LogicalDevice. "
    ::= { win32BatteryEntry 8 }

hwbaCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice. "
    ::= { win32BatteryEntry 9 }

hwbaDescription OBJECT-TYPE
    SYNTAX     DisplayString
    MAX-ACCESS read-only
    STATUS     current
    DESCRIPTION
        "Description of the object. This property is
        inherited from CIM_ManagedSystemElement. "
    ::= { win32BatteryEntry 10 }

hwbaDesignCapacity OBJECT-TYPE
    SYNTAX     Gauge32
    MAX-ACCESS read-only
    STATUS     current
    DESCRIPTION
        "Design capacity of the battery in milliwatt-hours.
        If the property is not supported, enter 0 (zero).
        This property is inherited from CIM_Battery. "
    ::= { win32BatteryEntry 11 }

hwbaDesignVoltage OBJECT-TYPE
    SYNTAX     Gauge32
    MAX-ACCESS read-only
    STATUS     current
    DESCRIPTION
        "Design voltage of the battery in millivolts. If
        the attribute is not supported, enter 0 (zero).
        This property is inherited from CIM_Battery. "
    ::= { win32BatteryEntry 12 }

hwbaDeviceID OBJECT-TYPE
    SYNTAX     DisplayString
    MAX-ACCESS read-only
    STATUS     current
    DESCRIPTION
        "Identifies the battery. This property is inherited
        from CIM_LogicalDevice.
        Example: 'Internal Battery'"
    ::= { win32BatteryEntry 13 }

hwbaErrorCleared OBJECT-TYPE
    SYNTAX     TruthValue
    MAX-ACCESS read-only
    STATUS     current
    DESCRIPTION
        "If true, the error reported in the LastErrorCode
        property is now cleared. This property is inherited
        from CIM_LogicalDevice."
    ::= { win32BatteryEntry 14 }

hwbaErrorDescription OBJECT-TYPE
    SYNTAX     DisplayString
    MAX-ACCESS read-only
    STATUS     current
    DESCRIPTION
        "Free-form string that supplies more information
        about the error recorded in LastErrorCode property,
        and information about any corrective actions that
        may be taken. This property is inherited from
        CIM_LogicalDevice."
    ::= { win32BatteryEntry 15 }

hwbaEstimatedChargeRemaining OBJECT-TYPE
    SYNTAX     Integer32
    MAX-ACCESS read-only
    STATUS     current
    DESCRIPTION
        "Estimate of the percentage of full charge
        remaining. This property is inherited from
        CIM_Battery."
    ::= { win32BatteryEntry 16 }

hwbaEstimatedRunTime OBJECT-TYPE
    SYNTAX     Gauge32
    MAX-ACCESS read-only
    STATUS     current
    DESCRIPTION
        "Estimate in minutes of the time to battery charge
        depletion under the present load conditions if the
        utility power is off, or lost and remains off, or a
        laptop is disconnected from a power source. This
        property is inherited from CIM_Battery."
    ::= { win32BatteryEntry 17 }

hwbaExpectedBatteryLife OBJECT-TYPE
    SYNTAX     Gauge32
    UNITS "Minutes"
    MAX-ACCESS read-only
    STATUS     current
    DESCRIPTION
        "Amount of time it takes to completely drain the
        battery after it is fully charged. This property is
        no longer used and is considered obsolete."
    ::= { win32BatteryEntry 18 }

hwbaExpectedLife OBJECT-TYPE
    SYNTAX     Gauge32
    MAX-ACCESS read-only
    STATUS     current
    DESCRIPTION
        "Battery's expected lifetime in minutes, assuming
        that the battery is fully charged. The property
        represents the total expected life of the battery,
        not its current remaining life, which is indicated
        by the EstimatedRunTime property. This property is
        inherited from CIM_Battery."
    ::= { win32BatteryEntry 19 }

hwbaFullChargeCapacity OBJECT-TYPE
    SYNTAX     Gauge32
    MAX-ACCESS read-only
    STATUS     current
    DESCRIPTION
        "Full charge capacity of the battery in
        milliwatt-hours. Comparison of the value to the
        DesignCapacity property determines when the battery
        requires replacement. A battery's end of life is
        typically when the FullChargeCapacity property
        falls below 80% of the DesignCapacity property. If
        the property is not supported, enter 0 (zero). This
        property is inherited from CIM_Battery."
    ::= { win32BatteryEntry 20 }

hwbaInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32BatteryEntry 21 }

hwbaLastErrorCode OBJECT-TYPE
    SYNTAX     Gauge32
    MAX-ACCESS read-only
    STATUS     current
    DESCRIPTION
        "Last error code reported by the logical device.
        This property is inherited from CIM_LogicalDevice."
    ::= { win32BatteryEntry 22 }

hwbaMaxRechargeTime OBJECT-TYPE
    SYNTAX     Gauge32
    MAX-ACCESS read-only
    STATUS     current
    DESCRIPTION
        "Maximum time, in minutes, to fully charge the
        battery. The property represents the time to
        recharge a fully depleted battery, not the current
        remaining charge time, which is indicated in the
        TimeToFullCharge property. This property is
        inherited from CIM_Battery."
    ::= { win32BatteryEntry 23 }

hwbaName OBJECT-TYPE
    SYNTAX     DisplayString
    MAX-ACCESS read-only
    STATUS     current
    DESCRIPTION
        "Defines the label by which the object is known.
        When subclassed, the property can be overridden to
        be a key property. This property is inherited from
        CIM_ManagedSystemElement."
    ::= { win32BatteryEntry 24 }

hwbaPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32BatteryEntry 25 }

hwbaPowerManagementCapabilities OBJECT-TYPE
    SYNTAX     DisplayString
    MAX-ACCESS read-only
    STATUS     current
    DESCRIPTION
        "Array of the specific power-related capabilities
        of a logical device. The Enabled value indicates
        that the power management features are currently
        enabled, but the exact feature set is unknown or
        the information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32BatteryEntry 26 }

hwbaPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32BatteryEntry 27 }

hwbaSmartBatteryVersion OBJECT-TYPE
    SYNTAX     DisplayString
    MAX-ACCESS read-only
    STATUS     current
    DESCRIPTION
        "Data Specification version number supported by the
        battery. If the battery does not support this
        function, the value should be left blank. This
        property is inherited from CIM_Battery."
    ::= { win32BatteryEntry 28 }

hwbaStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32BatteryEntry 29 }

hwbaStatusInfo OBJECT-TYPE
    SYNTAX     INTEGER {
        other(1),
        unknown(2),
        enabled(3),
        disabled(4),
        notApplicable(5)
    }
    MAX-ACCESS read-only
    STATUS     current
    DESCRIPTION
        "State of the logical device. If the property does
        not apply to the logical device, the value 5 (Not
        Applicable) should be used. This property is
        inherited from CIM_LogicalDevice."
    ::= { win32BatteryEntry 30 }

hwbaSystemCreationClassName OBJECT-TYPE
    SYNTAX     DisplayString
    MAX-ACCESS read-only
    STATUS     current
    DESCRIPTION
        "Value of the scoping computer's CreationClassName
        property. This property is inherited from
        CIM_LogicalDevice."
    ::= { win32BatteryEntry 31 }

hwbaSystemName OBJECT-TYPE
    SYNTAX     DisplayString
    MAX-ACCESS read-only
    STATUS     current
    DESCRIPTION
        "Name of the scoping system. This property is
        inherited from CIM_LogicalDevice."
    ::= { win32BatteryEntry 32 }

hwbaTimeOnBattery OBJECT-TYPE
    SYNTAX     Gauge32
    MAX-ACCESS read-only
    STATUS     current
    DESCRIPTION
        "Elapsed time in seconds since the computer
        system's UPS last switched to battery power, or the
        time since the system or UPS was last restarted,
        whichever is less. If the battery is 'on line', 0
        (zero) is returned. This property is inherited from
        CIM_Battery."
    ::= { win32BatteryEntry 33 }

hwbaTimeToFullCharge OBJECT-TYPE
    SYNTAX     Gauge32
    MAX-ACCESS read-only
    STATUS     current
    DESCRIPTION
        "Remaining time to charge the battery fully in
        minutes at the current charging rate and usage.
        This property is inherited from CIM_Battery."
    ::= { win32BatteryEntry 34 }

win32CurrentProbeTable OBJECT-TYPE
    SYNTAX     SEQUENCE OF Win32CurrentProbeEntry
    MAX-ACCESS not-accessible
    STATUS     current
    DESCRIPTION
        "The Win32_CurrentProbe WMI class represents the
        properties of a current monitoring sensor
        (ammeter)."
    ::= { wmiPower 2 }

win32CurrentProbeEntry OBJECT-TYPE
    SYNTAX     Win32CurrentProbeEntry
    MAX-ACCESS not-accessible
    STATUS     current
    DESCRIPTION
        "None"
    INDEX      { hwcpIndex }
    ::= { win32CurrentProbeTable 1 }

Win32CurrentProbeEntry ::= SEQUENCE {
    hwcpIndex Integer32,
    hwcpAccuracy Integer32,
    hwcpAvailability INTEGER,
    hwcpCaption DisplayString,
    hwcpConfigManagerErrorCode INTEGER,
    hwcpConfigManagerUserConfig TruthValue,
    hwcpCreationClassName DisplayString,
    hwcpCurrentReading Integer32,
    hwcpDescription DisplayString,
    hwcpDeviceID DisplayString,
    hwcpErrorCleared TruthValue,
    hwcpErrorDescription DisplayString,
    hwcpInstallDate DateAndTime,
    hwcpIsLinear TruthValue,
    hwcpLastErrorCode Gauge32,
    hwcpLowerThresholdCritical Integer32,
    hwcpLowerThresholdFatal Integer32,
    hwcpLowerThresholdNonCritical Integer32,
    hwcpMaxReadable Integer32,
    hwcpMinReadable Integer32,
    hwcpName DisplayString,
    hwcpNominalReading Integer32,
    hwcpNormalMax Integer32,
    hwcpNormalMin Integer32,
    hwcpPNPDeviceID DisplayString,
    hwcpPowerManagementCapabilities DisplayString,
    hwcpPowerManagementSupported TruthValue,
    hwcpResolution Gauge32,
    hwcpStatus INTEGER,
    hwcpStatusInfo INTEGER,
    hwcpSystemCreationClassName DisplayString,
    hwcpSystemName DisplayString,
    hwcpTolerance Integer32,
    hwcpUpperThresholdCritical Integer32,
    hwcpUpperThresholdFatal Integer32,
    hwcpUpperThresholdNonCritical Integer32
}

hwcpIndex OBJECT-TYPE
    SYNTAX     Integer32 (1..2147483647)
    MAX-ACCESS read-only
    STATUS     current
    DESCRIPTION
        "The value of this object uniquely identifies the
        instance entry for this class."
    ::= { win32CurrentProbeEntry 1 }

hwcpAccuracy OBJECT-TYPE
    SYNTAX     Integer32
    UNITS "Hundredths of Percent"
    MAX-ACCESS read-only
    STATUS     current
    DESCRIPTION
        "Accuracy of the sensor for the measured property.
        The value is recorded as plus/minus hundredths of a
        percent. Accuracy, along with resolution and
        tolerance, is used to calculate the actual value of
        the measured physical property. Accuracy may vary
        and depends on whether or not the device is linear
        over its dynamic range. This property is inherited
        from CIM_NumericSensor."
    ::= { win32CurrentProbeEntry 2 }

hwcpAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice. "
    ::= { win32CurrentProbeEntry 3 }

hwcpCaption OBJECT-TYPE
    SYNTAX     DisplayString
    MAX-ACCESS read-only
    STATUS     current
    DESCRIPTION
        "Short description of the object a one-line string.
        This property is inherited from
        CIM_ManagedSystemElement."
    ::= { win32CurrentProbeEntry 4 }

hwcpConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32CurrentProbeEntry 5 }

hwcpConfigManagerUserConfig OBJECT-TYPE
    SYNTAX     TruthValue
    MAX-ACCESS read-only
    STATUS     current
    DESCRIPTION
        "If TRUE, the device is using a user-defined
        configuration. This property is inherited from
        CIM_LogicalDevice."
    ::= { win32CurrentProbeEntry 6 }

hwcpCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be identified
        uniquely. This property is inherited from
        CIM_LogicalDevice."
    ::= { win32CurrentProbeEntry 7 }

hwcpCurrentReading OBJECT-TYPE
    SYNTAX     Integer32
    UNITS "Milliamps"
    MAX-ACCESS read-only
    STATUS     current
    DESCRIPTION
        "Current value indicated by the sensor. This
        property is inherited from CIM_NumericSensor."
    ::= { win32CurrentProbeEntry 8 }

hwcpDescription OBJECT-TYPE
    SYNTAX     DisplayString
    MAX-ACCESS read-only
    STATUS     current
    DESCRIPTION
        "Description of the object. This property is
        inherited from CIM_ManagedSystemElement."
    ::= { win32CurrentProbeEntry 9 }

hwcpDeviceID OBJECT-TYPE
    SYNTAX     DisplayString
    MAX-ACCESS read-only
    STATUS     current
    DESCRIPTION
        "Unique identifier of the current probe. This
        property is inherited from CIM_LogicalDevice."
    ::= { win32CurrentProbeEntry 10 }

hwcpErrorCleared OBJECT-TYPE
    SYNTAX     TruthValue
    MAX-ACCESS read-only
    STATUS     current
    DESCRIPTION
        "If TRUE, the error reported in LastErrorCode is
        now cleared. This property is inherited from
        CIM_LogicalDevice."
    ::= { win32CurrentProbeEntry 11 }

hwcpErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32CurrentProbeEntry 12 }

hwcpInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32CurrentProbeEntry 13 }

hwcpIsLinear OBJECT-TYPE
    SYNTAX     TruthValue
    MAX-ACCESS read-only
    STATUS     current
    DESCRIPTION
        "If TRUE, the sensor is linear over its dynamic
        range. This property is inherited from
        CIM_NumericSensor."
    ::= { win32CurrentProbeEntry 14 }

hwcpLastErrorCode OBJECT-TYPE
    SYNTAX     Gauge32
    MAX-ACCESS read-only
    STATUS     current
    DESCRIPTION
        "Last error code reported by the logical device.
        This property is inherited from CIM_LogicalDevice."
    ::= { win32CurrentProbeEntry 15 }

hwcpLowerThresholdCritical OBJECT-TYPE
    SYNTAX     Integer32
    UNITS "Milliamps"
    MAX-ACCESS read-only
    STATUS     current
    DESCRIPTION
        "Sensor threshold values specify the ranges
        (minimum and maximum values) to determine whether
        or not the sensor is operating under normal,
        non-critical, critical, or fatal conditions. If
        CurrentReading is between LowerThresholdCritical
        and LowerThresholdFatal, the current state is
        critical. This property is inherited from
        CIM_NumericSensor."
    ::= { win32CurrentProbeEntry 16 }

hwcpLowerThresholdFatal OBJECT-TYPE
    SYNTAX     Integer32
    UNITS "Milliamps"
    MAX-ACCESS read-only
    STATUS     current
    DESCRIPTION
        "Sensor's threshold values specify the ranges
        (minimum and maximum values) for determining
        whether the sensor is operating under normal,
        non-critical, critical, or fatal conditions. If
        CurrentReading is below LowerThresholdFatal, the
        current state is fatal. This property is inherited
        from CIM_NumericSensor."
    ::= { win32CurrentProbeEntry 17 }

hwcpLowerThresholdNonCritical OBJECT-TYPE
    SYNTAX     Integer32
    UNITS "Milliamps"
    MAX-ACCESS read-only
    STATUS     current
    DESCRIPTION
        "Sensor's threshold values specify the ranges
        (minimum and maximum values) for determining
        whether the sensor is operating under normal,
        non-critical, critical, or fatal conditions. If
        CurrentReading is between LowerThresholdNonCritical
        and UpperThresholdNonCritical, the sensor is
        reporting a normal value. If CurrentReading is
        between LowerThresholdNonCritical and
        LowerThresholdCritical, the current state is
        non-critical. This property is inherited from
        CIM_NumericSensor."
    ::= { win32CurrentProbeEntry 18 }

hwcpMaxReadable OBJECT-TYPE
    SYNTAX     Integer32
    UNITS "Milliamps"
    MAX-ACCESS read-only
    STATUS     current
    DESCRIPTION
        "Largest value of the measured property that can be
        read by the numeric sensor. This property is
        inherited from CIM_NumericSensor."
    ::= { win32CurrentProbeEntry 19 }

hwcpMinReadable OBJECT-TYPE
    SYNTAX     Integer32
    UNITS "Milliamps"
    MAX-ACCESS read-only
    STATUS     current
    DESCRIPTION
        "Smallest value of the measured property that can
        be read by the numeric sensor. This property is
        inherited from CIM_NumericSensor."
    ::= { win32CurrentProbeEntry 20 }

hwcpName OBJECT-TYPE
    SYNTAX     DisplayString
    MAX-ACCESS read-only
    STATUS     current
    DESCRIPTION
        "Label by which the object is known. When
        subclassed, the property can be overridden to be a
        key property. This property is inherited from
        CIM_ManagedSystemElement."
    ::= { win32CurrentProbeEntry 21 }

hwcpNominalReading OBJECT-TYPE
    SYNTAX     Integer32
    UNITS "Milliamps"
    MAX-ACCESS read-only
    STATUS     current
    DESCRIPTION
        "Normal or expected value for the numeric sensor.
        This property is inherited from CIM_NumericSensor."
    ::= { win32CurrentProbeEntry 22 }

hwcpNormalMax OBJECT-TYPE
    SYNTAX     Integer32
    UNITS "Milliamps"
    MAX-ACCESS read-only
    STATUS     current
    DESCRIPTION
        "Normal or expected value for the numeric sensor.
        This property is inherited from CIM_NumericSensor."
    ::= { win32CurrentProbeEntry 23 }

hwcpNormalMin OBJECT-TYPE
    SYNTAX     Integer32
    UNITS "Milliamps"
    MAX-ACCESS read-only
    STATUS     current
    DESCRIPTION
        "Guidance for the user as to the normal minimum
        range for the numeric sensor. This property is
        inherited from CIM_NumericSensor."
    ::= { win32CurrentProbeEntry 24 }

hwcpPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32CurrentProbeEntry 25 }

hwcpPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32CurrentProbeEntry 26 }

hwcpPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32CurrentProbeEntry 27 }

hwcpResolution OBJECT-TYPE
    SYNTAX     Gauge32
    UNITS "Tenths of Milliamps"
    MAX-ACCESS read-only
    STATUS     current
    DESCRIPTION
        "Ability of the sensor to resolve differences in
        the measured property. This value may vary
        depending on whether the device is linear over its
        dynamic range. This property is inherited from
        CIM_NumericSensor."
    ::= { win32CurrentProbeEntry 28 }

hwcpStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32CurrentProbeEntry 29 }

hwcpStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32CurrentProbeEntry 30 }

hwcpSystemCreationClassName OBJECT-TYPE
    SYNTAX     DisplayString
    MAX-ACCESS read-only
    STATUS     current
    DESCRIPTION
        "Value for the scoping computer's CreationClassName
        property. This property is inherited from
        CIM_LogicalDevice."
    ::= { win32CurrentProbeEntry 31 }

hwcpSystemName OBJECT-TYPE
    SYNTAX     DisplayString
    MAX-ACCESS read-only
    STATUS     current
    DESCRIPTION
        "Name of the scoping system. This property is
        inherited from CIM_LogicalDevice."
    ::= { win32CurrentProbeEntry 32 }

hwcpTolerance OBJECT-TYPE
    SYNTAX     Integer32
    UNITS "Milliamps"
    MAX-ACCESS read-only
    STATUS     current
    DESCRIPTION
        "Tolerance of the sensor for the measured property.
        Tolerance, along with resolution and accuracy, is
        used to calculate the actual value of the measured
        physical property. Tolerance may vary depending on
        whether the device is linear over its dynamic
        range. This property is inherited from
        CIM_NumericSensor."
    ::= { win32CurrentProbeEntry 33 }

hwcpUpperThresholdCritical OBJECT-TYPE
    SYNTAX     Integer32
    UNITS "Milliamps"
    MAX-ACCESS read-only
    STATUS     current
    DESCRIPTION
        "Sensor's threshold values specify the ranges
        (minimum and maximum values) for determining
        whether the sensor is operating under normal,
        non-critical, critical, or fatal conditions. If
        CurrentReading is between UpperThresholdCritical
        and UpperThresholdFatal, the current state is
        critical. This property is inherited from
        CIM_NumericSensor."
    ::= { win32CurrentProbeEntry 34 }

hwcpUpperThresholdFatal OBJECT-TYPE
    SYNTAX     Integer32
    UNITS "Milliamps"
    MAX-ACCESS read-only
    STATUS     current
    DESCRIPTION
        "Sensor's threshold values specify the ranges
        (minimum and maximum values) for determining
        whether the sensor is operating under normal,
        non-critical, critical, or fatal conditions. If
        CurrentReading is above UpperThresholdFatal, the
        current state is fatal. This property is inherited
        from CIM_NumericSensor."
    ::= { win32CurrentProbeEntry 35 }

hwcpUpperThresholdNonCritical OBJECT-TYPE
    SYNTAX     Integer32
    UNITS "Milliamps"
    MAX-ACCESS read-only
    STATUS     current
    DESCRIPTION
        "Sensor's threshold values specify the ranges
        (minimum and maximum values) for determining
        whether the sensor is operating under normal,
        non-critical, critical, or fatal conditions. If
        CurrentReading is between LowerThresholdNonCritical
        and UpperThresholdNonCritical, the sensor is
        reporting a normal value. If CurrentReading is
        between UpperThresholdNonCritical and
        UpperThresholdCritical, the current state is
        non-critical. This property is inherited from
        CIM_NumericSensor."
    ::= { win32CurrentProbeEntry 36 }

win32PortableBatteryTable OBJECT-TYPE
    SYNTAX     SEQUENCE OF Win32PortableBatteryEntry
    MAX-ACCESS not-accessible
    STATUS     current
    DESCRIPTION
        "The Win32_PortableBattery WMI class contains the
        properties related to a portable battery, such a
        notebook computer battery."
    ::= { wmiPower 3 }

win32PortableBatteryEntry OBJECT-TYPE
    SYNTAX     Win32PortableBatteryEntry
    MAX-ACCESS not-accessible
    STATUS     current
    DESCRIPTION
        "None"
    INDEX      { hwpbIndex }
    ::= { win32PortableBatteryTable 1 }

Win32PortableBatteryEntry ::= SEQUENCE {
    hwpbIndex Integer32,
    hwpbAvailability INTEGER,
    hwpbBatteryRechargeTime Gauge32,
    hwpbBatteryStatus INTEGER,
    hwpbCapacityMultiplier Integer32,
    hwpbCaption DisplayString,
    hwpbChemistry INTEGER,
    hwpbConfigManagerErrorCode INTEGER,
    hwpbConfigManagerUserConfig TruthValue,
    hwpbCreationClassName DisplayString,
    hwpbDescription DisplayString,
    hwpbDesignCapacity Gauge32,
    hwpbDesignVoltage Gauge32,
    hwpbDeviceID DisplayString,
    hwpbErrorCleared TruthValue,
    hwpbErrorDescription DisplayString,
    hwpbEstimatedChargeRemaining Integer32,
    hwpbEstimatedRunTime Gauge32,
    hwpbExpectedBatteryLife Gauge32,
    hwpbExpectedLife Gauge32,
    hwpbFullChargeCapacity Gauge32,
    hwpbInstallDate DateAndTime,
    hwpbLastErrorCode Gauge32,
    hwpbLocation DisplayString,
    hwpbManufactureDate DisplayString,
    hwpbManufacturer DisplayString,
    hwpbMaxBatteryError Integer32,
    hwpbMaxRechargeTime Gauge32,
    hwpbName DisplayString,
    hwpbPNPDeviceID DisplayString,
    hwpbPowerManagementCapabilities DisplayString,
    hwpbPowerManagementSupported TruthValue,
    hwpbSmartBatteryVersion DisplayString,
    hwpbStatus INTEGER,
    hwpbStatusInfo INTEGER,
    hwpbSystemCreationClassName DisplayString,
    hwpbSystemName DisplayString,
    hwpbTimeOnBattery Gauge32,
    hwpbTimeToFullCharge Gauge32
}

hwpbIndex OBJECT-TYPE
    SYNTAX     Integer32 (1..2147483647)
    MAX-ACCESS read-only
    STATUS     current
    DESCRIPTION
        "The value of this object uniquely identifies the
        instance entry for this class."
    ::= { win32PortableBatteryEntry 1 }

hwpbAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32PortableBatteryEntry 2 }

hwpbBatteryRechargeTime OBJECT-TYPE
    SYNTAX     Gauge32
    MAX-ACCESS read-only
    STATUS     current
    DESCRIPTION
        "Time required to fully charge the battery. This
        property is inherited from CIM_Battery.
        Windows 2000:  This property is not supported.
        Windows XP and Windows Server 2003:  This property
        is removed."
    ::= { win32PortableBatteryEntry 3 }

hwpbBatteryStatus OBJECT-TYPE
    SYNTAX     INTEGER {
        other(1),
        unknown(2),
        fullyCharged(3),
        low(4),
        critical(5),
        charging(6),
        chargingAndHigh(7),
        chargingAndLow(8),
        chargingAndCritical(9),
        undefined(10),
        partiallyCharged(11)
    }
    MAX-ACCESS read-only
    STATUS     current
    DESCRIPTION
        "Description of the battery's charge status. The
        value 10 (Undefined) is not valid in the Common
        Information Model (CIM) schema because in Desktop
        Management Interface (DMI) it represents that no
        battery is installed. In this case, this object
        should not be instantiated. This property is
        inherited from CIM_Battery."
    ::= { win32PortableBatteryEntry 4 }

hwpbCapacityMultiplier OBJECT-TYPE
    SYNTAX     Integer32
    MAX-ACCESS read-only
    STATUS     current
    DESCRIPTION
        "Multiplication factor of the DesignCapacity value
        to ensure that the milliwatt hour value does not
        overflow for Smart Battery Data Specification
        (SBDS) implementations."
    ::= { win32PortableBatteryEntry 5 }

hwpbCaption OBJECT-TYPE
    SYNTAX     DisplayString
    MAX-ACCESS read-only
    STATUS     current
    DESCRIPTION
        "Short description of the object a one-line string.
        This property is inherited from
        CIM_ManagedSystemElement."
    ::= { win32PortableBatteryEntry 6 }

hwpbChemistry OBJECT-TYPE
    SYNTAX     INTEGER {
        other(1),
        unknown(2),
        leadAcid(3),
        nickelCadmium(4),
        nickelMetalHydride(5),
        lithiumion(6),
        zincAir(7),
        lithiumPolymer(8)
    }
    MAX-ACCESS read-only
    STATUS     current
    DESCRIPTION
        "Chemistry of the battery. This property is
        inherited from CIM_Battery."
    ::= { win32PortableBatteryEntry 7 }

hwpbConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32PortableBatteryEntry 8 }

hwpbConfigManagerUserConfig OBJECT-TYPE
    SYNTAX     TruthValue
    MAX-ACCESS read-only
    STATUS     current
    DESCRIPTION
        "If TRUE, the device is using a user-defined
        configuration. This property is inherited from
        CIM_LogicalDevice."
    ::= { win32PortableBatteryEntry 9 }

hwpbCreationClassName OBJECT-TYPE
    SYNTAX     DisplayString (SIZE (0..256))
    MAX-ACCESS read-only
    STATUS     current
    DESCRIPTION
        "Name of the first concrete class that appears in
        the inheritance chain used in the creation of an
        instance. When used with the other key properties
        of the class, the property allows all instances of
        this class and its subclasses to be uniquely
        identified. This property is inherited from
        CIM_LogicalDevice."
    ::= { win32PortableBatteryEntry 10 }

hwpbDescription OBJECT-TYPE
    SYNTAX     DisplayString
    MAX-ACCESS read-only
    STATUS     current
    DESCRIPTION
        "Description of the object. This property is
        inherited from CIM_ManagedSystemElement."
    ::= { win32PortableBatteryEntry 11 }

hwpbDesignCapacity OBJECT-TYPE
    SYNTAX     Gauge32
    MAX-ACCESS read-only
    STATUS     current
    DESCRIPTION
        "Design capacity of the battery in milliwatt-hours.
        If this property is not supported, enter 0 (zero).
        This property is inherited from CIM_Battery."
    ::= { win32PortableBatteryEntry 12 }

hwpbDesignVoltage OBJECT-TYPE
    SYNTAX     Gauge32
    MAX-ACCESS read-only
    STATUS     current
    DESCRIPTION
        "Design voltage of the battery in Millivolts. If
        this attribute is not supported, enter 0 (zero).
        This property is inherited from CIM_Battery."
    ::= { win32PortableBatteryEntry 13 }

hwpbDeviceID OBJECT-TYPE
    SYNTAX     DisplayString
    MAX-ACCESS read-only
    STATUS     current
    DESCRIPTION
        "Battery identifier. This property is inherited
        from CIM_LogicalDevice.
        Example: 'Internal Battery'"
    ::= { win32PortableBatteryEntry 14 }

hwpbErrorCleared OBJECT-TYPE
    SYNTAX     TruthValue
    MAX-ACCESS read-only
    STATUS     current
    DESCRIPTION
        "If TRUE, the error reported in LastErrorCode is
        now cleared. This property is inherited from
        CIM_LogicalDevice."
    ::= { win32PortableBatteryEntry 15 }

hwpbErrorDescription OBJECT-TYPE
    SYNTAX     DisplayString
    MAX-ACCESS read-only
    STATUS     current
    DESCRIPTION
        "More information about the error recorded in
        LastErrorCode, and any corrective actions that may
        be taken. This property is inherited from
        CIM_LogicalDevice."
    ::= { win32PortableBatteryEntry 16 }

hwpbEstimatedChargeRemaining OBJECT-TYPE
    SYNTAX     Integer32
    MAX-ACCESS read-only
    STATUS     current
    DESCRIPTION
        "Estimate of the percentage of full charge
        remaining. This property is inherited from
        CIM_Battery."
    ::= { win32PortableBatteryEntry 17 }

hwpbEstimatedRunTime OBJECT-TYPE
    SYNTAX     Gauge32
    MAX-ACCESS read-only
    STATUS     current
    DESCRIPTION
        "Estimate in minutes of the time to battery charge
        depletion under the present load conditions if the
        utility power is off, or lost and remains off, or a
        laptop is disconnected from a power source. This
        property is inherited from CIM_Battery."
    ::= { win32PortableBatteryEntry 18 }

hwpbExpectedBatteryLife OBJECT-TYPE
    SYNTAX     Gauge32
    MAX-ACCESS read-only
    STATUS     current
    DESCRIPTION
        "Amount of time it takes to completely drain the
        battery after it has been fully charged. This
        property is inherited from CIM_Battery.
        Windows 2000:  This property is not supported.
        Windows XP and Windows Server 2003:  This property
        has been removed."
    ::= { win32PortableBatteryEntry 19 }

hwpbExpectedLife OBJECT-TYPE
    SYNTAX     Gauge32
    MAX-ACCESS read-only
    STATUS     current
    DESCRIPTION
        "Battery's expected lifetime in minutes, assuming
        that the battery is fully charged. This property
        represents the total expected life of the battery,
        not its current remaining life, which is indicated
        by the EstimatedRunTime property. This property is
        inherited from CIM_Battery."
    ::= { win32PortableBatteryEntry 20 }

hwpbFullChargeCapacity OBJECT-TYPE
    SYNTAX     Gauge32
    MAX-ACCESS read-only
    STATUS     current
    DESCRIPTION
        "Full charge capacity of the battery in
        milliwatt-hours. Comparison of this value to the
        DesignCapacity property determines when the battery
        requires replacement. A battery's end of life is
        typically when the FullChargeCapacity property
        falls below 80% of the DesignCapacity property. If
        this property is not supported, enter 0 (zero).
        This property is inherited from CIM_Battery."
    ::= { win32PortableBatteryEntry 21 }

hwpbInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32PortableBatteryEntry 22 }

hwpbLastErrorCode OBJECT-TYPE
    SYNTAX     Gauge32
    MAX-ACCESS read-only
    STATUS     current
    DESCRIPTION
        "Last error code reported by the logical device.
        This property is inherited from CIM_LogicalDevice."
    ::= { win32PortableBatteryEntry 23 }

hwpbLocation OBJECT-TYPE
    SYNTAX     DisplayString
    MAX-ACCESS read-only
    STATUS     current
    DESCRIPTION
        "Physical location of the battery. This property is
        filled by the computer manufacturer.
        Example: 'In the back, on the left-hand side'"
    ::= { win32PortableBatteryEntry 24 }

hwpbManufactureDate OBJECT-TYPE
    SYNTAX     DisplayString
    MAX-ACCESS read-only
    STATUS     current
    DESCRIPTION
        "Date when the battery was manufactured."
    ::= { win32PortableBatteryEntry 25 }

hwpbManufacturer OBJECT-TYPE
    SYNTAX     DisplayString
    MAX-ACCESS read-only
    STATUS     current
    DESCRIPTION
        "Manufacturer of the battery."
    ::= { win32PortableBatteryEntry 26 }

hwpbMaxBatteryError OBJECT-TYPE
    SYNTAX     Integer32
    UNITS "Percent"
    MAX-ACCESS read-only
    STATUS     current
    DESCRIPTION
        "Difference between the highest estimated amount of
        energy left in the battery and the current amount
        reported by the battery."
    ::= { win32PortableBatteryEntry 27 }

hwpbMaxRechargeTime OBJECT-TYPE
    SYNTAX     Gauge32
    MAX-ACCESS read-only
    STATUS     current
    DESCRIPTION
        "Maximum time, in minutes, to fully charge the
        battery. This property represents the time to
        recharge a fully depleted battery, not the current
        remaining charge time, which is indicated in the
        TimeToFullCharge property. This property is
        inherited from CIM_Battery."
    ::= { win32PortableBatteryEntry 28 }

hwpbName OBJECT-TYPE
    SYNTAX     DisplayString
    MAX-ACCESS read-only
    STATUS     current
    DESCRIPTION
        "Label by which the object is known. When
        subclassed, the property can be overridden to be a
        key property. This property is inherited from
        CIM_ManagedSystemElement."
    ::= { win32PortableBatteryEntry 29 }

hwpbPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32PortableBatteryEntry 30 }

hwpbPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Timeset to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32PortableBatteryEntry 31 }

hwpbPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32PortableBatteryEntry 32 }

hwpbSmartBatteryVersion OBJECT-TYPE
    SYNTAX     DisplayString
    MAX-ACCESS read-only
    STATUS     current
    DESCRIPTION
        "Smart Battery Data Specification version number
        supported by this battery. If the battery does not
        support this function, the value should be left
        blank. This property is inherited from
        CIM_Battery."
    ::= { win32PortableBatteryEntry 33 }

hwpbStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PortableBatteryEntry 34 }

hwpbStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32PortableBatteryEntry 35 }

hwpbSystemCreationClassName OBJECT-TYPE
    SYNTAX     DisplayString
    MAX-ACCESS read-only
    STATUS     current
    DESCRIPTION
        "Value of the scoping computer's CreationClassName
        property. This property is inherited from
        CIM_LogicalDevice."
    ::= { win32PortableBatteryEntry 36 }

hwpbSystemName OBJECT-TYPE
    SYNTAX     DisplayString
    MAX-ACCESS read-only
    STATUS     current
    DESCRIPTION
        "Name of the scoping system. This property is
        inherited from CIM_LogicalDevice."
    ::= { win32PortableBatteryEntry 37 }

hwpbTimeOnBattery OBJECT-TYPE
    SYNTAX     Gauge32
    MAX-ACCESS read-only
    STATUS     current
    DESCRIPTION
        "Elapsed time in seconds since the computer
        system's UPS last switched to battery power, or the
        time since the system or UPS was last restarted,
        whichever is less. If the battery is online, 0
        (zero) is returned. This property is inherited from
        CIM_Battery."
    ::= { win32PortableBatteryEntry 38 }

hwpbTimeToFullCharge OBJECT-TYPE
    SYNTAX     Gauge32
    MAX-ACCESS read-only
    STATUS     current
    DESCRIPTION
        "Remaining time in minutes to charge the battery
        fully at the current charge rate and usage. This
        property is inherited from CIM_Battery."
    ::= { win32PortableBatteryEntry 39 }

win32UninterruptPowerSupplyTable OBJECT-TYPE
    SYNTAX     SEQUENCE OF Win32UninterruptPowerSupplyEntry
    MAX-ACCESS not-accessible
    STATUS     current
    DESCRIPTION
        "The Win32_UninterruptiblePowerSupply WMI class
        represents the capabilities and management capacity
        of an uninterruptible power supply (UPS). The
        properties of the UPS device indicate when incoming
        power is trimmed or boosted, and the aggregated
        information of the batteries, generators, and so
        on, that comprise the device. These individual
        components (for example, multiple batteries) can
        also be independently modeled and associated with
        the UPS."
    ::= { wmiPower 4 }

win32UninterruptPowerSupplyEntry OBJECT-TYPE
    SYNTAX     Win32UninterruptPowerSupplyEntry
    MAX-ACCESS not-accessible
    STATUS     current
    DESCRIPTION
        "None"
    INDEX      { hwupsIndex }
    ::= { win32UninterruptPowerSupplyTable 1 }

Win32UninterruptPowerSupplyEntry ::= SEQUENCE {
    hwupsIndex Integer32,
    hwupsActiveInputVoltage INTEGER,
    hwupsAvailability INTEGER,
    hwupsBatteryInstalled TruthValue,
    hwupsCanTurnOffRemotely TruthValue,
    hwupsCaption DisplayString,
    hwupsCommandFile DisplayString,
    hwupsConfigManagerErrorCode INTEGER,
    hwupsConfigManagerUserConfig TruthValue,
    hwupsCreationClassName DisplayString,
    hwupsDescription DisplayString,
    hwupsDeviceID DisplayString,
    hwupsErrorCleared TruthValue,
    hwupsErrorDescription DisplayString,
    hwupsEstimatedChargeRemaining Integer32,
    hwupsEstimatedRunTime Gauge32,
    hwupsFirstMessageDelay Gauge32,
    hwupsInstallDate DateAndTime,
    hwupsIsSwitchingSupply TruthValue,
    hwupsLastErrorCode Gauge32,
    hwupsLowBatterySignal TruthValue,
    hwupsMessageInterval Gauge32,
    hwupsName DisplayString,
    hwupsPNPDeviceID DisplayString,
    hwupsPowerFailSignal TruthValue,
    hwupsPowerManagementCapabilities DisplayString,
    hwupsPowerManagementSupported TruthValue,
    hwupsRange1InputFrequencyHigh Gauge32,
    hwupsRange1InputFrequencyLow Gauge32,
    hwupsRange1InputVoltageHigh Gauge32,
    hwupsRange1InputVoltageLow Gauge32,
    hwupsRange2InputFrequencyHigh Gauge32,
    hwupsRange2InputFrequencyLow Gauge32,
    hwupsRange2InputVoltageHigh Gauge32,
    hwupsRange2InputVoltageLow Gauge32,
    hwupsRemainingCapacityStatus INTEGER,
    hwupsStatus INTEGER,
    hwupsStatusInfo INTEGER,
    hwupsSystemCreationClassName DisplayString,
    hwupsSystemName DisplayString,
    hwupsTimeOnBackup Gauge32,
    hwupsTotalOutputPower Gauge32,
    hwupsTypeOfRangeSwitching INTEGER,
    hwupsUPSPort DisplayString
}

hwupsIndex OBJECT-TYPE
    SYNTAX     Integer32 (1..2147483647)
    MAX-ACCESS read-only
    STATUS     current
    DESCRIPTION
        "The value of this object uniquely identifies the
        instance entry for this class."
    ::= { win32UninterruptPowerSupplyEntry 1 }

hwupsActiveInputVoltage OBJECT-TYPE
    SYNTAX     INTEGER {
        other(1),
        unknown(2),
        range1(3),
        range2(4),
        both(5),
        neither(6)
    }
    MAX-ACCESS read-only
    STATUS     current
    DESCRIPTION
        "Input voltage range currently in use. This
        property is inherited from CIM_PowerSupply."
    ::= { win32UninterruptPowerSupplyEntry 2 }

hwupsAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32UninterruptPowerSupplyEntry 3 }

hwupsBatteryInstalled OBJECT-TYPE
    SYNTAX     TruthValue
    MAX-ACCESS read-only
    STATUS     current
    DESCRIPTION
        "If TRUE, a battery is installed on the device."
    ::= { win32UninterruptPowerSupplyEntry 4 }

hwupsCanTurnOffRemotely OBJECT-TYPE
    SYNTAX     TruthValue
    MAX-ACCESS read-only
    STATUS     current
    DESCRIPTION
        "If TRUE, the power supply can be turned off
        remotely."
    ::= { win32UninterruptPowerSupplyEntry 5 }

hwupsCaption OBJECT-TYPE
    SYNTAX     DisplayString (SIZE (0..64))
    MAX-ACCESS read-only
    STATUS     current
    DESCRIPTION
        "Short description of an object a one-line string.
        This property is inherited from
        CIM_ManagedSystemElement."
    ::= { win32UninterruptPowerSupplyEntry 6 }

hwupsCommandFile OBJECT-TYPE
    SYNTAX     DisplayString
    MAX-ACCESS read-only
    STATUS     current
    DESCRIPTION
        "Name of a command file to execute immediately
        before shutting down."
    ::= { win32UninterruptPowerSupplyEntry 7 }

hwupsConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32UninterruptPowerSupplyEntry 8 }

hwupsConfigManagerUserConfig OBJECT-TYPE
    SYNTAX     TruthValue
    MAX-ACCESS read-only
    STATUS     current
    DESCRIPTION
        "If TRUE, the device is using a user-defined
        configuration. This property is inherited from
        CIM_LogicalDevice."
    ::= { win32UninterruptPowerSupplyEntry 9 }

hwupsCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32UninterruptPowerSupplyEntry 10 }

hwupsDescription OBJECT-TYPE
    SYNTAX     DisplayString
    MAX-ACCESS read-only
    STATUS     current
    DESCRIPTION
        "Description of the object. This property is
        inherited from CIM_ManagedSystemElement."
    ::= { win32UninterruptPowerSupplyEntry 11 }

hwupsDeviceID OBJECT-TYPE
    SYNTAX     DisplayString
    MAX-ACCESS read-only
    STATUS     current
    DESCRIPTION
        "Unique identifier of this UPS device with other
        devices on the system. This property is inherited
        from CIM_LogicalDevice."
    ::= { win32UninterruptPowerSupplyEntry 12 }

hwupsErrorCleared OBJECT-TYPE
    SYNTAX     TruthValue
    MAX-ACCESS read-only
    STATUS     current
    DESCRIPTION
        "If TRUE, the error reported in LastErrorCode is
        now cleared. This property is inherited from
        CIM_LogicalDevice."
    ::= { win32UninterruptPowerSupplyEntry 13 }

hwupsErrorDescription OBJECT-TYPE
    SYNTAX     DisplayString
    MAX-ACCESS read-only
    STATUS     current
    DESCRIPTION
        "Free-form string that supplies more information
        about the error recorded in LastErrorCode, and
        information about corrective actions that can be
        taken. This property is inherited from
        CIM_LogicalDevice."
    ::= { win32UninterruptPowerSupplyEntry 14 }

hwupsEstimatedChargeRemaining OBJECT-TYPE
    SYNTAX     Integer32
    MAX-ACCESS read-only
    STATUS     current
    DESCRIPTION
        "Estimate of the percentage of full charge that
        remains for a UPS that uses battery technology.
        This property is inherited from
        CIM_UninterruptiblePowerSupply."
    ::= { win32UninterruptPowerSupplyEntry 15 }

hwupsEstimatedRunTime OBJECT-TYPE
    SYNTAX     Gauge32
    MAX-ACCESS read-only
    STATUS     current
    DESCRIPTION
        "Estimated time, in minutes, until battery or
        generator depletion in the present load conditions
        if the utility power is off or lost and remains
        off. This property is inherited from
        CIM_UninterruptiblePowerSupply."
    ::= { win32UninterruptPowerSupplyEntry 16 }

hwupsFirstMessageDelay OBJECT-TYPE
    SYNTAX     Gauge32
    UNITS "Seconds"
    MAX-ACCESS read-only
    STATUS     current
    DESCRIPTION
        "Length of time between initial power failure and
        the first message sent to users. If power is
        restored within the FirstMessageDelay value, no
        message is sent, but the event is logged."
    ::= { win32UninterruptPowerSupplyEntry 17 }

hwupsInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32UninterruptPowerSupplyEntry 18 }

hwupsIsSwitchingSupply OBJECT-TYPE
    SYNTAX     TruthValue
    MAX-ACCESS read-only
    STATUS     current
    DESCRIPTION
        "If TRUE, the power supply is a switching supply as
        opposed to linear. This property is inherited from
        CIM_PowerSupply."
    ::= { win32UninterruptPowerSupplyEntry 19 }

hwupsLastErrorCode OBJECT-TYPE
    SYNTAX     Gauge32
    MAX-ACCESS read-only
    STATUS     current
    DESCRIPTION
        "Last error code the logical device reports. This
        property is inherited from CIM_LogicalDevice."
    ::= { win32UninterruptPowerSupplyEntry 20 }

hwupsLowBatterySignal OBJECT-TYPE
    SYNTAX     TruthValue
    MAX-ACCESS read-only
    STATUS     current
    DESCRIPTION
        "If TRUE, the power supply has a low battery
        signal."
    ::= { win32UninterruptPowerSupplyEntry 21 }

hwupsMessageInterval OBJECT-TYPE
    SYNTAX     Gauge32
    UNITS "Seconds"
    MAX-ACCESS read-only
    STATUS     current
    DESCRIPTION
        "Length of time between messages sent to users to
        inform the users of power failure."
    ::= { win32UninterruptPowerSupplyEntry 22 }

hwupsName OBJECT-TYPE
    SYNTAX     DisplayString
    MAX-ACCESS read-only
    STATUS     current
    DESCRIPTION
        "Label for the object. When subclassed, the
        property can be overridden to be a key property.
        This property is inherited from
        CIM_ManagedSystemElement."
    ::= { win32UninterruptPowerSupplyEntry 23 }

hwupsPNPDeviceID OBJECT-TYPE
    SYNTAX     DisplayString
    MAX-ACCESS read-only
    STATUS     current
    DESCRIPTION
        "Plug and Play device identifier of the logical
        device. This property is inherited from
        CIM_LogicalDevice.
        Example: '*PNP030b'"
    ::= { win32UninterruptPowerSupplyEntry 24 }

hwupsPowerFailSignal OBJECT-TYPE
    SYNTAX     TruthValue
    MAX-ACCESS read-only
    STATUS     current
    DESCRIPTION
        "If TRUE, the power supply has a power failure
        signal."
    ::= { win32UninterruptPowerSupplyEntry 25 }

hwupsPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32UninterruptPowerSupplyEntry 26 }

hwupsPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32UninterruptPowerSupplyEntry 27 }

hwupsRange1InputFrequencyHigh OBJECT-TYPE
    SYNTAX     Gauge32
    MAX-ACCESS read-only
    STATUS     current
    DESCRIPTION
        "Frequency, in hertz, at the high end of the power
        supply input frequency range 1. A value of 0 (zero)
        indicates DC. This property is inherited from
        CIM_PowerSupply."
    ::= { win32UninterruptPowerSupplyEntry 28 }

hwupsRange1InputFrequencyLow OBJECT-TYPE
    SYNTAX     Gauge32
    MAX-ACCESS read-only
    STATUS     current
    DESCRIPTION
        "Frequency, in hertz, at the low end of the power
        supply input frequency range 1. A value of 0 (zero)
        indicates DC. This property is inherited from
        CIM_PowerSupply."
    ::= { win32UninterruptPowerSupplyEntry 29 }

hwupsRange1InputVoltageHigh OBJECT-TYPE
    SYNTAX     Gauge32
    MAX-ACCESS read-only
    STATUS     current
    DESCRIPTION
        "Voltage level, in millivolts, above which the UPS
        must compensate by trimming the voltage. A value of
        0 (zero)indicates that the voltage at trimming time
        is 'unknown'. This property is inherited from
        CIM_PowerSupply."
    ::= { win32UninterruptPowerSupplyEntry 30 }

hwupsRange1InputVoltageLow OBJECT-TYPE
    SYNTAX     Gauge32
    MAX-ACCESS read-only
    STATUS     current
    DESCRIPTION
        "Voltage level, in millivolts, below which the UPS
        must compensate by boosting the voltage using its
        power source. A value of 0 (zero) indicates that
        the voltage at boosting time is 'unknown'. This
        property is inherited from CIM_PowerSupply."
    ::= { win32UninterruptPowerSupplyEntry 31 }

hwupsRange2InputFrequencyHigh OBJECT-TYPE
    SYNTAX     Gauge32
    MAX-ACCESS read-only
    STATUS     current
    DESCRIPTION
        "Frequency, in hertz, at the high end of the power
        supply input frequency range 2. A value of 0 (zero)
        indicates DC. This property is inherited from
        CIM_PowerSupply."
    ::= { win32UninterruptPowerSupplyEntry 32 }

hwupsRange2InputFrequencyLow OBJECT-TYPE
    SYNTAX     Gauge32
    MAX-ACCESS read-only
    STATUS     current
    DESCRIPTION
        "Frequency, in hertz, at the low end of the power
        supply input frequency range 2. A value of 0 (zero)
        indicates DC. This property is inherited from
        CIM_PowerSupply."
    ::= { win32UninterruptPowerSupplyEntry 33 }

hwupsRange2InputVoltageHigh OBJECT-TYPE
    SYNTAX     Gauge32
    MAX-ACCESS read-only
    STATUS     current
    DESCRIPTION
        "Voltage level, in millivolts, above which the UPS
        must compensate by trimming the voltage. A value of
        0 (zero)indicates that the voltage at trimming time
        is 'unknown'. This property is inherited from
        CIM_PowerSupply."
    ::= { win32UninterruptPowerSupplyEntry 34 }

hwupsRange2InputVoltageLow OBJECT-TYPE
    SYNTAX     Gauge32
    MAX-ACCESS read-only
    STATUS     current
    DESCRIPTION
        "Voltage level, in millivolts, below which the UPS
        must compensate by using the power source to boost
        the voltage. A value of 0 (zero) indicates that the
        voltage at boosting time is 'unknown'. This
        property is inherited from CIM_PowerSupply."
    ::= { win32UninterruptPowerSupplyEntry 35 }

hwupsRemainingCapacityStatus OBJECT-TYPE
    SYNTAX     INTEGER {
        unknown(1),
        norma(2),
        low(3),
        depleted(4)
    }
    MAX-ACCESS read-only
    STATUS     current
    DESCRIPTION
        "Capacity remaining in the UPS' batteries and
        generator. Normal (2) indicates that the remaining
        estimated minutes of run-time is greater than the
        UPS' defined 'low power' state (typically two
        minutes). Low (3) indicates that the remaining
        estimated minutes of run-time is less than or equal
        to the UPS' defined 'low power' state. Depleted (4)
        indicates that the UPS will be unable to sustain
        the present load when and if the utility power is
        lost (including the possibility that the utility
        power is currently absent). This property is
        inherited from CIM_UninterruptiblePowerSupply."
    ::= { win32UninterruptPowerSupplyEntry 36 }

hwupsStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32UninterruptPowerSupplyEntry 37 }

hwupsStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32UninterruptPowerSupplyEntry 38 }

hwupsSystemCreationClassName OBJECT-TYPE
    SYNTAX     DisplayString
    MAX-ACCESS read-only
    STATUS     current
    DESCRIPTION
        "Value of the scoping computer's CreationClassName
        property. This property is inherited from
        CIM_LogicalDevice."
    ::= { win32UninterruptPowerSupplyEntry 39 }

hwupsSystemName OBJECT-TYPE
    SYNTAX     DisplayString
    MAX-ACCESS read-only
    STATUS     current
    DESCRIPTION
        "Name of the scoping system. This property is
        inherited from CIM_LogicalDevice."
    ::= { win32UninterruptPowerSupplyEntry 40 }

hwupsTimeOnBackup OBJECT-TYPE
    SYNTAX     Gauge32
    MAX-ACCESS read-only
    STATUS     current
    DESCRIPTION
        "Elapsed time, in seconds, after the UPS last
        switched to battery power, generator, or the time
        after the UPS was last restarted, whichever is
        less. If the UPS is 'on line', 0 (zero) is
        returned. This property is inherited from
        CIM_UninterruptiblePowerSupply."
    ::= { win32UninterruptPowerSupplyEntry 41 }

hwupsTotalOutputPower OBJECT-TYPE
    SYNTAX     Gauge32
    MAX-ACCESS read-only
    STATUS     current
    DESCRIPTION
        "Total output power of the power supply in
        milliwatts. The value 0 (zero) denotes 'unknown'.
        This property is inherited from CIM_PowerSupply."
    ::= { win32UninterruptPowerSupplyEntry 42 }

hwupsTypeOfRangeSwitching OBJECT-TYPE
    SYNTAX     INTEGER {
        other(1),
        unknown(2),
        manual(3),
        autoswitch(4),
        wideRange(5),
        notApplicable(6)
    }
    MAX-ACCESS read-only
    STATUS     current
    DESCRIPTION
        "Type of input voltage range switching implemented
        in this power supply. This property is inherited
        from CIM_PowerSupply."
    ::= { win32UninterruptPowerSupplyEntry 43 }

hwupsUPSPort OBJECT-TYPE
    SYNTAX     DisplayString
    MAX-ACCESS read-only
    STATUS     current
    DESCRIPTION
        "Name of the serial port to which the UPS is
        connected.
        Example: 'COM1:'"
    ::= { win32UninterruptPowerSupplyEntry 44 }

win32VoltageProbeTable OBJECT-TYPE
    SYNTAX     SEQUENCE OF Win32VoltageProbeEntry
    MAX-ACCESS not-accessible
    STATUS     current
    DESCRIPTION
        "The Win32_VoltageProbe WMI class represents the
        properties of a voltage sensor (electronic
        voltmeter)."
    ::= { wmiPower 5 }

win32VoltageProbeEntry OBJECT-TYPE
    SYNTAX     Win32VoltageProbeEntry
    MAX-ACCESS not-accessible
    STATUS     current
    DESCRIPTION
        "None"
    INDEX      { hwvpIndex }
    ::= { win32VoltageProbeTable 1 }

Win32VoltageProbeEntry ::= SEQUENCE {
    hwvpIndex Integer32,
    hwvpAccuracy Integer32,
    hwvpAvailability INTEGER,
    hwvpCaption DisplayString,
    hwvpConfigManagerErrorCode INTEGER,
    hwvpConfigManagerUserConfig TruthValue,
    hwvpCreationClassName DisplayString,
    hwvpCurrentReading Integer32,
    hwvpDescription DisplayString,
    hwvpDeviceID DisplayString,
    hwvpErrorCleared TruthValue,
    hwvpErrorDescription DisplayString,
    hwvpInstallDate DateAndTime,
    hwvpIsLinear TruthValue,
    hwvpLastErrorCode Gauge32,
    hwvpLowerThresholdCritical Integer32,
    hwvpLowerThresholdFatal Integer32,
    hwvpLowerThresholdNonCritical Integer32,
    hwvpMaxReadable Integer32,
    hwvpMinReadable Integer32,
    hwvpName DisplayString,
    hwvpNominalReading Integer32,
    hwvpNormalMax Integer32,
    hwvpNormalMin Integer32,
    hwvpPNPDeviceID DisplayString,
    hwvpPowerManagementCapabilities DisplayString,
    hwvpPowerManagementSupported TruthValue,
    hwvpResolution Gauge32,
    hwvpStatus INTEGER,
    hwvpStatusInfo INTEGER,
    hwvpSystemCreationClassName DisplayString,
    hwvpSystemName DisplayString,
    hwvpTolerance Integer32,
    hwvpUpperThresholdCritical Integer32,
    hwvpUpperThresholdFatal Integer32,
    hwvpUpperThresholdNonCritical Integer32
}

hwvpIndex OBJECT-TYPE
    SYNTAX     Integer32 (1..2147483647)
    MAX-ACCESS read-only
    STATUS     current
    DESCRIPTION
        "The value of this object uniquely identifies the
        instance entry for this class."
    ::= { win32VoltageProbeEntry 1 }

hwvpAccuracy OBJECT-TYPE
    SYNTAX     Integer32
    UNITS "Hundredths of Percent"
    MAX-ACCESS read-only
    STATUS     current
    DESCRIPTION
        "Accuracy of the sensor for the measured property.
        The accuracy value is recorded as plus or minus
        hundredths of a percent. Accuracy, along with
        resolution and tolerance, is used to calculate the
        actual value of the measured physical property. The
        accuracy may vary and depends on whether or not the
        device is linear in its dynamic range. This
        property is inherited from CIM_NumericSensor."
    ::= { win32VoltageProbeEntry 2 }

hwvpAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32VoltageProbeEntry 3 }

hwvpCaption OBJECT-TYPE
    SYNTAX     DisplayString (SIZE (0..64))
    MAX-ACCESS read-only
    STATUS     current
    DESCRIPTION
        "Short description of the object a one-line string.
        This property is inherited from
        CIM_ManagedSystemElement."
    ::= { win32VoltageProbeEntry 4 }

hwvpConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32VoltageProbeEntry 5 }

hwvpConfigManagerUserConfig OBJECT-TYPE
    SYNTAX     TruthValue
    MAX-ACCESS read-only
    STATUS     current
    DESCRIPTION
        "If TRUE, the device is using a user-defined
        configuration. This property is inherited from
        CIM_LogicalDevice."
    ::= { win32VoltageProbeEntry 6 }

hwvpCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32VoltageProbeEntry 7 }

hwvpCurrentReading OBJECT-TYPE
    SYNTAX     Integer32
    UNITS "Millivolts"
    MAX-ACCESS read-only
    STATUS     current
    DESCRIPTION
        "Current value indicated by the sensor. This
        property is inherited from CIM_NumericSensor."
    ::= { win32VoltageProbeEntry 8 }

hwvpDescription OBJECT-TYPE
    SYNTAX     DisplayString
    MAX-ACCESS read-only
    STATUS     current
    DESCRIPTION
        "Description of the object. This property is
        inherited from CIM_ManagedSystemElement."
    ::= { win32VoltageProbeEntry 9 }

hwvpDeviceID OBJECT-TYPE
    SYNTAX     DisplayString
    MAX-ACCESS read-only
    STATUS     current
    DESCRIPTION
        "Unique identifier of the voltage probe. This
        property is inherited from CIM_LogicalDevice."
    ::= { win32VoltageProbeEntry 10 }

hwvpErrorCleared OBJECT-TYPE
    SYNTAX     TruthValue
    MAX-ACCESS read-only
    STATUS     current
    DESCRIPTION
        "If TRUE, the error reported in LastErrorCode is
        now cleared. This property is inherited from
        CIM_LogicalDevice."
    ::= { win32VoltageProbeEntry 11 }

hwvpErrorDescription OBJECT-TYPE
    SYNTAX     DisplayString
    MAX-ACCESS read-only
    STATUS     current
    DESCRIPTION
        "More information about the error recorded in
        LastErrorCode, and information about any corrective
        actions that may be taken. This property is
        inherited from CIM_LogicalDevice."
    ::= { win32VoltageProbeEntry 12 }

hwvpInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32VoltageProbeEntry 13 }

hwvpIsLinear OBJECT-TYPE
    SYNTAX     TruthValue
    MAX-ACCESS read-only
    STATUS     current
    DESCRIPTION
        "If TRUE, the sensor is linear over its dynamic
        range. This property is inherited from
        CIM_NumericSensor."
    ::= { win32VoltageProbeEntry 14 }

hwvpLastErrorCode OBJECT-TYPE
    SYNTAX     Gauge32
    MAX-ACCESS read-only
    STATUS     current
    DESCRIPTION
        "Last error code reported by the logical device.
        This property is inherited from CIM_LogicalDevice."
    ::= { win32VoltageProbeEntry 15 }

hwvpLowerThresholdCritical OBJECT-TYPE
    SYNTAX     Integer32
    UNITS "Millivolts"
    MAX-ACCESS read-only
    STATUS     current
    DESCRIPTION
        "Sensor threshold values specify the ranges
        (minimum and maximum values) to determine if the
        sensor is operating under normal, non-critical,
        critical, or fatal conditions. If CurrentReading is
        between LowerThresholdCritical and
        LowerThresholdFatal, the current state is critical.
        This property is inherited from CIM_NumericSensor."
    ::= { win32VoltageProbeEntry 16 }

hwvpLowerThresholdFatal OBJECT-TYPE
    SYNTAX     Integer32
    UNITS "Millivolts"
    MAX-ACCESS read-only
    STATUS     current
    DESCRIPTION
        "Sensor threshold values specify the ranges
        (minimum and maximum values) to determine if the
        sensor is operating under normal, non-critical,
        critical, or fatal conditions. If CurrentReading is
        below LowerThresholdFatal, the current state is
        fatal. This property is inherited from
        CIM_NumericSensor."
    ::= { win32VoltageProbeEntry 17 }

hwvpLowerThresholdNonCritical OBJECT-TYPE
    SYNTAX     Integer32
    UNITS "Millivolts"
    MAX-ACCESS read-only
    STATUS     current
    DESCRIPTION
        "Sensor threshold values specify the ranges
        (minimum and maximum values) to determine if the
        sensor is operating under normal, non-critical,
        critical, or fatal conditions. If CurrentReading is
        between LowerThresholdNonCritical and
        UpperThresholdNonCritical, the sensor is reporting
        a normal value. If CurrentReading is between
        LowerThresholdNonCritical and
        LowerThresholdCritical, the current state is
        non-critical. This property is inherited from
        CIM_NumericSensor."
    ::= { win32VoltageProbeEntry 18 }

hwvpMaxReadable OBJECT-TYPE
    SYNTAX     Integer32
    UNITS "Millivolts"
    MAX-ACCESS read-only
    STATUS     current
    DESCRIPTION
        "Largest value of the measured property that the
        numeric sensor can read. This property is inherited
        from CIM_NumericSensor."
    ::= { win32VoltageProbeEntry 19 }

hwvpMinReadable OBJECT-TYPE
    SYNTAX     Integer32
    UNITS "Millivolts"
    MAX-ACCESS read-only
    STATUS     current
    DESCRIPTION
        "Smallest value of the measured property that the
        numeric sensor can read. This property is inherited
        from CIM_NumericSensor."
    ::= { win32VoltageProbeEntry 20 }

hwvpName OBJECT-TYPE
    SYNTAX     DisplayString
    MAX-ACCESS read-only
    STATUS     current
    DESCRIPTION
        "Label for an object. When subclassed, the property
        can be overridden to be a key property. This
        property is inherited from
        CIM_ManagedSystemElement."
    ::= { win32VoltageProbeEntry 21 }

hwvpNominalReading OBJECT-TYPE
    SYNTAX     Integer32
    UNITS "Millivolts"
    MAX-ACCESS read-only
    STATUS     current
    DESCRIPTION
        "Normal or expected value for the numeric sensor.
        This property is inherited from CIM_NumericSensor."
    ::= { win32VoltageProbeEntry 22 }

hwvpNormalMax OBJECT-TYPE
    SYNTAX     Integer32
    UNITS "Millivolts"
    MAX-ACCESS read-only
    STATUS     current
    DESCRIPTION
        "Normal or expected value for the numeric sensor.
        This property is inherited from CIM_NumericSensor."
    ::= { win32VoltageProbeEntry 23 }

hwvpNormalMin OBJECT-TYPE
    SYNTAX     Integer32
    UNITS "Millivolts"
    MAX-ACCESS read-only
    STATUS     current
    DESCRIPTION
        "Guidance for the user to indicate the normal
        minimum range for the numeric sensor. This property
        is inherited from CIM_NumericSensor."
    ::= { win32VoltageProbeEntry 24 }

hwvpPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32VoltageProbeEntry 25 }

hwvpPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32VoltageProbeEntry 26 }

hwvpPowerManagementSupported OBJECT-TYPE
    SYNTAX     TruthValue
    MAX-ACCESS read-only
    STATUS     current
    DESCRIPTION
        "If TRUE, the device can be power-managed, which
        means that it can be put into suspend mode, and so
        on. The property does not indicate that power
        management features are currently enabled, but it
        does indicate that the logical device is capable of
        power management. This property is inherited from
        CIM_LogicalDevice."
    ::= { win32VoltageProbeEntry 27 }

hwvpResolution OBJECT-TYPE
    SYNTAX     Gauge32
    UNITS "Tenths of Millivolts"
    MAX-ACCESS read-only
    STATUS     current
    DESCRIPTION
        "Ability of the sensor to resolve differences in
        the measured property. This value may vary and
        depends on whether the device is linear in its
        dynamic range. This property is inherited from
        CIM_NumericSensor."
    ::= { win32VoltageProbeEntry 28 }

hwvpStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32VoltageProbeEntry 29 }

hwvpStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32VoltageProbeEntry 30 }

hwvpSystemCreationClassName OBJECT-TYPE
    SYNTAX     DisplayString
    MAX-ACCESS read-only
    STATUS     current
    DESCRIPTION
        "Value for the CreationClassName property of the
        scoping computer. This property is inherited from
        CIM_LogicalDevice."
    ::= { win32VoltageProbeEntry 31 }

hwvpSystemName OBJECT-TYPE
    SYNTAX     DisplayString
    MAX-ACCESS read-only
    STATUS     current
    DESCRIPTION
        "Name of the scoping system. This property is
        inherited from CIM_LogicalDevice."
    ::= { win32VoltageProbeEntry 32 }

hwvpTolerance OBJECT-TYPE
    SYNTAX     Integer32
    UNITS "Millivolts"
    MAX-ACCESS read-only
    STATUS     current
    DESCRIPTION
        "Tolerance of the sensor for the measured property.
        Tolerance, along with resolution and accuracy, is
        used to calculate the actual value of the measured
        physical property. Tolerance may vary, and depends
        on whether the device is linear in its dynamic
        range. This property is inherited from
        CIM_NumericSensor."
    ::= { win32VoltageProbeEntry 33 }

hwvpUpperThresholdCritical OBJECT-TYPE
    SYNTAX     Integer32
    UNITS "Millivolts"
    MAX-ACCESS read-only
    STATUS     current
    DESCRIPTION
        "Sensor threshold values specify the ranges
        (minimum and maximum values) to determine whether
        the sensor is operating under normal, non-critical,
        critical, or fatal conditions. If CurrentReading is
        between UpperThresholdCritical and
        UpperThresholdFatal, the current state is critical.
        This property is inherited from CIM_NumericSensor."
    ::= { win32VoltageProbeEntry 34 }

hwvpUpperThresholdFatal OBJECT-TYPE
    SYNTAX     Integer32
    UNITS "Millivolts"
    MAX-ACCESS read-only
    STATUS     current
    DESCRIPTION
        "Sensor threshold values specify the ranges
        (minimum and maximum values) to determine whether
        the sensor is operating under normal, non-critical,
        critical, or fatal conditions. If CurrentReading is
        above UpperThresholdFatal, the current state is
        fatal. This property is inherited from
        CIM_NumericSensor."
    ::= { win32VoltageProbeEntry 35 }

hwvpUpperThresholdNonCritical OBJECT-TYPE
    SYNTAX     Integer32
    UNITS "Millivolts"
    MAX-ACCESS read-only
    STATUS     current
    DESCRIPTION
        "Sensor threshold values specify the ranges
        (minimum and maximum values) to determine whether
        the sensor is operating under normal, non-critical,
        critical, or fatal conditions. If CurrentReading is
        between LowerThresholdNonCriticaland
        UpperThresholdNonCritical, the sensor is reporting
        a normal value. If CurrentReading is between
        UpperThresholdNonCritical and
        UpperThresholdCritical, the current state is
        non-critical. This property is inherited from
        CIM_NumericSensor."
    ::= { win32VoltageProbeEntry 36 }

wmiPrinting OBJECT-IDENTITY
    STATUS     current
    DESCRIPTION
        "The Printing subcategory groups classes that
        represent printers, printer configurations, and
        print jobs."
    ::= { wmiHardware 7 }

win32PrinterTable OBJECT-TYPE
    SYNTAX     SEQUENCE OF Win32PrinterEntry
    MAX-ACCESS not-accessible
    STATUS     current
    DESCRIPTION
        "The Win32_Printer WMI class represents a device
        connected to a Windows computer system that can
        reproduce a visual image on paper or other medium."
    ::= { wmiPrinting 1 }

win32PrinterEntry OBJECT-TYPE
    SYNTAX     Win32PrinterEntry
    MAX-ACCESS not-accessible
    STATUS     current
    DESCRIPTION
        "None"
    INDEX      { hwprIndex }
    ::= { win32PrinterTable 1 }

Win32PrinterEntry ::= SEQUENCE {
    hwprIndex Integer32,
    hwprAttributes Gauge32,
    hwprAvailability INTEGER,
    hwprAvailableJobSheets DisplayString,
    hwprAveragePagesPerMinute Gauge32,
    hwprCapabilities DisplayString,
    hwprCapabilityDescriptions DisplayString,
    hwprCaption DisplayString,
    hwprCharSetsSupported DisplayString,
    hwprComment DisplayString,
    hwprConfigManagerErrorCode INTEGER,
    hwprConfigManagerUserConfig TruthValue,
    hwprCreationClassName DisplayString,
    hwprCurrentCapabilities DisplayString,
    hwprCurrentCharSet DisplayString,
    hwprCurrentLanguage INTEGER,
    hwprCurrentMimeType DisplayString,
    hwprCurrentNaturalLanguage DisplayString,
    hwprCurrentPaperType DisplayString,
    hwprDefault TruthValue,
    hwprDefaultCapabilities DisplayString,
    hwprDefaultCopies Gauge32,
    hwprDefaultLanguage INTEGER,
    hwprDefaultMimeType DisplayString,
    hwprDefaultNumberUp Gauge32,
    hwprDefaultPaperType DisplayString,
    hwprDefaultPriority Gauge32,
    hwprDescription DisplayString,
    hwprDetectedErrorState INTEGER,
    hwprDeviceID DisplayString,
    hwprDirect TruthValue,
    hwprDoCompleteFirst TruthValue,
    hwprDriverName DisplayString,
    hwprEnableBIDI TruthValue,
    hwprEnableDevQueryPrint TruthValue,
    hwprErrorCleared TruthValue,
    hwprErrorDescription DisplayString,
    hwprErrorInformation DisplayString,
    hwprExtendedDetectedErrorState INTEGER,
    hwprExtendedPrinterStatus INTEGER,
    hwprHidden TruthValue,
    hwprHorizontalResolution Gauge32,
    hwprInstallDate DateAndTime,
    hwprJobCountSinceLastReset Gauge32,
    hwprKeepPrintedJobs TruthValue,
    hwprLanguagesSupported DisplayString,
    hwprLastErrorCode Gauge32,
    hwprLocal TruthValue,
    hwprLocation DisplayString,
    hwprMarkingTechnology INTEGER,
    hwprMaxCopies Gauge32,
    hwprMaxNumberUp Gauge32,
    hwprMaxSizeSupported Gauge32,
    hwprMimeTypesSupported DisplayString,
    hwprName DisplayString,
    hwprNaturalLanguagesSupported DisplayString,
    hwprNetwork TruthValue,
    hwprPaperSizesSupported DisplayString,
    hwprPaperTypesAvailable DisplayString,
    hwprParameters DisplayString,
    hwprPNPDeviceID DisplayString,
    hwprPortName DisplayString,
    hwprPowerManagementCapabilities DisplayString,
    hwprPowerManagementSupported TruthValue,
    hwprPrinterPaperNames DisplayString,
    hwprPrinterState INTEGER,
    hwprPrinterStatus INTEGER,
    hwprPrintJobDataType DisplayString,
    hwprPrintProcessor DisplayString,
    hwprPriority Gauge32,
    hwprPublished TruthValue,
    hwprQueued TruthValue,
    hwprRawOnly TruthValue,
    hwprSeparatorFile DisplayString,
    hwprServerName DisplayString,
    hwprShared TruthValue,
    hwprShareName DisplayString,
    hwprSpoolEnabled TruthValue,
    hwprStartTime DateAndTime,
    hwprStatus INTEGER,
    hwprStatusInfo INTEGER,
    hwprSystemCreationClassName DisplayString,
    hwprSystemName DisplayString,
    hwprTimeOfLastReset DateAndTime,
    hwprUntilTime DateAndTime,
    hwprVerticalResolution Gauge32,
    hwprWorkOffline TruthValue
}

hwprIndex OBJECT-TYPE
    SYNTAX     Integer32 (1..2147483647)
    MAX-ACCESS read-only
    STATUS     current
    DESCRIPTION
        "The value of this object uniquely identifies the
        instance entry for this class."
    ::= { win32PrinterEntry 1 }

hwprAttributes OBJECT-TYPE
    SYNTAX     Gauge32
    MAX-ACCESS read-only
    STATUS     current
    DESCRIPTION
        "Attributes of a Windows printing device
        represented by a combination of flags.
        Value used to set the bit Meaning 
        0x1 Print jobs are buffered and queued.  
        0x2 Document to be sent directly to the printer.
        This value is used if print jobs are not being
        queued correctly.  
        0x4 Default printer on a computer.  
        0x8 Available as a shared network resource.  
        0x10 Attached to a network. If both Local and
        Network bits are set, this indicates a network
        printer.  
        0x20 Hidden from some users on the network.  
        0x40 Directly connected to a computer. If both
        Local and Network bits are set, this indicates a
        network printer.  
        0x80 Enable the queue on the printer if available. 
        
        0x100 Spooler should not delete documents after
        they are printed.  
        0x200 Start jobs that are finished spooling first. 
        
        0x400 Queue print jobs when a printer is not
        available.  
        0x800 Enable bi-directional printing.  
        0x1000 Allow only raw data type jobs to be spooled.
         
        0x2000 Published in the network directory service. 
        "
    ::= { win32PrinterEntry 2 }

hwprAvailability OBJECT-TYPE
    SYNTAX     INTEGER {
        other(1),
        unknown(2),
        runningOrFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of a device. Power Save -
        Unknown indicates that the device is in a power
        save mode, but the exact status is unknown; Power
        Save - Low Power Mode indicates that the device is
        in a power save state but still functioning, and
        may exhibit degraded performance; Power Save -
        Standby indicates that the device is not
        functioning but can be brought to full power
        quickly; and Power Save - Warning indicates that
        the device is in a warning state, and a power save
        mode. This property is inherited from
        CIM_LogicalDevice."
    ::= { win32PrinterEntry 3 }

hwprAvailableJobSheets OBJECT-TYPE
    SYNTAX     DisplayString
    MAX-ACCESS read-only
    STATUS     current
    DESCRIPTION
        "Array of all the job sheets available on a
        printer. Can also be used to describe the banner
        that a printer might provide at the beginning of
        each job, or other user-specified options. This
        property is inherited from CIM_Printer. This
        property is new for Windows XP."
    ::= { win32PrinterEntry 4 }

hwprAveragePagesPerMinute OBJECT-TYPE
    SYNTAX     Gauge32
    MAX-ACCESS read-only
    STATUS     current
    DESCRIPTION
        "Printing rate that a printer can produce output
        the average number of pages per minute."
    ::= { win32PrinterEntry 5 }

hwprCapabilities OBJECT-TYPE
    SYNTAX     DisplayString
    MAX-ACCESS read-only
    STATUS     current
    DESCRIPTION
        "Array of printer capabilities. This property is
        inherited from CIM_Printer.
        Value Meaning 
        0 Unknown 
        1 Other 
        2 Color Printing 
        3 Duplex Printing 
        4 Copies 
        5 Collation 
        6 Stapling 
        7 Transparency Printing 
        8 Punch 
        9 Cover 
        10 Bind 
        11 Black and White Printing 
        12 One Sided 
        13 Two Sided Long Edge 
        14 Two Sided Short Edge 
        15 Portrait 
        16 Landscape 
        17 Reverse Portrait 
        18 Reverse Landscape 
        19 Quality High 
        20 Quality Normal 
        21 Quality Low "
    ::= { win32PrinterEntry 6 }

hwprCapabilityDescriptions OBJECT-TYPE
    SYNTAX     DisplayString
    MAX-ACCESS read-only
    STATUS     current
    DESCRIPTION
        "Array of free-form strings that provide detailed
        explanations for the printer features indicated in
        the Capabilities array. Each entry of this array is
        related to an entry in the Capabilities array that
        is located in the same index. This property is
        inherited from CIM_Printer."
    ::= { win32PrinterEntry 7 }

hwprCaption OBJECT-TYPE
    SYNTAX     DisplayString (SIZE (0..64))
    MAX-ACCESS read-only
    STATUS     current
    DESCRIPTION
        "Short description of an object a one-line string.
        This property is inherited from
        CIM_ManagedSystemElement."
    ::= { win32PrinterEntry 8 }

hwprCharSetsSupported OBJECT-TYPE
    SYNTAX     DisplayString
    MAX-ACCESS read-only
    STATUS     current
    DESCRIPTION
        "Array of available character sets for output.
        Strings provided in this property must conform to
        the semantics and syntax specified by section 4.1.2
        ('Charset parameters') in RFC 2046 (MIME Part 2)
        and contained in the IANA character-set registry.
        Examples include utf-8, us-ascii and iso-8859-1.
        This property is inherited from CIM_Printer. This
        property is new for Windows XP."
    ::= { win32PrinterEntry 9 }

hwprComment OBJECT-TYPE
    SYNTAX     DisplayString
    MAX-ACCESS read-only
    STATUS     current
    DESCRIPTION
        "Comment for a print queue. This property is new
        for Windows XP.
        Example: Color printer"
    ::= { win32PrinterEntry 10 }

hwprConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32PrinterEntry 11 }

hwprConfigManagerUserConfig OBJECT-TYPE
    SYNTAX     TruthValue
    MAX-ACCESS read-only
    STATUS     current
    DESCRIPTION
        "If TRUE, the device is using a user-defined
        configuration. This property is inherited from
        CIM_LogicalDevice."
    ::= { win32PrinterEntry 12 }

hwprCreationClassName OBJECT-TYPE
    SYNTAX     DisplayString
    MAX-ACCESS read-only
    STATUS     current
    DESCRIPTION
        "Name of the first concrete class to appear in the
        inheritance chain used to create an instance. When
        used with other key properties of the class, the
        property allows all instances of this class and its
        subclasses to be identified uniquely. This property
        is inherited from CIM_LogicalDevice."
    ::= { win32PrinterEntry 13 }

hwprCurrentCapabilities OBJECT-TYPE
    SYNTAX     DisplayString
    MAX-ACCESS read-only
    STATUS     current
    DESCRIPTION
        "Array of printer finishings and other capabilities
        that are being used currently. An entry in this
        property must also be listed in the Capabilities
        array. This property is inherited from CIM_Printer.
        This property is new for Windows XP.
        Value Meaning 
        0 Unknown 
        1 Other 
        2 Color Printing 
        3 Duplex Printing 
        4 Copies 
        5 Collation 
        6 Stapling 
        7 Transparency Printing 
        8 Punch 
        9 Cover 
        10 Bind 
        11 Black and White Printing 
        12 One Sided 
        13 Two Sided Long Edge 
        14 Two Sided Short Edge 
        15 Portrait 
        16 Landscape 
        17 Reverse Portrait 
        18 Reverse Landscape 
        19 Quality High 
        20 Quality Normal 
        21 Quality Low "
    ::= { win32PrinterEntry 14 }

hwprCurrentCharSet OBJECT-TYPE
    SYNTAX     DisplayString
    MAX-ACCESS read-only
    STATUS     current
    DESCRIPTION
        "The character set currently being used for output.
        Strings provided in this property must conform to
        the semantics and syntax specified by section 4.1.2
        ('Charset parameters') in RFC 2046 (MIME Part 2)
        and contained in the IANA character-set registry.
        Examples include utf-8, us-ascii and iso-8859-1.
        This property is inherited from CIM_Printer. This
        property is new for Windows XP."
    ::= { win32PrinterEntry 15 }

hwprCurrentLanguage OBJECT-TYPE
    SYNTAX     INTEGER {
        other(1),
        unknown(2),
        pcl(3),
        hpgl(4),
        pjl(5),
        ps(6),
        psprinter(7),
        ipds(8),
        ppds(9),
        escapeP(10),
        epson(11),
        ddif(12),
        interpress(13),
        iso6429(14),
        lineData(15),
        dodca(16),
        regis(17),
        scs(18),
        spdl(19),
        tek4014(20),
        pds(21),
        igp(22),
        codeV(23),
        dscdse(24),
        wps(25),
        ln03(26),
        ccitt(27),
        quic(28),
        cpap(29),
        decPPL(30),
        simpleText(31),
        npap(32),
        doc(33),
        imPress(34),
        pinwriter(35),
        npdl(36),
        nec201PL(37),
        automatic(38),
        pages(39),
        lips(40),
        tiff(41),
        diagnostic(42),
        caPSL(43),
        excl(44),
        lcds(45),
        xes(46),
        mime(47)
    }
    MAX-ACCESS read-only
    STATUS     current
    DESCRIPTION
        "Windows Server 2003 and Windows XP:  Printer
        language currently being used. The language being
        used must be listed in the LanguagesSupported
        property. This property is inherited from
        CIM_Printer.
        This property is new for Windows XP."
    ::= { win32PrinterEntry 16 }

hwprCurrentMimeType OBJECT-TYPE
    SYNTAX     DisplayString
    MAX-ACCESS read-only
    STATUS     current
    DESCRIPTION
        "MIME type currently being used if the
        CurrentLanguage is a MIME type (value = 47). This
        property is inherited from CIM_Printer. This
        property is new for Windows XP."
    ::= { win32PrinterEntry 17 }

hwprCurrentNaturalLanguage OBJECT-TYPE
    SYNTAX     DisplayString
    MAX-ACCESS read-only
    STATUS     current
    DESCRIPTION
        "Language that the printer is using for management
        currently. The language listed here must also be
        listed in the NaturalLanguagesSupported property.
        This property is inherited from CIM_Printer. This
        property is new for Windows XP."
    ::= { win32PrinterEntry 18 }

hwprCurrentPaperType OBJECT-TYPE
    SYNTAX     DisplayString
    MAX-ACCESS read-only
    STATUS     current
    DESCRIPTION
        "Type of paper the printer is using. Must be
        expressed in the form specified by the ISO/IEC
        10175 Document Printing Application (DPA), which is
        summarized in Appendix C of RFC 1759 (Printer MIB).
        This property is inherited from CIM_Printer. This
        property is new for Windows XP."
    ::= { win32PrinterEntry 19 }

hwprDefault OBJECT-TYPE
    SYNTAX     TruthValue
    MAX-ACCESS read-only
    STATUS     current
    DESCRIPTION
        "If TRUE, the printer is the default printer on the
        computer. This property is new for Windows XP."
    ::= { win32PrinterEntry 20 }

hwprDefaultCapabilities OBJECT-TYPE
    SYNTAX     DisplayString
    MAX-ACCESS read-only
    STATUS     current
    DESCRIPTION
        "Array of the finishings and other printer
        capabilities that are used by default. Each entry
        in the DefaultCapabilities array must also be
        listed in the Capabilities array. This property is
        inherited from CIM_Printer. This property is new
        for Windows XP.
        Value Meaning 
        0 Unknown 
        1 Other 
        2 Color Printing 
        3 Duplex Printing 
        4 Copies 
        5 Collation 
        6 Stapling 
        7 Transparency Printing 
        8 Punch 
        9 Cover 
        10 Bind 
        11 Black and White Printing 
        12 One Sided 
        13 Two Sided Long Edge 
        14 Two Sided Short Edge 
        15 Portrait 
        16 Landscape 
        17 Reverse Portrait 
        18 Reverse Landscape 
        19 Quality High 
        20 Quality Normal 
        21 Quality Low "
    ::= { win32PrinterEntry 21 }

hwprDefaultCopies OBJECT-TYPE
    SYNTAX     Gauge32
    MAX-ACCESS read-only
    STATUS     current
    DESCRIPTION
        "Number of copies that are produced for one job
        unless otherwise specified. This property is
        inherited from CIM_Printer. This property is new
        for Windows XP."
    ::= { win32PrinterEntry 22 }

hwprDefaultLanguage OBJECT-TYPE
    SYNTAX     INTEGER {
        other(1),
        unknown(2),
        pcl(3),
        hpgl(4),
        pjl(5),
        ps(6),
        psprinter(7),
        ipds(8),
        ppds(9),
        escapeP(10),
        epson(11),
        ddif(12),
        interpress(13),
        iso6429(14),
        lineData(15),
        dodca(16),
        regis(17),
        scs(18),
        spdl(19),
        tek4014(20),
        pds(21),
        igp(22),
        codeV(23),
        dscdse(24),
        wps(25),
        ln03(26),
        ccitt(27),
        quic(28),
        cpap(29),
        decPPL(30),
        simpleText(31),
        npap(32),
        doc(33),
        imPress(34),
        pinwriter(35),
        npdl(36),
        nec201PL(37),
        automatic(38),
        pages(39),
        lips(40),
        tiff(41),
        diagnostic(42),
        caPSL(43),
        excl(44),
        lcds(45),
        xes(46),
        mime(47)
    }
    MAX-ACCESS read-only
    STATUS     current
    DESCRIPTION
        "Windows Server 2003 and Windows XP:  Default
        printer language. The language listed here must
        also be listed in the LanguagesSupported property.
        This property is inherited from CIM_Printer."
    ::= { win32PrinterEntry 23 }

hwprDefaultMimeType OBJECT-TYPE
    SYNTAX     DisplayString
    MAX-ACCESS read-only
    STATUS     current
    DESCRIPTION
        "Windows Server 2003 and Windows XP:  MIME type
        currently being used, if the DefaultLanguage value
        is a MIME type (value = 47). This property is
        inherited from CIM_Printer."
    ::= { win32PrinterEntry 24 }

hwprDefaultNumberUp OBJECT-TYPE
    SYNTAX     Gauge32
    MAX-ACCESS read-only
    STATUS     current
    DESCRIPTION
        "Windows Server 2003 and Windows XP:  Number of
        print-stream pages that the printer renders on one
        media sheet unless a job specifies otherwise. This
        property is inherited from CIM_Printer."
    ::= { win32PrinterEntry 25 }

hwprDefaultPaperType OBJECT-TYPE
    SYNTAX     DisplayString
    MAX-ACCESS read-only
    STATUS     current
    DESCRIPTION
        "Windows Server 2003 and Windows XP:  Paper type
        that the printer uses unless a print job specifies
        a different paper type. The string must be
        expressed in the form specified by ISO/IEC 1017
        Document Printing Application (DPA), which is
        summarized in Appendix C of RFC 1759 (Printer MIB).
        This property is inherited from CIM_Printer."
    ::= { win32PrinterEntry 26 }

hwprDefaultPriority OBJECT-TYPE
    SYNTAX     Gauge32
    MAX-ACCESS read-only
    STATUS     current
    DESCRIPTION
        "Default priority value assigned to each print
        job."
    ::= { win32PrinterEntry 27 }

hwprDescription OBJECT-TYPE
    SYNTAX     DisplayString
    MAX-ACCESS read-only
    STATUS     current
    DESCRIPTION
        "Description of an object. This property is
        inherited from CIM_ManagedSystemElement."
    ::= { win32PrinterEntry 28 }

hwprDetectedErrorState OBJECT-TYPE
    SYNTAX     INTEGER {
        unknown(1),
        other(2),
        noError(3),
        lowPaper(4),
        noPaper(5),
        lowToner(6),
        noToner(7),
        doorOpen(8),
        jammed(9),
        offline(10),
        serviceRequested(11),
        outputBinFull(12)
    }
    MAX-ACCESS read-only
    STATUS     current
    DESCRIPTION
        "Printer error information. This property is
        inherited from CIM_Printer."
    ::= { win32PrinterEntry 29 }

hwprDeviceID OBJECT-TYPE
    SYNTAX     DisplayString
    MAX-ACCESS read-only
    STATUS     current
    DESCRIPTION
        "Unique identifier of the printer on a system. This
        property is inherited from CIM_LogicalDevice."
    ::= { win32PrinterEntry 30 }

hwprDirect OBJECT-TYPE
    SYNTAX     TruthValue
    MAX-ACCESS read-only
    STATUS     current
    DESCRIPTION
        "Windows Server 2003 and Windows XP:  If TRUE, the
        print job is sent directly to the printer. If
        FALSE, the print job is spooled."
    ::= { win32PrinterEntry 31 }

hwprDoCompleteFirst OBJECT-TYPE
    SYNTAX     TruthValue
    MAX-ACCESS read-only
    STATUS     current
    DESCRIPTION
        "Windows Server 2003 and Windows XP:  If TRUE, the
        printer starts jobs that are finished spooling. If
        FALSE, the printer starts jobs in the order that
        the jobs are received. "
    ::= { win32PrinterEntry 32 }

hwprDriverName OBJECT-TYPE
    SYNTAX     DisplayString
    MAX-ACCESS read-only
    STATUS     current
    DESCRIPTION
        "Name of the Windows printer driver.
        Example: Windows NT Fax Driver"
    ::= { win32PrinterEntry 33 }

hwprEnableBIDI OBJECT-TYPE
    SYNTAX     TruthValue
    MAX-ACCESS read-only
    STATUS     current
    DESCRIPTION
        "Windows Server 2003 and Windows XP:  If TRUE, the
        printer can print bi-directionally."
    ::= { win32PrinterEntry 34 }

hwprEnableDevQueryPrint OBJECT-TYPE
    SYNTAX     TruthValue
    MAX-ACCESS read-only
    STATUS     current
    DESCRIPTION
        "Windows Server 2003 and Windows XP:  If TRUE, the
        printer holds documents in the queue if document
        and printer setups do not match."
    ::= { win32PrinterEntry 35 }

hwprErrorCleared OBJECT-TYPE
    SYNTAX     TruthValue
    MAX-ACCESS read-only
    STATUS     current
    DESCRIPTION
        "If TRUE, the error reported in LastErrorCode has
        been cleared. This property is inherited from
        CIM_LogicalDevice."
    ::= { win32PrinterEntry 36 }

hwprErrorDescription OBJECT-TYPE
    SYNTAX     DisplayString
    MAX-ACCESS read-only
    STATUS     current
    DESCRIPTION
        "Information about the error recorded in
        LastErrorCode, and information about corrective
        actions that can be taken. This property is
        inherited from CIM_LogicalDevice."
    ::= { win32PrinterEntry 37 }

hwprErrorInformation OBJECT-TYPE
    SYNTAX     DisplayString
    MAX-ACCESS read-only
    STATUS     current
    DESCRIPTION
        "Windows Server 2003 and Windows XP:  Array of
        supplemental information for the current error
        state indicated in DetectedErrorState. This
        property is inherited from CIM_Printer."
    ::= { win32PrinterEntry 38 }

hwprExtendedDetectedErrorState OBJECT-TYPE
    SYNTAX     INTEGER {
        unknown(0),
        other(1),
        noError(2),
        lowPaper(3),
        noPaper(4),
        lowToner(5),
        noToner(6),
        doorOpen(7),
        jammed(8),
        serviceRequested(9),
        outputBinFull(10),
        paperProblem(11),
        cannotPrintPage(12),
        userInterventionRequired(13),
        outOfMemory(14),
        serverUnknown(15)
    }
    MAX-ACCESS read-only
    STATUS     current
    DESCRIPTION
        "Windows Server 2003 and Windows XP:  Reports
        standard error information. Additional information
        should be recorded in DetectedErrorState."
    ::= { win32PrinterEntry 39 }

hwprExtendedPrinterStatus OBJECT-TYPE
    SYNTAX     INTEGER {
        other(1),
        unknown(2),
        idle(3),
        printing(4),
        warmup(5),
        stoppedPrinting(6),
        offline(7),
        paused(8),
        error(9),
        busy(10),
        notAvailable(11),
        waiting(12),
        processing(13),
        initialization(14),
        powerSave(15),
        pendingDeletion(16),
        iOActive(17),
        manualFeed(18)
    }
    MAX-ACCESS read-only
    STATUS     current
    DESCRIPTION
        "Windows Server 2003 and Windows XP:  Status
        information for a printer that is different from
        information specified in the Availability
        property."
    ::= { win32PrinterEntry 40 }

hwprHidden OBJECT-TYPE
    SYNTAX     TruthValue
    MAX-ACCESS read-only
    STATUS     current
    DESCRIPTION
        "Windows Server 2003 and Windows XP:  If TRUE, the
        printer is hidden from network users."
    ::= { win32PrinterEntry 41 }

hwprHorizontalResolution OBJECT-TYPE
    SYNTAX     Gauge32
    MAX-ACCESS read-only
    STATUS     current
    DESCRIPTION
        "Horizontal resolution of the printer in pixels per
        inch. This property is inherited from CIM_Printer."
    ::= { win32PrinterEntry 42 }

hwprInstallDate OBJECT-TYPE
    SYNTAX     DateAndTime
    MAX-ACCESS read-only
    STATUS     current
    DESCRIPTION
        "Date and time an object was installed. The object
        may be installed without a value being written to
        this property. This property is inherited from
        CIM_ManagedSystemElement."
    ::= { win32PrinterEntry 43 }

hwprJobCountSinceLastReset OBJECT-TYPE
    SYNTAX     Gauge32
    MAX-ACCESS read-only
    STATUS     current
    DESCRIPTION
        "Number of print jobs since the printer was last
        reset. This property is inherited from
        CIM_Printer."
    ::= { win32PrinterEntry 44 }

hwprKeepPrintedJobs OBJECT-TYPE
    SYNTAX     TruthValue
    MAX-ACCESS read-only
    STATUS     current
    DESCRIPTION
        "Windows Server 2003 and Windows XP:  If TRUE, the
        print spooler does not delete the completed jobs."
    ::= { win32PrinterEntry 45 }

hwprLanguagesSupported OBJECT-TYPE
    SYNTAX     DisplayString
    MAX-ACCESS read-only
    STATUS     current
    DESCRIPTION
        "Array of the print languages natively supported.
        This property is inherited from CIM_Printer.
        Value Meaning 
        1 Other 
        2 Unknown 
        3 PCL 
        4 HPGL 
        5 PJL 
        6 PS 
        7 PSPrinter 
        8 IPDS 
        9 PPDS 
        10 EscapeP 
        11 Epson 
        12 DDIF 
        13 Interpress 
        14 ISO6429 
        15 LineData 
        16 DODCA 
        17 REGIS 
        18 SCS 
        19 SPDL 
        20 TEK4014 
        21 PDS 
        22 IGP 
        23 CodeV 
        24 DSCDSE 
        25 WPS 
        26 LN03 
        27 CCITT 
        28 QUIC 
        29 CPAP 
        30 DecPPL 
        31 SimpleText 
        32 NPAP 
        33 DOC 
        34 imPress 
        35 Pinwriter 
        36 NPDL 
        37 NEC201PL 
        38 Automatic 
        39 Pages 
        40 LIPS 
        41 TIFF 
        42 Diagnostic 
        43 CaPSL 
        44 EXCL 
        45 LCDS 
        46 XES 
        47 MIME "
    ::= { win32PrinterEntry 46 }

hwprLastErrorCode OBJECT-TYPE
    SYNTAX     Gauge32
    MAX-ACCESS read-only
    STATUS     current
    DESCRIPTION
        "Last error code that the logical device reports.
        This property is inherited from CIM_LogicalDevice."
    ::= { win32PrinterEntry 47 }

hwprLocal OBJECT-TYPE
    SYNTAX     TruthValue
    MAX-ACCESS read-only
    STATUS     current
    DESCRIPTION
        "Windows Server 2003 and Windows XP:  If TRUE, the
        printer is not attached to a network. If both the
        Local and Network properties are set to TRUE, then
        the printer is a network printer."
    ::= { win32PrinterEntry 48 }

hwprLocation OBJECT-TYPE
    SYNTAX     DisplayString
    MAX-ACCESS read-only
    STATUS     current
    DESCRIPTION
        "Physical location of the printer.
        Example: Bldg. 38, Room 1164"
    ::= { win32PrinterEntry 49 }

hwprMarkingTechnology OBJECT-TYPE
    SYNTAX     INTEGER {
        other(1),
        unknown(2),
        electrophotographicLED(3),
        electrophotographicLaser(4),
        electrophotographicOther(5),
        impactMovingHeadDotMatrix9pin(6),
        impactMovingHeadDotMatrix24pin(7),
        impactMovingHeadDotMatrixOther(8),
        impactMovingHeadFullyFormed(9),
        impactBand(10),
        impactOther(11),
        inkjetAqueous(12),
        inkjetSolid(13),
        inkjetOther(14),
        pen(15),
        thermalTransfer(16),
        thermalSensitive(17),
        thermalDiffusion(18),
        thermalOther(19),
        electroerosion(20),
        electrostatic(21),
        photographicMicrofiche(22),
        photographicImagesetter(23),
        photographicOther(24),
        ionDeposition(25),
        eBeam(26),
        typesetter(27)
    }
    MAX-ACCESS read-only
    STATUS     current
    DESCRIPTION
        "Windows Server 2003 and Windows XP:  Marking
        technology that the printer uses. This property is
        inherited from CIM_Printer."
    ::= { win32PrinterEntry 50 }

hwprMaxCopies OBJECT-TYPE
    SYNTAX     Gauge32
    MAX-ACCESS read-only
    STATUS     current
    DESCRIPTION
        "Windows Server 2003 and Windows XP:  Maximum
        number of copies the printer can produce for one
        job. This property is inherited from CIM_Printer."
    ::= { win32PrinterEntry 51 }

hwprMaxNumberUp OBJECT-TYPE
    SYNTAX     Gauge32
    MAX-ACCESS read-only
    STATUS     current
    DESCRIPTION
        "Windows Server 2003 and Windows XP:  Maximum
        number of print-stream pages the printer can render
        on one media sheet such as paper. This property is
        inherited from CIM_Printer. "
    ::= { win32PrinterEntry 52 }

hwprMaxSizeSupported OBJECT-TYPE
    SYNTAX     Gauge32
    MAX-ACCESS read-only
    STATUS     current
    DESCRIPTION
        "Windows Server 2003 and Windows XP:  Largest job
        as a byte steam that the printer can accept in
        kilobytes. A value of 0 (zero) indicates that no
        limit is set. This property is inherited from
        CIM_Printer. "
    ::= { win32PrinterEntry 53 }

hwprMimeTypesSupported OBJECT-TYPE
    SYNTAX     DisplayString
    MAX-ACCESS read-only
    STATUS     current
    DESCRIPTION
        "Windows Server 2003 and Windows XP:  Array of
        detailed MIME type explanations that the printer
        supports. If data is provided, then the value 47
        ('MIME') must be included in the LanguagesSupported
        property. This property is inherited from
        CIM_Printer."
    ::= { win32PrinterEntry 54 }

hwprName OBJECT-TYPE
    SYNTAX     DisplayString
    MAX-ACCESS read-only
    STATUS     current
    DESCRIPTION
        "Label for an object. When inherited by a subclass,
        the property can be overridden to be a key
        property."
    ::= { win32PrinterEntry 55 }

hwprNaturalLanguagesSupported OBJECT-TYPE
    SYNTAX     DisplayString
    MAX-ACCESS read-only
    STATUS     current
    DESCRIPTION
        "Windows XP and Windows Server 2003:  Array of
        languages supported for strings that the printer
        uses for output of management information. Must
        conform to RFC 1766. For example, 'en' is used for
        English. This property is inherited from
        CIM_Printer."
    ::= { win32PrinterEntry 56 }

hwprNetwork OBJECT-TYPE
    SYNTAX     TruthValue
    MAX-ACCESS read-only
    STATUS     current
    DESCRIPTION
        "Windows XP and Windows Server 2003:  If TRUE, the
        printer is a network printer. If both the Local and
        Network properties are set to TRUE, then the
        printer is a network printer."
    ::= { win32PrinterEntry 57 }

hwprPaperSizesSupported OBJECT-TYPE
    SYNTAX     DisplayString
    MAX-ACCESS read-only
    STATUS     current
    DESCRIPTION
        "Array of the paper types that the printer
        supports. This property is inherited from
        CIM_Printer.
        Value Meaning 
        0 Unknown 
        1 Other 
        2 A 
        3 B 
        4 C 
        5 D 
        6 E 
        7 Letter 
        8 Legal 
        9 NA-10x13-Envelope 
        10 NA-9x12-Envelope 
        11 NA-Number-10-Envelope 
        12 NA-7x9-Envelope 
        13 NA-9x11-Envelope 
        14 NA-10x14-Envelope 
        15 NA-Number-9-Envelope 
        16 NA-6x9-Envelope 
        17 NA-10x15-Envelope 
        18 A0 
        19 A1 
        20 A2 
        21 A3 
        22 A4 
        23 A5 
        24 A6 
        25 A7 
        26 A8 
        27 A9A10 
        28 B0 
        29 B1 
        30 B2 
        31 B3 
        32 B4 
        33 B5 
        34 B6 
        35 B7 
        36 B8 
        37 B9 
        38 B10 
        39 C0 
        40 C1 
        41 C2 
        42 C3 
        43 C4 
        44 C5 
        45 C6 
        46 C7 
        47 C8 
        48 ISO-Designated 
        49 JIS B0 
        50 JIS B1 
        51 JIS B2 
        52 JIS B3 
        53 JIS B4 
        54 JIS B5 
        55 JIS B6 
        56 JIS B7 
        57 JIS B8 
        58 JIS B9 
        59 JIS B10 "
    ::= { win32PrinterEntry 58 }

hwprPaperTypesAvailable OBJECT-TYPE
    SYNTAX     DisplayString
    MAX-ACCESS read-only
    STATUS     current
    DESCRIPTION
        "Windows XP and Windows Server 2003:  Array of
        paper types that are currently available currently
        on the printer. Each string must be expressed in
        the format specified by ISO/IEC 10175 Document
        Printing Application (DPA), which is summarized in
        Appendix C of RFC 1759 (Printer MIB). Any paper
        size identified in this property must also appear
        in the PaperSizesSupported property. This property
        is inherited from CIM_Printer. 
        Example: iso-a4-colored"
    ::= { win32PrinterEntry 59 }

hwprParameters OBJECT-TYPE
    SYNTAX     DisplayString
    MAX-ACCESS read-only
    STATUS     current
    DESCRIPTION
        "Windows XP and Windows Server 2003:  Optional
        parameters for the print processor.
        Example: Copies=2"
    ::= { win32PrinterEntry 60 }

hwprPNPDeviceID OBJECT-TYPE
    SYNTAX     DisplayString
    MAX-ACCESS read-only
    STATUS     current
    DESCRIPTION
        "Windows plug and play device identifier of the
        logical device. This property is inherited from
        CIM_LogicalDevice.
        Example: *PNP030b"
    ::= { win32PrinterEntry 61 }

hwprPortName OBJECT-TYPE
    SYNTAX     DisplayString
    MAX-ACCESS read-only
    STATUS     current
    DESCRIPTION
        "Port that is used to transmit data to a printer.
        If a printer is connected to more than one port,
        the names of each port are separated by commas.
        Under Windows 95, only one port can be specified.
        Example: LPT1:, LPT2:, LPT3:"
    ::= { win32PrinterEntry 62 }

hwprPowerManagementCapabilities OBJECT-TYPE
    SYNTAX     DisplayString
    MAX-ACCESS read-only
    STATUS     current
    DESCRIPTION
        "Specific power capabilities of a logical device.
        The Enabled value indicates that the power
        management features are currently enabled, but the
        exact setting is unknown or the information is
        unavailable. Power Saving Modes Entered
        Automatically indicates that a device can change
        its power state based on usage or other criteria.
        Power State Settable indicates that the
        SetPowerState method is supported. Power Cycling
        Supported indicates that the SetPowerState method
        can be invoked with the PowerState parameter set to
        5. Timed Power On Supported indicates that the
        SetPowerState method can be invoked with the
        PowerState parameter set to 5 and Time set to a
        specific date and time, or interval to power ON.
        This property is inherited from
        CIM_UnitaryComputerSystem.
        Value Meaning 
        0 Unknown 
        1 Not Supported 
        2 Disabled 
        3 Enabled 
        4 Power Saving Modes Entered Automatically 
        5 Power State Settable 
        6 Power Cycling Supported 
        7 Timed Power On Supported "
    ::= { win32PrinterEntry 63 }

hwprPowerManagementSupported OBJECT-TYPE
    SYNTAX     TruthValue
    MAX-ACCESS read-only
    STATUS     current
    DESCRIPTION
        "If TRUE, the power of the device can be managed,
        which means that it can be put into suspend mode,
        and so on. The property does not indicate that
        power management features are enabled, only that
        the logical device is capable of power management.
        This property is inherited from CIM_LogicalDevice."
    ::= { win32PrinterEntry 64 }

hwprPrinterPaperNames OBJECT-TYPE
    SYNTAX     DisplayString
    MAX-ACCESS read-only
    STATUS     current
    DESCRIPTION
        "Array of paper sizes supported by the printer. The
        printer-specified names are used to represent
        supported paper sizes.
        Example: B5 (JIS)"
    ::= { win32PrinterEntry 65 }

hwprPrinterState OBJECT-TYPE
    SYNTAX     INTEGER {
        paused(1),
        error(2),
        pendingDeletion(3),
        paperJam(4),
        paperOut(5),
        manualFeed(6),
        paperProblem(7),
        offline(8),
        ioActive(9),
        busy(10),
        printing(11),
        outputBinFull(12),
        notAvailable(13),
        waiting(14),
        processing(15),
        initialization(16),
        warmingUp(17),
        tonerLow(18),
        noToner(19),
        pagePunt(20),
        userInterventionRequired(21),
        outOfMemory(22),
        doorOpen(23),
        serverUnknown(24),
        powerSave(25)
    }
    MAX-ACCESS read-only
    STATUS     current
    DESCRIPTION
        "One of the possible states relating to this
        printer. This property is obsolete. In place of
        this property, use PrinterStatus."
    ::= { win32PrinterEntry 66 }

hwprPrinterStatus OBJECT-TYPE
    SYNTAX     INTEGER {
        other(1),
        unknown(2),
        idle(3),
        printing(4),
        warmup(5),
        stoppedPrinting(6),
        offline(7)
    }
    MAX-ACCESS read-only
    STATUS     current
    DESCRIPTION
        "Status information for a printer that is different
        from information specified in the logical device
        Availability property. This property is inherited
        from CIM_Printer."
    ::= { win32PrinterEntry 67 }

hwprPrintJobDataType OBJECT-TYPE
    SYNTAX     DisplayString
    MAX-ACCESS read-only
    STATUS     current
    DESCRIPTION
        "Data type of a print job waiting for the Windows
        printing device."
    ::= { win32PrinterEntry 68 }

hwprPrintProcessor OBJECT-TYPE
    SYNTAX     DisplayString
    MAX-ACCESS read-only
    STATUS     current
    DESCRIPTION
        "Name of the print spooler that handles print jobs.
        Example: SPOOLSS.DLL"
    ::= { win32PrinterEntry 69 }

hwprPriority OBJECT-TYPE
    SYNTAX     Gauge32
    MAX-ACCESS read-only
    STATUS     current
    DESCRIPTION
        "Windows XP and Windows Server 2003:  Priority of
        the printer. Jobs on a higher priority printer are
        scheduled first."
    ::= { win32PrinterEntry 70 }

hwprPublished OBJECT-TYPE
    SYNTAX     TruthValue
    MAX-ACCESS read-only
    STATUS     current
    DESCRIPTION
        "Windows XP and Windows Server 2003:  If TRUE, the
        printer is published in the network directory
        service."
    ::= { win32PrinterEntry 71 }

hwprQueued OBJECT-TYPE
    SYNTAX     TruthValue
    MAX-ACCESS read-only
    STATUS     current
    DESCRIPTION
        "Windows XP and Windows Server 2003:  If TRUE, the
        printer buffers and queues print jobs."
    ::= { win32PrinterEntry 72 }

hwprRawOnly OBJECT-TYPE
    SYNTAX     TruthValue
    MAX-ACCESS read-only
    STATUS     current
    DESCRIPTION
        "Windows XP and Windows Server 2003:  If TRUE, the
        printer accepts only raw data to be spooled."
    ::= { win32PrinterEntry 73 }

hwprSeparatorFile OBJECT-TYPE
    SYNTAX     DisplayString
    MAX-ACCESS read-only
    STATUS     current
    DESCRIPTION
        "Name of the file used to create a separator page.
        This page is used to separate print jobs sent to
        the printer."
    ::= { win32PrinterEntry 74 }

hwprServerName OBJECT-TYPE
    SYNTAX     DisplayString
    MAX-ACCESS read-only
    STATUS     current
    DESCRIPTION
        "Name of the server that controls the printer. If
        this string is NULL, the printer is controlled
        locally."
    ::= { win32PrinterEntry 75 }

hwprShared OBJECT-TYPE
    SYNTAX     TruthValue
    MAX-ACCESS read-only
    STATUS     current
    DESCRIPTION
        "Windows XP and Windows Server 2003:  If TRUE, the
        printer is available as a shared network resource."
    ::= { win32PrinterEntry 76 }

hwprShareName OBJECT-TYPE
    SYNTAX     DisplayString
    MAX-ACCESS read-only
    STATUS     current
    DESCRIPTION
        "Share name of the Windows printing device.
        Example: \\PRINTSERVER1\PRINTER2"
    ::= { win32PrinterEntry 77 }

hwprSpoolEnabled OBJECT-TYPE
    SYNTAX     TruthValue
    MAX-ACCESS read-only
    STATUS     current
    DESCRIPTION
        "This property is obsolete; do not use. If TRUE,
        spooling is enabled for printer."
    ::= { win32PrinterEntry 78 }

hwprStartTime OBJECT-TYPE
    SYNTAX     DateAndTime
    MAX-ACCESS read-only
    STATUS     current
    DESCRIPTION
        "Date and time that a printer can start to print a
        job if the printer is limited to print at specific
        times. This value is expressed as the time elapsed
        since 12:00 AM GMT (Greenwich mean time)."
    ::= { win32PrinterEntry 79 }

hwprStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror- resilvering
        of a disk, reload of a user permissions list, or
        other administrative work. Not all such work is
        on-line, yet the managed element is neither 'OK'
        nor in one of the other states. This property is
        inherited from CIM_ManagedSystemElement."
    ::= { win32PrinterEntry 80 }

hwprStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32PrinterEntry 81 }

hwprSystemCreationClassName OBJECT-TYPE
    SYNTAX     DisplayString
    MAX-ACCESS read-only
    STATUS     current
    DESCRIPTION
        "Value of the scoping computer's CreationClassName
        property. This property is inherited from
        CIM_LogicalDevice."
    ::= { win32PrinterEntry 82 }

hwprSystemName OBJECT-TYPE
    SYNTAX     DisplayString
    MAX-ACCESS read-only
    STATUS     current
    DESCRIPTION
        "Name of the scoping system. This property is
        inherited from CIM_LogicalDevice."
    ::= { win32PrinterEntry 83 }

hwprTimeOfLastReset OBJECT-TYPE
    SYNTAX     DateAndTime
    MAX-ACCESS read-only
    STATUS     current
    DESCRIPTION
        "Date and time the printer was last reset. This
        property is inherited from CIM_Printer."
    ::= { win32PrinterEntry 84 }

hwprUntilTime OBJECT-TYPE
    SYNTAX     DateAndTime
    MAX-ACCESS read-only
    STATUS     current
    DESCRIPTION
        "Date and time that a printer can print the last
        job if the printer is limited to print at specific
        times. This value is expressed as the time elapsed
        since 12:00 AM GMT (Greenwich mean time)."
    ::= { win32PrinterEntry 85 }

hwprVerticalResolution OBJECT-TYPE
    SYNTAX     Gauge32
    MAX-ACCESS read-only
    STATUS     current
    DESCRIPTION
        "Vertical resolution of the printer in pixels per
        inch. This property is inherited from CIM_Printer."
    ::= { win32PrinterEntry 86 }

hwprWorkOffline OBJECT-TYPE
    SYNTAX     TruthValue
    MAX-ACCESS read-only
    STATUS     current
    DESCRIPTION
        "Windows XP and Windows Server 2003:  If TRUE, you
        can queue print jobs on the computer when the
        printer is offline."
    ::= { win32PrinterEntry 87 }

win32PrinterConfigurationTable OBJECT-TYPE
    SYNTAX     SEQUENCE OF Win32PrinterConfigurationEntry
    MAX-ACCESS not-accessible
    STATUS     current
    DESCRIPTION
        "The Win32_PrinterConfiguration WMI class defines
        the configuration for a printer device. This
        includes capabilities such as resolution, color,
        fonts, and orientation."
    ::= { wmiPrinting 2 }

win32PrinterConfigurationEntry OBJECT-TYPE
    SYNTAX     Win32PrinterConfigurationEntry
    MAX-ACCESS not-accessible
    STATUS     current
    DESCRIPTION
        "None"
    INDEX      { hwprcIndex }
    ::= { win32PrinterConfigurationTable 1 }

Win32PrinterConfigurationEntry ::= SEQUENCE {
    hwprcIndex Integer32,
    hwprcBitsPerPel Gauge32,
    hwprcCaption DisplayString,
    hwprcCollate TruthValue,
    hwprcColor INTEGER,
    hwprcCopies Gauge32,
    hwprcDescription DisplayString,
    hwprcDeviceName DisplayString,
    hwprcDisplayFlags Gauge32,
    hwprcDisplayFrequency Gauge32,
    hwprcDitherType INTEGER,
    hwprcDriverVersion Gauge32,
    hwprcDuplex TruthValue,
    hwprcFormName DisplayString,
    hwprcHorizontalResolution Gauge32,
    hwprcICMIntent INTEGER,
    hwprcICMMethod INTEGER,
    hwprcLogPixels Gauge32,
    hwprcMediaType INTEGER,
    hwprcName DisplayString,
    hwprcOrientation INTEGER,
    hwprcPaperLength Gauge32,
    hwprcPaperSize DisplayString,
    hwprcPaperWidth Gauge32,
    hwprcPelsHeight Gauge32,
    hwprcPelsWidth Gauge32,
    hwprcPrintQuality Gauge32,
    hwprcScale Gauge32,
    hwprcSettingID DisplayString,
    hwprcSpecificationVersion Gauge32,
    hwprcTTOption INTEGER,
    hwprcVerticalResolution Gauge32,
    hwprcXResolution Gauge32,
    hwprcYResolution Gauge32
}

hwprcIndex OBJECT-TYPE
    SYNTAX     Integer32 (1..2147483647)
    MAX-ACCESS read-only
    STATUS     current
    DESCRIPTION
        "The value of this object uniquely identifies the
        instance entry for this class."
    ::= { win32PrinterConfigurationEntry 1 }

hwprcBitsPerPel OBJECT-TYPE
    SYNTAX     Gauge32
    MAX-ACCESS read-only
    STATUS     current
    DESCRIPTION
        "This property must not be used."
    ::= { win32PrinterConfigurationEntry 2 }

hwprcCaption OBJECT-TYPE
    SYNTAX     DisplayString (SIZE (0..64))
    MAX-ACCESS read-only
    STATUS     current
    DESCRIPTION
        "Short description (one-line string) of the
        CIM_Setting object. This property is inherited from
        CIM_Setting."
    ::= { win32PrinterConfigurationEntry 3 }

hwprcCollate OBJECT-TYPE
    SYNTAX     TruthValue
    MAX-ACCESS read-only
    STATUS     current
    DESCRIPTION
        "If TRUE, the pages that are printed should be
        collated. To collate is to print out the entire
        document before printing the next copy, as opposed
        to printing out each page of the document the
        required number of times. This property is ignored
        unless the printer driver indicates support for
        collation."
    ::= { win32PrinterConfigurationEntry 4 }

hwprcColor OBJECT-TYPE
    SYNTAX     INTEGER {
        monochrome(1),
        color(2)
    }
    MAX-ACCESS read-only
    STATUS     current
    DESCRIPTION
        "Color of the document. Some color printers have
        the capability to print using true black instead of
        a combination of cyan, magenta, and yellow (CMY).
        This usually creates darker and sharper text for
        documents. This option is only useful for color
        printers that support true black printing."
    ::= { win32PrinterConfigurationEntry 5 }

hwprcCopies OBJECT-TYPE
    SYNTAX     Gauge32
    MAX-ACCESS read-only
    STATUS     current
    DESCRIPTION
        "Number of copies to be printed. The printer driver
        must support printing multi-page copies.
        Example: 2"
    ::= { win32PrinterConfigurationEntry 6 }

hwprcDescription OBJECT-TYPE
    SYNTAX     DisplayString
    MAX-ACCESS read-only
    STATUS     current
    DESCRIPTION
        "Description of the CIM_Setting object. This
        property is inherited from CIM_Setting."
    ::= { win32PrinterConfigurationEntry 7 }

hwprcDeviceName OBJECT-TYPE
    SYNTAX     DisplayString
    MAX-ACCESS read-only
    STATUS     current
    DESCRIPTION
        "Friendly name of the printer. This name is unique
        to the type of printer and may be truncated because
        of the limitations of the string from which it is
        derived.
        Example: 'PCL/HP LaserJet'"
    ::= { win32PrinterConfigurationEntry 8 }

hwprcDisplayFlags OBJECT-TYPE
    SYNTAX     Gauge32
    MAX-ACCESS read-only
    STATUS     current
    DESCRIPTION
        "This property must not be used."
    ::= { win32PrinterConfigurationEntry 9 }

hwprcDisplayFrequency OBJECT-TYPE
    SYNTAX     Gauge32
    MAX-ACCESS read-only
    STATUS     current
    DESCRIPTION
        "This property must not be used."
    ::= { win32PrinterConfigurationEntry 10 }

hwprcDitherType OBJECT-TYPE
    SYNTAX     INTEGER {
        noDithering(1),
        coarseBrush(2),
        fineBrush(3),
        lineArt(4),
        greyscale(5)
    }
    MAX-ACCESS read-only
    STATUS     current
    DESCRIPTION
        "Dither type of the printer. This property can
        assume predefined values of 1 to 5, or
        driver-defined values from 6 to 256. Line art
        dithering is a special dithering method that
        produces well defined borders between black, white,
        and gray scalings. It is not suitable for images
        that include continuous graduations in intensity
        and hue such as scanned photographs."
    ::= { win32PrinterConfigurationEntry 11 }

hwprcDriverVersion OBJECT-TYPE
    SYNTAX     Gauge32
    MAX-ACCESS read-only
    STATUS     current
    DESCRIPTION
        "Version number of the Windows printer driver. The
        version numbers are created and maintained by the
        driver manufacturer."
    ::= { win32PrinterConfigurationEntry 12 }

hwprcDuplex OBJECT-TYPE
    SYNTAX     TruthValue
    MAX-ACCESS read-only
    STATUS     current
    DESCRIPTION
        "If TRUE, printing is done on both sides. If FALSE,
        printing is done on only one side of the media."
    ::= { win32PrinterConfigurationEntry 13 }

hwprcFormName OBJECT-TYPE
    SYNTAX     DisplayString
    MAX-ACCESS read-only
    STATUS     current
    DESCRIPTION
        "Name of the form used for the print job. This
        property is used only on Windows NT/Windows 2000
        systems.
        Example: 'Legal'"
    ::= { win32PrinterConfigurationEntry 14 }

hwprcHorizontalResolution OBJECT-TYPE
    SYNTAX     Gauge32
    UNITS "dots per inch"
    MAX-ACCESS read-only
    STATUS     current
    DESCRIPTION
        "Print resolution in dots per inch along the X axis
        (width) of the print job (similar to the obsolete
        XResolution property). This value is only set when
        the PrintQuality property of this class is
        positive."
    ::= { win32PrinterConfigurationEntry 15 }

hwprcICMIntent OBJECT-TYPE
    SYNTAX     INTEGER {
        saturation(1),
        contrast(2),
        exactColor(3)
    }
    MAX-ACCESS read-only
    STATUS     current
    DESCRIPTION
        "Specific value of one of the three possible color
        matching methods (called intents) that should be
        used by default. ICM applications establish intents
        by using the ICM functions. This property can
        assume predefined values of 1 to 3, or
        driver-defined values from 4 to 256. Non-ICM
        applications can use this value to determine how
        the printer handles color printing jobs."
    ::= { win32PrinterConfigurationEntry 16 }

hwprcICMMethod OBJECT-TYPE
    SYNTAX     INTEGER {
        disabled(1),
        windows(2),
        deviceDriver(3),
        device(4)
    }
    MAX-ACCESS read-only
    STATUS     current
    DESCRIPTION
        "How ICM is handled. For a non-ICM application,
        this property determines if ICM is enabled or
        disabled. For ICM applications, the system examines
        this property to determine which part of the
        computer system handles ICM support."
    ::= { win32PrinterConfigurationEntry 17 }

hwprcLogPixels OBJECT-TYPE
    SYNTAX     Gauge32
    MAX-ACCESS read-only
    STATUS     current
    DESCRIPTION
        "This property must not be used."
    ::= { win32PrinterConfigurationEntry 18 }

hwprcMediaType OBJECT-TYPE
    SYNTAX     INTEGER {
        standard(1),
        transparency(2),
        glossy(3)
    }
    MAX-ACCESS read-only
    STATUS     current
    DESCRIPTION
        "Type of media being printed on. The property can
        be set to a predefined value or a driver-defined
        value greater than or equal to 256. This property
        is supported in Windows 95 and later."
    ::= { win32PrinterConfigurationEntry 19 }

hwprcName OBJECT-TYPE
    SYNTAX     DisplayString (SIZE (0..256))
    MAX-ACCESS read-only
    STATUS     current
    DESCRIPTION
        "Name of the printer with which this configuration
        is associated."
    ::= { win32PrinterConfigurationEntry 20 }

hwprcOrientation OBJECT-TYPE
    SYNTAX     INTEGER {
        portrait(1),
        landscape(2)
    }
    MAX-ACCESS read-only
    STATUS     current
    DESCRIPTION
        "Printing orientation of the paper."
    ::= { win32PrinterConfigurationEntry 21 }

hwprcPaperLength OBJECT-TYPE
    SYNTAX     Gauge32
    UNITS "Tenths of a Millimeter"
    MAX-ACCESS read-only
    STATUS     current
    DESCRIPTION
        "Length of the paper.
        Example: 2794"
    ::= { win32PrinterConfigurationEntry 22 }

hwprcPaperSize OBJECT-TYPE
    SYNTAX     DisplayString
    MAX-ACCESS read-only
    STATUS     current
    DESCRIPTION
        "Size of the paper.
        Example: 'A4 or Letter'"
    ::= { win32PrinterConfigurationEntry 23 }

hwprcPaperWidth OBJECT-TYPE
    SYNTAX     Gauge32
    UNITS "Tenths of a Millimeter"
    MAX-ACCESS read-only
    STATUS     current
    DESCRIPTION
        "Width of the paper.
        Example: 2159"
    ::= { win32PrinterConfigurationEntry 24 }

hwprcPelsHeight OBJECT-TYPE
    SYNTAX     Gauge32
    MAX-ACCESS read-only
    STATUS     current
    DESCRIPTION
        "This property must not be used."
    ::= { win32PrinterConfigurationEntry 25 }

hwprcPelsWidth OBJECT-TYPE
    SYNTAX     Gauge32
    MAX-ACCESS read-only
    STATUS     current
    DESCRIPTION
        "This property must not be used."
    ::= { win32PrinterConfigurationEntry 26 }

hwprcPrintQuality OBJECT-TYPE
    SYNTAX     Gauge32
    MAX-ACCESS read-only
    STATUS     current
    DESCRIPTION
        "One of four quality levels of the print job. If a
        positive value is specified, the quality is
        measured in dots per inch."
    ::= { win32PrinterConfigurationEntry 27 }

hwprcScale OBJECT-TYPE
    SYNTAX     Gauge32
    UNITS "Percent"
    MAX-ACCESS read-only
    STATUS     current
    DESCRIPTION
        "Factor by which the printed output is to be
        scaled. For example, a scale of 75 reduces the
        print output to 3/4 its original height and width."
    ::= { win32PrinterConfigurationEntry 28 }

hwprcSettingID OBJECT-TYPE
    SYNTAX     DisplayString (SIZE (0..256))
    MAX-ACCESS read-only
    STATUS     current
    DESCRIPTION
        "Identifier by which the CIM_Setting object is
        known. This property is inherited from
        CIM_Setting."
    ::= { win32PrinterConfigurationEntry 29 }

hwprcSpecificationVersion OBJECT-TYPE
    SYNTAX     Gauge32
    MAX-ACCESS read-only
    STATUS     current
    DESCRIPTION
        "Version number of the initialization data for the
        device associated with the Windows printer."
    ::= { win32PrinterConfigurationEntry 30 }

hwprcTTOption OBJECT-TYPE
    SYNTAX     INTEGER {
        bitmap (1), -- Prints TrueType fonts as graphics. This is the default action for dot-matrix printers.
        download (2), -- Downloads TrueType fonts as soft fonts. This is the default action for printers that use the Printer Control Language (PCL).
        substitute (3) -- Substitutes device fonts for TrueType fonts. This is the default action for PostScript printers.
    }
    MAX-ACCESS read-only
    STATUS     current
    DESCRIPTION
        "How TrueType fonts should be printed."
    ::= { win32PrinterConfigurationEntry 31 }

hwprcVerticalResolution OBJECT-TYPE
    SYNTAX     Gauge32
    UNITS "dots per inch"
    MAX-ACCESS read-only
    STATUS     current
    DESCRIPTION
        "Print resolution along the Y axis (height) of the
        print job (similar to the obsolete YResolution
        property). This value is only set when the
        PrintQuality property of this class is positive."
    ::= { win32PrinterConfigurationEntry 32 }

hwprcXResolution OBJECT-TYPE
    SYNTAX     Gauge32
    MAX-ACCESS read-only
    STATUS     current
    DESCRIPTION
        "This property must not be used."
    ::= { win32PrinterConfigurationEntry 33 }

hwprcYResolution OBJECT-TYPE
    SYNTAX     Gauge32
    MAX-ACCESS read-only
    STATUS     current
    DESCRIPTION
        "This property must not be used."
    ::= { win32PrinterConfigurationEntry 34 }

win32PrinterDriverTable OBJECT-TYPE
    SYNTAX     SEQUENCE OF Win32PrinterDriverEntry
    MAX-ACCESS not-accessible
    STATUS     current
    DESCRIPTION
        "The Win32_PrinterDriver WMI class represents the
        drivers for a Win32_Printer instance. This class is
        new for Windows XP."
    ::= { wmiPrinting 3 }

win32PrinterDriverEntry OBJECT-TYPE
    SYNTAX     Win32PrinterDriverEntry
    MAX-ACCESS not-accessible
    STATUS     current
    DESCRIPTION
        "None"
    INDEX      { hwprdIndex }
    ::= { win32PrinterDriverTable 1 }

Win32PrinterDriverEntry ::= SEQUENCE {
    hwprdIndex Integer32,
    hwprdCaption DisplayString,
    hwprdConfigFile DisplayString,
    hwprdCreationClassName DisplayString,
    hwprdDataFile DisplayString,
    hwprdDefaultDataType DisplayString,
    hwprdDependentFiles DisplayString,
    hwprdDescription DisplayString,
    hwprdDriverPath DisplayString,
    hwprdFilePath DisplayString,
    hwprdHelpFile DisplayString,
    hwprdInfName DisplayString,
    hwprdInstallDate DateAndTime,
    hwprdMonitorName DisplayString,
    hwprdName DisplayString,
    hwprdOEMUrl DisplayString,
    hwprdStarted TruthValue,
    hwprdStartMode INTEGER,
    hwprdStatus INTEGER,
    hwprdSupportedPlatform DisplayString,
    hwprdSystemCreationClassName DisplayString,
    hwprdSystemName DisplayString,
    hwprdVersion INTEGER
}

hwprdIndex OBJECT-TYPE
    SYNTAX     Integer32 (1..2147483647)
    MAX-ACCESS read-only
    STATUS     current
    DESCRIPTION
        "The value of this object uniquely identifies the
        instance entry for this class."
    ::= { win32PrinterDriverEntry 1 }

hwprdCaption OBJECT-TYPE
    SYNTAX     DisplayString (SIZE (0..64))
    MAX-ACCESS read-only
    STATUS     current
    DESCRIPTION
        "Short description of the object a one-line string.
        This property is inherited from
        CIM_ManagedSystemElement."
    ::= { win32PrinterDriverEntry 2 }

hwprdConfigFile OBJECT-TYPE
    SYNTAX     DisplayString
    MAX-ACCESS read-only
    STATUS     current
    DESCRIPTION
        "Configuration file for this printer driver.
        Example: 'pscrptui.dll'"
    ::= { win32PrinterDriverEntry 3 }

hwprdCreationClassName OBJECT-TYPE
    SYNTAX     DisplayString
    MAX-ACCESS read-only
    STATUS     current
    DESCRIPTION
        "Name of the class or the subclass used in the
        creation of an instance. When used with the other
        key properties of this class, this property allows
        all instances of this class and its subclasses to
        be uniquely identified. This property is inherited
        from CIM_Service."
    ::= { win32PrinterDriverEntry 4 }

hwprdDataFile OBJECT-TYPE
    SYNTAX     DisplayString
    MAX-ACCESS read-only
    STATUS     current
    DESCRIPTION
        "Data file for this printer driver.
        Example: 'qms810.ppd'"
    ::= { win32PrinterDriverEntry 5 }

hwprdDefaultDataType OBJECT-TYPE
    SYNTAX     DisplayString
    MAX-ACCESS read-only
    STATUS     current
    DESCRIPTION
        "Default data type for this printer driver.
        Example: 'EMF'"
    ::= { win32PrinterDriverEntry 6 }

hwprdDependentFiles OBJECT-TYPE
    SYNTAX     DisplayString
    MAX-ACCESS read-only
    STATUS     current
    DESCRIPTION
        "Array of dependent files for this printer driver."
    ::= { win32PrinterDriverEntry 7 }

hwprdDescription OBJECT-TYPE
    SYNTAX     DisplayString
    MAX-ACCESS read-only
    STATUS     current
    DESCRIPTION
        "Comment that describes the link. This property is
        inherited from CIM_ManagedSystemElement."
    ::= { win32PrinterDriverEntry 8 }

hwprdDriverPath OBJECT-TYPE
    SYNTAX     DisplayString
    MAX-ACCESS read-only
    STATUS     current
    DESCRIPTION
        "Path for this printer driver.
        Example: 'C:\\drivers\\pscript.dll'"
    ::= { win32PrinterDriverEntry 9 }

hwprdFilePath OBJECT-TYPE
    SYNTAX     DisplayString
    MAX-ACCESS read-only
    STATUS     current
    DESCRIPTION
        "Path to the INF file being used.
        Example: 'c:\\temp\\driver'"
    ::= { win32PrinterDriverEntry 10 }

hwprdHelpFile OBJECT-TYPE
    SYNTAX     DisplayString
    MAX-ACCESS read-only
    STATUS     current
    DESCRIPTION
        "Help file for this printer driver.
        Example: 'pscrptui.hlp'"
    ::= { win32PrinterDriverEntry 11 }

hwprdInfName OBJECT-TYPE
    SYNTAX     DisplayString
    MAX-ACCESS read-only
    STATUS     current
    DESCRIPTION
        "Name of the INF file being used. The default is
        'ntprint.INF'. This will only be different if the
        drivers are provided directly by the manufacturer
        of the printer and not the operating system."
    ::= { win32PrinterDriverEntry 12 }

hwprdInstallDate OBJECT-TYPE
    SYNTAX     DateAndTime
    MAX-ACCESS read-only
    STATUS     current
    DESCRIPTION
        "Date and time when the object is installed. This
        property does not need a value to indicate that the
        object is installed. This property is inherited
        from CIM_ManagedSystemElement."
    ::= { win32PrinterDriverEntry 13 }

hwprdMonitorName OBJECT-TYPE
    SYNTAX     DisplayString
    MAX-ACCESS read-only
    STATUS     current
    DESCRIPTION
        "Name of the monitor for this printer driver.
        Example: 'PJL monitor'"
    ::= { win32PrinterDriverEntry 14 }

hwprdName OBJECT-TYPE
    SYNTAX     DisplayString
    MAX-ACCESS read-only
    STATUS     current
    DESCRIPTION
        "Driver name for this printer. This is a compound
        key composed of the Name, Version, and
        SupportedPlatform values. This property is
        inherited from CIM_ManagedSystemElement and
        overrides the Name definition in that class."
    ::= { win32PrinterDriverEntry 15 }

hwprdOEMUrl OBJECT-TYPE
    SYNTAX     DisplayString
    MAX-ACCESS read-only
    STATUS     current
    DESCRIPTION
        "World Wide Web (WWW) link to the printer
        manufacturer's Web site. Note that this property is
        not populated when the Win32.inf file is used, and
        is only applicable for drivers provided directly
        from the manufacturer."
    ::= { win32PrinterDriverEntry 16 }

hwprdStarted OBJECT-TYPE
    SYNTAX     TruthValue
    MAX-ACCESS read-only
    STATUS     current
    DESCRIPTION
        "If TRUE, the service is started. If FALSE, the
        service is stopped. This property is inherited from
        CIM_Service."
    ::= { win32PrinterDriverEntry 17 }

hwprdStartMode OBJECT-TYPE
    SYNTAX     INTEGER {
        automatic(1),
        manual(2)
    }
    MAX-ACCESS read-only
    STATUS     current
    DESCRIPTION
        "Start mode of the service is automatically started
        by an operating system, or only started when
        requested. This property is inherited from
        CIM_Service."
    ::= { win32PrinterDriverEntry 18 }

hwprdStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PrinterDriverEntry 19 }

hwprdSupportedPlatform OBJECT-TYPE
    SYNTAX     DisplayString
    MAX-ACCESS read-only
    STATUS     current
    DESCRIPTION
        "Operating environments that the driver is intended
        for.
        Example: 'Windows NT x86' or 'Windows IA64'"
    ::= { win32PrinterDriverEntry 20 }

hwprdSystemCreationClassName OBJECT-TYPE
    SYNTAX     DisplayString
    MAX-ACCESS read-only
    STATUS     current
    DESCRIPTION
        "Scoping system's creation class name. This
        property is inherited from CIM_Service."
    ::= { win32PrinterDriverEntry 21 }

hwprdSystemName OBJECT-TYPE
    SYNTAX     DisplayString
    MAX-ACCESS read-only
    STATUS     current
    DESCRIPTION
        "Name of the system that hosts this service. This
        property is inherited from CIM_Service."
    ::= { win32PrinterDriverEntry 22 }

hwprdVersion OBJECT-TYPE
    SYNTAX     INTEGER {
        win9x(0),
        win351(1),
        nt40(2),
        win2k(3)
    }
    MAX-ACCESS read-only
    STATUS     current
    DESCRIPTION
        "Operating system version for the printer driver."
    ::= { win32PrinterDriverEntry 23 }

win32PrintJobTable OBJECT-TYPE
    SYNTAX     SEQUENCE OF Win32PrintJobEntry
    MAX-ACCESS not-accessible
    STATUS     current
    DESCRIPTION
        "The Win32_PrintJob WMI class represents a print
        job that a Windows application generates. Any unit
        of work generated by the print command of an
        application that is running on a Windows system is
        a descendent or member of this class."
    ::= { wmiPrinting 4 }

win32PrintJobEntry OBJECT-TYPE
    SYNTAX     Win32PrintJobEntry
    MAX-ACCESS not-accessible
    STATUS     current
    DESCRIPTION
        "None"
    INDEX      { hwprjIndex }
    ::= { win32PrintJobTable 1 }

Win32PrintJobEntry ::= SEQUENCE {
    hwprjIndex Integer32,
    hwprjCaption DisplayString,
    hwprjDataType DisplayString,
    hwprjDescription DisplayString,
    hwprjDocument DisplayString,
    hwprjDriverName DisplayString,
    hwprjElapsedTime DateAndTime,
    hwprjHostPrintQueue DisplayString,
    hwprjInstallDate DateAndTime,
    hwprjJobId Gauge32,
    hwprjJobStatus INTEGER,
    hwprjName DisplayString,
    hwprjNotify DisplayString,
    hwprjOwner DisplayString,
    hwprjPagesPrinted Gauge32,
    hwprjParameters DisplayString,
    hwprjPrintProcessor DisplayString,
    hwprjPriority Gauge32,
    hwprjSize Gauge32,
    hwprjStartTime DateAndTime,
    hwprjStatus INTEGER,
    hwprjStatusMask INTEGER,
    hwprjTimeSubmitted DateAndTime,
    hwprjTotalPages Gauge32,
    hwprjUntilTime DateAndTime
}

hwprjIndex OBJECT-TYPE
    SYNTAX     Integer32 (1..2147483647)
    MAX-ACCESS read-only
    STATUS     current
    DESCRIPTION
        "The value of this object uniquely identifies the
        instance entry for this class."
    ::= { win32PrintJobEntry 1 }

hwprjCaption OBJECT-TYPE
    SYNTAX     DisplayString (SIZE (0..64))
    MAX-ACCESS read-only
    STATUS     current
    DESCRIPTION
        "Short description of the object a one-line string.
        This property is inherited from
        CIM_ManagedSystemElement."
    ::= { win32PrintJobEntry 2 }

hwprjDataType OBJECT-TYPE
    SYNTAX     DisplayString
    MAX-ACCESS read-only
    STATUS     current
    DESCRIPTION
        "Format of the data for this print job. This
        instructs the printer driver to translate the data
        (generic text, PostScript, or PCL) before printing,
        or print in a raw format (for graphics and
        pictures).
        Example: 'TEXT'"
    ::= { win32PrintJobEntry 3 }

hwprjDescription OBJECT-TYPE
    SYNTAX     DisplayString
    MAX-ACCESS read-only
    STATUS     current
    DESCRIPTION
        "Description of the object. This property is
        inherited from CIM_ManagedSystemElement."
    ::= { win32PrintJobEntry 4 }

hwprjDocument OBJECT-TYPE
    SYNTAX     DisplayString
    MAX-ACCESS read-only
    STATUS     current
    DESCRIPTION
        "Name of the print job. The user sees this name
        when viewing documents that are waiting to be
        printed.
        Example: 'Microsoft Word - Review.doc'"
    ::= { win32PrintJobEntry 5 }

hwprjDriverName OBJECT-TYPE
    SYNTAX     DisplayString
    MAX-ACCESS read-only
    STATUS     current
    DESCRIPTION
        "Name of the printer driver used for the print
        job."
    ::= { win32PrintJobEntry 6 }

hwprjElapsedTime OBJECT-TYPE
    SYNTAX     DateAndTime
    MAX-ACCESS read-only
    STATUS     current
    DESCRIPTION
        "Length of time that the job has been executing.
        This property is inherited from CIM_Job."
    ::= { win32PrintJobEntry 7 }

hwprjHostPrintQueue OBJECT-TYPE
    SYNTAX     DisplayString
    MAX-ACCESS read-only
    STATUS     current
    DESCRIPTION
        "Name of the computer on which the print job is
        created."
    ::= { win32PrintJobEntry 8 }

hwprjInstallDate OBJECT-TYPE
    SYNTAX     DateAndTime
    MAX-ACCESS read-only
    STATUS     current
    DESCRIPTION
        "Date and time the object is installed. This
        property does not need a value to indicate that the
        object is installed. This property is inherited
        from CIM_ManagedSystemElement."
    ::= { win32PrintJobEntry 9 }

hwprjJobId OBJECT-TYPE
    SYNTAX     Gauge32
    MAX-ACCESS read-only
    STATUS     current
    DESCRIPTION
        "Identifier number of the job. It is used by other
        methods as a handle to a job spooling to the
        printer."
    ::= { win32PrintJobEntry 10 }

hwprjJobStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Free-form string that represents the job status.
        This property is inherited from CIM_Job."
    ::= { win32PrintJobEntry 11 }

hwprjName OBJECT-TYPE
    SYNTAX     DisplayString
    MAX-ACCESS read-only
    STATUS     current
    DESCRIPTION
        "Name of the printer to which the print job is
        being spooled. This property is inherited from
        CIM_ManagedSystemElement."
    ::= { win32PrintJobEntry 12 }

hwprjNotify OBJECT-TYPE
    SYNTAX     DisplayString
    MAX-ACCESS read-only
    STATUS     current
    DESCRIPTION
        "User is to be notified when job completes or
        fails. This property is restricted to 16 characters
        in Windows 95/98 platforms. This property is
        inherited from CIM_Job."
    ::= { win32PrintJobEntry 13 }

hwprjOwner OBJECT-TYPE
    SYNTAX     DisplayString
    MAX-ACCESS read-only
    STATUS     current
    DESCRIPTION
        "User that submitted the job. This property is
        inherited from CIM_Job."
    ::= { win32PrintJobEntry 14 }

hwprjPagesPrinted OBJECT-TYPE
    SYNTAX     Gauge32
    MAX-ACCESS read-only
    STATUS     current
    DESCRIPTION
        "Number of pages that are printed. This value may
        be 0 (zero) if the print job does not contain page
        delimiting information."
    ::= { win32PrintJobEntry 15 }

hwprjParameters OBJECT-TYPE
    SYNTAX     DisplayString
    MAX-ACCESS read-only
    STATUS     current
    DESCRIPTION
        "Optional parameters to send to the print
        processor. For more information, see the
        PrintProcessor property."
    ::= { win32PrintJobEntry 16 }

hwprjPrintProcessor OBJECT-TYPE
    SYNTAX     DisplayString
    MAX-ACCESS read-only
    STATUS     current
    DESCRIPTION
        "Print processor service used to process the print
        job. A printer processor works in conjunction with
        the printer driver to provide additional
        translation of printer data for the printer, and
        can also be used to provide special options such as
        a title page for the job."
    ::= { win32PrintJobEntry 17 }

hwprjPriority OBJECT-TYPE
    SYNTAX     Gauge32
    MAX-ACCESS read-only
    STATUS     current
    DESCRIPTION
        "Urgency or importance of job execution. This
        property is inherited from CIM_Job."
    ::= { win32PrintJobEntry 18 }

hwprjSize OBJECT-TYPE
    SYNTAX     Gauge32
    UNITS "Bytes"
    MAX-ACCESS read-only
    STATUS     current
    DESCRIPTION
        "Size of the print job."
    ::= { win32PrintJobEntry 19 }

hwprjStartTime OBJECT-TYPE
    SYNTAX     DateAndTime
    MAX-ACCESS read-only
    STATUS     current
    DESCRIPTION
        "Date and time that the job begins. This property
        is inherited from CIM_Job."
    ::= { win32PrintJobEntry 20 }

hwprjStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32PrintJobEntry 21 }

hwprjStatusMask OBJECT-TYPE
    SYNTAX     INTEGER {
        paused(1),
        error(2),
        deleting(4),
        spooling(8),
        printing(16),
        offline(32),
        paperout(64),
        printed(128),
        deleted(256),
        blockedDevQ(512),
        userInterventionReq(1024),
        restart(2948)
    }
    MAX-ACCESS read-only
    STATUS     current
    DESCRIPTION
        "Bitmap of the possible statuses that relate to
        this print job."
    ::= { win32PrintJobEntry 22 }

hwprjTimeSubmitted OBJECT-TYPE
    SYNTAX     DateAndTime
    MAX-ACCESS read-only
    STATUS     current
    DESCRIPTION
        "Time that the job is submitted. This property is
        inherited from CIM_Job."
    ::= { win32PrintJobEntry 23 }

hwprjTotalPages OBJECT-TYPE
    SYNTAX     Gauge32
    MAX-ACCESS read-only
    STATUS     current
    DESCRIPTION
        "Number of pages required to complete the job. This
        value may be 0 (zero) if the print job does not
        contain page-delimiting information."
    ::= { win32PrintJobEntry 24 }

hwprjUntilTime OBJECT-TYPE
    SYNTAX     DateAndTime
    MAX-ACCESS read-only
    STATUS     current
    DESCRIPTION
        "Time when the job is invalid or should be stopped.
        This property is inherited from CIM_Job."
    ::= { win32PrintJobEntry 25 }

win32TCPIPPrinterPortTable OBJECT-TYPE
    SYNTAX     SEQUENCE OF Win32TCPIPPrinterPortEntry
    MAX-ACCESS not-accessible
    STATUS     current
    DESCRIPTION
        "The Win32_TCPIPPrinterPort WMI class represents a
        TCP/IP service access point. This class has been
        added for Windows XP."
    ::= { wmiPrinting 5 }

win32TCPIPPrinterPortEntry OBJECT-TYPE
    SYNTAX     Win32TCPIPPrinterPortEntry
    MAX-ACCESS not-accessible
    STATUS     current
    DESCRIPTION
        "None"
    INDEX      { hwtppIndex }
    ::= { win32TCPIPPrinterPortTable 1 }

Win32TCPIPPrinterPortEntry ::= SEQUENCE {
    hwtppIndex Integer32,
    hwtppByteCount TruthValue,
    hwtppCaption DisplayString,
    hwtppCreationClassName DisplayString,
    hwtppDescription DisplayString,
    hwtppHostAddress DisplayString,
    hwtppInstallDate DateAndTime,
    hwtppName DisplayString,
    hwtppPortNumber Gauge32,
    hwtppProtocol INTEGER,
    hwtppQueue DisplayString,
    hwtppSNMPCommunity DisplayString,
    hwtppSNMPDevIndex Gauge32,
    hwtppSNMPEnabled TruthValue,
    hwtppStatus INTEGER,
    hwtppSystemCreationClassName DisplayString,
    hwtppSystemName DisplayString,
    hwtppType INTEGER
}

hwtppIndex OBJECT-TYPE
    SYNTAX     Integer32 (1..2147483647)
    MAX-ACCESS read-only
    STATUS     current
    DESCRIPTION
        "The value of this object uniquely identifies the
        instance entry for this class."
    ::= { win32TCPIPPrinterPortEntry 1 }

hwtppByteCount OBJECT-TYPE
    SYNTAX     TruthValue
    MAX-ACCESS read-only
    STATUS     current
    DESCRIPTION
        "If TRUE, the computer counts the bytes in a
        document before sending them to the printer and the
        printer reports back the number of bytes actually
        read. This capability is used for diagnostics when
        missing bytes are detected in the print output."
    ::= { win32TCPIPPrinterPortEntry 2 }

hwtppCaption OBJECT-TYPE
    SYNTAX     DisplayString (SIZE (0..64))
    MAX-ACCESS read-only
    STATUS     current
    DESCRIPTION
        "Short description (one-line string) of the object.
        This property is inherited from
        CIM_ManagedSystemElement."
    ::= { win32TCPIPPrinterPortEntry 3 }

hwtppCreationClassName OBJECT-TYPE
    SYNTAX     DisplayString (SIZE (0..256))
    MAX-ACCESS read-only
    STATUS     current
    DESCRIPTION
        "Name of the class or the subclass used in the
        creation of an instance. When used with the other
        key properties of this class, this property allows
        all instances of this class and its subclasses to
        be uniquely identified. This property is inherited
        from CIM_ServiceAccessPoint."
    ::= { win32TCPIPPrinterPortEntry 4 }

hwtppDescription OBJECT-TYPE
    SYNTAX     DisplayString
    MAX-ACCESS read-only
    STATUS     current
    DESCRIPTION
        "Detailed description of the functionality managed.
        This property is inherited from
        CIM_ManagedSystemElement."
    ::= { win32TCPIPPrinterPortEntry 5 }

hwtppHostAddress OBJECT-TYPE
    SYNTAX     DisplayString
    MAX-ACCESS read-only
    STATUS     current
    DESCRIPTION
        "Address of the device or print server."
    ::= { win32TCPIPPrinterPortEntry 6 }

hwtppInstallDate OBJECT-TYPE
    SYNTAX     DateAndTime
    MAX-ACCESS read-only
    STATUS     current
    DESCRIPTION
        "Date and time when the object was installed. This
        property does not need a value to indicate that the
        object is installed. This property is inherited
        from CIM_ManagedSystemElement."
    ::= { win32TCPIPPrinterPortEntry 7 }

hwtppName OBJECT-TYPE
    SYNTAX     DisplayString (SIZE (0..256))
    MAX-ACCESS read-only
    STATUS     current
    DESCRIPTION
        "Identifier for the service access point that
        provides an indication of the functionality that is
        managed. This functionality is described in more
        detail in the object's Description property. This
        property is inherited from
        CIM_ManagedSystemElement."
    ::= { win32TCPIPPrinterPortEntry 8 }

hwtppPortNumber OBJECT-TYPE
    SYNTAX     Gauge32
    MAX-ACCESS read-only
    STATUS     current
    DESCRIPTION
        "Number of the TCP port used by the port monitor to
        communicate with the device."
    ::= { win32TCPIPPrinterPortEntry 9 }

hwtppProtocol OBJECT-TYPE
    SYNTAX     INTEGER {
        raw(0),
        lpr(1)
    }
    MAX-ACCESS read-only
    STATUS     current
    DESCRIPTION
        "Printing protocol used. Some printers support only
        LPR."
    ::= { win32TCPIPPrinterPortEntry 10 }

hwtppQueue OBJECT-TYPE
    SYNTAX     DisplayString
    MAX-ACCESS read-only
    STATUS     current
    DESCRIPTION
        "Name of the print queue on the server when used
        with the LPR protocol."
    ::= { win32TCPIPPrinterPortEntry 11 }

hwtppSNMPCommunity OBJECT-TYPE
    SYNTAX     DisplayString
    MAX-ACCESS read-only
    STATUS     current
    DESCRIPTION
        "Security level value for the device.
        Example: 'public''"
    ::= { win32TCPIPPrinterPortEntry 12 }

hwtppSNMPDevIndex OBJECT-TYPE
    SYNTAX     Gauge32
    MAX-ACCESS read-only
    STATUS     current
    DESCRIPTION
        "SNMP index number of this device for the SNMP
        agent."
    ::= { win32TCPIPPrinterPortEntry 13 }

hwtppSNMPEnabled OBJECT-TYPE
    SYNTAX     TruthValue
    MAX-ACCESS read-only
    STATUS     current
    DESCRIPTION
        "If TRUE, this printer supports RFC1759 (Simple
        Network Management Protocol) and can provide rich
        status information from the device."
    ::= { win32TCPIPPrinterPortEntry 14 }

hwtppStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32TCPIPPrinterPortEntry 15 }

hwtppSystemCreationClassName OBJECT-TYPE
    SYNTAX     DisplayString (SIZE (0..256))
    MAX-ACCESS read-only
    STATUS     current
    DESCRIPTION
        "Creation class name of the scoping system. This
        property is inherited from CIM_ServiceAccessPoint."
    ::= { win32TCPIPPrinterPortEntry 16 }

hwtppSystemName OBJECT-TYPE
    SYNTAX     DisplayString (SIZE (0..256))
    MAX-ACCESS read-only
    STATUS     current
    DESCRIPTION
        "Name of the scoping system. This property is
        inherited from CIM_ServiceAccessPoint."
    ::= { win32TCPIPPrinterPortEntry 17 }

hwtppType OBJECT-TYPE
    SYNTAX     INTEGER {
        n0x1Write(1),
        n0x2Read(2),
        n0x4Redirected(4),
        n0x8NetAttached(8),
        n0x10Unknown(16)
    }
    MAX-ACCESS read-only
    STATUS     current
    DESCRIPTION
        "Bitmap showing the type of service access point
        (SAP). This property is inherited from
        CIM_ServiceAccessPoint."
    ::= { win32TCPIPPrinterPortEntry 18 }

wmiTelephony OBJECT-IDENTITY
    STATUS     current
    DESCRIPTION
        "The Telephony subcategory groups classes that
        represent 'plain old telephone' modem devices and
        their associated serial connections."
    ::= { wmiHardware 8 }

win32POTSModemTable OBJECT-TYPE
    SYNTAX     SEQUENCE OF Win32POTSModemEntry
    MAX-ACCESS not-accessible
    STATUS     current
    DESCRIPTION
        "The Win32_POTSModem WMI class represents the
        services and characteristics of a Plain Old
        Telephone Service (POTS) modem on a Windows
        system."
    ::= { wmiTelephony 1 }

win32POTSModemEntry OBJECT-TYPE
    SYNTAX     Win32POTSModemEntry
    MAX-ACCESS not-accessible
    STATUS     current
    DESCRIPTION
        "None"
    INDEX      { hwpmIndex }
    ::= { win32POTSModemTable 1 }

Win32POTSModemEntry ::= SEQUENCE {
    hwpmIndex Integer32,
    hwpmAnswerMode INTEGER,
    hwpmAttachedTo DisplayString,
    hwpmAvailability INTEGER,
    hwpmBlindOff DisplayString,
    hwpmBlindOn DisplayString,
    hwpmCaption DisplayString,
    hwpmCompatibilityFlags DisplayString,
    hwpmCompressionInfo INTEGER,
    hwpmCompressionOff DisplayString,
    hwpmCompressionOn DisplayString,
    hwpmConfigManagerErrorCode INTEGER,
    hwpmConfigManagerUserConfig TruthValue,
    hwpmConfigurationDialog DisplayString,
    hwpmCountriesSupported DisplayString,
    hwpmCountrySelected DisplayString,
    hwpmCreationClassName DisplayString,
    hwpmCurrentPasswords DisplayString,
    hwpmDCB DisplayString,
    hwpmDefault DisplayString,
    hwpmDescription DisplayString,
    hwpmDeviceID DisplayString,
    hwpmDeviceLoader DisplayString,
    hwpmDeviceType INTEGER,
    hwpmDialType INTEGER,
    hwpmDriverDate DateAndTime,
    hwpmErrorCleared TruthValue,
    hwpmErrorControlForced DisplayString,
    hwpmErrorControlInfo INTEGER,
    hwpmErrorControlOff DisplayString,
    hwpmErrorControlOn DisplayString,
    hwpmErrorDescription DisplayString,
    hwpmFlowControlHard DisplayString,
    hwpmFlowControlOff DisplayString,
    hwpmFlowControlSoft DisplayString,
    hwpmInactivityScale DisplayString,
    hwpmInactivityTimeout Gauge32,
    hwpmModemIndex Gauge32,
    hwpmInstallDate DateAndTime,
    hwpmLastErrorCode Gauge32,
    hwpmMaxBaudRateToPhone Gauge32,
    hwpmMaxBaudRateToSerialPort Gauge32,
    hwpmMaxNumberOfPasswords Integer32,
    hwpmModel DisplayString,
    hwpmModemInfPath DisplayString,
    hwpmModemInfSection DisplayString,
    hwpmModulationBell DisplayString,
    hwpmModulationCCITT DisplayString,
    hwpmModulationScheme INTEGER,
    hwpmName DisplayString,
    hwpmPNPDeviceID DisplayString,
    hwpmPortSubClass INTEGER,
    hwpmPowerManagementCapabilities DisplayString,
    hwpmPowerManagementSupported TruthValue,
    hwpmPrefix DisplayString,
    hwpmProperties DisplayString,
    hwpmProviderName DisplayString,
    hwpmPulse DisplayString,
    hwpmReset DisplayString,
    hwpmResponsesKeyName DisplayString,
    hwpmRingsBeforeAnswer Integer32,
    hwpmSpeakerModeDial DisplayString,
    hwpmSpeakerModeOff DisplayString,
    hwpmSpeakerModeOn DisplayString,
    hwpmSpeakerModeSetup DisplayString,
    hwpmSpeakerVolumeHigh DisplayString,
    hwpmSpeakerVolumeInfo INTEGER,
    hwpmSpeakerVolumeLow DisplayString,
    hwpmSpeakerVolumeMed DisplayString,
    hwpmStatus INTEGER,
    hwpmStatusInfo INTEGER,
    hwpmStringFormat DisplayString,
    hwpmSupportsCallback TruthValue,
    hwpmSupportsSynchronousConnect TruthValue,
    hwpmSystemCreationClassName DisplayString,
    hwpmSystemName DisplayString,
    hwpmTerminator DisplayString,
    hwpmTimeOfLastReset DateAndTime,
    hwpmTone DisplayString,
    hwpmVoiceSwitchFeature DisplayString
}

hwpmIndex OBJECT-TYPE
    SYNTAX     Integer32 (1..2147483647)
    MAX-ACCESS read-only
    STATUS     current
    DESCRIPTION
        "The value of this object uniquely identifies the
        instance entry for this class."
    ::= { win32POTSModemEntry 1 }

hwpmAnswerMode OBJECT-TYPE
    SYNTAX     INTEGER {
        unknown(1),
        other(2),
        disabled(3),
        manualAnswer(4),
        autoAnswer(5),
        autoAnswerWithCallBack(6)
    }
    MAX-ACCESS read-only
    STATUS     current
    DESCRIPTION
        "Current auto-answer/call-back setting for the
        modem. This property is inherited from
        CIM_PotsModem."
    ::= { win32POTSModemEntry 2 }

hwpmAttachedTo OBJECT-TYPE
    SYNTAX     DisplayString
    MAX-ACCESS read-only
    STATUS     current
    DESCRIPTION
        "Port to which the POTS modem is attached.
        Example: 'COM1'"
    ::= { win32POTSModemEntry 3 }

hwpmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32POTSModemEntry 4 }

hwpmBlindOff OBJECT-TYPE
    SYNTAX     DisplayString
    MAX-ACCESS read-only
    STATUS     current
    DESCRIPTION
        "Command string used to detect a dial tone before
        dialing.
        Example: 'X4'"
    ::= { win32POTSModemEntry 5 }

hwpmBlindOn OBJECT-TYPE
    SYNTAX     DisplayString
    MAX-ACCESS read-only
    STATUS     current
    DESCRIPTION
        "Command string used to dial whether or not there
        is a dial tone.
        Example: 'X3'"
    ::= { win32POTSModemEntry 6 }

hwpmCaption OBJECT-TYPE
    SYNTAX     DisplayString (SIZE (0..64))
    MAX-ACCESS read-only
    STATUS     current
    DESCRIPTION
        "Short description (one-line string) of the object.
        This property is inherited from
        CIM_ManagedSystemElement."
    ::= { win32POTSModemEntry 7 }

hwpmCompatibilityFlags OBJECT-TYPE
    SYNTAX     DisplayString
    MAX-ACCESS read-only
    STATUS     current
    DESCRIPTION
        "All modem connection protocols with which this
        modem device is compatible."
    ::= { win32POTSModemEntry 8 }

hwpmCompressionInfo OBJECT-TYPE
    SYNTAX     INTEGER {
        unknown(1),
        other(2),
        noCompression(3),
        mnp5(4),
        v42bis(5)
    }
    MAX-ACCESS read-only
    STATUS     current
    DESCRIPTION
        "Data compression characteristics of the modem.
        This property is inherited from CIM_PotsModem."
    ::= { win32POTSModemEntry 9 }

hwpmCompressionOff OBJECT-TYPE
    SYNTAX     DisplayString
    MAX-ACCESS read-only
    STATUS     current
    DESCRIPTION
        "Command string used to disable hardware data
        compression.
        Example: 'S46=136'"
    ::= { win32POTSModemEntry 10 }

hwpmCompressionOn OBJECT-TYPE
    SYNTAX     DisplayString
    MAX-ACCESS read-only
    STATUS     current
    DESCRIPTION
        "Command string used to enable hardware data
        compression.
        Example: 'S46=138'"
    ::= { win32POTSModemEntry 11 }

hwpmConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32POTSModemEntry 12 }

hwpmConfigManagerUserConfig OBJECT-TYPE
    SYNTAX     TruthValue
    MAX-ACCESS read-only
    STATUS     current
    DESCRIPTION
        "If TRUE, the device is using a user-defined
        configuration. This property is inherited from
        CIM_LogicalDevice."
    ::= { win32POTSModemEntry 13 }

hwpmConfigurationDialog OBJECT-TYPE
    SYNTAX     DisplayString
    MAX-ACCESS read-only
    STATUS     current
    DESCRIPTION
        "Modem initialization string. This property is
        comprised of command strings from other properties
        of this class."
    ::= { win32POTSModemEntry 14 }

hwpmCountriesSupported OBJECT-TYPE
    SYNTAX     DisplayString
    MAX-ACCESS read-only
    STATUS     current
    DESCRIPTION
        "Array of countries/regions in which the modem can
        operate. This property is inherited from
        CIM_PotsModem."
    ::= { win32POTSModemEntry 15 }

hwpmCountrySelected OBJECT-TYPE
    SYNTAX     DisplayString
    MAX-ACCESS read-only
    STATUS     current
    DESCRIPTION
        "Country/region for which the modem is currently
        programmed. When multiple countries/regions are
        supported, this property defines which one is
        currently selected for use. This property is
        inherited from CIM_PotsModem."
    ::= { win32POTSModemEntry 16 }

hwpmCreationClassName OBJECT-TYPE
    SYNTAX     DisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32POTSModemEntry 17 }

hwpmCurrentPasswords OBJECT-TYPE
    SYNTAX     DisplayString
    MAX-ACCESS read-only
    STATUS     current
    DESCRIPTION
        "List of currently defined passwords for the modem.
        This array may be left blank for security reasons.
        This property is inherited from CIM_PotsModem."
    ::= { win32POTSModemEntry 18 }

hwpmDCB OBJECT-TYPE
    SYNTAX     DisplayString
    MAX-ACCESS read-only
    STATUS     current
    DESCRIPTION
        "Control settings for a serial communications
        device, in this case, the modem device."
    ::= { win32POTSModemEntry 19 }

hwpmDefault OBJECT-TYPE
    SYNTAX     DisplayString
    MAX-ACCESS read-only
    STATUS     current
    DESCRIPTION
        "If TRUE, this POTS modem is the default modem on
        the Windows computer system."
    ::= { win32POTSModemEntry 20 }

hwpmDescription OBJECT-TYPE
    SYNTAX     DisplayString
    MAX-ACCESS read-only
    STATUS     current
    DESCRIPTION
        "Description of the object. This property is
        inherited from CIM_ManagedSystemElement."
    ::= { win32POTSModemEntry 21 }

hwpmDeviceID OBJECT-TYPE
    SYNTAX     DisplayString
    MAX-ACCESS read-only
    STATUS     current
    DESCRIPTION
        "Unique identifier of this POTS modem from other
        devices on the system. This property is inherited
        from CIM_LogicalDevice."
    ::= { win32POTSModemEntry 22 }

hwpmDeviceLoader OBJECT-TYPE
    SYNTAX     DisplayString
    MAX-ACCESS read-only
    STATUS     current
    DESCRIPTION
        "Name of the device loader for the modem. A device
        loader loads and manages device drivers and
        enumerators for a given device."
    ::= { win32POTSModemEntry 23 }

hwpmDeviceType OBJECT-TYPE
    SYNTAX     INTEGER {
        nullModem(1),
        internalModem(2),
        externalModem(3),
        pcmciaModem(4),
        unknown(5)
    }
    MAX-ACCESS read-only
    STATUS     current
    DESCRIPTION
        "Physical type of the modem."
    ::= { win32POTSModemEntry 24 }

hwpmDialType OBJECT-TYPE
    SYNTAX     INTEGER {
        unknown(0),
        tone(1),
        pulse(2)
    }
    MAX-ACCESS read-only
    STATUS     current
    DESCRIPTION
        "Type of dialing method used. This property is
        inherited from CIM_PotsModem."
    ::= { win32POTSModemEntry 25 }

hwpmDriverDate OBJECT-TYPE
    SYNTAX     DateAndTime
    MAX-ACCESS read-only
    STATUS     current
    DESCRIPTION
        "Date of the modem driver."
    ::= { win32POTSModemEntry 26 }

hwpmErrorCleared OBJECT-TYPE
    SYNTAX     TruthValue
    MAX-ACCESS read-only
    STATUS     current
    DESCRIPTION
        "If TRUE, the error reported in LastErrorCode is
        now cleared. This property is inherited from
        CIM_LogicalDevice."
    ::= { win32POTSModemEntry 27 }

hwpmErrorControlForced OBJECT-TYPE
    SYNTAX     DisplayString
    MAX-ACCESS read-only
    STATUS     current
    DESCRIPTION
        "Command string used to enable error correction
        control when establishing a connection. This
        increases the reliability of the connection.
        Example: '+Q5S36=4S48=7'"
    ::= { win32POTSModemEntry 28 }

hwpmErrorControlInfo OBJECT-TYPE
    SYNTAX     INTEGER {
        unknown(1),
        other(2),
        noErrorCorrection(3),
        mnp4(4),
        lapm(5)
    }
    MAX-ACCESS read-only
    STATUS     current
    DESCRIPTION
        "Error correction characteristics of the modem.
        This property is inherited from CIM_PotsModem."
    ::= { win32POTSModemEntry 29 }

hwpmErrorControlOff OBJECT-TYPE
    SYNTAX     DisplayString
    MAX-ACCESS read-only
    STATUS     current
    DESCRIPTION
        "Command string used to disable error control.
        Example: '+Q6S36=3S48=128'"
    ::= { win32POTSModemEntry 30 }

hwpmErrorControlOn OBJECT-TYPE
    SYNTAX     DisplayString
    MAX-ACCESS read-only
    STATUS     current
    DESCRIPTION
        "Command string used to enable error control.
        Example: '+Q5S36=7S48=7'"
    ::= { win32POTSModemEntry 31 }

hwpmErrorDescription OBJECT-TYPE
    SYNTAX     DisplayString
    MAX-ACCESS read-only
    STATUS     current
    DESCRIPTION
        "More information about the error recorded in
        LastErrorCode, and information on any corrective
        actions that may be taken. This property is
        inherited from CIM_LogicalDevice."
    ::= { win32POTSModemEntry 32 }

hwpmFlowControlHard OBJECT-TYPE
    SYNTAX     DisplayString
    MAX-ACCESS read-only
    STATUS     current
    DESCRIPTION
        "Command string used to enable hardware flow
        control. Flow control consists of signals sent
        between computers that verify that both computers
        are ready to transmit or receive data.
        Example: '&K1'"
    ::= { win32POTSModemEntry 33 }

hwpmFlowControlOff OBJECT-TYPE
    SYNTAX     DisplayString
    MAX-ACCESS read-only
    STATUS     current
    DESCRIPTION
        "Command string used to disable flow control. Flow
        control consists of signals sent between computers
        that verify that both computers are ready to
        transmit or receive data.
        Example: '&K0'"
    ::= { win32POTSModemEntry 34 }

hwpmFlowControlSoft OBJECT-TYPE
    SYNTAX     DisplayString
    MAX-ACCESS read-only
    STATUS     current
    DESCRIPTION
        "Command string used to enable software flow
        control. Flow control consists of signals sent
        between computers that verify that both computers
        are ready to transmit or receive data.
        Example: '&K2'"
    ::= { win32POTSModemEntry 35 }

hwpmInactivityScale OBJECT-TYPE
    SYNTAX     DisplayString
    MAX-ACCESS read-only
    STATUS     current
    DESCRIPTION
        "Multiplier used with the InactivityTimeout
        property to calculate the timeout period of a
        connection."
    ::= { win32POTSModemEntry 36 }

hwpmInactivityTimeout OBJECT-TYPE
    SYNTAX     Gauge32
    UNITS "Seconds"
    MAX-ACCESS read-only
    STATUS     current
    DESCRIPTION
        "Time limit (in seconds) for automatic
        disconnection of the phone line, if no data is
        exchanged. A value of 0 indicates that this feature
        is present but not enabled. This property is
        inherited from CIM_PotsModem."
    ::= { win32POTSModemEntry 37 }

hwpmModemIndex OBJECT-TYPE
    SYNTAX     Gauge32
    MAX-ACCESS read-only
    STATUS     current
    DESCRIPTION
        "Index number for this POTS modem.
        Example: 0"
    ::= { win32POTSModemEntry 38 }

hwpmInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32POTSModemEntry 39 }

hwpmLastErrorCode OBJECT-TYPE
    SYNTAX     Gauge32
    MAX-ACCESS read-only
    STATUS     current
    DESCRIPTION
        "Last error code reported by the logical device.
        This property is inherited from CIM_LogicalDevice."
    ::= { win32POTSModemEntry 40 }

hwpmMaxBaudRateToPhone OBJECT-TYPE
    SYNTAX     Gauge32
    UNITS "Bits per second"
    MAX-ACCESS read-only
    STATUS     current
    DESCRIPTION
        "Maximum settable communication speed for accessing
        the phone system. This property is inherited from
        CIM_PotsModem."
    ::= { win32POTSModemEntry 41 }

hwpmMaxBaudRateToSerialPort OBJECT-TYPE
    SYNTAX     Gauge32
    UNITS "Bits per second"
    MAX-ACCESS read-only
    STATUS     current
    DESCRIPTION
        "Maximum settable communication speed to the COM
        port for an external modem. Enter 0 if not
        applicable. This property is inherited from
        CIM_PotsModem."
    ::= { win32POTSModemEntry 42 }

hwpmMaxNumberOfPasswords OBJECT-TYPE
    SYNTAX     Integer32
    MAX-ACCESS read-only
    STATUS     current
    DESCRIPTION
        "Number of passwords definable in the modem itself.
        If this feature is not supported, enter 0. This
        property is inherited from CIM_PotsModem."
    ::= { win32POTSModemEntry 43 }

hwpmModel OBJECT-TYPE
    SYNTAX     DisplayString
    MAX-ACCESS read-only
    STATUS     current
    DESCRIPTION
        "Model of this POTS modem.
        Example: 'Sportster 56K External'"
    ::= { win32POTSModemEntry 44 }

hwpmModemInfPath OBJECT-TYPE
    SYNTAX     DisplayString
    MAX-ACCESS read-only
    STATUS     current
    DESCRIPTION
        "Path to this modem's .inf file. This file contains
        initialization information for the modem and its
        driver.
        Example: 'C:\WINNT\INF'"
    ::= { win32POTSModemEntry 45 }

hwpmModemInfSection OBJECT-TYPE
    SYNTAX     DisplayString
    MAX-ACCESS read-only
    STATUS     current
    DESCRIPTION
        "Name of the section in the modem's .inf file that
        contains information about the modem."
    ::= { win32POTSModemEntry 46 }

hwpmModulationBell OBJECT-TYPE
    SYNTAX     DisplayString
    MAX-ACCESS read-only
    STATUS     current
    DESCRIPTION
        "Command string used to instruct the modem to use
        Bell modulations for 300 and 1200 bps.
        Example: 'B1'"
    ::= { win32POTSModemEntry 47 }

hwpmModulationCCITT OBJECT-TYPE
    SYNTAX     DisplayString
    MAX-ACCESS read-only
    STATUS     current
    DESCRIPTION
        "Command string used to instruct the modem to use
        CCITT modulations for 300 and 1200 bps.
        Example: 'B0'"
    ::= { win32POTSModemEntry 48 }

hwpmModulationScheme OBJECT-TYPE
    SYNTAX     INTEGER {
        unknown(1),
        other(2),
        notSupported(3),
        bell103(4),
        bell212A(5),
        v22bis(6),
        v32(7),
        v32bis(8),
        vturbo(9),
        vFC(10),
        v34(11),
        v34bis(12)
    }
    MAX-ACCESS read-only
    STATUS     current
    DESCRIPTION
        "Modulation scheme of the modem. This property is
        inherited from CIM_PotsModem."
    ::= { win32POTSModemEntry 49 }

hwpmName OBJECT-TYPE
    SYNTAX     DisplayString
    MAX-ACCESS read-only
    STATUS     current
    DESCRIPTION
        "Label by which the object is known. When
        subclassed, the property can be overridden to be a
        key property. This property is inherited from
        CIM_ManagedSystemElement."
    ::= { win32POTSModemEntry 50 }

hwpmPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32POTSModemEntry 51 }

hwpmPortSubClass OBJECT-TYPE
    SYNTAX     INTEGER {
        parallelPort(0),
        serialPort(1),
        modem(2)
    }
    MAX-ACCESS read-only
    STATUS     current
    DESCRIPTION
        "Definition of the port used for this modem."
    ::= { win32POTSModemEntry 52 }

hwpmPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32POTSModemEntry 53 }

hwpmPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32POTSModemEntry 54 }

hwpmPrefix OBJECT-TYPE
    SYNTAX     DisplayString
    MAX-ACCESS read-only
    STATUS     current
    DESCRIPTION
        "Dialing prefix used to access an outside line."
    ::= { win32POTSModemEntry 55 }

hwpmProperties OBJECT-TYPE
    SYNTAX     DisplayString
    MAX-ACCESS read-only
    STATUS     current
    DESCRIPTION
        "List of all the properties (and their values) for
        this modem."
    ::= { win32POTSModemEntry 56 }

hwpmProviderName OBJECT-TYPE
    SYNTAX     DisplayString
    MAX-ACCESS read-only
    STATUS     current
    DESCRIPTION
        "Network path to the computer that provides the
        modem services."
    ::= { win32POTSModemEntry 57 }

hwpmPulse OBJECT-TYPE
    SYNTAX     DisplayString
    MAX-ACCESS read-only
    STATUS     current
    DESCRIPTION
        "Command string used to instruct the modem to use
        pulse mode for dialing. Pulse dialing is necessary
        for phone lines that are unable to handle tone
        dialing.
        Example: 'P'"
    ::= { win32POTSModemEntry 58 }

hwpmReset OBJECT-TYPE
    SYNTAX     DisplayString
    MAX-ACCESS read-only
    STATUS     current
    DESCRIPTION
        "Command string used to reset the modem for the
        next call.
        Example: 'AT&F'"
    ::= { win32POTSModemEntry 59 }

hwpmResponsesKeyName OBJECT-TYPE
    SYNTAX     DisplayString
    MAX-ACCESS read-only
    STATUS     current
    DESCRIPTION
        "Response this modem might report to the operating
        system during the connection process. The first two
        characters specify the type of response. The second
        two characters specify information about the
        connection being made. The second two characters
        are used only for Negotiation Progress or Connect
        response codes. The next eight characters specify
        the modem-to-modem line speed negotiated in bits
        per second (bps). The characters represent a 32-bit
        integer doubleword format (byte and word reversed).
        The last eight characters indicate that the modem
        is changing to a different port or Data Terminal
        Equipment (DTE) speed. Usually this field is not
        used because modems make connections at a locked
        port speed regardless of the modem-to-modem or Data
        Communications Equipment (DCE) speed."
    ::= { win32POTSModemEntry 60 }

hwpmRingsBeforeAnswer OBJECT-TYPE
    SYNTAX     Integer32 (0..255)
    MAX-ACCESS read-only
    STATUS     current
    DESCRIPTION
        "Number of rings before the modem answers an
        incoming call. This property is inherited from
        CIM_PotsModem."
    ::= { win32POTSModemEntry 61 }

hwpmSpeakerModeDial OBJECT-TYPE
    SYNTAX     DisplayString
    MAX-ACCESS read-only
    STATUS     current
    DESCRIPTION
        "Command string used to turn the modem speaker on
        after dialing a number, and turning the speaker off
        when a connection has been established.
        Example: 'M1'"
    ::= { win32POTSModemEntry 62 }

hwpmSpeakerModeOff OBJECT-TYPE
    SYNTAX     DisplayString
    MAX-ACCESS read-only
    STATUS     current
    DESCRIPTION
        "Command string used to turn the modem speaker off.
        Example: 'M0'"
    ::= { win32POTSModemEntry 63 }

hwpmSpeakerModeOn OBJECT-TYPE
    SYNTAX     DisplayString
    MAX-ACCESS read-only
    STATUS     current
    DESCRIPTION
        "Command string used to turn the modem speaker on.
        Example: 'M2'"
    ::= { win32POTSModemEntry 64 }

hwpmSpeakerModeSetup OBJECT-TYPE
    SYNTAX     DisplayString
    MAX-ACCESS read-only
    STATUS     current
    DESCRIPTION
        "Command string used to instruct the modem to turn
        the speaker on (until a connection is established).
        Example: 'M3'"
    ::= { win32POTSModemEntry 65 }

hwpmSpeakerVolumeHigh OBJECT-TYPE
    SYNTAX     DisplayString
    MAX-ACCESS read-only
    STATUS     current
    DESCRIPTION
        "Command string used to set the modem speaker to
        the highest volume.
        Example: 'L3'"
    ::= { win32POTSModemEntry 66 }

hwpmSpeakerVolumeInfo OBJECT-TYPE
    SYNTAX     INTEGER {
        unknown(0),
        other(1),
        notSupported(2),
        high(3),
        medium(4),
        low(5),
        off(6),
        auto(7)
    }
    MAX-ACCESS read-only
    STATUS     current
    DESCRIPTION
        "Describes the volume level of the audible tones
        from the modem. This property is inherited from
        CIM_PotsModem."
    ::= { win32POTSModemEntry 67 }

hwpmSpeakerVolumeLow OBJECT-TYPE
    SYNTAX     DisplayString
    MAX-ACCESS read-only
    STATUS     current
    DESCRIPTION
        "Command string used to set the modem speaker to
        the lowest volume.
        Example: 'L1'"
    ::= { win32POTSModemEntry 68 }

hwpmSpeakerVolumeMed OBJECT-TYPE
    SYNTAX     DisplayString
    MAX-ACCESS read-only
    STATUS     current
    DESCRIPTION
        "Command string used to set the modem speaker to a
        medium volume.
        Example: 'L2'"
    ::= { win32POTSModemEntry 69 }

hwpmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32POTSModemEntry 70 }

hwpmStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32POTSModemEntry 71 }

hwpmStringFormat OBJECT-TYPE
    SYNTAX     DisplayString
    MAX-ACCESS read-only
    STATUS     current
    DESCRIPTION
        "Type of characters used for text passed through
        the modem. Values are:
        'ASCII string format'
        'DBCS string format'
        'UNICODE string format'"
    ::= { win32POTSModemEntry 72 }

hwpmSupportsCallback OBJECT-TYPE
    SYNTAX     TruthValue
    MAX-ACCESS read-only
    STATUS     current
    DESCRIPTION
        "If TRUE, the modem supports call-back. This
        property is inherited from CIM_PotsModem."
    ::= { win32POTSModemEntry 73 }

hwpmSupportsSynchronousConnect OBJECT-TYPE
    SYNTAX     TruthValue
    MAX-ACCESS read-only
    STATUS     current
    DESCRIPTION
        "If TRUE, synchronous, as well as asynchronous,
        communication is supported. This property is
        inherited from CIM_PotsModem."
    ::= { win32POTSModemEntry 74 }

hwpmSystemCreationClassName OBJECT-TYPE
    SYNTAX     DisplayString
    MAX-ACCESS read-only
    STATUS     current
    DESCRIPTION
        "Value of the scoping computer's CreationClassName
        property. This property is inherited from
        CIM_LogicalDevice."
    ::= { win32POTSModemEntry 75 }

hwpmSystemName OBJECT-TYPE
    SYNTAX     DisplayString
    MAX-ACCESS read-only
    STATUS     current
    DESCRIPTION
        "Name of the scoping system. This property is
        inherited from CIM_LogicalDevice."
    ::= { win32POTSModemEntry 76 }

hwpmTerminator OBJECT-TYPE
    SYNTAX     DisplayString
    MAX-ACCESS read-only
    STATUS     current
    DESCRIPTION
        "String that marks the end of a command string.
        Example: '<cr'"
    ::= { win32POTSModemEntry 77 }

hwpmTimeOfLastReset OBJECT-TYPE
    SYNTAX     DateAndTime
    MAX-ACCESS read-only
    STATUS     current
    DESCRIPTION
        "Date and time the modem was last reset. This
        property is inherited from CIM_PotsModem."
    ::= { win32POTSModemEntry 78 }

hwpmTone OBJECT-TYPE
    SYNTAX     DisplayString
    MAX-ACCESS read-only
    STATUS     current
    DESCRIPTION
        "Command string that instructs the modem to use
        tone mode for dialing. The phone line must support
        tone dialing.
        Example: 'T'"
    ::= { win32POTSModemEntry 79 }

hwpmVoiceSwitchFeature OBJECT-TYPE
    SYNTAX     DisplayString
    MAX-ACCESS read-only
    STATUS     current
    DESCRIPTION
        "Command strings used to activate the voice
        capabilities of a voice modem.
        Example: 'AT+V'"
    ::= { win32POTSModemEntry 80 }

wmiVideoMonitor OBJECT-IDENTITY
    STATUS     current
    DESCRIPTION
        "The Video and Monitors subcategory groups classes
        that represent monitors, video cards, and their
        associated settings."
    ::= { wmiHardware 9 }

win32DesktopMonitorTable OBJECT-TYPE
    SYNTAX     SEQUENCE OF Win32DesktopMonitorEntry
    MAX-ACCESS not-accessible
    STATUS     current
    DESCRIPTION
        "The Win32_DesktopMonitor WMI class represents the
        type of monitor or display device attached to the
        computer system."
    ::= { wmiVideoMonitor 1 }

win32DesktopMonitorEntry OBJECT-TYPE
    SYNTAX     Win32DesktopMonitorEntry
    MAX-ACCESS not-accessible
    STATUS     current
    DESCRIPTION
        "None"
    INDEX      { hwdmIndex }
    ::= { win32DesktopMonitorTable 1 }

Win32DesktopMonitorEntry ::= SEQUENCE {
    hwdmIndex Integer32,
    hwdmAvailability INTEGER,
    hwdmBandwidth Gauge32,
    hwdmCaption DisplayString,
    hwdmConfigManagerErrorCode INTEGER,
    hwdmConfigManagerUserConfig TruthValue,
    hwdmCreationClassName DisplayString,
    hwdmDescription DisplayString,
    hwdmDeviceID DisplayString,
    hwdmDisplayType INTEGER,
    hwdmErrorCleared TruthValue,
    hwdmErrorDescription DisplayString,
    hwdmInstallDate DateAndTime,
    hwdmIsLocked TruthValue,
    hwdmLastErrorCode Gauge32,
    hwdmMonitorManufacturer DisplayString,
    hwdmMonitorType DisplayString,
    hwdmName DisplayString,
    hwdmPixelsPerXLogicalInch Gauge32,
    hwdmPixelsPerYLogicalInch Gauge32,
    hwdmPNPDeviceID DisplayString,
    hwdmPowerManagementCapabilities DisplayString,
    hwdmPowerManagementSupported TruthValue,
    hwdmScreenHeight Gauge32,
    hwdmScreenWidth Gauge32,
    hwdmStatus INTEGER,
    hwdmStatusInfo INTEGER,
    hwdmSystemCreationClassName DisplayString,
    hwdmSystemName DisplayString
}

hwdmIndex OBJECT-TYPE
    SYNTAX     Integer32 (1..2147483647)
    MAX-ACCESS read-only
    STATUS     current
    DESCRIPTION
        "The value of this object uniquely identifies the
        instance entry for this class."
    ::= { win32DesktopMonitorEntry 1 }

hwdmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32DesktopMonitorEntry 2 }

hwdmBandwidth OBJECT-TYPE
    SYNTAX     Gauge32
    MAX-ACCESS read-only
    STATUS     current
    DESCRIPTION
        "Monitor's bandwidth in megahertz. If unknown,
        enter 0. This property is inherited from
        CIM_DesktopMonitor."
    ::= { win32DesktopMonitorEntry 3 }

hwdmCaption OBJECT-TYPE
    SYNTAX     DisplayString
    MAX-ACCESS read-only
    STATUS     current
    DESCRIPTION
        "Short description (one-line string) of the object.
        This property is inherited from
        CIM_ManagedSystemElement."
    ::= { win32DesktopMonitorEntry 4 }

hwdmConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32DesktopMonitorEntry 5 }

hwdmConfigManagerUserConfig OBJECT-TYPE
    SYNTAX     TruthValue
    MAX-ACCESS read-only
    STATUS     current
    DESCRIPTION
        "If TRUE, the device is using a user-defined
        configuration. This property is inherited from
        CIM_LogicalDevice."
    ::= { win32DesktopMonitorEntry 6 }

hwdmCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32DesktopMonitorEntry 7 }

hwdmDescription OBJECT-TYPE
    SYNTAX     DisplayString
    MAX-ACCESS read-only
    STATUS     current
    DESCRIPTION
        "Description of the object. This property is
        inherited from CIM_ManagedSystemElement."
    ::= { win32DesktopMonitorEntry 8 }

hwdmDeviceID OBJECT-TYPE
    SYNTAX     DisplayString
    MAX-ACCESS read-only
    STATUS     current
    DESCRIPTION
        "Unique identifier of a desktop monitor. This
        property is inherited from CIM_LogicalDevice."
    ::= { win32DesktopMonitorEntry 9 }

hwdmDisplayType OBJECT-TYPE
    SYNTAX     INTEGER {
        unknown(0),
        other(1),
        multiscanColor(2),
        multiscanMonochrome(3),
        fixedFrequencyColor(4),
        fixedFrequencyMonochrome(5)
    }
    MAX-ACCESS read-only
    STATUS     current
    DESCRIPTION
        "Type of desktop monitor or CRT. This property is
        inherited from CIM_DesktopMonitor."
    ::= { win32DesktopMonitorEntry 10 }

hwdmErrorCleared OBJECT-TYPE
    SYNTAX     TruthValue
    MAX-ACCESS read-only
    STATUS     current
    DESCRIPTION
        "If TRUE, the error reported in LastErrorCode is
        now cleared. This property is inherited from
        CIM_LogicalDevice."
    ::= { win32DesktopMonitorEntry 11 }

hwdmErrorDescription OBJECT-TYPE
    SYNTAX     DisplayString
    MAX-ACCESS read-only
    STATUS     current
    DESCRIPTION
        "Free-form string supplying more information about
        the error recorded in LastErrorCode, and
        information on any corrective actions that may be
        taken. This property is inherited from
        CIM_LogicalDevice."
    ::= { win32DesktopMonitorEntry 12 }

hwdmInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32DesktopMonitorEntry 13 }

hwdmIsLocked OBJECT-TYPE
    SYNTAX     TruthValue
    MAX-ACCESS read-only
    STATUS     current
    DESCRIPTION
        "If TRUE, the device is locked, preventing user
        input or output. This property is inherited from
        CIM_UserDevice."
    ::= { win32DesktopMonitorEntry 14 }

hwdmLastErrorCode OBJECT-TYPE
    SYNTAX     Gauge32
    MAX-ACCESS read-only
    STATUS     current
    DESCRIPTION
        "Last error code reported by the logical device.
        This property is inherited from CIM_LogicalDevice."
    ::= { win32DesktopMonitorEntry 15 }

hwdmMonitorManufacturer OBJECT-TYPE
    SYNTAX     DisplayString
    MAX-ACCESS read-only
    STATUS     current
    DESCRIPTION
        "Name of the monitor manufacturer.
        Example: 'NEC'"
    ::= { win32DesktopMonitorEntry 16 }

hwdmMonitorType OBJECT-TYPE
    SYNTAX     DisplayString
    MAX-ACCESS read-only
    STATUS     current
    DESCRIPTION
        "Type of monitor.
        Example: 'NEC 5FGp'"
    ::= { win32DesktopMonitorEntry 17 }

hwdmName OBJECT-TYPE
    SYNTAX     DisplayString
    MAX-ACCESS read-only
    STATUS     current
    DESCRIPTION
        "Label by which the object is known. When
        subclassed, the property can be overridden to be a
        key property. This property is inherited from
        CIM_ManagedSystemElement."
    ::= { win32DesktopMonitorEntry 18 }

hwdmPixelsPerXLogicalInch OBJECT-TYPE
    SYNTAX     Gauge32
    UNITS "Pixels per Logical Inch"
    MAX-ACCESS read-only
    STATUS     current
    DESCRIPTION
        "Resolution along the X axis (horizontal direction)
        of the monitor."
    ::= { win32DesktopMonitorEntry 19 }

hwdmPixelsPerYLogicalInch OBJECT-TYPE
    SYNTAX     Gauge32
    UNITS "Pixels per Logical Inch"
    MAX-ACCESS read-only
    STATUS     current
    DESCRIPTION
        "Resolution along the Y axis (vertical direction)
        of the monitor."
    ::= { win32DesktopMonitorEntry 20 }

hwdmPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32DesktopMonitorEntry 21 }

hwdmPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32DesktopMonitorEntry 22 }

hwdmPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32DesktopMonitorEntry 23 }

hwdmScreenHeight OBJECT-TYPE
    SYNTAX     Gauge32
    MAX-ACCESS read-only
    STATUS     current
    DESCRIPTION
        "Logical height of the display in screen
        coordinates. This property is inherited from
        CIM_DesktopMonitor."
    ::= { win32DesktopMonitorEntry 24 }

hwdmScreenWidth OBJECT-TYPE
    SYNTAX     Gauge32
    MAX-ACCESS read-only
    STATUS     current
    DESCRIPTION
        "Logical width of the display in screen
        coordinates. This property is inherited from
        CIM_DesktopMonitor."
    ::= { win32DesktopMonitorEntry 25 }

hwdmStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32DesktopMonitorEntry 26 }

hwdmStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32DesktopMonitorEntry 27 }

hwdmSystemCreationClassName OBJECT-TYPE
    SYNTAX     DisplayString
    MAX-ACCESS read-only
    STATUS     current
    DESCRIPTION
        "Value of the scoping computer's CreationClassName
        property. This property is inherited from
        CIM_LogicalDevice."
    ::= { win32DesktopMonitorEntry 28 }

hwdmSystemName OBJECT-TYPE
    SYNTAX     DisplayString
    MAX-ACCESS read-only
    STATUS     current
    DESCRIPTION
        "Name of the scoping system. This property is
        inherited from CIM_LogicalDevice."
    ::= { win32DesktopMonitorEntry 29 }

win32VideoControllerTable OBJECT-TYPE
    SYNTAX     SEQUENCE OF Win32VideoControllerEntry
    MAX-ACCESS not-accessible
    STATUS     current
    DESCRIPTION
        "The Win32_VideoController WMI class represents the
        capabilities and management capacity of the video
        controller on a Windows computer system."
    ::= { wmiVideoMonitor 2 }

win32VideoControllerEntry OBJECT-TYPE
    SYNTAX     Win32VideoControllerEntry
    MAX-ACCESS not-accessible
    STATUS     current
    DESCRIPTION
        "None"
    INDEX      { hwvcIndex }
    ::= { win32VideoControllerTable 1 }

Win32VideoControllerEntry ::= SEQUENCE {
    hwvcIndex Integer32,
    hwvcAcceleratorCapabilities DisplayString,
    hwvcAdapterCompatibility DisplayString,
    hwvcAdapterDACType DisplayString,
    hwvcAdapterRAM Gauge32,
    hwvcAvailability INTEGER,
    hwvcCapabilityDescriptions DisplayString,
    hwvcCaption DisplayString,
    hwvcColorTableEntries Gauge32,
    hwvcConfigManagerErrorCode INTEGER,
    hwvcConfigManagerUserConfig TruthValue,
    hwvcCreationClassName DisplayString,
    hwvcCurrentBitsPerPixel Gauge32,
    hwvcCurrentHorizontalResolution Gauge32,
    hwvcCurrentNumberOfColors Gauge32,
    hwvcCurrentNumberOfColumns Gauge32,
    hwvcCurrentNumberOfRows Gauge32,
    hwvcCurrentRefreshRate Gauge32,
    hwvcCurrentScanMode INTEGER,
    hwvcCurrentVerticalResolution Gauge32,
    hwvcDescription DisplayString,
    hwvcDeviceID DisplayString,
    hwvcDeviceSpecificPens Gauge32,
    hwvcDitherType INTEGER,
    hwvcDriverDate DateAndTime,
    hwvcDriverVersion DisplayString,
    hwvcErrorCleared TruthValue,
    hwvcErrorDescription DisplayString,
    hwvcICMIntent INTEGER,
    hwvcICMMethod INTEGER,
    hwvcInfFilename DisplayString,
    hwvcInfSection DisplayString,
    hwvcInstallDate DateAndTime,
    hwvcInstalledDisplayDrivers DisplayString,
    hwvcLastErrorCode Gauge32,
    hwvcMaxMemorySupported Gauge32,
    hwvcMaxNumberControlled Gauge32,
    hwvcMaxRefreshRate Gauge32,
    hwvcMinRefreshRate Gauge32,
    hwvcMonochrome TruthValue,
    hwvcName DisplayString,
    hwvcNumberOfColorPlanes Integer32,
    hwvcNumberOfVideoPages Gauge32,
    hwvcPNPDeviceID DisplayString,
    hwvcPowerManagementCapabilities DisplayString,
    hwvcPowerManagementSupported TruthValue,
    hwvcProtocolSupported INTEGER,
    hwvcReservedSystemPaletteEntries Gauge32,
    hwvcSpecificationVersion Gauge32,
    hwvcStatus INTEGER,
    hwvcStatusInfo INTEGER,
    hwvcSystemCreationClassName DisplayString,
    hwvcSystemName DisplayString,
    hwvcSystemPaletteEntries Gauge32,
    hwvcTimeOfLastReset DateAndTime,
    hwvcVideoArchitecture INTEGER,
    hwvcVideoMemoryType INTEGER,
    hwvcVideoMode Integer32,
    hwvcVideoModeDescription DisplayString,
    hwvcVideoProcessor DisplayString
}

hwvcIndex OBJECT-TYPE
    SYNTAX     Integer32 (1..2147483647)
    MAX-ACCESS read-only
    STATUS     current
    DESCRIPTION
        "The value of this object uniquely identifies the
        instance entry for this class."
    ::= { win32VideoControllerEntry 1 }

hwvcAcceleratorCapabilities OBJECT-TYPE
    SYNTAX     DisplayString
    MAX-ACCESS read-only
    STATUS     current
    DESCRIPTION
        "Array of graphics and 3D capabilities of the video
        controller. This property is inherited from
        CIM_VideoController.
        Value Meaning 
        0 Unknown 
        1 Other 
        2 Graphics Accelerator 
        3 3D Accelerator "
    ::= { win32VideoControllerEntry 2 }

hwvcAdapterCompatibility OBJECT-TYPE
    SYNTAX     DisplayString
    MAX-ACCESS read-only
    STATUS     current
    DESCRIPTION
        "General chip set used for this controller to
        compare compatibilities with the system."
    ::= { win32VideoControllerEntry 3 }

hwvcAdapterDACType OBJECT-TYPE
    SYNTAX     DisplayString
    MAX-ACCESS read-only
    STATUS     current
    DESCRIPTION
        "Name or identifier of the digital-to-analog
        converter (DAC) chip. The character set of this
        property is alphanumeric."
    ::= { win32VideoControllerEntry 4 }

hwvcAdapterRAM OBJECT-TYPE
    SYNTAX     Gauge32
    UNITS "Bytes"
    MAX-ACCESS read-only
    STATUS     current
    DESCRIPTION
        "Memory size of the video adapter.
        Example: 64000"
    ::= { win32VideoControllerEntry 5 }

hwvcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32VideoControllerEntry 6 }

hwvcCapabilityDescriptions OBJECT-TYPE
    SYNTAX     DisplayString
    MAX-ACCESS read-only
    STATUS     current
    DESCRIPTION
        "Free-form strings providing more detailed
        explanations for any of the video accelerator
        features indicated in the AcceleratorCapabilities
        array. Note, each entry of this array is related to
        the entry in the AcceleratorCapabilities array that
        is located at the same index. This property is
        inherited from CIM_VideoController."
    ::= { win32VideoControllerEntry 7 }

hwvcCaption OBJECT-TYPE
    SYNTAX     DisplayString (SIZE (0..64))
    MAX-ACCESS read-only
    STATUS     current
    DESCRIPTION
        "Short description (one-line string) of the object.
        This property is inherited from
        CIM_ManagedSystemElement."
    ::= { win32VideoControllerEntry 8 }

hwvcColorTableEntries OBJECT-TYPE
    SYNTAX     Gauge32
    MAX-ACCESS read-only
    STATUS     current
    DESCRIPTION
        "Size of the system's color table. The device must
        have a color depth of no more than 8 bits per
        pixel; otherwise, this property is not set.
        Example: 256"
    ::= { win32VideoControllerEntry 9 }

hwvcConfigManagerErrorCode OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32VideoControllerEntry 10 }

hwvcConfigManagerUserConfig OBJECT-TYPE
    SYNTAX     TruthValue
    MAX-ACCESS read-only
    STATUS     current
    DESCRIPTION
        "If TRUE, the device is using a user-defined
        configuration. This property is inherited from
        CIM_LogicalDevice."
    ::= { win32VideoControllerEntry 11 }

hwvcCreationClassName OBJECT-TYPE
    SYNTAX     DisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32VideoControllerEntry 12 }

hwvcCurrentBitsPerPixel OBJECT-TYPE
    SYNTAX     Gauge32
    UNITS "Bits"
    MAX-ACCESS read-only
    STATUS     current
    DESCRIPTION
        "Number of bits used to display each pixel. This
        property is inherited from CIM_VideoController."
    ::= { win32VideoControllerEntry 13 }

hwvcCurrentHorizontalResolution OBJECT-TYPE
    SYNTAX     Gauge32
    UNITS "Pixels"
    MAX-ACCESS read-only
    STATUS     current
    DESCRIPTION
        "Current number of horizontal pixels. This property
        is inherited from CIM_VideoController."
    ::= { win32VideoControllerEntry 14 }

hwvcCurrentNumberOfColors OBJECT-TYPE
    SYNTAX     Gauge32
    MAX-ACCESS read-only
    STATUS     current
    DESCRIPTION
        "Number of colors supported at the current
        resolution. This property is inherited from
        CIM_VideoController."
    ::= { win32VideoControllerEntry 15 }

hwvcCurrentNumberOfColumns OBJECT-TYPE
    SYNTAX     Gauge32
    MAX-ACCESS read-only
    STATUS     current
    DESCRIPTION
        "Number of columns for this video controller (if in
        character mode). Otherwise, enter 0. This property
        is inherited from CIM_VideoController."
    ::= { win32VideoControllerEntry 16 }

hwvcCurrentNumberOfRows OBJECT-TYPE
    SYNTAX     Gauge32
    MAX-ACCESS read-only
    STATUS     current
    DESCRIPTION
        "Number of rows for this video controller (if in
        character mode). Otherwise, enter 0. This property
        is inherited from CIM_VideoController."
    ::= { win32VideoControllerEntry 17 }

hwvcCurrentRefreshRate OBJECT-TYPE
    SYNTAX     Gauge32
    UNITS "Hertz"
    MAX-ACCESS read-only
    STATUS     current
    DESCRIPTION
        "Frequency at which the video controller refreshes
        the image for the monitor. A value of 0 indicates
        the default rate is being used, while 0xFFFFFFFF
        indicates the optimal rate is being used. This
        property is inherited from CIM_VideoController."
    ::= { win32VideoControllerEntry 18 }

hwvcCurrentScanMode OBJECT-TYPE
    SYNTAX     INTEGER {
        other(1),
        unknown(2),
        interlaced(3),
        nonInterlaced(4)
    }
    MAX-ACCESS read-only
    STATUS     current
    DESCRIPTION
        "Current scan mode. This property is inherited from
        CIM_VideoController."
    ::= { win32VideoControllerEntry 19 }

hwvcCurrentVerticalResolution OBJECT-TYPE
    SYNTAX     Gauge32
    UNITS "Pixels"
    MAX-ACCESS read-only
    STATUS     current
    DESCRIPTION
        "Current number of vertical pixels. This property
        is inherited from CIM_VideoController."
    ::= { win32VideoControllerEntry 20 }

hwvcDescription OBJECT-TYPE
    SYNTAX     DisplayString
    MAX-ACCESS read-only
    STATUS     current
    DESCRIPTION
        "Description of the object. This property is
        inherited from CIM_ManagedSystemElement."
    ::= { win32VideoControllerEntry 21 }

hwvcDeviceID OBJECT-TYPE
    SYNTAX     DisplayString
    MAX-ACCESS read-only
    STATUS     current
    DESCRIPTION
        "Identifier (unique to the computer system) for
        this video controller. This property is inherited
        from CIM_LogicalDevice."
    ::= { win32VideoControllerEntry 22 }

hwvcDeviceSpecificPens OBJECT-TYPE
    SYNTAX     Gauge32
    MAX-ACCESS read-only
    STATUS     current
    DESCRIPTION
        "Current number of device-specific pens. A value of
        0xffff means that the device does not support pens.
        Example: 3"
    ::= { win32VideoControllerEntry 23 }

hwvcDitherType OBJECT-TYPE
    SYNTAX     INTEGER {
        noDithering(1),
        ditheringWithACoarseBrush(2),
        ditheringWithAFineBrush(3),
        lineArtDithering(4),
        deviceDoesGrayScaling(5)
    }
    MAX-ACCESS read-only
    STATUS     current
    DESCRIPTION
        "Dither type of the video controller. The property
        can be one of the predefined values, or a
        driver-defined value greater than or equal to 256.
        If line art dithering is chosen, the controller
        uses a dithering method that produces well-defined
        borders between black, white, and gray scalings.
        Line art dithering is not suitable for images that
        include continuous graduations in intensity and hue
        such as scanned photographs."
    ::= { win32VideoControllerEntry 24 }

hwvcDriverDate OBJECT-TYPE
    SYNTAX     DateAndTime
    MAX-ACCESS read-only
    STATUS     current
    DESCRIPTION
        "Last modification date and time of the
        currently-installed video driver."
    ::= { win32VideoControllerEntry 25 }

hwvcDriverVersion OBJECT-TYPE
    SYNTAX     DisplayString
    MAX-ACCESS read-only
    STATUS     current
    DESCRIPTION
        "Version number of the video driver."
    ::= { win32VideoControllerEntry 26 }

hwvcErrorCleared OBJECT-TYPE
    SYNTAX     TruthValue
    MAX-ACCESS read-only
    STATUS     current
    DESCRIPTION
        "If TRUE, the error reported in LastErrorCode
        property is now cleared. This property is inherited
        from CIM_LogicalDevice."
    ::= { win32VideoControllerEntry 27 }

hwvcErrorDescription OBJECT-TYPE
    SYNTAX     DisplayString
    MAX-ACCESS read-only
    STATUS     current
    DESCRIPTION
        "Free-form string supplying more information about
        the error recorded in LastErrorCode property, and
        information on any corrective actions that may be
        taken. This property is inherited from
        CIM_LogicalDevice."
    ::= { win32VideoControllerEntry 28 }

hwvcICMIntent OBJECT-TYPE
    SYNTAX     INTEGER {
        saturation(1),
        contrast(2),
        exactColor(3)
    }
    MAX-ACCESS read-only
    STATUS     current
    DESCRIPTION
        "Specific value of one of the three possible
        color-matching methods or intents that should be
        used by default. This property is used primarily
        for non-ICM applications. ICM applications
        establish intents by using the ICM functions. This
        property can be a predefined value or a driver
        defined value greater than or equal to 256. Color
        matching based on saturation is the most
        appropriate choice for business graphs when
        dithering is not desired. Color matching based on
        contrast is the most appropriate choice for scanned
        or photographic images when dithering is desired.
        Color matching optimized to match the exact color
        requested is most appropriate for use with business
        logos or other images when an exact color match is
        desired."
    ::= { win32VideoControllerEntry 29 }

hwvcICMMethod OBJECT-TYPE
    SYNTAX     INTEGER {
        disabled(1),
        windows(2),
        deviceDriver(3),
        destinationDevice(4)
    }
    MAX-ACCESS read-only
    STATUS     current
    DESCRIPTION
        "Method of handling ICM. For non-ICM applications,
        this property determines if ICM is enabled. For ICM
        applications, the system examines this property to
        determine how to handle ICM support. This property
        can be a predefined value or a driver-defined value
        greater than or equal to 256. The value determines
        which system handles image color matching."
    ::= { win32VideoControllerEntry 30 }

hwvcInfFilename OBJECT-TYPE
    SYNTAX     DisplayString
    MAX-ACCESS read-only
    STATUS     current
    DESCRIPTION
        "Path to the video adapter's .inf file.
        Example: 'C:\WINNT\SYSTEM32\DRIVERS'"
    ::= { win32VideoControllerEntry 31 }

hwvcInfSection OBJECT-TYPE
    SYNTAX     DisplayString
    MAX-ACCESS read-only
    STATUS     current
    DESCRIPTION
        "Section of the .inf file where the Windows video
        information resides."
    ::= { win32VideoControllerEntry 32 }

hwvcInstallDate OBJECT-TYPE
    SYNTAX     DateAndTime
    MAX-ACCESS read-only
    STATUS     current
    DESCRIPTION
        "Date and time the object was installed. This
        property does not need a value to indicate that the
        object is installed. This property is inherited
        from CIM_ManagedSystemElement."
    ::= { win32VideoControllerEntry 33 }

hwvcInstalledDisplayDrivers OBJECT-TYPE
    SYNTAX     DisplayString
    MAX-ACCESS read-only
    STATUS     current
    DESCRIPTION
        "Name of the installed display device driver."
    ::= { win32VideoControllerEntry 34 }

hwvcLastErrorCode OBJECT-TYPE
    SYNTAX     Gauge32
    MAX-ACCESS read-only
    STATUS     current
    DESCRIPTION
        "Last error code reported by the logical device.
        This property is inherited from CIM_LogicalDevice."
    ::= { win32VideoControllerEntry 35 }

hwvcMaxMemorySupported OBJECT-TYPE
    SYNTAX     Gauge32
    UNITS "Bytes"
    MAX-ACCESS read-only
    STATUS     current
    DESCRIPTION
        "Maximum amount of memory supported in bytes. This
        property is inherited from CIM_VideoController."
    ::= { win32VideoControllerEntry 36 }

hwvcMaxNumberControlled OBJECT-TYPE
    SYNTAX     Gauge32
    MAX-ACCESS read-only
    STATUS     current
    DESCRIPTION
        "Maximum number of directly addressable entities
        supportable by this controller. A value of 0 should
        be used if the number is unknown. This property is
        inherited from CIM_Controller."
    ::= { win32VideoControllerEntry 37 }

hwvcMaxRefreshRate OBJECT-TYPE
    SYNTAX     Gauge32
    UNITS "Hertz"
    MAX-ACCESS read-only
    STATUS     current
    DESCRIPTION
        "Maximum refresh rate of the video controller in
        hertz. This property is inherited from
        CIM_VideoController."
    ::= { win32VideoControllerEntry 38 }

hwvcMinRefreshRate OBJECT-TYPE
    SYNTAX     Gauge32
    UNITS "Hertz"
    MAX-ACCESS read-only
    STATUS     current
    DESCRIPTION
        "Minimum refresh rate of the video controller in
        hertz. This property is inherited from
        CIM_VideoController."
    ::= { win32VideoControllerEntry 39 }

hwvcMonochrome OBJECT-TYPE
    SYNTAX     TruthValue
    MAX-ACCESS read-only
    STATUS     current
    DESCRIPTION
        "If TRUE, gray scale is used to display images."
    ::= { win32VideoControllerEntry 40 }

hwvcName OBJECT-TYPE
    SYNTAX     DisplayString
    MAX-ACCESS read-only
    STATUS     current
    DESCRIPTION
        "Label by which the object is known. When
        subclassed, the property can be overridden to be a
        key property. This property is inherited from
        CIM_ManagedSystemElement."
    ::= { win32VideoControllerEntry 41 }

hwvcNumberOfColorPlanes OBJECT-TYPE
    SYNTAX     Integer32
    MAX-ACCESS read-only
    STATUS     current
    DESCRIPTION
        "Current number of color planes. If this value is
        not applicable for the current video configuration,
        enter 0. This property is inherited from
        CIM_PCVideoController."
    ::= { win32VideoControllerEntry 42 }

hwvcNumberOfVideoPages OBJECT-TYPE
    SYNTAX     Gauge32
    MAX-ACCESS read-only
    STATUS     current
    DESCRIPTION
        "Number of video pages supported given the current
        resolutions and available memory. This property is
        inherited from CIM_VideoController."
    ::= { win32VideoControllerEntry 43 }

hwvcPNPDeviceID OBJECT-TYPE
    SYNTAX     DisplayString
    MAX-ACCESS read-only
    STATUS     current
    DESCRIPTION
        "Windows Plug and Play device identifier of the
        logical device. This property is inherited from
        CIM_LogicalDevice.
        Example: '*PNP030b'"
    ::= { win32VideoControllerEntry 44 }

hwvcPowerManagementCapabilities OBJECT-TYPE
    SYNTAX     DisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32VideoControllerEntry 45 }

hwvcPowerManagementSupported OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32VideoControllerEntry 46 }

hwvcProtocolSupported OBJECT-TYPE
    SYNTAX     INTEGER {
        other(0),
        unknown(1),
        eisa(2),
        isa(3),
        pci(4),
        ataATAPI(5),
        flexibleDiskette(6),
        n1496(7),
        scsiParallelInterface(8),
        scsiFibreChannelProtocol(9),
        scsiSerialBusProtocol(10),
        scsiSerialBusProtocol1394(11),
        scsiSerialStorageArchitecture(12),
        vesa(13),
        pcmcia(14),
        universalSerialBus(15),
        parallelProtocol(16),
        escon(17),
        diagnostic(18),
        i2C(19),
        power(20),
        hippi(21),
        multiBus(22),
        vme(23),
        ipi(24),
        ieee488(25),
        rs232(26),
        ieee802310BASE5(27),
        ieee802310BASE2(28),
        ieee80231BASE5(29),
        ieee802310BROAD36(30),
        ieee8023100BASEVG(31),
        ieee8025TokenRing(32),
        ansiX3T95FDDI(33),
        mca(34),
        esdi(35),
        ide(36),
        cmd(37),
        st506(38),
        dssi(39),
        qic2(40),
        enhancedATAIDE(41),
        agp(42),
        twowayInfrared(43),
        fastInfrared(44),
        serialInfrared(45),
        irBus(46)
    }
    MAX-ACCESS read-only
    STATUS     current
    DESCRIPTION
        "Protocol used by the controller to access
        'controlled' devices. This property is inherited
        from CIM_Controller."
    ::= { win32VideoControllerEntry 47 }

hwvcReservedSystemPaletteEntries OBJECT-TYPE
    SYNTAX     Gauge32
    MAX-ACCESS read-only
    STATUS     current
    DESCRIPTION
        "Number of reserved entries in the system palette.
        The operating system may reserve entries to support
        standard colors for task bars and other desktop
        display items. This index is valid only if the
        device driver sets the RC_PALETTE bit in the
        RASTERCAPS index, and is available only if the
        driver is compatible with 16-bit Windows. If the
        system is not using a palette,
        ReservedSystemPaletteEntries is not set.
        Example: 20"
    ::= { win32VideoControllerEntry 48 }

hwvcSpecificationVersion OBJECT-TYPE
    SYNTAX     Gauge32
    MAX-ACCESS read-only
    STATUS     current
    DESCRIPTION
        "Version number of the initialization data
        specification (upon which the structure is based)."
    ::= { win32VideoControllerEntry 49 }

hwvcStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32VideoControllerEntry 50 }

hwvcStatusInfo OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32VideoControllerEntry 51 }

hwvcSystemCreationClassName OBJECT-TYPE
    SYNTAX     DisplayString
    MAX-ACCESS read-only
    STATUS     current
    DESCRIPTION
        "Value of the scoping computer's CreationClassName
        property. This property is inherited from
        CIM_LogicalDevice."
    ::= { win32VideoControllerEntry 52 }

hwvcSystemName OBJECT-TYPE
    SYNTAX     DisplayString
    MAX-ACCESS read-only
    STATUS     current
    DESCRIPTION
        "Name of the scoping system. This property is
        inherited from CIM_LogicalDevice."
    ::= { win32VideoControllerEntry 53 }

hwvcSystemPaletteEntries OBJECT-TYPE
    SYNTAX     Gauge32
    MAX-ACCESS read-only
    STATUS     current
    DESCRIPTION
        "Current number of color index entries in the
        system palette. This index is valid only if the
        device driver sets the RC_PALETTE bit in the
        RASTERCAPS index, and is available only if the
        driver is compatible with 16-bit Windows. If the
        system is not using a palette, SystemPaletteEntries
        is not set.
        Example: 20"
    ::= { win32VideoControllerEntry 54 }

hwvcTimeOfLastReset OBJECT-TYPE
    SYNTAX     DateAndTime
    MAX-ACCESS read-only
    STATUS     current
    DESCRIPTION
        "Date and time this controller was last reset. This
        could mean the controller was powered down, or
        reinitialized. This property is inherited from
        CIM_Controller."
    ::= { win32VideoControllerEntry 55 }

hwvcVideoArchitecture OBJECT-TYPE
    SYNTAX     INTEGER {
        other(1),
        unknown(2),
        cga(3),
        ega(4),
        vga(5),
        svga(6),
        mda(7),
        hgc(8),
        mcga(9),
        n8514A(10),
        xga(11),
        linearFrameBuffer(12),
        pc98(160)
    }
    MAX-ACCESS read-only
    STATUS     current
    DESCRIPTION
        "Type of video architecture. This property is
        inherited from CIM_PCVideoController."
    ::= { win32VideoControllerEntry 56 }

hwvcVideoMemoryType OBJECT-TYPE
    SYNTAX     INTEGER {
        other(1),
        unknown(2),
        vram(3),
        dram(4),
        sram(5),
        wram(6),
        edoRAM(7),
        burstSynchronousDRAM(8),
        pipelinedBurstSRAM(9),
        cdram(10),
        n3DRAM(11),
        sdram(12),
        sgram(13)
    }
    MAX-ACCESS read-only
    STATUS     current
    DESCRIPTION
        "Type of video memory. This property is inherited
        from CIM_VideoController."
    ::= { win32VideoControllerEntry 57 }

hwvcVideoMode OBJECT-TYPE
    SYNTAX     Integer32
    MAX-ACCESS read-only
    STATUS     current
    DESCRIPTION
        "Current video mode. This property is inherited
        from CIM_PCVideoController."
    ::= { win32VideoControllerEntry 58 }

hwvcVideoModeDescription OBJECT-TYPE
    SYNTAX     DisplayString
    MAX-ACCESS read-only
    STATUS     current
    DESCRIPTION
        "Current resolution, color, and scan mode settings
        of the video controller.
        Example: '1024 x 768 x 256 colors'"
    ::= { win32VideoControllerEntry 59 }

hwvcVideoProcessor OBJECT-TYPE
    SYNTAX     DisplayString
    MAX-ACCESS read-only
    STATUS     current
    DESCRIPTION
        "Free-form string describing the video processor.
        This property is inherited from
        CIM_VideoController."
    ::= { win32VideoControllerEntry 60 }

END
