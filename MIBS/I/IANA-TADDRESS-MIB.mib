-- extracted from draft-ops-taddress-mib-00.txt
-- at Wed May 31 07:07:26 2000

   IANA-TADDRESS-MIB DEFINITIONS ::= BEGIN

   IMPORTS
       MODULE-IDENTITY, OBJECT-IDENTITY, mib-2     FROM SNMPv2-SMI
       TEXTUAL-CONVENTION                          FROM SNMPv2-TC;

   ianaTAddressMIB MODULE-IDENTITY
       LAST-UPDATED "200005260000Z"
       ORGANIZATION
           "Internet Assigned Numbers Authority (IANA)"
       CONTACT-INFO
           "Internet Assigned Numbers Authority
            Internet Corporation for Assigned Names and Numbers
            4676 Admiralty Way, Suite 330
            Marina del Rey, CA 90292-6601
            USA

            Phone: +1 310-823-9358
            EMail: iana@iana.org"
       DESCRIPTION
   	"This MIB module provides commonly-used transport
            address definitions."
       REVISION    "200005260000Z"
       DESCRIPTION
           "Initial version, published as RFC XXXX."
       ::= { mib-2 1 } -- to be assigned by IANA

   --
   -- Transport protocol domains:
   --

   ianaTDomains	OBJECT IDENTIFIER ::= { ianaTAddressMIB 1 }

   ianaTDomainUdpIpv4 OBJECT-IDENTITY
       STATUS      current
       DESCRIPTION
           "The UDP over IPv4 transport domain.  The corresponding
            transport address is of type IanaTAddressIPv4."
       ::= { ianaTDomains 1 }

   ianaTDomainUdpIpv6 OBJECT-IDENTITY
       STATUS      current
       DESCRIPTION
           "The UDP over IPv6 transport domain.  The corresponding
            transport address is of type IanaTAddressIPv6 for global
            IPv6 addresses and IanaTAddressIPv6s for scoped IPv6
            addresses."
       ::= { ianaTDomains 2 }

   ianaTDomainTcpIpv4 OBJECT-IDENTITY
       STATUS      current
       DESCRIPTION
           "The TCP over IPv4 transport domain.  The corresponding
            transport address is of type IanaTAddressIPv4."
       ::= { ianaTDomains 3 }

   ianaTDomainTcpIpv6 OBJECT-IDENTITY
       STATUS      current
       DESCRIPTION
           "The TCP over IPv6 transport domain.  The corresponding
            transport address is of type IanaTAddressIPv6 for global
            IPv6 addresses and IanaTAddressIPv6s for scoped IPv6
            addresses."
       ::= { ianaTDomains 4 }

   ianaTDomainLocal OBJECT-IDENTITY
       STATUS      current
       DESCRIPTION
           "The Posix Local IPC transport domain. The corresponding
            transport address is of type IanaTAddressLocal.

            The Posix Local IPC transport domain incorporates the
            well known UNIX domain sockets."
       ::= { ianaTDomains 5 }

   ianaTDomainClns OBJECT-IDENTITY
       STATUS      current
       DESCRIPTION
           "The CLNS transport domain.  The corresponding
            transport address is of type IanaTAddressOSI."
       ::= { ianaTDomains 6 }

   ianaTDomainCons OBJECT-IDENTITY
       STATUS      current
       DESCRIPTION
           "The CONS transport domain.  The corresponding
            transport address is of type IanaTAddressOSI."
       ::= { ianaTDomains 7 }

   ianaTDomainDdp OBJECT-IDENTITY
       STATUS      current
       DESCRIPTION
           "The DDP transport domain.  The corresponding
            transport address is of type IanaTAddressNBP."
       ::= { ianaTDomains 8 }

   ianaTDomainIpx OBJECT-IDENTITY
       STATUS     current
       DESCRIPTION
           "The IPX transport domain.  The corresponding
            transport address is of type IanaTAddressIPX."
       ::= { ianaTDomains 9 }


   --
   -- Textual convention for the transport address types/domains.
   --
   -- The enumerated values of this textual convention SHOULD be
   -- identical to the last sub-identifier of the OID registered
   -- for the same domain.
   --

   IanaTAddressType ::= TEXTUAL-CONVENTION
       STATUS      current
       DESCRIPTION
           "Denotes a kind of transport service. This is the enumerated
            version of the transport domain registrations in this MIB
            module. The enumerated values have the following meaning:

            unknown(0)     An unknown transport address type.

            udpIpv4(1)     UDP-over-IPv4   (ianaTDomainUdpIpv4)

            udpIpv6(2)     UDP-over-IPv6   (ianaTDomainUdpIpv6)

            tcpIpv4(3)     TCP-over-IPv4   (ianaTDomainTcpIpv4)

            tcpIpv6(4)     TCP-over-IPv6   (ianaTDomainTcpIpv6)

            local(5)       POSIX Local IPC (ianaTDomainLocal)

            clns(6)        OSI CLNS        (ianaTDomainClns)

            cons(7)        OSI CONS        (ianaTDomainCons)

            ddp(8)         Appltalk DDP    (ianaTDomainDdp)

            ipx(9)         IPX             (ianaTDomainIpx)
            This textual convention can be used to represent transport
            domains in situations where a syntax of TDomain is unwieldy
            (for example, when used as an index)."
       SYNTAX      INTEGER {
                       other(0),
                       udpIpv4(1),
                       udpIpv6(2),
                       tcpIpv4(3),
                       tcpIpv6(4),
                       local(5),
                       clns(6),
                       cons(7),
                       ddp(8),
                       ipx(9)
                   }

   --
   -- Textual conventions for transport endpoints:
   --

   IanaTAddressIPv4 ::= TEXTUAL-CONVENTION
       DISPLAY-HINT "1d.1d.1d.1d:2d"
       STATUS       current
       DESCRIPTION
           "Represents a TCP-over-IPv4 or a UDP-over-IPv4
            transport address:

             octets       contents                   encoding
              1-4         IPv4 addres                network-byte order
              5-6         TCP or UDP port            network-byte order"
       SYNTAX      OCTET STRING (SIZE (6))

   IanaTAddressIPv6 ::= TEXTUAL-CONVENTION
       DISPLAY-HINT "0a[2x:2x:2x:2x:2x:2x:2x:2x]0a:2d"
       STATUS       current
       DESCRIPTION
           "Represents a TCP-over-IPv6 or a UDP-over-IPv6
            transport address for global IPv6 addresses:

             octets       contents                   encoding
              1-16        IPv6 address               network-byte order
             17-18        TCP or UDP port            network-byte order"
       REFERENCE
           "IP Version 6 Addressing Architecture (RFC 2373)"
       SYNTAX      OCTET STRING (SIZE (18))

   IanaTAddressIPv6s ::= TEXTUAL-CONVENTION
       DISPLAY-HINT "0a[2x:2x:2x:2x:2x:2x:2x:2x%4d]0a:2d"
       STATUS       current
       DESCRIPTION
           "Represents a TCP-over-IPv6 or a UDP-over-IPv6
            transport address for scoped IPv6 addresses:

             octets       contents                   encoding
              1-16        IPv6 address               network-byte order
             17-20        scope identifier           network-byte order
             21-22        TCP or UDP port            network-byte order"
       REFERENCE
           "IP Version 6 Addressing Architecture (RFC 2373)"
       SYNTAX      OCTET STRING (SIZE (22))

   IanaTAddressLocal ::= TEXTUAL-CONVENTION
       DISPLAY-HINT "1a"
       STATUS       current
       DESCRIPTION
           "Represents a POSIX Local IPC transport address:

             octets       contents        	          encoding
              all         POSIX Local IPC address    string

            The Posix Local IPC transport domain subsumes UNIX domain
            sockets."
       REFERENCE
           "Protocol Independent Interfaces (IEEE POSIX 1003.1g)"
       SYNTAX      OCTET STRING (SIZE (1..255))

   IanaTAddressOSI ::= TEXTUAL-CONVENTION
       DISPLAY-HINT "*1x:/1x:"
       STATUS       current
       DESCRIPTION
           "Represents an OSI transport-address:

             octets       contents           encoding
               1          length of NSAP     'n' as an unsigned-integer
                                             (either 0 or from 3 to 20)
             2..(n+1)     NSAP               concrete binary representation
             (n+2)..m     TSEL               string of (up to 64) octets"
       SYNTAX      OCTET STRING (SIZE (1 | 4..85))

   IanaTAddressNBP ::= TEXTUAL-CONVENTION
       STATUS       current
       DESCRIPTION
           "Represents an NBP name:

                octets        contents          encoding
                   1          length of object  'n' as an unsigned integer
                2..(n+1)      object            string of (up to 32) octets
                  n+2         length of type    'p' as an unsigned integer

             (n+3)..(n+2+p)   type              string of (up to 32) octets
                 n+3+p        length of zone    'q' as an unsigned integer
           (n+4+p)..(n+3+p+q) zone              string of (up to 32) octets

            For comparison purposes, strings are case-insensitive. All
            strings may contain any octet other than 255 (hex ff)."
       SYNTAX      OCTET STRING (SIZE (3..99))

   IanaTAddressIPX ::= TEXTUAL-CONVENTION
       DISPLAY-HINT "4x.1x:1x:1x:1x:1x:1x.2d"
       STATUS       current
       DESCRIPTION
           "Represents an IPX address:

             octets       contents           encoding
              1-4         network-number     network-byte order
              5-10        physical-address   network-byte order
             11-12        socket-number      network-byte order"
       SYNTAX      OCTET STRING (SIZE (12))

   END

-- 
--    Copyright (C) The Internet Society (2000). All Rights Reserved.
-- 
--    This document and translations of it may be copied and furnished to
--    others, and derivative works that comment on or otherwise explain it
--    or assist in its implmentation may be prepared, copied, published
--    and distributed, in whole or in part, without restriction of any
--    kind, provided that the above copyright notice and this paragraph
--    are included on all such copies and derivative works. However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
--
