INFORMANT-PERF-CITRIX DEFINITIONS ::= BEGIN

IMPORTS
    MODULE-IDENTITY, OBJECT-TYPE, OBJECT-IDENTITY, Gauge32
        FROM SNMPv2-SMI
    InstanceName, informant
        FROM WTCS;

citrixPerformance MODULE-IDENTITY
    LAST-UPDATED "200806132254Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant Citrix performance
            entities."
    REVISION      "200806132254Z"
    DESCRIPTION
            "The initial revision of this MIB module."
    ::= { informant 41 }

ctxCPUUtilizationMgmtUserTable OBJECT-TYPE
    SYNTAX     SEQUENCE OF CitrixCPUUtilizationMgmtUsrEntry
    MAX-ACCESS not-accessible
    STATUS     current
    DESCRIPTION
	    "A table containing performance information for
	    instances of 'Citrix CPU Utilization Mgmt User'
	    objects."
    ::= { citrixPerformance 1 }

ctxCPUUtilizationMgmtUserEntry OBJECT-TYPE
    SYNTAX     CitrixCPUUtilizationMgmtUsrEntry
    MAX-ACCESS not-accessible
    STATUS     current
    DESCRIPTION
	    "Performance information for one particular
	    instance of 'Citrix CPU Utilization Mgmt User'
	    object."
    INDEX      { ctxcumuInstance }
    ::= { ctxCPUUtilizationMgmtUserTable 1 }

CitrixCPUUtilizationMgmtUsrEntry ::= SEQUENCE {
    ctxcumuInstance InstanceName,
    ctxcumuCPUEntitlement Gauge32,
    ctxcumuCPUReservation Gauge32,
    ctxcumuCPUShares Gauge32,
    ctxcumuCPUUsage Gauge32,
    ctxcumuLongTermCPUUsage Gauge32
}

ctxcumuInstance OBJECT-TYPE
    SYNTAX     InstanceName
    MAX-ACCESS read-only
    STATUS     current
    DESCRIPTION
	    "Instance name."
    ::= { ctxCPUUtilizationMgmtUserEntry 1 }

ctxcumuCPUEntitlement OBJECT-TYPE
    SYNTAX     Gauge32
    MAX-ACCESS read-only
    STATUS     current
    DESCRIPTION
	    "CPU Entitlement is the percentage CPU resource
	    Citrix CPU Utilization Mgmt makes available to
	    a user at a given time. When the CPU resource
	    is fully utilized, Citrix CPU Utilization Mgmt
	    uses the share/reservation assignment and
	    recent CPU consumption of each contending user
	    to determine the CPU entitlement of that user.
	    On multi-processor machines the maximum value
	    of the counter is 100% times the number of
	    logical processors."
    ::= { ctxCPUUtilizationMgmtUserEntry 2 }

ctxcumuCPUReservation OBJECT-TYPE
    SYNTAX     Gauge32
    MAX-ACCESS read-only
    STATUS     current
    DESCRIPTION
	    "CPU Reservation is a percentage of the total
	    machine CPU resource reserved for a user,
	    should that user require it. A value in the
	    range 1-99 indicates that a CPU reservation is
	    applied. Zero indicates that no CPU reservation
	    is being used. When the CPU resource is fully
	    utilized, Citrix CPU Utilization Mgmt uses the
	    reservation when calculating the CPU
	    entitlement of a user."
    ::= { ctxCPUUtilizationMgmtUserEntry 3 }

ctxcumuCPUShares OBJECT-TYPE
    SYNTAX     Gauge32
    MAX-ACCESS read-only
    STATUS     current
    DESCRIPTION
	    "CPU Shares represents the proportion of CPU
	    resource assigned to a user. The value is an
	    integer in the range 1-64. Zero indicates that
	    no CPU shares value is being used. When the CPU
	    resource is fully utilized, Citrix CPU
	    Utilization Mgmt uses the shares value when
	    calculating the CPU entitlement of a user."
    ::= { ctxCPUUtilizationMgmtUserEntry 4 }

ctxcumuCPUUsage OBJECT-TYPE
    SYNTAX     Gauge32
    MAX-ACCESS read-only
    STATUS     current
    DESCRIPTION
	    "CPU Usage is the percentage of CPU resource
	    consumed by a user at a given time, averaged
	    over a few seconds. Used to identify
	    significant consumers of CPU resource and to
	    provide CPU usage accounting data. On
	    multi-processor machines the maximum value of
	    the counter is 100% times the number of logical
	    processors."
    ::= { ctxCPUUtilizationMgmtUserEntry 5 }

ctxcumuLongTermCPUUsage OBJECT-TYPE
    SYNTAX     Gauge32
    MAX-ACCESS read-only
    STATUS     current
    DESCRIPTION
	    "Long-term CPU Usage is the percentage of CPU
	    resource consumed by a user, averaged over a
	    longer period than the CPU Usage counter. On
	    multi-processor machines the maximum value of
	    the counter is 100% times the number of logical
	    processors."
    ::= { ctxCPUUtilizationMgmtUserEntry 6 }

ctxDataLayerTable OBJECT-TYPE
    SYNTAX     SEQUENCE OF CitrixDataLayerEntry
    MAX-ACCESS not-accessible
    STATUS     current
    DESCRIPTION
	    "A table containing performance information for
	    instances of 'Citrix Data Layer V0.1' objects."
    ::= { citrixPerformance 2 }

ctxDataLayerEntry OBJECT-TYPE
    SYNTAX     CitrixDataLayerEntry
    MAX-ACCESS not-accessible
    STATUS     current
    DESCRIPTION
	    "Performance information for one particular
	    instance of 'Citrix Data Layer V0.1' object."
    INDEX      { ctxdlInstance }
    ::= { ctxDataLayerTable 1 }

CitrixDataLayerEntry ::= SEQUENCE {
    ctxdlInstance InstanceName,
    ctxdlCommitsPerSec Gauge32,
    ctxdlContextsPerSec Gauge32,
    ctxdlDeletesPerSec Gauge32,
    ctxdlInsertsPerSec Gauge32,
    ctxdlNumberOfContextsInThePool Gauge32,
    ctxdlNumOfCntxtRequestsWaiting Gauge32,
    ctxdlReadStreamsCreatedPerSec Gauge32,
    ctxdlStreamBytesReadPerSec Gauge32,
    ctxdlStreamBytesWrittenPerSec Gauge32,
    ctxdlStreamsCreatedPerSec Gauge32,
    ctxdlUpdatesPerSec Gauge32,
    ctxdlWriteStreamsCreatedPerSec Gauge32
}

ctxdlInstance OBJECT-TYPE
    SYNTAX     InstanceName
    MAX-ACCESS read-only
    STATUS     current
    DESCRIPTION
	    "Instance name."
    ::= { ctxDataLayerEntry 1 }

ctxdlCommitsPerSec OBJECT-TYPE
    SYNTAX     Gauge32
    MAX-ACCESS read-only
    STATUS     current
    DESCRIPTION
	    "Commits/sec"
    ::= { ctxDataLayerEntry 2 }

ctxdlContextsPerSec OBJECT-TYPE
    SYNTAX     Gauge32
    MAX-ACCESS read-only
    STATUS     current
    DESCRIPTION
	    "Contexts/sec"
    ::= { ctxDataLayerEntry 3 }

ctxdlDeletesPerSec OBJECT-TYPE
    SYNTAX     Gauge32
    MAX-ACCESS read-only
    STATUS     current
    DESCRIPTION
	    "Deletes/sec"
    ::= { ctxDataLayerEntry 4 }

ctxdlInsertsPerSec OBJECT-TYPE
    SYNTAX     Gauge32
    MAX-ACCESS read-only
    STATUS     current
    DESCRIPTION
	    "Inserts/sec"
    ::= { ctxDataLayerEntry 5 }

ctxdlNumberOfContextsInThePool OBJECT-TYPE
    SYNTAX     Gauge32
    MAX-ACCESS read-only
    STATUS     current
    DESCRIPTION
	    "Number of Contexts in the pool"
    ::= { ctxDataLayerEntry 6 }

ctxdlNumOfCntxtRequestsWaiting OBJECT-TYPE
    SYNTAX     Gauge32
    MAX-ACCESS read-only
    STATUS     current
    DESCRIPTION
	    "Number of context requests waiting"
    ::= { ctxDataLayerEntry 7 }

ctxdlReadStreamsCreatedPerSec OBJECT-TYPE
    SYNTAX     Gauge32
    MAX-ACCESS read-only
    STATUS     current
    DESCRIPTION
	    "Read streams created/sec"
    ::= { ctxDataLayerEntry 8 }

ctxdlStreamBytesReadPerSec OBJECT-TYPE
    SYNTAX     Gauge32
    MAX-ACCESS read-only
    STATUS     current
    DESCRIPTION
	    "Stream bytes read/sec"
    ::= { ctxDataLayerEntry 9 }

ctxdlStreamBytesWrittenPerSec OBJECT-TYPE
    SYNTAX     Gauge32
    MAX-ACCESS read-only
    STATUS     current
    DESCRIPTION
	    "Stream bytes written/sec"
    ::= { ctxDataLayerEntry 10 }

ctxdlStreamsCreatedPerSec OBJECT-TYPE
    SYNTAX     Gauge32
    MAX-ACCESS read-only
    STATUS     current
    DESCRIPTION
	    "Streams created/sec"
    ::= { ctxDataLayerEntry 11 }

ctxdlUpdatesPerSec OBJECT-TYPE
    SYNTAX     Gauge32
    MAX-ACCESS read-only
    STATUS     current
    DESCRIPTION
	    "Updates/sec"
    ::= { ctxDataLayerEntry 12 }

ctxdlWriteStreamsCreatedPerSec OBJECT-TYPE
    SYNTAX     Gauge32
    MAX-ACCESS read-only
    STATUS     current
    DESCRIPTION
	    "Write streams created/sec"
    ::= { ctxDataLayerEntry 13 }

ctxIMANetworkingTable OBJECT-TYPE
    SYNTAX     SEQUENCE OF CitrixIMANetworkingEntry
    MAX-ACCESS not-accessible
    STATUS     current
    DESCRIPTION
	    "A table containing performance information for
	    instances of 'Citrix IMA Networking' objects."
    ::= { citrixPerformance 3 }

ctxIMANetworkingEntry OBJECT-TYPE
    SYNTAX     CitrixIMANetworkingEntry
    MAX-ACCESS not-accessible
    STATUS     current
    DESCRIPTION
	    "Performance information for one particular
	    instance of 'Citrix IMA Networking' object."
    INDEX      { ctximanInstance }
    ::= { ctxIMANetworkingTable 1 }

CitrixIMANetworkingEntry ::= SEQUENCE {
    ctximanInstance InstanceName,
    ctximanBytesReceivedPerSec Gauge32,
    ctximanBytesSentPerSec Gauge32,
    ctximanNetworkConnections Gauge32
}

ctximanInstance OBJECT-TYPE
    SYNTAX     InstanceName
    MAX-ACCESS read-only
    STATUS     current
    DESCRIPTION
	    "Instance name."
    ::= { ctxIMANetworkingEntry 1 }

ctximanBytesReceivedPerSec OBJECT-TYPE
    SYNTAX     Gauge32
    MAX-ACCESS read-only
    STATUS     current
    DESCRIPTION
	    "This Counter is for Inbound bytes/sec"
    ::= { ctxIMANetworkingEntry 2 }

ctximanBytesSentPerSec OBJECT-TYPE
    SYNTAX     Gauge32
    MAX-ACCESS read-only
    STATUS     current
    DESCRIPTION
	    "This Counter is for Outbound bytes/sec"
    ::= { ctxIMANetworkingEntry 3 }

ctximanNetworkConnections OBJECT-TYPE
    SYNTAX     Gauge32
    MAX-ACCESS read-only
    STATUS     current
    DESCRIPTION
	    "Number of Active IMA network connections other
	    IMA Servers"
    ::= { ctxIMANetworkingEntry 4 }

citrixLicensing OBJECT IDENTIFIER
    ::= { citrixPerformance 4 }

ctxlAverageCheckInRspTimeMs OBJECT-TYPE
    SYNTAX     Gauge32
    MAX-ACCESS read-only
    STATUS     current
    DESCRIPTION
	    "This Counter displays the average license
	    check-in response time in milliseconds."
    ::= { citrixLicensing 1 }

ctxlAverageCheckOutRspTimeMs OBJECT-TYPE
    SYNTAX     Gauge32
    MAX-ACCESS read-only
    STATUS     current
    DESCRIPTION
	    "This Counter displays the average license
	    check-out response time in milliseconds."
    ::= { citrixLicensing 2 }

ctxlLastRecordCheckInRspTimeMs OBJECT-TYPE
    SYNTAX     Gauge32
    MAX-ACCESS read-only
    STATUS     current
    DESCRIPTION
	    "Ce compteur affiche le dernier temps de rponse
	    enregistr de libration de licence en
	    millisecondes."
    ::= { citrixLicensing 3 }

ctxlLastRecordCheckOutRspTimeMs OBJECT-TYPE
    SYNTAX     Gauge32
    MAX-ACCESS read-only
    STATUS     current
    DESCRIPTION
	    "This Counter displays the last recorded
	    license check-out response time in
	    milliseconds."
    ::= { citrixLicensing 4 }

ctxlServerConnectionFailure OBJECT-TYPE
    SYNTAX     Gauge32
    MAX-ACCESS read-only
    STATUS     current
    DESCRIPTION
	    "This Counter displays the number of minutes
	    that the Citrix MetaFrame Presentation Server
	    has been disconnected from the License Server."
    ::= { citrixLicensing 5 }

ctxlMaximumCheckInRspTimeMs OBJECT-TYPE
    SYNTAX     Gauge32
    MAX-ACCESS read-only
    STATUS     current
    DESCRIPTION
	    "This Counter displays the maximum license
	    check-in response time in milliseconds."
    ::= { citrixLicensing 6 }

ctxlMaximumCheckOutRspTimeMs OBJECT-TYPE
    SYNTAX     Gauge32
    MAX-ACCESS read-only
    STATUS     current
    DESCRIPTION
	    "This Counter displays the maximum license
	    check-out response time in milliseconds."
    ::= { citrixLicensing 7 }

citrixMetaFramePresentationSvr OBJECT-IDENTITY
    STATUS     current
    DESCRIPTION
	    "This object monitors various MetaFrame XP
	    functions"
    ::= { citrixPerformance 5 }

ctxmpsApplEnumerationsPerSec OBJECT-TYPE
    SYNTAX     Gauge32
    MAX-ACCESS read-only
    STATUS     current
    DESCRIPTION
	    "This Counter is for Application
	    Enumeration/sec"
    ::= { citrixMetaFramePresentationSvr 1 }

ctxmpsApplResolutionTimeMs OBJECT-TYPE
    SYNTAX     Gauge32
    MAX-ACCESS read-only
    STATUS     current
    DESCRIPTION
	    "Shows the time in milliseconds that a
	    resolution took to complete"
    ::= { citrixMetaFramePresentationSvr 2 }

ctxmpsApplResolutionFailedPerSec OBJECT-TYPE
    SYNTAX     Gauge32
    MAX-ACCESS read-only
    STATUS     current
    DESCRIPTION
	    "This counter is for Application Resolutions
	    Failed/sec"
    ::= { citrixMetaFramePresentationSvr 3 }

ctxmpsApplResolutionsPerSec OBJECT-TYPE
    SYNTAX     Gauge32
    MAX-ACCESS read-only
    STATUS     current
    DESCRIPTION
	    "This Counter is for Application
	    Resolutions/sec"
    ::= { citrixMetaFramePresentationSvr 4 }

ctxmpsDataStoreConnectionFailure OBJECT-TYPE
    SYNTAX     Gauge32
    MAX-ACCESS read-only
    STATUS     current
    DESCRIPTION
	    "This Counter displays the number of minutes
	    that the Citrix MetaFrame Presentation Server
	    has been disconnected from the Data Store."
    ::= { citrixMetaFramePresentationSvr 5 }

ctxmpsDataStoreBytesRead OBJECT-TYPE
    SYNTAX     Gauge32
    MAX-ACCESS read-only
    STATUS     current
    DESCRIPTION
	    "This Counter displays Number of Bytes read
	    from the IMA DataStore."
    ::= { citrixMetaFramePresentationSvr 6 }

ctxmpsDataStoreBytesReadPerSec OBJECT-TYPE
    SYNTAX     Gauge32
    MAX-ACCESS read-only
    STATUS     current
    DESCRIPTION
	    "This Counter displays Number of Bytes of IMA
	    Data Store data read/sec"
    ::= { citrixMetaFramePresentationSvr 7 }

ctxmpsDataStoreBytesWritePerSec OBJECT-TYPE
    SYNTAX     Gauge32
    MAX-ACCESS read-only
    STATUS     current
    DESCRIPTION
	    "This Counter displays Number of Bytes of IMA
	    Data Store data written/sec"
    ::= { citrixMetaFramePresentationSvr 8 }

ctxmpsDataStoreReads OBJECT-TYPE
    SYNTAX     Gauge32
    MAX-ACCESS read-only
    STATUS     current
    DESCRIPTION
	    "This Counter displays number of times data was
	    read from the IMA DataStore."
    ::= { citrixMetaFramePresentationSvr 9 }

ctxmpsDataStoreReadsPerSec OBJECT-TYPE
    SYNTAX     Gauge32
    MAX-ACCESS read-only
    STATUS     current
    DESCRIPTION
	    "This Counter displays number of times data was
	    read from the IMA DataStore"
    ::= { citrixMetaFramePresentationSvr 10 }

ctxmpsDataStoreWritesPerSec OBJECT-TYPE
    SYNTAX     Gauge32
    MAX-ACCESS read-only
    STATUS     current
    DESCRIPTION
	    "This Counter displays number of times data was
	    written to the IMA Data Store"
    ::= { citrixMetaFramePresentationSvr 11 }

ctxmpsDSGatewayUpdateCount OBJECT-TYPE
    SYNTAX     Gauge32
    MAX-ACCESS read-only
    STATUS     current
    DESCRIPTION
	    "This Counter displays the number of dynamic
	    store update packets sent to remote data
	    collectors."
    ::= { citrixMetaFramePresentationSvr 12 }

ctxmpsDSGatewayUpdateBytesSent OBJECT-TYPE
    SYNTAX     Gauge32
    MAX-ACCESS read-only
    STATUS     current
    DESCRIPTION
	    "This Counter displays the number of bytes of
	    data sent across gateways to remote data
	    collectors."
    ::= { citrixMetaFramePresentationSvr 13 }

ctxmpsDSQueryCount OBJECT-TYPE
    SYNTAX     Gauge32
    MAX-ACCESS read-only
    STATUS     current
    DESCRIPTION
	    "This Counter displays the number of dynamic
	    store queries that have been performed."
    ::= { citrixMetaFramePresentationSvr 14 }

ctxmpsDSQueryRequestBytesReceive OBJECT-TYPE
    SYNTAX     Gauge32
    MAX-ACCESS read-only
    STATUS     current
    DESCRIPTION
	    "This Counter displays the number of bytes of
	    data received in dynamic store query request
	    packets."
    ::= { citrixMetaFramePresentationSvr 15 }

ctxmpsDSQueryResponseBytesSent OBJECT-TYPE
    SYNTAX     Gauge32
    MAX-ACCESS read-only
    STATUS     current
    DESCRIPTION
	    "This Counter displays the number of bytes of
	    data sent in response to dynamic store
	    queries."
    ::= { citrixMetaFramePresentationSvr 16 }

ctxmpsDSUpdateBytesReceived OBJECT-TYPE
    SYNTAX     Gauge32
    MAX-ACCESS read-only
    STATUS     current
    DESCRIPTION
	    "This Counter displays the number of bytes of
	    data received in dynamic store update packets."
    ::= { citrixMetaFramePresentationSvr 17 }

ctxmpsDSUpdatePacketsReceived OBJECT-TYPE
    SYNTAX     Gauge32
    MAX-ACCESS read-only
    STATUS     current
    DESCRIPTION
	    "This Counter displays the number of update
	    packets received by the dynamic store."
    ::= { citrixMetaFramePresentationSvr 18 }

ctxmpsDSUpdateResponseBytesSent OBJECT-TYPE
    SYNTAX     Gauge32
    MAX-ACCESS read-only
    STATUS     current
    DESCRIPTION
	    "This Counter displays the number of bytes of
	    data sent in response to dynamic store update
	    packets."
    ::= { citrixMetaFramePresentationSvr 19 }

ctxmpsDSBytesReadPerSec OBJECT-TYPE
    SYNTAX     Gauge32
    MAX-ACCESS read-only
    STATUS     current
    DESCRIPTION
	    "This Counter displays Number of Bytes of IMA
	    Dynamic Store data read/sec"
    ::= { citrixMetaFramePresentationSvr 20 }

ctxmpsDSBytesWrittenPerSec OBJECT-TYPE
    SYNTAX     Gauge32
    MAX-ACCESS read-only
    STATUS     current
    DESCRIPTION
	    "This Counter displays Number of Bytes of IMA
	    Dynamic Store data written/sec"
    ::= { citrixMetaFramePresentationSvr 21 }

ctxmpsDSReadsPerSec OBJECT-TYPE
    SYNTAX     Gauge32
    MAX-ACCESS read-only
    STATUS     current
    DESCRIPTION
	    "This Counter displays number of times data was
	    read from the IMA Dynamic Store"
    ::= { citrixMetaFramePresentationSvr 22 }

ctxmpsDSWritesPerSec OBJECT-TYPE
    SYNTAX     Gauge32
    MAX-ACCESS read-only
    STATUS     current
    DESCRIPTION
	    "This Counter displays number of times data was
	    written to the IMA Dynamic Store"
    ::= { citrixMetaFramePresentationSvr 23 }

ctxmpsFilteredApplEnumsPerSec OBJECT-TYPE
    SYNTAX     Gauge32
    MAX-ACCESS read-only
    STATUS     current
    DESCRIPTION
	    "This Counter is for Filtered Application
	    Enumeration/sec"
    ::= { citrixMetaFramePresentationSvr 24 }

ctxmpsLCCacheBytesReadPerSec OBJECT-TYPE
    SYNTAX     Gauge32
    MAX-ACCESS read-only
    STATUS     current
    DESCRIPTION
	    "This Counter displays Number of Bytes of IMA
	    Local Host Cache data read/sec"
    ::= { citrixMetaFramePresentationSvr 25 }

ctxmpsLCCacheBytesWrittenPerSec OBJECT-TYPE
    SYNTAX     Gauge32
    MAX-ACCESS read-only
    STATUS     current
    DESCRIPTION
	    "This Counter displays Number of Bytes of IMA
	    Local Host Cache data written/sec"
    ::= { citrixMetaFramePresentationSvr 26 }

ctxmpsLCCacheReadsPerSec OBJECT-TYPE
    SYNTAX     Gauge32
    MAX-ACCESS read-only
    STATUS     current
    DESCRIPTION
	    "This Counter displays number of times data was
	    read from the IMA Local Host Cache"
    ::= { citrixMetaFramePresentationSvr 27 }

ctxmpsLCCacheWritesPerSec OBJECT-TYPE
    SYNTAX     Gauge32
    MAX-ACCESS read-only
    STATUS     current
    DESCRIPTION
	    "This Counter displays number of times data was
	    written to the IMA Local Host Cache"
    ::= { citrixMetaFramePresentationSvr 28 }

ctxmpsMaximumNumberOfXMLThreads OBJECT-TYPE
    SYNTAX     Gauge32
    MAX-ACCESS read-only
    STATUS     current
    DESCRIPTION
	    "This Counter displays the maximum number of
	    XML threads."
    ::= { citrixMetaFramePresentationSvr 29 }

ctxmpsNumberOfXMLThreads OBJECT-TYPE
    SYNTAX     Gauge32
    MAX-ACCESS read-only
    STATUS     current
    DESCRIPTION
	    "This Counter displays the number of XML
	    threads."
    ::= { citrixMetaFramePresentationSvr 30 }

ctxmpsNumberOfBusyXMLThreads OBJECT-TYPE
    SYNTAX     Gauge32
    MAX-ACCESS read-only
    STATUS     current
    DESCRIPTION
	    "This Counter displays the number of busy XML
	    threads."
    ::= { citrixMetaFramePresentationSvr 31 }

ctxmpsResWorkItemQueueExecuteCnt OBJECT-TYPE
    SYNTAX     Gauge32
    MAX-ACCESS read-only
    STATUS     current
    DESCRIPTION
	    "This Counter displays the number of work items
	    that are currently being executed."
    ::= { citrixMetaFramePresentationSvr 32 }

ctxmpsResWorkItemQueueReadyCount OBJECT-TYPE
    SYNTAX     Gauge32
    MAX-ACCESS read-only
    STATUS     current
    DESCRIPTION
	    "This Counter displays the number of work items
	    that are ready to be executed."
    ::= { citrixMetaFramePresentationSvr 33 }

ctxmpsWorkItemQueueExecuteCount OBJECT-TYPE
    SYNTAX     Gauge32
    MAX-ACCESS read-only
    STATUS     current
    DESCRIPTION
	    "This Counter displays the number of work items
	    that are currently being executed."
    ::= { citrixMetaFramePresentationSvr 34 }

ctxmpsWorkItemQueuePendingCount OBJECT-TYPE
    SYNTAX     Gauge32
    MAX-ACCESS read-only
    STATUS     current
    DESCRIPTION
	    "This Counter displays the number of work items
	    that are not yet ready to be executed."
    ::= { citrixMetaFramePresentationSvr 35 }

ctxmpsWorkItemQueueReadyCount OBJECT-TYPE
    SYNTAX     Gauge32
    MAX-ACCESS read-only
    STATUS     current
    DESCRIPTION
	    "This Counter displays the number of work items
	    that are ready to be executed."
    ::= { citrixMetaFramePresentationSvr 36 }

ctxmpsZoneElections OBJECT-TYPE
    SYNTAX     Gauge32
    MAX-ACCESS read-only
    STATUS     current
    DESCRIPTION
	    "This Counter displays number of zone elections
	    that have occurred."
    ::= { citrixMetaFramePresentationSvr 37 }

ctxmpsZoneElectionsWon OBJECT-TYPE
    SYNTAX     Gauge32
    MAX-ACCESS read-only
    STATUS     current
    DESCRIPTION
	    "This Counter displays number of times this
	    server has won a zone election."
    ::= { citrixMetaFramePresentationSvr 38 }

ctxSmartAuditorAgent OBJECT IDENTIFIER
    ::= { citrixPerformance 6 }

ctxsaaActiveRecordingCount OBJECT-TYPE
    SYNTAX     Gauge32
    MAX-ACCESS read-only
    STATUS     current
    DESCRIPTION
	    "The number of sessions presently being
	    recorded."
    ::= { ctxSmartAuditorAgent 1 }

ctxsaaReadSmartAuditorDriverSec OBJECT-TYPE
    SYNTAX     Gauge32
    MAX-ACCESS read-only
    STATUS     current
    DESCRIPTION
	    "The average bytes/sec read from the
	    SmartAuditor Driver."
    ::= { ctxSmartAuditorAgent 2 }

ctxSmartAuditorStorageManager OBJECT IDENTIFIER
    ::= { citrixPerformance 7 }

ctxsasmActiveRecordingCount OBJECT-TYPE
    SYNTAX     Gauge32
    MAX-ACCESS read-only
    STATUS     current
    DESCRIPTION
	    "Number of currently active session
	    recordings."
    ::= { ctxSmartAuditorStorageManager 1 }

ctxsasmMessageBytesPerSec OBJECT-TYPE
    SYNTAX     Gauge32
    MAX-ACCESS read-only
    STATUS     current
    DESCRIPTION
	    "The SmartAuditor Storage Manager throughput
	    rate expressed as number of message bytes
	    received per second."
    ::= { ctxSmartAuditorStorageManager 2 }

ctxsasmMessagesPerSec OBJECT-TYPE
    SYNTAX     Gauge32
    MAX-ACCESS read-only
    STATUS     current
    DESCRIPTION
	    "The SmartAuditor Storage Manager throughput
	    rate expressed as number of messages received
	    per second."
    ::= { ctxSmartAuditorStorageManager 3 }

ctxDesktopBrokerDatabaseService OBJECT IDENTIFIER
    ::= { citrixPerformance 8 }

ctxdbdsHostedDesktopReleasesSec OBJECT-TYPE
    SYNTAX     Gauge32
    MAX-ACCESS read-only
    STATUS     current
    DESCRIPTION
	    "The rate at which virtual machines are being
	    released from execution by clients shutting
	    down Presentation Server sessions."
    ::= { ctxDesktopBrokerDatabaseService 1 }

ctxdbdsHostedDesktopRequestsSec OBJECT-TYPE
    SYNTAX     Gauge32
    MAX-ACCESS read-only
    STATUS     current
    DESCRIPTION
	    "The rate at which virtual machines are being
	    requested for execution by clients running
	    Presentation Server sessions."
    ::= { ctxDesktopBrokerDatabaseService 2 }

ctxdbdsHostedDesktopStateUpdSec OBJECT-TYPE
    SYNTAX     Gauge32
    MAX-ACCESS read-only
    STATUS     current
    DESCRIPTION
	    "The rate at which state updates for virtual
	    machines running in Presentation Server
	    sessions are being received."
    ::= { ctxDesktopBrokerDatabaseService 3 }

ctxICASessionTable OBJECT-TYPE
    SYNTAX     SEQUENCE OF ICASessionEntry
    MAX-ACCESS not-accessible
    STATUS     current
    DESCRIPTION
	    "This object has several counters that can be
	    used to monitor the performance in ICA
	    sessions"
    ::= { citrixPerformance 9 }

ctxICASessionEntry OBJECT-TYPE
    SYNTAX     ICASessionEntry
    MAX-ACCESS not-accessible
    STATUS     current
    DESCRIPTION
	    "Performance information for one particular
	    instance of 'ICA Session' object."
    INDEX      { ctxisInstance }
    ::= { ctxICASessionTable 1 }

ICASessionEntry ::= SEQUENCE {
    ctxisInstance InstanceName,
    ctxisInputAudioBandwidth Gauge32,
    ctxisInputCOM1Bandwidth Gauge32,
    ctxisInputCOM2Bandwidth Gauge32,
    ctxisInputCOMBandwidth Gauge32,
    ctxisInputClipboardBandwidt Gauge32,
    ctxisInputControlChanBandwidth Gauge32,
    ctxisInputDriveBandwidth Gauge32,
    ctxisInputFontDataBandwidth Gauge32,
    ctxisInputLPT1Bandwidth Gauge32,
    ctxisInputLPT2Bandwidth Gauge32,
    ctxisInputLicensingBandwidth Gauge32,
    ctxisInputManagementBandwidth Gauge32,
    ctxisInputPNBandwidth Gauge32,
    ctxisInputPrinterBandwidth Gauge32,
    ctxisInputSeamlessBandwidth Gauge32,
    ctxisInputSessionBandwidth Gauge32,
    ctxisInputSessionCompression Gauge32,
    ctxisInputSessionLineSpeed Gauge32,
    ctxisInputSpeedScreenDataChanBW Gauge32,
    ctxisInputTextEchoBandwidth Gauge32,
    ctxisInputThinWireBandwidth Gauge32,
    ctxisInputVideoFrameBandwidth Gauge32,
    ctxisLatencyLastRecorded Gauge32,
    ctxisLatencySessionAverage Gauge32,
    ctxisLatencySessionDeviation Gauge32,
    ctxisOutputAudioBandwidth Gauge32,
    ctxisOutputCOM1Bandwidth Gauge32,
    ctxisOutputCOM2Bandwidth Gauge32,
    ctxisOutputCOMBandwidth Gauge32,
    ctxisOutputClipboardBandwidth Gauge32,
    ctxisOutputControlChannBandwidth Gauge32,
    ctxisOutputDriveBandwidth Gauge32,
    ctxisOutputFontDataBandwidth Gauge32,
    ctxisOutputLPT1Bandwidth Gauge32,
    ctxisOutputLPT2Bandwidth Gauge32,
    ctxisOutputLicensingBandwidth Gauge32,
    ctxisOutputManagementBandwidth Gauge32,
    ctxisOutputPNBandwidth Gauge32,
    ctxisOutputPrinterBandwidth Gauge32,
    ctxisOutputSeamlessBandwidth Gauge32,
    ctxisOutputSessionBandwidth Gauge32,
    ctxisOutputSessionCompression Gauge32,
    ctxisOutputSessionLineSpeed Gauge32,
    ctxisOutputSpeedScreenDataChanBW Gauge32,
    ctxisOutputTextEchoBandwidth Gauge32,
    ctxisOutputThinWireBandwidth Gauge32,
    ctxisOutputVideoFrameBandwidth Gauge32
}

ctxisInstance OBJECT-TYPE
    SYNTAX     InstanceName
    MAX-ACCESS read-only
    STATUS     current
    DESCRIPTION
	    "Instance name."
    ::= { ctxICASessionEntry 1 }

ctxisInputAudioBandwidth OBJECT-TYPE
    SYNTAX     Gauge32
    MAX-ACCESS read-only
    STATUS     current
    DESCRIPTION
	    "This value represents the bandwidth from
	    client to server traffic on this virtual
	    channel. This is measured in bps"
    ::= { ctxICASessionEntry 2 }

ctxisInputCOM1Bandwidth OBJECT-TYPE
    SYNTAX     Gauge32
    MAX-ACCESS read-only
    STATUS     current
    DESCRIPTION
	    "This value represents the bandwidth from
	    client to server traffic on this virtual
	    channel. This is measured in bps"
    ::= { ctxICASessionEntry 3 }

ctxisInputCOM2Bandwidth OBJECT-TYPE
    SYNTAX     Gauge32
    MAX-ACCESS read-only
    STATUS     current
    DESCRIPTION
	    "This value represents the bandwidth from
	    client to server traffic on this virtual
	    channel. This is measured in bps"
    ::= { ctxICASessionEntry 4 }

ctxisInputCOMBandwidth OBJECT-TYPE
    SYNTAX     Gauge32
    MAX-ACCESS read-only
    STATUS     current
    DESCRIPTION
	    "This value represents the bandwidth from
	    client to server traffic on this virtual
	    channel. This is measured in bps"
    ::= { ctxICASessionEntry 5 }

ctxisInputClipboardBandwidt OBJECT-TYPE
    SYNTAX     Gauge32
    MAX-ACCESS read-only
    STATUS     current
    DESCRIPTION
	    "This value represents the bandwidth from
	    client to server traffic on this virtual
	    channel. This is measured in bps"
    ::= { ctxICASessionEntry 6 }

ctxisInputControlChanBandwidth OBJECT-TYPE
    SYNTAX     Gauge32
    MAX-ACCESS read-only
    STATUS     current
    DESCRIPTION
	    "This value represents the bandwidth from
	    client to server traffic on this virtual
	    channel. This is measured in bps"
    ::= { ctxICASessionEntry 7 }

ctxisInputDriveBandwidth OBJECT-TYPE
    SYNTAX     Gauge32
    MAX-ACCESS read-only
    STATUS     current
    DESCRIPTION
	    "This value represents the bandwidth from
	    client to server traffic on this virtual
	    channel. This is measured in bps"
    ::= { ctxICASessionEntry 8 }

ctxisInputFontDataBandwidth OBJECT-TYPE
    SYNTAX     Gauge32
    MAX-ACCESS read-only
    STATUS     current
    DESCRIPTION
	    "This value represents the bandwidth from
	    client to server traffic on this virtual
	    channel. This is measured in bps"
    ::= { ctxICASessionEntry 9 }

ctxisInputLPT1Bandwidth OBJECT-TYPE
    SYNTAX     Gauge32
    MAX-ACCESS read-only
    STATUS     current
    DESCRIPTION
	    "This value represents the bandwidth from
	    client to server traffic on this virtual
	    channel. This is measured in bps"
    ::= { ctxICASessionEntry 10 }

ctxisInputLPT2Bandwidth OBJECT-TYPE
    SYNTAX     Gauge32
    MAX-ACCESS read-only
    STATUS     current
    DESCRIPTION
	    "This value represents the bandwidth from
	    client to server traffic on this virtual
	    channel. This is measured in bps"
    ::= { ctxICASessionEntry 11 }

ctxisInputLicensingBandwidth OBJECT-TYPE
    SYNTAX     Gauge32
    MAX-ACCESS read-only
    STATUS     current
    DESCRIPTION
	    "This value represents the bandwidth from
	    client to server traffic on this virtual
	    channel. This is measured in bps"
    ::= { ctxICASessionEntry 12 }

ctxisInputManagementBandwidth OBJECT-TYPE
    SYNTAX     Gauge32
    MAX-ACCESS read-only
    STATUS     current
    DESCRIPTION
	    "This value represents the bandwidth from
	    client to server traffic on this virtual
	    channel. This is measured in bps"
    ::= { ctxICASessionEntry 13 }

ctxisInputPNBandwidth OBJECT-TYPE
    SYNTAX     Gauge32
    MAX-ACCESS read-only
    STATUS     current
    DESCRIPTION
	    "This value represents the bandwidth from
	    client to server traffic on this virtual
	    channel. This is measured in bps"
    ::= { ctxICASessionEntry 14 }

ctxisInputPrinterBandwidth OBJECT-TYPE
    SYNTAX     Gauge32
    MAX-ACCESS read-only
    STATUS     current
    DESCRIPTION
	    "This value represents the bandwidth from
	    client to server traffic on this virtual
	    channel. This is measured in bps"
    ::= { ctxICASessionEntry 15 }

ctxisInputSeamlessBandwidth OBJECT-TYPE
    SYNTAX     Gauge32
    MAX-ACCESS read-only
    STATUS     current
    DESCRIPTION
	    "This value represents the bandwidth from
	    client to server traffic on this virtual
	    channel. This is measured in bps"
    ::= { ctxICASessionEntry 16 }

ctxisInputSessionBandwidth OBJECT-TYPE
    SYNTAX     Gauge32
    MAX-ACCESS read-only
    STATUS     current
    DESCRIPTION
	    "This value represents the bandwidth from
	    client to server traffic for a session in bps"
    ::= { ctxICASessionEntry 17 }

ctxisInputSessionCompression OBJECT-TYPE
    SYNTAX     Gauge32
    MAX-ACCESS read-only
    STATUS     current
    DESCRIPTION
	    "This value represents the compression ratio
	    for client to server traffic for a session"
    ::= { ctxICASessionEntry 18 }

ctxisInputSessionLineSpeed OBJECT-TYPE
    SYNTAX     Gauge32
    MAX-ACCESS read-only
    STATUS     current
    DESCRIPTION
	    "This value represents the line speed from
	    client to server for a session in bps"
    ::= { ctxICASessionEntry 19 }

ctxisInputSpeedScreenDataChanBW OBJECT-TYPE
    SYNTAX     Gauge32
    MAX-ACCESS read-only
    STATUS     current
    DESCRIPTION
	    "This value represents the bandwidth from
	    client to server traffic on this virtual
	    channel. This is measured in bps"
    ::= { ctxICASessionEntry 20 }

ctxisInputTextEchoBandwidth OBJECT-TYPE
    SYNTAX     Gauge32
    MAX-ACCESS read-only
    STATUS     current
    DESCRIPTION
	    "This value represents the bandwidth from
	    client to server traffic on this virtual
	    channel. This is measured in bps"
    ::= { ctxICASessionEntry 21 }

ctxisInputThinWireBandwidth OBJECT-TYPE
    SYNTAX     Gauge32
    MAX-ACCESS read-only
    STATUS     current
    DESCRIPTION
	    "This value represents the bandwidth from
	    client to server traffic on this virtual
	    channel. This is measured in bps"
    ::= { ctxICASessionEntry 22 }

ctxisInputVideoFrameBandwidth OBJECT-TYPE
    SYNTAX     Gauge32
    MAX-ACCESS read-only
    STATUS     current
    DESCRIPTION
	    "This value represents the bandwidth from
	    client to server traffic on this virtual
	    channel. This is measured in bps"
    ::= { ctxICASessionEntry 23 }

ctxisLatencyLastRecorded OBJECT-TYPE
    SYNTAX     Gauge32
    MAX-ACCESS read-only
    STATUS     current
    DESCRIPTION
	    "This value represents the last recorded
	    latency measurement for this session."
    ::= { ctxICASessionEntry 24 }

ctxisLatencySessionAverage OBJECT-TYPE
    SYNTAX     Gauge32
    MAX-ACCESS read-only
    STATUS     current
    DESCRIPTION
	    "This value represents the average client
	    latency over the life of a session."
    ::= { ctxICASessionEntry 25 }

ctxisLatencySessionDeviation OBJECT-TYPE
    SYNTAX     Gauge32
    MAX-ACCESS read-only
    STATUS     current
    DESCRIPTION
	    "This value represents the difference between
	    the minimum and maximum measured latency values
	    for a session."
    ::= { ctxICASessionEntry 26 }

ctxisOutputAudioBandwidth OBJECT-TYPE
    SYNTAX     Gauge32
    MAX-ACCESS read-only
    STATUS     current
    DESCRIPTION
	    "This value represents the bandwidth from
	    server to client traffic on this virtual
	    channel. This is measured in bps"
    ::= { ctxICASessionEntry 27 }

ctxisOutputCOM1Bandwidth OBJECT-TYPE
    SYNTAX     Gauge32
    MAX-ACCESS read-only
    STATUS     current
    DESCRIPTION
	    "This value represents the bandwidth from
	    server to client traffic on this virtual
	    channel. This is measured in bps"
    ::= { ctxICASessionEntry 28 }

ctxisOutputCOM2Bandwidth OBJECT-TYPE
    SYNTAX     Gauge32
    MAX-ACCESS read-only
    STATUS     current
    DESCRIPTION
	    "This value represents the bandwidth from
	    server to client traffic on this virtual
	    channel. This is measured in bps"
    ::= { ctxICASessionEntry 29 }

ctxisOutputCOMBandwidth OBJECT-TYPE
    SYNTAX     Gauge32
    MAX-ACCESS read-only
    STATUS     current
    DESCRIPTION
	    "This value represents the bandwidth from
	    server to client traffic on this virtual
	    channel. This is measured in bps"
    ::= { ctxICASessionEntry 30 }

ctxisOutputClipboardBandwidth OBJECT-TYPE
    SYNTAX     Gauge32
    MAX-ACCESS read-only
    STATUS     current
    DESCRIPTION
	    "This value represents the bandwidth from
	    server to client traffic on this virtual
	    channel. This is measured in bps"
    ::= { ctxICASessionEntry 31 }

ctxisOutputControlChannBandwidth OBJECT-TYPE
    SYNTAX     Gauge32
    MAX-ACCESS read-only
    STATUS     current
    DESCRIPTION
	    "This value represents the bandwidth from
	    server to client traffic on this virtual
	    channel. This is measured in bps"
    ::= { ctxICASessionEntry 32 }

ctxisOutputDriveBandwidth OBJECT-TYPE
    SYNTAX     Gauge32
    MAX-ACCESS read-only
    STATUS     current
    DESCRIPTION
	    "This value represents the bandwidth from
	    server to client traffic on this virtual
	    channel. This is measured in bps"
    ::= { ctxICASessionEntry 33 }

ctxisOutputFontDataBandwidth OBJECT-TYPE
    SYNTAX     Gauge32
    MAX-ACCESS read-only
    STATUS     current
    DESCRIPTION
	    "This value represents the bandwidth from
	    server to client traffic on this virtual
	    channel. This is measured in bps"
    ::= { ctxICASessionEntry 34 }

ctxisOutputLPT1Bandwidth OBJECT-TYPE
    SYNTAX     Gauge32
    MAX-ACCESS read-only
    STATUS     current
    DESCRIPTION
	    "This value represents the bandwidth from
	    server to client traffic on this virtual
	    channel. This is measured in bps"
    ::= { ctxICASessionEntry 35 }

ctxisOutputLPT2Bandwidth OBJECT-TYPE
    SYNTAX     Gauge32
    MAX-ACCESS read-only
    STATUS     current
    DESCRIPTION
	    "This value represents the bandwidth from
	    server to client traffic on this virtual
	    channel. This is measured in bps"
    ::= { ctxICASessionEntry 36 }

ctxisOutputLicensingBandwidth OBJECT-TYPE
    SYNTAX     Gauge32
    MAX-ACCESS read-only
    STATUS     current
    DESCRIPTION
	    "This value represents the bandwidth from
	    server to client traffic on this virtual
	    channel. This is measured in bps"
    ::= { ctxICASessionEntry 37 }

ctxisOutputManagementBandwidth OBJECT-TYPE
    SYNTAX     Gauge32
    MAX-ACCESS read-only
    STATUS     current
    DESCRIPTION
	    "This value represents the bandwidth from
	    server to client traffic on this virtual
	    channel. This is measured in bps"
    ::= { ctxICASessionEntry 38 }

ctxisOutputPNBandwidth OBJECT-TYPE
    SYNTAX     Gauge32
    MAX-ACCESS read-only
    STATUS     current
    DESCRIPTION
	    "This value represents the bandwidth from
	    server to client traffic on this virtual
	    channel. This is measured in bps"
    ::= { ctxICASessionEntry 39 }

ctxisOutputPrinterBandwidth OBJECT-TYPE
    SYNTAX     Gauge32
    MAX-ACCESS read-only
    STATUS     current
    DESCRIPTION
	    "This value represents the bandwidth from
	    server to client traffic on this virtual
	    channel. This is measured in bps"
    ::= { ctxICASessionEntry 40 }

ctxisOutputSeamlessBandwidth OBJECT-TYPE
    SYNTAX     Gauge32
    MAX-ACCESS read-only
    STATUS     current
    DESCRIPTION
	    "This value represents the bandwidth from
	    server to client traffic on this virtual
	    channel. This is measured in bps"
    ::= { ctxICASessionEntry 41 }

ctxisOutputSessionBandwidth OBJECT-TYPE
    SYNTAX     Gauge32
    MAX-ACCESS read-only
    STATUS     current
    DESCRIPTION
	    "This value represents the bandwidth from
	    server to client traffic for a session in bps"
    ::= { ctxICASessionEntry 42 }

ctxisOutputSessionCompression OBJECT-TYPE
    SYNTAX     Gauge32
    MAX-ACCESS read-only
    STATUS     current
    DESCRIPTION
	    "This value represents the compression ratio
	    for server to client traffic for a session"
    ::= { ctxICASessionEntry 43 }

ctxisOutputSessionLineSpeed OBJECT-TYPE
    SYNTAX     Gauge32
    MAX-ACCESS read-only
    STATUS     current
    DESCRIPTION
	    "This value represents the line speed from
	    server to client for a session in bps"
    ::= { ctxICASessionEntry 44 }

ctxisOutputSpeedScreenDataChanBW OBJECT-TYPE
    SYNTAX     Gauge32
    MAX-ACCESS read-only
    STATUS     current
    DESCRIPTION
	    "This value represents the bandwidth from
	    server to client traffic on this virtual
	    channel. This is measured in bps"
    ::= { ctxICASessionEntry 45 }

ctxisOutputTextEchoBandwidth OBJECT-TYPE
    SYNTAX     Gauge32
    MAX-ACCESS read-only
    STATUS     current
    DESCRIPTION
	    "This value represents the bandwidth from
	    server to client traffic on this virtual
	    channel. This is measured in bps"
    ::= { ctxICASessionEntry 46 }

ctxisOutputThinWireBandwidth OBJECT-TYPE
    SYNTAX     Gauge32
    MAX-ACCESS read-only
    STATUS     current
    DESCRIPTION
	    "This value represents the bandwidth from
	    server to client traffic on this virtual
	    channel. This is measured in bps"
    ::= { ctxICASessionEntry 47 }

ctxisOutputVideoFrameBandwidth OBJECT-TYPE
    SYNTAX     Gauge32
    MAX-ACCESS read-only
    STATUS     current
    DESCRIPTION
	    "This value represents the bandwidth from
	    server to client traffic on this virtual
	    channel. This is measured in bps"
    ::= { ctxICASessionEntry 48 }

ctxSecureTicketAuthority OBJECT-IDENTITY
    STATUS     current
    DESCRIPTION
	    "The Secure Ticket Authority Service object
	    includes those counters that apply to the
	    Secure Ticket Authority service."
    ::= { citrixPerformance 10 }

ctxstaSTABadDataRequestCount OBJECT-TYPE
    SYNTAX     Gauge32
    MAX-ACCESS read-only
    STATUS     current
    DESCRIPTION
	    "The total number of unsuccessful ticket
	    validation and data retrieval requests during
	    the lifetime of the STA."
    ::= { ctxSecureTicketAuthority 1 }

ctxstaSTABadRefreshRequestCount OBJECT-TYPE
    SYNTAX     Gauge32
    MAX-ACCESS read-only
    STATUS     current
    DESCRIPTION
	    "The total number of unsuccessful ticket
	    refresh requests received during the lifetime
	    of the STA."
    ::= { ctxSecureTicketAuthority 2 }

ctxstaSTABadTicketRequestCount OBJECT-TYPE
    SYNTAX     Gauge32
    MAX-ACCESS read-only
    STATUS     current
    DESCRIPTION
	    "The total number of unsuccessful ticket
	    generation requests received during the
	    lifetime of the STA."
    ::= { ctxSecureTicketAuthority 3 }

ctxstaSTACountOfActiveTickets OBJECT-TYPE
    SYNTAX     Gauge32
    MAX-ACCESS read-only
    STATUS     current
    DESCRIPTION
	    "Total count of active tickets currently held
	    in the STA."
    ::= { ctxSecureTicketAuthority 4 }

ctxstaSTAGoodDataRequestCount OBJECT-TYPE
    SYNTAX     Gauge32
    MAX-ACCESS read-only
    STATUS     current
    DESCRIPTION
	    "The total number of successful ticket
	    validation and data retrieval requests received
	    during the lifetime of the STA."
    ::= { ctxSecureTicketAuthority 5 }

ctxstaSTAGoodRefreshRequestCount OBJECT-TYPE
    SYNTAX     Gauge32
    MAX-ACCESS read-only
    STATUS     current
    DESCRIPTION
	    "The total number of successful ticket refresh
	    requests received during the lifetime of the
	    STA."
    ::= { ctxSecureTicketAuthority 6 }

ctxstaSTAGoodTicketRequestCount OBJECT-TYPE
    SYNTAX     Gauge32
    MAX-ACCESS read-only
    STATUS     current
    DESCRIPTION
	    "The total number of successful ticket
	    generation requests received during the
	    lifetime of the STA."
    ::= { ctxSecureTicketAuthority 7 }

ctxstaSTAPeakAllRequestRate OBJECT-TYPE
    SYNTAX     Gauge32
    MAX-ACCESS read-only
    STATUS     current
    DESCRIPTION
	    "The maximum rate of all monitored activities
	    per second."
    ::= { ctxSecureTicketAuthority 8 }

ctxstaSTAPeakDataRequestRate OBJECT-TYPE
    SYNTAX     Gauge32
    MAX-ACCESS read-only
    STATUS     current
    DESCRIPTION
	    "The maximum rate of data requests per second
	    during the lifetime of the STA."
    ::= { ctxSecureTicketAuthority 9 }

ctxstaSTAPeakTicketRefreshRate OBJECT-TYPE
    SYNTAX     Gauge32
    MAX-ACCESS read-only
    STATUS     current
    DESCRIPTION
	    "The maximum rate of refresh requests per
	    second during the lifetime of the STA."
    ::= { ctxSecureTicketAuthority 10 }

ctxstaSTAPeakTicketRequestRate OBJECT-TYPE
    SYNTAX     Gauge32
    MAX-ACCESS read-only
    STATUS     current
    DESCRIPTION
	    "The maximum rate of ticket generation requests
	    per second during the lifetime of the STA."
    ::= { ctxSecureTicketAuthority 11 }

ctxstaSTATicketTimeoutCount OBJECT-TYPE
    SYNTAX     Gauge32
    MAX-ACCESS read-only
    STATUS     current
    DESCRIPTION
	    "The total number of ticket timeouts that
	    occurred during the lifetime of the STA."
    ::= { ctxSecureTicketAuthority 12 }

END
