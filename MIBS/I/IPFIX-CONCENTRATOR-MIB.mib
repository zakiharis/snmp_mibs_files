-- extracted from draft-kobayashi-ipfix-concentrator-mib-01.txt
-- at Sat Mar  4 06:10:53 2006

   IPFIX-CONCENTRATOR-MIB DEFINITIONS ::= BEGIN

   IMPORTS
       MODULE-IDENTITY, OBJECT-TYPE, Integer32,  mib-2
           FROM SNMPv2-SMI                  -- RFC2578
       TEXTUAL-CONVENTION, RowStatus, DateAndTime, TruthValue
           FROM SNMPv2-TC                   -- RFC2579
       MODULE-COMPLIANCE, OBJECT-GROUP
           FROM SNMPv2-CONF                 -- RFC2580
       InetAddressType, InetAddress
           FROM INET-ADDRESS-MIB;           -- RFC3291

   ipfixConcentratorMIB MODULE-IDENTITY
       LAST-UPDATED "200602161600Z"         -- 15 February 2006
       ORGANIZATION "IETF IPFIX Working Group"
       CONTACT-INFO
           "Editor:
              Atsushi Kobayashi
              NTT Information Sharing Platform Laboratories
              3-9-11 Midori-cho
              Musashino-shi
              180-8585
              Japan
              Phone: +81-422-59-3978>
              Email: akoba@nttv6.net"
       DESCRIPTION
           "The IPFIX concentrator MIB defines managed objects that are
           used by each process in IPFIX concentrator. These objects
           provide information that are instruction rules and supporting
           parameters of each function. These objects can be configured.
           By using these objects, the selection process decides which
           flow records are selected. The storing process decides
           which fields are stored and the aggregation process decides
           how to aggregate these flow records.  These objects support
           information to enable these functions.

           Copyright (C) The Internet Society (2005).  This version
           of this MIB module is part of RFC yyyy;  see the RFC
           itself for full legal notices."
   -- replace yyyy with actual RFC number & remove this noti

   --  Revision history

       REVISION     "200602161600Z"         -- 16 February 2006
       DESCRIPTION
            "Initial version, published as RFC yyyy."
   -- replace yyyy with actual RFC number & remove this notice

       ::= { mib-2 5555 }
   --    ::= { mib-2 XXXX }
   -- XXXX to be assigned by IANA.

   ConcFieldModifier ::= TEXTUAL-CONVENTION
       STATUS  current
       DESCRIPTION
           "This field modifier is used by the aggregation process and
           storing process.  This is used as in the following method.
           method:

           keep(1) - the field that is specified by this value is
               distinguished by each process.

           discard(2) - the field that is specified by this value is
               discarded by each process."
       SYNTAX    INTEGER {
                     keep(1),
                     discard(2)
                 }

   -- Top level structure of the MIB

   concentratorObjects     OBJECT IDENTIFIER
       ::= { ipfixConcentratorMIB 1 }
   concentratorConformance OBJECT IDENTIFIER
       ::= { ipfixConcentratorMIB 2 }

   --------------------------------------------------------------------
   -- objects of collection process
   --------------------------------------------------------------------

   concExtraction OBJECT IDENTIFIER ::= { concentratorObjects 1 }

   --------------------------------------------------------------------
   -- 1: Extraction Function Available
   --------------------------------------------------------------------

   concExtractIsAvail  OBJECT-TYPE
       SYNTAX      TruthValue
       MAX-ACCESS  read-only
       STATUS      current
       DESCRIPTION
           "This object indicates the availability of the function for
           extracting flow records from storage database."
       DEFVAL { false }
       ::= { concExtraction 1 }

   --------------------------------------------------------------------
   -- 2: Extraction Table
   --------------------------------------------------------------------

   concExtractTable  OBJECT-TYPE
       SYNTAX      SEQUENCE OF
                   ConcExtractEntry
       MAX-ACCESS  not-accessible
       STATUS      current
       DESCRIPTION
           "This table lists parameters that are used by extracting
           flow records from the storage database."
       ::= { concExtraction 2 }

   concExtractEntry OBJECT-TYPE
       SYNTAX      ConcExtractEntry
       MAX-ACCESS  not-accessible
       STATUS      current
       DESCRIPTION
           "Defines an entry in the concExtractTable"
       INDEX { concExtractIndex }
       ::= { concExtractTable 1 }

   ConcExtractEntry ::=
       SEQUENCE {
           concExtractIndex              Integer32,
           concExtractEtrIpAddrType      InetAddressType,
           concExtractEtrIpAddr          InetAddress,
           concExtractStartTime          DateAndTime,
           concExtractEndTime            DateAndTime,
           concExtractProcessId          Integer32,
           concExtractRowStatus          RowStatus
       }

   concExtractIndex OBJECT-TYPE
       SYNTAX      Integer32 (1..2147483647)
       MAX-ACCESS  not-accessible
       STATUS      current
       DESCRIPTION
           "Locally arbitrary, but unique identifier of an entry
           in concExtractTable.

           The value is expected to remain constant from a
           re-initialization of the entity's network management system
           to the next re-initialization.

           It is used in entries of the concEtrListTable as
           reference to concExtractTable table and its
           associated parameters."
       ::= { concExtractEntry 1 }

   concExtractEtrIpAddrType OBJECT-TYPE
       SYNTAX      InetAddressType
       MAX-ACCESS  read-create
       STATUS      current
       DESCRIPTION
           "The IP address type of the exporter.  The value for IPv4 is
           ipv4(1).  The value for IPv6 is ipv6(2)."
       ::= { concExtractEntry 2 }

   concExtractEtrIpAddr OBJECT-TYPE
       SYNTAX      InetAddress
       MAX-ACCESS  read-create
       STATUS      current
       DESCRIPTION
           "The IP address is the exporter that is stored in the
           database. The collection process extracts flow records that
           are exported from this exporter address."
       ::= { concExtractEntry 3 }

   concExtractStartTime OBJECT-TYPE
       SYNTAX      DateAndTime
       MAX-ACCESS  read-create
       STATUS      current
       DESCRIPTION
           "This hour is used by extracting flow records.  The
           collection process extracts flow records that are created
           after this time. Then, these flow-records that belong
           in the period of time between concExtractStartTime and
           concExtractEndTime are extracted."
       ::= { concExtractEntry 4 }

   concExtractEndTime OBJECT-TYPE
       SYNTAX      DateAndTime
       MAX-ACCESS  read-create
       STATUS      current
       DESCRIPTION
           "This hour is used by extracting flow records.  The
           collection process does not extract flow records that are
           created after this hour."
       ::= { concExtractEntry 5 }

   concExtractProcessId OBJECT-TYPE
       SYNTAX      Integer32 (0..256)
       MAX-ACCESS  read-only
       STATUS      current
       DESCRIPTION
           "The process id is used by the IPFIX collectng process."
      ::= { concExtractEntry 6 }

   concExtractRowStatus OBJECT-TYPE
       SYNTAX      RowStatus
       MAX-ACCESS  read-create
       STATUS      current
       DESCRIPTION
           "The status of this row of the table."
      ::= { concExtractEntry 7 }

   --------------------------------------------------------------------
   -- Objects of Selection Process
   --------------------------------------------------------------------

   concSelection OBJECT IDENTIFIER ::= { concentratorObjects 2 }

   --------------------------------------------------------------------
   -- 1: Selection Function Available
   --------------------------------------------------------------------

   concSelectIsAvail  OBJECT-TYPE
       SYNTAX      TruthValue
       MAX-ACCESS  read-only
       STATUS      current
       DESCRIPTION
           "This object indicates the availability of the selection
           function."
       DEFVAL { false }
       ::= { concSelection 1 }

   --------------------------------------------------------------------
   -- 2: Selection Match Parameter Set Table
   --------------------------------------------------------------------

   concSelectMatchParamSetTable  OBJECT-TYPE
       SYNTAX      SEQUENCE OF
                   ConcSelectMatchParamSetEntry
       MAX-ACCESS  not-accessible
       STATUS      current
       DESCRIPTION
           "This table lists configurations of match filtering. The
           match filtering is based on IPFIX/PSAMP Information
           Elements.  The parameter set contains the Information Element
           Id, a value or value range, and a mask."
       ::= { concSelection 2 }

   concSelectMatchParamSetEntry OBJECT-TYPE
       SYNTAX      ConcSelectMatchParamSetEntry
       MAX-ACCESS  not-accessible
       STATUS      current
       DESCRIPTION
           "Defines an entry in the concSelectMatchParamSetTable"
       INDEX {
           concSelectMatchIndex,
           concSelectMatchInfoEltId
       }
       ::= { concSelectMatchParamSetTable 1 }

   ConcSelectMatchParamSetEntry ::=
       SEQUENCE {
           concSelectMatchIndex                 Integer32,
           concSelectMatchInfoEltId             Integer32,
           concSelectMatchStartValue            OCTET STRING,
           concSelectMatchEndValue              OCTET STRING,
           concSelectMatchMask                  OCTET STRING,
           concSelectMatchRowStatus             RowStatus
       }

   concSelectMatchIndex OBJECT-TYPE
       SYNTAX      Integer32 (1..2147483647)
       MAX-ACCESS  not-accessible
       STATUS      current
       DESCRIPTION
           "Locally arbitrary, but unique identifier of an entry
           in this parameter set table.

           The value is expected to remain constant from a
           re-initialization of the entity's network management system
           to the next re-initialization.

           It is used in entries of the concBaseAssocTable
           reference to this method and its associated parameter set."
       ::= { concSelectMatchParamSetEntry 1 }

   concSelectMatchInfoEltId OBJECT-TYPE
       SYNTAX      Integer32 (1..2147483647)
       MAX-ACCESS  read-create
       STATUS      current
       DESCRIPTION
           "The id of the information element that is encoded as
           InfoElementId defined in the IPFIX/PSAMP Information
           Models."
       ::= { concSelectMatchParamSetEntry 2 }

   concSelectMatchStartValue OBJECT-TYPE
       SYNTAX      OCTET STRING
       MAX-ACCESS  read-create
       STATUS      current
       DESCRIPTION
           "This indicates the value of the information element or the
           start of the value range.  If concSelectMatchEndValue is
           defined, then the range between the start value and the end
           value is a value range.  If concSelectMatchMask is defined,
           then concSelectMatchEndValue is ignored.  In this case,
           the flow record is selected if the masked value exactly
           matches the start value, concSelectMatchStartValue."
       ::= { concSelectMatchParamSetEntry 3 }

   concSelectMatchEndValue OBJECT-TYPE
       SYNTAX      OCTET STRING
       MAX-ACCESS  read-create
       STATUS      current
       DESCRIPTION
           "The final value of a value range. It should be equal to
           it's default value (''H) if a single value should be
           encoded. It is ignored if concSelectFilterMatchMask is
           defined."
       DEFVAL { ''H }
       ::= { concSelectMatchParamSetEntry 4 }

   concSelectMatchMask OBJECT-TYPE
       SYNTAX      OCTET STRING
       MAX-ACCESS  read-create
       STATUS      current
       DESCRIPTION
           "The selected value of the given information element is
           masked with this value.  The resulting value is compared to
           concSelectMatchStartValue and the flow record is selected
           if they match.  If concSelectFilterMatchEndValue and
           concnetSelectFilterMatchMask are defined at the same time,
           concSelectFilterMatchEndValue is ignored.  Note that a
           mask is not useful for all information elements and, if
           it is specified, the mask has the same data type and encoding
           as the information element referenced by
           concSelectMatchInfoEltId."
       DEFVAL { ''H }
       ::= { concSelectMatchParamSetEntry 5 }

   concSelectMatchRowStatus OBJECT-TYPE
       SYNTAX      RowStatus
       MAX-ACCESS  read-create
       STATUS      current
       DESCRIPTION
           "The status of this row of the table."
       ::= { concSelectMatchParamSetEntry 6 }

   --------------------------------------------------------------------
   -- Objects of Aggregation Process
   --------------------------------------------------------------------

   concAggregation OBJECT IDENTIFIER ::= { concentratorObjects 3 }

   --------------------------------------------------------------------
   -- 1: Aggregation Function Available
   --------------------------------------------------------------------
   concAggrIsAvail  OBJECT-TYPE
       SYNTAX      TruthValue
       MAX-ACCESS  read-only
       STATUS      current
       DESCRIPTION
           "This object indicates the availability of the aggregating
           flow records."
       DEFVAL { false }
       ::= { concAggregation 1 }

   --------------------------------------------------------------------
   -- 2: Aggregation Parameter Set Table
   --------------------------------------------------------------------

   concAggrParamSetTable OBJECT-TYPE
       SYNTAX      SEQUENCE OF
                   ConcAggrParamSetEntry
       MAX-ACCESS  not-accessible
       STATUS      current
       DESCRIPTION
           "This table lists parameters that are used for aggregating
           flow records."
       ::= { concAggregation 2 }

   concAggrParamSetEntry OBJECT-TYPE
       SYNTAX      ConcAggrParamSetEntry
       MAX-ACCESS  not-accessible
       STATUS      current
       DESCRIPTION
           "Defines an entry in the concAggrParamSetTable"
       INDEX { concAggrIndex }
       ::= { concAggrParamSetTable 1 }

   ConcAggrParamSetEntry ::=
       SEQUENCE {
           concAggrIndex                 Integer32,
           concAggrTimeInterval          Integer32,
           concAggrParamRowStatus        RowStatus
       }

   concAggrIndex OBJECT-TYPE
       SYNTAX      Integer32 (1..2147483647)
       MAX-ACCESS  not-accessible
       STATUS      current
       DESCRIPTION
           "Locally arbitrary, but unique identifier of an entry
           in concAggrParamSetTable.
           The value is expected to remain constant from a
           re-initialization of the entity's network management system
           to the next re-initialization.

           It is used in entries of the concBaseAssocTable as
           reference to the concAggrParamSetTable table and its
           associated parameters."
       ::= { concAggrParamSetEntry 1 }

   concAggrTimeInterval OBJECT-TYPE
       SYNTAX      Integer32 (1..2147483647)
       UNITS       "seconds"
       MAX-ACCESS  read-create
       STATUS      current
       DESCRIPTION
           "This object specifies a time interval that is used by the
           aggregation process. This process gathers flow records within
           this time interval and then aggregates flow records that have
           a common property."
       ::= { concAggrParamSetEntry 2 }

   concAggrParamRowStatus OBJECT-TYPE
      SYNTAX      RowStatus
      MAX-ACCESS  read-create
      STATUS      current
      DESCRIPTION
          "The status of this row of the table."
      ::= { concAggrParamSetEntry 3 }

   --------------------------------------------------------------------
   -- 3: Aggregation Field Set Table
   --------------------------------------------------------------------

   concAggrFieldSetTable OBJECT-TYPE
       SYNTAX      SEQUENCE OF
                   ConcAggrFieldSetEntry
       MAX-ACCESS  not-accessible
       STATUS      current
       DESCRIPTION
           "This table lists field modifiers that are used for
           aggregating flow records."
       ::= { concAggregation 3 }

   concAggrFieldSetEntry OBJECT-TYPE
       SYNTAX      ConcAggrFieldSetEntry
       MAX-ACCESS  not-accessible
       STATUS      current
       DESCRIPTION
           "Defines an entry in the concAggrParamSetTable"
       INDEX {
           concAggrIndex,
           concAggrFieldSetId
       }
       ::= { concAggrFieldSetTable 1 }

   ConcAggrFieldSetEntry ::=
       SEQUENCE {
           concAggrFieldSetId            Integer32,
           concAggrFieldModifier         ConcFieldModifier,
           concAggrFieldRowStatus        RowStatus
       }

   concAggrFieldSetId OBJECT-TYPE
       SYNTAX      Integer32 (1..2147483647)
       MAX-ACCESS  read-create
       STATUS      current
       DESCRIPTION
           "This object specifies the id of the information element.
           These are encoded as the InfoEltId that is defined in
           IPFIX/PSAMP Information Models."
       ::= { concAggrFieldSetEntry 2 }

   concAggrFieldModifier  OBJECT-TYPE
       SYNTAX      ConcFieldModifier
       MAX-ACCESS  read-create
       STATUS      current
       DESCRIPTION
           "This field modifier is used by the aggregation process.  If
           the keep modifier of this object is specified, the
           information element of concAggrFieldSetId is
           distinguished in the aggregated flow record. In addition,
           if the information element of concAggrFieldSetId is the
           flow key, this field becomes the key of aggregated flow. If
           it is not the flow key, this field is merged into a single
           counter. If the IP address field and prefix field are
           specified, a significant bit of the IP address field is
           reduced by the prefix. That means the keep modifier of the
           mask value of this IP address is specified."
       DEFVAL { discard }
       ::= { concAggrFieldSetEntry 3 }

   concAggrFieldRowStatus OBJECT-TYPE
      SYNTAX      RowStatus
      MAX-ACCESS  read-create
      STATUS      current
      DESCRIPTION
          "The status of this row of the table."
      ::= { concAggrFieldSetEntry 4 }

   --------------------------------------------------------------------
   -- 4: Aggregation Additional Field Set Table
   --------------------------------------------------------------------

   concAggrAddFieldSetTable OBJECT-TYPE
       SYNTAX      SEQUENCE OF
                   ConcAggrAddFieldSetEntry
       MAX-ACCESS  not-accessible
       STATUS      current
       DESCRIPTION
           "This table lists the information element id that is added to
           the aggregated flow."
       ::= { concAggregation 4 }

   concAggrAddFieldSetEntry OBJECT-TYPE
       SYNTAX      ConcAggrAddFieldSetEntry
       MAX-ACCESS  not-accessible
       STATUS      current
       DESCRIPTION
           "Defines an entry in the concAggrAddFieldSetTable"
       INDEX {
           concAggrIndex,
           concAggrAddFieldSetId
       }
       ::= { concAggrAddFieldSetTable 1 }

   ConcAggrAddFieldSetEntry ::=
       SEQUENCE {
           concAggrAddFieldSetId            Integer32,
           concAggrAddFieldRowStatus        RowStatus
       }

   concAggrAddFieldSetId OBJECT-TYPE
       SYNTAX      Integer32 (1..2147483647)
       MAX-ACCESS  read-create
       STATUS      current
       DESCRIPTION
           "This object specifies the Id of the information element.
           This object is encoded as the InfoEltId that is defined in
           IPFIX/PSAMP Information Models.  This information element
           complements information that is discarded during the
           aggregation process. For example, these information elements
           are the total number of flows in aggregated flow and an
           average number of packets per-flow in aggregated flow.
           If this object is specified as an information element,
           the aggregation process calculates and adds to create this
           field and this information element is included in the
           aggregated flow record."
       ::= { concAggrAddFieldSetEntry 2 }

   concAggrAddFieldRowStatus OBJECT-TYPE
       SYNTAX      RowStatus
       MAX-ACCESS  read-create
       STATUS      current
       DESCRIPTION
           "The status of this row of the table."
       ::= { concAggrAddFieldSetEntry 3 }

   --------------------------------------------------------------------
   -- Objects of Report and Exporting Process
   --------------------------------------------------------------------

   concReport OBJECT IDENTIFIER ::= { concentratorObjects 4 }

   --------------------------------------------------------------------
   -- 1: Report Parameter Set Table
   --------------------------------------------------------------------

   concReportCtrTable OBJECT-TYPE
       SYNTAX      SEQUENCE OF
                   ConcReportCtrEntry
       MAX-ACCESS  not-accessible
       STATUS      current
       DESCRIPTION
           "This table lists collectors to which IPFIX concentrator
           selected flow records are exported."
       ::= { concReport 1 }

   concReportCtrEntry OBJECT-TYPE
       SYNTAX      ConcReportCtrEntry
       MAX-ACCESS  not-accessible
       STATUS      current
       DESCRIPTION
           "Defines an entry in the concReportCtrTable."
       INDEX { concReportCtrIndex }
       ::= { concReportCtrTable 1 }

   ConcReportCtrEntry ::=
       SEQUENCE {
           concReportCtrIndex             Integer32,
           concReportCtrDstIpAddrType     InetAddressType,
           concReportCtrDstIpAddr         InetAddress,
           concReportCtrDstProtocol       Integer32,
           concReportCtrDstPort           Integer32,
           concReportCtrReportsSent       Integer32,
           concReportCtrRowStatus         RowStatus
       }

   concReportCtrIndex OBJECT-TYPE
       SYNTAX      Integer32 (1..2147483647)
       MAX-ACCESS  not-accessible
       STATUS      current
       DESCRIPTION
           "Locally arbitrary, but unique identifier of an entry
            in this collector table.

            The value is expected to remain constant from a
            re-initialization of the entity's network management system
            to the next re-initialization.

            It is used in entries of
            concReportCtrGrTable as reference to this
            collector and its associated parameters."
       ::= { concReportCtrEntry 1 }

   concReportCtrDstIpAddrType OBJECT-TYPE
       SYNTAX      InetAddressType
       MAX-ACCESS  read-create
       STATUS      current
       DESCRIPTION
           "The IP address type of the collector. The value for IPv4
            is ipv4(1). The value for IPv6 is ipv6(2)."
       ::= { concReportCtrEntry 2 }

   concReportCtrDstIpAddr OBJECT-TYPE
       SYNTAX      InetAddress
       MAX-ACCESS  read-create
       STATUS      current
       DESCRIPTION
           "The IP address of the collector."
       ::= { concReportCtrEntry 3 }

   concReportCtrDstProtocol OBJECT-TYPE
       SYNTAX      Integer32 (0..256)
       MAX-ACCESS  read-create
       STATUS      current
       DESCRIPTION
           "Transport protocol used for exporting sampled packets
           to the collector. The recommended protocols are TCP (6),
           UDP (17), and SCTP (132). The default is SCTP."
       DEFVAL { 132 }
       ::= { concReportCtrEntry 4 }

   concReportCtrDstPort OBJECT-TYPE
       SYNTAX      Integer32 (0..65535)
       MAX-ACCESS  read-create
       STATUS      current
       DESCRIPTION
           "Transport protocol port number of the collector."
       DEFVAL { 4739 }
       ::= { concReportCtrEntry 5 }

   concReportCtrReportsSent OBJECT-TYPE
       SYNTAX      Integer32
       MAX-ACCESS  read-only
       STATUS      current
       DESCRIPTION
           "Number of packet reports sent to the collector."
       ::= { concReportCtrEntry 6 }

   concReportCtrRowStatus OBJECT-TYPE
       SYNTAX      RowStatus
       MAX-ACCESS  read-create
       STATUS      current
       DESCRIPTION
           "Status of this row of the table."
       ::= { concReportCtrEntry 7 }

   --------------------------------------------------------------------
   -- 2: Collector Gr Table
   --------------------------------------------------------------------

   concReportCtrGrTable OBJECT-TYPE
       SYNTAX      SEQUENCE OF ConcReportCtrGrEntry
       MAX-ACCESS  not-accessible
       STATUS      current
       DESCRIPTION
           "This table lists groups of collectors to which IPFIX
           concentrator selected flow records are exported
           simultaneously.  If IPFIX concentrator selected flow records
           are exported to only one collector, the group consists of
           exactly one collector."
       ::= { concReport 2 }

   concReportCtrGrEntry OBJECT-TYPE
       SYNTAX      ConcReportCtrGrEntry
       MAX-ACCESS  not-accessible
       STATUS      current
       DESCRIPTION
           "Defines an entry in the
           concReportCtrGrTable."
       INDEX {
           concReportCtrGrIndex,
           concReportCtrIndex
       }
       ::= { concReportCtrGrTable 1 }

   ConcReportCtrGrEntry ::=
       SEQUENCE {
           concReportCtrGrIndex                Integer32,
           concReportCtrGrRowStatus            RowStatus
       }

   concReportCtrGrIndex OBJECT-TYPE
       SYNTAX      Integer32 (1..2147483647)
       MAX-ACCESS  not-accessible
       STATUS      current
       DESCRIPTION
           "Locally arbitrary, but unique identifier of an entry
           in this parameter set table.

           The value is expected to remain constant from a
           re-initialization of the entity's network management system
           to the next re-initialization.

           It is used in entries of the concBaseAssocTable as
           reference to this collector group and its associated
           parameters."
       ::= { concReportCtrGrEntry 1 }

   concReportCtrGrRowStatus OBJECT-TYPE
       SYNTAX      RowStatus
       MAX-ACCESS  read-create
       STATUS      current
       DESCRIPTION
           "The status of this row of the table."
       ::= { concReportCtrGrEntry 3 }

   --------------------------------------------------------------------
   -- 3: (Data) Template Record Table
   --------------------------------------------------------------------

   concReportTemplateRcdTable OBJECT-TYPE
       SYNTAX      SEQUENCE OF ConcReportTemplateRcdEntry
       MAX-ACCESS  not-accessible
       STATUS      current
       DESCRIPTION
           "This table lists templates used by the exporter."
       ::= { concReport 3 }

   concReportTemplateRcdEntry OBJECT-TYPE
       SYNTAX      ConcReportTemplateRcdEntry
       MAX-ACCESS  not-accessible
       STATUS      current
       DESCRIPTION
           "Defines an entry in the concReportTemplateTable."
       INDEX {
           concReportTemplateRcdId,
           concReportTemplateRcdIndex
       }
       ::= { concReportTemplateRcdTable 1 }

   ConcReportTemplateRcdEntry ::=
       SEQUENCE {
           concReportTemplateRcdId             Integer32,
           concReportTemplateRcdIndex          Integer32,
           concReportTemplateRcdInfoEltId      Integer32,
           concReportTemplateRcdRowStatus      RowStatus
       }

   concReportTemplateRcdId OBJECT-TYPE
       SYNTAX      Integer32 (1..2147483647)
       MAX-ACCESS  not-accessible
       STATUS      current
       DESCRIPTION
           "Locally arbitrary, but unique identifier of an entry
           in this template record table.

           The value is expected to remain constant from a
           re-initialization of the entity's network management system
           to the next re-initialization.

           It is used in entries of the concBaseAssocTable as
           reference to this template record and its associated
           parameters. It groups the information element ids in a
           template record."
       ::= { concReportTemplateRcdEntry 1 }

   concReportTemplateRcdIndex OBJECT-TYPE
       SYNTAX      Integer32 (1..2147483647)
       MAX-ACCESS  not-accessible
       STATUS      current
       DESCRIPTION
           "Locally arbitrary, but unique identifier of a
            information element id in the template record identified by
            concReportTemplateRcdId.

            The value is expected to remain constant from a
            re-initialization of the entity's network management system
            to the next re-initialization.

            The concReportTemplateRcdIndex specifies the order
            in which the information element ids are used in the
            template record."
          ::= { concReportTemplateRcdEntry 2 }

   concReportTemplateRcdInfoEltId OBJECT-TYPE
       SYNTAX      Integer32
       MAX-ACCESS  read-only
       STATUS      current
       DESCRIPTION
           "The Information Elt Id at position
            concReportTemplateRcdIndex in the template
            concReportTemplateRcdId. This implicitly gives the
            data type and state values that are exported."
       ::= { concReportTemplateRcdEntry 3 }

   concReportTemplateRcdRowStatus OBJECT-TYPE
       SYNTAX      RowStatus
       MAX-ACCESS  read-create
       STATUS      current
       DESCRIPTION
           "The status of this row of the table."
       ::= { concReportTemplateRcdEntry 4 }

   --------------------------------------------------------------------
   -- Objects of Storing Process
   --------------------------------------------------------------------

   concStoring OBJECT IDENTIFIER ::= { concentratorObjects 5 }

   --------------------------------------------------------------------
   -- 1: Storing Function Available
   --------------------------------------------------------------------

   concStoringIsAvail  OBJECT-TYPE
       SYNTAX      TruthValue
       MAX-ACCESS  read-only
       STATUS      current
       DESCRIPTION
           "This object indicates the availability of the storing
           function."
       DEFVAL { false }
       ::= { concStoring 1 }

   --------------------------------------------------------------------
   -- 2: Storing Parameter Set Table
   --------------------------------------------------------------------

   concStoringParamSetTable  OBJECT-TYPE
       SYNTAX      SEQUENCE OF
                   ConcStoringParamSetEntry
       MAX-ACCESS  not-accessible
       STATUS      current
       DESCRIPTION
           "This table lists the field modifiers that are used for
           storing IPFIX header information."
       ::= { concStoring 2 }

   concStoringParamSetEntry OBJECT-TYPE
       SYNTAX      ConcStoringParamSetEntry
       MAX-ACCESS  not-accessible
       STATUS      current
       DESCRIPTION
           "Defines an entry in the concStoringParamSetTable"
       INDEX { concStoringIndex }
       ::= { concStoringParamSetTable 1 }

   ConcStoringParamSetEntry ::=
       SEQUENCE {
           concStoringIndex                     Integer32,
           concStoringSourceidModifier          ConcFieldModifier,
           concStoringExportTimeModifier        ConcFieldModifier,
           concStoringProcessId                 Integer32,
           concStoringParamRowStatus            RowStatus
       }

   concStoringIndex OBJECT-TYPE
       SYNTAX      Integer32 (1..2147483647)
       MAX-ACCESS  not-accessible
       STATUS      current
       DESCRIPTION
           "Locally arbitrary, but unique identifier of an entry
           in this parameter set table.

           The value is expected to remain constant from one
           re-initialization of the entity's network management system
           to the next re-initialization.

           It is used in entries as the concBaseAssocTable
           reference to this method and its associated parameter set."
       ::= { concStoringParamSetEntry 1 }

   concStoringSourceidModifier OBJECT-TYPE
       SYNTAX      ConcFieldModifier
       MAX-ACCESS  read-create
       STATUS      current
       DESCRIPTION
           "This field modifier is used by the storing process.  If the
           keep modifier of this object is specified, the source Id of
           IPFIX header information is stored in the storage database.
           If the discard modifier of this object is specified, it is
           not stored."
       DEFVAL      { discard }
       ::= { concStoringParamSetEntry 2 }

   concStoringExportTimeModifier OBJECT-TYPE
       SYNTAX      ConcFieldModifier
       MAX-ACCESS  read-create
       STATUS      current
       DESCRIPTION
           "This field modifier is used by the storing process.  If the
           keep modifier of this object is specified, the Export time of
           IPFIX header information is stored in the storage database.
           If the discard modifier of this object is specified, it is
           not stored."
       DEFVAL  { discard }
       ::= { concStoringParamSetEntry 3 }

   concStoringProcessId OBJECT-TYPE
       SYNTAX      Integer32
       MAX-ACCESS  read-only
       STATUS      current
       DESCRIPTION
           "The process id is used by this storing process."
       ::= { concStoringParamSetEntry 4 }

   concStoringParamRowStatus OBJECT-TYPE
       SYNTAX      RowStatus
       MAX-ACCESS  read-create
       STATUS      current
       DESCRIPTION
           "The status of this row of the table."
       ::= { concStoringParamSetEntry 5 }

   --------------------------------------------------------------------
   -- 3: Storing Field Set Table
   --------------------------------------------------------------------
   concStoringFieldSetTable  OBJECT-TYPE
       SYNTAX      SEQUENCE OF
                   ConcStoringFieldSetEntry
       MAX-ACCESS  not-accessible
       STATUS      current
       DESCRIPTION
           "This table lists field modifiers that are used for
           storing flow records."
       ::= { concStoring 3 }

   concStoringFieldSetEntry OBJECT-TYPE
       SYNTAX      ConcStoringFieldSetEntry
       MAX-ACCESS  not-accessible
       STATUS      current
       DESCRIPTION
           "Defines an entry in concStoringFieldSetTable"
       INDEX { concStoringIndex,concStoringInfoEltId }
       ::= { concStoringFieldSetTable 1 }

   ConcStoringFieldSetEntry ::=
       SEQUENCE {
           concStoringInfoEltId                 Integer32,
           concStoringFieldModifier             ConcFieldModifier,
           concStoringRowStatus                 RowStatus
       }

   concStoringInfoEltId OBJECT-TYPE
       SYNTAX      Integer32 (1..2147483647)
       MAX-ACCESS  read-create
       STATUS      current
       DESCRIPTION
           "This object specifies the id of the information element.
           These are encoded as the InfoEltId that is defined in the
           IPFIX/PSAMP Information Models."
       ::= { concStoringFieldSetEntry 2 }

   concStoringFieldModifier OBJECT-TYPE
       SYNTAX      ConcFieldModifier
       MAX-ACCESS  read-create
       STATUS      current
       DESCRIPTION
           "This field modifier is used by the storing process.  If the
           keep modifier of this object is specified, the information
           element of concStoringInfoEltId is stored in the
           storage database.  If the discard modifier of this object is
           specified, the information element of
           concStoringInfoEltId is discarded."
       DEFVAL { discard }
       ::= { concStoringFieldSetEntry 3 }

   concStoringRowStatus OBJECT-TYPE
       SYNTAX      RowStatus
       MAX-ACCESS  read-create
       STATUS      current
       DESCRIPTION
           "The status of this row of the table."
       ::= { concStoringFieldSetEntry 4 }

   --------------------------------------------------------------------
   -- objects of Base Association
   --------------------------------------------------------------------

   concBaseAssociations OBJECT IDENTIFIER ::= { concentratorObjects 6 }

   --------------------------------------------------------------------
   -- 1: Base Association Table
   --------------------------------------------------------------------

   concBaseAssocTable OBJECT-TYPE
       SYNTAX      SEQUENCE OF
                   ConcBaseAssocEntry
       MAX-ACCESS  not-accessible
       STATUS      current
       DESCRIPTION
           "This table lists all Base Associations at the managed node."
       ::= { concBaseAssociations 1 }

   concBaseAssocEntry OBJECT-TYPE
       SYNTAX      ConcBaseAssocEntry
       MAX-ACCESS  not-accessible
       STATUS      current
       DESCRIPTION
           "Defines an entry in the concBaseAssocTable"
       INDEX { concBaseAssocIndex }
       ::= { concBaseAssocTable 1 }

   ConcBaseAssocEntry ::=
       SEQUENCE {
           concBaseAssocIndex                   Integer32,
           concBaseAssocSelectMatchIndex        Integer32,
           concBaseAssocAggrIndex               Integer32,
           concBaseAssocReportCtrGrIndex        Integer32,
           concBaseAssocReportTemplateRcdId     Integer32,
           concBaseAssocStoringIndex            Integer32,
           concBaseAssocMeteringProcessId       Integer32,
           concBaseAssocExtractIndex            Integer32,
           concBaseAssocRowStatus               RowStatus
       }

   concBaseAssocIndex OBJECT-TYPE
       SYNTAX      Integer32 (1..2147483647)
       MAX-ACCESS  not-accessible
       STATUS      current
       DESCRIPTION
           "Locally arbitrary, but unique identifier of an entry
           in this parameter set table.

           The value is expected to remain constant from a
           re-initialization of the entity's network management system
           to the next re-initialization."
       ::= { concBaseAssocEntry 1 }

   concBaseAssocSelectMatchIndex OBJECT-TYPE
       SYNTAX      Integer32 (1..2147483647)
       MAX-ACCESS  read-create
       STATUS      current
       DESCRIPTION
           "This object is the Index of the concSelectMatchIndex
           object.  It links the instance when the identified selection
           match parameter table is applied to the method of selection
           that uses the input flow records."
       ::= { concBaseAssocEntry 2 }

   concBaseAssocAggrIndex OBJECT-TYPE
       SYNTAX      Integer32 (1..2147483647)
       MAX-ACCESS  read-create
       STATUS      current
       DESCRIPTION
           "This object is the Index of the concAggrIndex object. It
           links the instance when the identified aggregation parameter
           set table including the associated table is applied to the
           method of aggregation of selected flow records."
       ::= { concBaseAssocEntry 3 }

   concBaseAssocReportCtrGrIndex OBJECT-TYPE
       SYNTAX      Integer32 (1..2147483647)
       MAX-ACCESS  read-create
       STATUS      current
       DESCRIPTION
           "This object is the index of the collector group to which
           packet reports are sent."
       ::= { concBaseAssocEntry 4 }

   concBaseAssocReportTemplateRcdId OBJECT-TYPE
       SYNTAX      Integer32 (1..2147483647)
       MAX-ACCESS  read-create
       STATUS      current
       DESCRIPTION
           "This object is the Id of a template in the template table.
           It links the instance, concEtrListTable, and template
           together.  The identified template is applied to the stream
           of selected/aggregated flow records."
       ::= { concBaseAssocEntry 5 }

   concBaseAssocStoringIndex OBJECT-TYPE
       SYNTAX      Integer32 (1..2147483647)
       MAX-ACCESS  read-create
       STATUS      current
       DESCRIPTION
           "This object is the index of the concStoringIndex object. It
           links the instance when the identified storing parameter is
           applied to the method of storing of input flow records.  In
           addition, if the index of the concBaseAssocExtractIndex is
           specified, this object SHOULD not be specified."
       ::= { concBaseAssocEntry 6 }

   concBaseAssocMeteringProcessId OBJECT-TYPE
       SYNTAX      Integer32
       MAX-ACCESS  read-only
       STATUS      current
       DESCRIPTION
           "The process Id of the metering process is used by this Base
           Association.  The metering process means the chain of
           selection process and aggregation process,
           and reporting process."
       ::= { concBaseAssocEntry 7 }

   concBaseAssocExtractIndex OBJECT-TYPE
       SYNTAX      Integer32
       MAX-ACCESS  read-only
       STATUS      current
       DESCRIPTION
           "This object is the Index of the concExtractIndex object.
           When it is specified, it links the parameters that are
           used by extracting flow records from the storage database.
           In addition, if the index of the concBaseAssocStoringIndex
           or concExporterListIndex is specified, this object SHOULD
           not be specified."
       ::= { concBaseAssocEntry 8 }

   concBaseAssocRowStatus OBJECT-TYPE
       SYNTAX      RowStatus
       MAX-ACCESS  read-create
       STATUS      current
       DESCRIPTION
           "The status of this row of the table."
       ::= { concBaseAssocEntry 9 }

   --------------------------------------------------------------------
   -- 2: Exporter List Table
   --------------------------------------------------------------------

   concExporterListTable OBJECT-TYPE
       SYNTAX      SEQUENCE OF
                   ConcExporterListEntry
       MAX-ACCESS  not-accessible
       STATUS      current
       DESCRIPTION
              "This table lists the concCollectExporterIndexes
              in the Base Association."
       ::= { concBaseAssociations 2 }

   concExporterListEntry OBJECT-TYPE
       SYNTAX      ConcExporterListEntry
       MAX-ACCESS  not-accessible
       STATUS      current
       DESCRIPTION
           "Defines an entry in concExporterListTable"
       INDEX { concBaseAssocIndex,concExporterListIndex }
       ::= { concExporterListTable 1 }

   ConcExporterListEntry ::=
       SEQUENCE {
           concExporterListIndex                Integer32,
           concExporterListMethod               OBJECT IDENTIFIER,
           concExporterListRowStatus            RowStatus
       }

   concExporterListIndex OBJECT-TYPE
       SYNTAX      Integer32 (1..2147483647)
       MAX-ACCESS  not-accessible
       STATUS      current
       DESCRIPTION
           "Locally arbitrary, but unique identifier of an entry
           in this parameter set table.

           The value is expected to remain constant from a
           re-initialization of the entity's network management system
           to the next re-initialization."
       ::= { concExporterListEntry 2 }

   concExporterListMethod OBJECT-TYPE
       SYNTAX      OBJECT IDENTIFIER
       MAX-ACCESS  read-create
       STATUS      current
       DESCRIPTION
           "The object is represented by a pointer (OID) of the
           collectExporterIndex in IPFIX collector MIB objects.
           If the Base Association deals with only flow records
           from one exporter, the table will hold exactly one entry
           per Base Association. The concExporterListIndex does not
           mean the position in the exporter list."
       ::= { concExporterListEntry 3 }

   concExporterListRowStatus OBJECT-TYPE
       SYNTAX      RowStatus
       MAX-ACCESS  read-create
       STATUS      current
       DESCRIPTION
           "The status of this row of the table."
       ::= { concExporterListEntry 4 }

   --==================================================================
   -- Conformance information
   --==================================================================

   concCompliances OBJECT IDENTIFIER ::= { concentratorConformance 1 }
   concGroups      OBJECT IDENTIFIER ::= { concentratorConformance 2 }

   --==================================================================
   -- Compliance statements
   --==================================================================

   concCompliance MODULE-COMPLIANCE
       STATUS  current
       DESCRIPTION
           "An implementation that complies to this module must
           implement the objects defined in the mandatory groups
           concGroupMetering.
           The imeplementation of all other objects depends on the
           imeplementation of the corresponding functionality in the
           equipment."
       MODULE  -- this module
           MANDATORY-GROUPS {
                             concGroupMetering
                            }
       GROUP concGroupExtracting
       DESCRIPTION
           "These objects must be implementes if the corresponding
           extraction function is implemented in the equipment."
       GROUP concGroupStoring
       DESCRIPTION
           "These objects must be implementes if the corresponding
           storing function is implemented in the equipment."
       ::= { concCompliances 1 }

   --==================================================================
   -- MIB groupings
   --==================================================================

   concGroupMetering OBJECT-GROUP
       OBJECTS {
           concAggrTimeInterval,
           concAggrParamRowStatus,
           concAggrFieldModifier,
           concAggrFieldRowStatus,
           concAggrAddFieldRowStatus,
           concAggrFieldSetId,
           concAggrIsAvail,
           concAggrAddFieldSetId,

           concSelectMatchInfoEltId,
           concSelectMatchStartValue,
           concSelectMatchEndValue,
           concSelectMatchMask,
           concSelectMatchRowStatus,
           concSelectIsAvail,

           concReportCtrDstIpAddrType,
           concReportCtrDstIpAddr,
           concReportCtrDstProtocol,
           concReportCtrDstPort,
           concReportCtrReportsSent,
           concReportCtrRowStatus,
           concReportCtrGrRowStatus,
           concReportTemplateRcdInfoEltId,
           concReportTemplateRcdRowStatus,

           concBaseAssocReportCtrGrIndex,
           concBaseAssocReportTemplateRcdId,
           concBaseAssocSelectMatchIndex,
           concBaseAssocAggrIndex,
           concBaseAssocMeteringProcessId,
           concBaseAssocRowStatus,

           concExporterListMethod,
           concExporterListRowStatus
               }
       STATUS  current
       DESCRIPTION
           "All objects that are basic for the aggregation function
           and the selection function and reporting function."
       ::= { concGroups 1 }

   concGroupExtracting OBJECT-GROUP
       OBJECTS {
           concExtractIsAvail,
           concExtractEtrIpAddrType,
           concExtractEtrIpAddr,
           concExtractStartTime,
           concExtractEndTime,
           concExtractProcessId,
           concExtractRowStatus,

           concBaseAssocExtractIndex
               }
       STATUS  current
       DESCRIPTION
           "All objects that are basic for the extraction function.
           This function is needed for extracting flow records from
           storage database."
       ::= { concGroups 2 }

   concGroupStoring OBJECT-GROUP
       OBJECTS {
           concStoringSourceidModifier,
           concStoringExportTimeModifier,
           concStoringProcessId,
           concStoringParamRowStatus,
           concBaseAssocStoringIndex,
           concStoringRowStatus,
           concStoringFieldModifier,
           concStoringInfoEltId,
           concStoringIsAvail
               }
       STATUS  current
       DESCRIPTION
           "All objects that are basic for the storing function.
           This function is needed for storing flow records to
           storage database."
       ::= { concGroups 3 }

   END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
