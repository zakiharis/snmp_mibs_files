IBM-REC-MIB    DEFINITIONS ::= BEGIN

    IMPORTS
        MODULE-IDENTITY,
        enterprises
            FROM SNMPv2-SMI;

    ibm MODULE-IDENTITY
	      LAST-UPDATED "200207150000Z"
	      ORGANIZATION "IBM Corp."
	      CONTACT-INFO
	      "   IBM Corporation 

		  Postal: 3039 Cornwallis Road,  RTP , Raleigh, NC, 27709
				  Dept. LJZA, Bldg. 205-1, JJ104
				  Phone: Ext: 919-543-6175, Tie: 441-6175,  Fax: Ext: 919-543-4455

		     Tel: 1-800-426-4968

		  E-mail: "
	DESCRIPTION
		"The Structure of Register Information for the
		 IBM Corporation."
    ::= { enterprises 2 }

--   ibmprod                   OBJECT IDENTIFIER ::= { ibm 6 }
--    ibm4psmseries                   OBJECT IDENTIFIER ::= { ibmprod 1 }

END
