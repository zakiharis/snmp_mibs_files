-- MIB generated by miftomib version 1.0a

INTELCORPORATIONICMBGENERICCHASSIS-MIB DEFINITIONS ::= BEGIN

-- This component allows limited monitoring and control ofa remote ICMB 
-- accessed chassis.The Groups in this component are a collection of new 
-- and Standard System MIF Groups.

IMPORTS
	TRAP-TYPE FROM RFC-1215
    OBJECT-TYPE
    FROM RFC-1212
    Counter, enterprises
    FROM RFC1155-SMI
    DisplayString
    FROM RFC1213-MIB;

DmiCounter			::= Counter
DmiInteger			::= INTEGER
DmiOctetstring		::= OCTET STRING
DmiDisplaystring	::= DisplayString
DmiDateX				::= OCTET STRING (SIZE (28))
DmiComponentIndex	::= INTEGER

intel                   OBJECT IDENTIFIER ::= {enterprises 343}
products                OBJECT IDENTIFIER ::= {intel 2}
server-products         OBJECT IDENTIFIER ::= {products 6}
platforms               OBJECT IDENTIFIER ::= {server-products 2}
icmbChassis             OBJECT IDENTIFIER ::= {platforms 5}
dmtfGroups              OBJECT IDENTIFIER ::= {icmbChassis 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This group is required."
	::= {dmtfGroups 1}

eComponentid OBJECT-TYPE
	SYNTAX		SComponentid
	ACCESS		not-accessible
	STATUS		mandatory
	DESCRIPTION	""
	--INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SIcmbState ::= SEQUENCE {
	a12ChassisAvailable                     	DmiInteger,
	a12IcmbId                               	DmiInteger,
	a12SdrDeviceId                          	DmiInteger,
	a12SelDeviceId                          	DmiInteger,
	a12SmDeviceId                           	DmiInteger,
	a12SdrReadState                         	DmiInteger,
	a12EventPollingPeriod                   	DmiInteger,
	a12EventCount                           	DmiInteger,
	a12ManageChassis                        	DmiInteger,
	a12SetAvailablityState                  	DmiInteger,
	a12UniqueId                             	DmiOctetstring,
	a12PreviousAvailabilityStatus           	DmiInteger
}

tIcmbState OBJECT-TYPE
	SYNTAX		SEQUENCE OF SIcmbState
	ACCESS		not-accessible
	STATUS		mandatory
	DESCRIPTION	"Access to information on basic chassis features."
	::= {dmtfGroups 12}

eIcmbState OBJECT-TYPE
	SYNTAX		SIcmbState
	ACCESS		not-accessible
	STATUS		mandatory
	DESCRIPTION	""
	--INDEX		{DmiComponentIndex}
	::= {tIcmbState 1}

a12ChassisAvailable OBJECT-TYPE
	SYNTAX		INTEGER {
		vAvailable                              	(0),
		vShuttingDown                           	(1),
		vUnavailable                            	(2),
		vInitializing                           	(3),
		vUnknown                                	(4),
		vNonaccessible                          	(5),
		vGoingNonaccessible                     	(6)
	}
	ACCESS		read-write
	STATUS		mandatory
	DESCRIPTION	"This attribute indicates whether the chassis is currently
visible on the ICMB."
	::= {eIcmbState 1}

a12IcmbId OBJECT-TYPE
	SYNTAX		DmiInteger
	ACCESS		read-write
	STATUS		mandatory
	DESCRIPTION	"This is the bus ID of the chassis' ICMB bridge."
	::= {eIcmbState 2}

a12SdrDeviceId OBJECT-TYPE
	SYNTAX		DmiInteger
	ACCESS		read-only
	STATUS		mandatory
	DESCRIPTION	"This is the IMB address of the device providing access to
the chassis Sensor Data Repository.
A value of 0xff indicates there is no
such device known."
	::= {eIcmbState 3}

a12SelDeviceId OBJECT-TYPE
	SYNTAX		DmiInteger
	ACCESS		read-only
	STATUS		mandatory
	DESCRIPTION	"This is the IMB address of the device providing access to
thechassis System Event Log.A value of 0xff indicates there is no such device
known."
	::= {eIcmbState 4}

a12SmDeviceId OBJECT-TYPE
	SYNTAX		DmiInteger
	ACCESS		read-only
	STATUS		mandatory
	DESCRIPTION	"This is the IMB address of the device providing access to
thechassis System Management software.A value of 0xff indicates there is
no such device known."
	::= {eIcmbState 5}

a12SdrReadState OBJECT-TYPE
	SYNTAX		INTEGER {
		vFalse                                  	(0),
		vTrue                                   	(1)
	}
	ACCESS		read-write
	STATUS		mandatory
	DESCRIPTION	"This attribute indicates whether the chassis SDR is used
topopulate the sensor tables"
	::= {eIcmbState 6}

a12EventPollingPeriod OBJECT-TYPE
	SYNTAX		DmiInteger
	ACCESS		read-write
	STATUS		mandatory
	DESCRIPTION	"This is the period in seconds between polls for new chassisevent
. A value of 0 disables polling."
	::= {eIcmbState 7}

a12EventCount OBJECT-TYPE
	SYNTAX		DmiInteger
	ACCESS		read-only
	STATUS		mandatory
	DESCRIPTION	"This is the number of chassis events generated."
	::= {eIcmbState 8}

a12ManageChassis OBJECT-TYPE
	SYNTAX		INTEGER {
		vFalse                                  	(0),
		vTrue                                   	(1)
	}
	ACCESS		read-write
	STATUS		mandatory
	DESCRIPTION	"This indicates whether events should be generated for this
chassis"
	::= {eIcmbState 9}

a12SetAvailablityState OBJECT-TYPE
	SYNTAX		DmiInteger
	ACCESS		read-write
	STATUS		mandatory
	DESCRIPTION	"Sets chassis availability state. Writing zero to this attribute
instructs the chassis to become unavailable. Writing non-zero instructs the
chassis to become available."
	::= {eIcmbState 10}

a12UniqueId OBJECT-TYPE
	SYNTAX		DmiOctetstring
	ACCESS		read-write
	STATUS		mandatory
	DESCRIPTION	""
	::= {eIcmbState 11}

a12PreviousAvailabilityStatus OBJECT-TYPE
	SYNTAX		INTEGER {
		vAvailable                              	(0),
		vShuttingDown                           	(1),
		vUnavailable                            	(2),
		vInitializing                           	(3)
	}
	ACCESS		read-write
	STATUS		mandatory
	DESCRIPTION	""
	::= {eIcmbState 12}

SOperationalState ::= SEQUENCE {
	a31OperationalStateInstanceIndex        	DmiInteger,
	a31DeviceGroupIndex                     	DmiInteger,
	a31OperationalStatus                    	DmiInteger,
	a31UsageState                           	DmiInteger,
	a31AvailabilityStatus                   	DmiInteger,
	a31AdministrativeState                  	DmiInteger,
	a31FatalErrorCount                      	DmiCounter,
	a31MajorErrorCount                      	DmiCounter,
	a31WarningErrorCount                    	DmiCounter,
	a31CurrentErrorStatus                   	DmiInteger
}

tOperationalState OBJECT-TYPE
	SYNTAX		SEQUENCE OF SOperationalState
	ACCESS		not-accessible
	STATUS		mandatory
	DESCRIPTION	"This group provides the operational state, usage, and availabili
y status, and administrative state indicators for specific Device Group instance
."
	::= {dmtfGroups 31}

eOperationalState OBJECT-TYPE
	SYNTAX		SOperationalState
	ACCESS		not-accessible
	STATUS		mandatory
	DESCRIPTION	""
	--INDEX		{DmiComponentIndex, a31OperationalStateInstanceIndex}
	::= {tOperationalState 1}

a31OperationalStateInstanceIndex OBJECT-TYPE
	SYNTAX		DmiInteger
	ACCESS		read-only
	STATUS		mandatory
	DESCRIPTION	"The Index into the Operational State table."
	::= {eOperationalState 1}

a31DeviceGroupIndex OBJECT-TYPE
	SYNTAX		DmiInteger
	ACCESS		read-only
	STATUS		mandatory
	DESCRIPTION	"The group ID of the group referencing this instance."
	::= {eOperationalState 2}

a31OperationalStatus OBJECT-TYPE
	SYNTAX		INTEGER {
		vOther                                  	(1),
		vUnknown                                	(2),
		vEnabled                                	(3),
		vDisabled                               	(4),
		vNotApplicable                          	(5)
	}
	ACCESS		read-only
	STATUS		mandatory
	DESCRIPTION	"The operational status of the Device Group instance."
	::= {eOperationalState 3}

a31UsageState OBJECT-TYPE
	SYNTAX		INTEGER {
		vOther                                  	(1),
		vUnknown                                	(2),
		vIdle                                   	(3),
		vActive                                 	(4),
		vBusy                                   	(5),
		vNotApplicable                          	(6)
	}
	ACCESS		read-only
	STATUS		mandatory
	DESCRIPTION	"The usage state of the Device Group instance."
	::= {eOperationalState 4}

a31AvailabilityStatus OBJECT-TYPE
	SYNTAX		INTEGER {
		vOther                                  	(1),
		vUnknown                                	(2),
		vRunning                                	(3),
		vWarning                                	(4),
		vInTest                                 	(5),
		vNotApplicable                          	(6),
		vPowerOff                               	(7),
		vOffLine                                	(8),
		vOffDuty                                	(9),
		vDegraded                               	(10),
		vNotInstalled                           	(11),
		vInstallError                           	(12),
		vPowerSave                              	(13)
	}
	ACCESS		read-only
	STATUS		mandatory
	DESCRIPTION	"The availability status of the Device Group instance."
	::= {eOperationalState 5}

a31AdministrativeState OBJECT-TYPE
	SYNTAX		INTEGER {
		vOther                                  	(1),
		vUnknown                                	(2),
		vLocked                                 	(3),
		vUnlocked                               	(4),
		vNotApplicable                          	(5),
		vShuttingDown                           	(6)
	}
	ACCESS		read-only
	STATUS		mandatory
	DESCRIPTION	"The administrative state of the Device Group instance."
	::= {eOperationalState 6}

a31FatalErrorCount OBJECT-TYPE
	SYNTAX		DmiCounter
	ACCESS		read-only
	STATUS		mandatory
	DESCRIPTION	"The accumulated Fatal or Non-recoverable error count for
this Device Group instance."
	::= {eOperationalState 7}

a31MajorErrorCount OBJECT-TYPE
	SYNTAX		DmiCounter
	ACCESS		read-only
	STATUS		mandatory
	DESCRIPTION	"The accumulated Major or Critical error count for this Device
Group instance."
	::= {eOperationalState 8}

a31WarningErrorCount OBJECT-TYPE
	SYNTAX		DmiCounter
	ACCESS		read-only
	STATUS		mandatory
	DESCRIPTION	"The accumulated Warning or Non-Critical error count for this
Device Group instance."
	::= {eOperationalState 9}

a31CurrentErrorStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"This attribute presents the current error status for this
Device Group instance. The most critical error status in effect should be
presented. I.e. if a part of the Device Group instance is 'Critical', while
other status is 'Non-critical' then the status'Critical' should be reported."
	::= {eOperationalState 10}

SFieldReplaceableUnit ::= SEQUENCE {
	a93FruIndex                             	DmiInteger,
	a93DeviceGroupIndex                     	DmiInteger,
	a93Description                          	DmiDisplaystring,
	a93Manufacturer                         	DmiDisplaystring,
	a93Model                                	DmiDisplaystring,
	a93PartNumber                           	DmiDisplaystring,
	a93FruSerialNumber                      	DmiDisplaystring,
	a93RevisionLevel                        	DmiDisplaystring,
	a93WarrantyStartDate                    	DmiDateX,
	a93WarrantyDuration                     	DmiInteger,
	a93SupportPhoneNumber                   	DmiDisplaystring,
	a93FruInternetUniformResourceLocator    	DmiDisplaystring
}

tFieldReplaceableUnit OBJECT-TYPE
	SYNTAX		SEQUENCE OF SFieldReplaceableUnit
	ACCESS		not-accessible
	STATUS		mandatory
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	::= {dmtfGroups 93}

eFieldReplaceableUnit OBJECT-TYPE
	SYNTAX		SFieldReplaceableUnit
	ACCESS		not-accessible
	STATUS		mandatory
	DESCRIPTION	""
	--INDEX		{DmiComponentIndex, a93FruIndex}
	::= {tFieldReplaceableUnit 1}

a93FruIndex OBJECT-TYPE
	SYNTAX		DmiInteger
	ACCESS		read-only
	STATUS		mandatory
	DESCRIPTION	"The index into the Field Replaceable Unit table."
	::= {eFieldReplaceableUnit 1}

a93DeviceGroupIndex OBJECT-TYPE
	SYNTAX		DmiInteger
	ACCESS		read-only
	STATUS		mandatory
	DESCRIPTION	"The group ID of the group referencing this Field Replaceable
Unitinstance."
	::= {eFieldReplaceableUnit 2}

a93Description OBJECT-TYPE
	SYNTAX		DmiDisplaystring
	ACCESS		read-only
	STATUS		mandatory
	DESCRIPTION	"A clear description of this Field Replaceable Unit."
	::= {eFieldReplaceableUnit 3}

a93Manufacturer OBJECT-TYPE
	SYNTAX		DmiDisplaystring
	ACCESS		read-only
	STATUS		mandatory
	DESCRIPTION	"The name of the company manufacturing or providing this Field
Replaceable Unit."
	::= {eFieldReplaceableUnit 4}

a93Model OBJECT-TYPE
	SYNTAX		DmiDisplaystring
	ACCESS		read-only
	STATUS		mandatory
	DESCRIPTION	"The manufacturer's model number for this Field Replaceable
Unit."
	::= {eFieldReplaceableUnit 5}

a93PartNumber OBJECT-TYPE
	SYNTAX		DmiDisplaystring
	ACCESS		read-only
	STATUS		mandatory
	DESCRIPTION	"A part number by which a replacement part can be ordered
for this Field Replaceable Unit."
	::= {eFieldReplaceableUnit 6}

a93FruSerialNumber OBJECT-TYPE
	SYNTAX		DmiDisplaystring
	ACCESS		read-only
	STATUS		mandatory
	DESCRIPTION	"The manufacturer's serial number for this Field Replaceable
Unit."
	::= {eFieldReplaceableUnit 7}

a93RevisionLevel OBJECT-TYPE
	SYNTAX		DmiDisplaystring
	ACCESS		read-only
	STATUS		mandatory
	DESCRIPTION	"The revision level of this Field Replaceable Unit."
	::= {eFieldReplaceableUnit 8}

a93WarrantyStartDate OBJECT-TYPE
	SYNTAX		DmiDateX
	ACCESS		read-only
	STATUS		mandatory
	DESCRIPTION	"The start date of the service warranty for this Field Replaceabl
 Unit."
	::= {eFieldReplaceableUnit 9}

a93WarrantyDuration OBJECT-TYPE
	SYNTAX		DmiInteger
	ACCESS		read-only
	STATUS		mandatory
	DESCRIPTION	"The total duration of this Field Replaceable Unit warranty
in months."
	::= {eFieldReplaceableUnit 10}

a93SupportPhoneNumber OBJECT-TYPE
	SYNTAX		DmiDisplaystring
	ACCESS		read-only
	STATUS		mandatory
	DESCRIPTION	"The phone number(s) for support for this Field Replaceable
Unit."
	::= {eFieldReplaceableUnit 11}

a93FruInternetUniformResourceLocator OBJECT-TYPE
	SYNTAX		DmiDisplaystring
	ACCESS		read-only
	STATUS		mandatory
	DESCRIPTION	"The Internet Uniform Resource Locator string that can be
used through a World Wide Web browser to obtain further information about
this FRU"
	::= {eFieldReplaceableUnit 12}

SEventGenerationForPhysicalContainer ::= SEQUENCE {
	a116EventType                           	DmiInteger,
	a116EventSeverity                       	DmiInteger,
	a116IsEventState-based                  	DmiInteger,
	a116EventStateKey                       	DmiInteger,
	a116AssociatedGroup                     	DmiDisplaystring,
	a116EventSystem                         	DmiInteger,
	a116EventSubsystem                      	DmiInteger
}

tEventGenerationForPhysicalContainer OBJECT-TYPE
	SYNTAX		SEQUENCE OF SEventGenerationForPhysicalContainer
	ACCESS		not-accessible
	STATUS		mandatory
	DESCRIPTION	""
	::= {dmtfGroups 116}

eEventGenerationForPhysicalContainer OBJECT-TYPE
	SYNTAX		SEventGenerationForPhysicalContainer
	ACCESS		not-accessible
	STATUS		mandatory
	DESCRIPTION	""
	--INDEX		{DmiComponentIndex, a116AssociatedGroup}
	::= {tEventGenerationForPhysicalContainer 1}

a116EventType OBJECT-TYPE
	SYNTAX		INTEGER {
		vSecuritySettingsChange                 	(1),
		vPowerSupplyStatusChange                	(2),
		vCoolingDeviceStatusChange              	(3),
		vPhysicalDeviceStatusChange             	(4),
		vLogicalDeviceStatusChange              	(5),
		vContainerSecurityBreach                	(6),
		vConfigurationError                     	(7),
		vContainerSecurityStatusOk              	(256)
	}
	ACCESS		read-only
	STATUS		mandatory
	DESCRIPTION	"The type of event that has occurred."
	::= {eEventGenerationForPhysicalContainer 1}

a116EventSeverity OBJECT-TYPE
	SYNTAX		INTEGER {
		vMonitor                                	(1),
		vInformation                            	(2),
		vOk                                     	(4),
		vNon-critical1                          	(8),
		vCritical                               	(16),
		vNon-recoverable1                       	(32)
	}
	ACCESS		read-only
	STATUS		mandatory
	DESCRIPTION	"The severity of this event."
	::= {eEventGenerationForPhysicalContainer 2}

a116IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForPhysicalContainer 3}

a116EventStateKey OBJECT-TYPE
	SYNTAX		DmiInteger
	ACCESS		read-only
	STATUS		mandatory
	DESCRIPTION	"A unique, single integer key into the Event State group if
this is a state-based Event. If this is not a state-based Event then this
attribute's value is not defined."
	::= {eEventGenerationForPhysicalContainer 4}

a116AssociatedGroup OBJECT-TYPE
	SYNTAX		DmiDisplaystring
	ACCESS		read-only
	STATUS		mandatory
	DESCRIPTION	"The class name of the group that is associated with the events
defined in this Event Generation group."
	::= {eEventGenerationForPhysicalContainer 5}

a116EventSystem OBJECT-TYPE
	SYNTAX		INTEGER {
		vOther                                  	(0),
		vUnknown                                	(1)
	}
	ACCESS		read-only
	STATUS		mandatory
	DESCRIPTION	"The major functional aspect of the product causing the fault."
	::= {eEventGenerationForPhysicalContainer 6}

a116EventSubsystem OBJECT-TYPE
	SYNTAX		INTEGER {
		vOther                                  	(0),
		vUnknown                                	(1)
	}
	ACCESS		read-only
	STATUS		mandatory
	DESCRIPTION	"The minor functional aspect of the product causing the fault."
	::= {eEventGenerationForPhysicalContainer 7}

SPhysicalContainerGlobalTable ::= SEQUENCE {
	a127ContainerOrChassisType              	DmiInteger,
	a127AssetTag                            	DmiDisplaystring,
	a127ChassisLockPresent                  	DmiInteger,
	a127BootupState                         	DmiInteger,
	a127PowerState                          	DmiInteger,
	a127ThermalState                        	DmiInteger,
	a127FruGroupIndex                       	DmiInteger,
	a127OperationalGroupIndex               	DmiInteger,
	a127ContainerIndex                      	DmiInteger,
	a127ContainerName                       	DmiDisplaystring,
	a127ContainerLocation                   	DmiDisplaystring,
	a127ContainerSecurityStatus             	DmiInteger
}

tPhysicalContainerGlobalTable OBJECT-TYPE
	SYNTAX		SEQUENCE OF SPhysicalContainerGlobalTable
	ACCESS		not-accessible
	STATUS		mandatory
	DESCRIPTION	"This group of attributes describes the fields in a row of
the Physical Container Global Table. This table lists all of the containers
(e.g. chassis, sub-chassis, etc.) included within the component whose structure
is being described."
	::= {dmtfGroups 127}

ePhysicalContainerGlobalTable OBJECT-TYPE
	SYNTAX		SPhysicalContainerGlobalTable
	ACCESS		not-accessible
	STATUS		mandatory
	DESCRIPTION	""
	--INDEX		{DmiComponentIndex, a127ContainerIndex}
	::= {tPhysicalContainerGlobalTable 1}

a127ContainerOrChassisType OBJECT-TYPE
	SYNTAX		INTEGER {
		vOther                                  	(1),
		vUnknown                                	(2),
		vDesktop                                	(3),
		vLowProfileDesktop                      	(4),
		vPizzaBox                               	(5),
		vMiniTower                              	(6),
		vTower                                  	(7),
		vPortable                               	(8),
		vLaptop                                 	(9),
		vNotebook                               	(10),
		vHandHeld                               	(11),
		vDockingStation                         	(12),
		vAllInOne                               	(13),
		vSubNotebook                            	(14),
		vSpace-saving                           	(15),
		vLunchBox                               	(16),
		vMainSystemChassis                      	(17),
		vExpansionChassis                       	(18),
		vSubchassis                             	(19),
		vBusExpansionChassis                    	(20),
		vPeripheralChassis                      	(21),
		vRaidChassis                            	(22),
		vRackMountChassis                       	(23)
	}
	ACCESS		read-only
	STATUS		mandatory
	DESCRIPTION	"The type of container or chassis."
	::= {ePhysicalContainerGlobalTable 1}

a127AssetTag OBJECT-TYPE
	SYNTAX		DmiDisplaystring
	ACCESS		read-write
	STATUS		mandatory
	DESCRIPTION	"The Container asset tag string.This asset tag string is writeabl
 by the system administrator."
	::= {ePhysicalContainerGlobalTable 2}

a127ChassisLockPresent OBJECT-TYPE
	SYNTAX		INTEGER {
		vFalse                                  	(0),
		vTrue                                   	(1)
	}
	ACCESS		read-only
	STATUS		mandatory
	DESCRIPTION	"If true, a chassis lock is present on the Container."
	::= {ePhysicalContainerGlobalTable 3}

a127BootupState OBJECT-TYPE
	SYNTAX		INTEGER {
		vOther                                  	(1),
		vUnknown                                	(2),
		vOk                                     	(3),
		vWarning                                	(4),
		vCritical                               	(5),
		vNon-recoverable                        	(6)
	}
	ACCESS		read-only
	STATUS		mandatory
	DESCRIPTION	"The current state of this system when it booted."
	::= {ePhysicalContainerGlobalTable 4}

a127PowerState OBJECT-TYPE
	SYNTAX		INTEGER {
		vOther                                  	(1),
		vUnknown                                	(2),
		vOk                                     	(3),
		vWarning                                	(4),
		vCritical                               	(5),
		vNon-recoverable                        	(6)
	}
	ACCESS		read-only
	STATUS		mandatory
	DESCRIPTION	"The current state of the power supply for this system."
	::= {ePhysicalContainerGlobalTable 5}

a127ThermalState OBJECT-TYPE
	SYNTAX		INTEGER {
		vOther                                  	(1),
		vUnknown                                	(2),
		vOk                                     	(3),
		vWarning                                	(4),
		vCritical                               	(5),
		vNon-recoverable                        	(6)
	}
	ACCESS		read-only
	STATUS		mandatory
	DESCRIPTION	"The current thermal state of this Container."
	::= {ePhysicalContainerGlobalTable 6}

a127FruGroupIndex OBJECT-TYPE
	SYNTAX		DmiInteger
	ACCESS		read-only
	STATUS		mandatory
	DESCRIPTION	"If this is a Field Replaceable Unit or if it is part of another
FRU, this provides an index into the FRU table; 'value = -1' indicates that
the group is not a FRU."
	::= {ePhysicalContainerGlobalTable 7}

a127OperationalGroupIndex OBJECT-TYPE
	SYNTAX		DmiInteger
	ACCESS		read-only
	STATUS		mandatory
	DESCRIPTION	"The index into the Operational State table for this device
if applicable."
	::= {ePhysicalContainerGlobalTable 8}

a127ContainerIndex OBJECT-TYPE
	SYNTAX		DmiInteger
	ACCESS		read-only
	STATUS		mandatory
	DESCRIPTION	"A unique index for the Physical Container in Physical Container
Global Table."
	::= {ePhysicalContainerGlobalTable 9}

a127ContainerName OBJECT-TYPE
	SYNTAX		DmiDisplaystring
	ACCESS		read-write
	STATUS		mandatory
	DESCRIPTION	"This is any 64-octet long name that the user or system administr
tor wishes to give this specific physical container."
	::= {ePhysicalContainerGlobalTable 10}

a127ContainerLocation OBJECT-TYPE
	SYNTAX		DmiDisplaystring
	ACCESS		read-write
	STATUS		mandatory
	DESCRIPTION	"This attribute is a string name for the location of the containe
. This attribute is Read-Write and may be set to any  appropriate value by
the user. The string may be 128 octets long."
	::= {ePhysicalContainerGlobalTable 11}

a127ContainerSecurityStatus OBJECT-TYPE
	SYNTAX		INTEGER {
		vOther                                  	(1),
		vUnknown                                	(2),
		vNoSecurityBreachDetected               	(3),
		vContainerSecurityBreachAttempted       	(4),
		vContainerSecurityBreached              	(5)
	}
	ACCESS		read-only
	STATUS		mandatory
	DESCRIPTION	"This attribute describes whether the Container is physically
secure or not. This includes the state of the door lock, or the boot devices
or the keyboard or mouse."
	::= {ePhysicalContainerGlobalTable 12}

SMiftomib ::= SEQUENCE {
	a1001MibName                            	DmiDisplaystring,
	a1001MibOid                             	DmiDisplaystring,
	a1001DisableTrap                        	DmiInteger
}

tMiftomib OBJECT-TYPE
	SYNTAX		SEQUENCE OF SMiftomib
	ACCESS		not-accessible
	STATUS		mandatory
	DESCRIPTION	"This group defines attributes required for DMI to
SNMP translati
n."
	::= {dmtfGroups 1001}

eMiftomib OBJECT-TYPE
	SYNTAX		SMiftomib
	ACCESS		not-accessible
	STATUS		mandatory
	DESCRIPTION	""
	--INDEX		{DmiComponentIndex}
	::= {tMiftomib 1}

a1001MibName OBJECT-TYPE
	SYNTAX		DmiDisplaystring
	ACCESS		read-only
	STATUS		mandatory
	DESCRIPTION	"The MIB name that defines this MIF"
	::= {eMiftomib 1}

a1001MibOid OBJECT-TYPE
	SYNTAX		DmiDisplaystring
	ACCESS		read-only
	STATUS		mandatory
	DESCRIPTION	"The MIB Object Identifier that corresponds to this MIF"
	::= {eMiftomib 2}

a1001DisableTrap OBJECT-TYPE
	SYNTAX		DmiInteger
	ACCESS		read-write
	STATUS		mandatory
	DESCRIPTION	"This attribute can be changed to disable sending oftraps
from this component"
	::= {eMiftomib 3}

SSystemControl ::= SEQUENCE {
	a1004Selfid                             	DmiInteger,
	a1004ResetSystem                        	DmiInteger,
	a1004TimedResetIncrement                	DmiInteger,
	a1004TimedResetResolution               	DmiInteger,
	a1004TimeUntilSystemReset               	DmiInteger,
	a1004SystemPowerCapabilities            	DmiInteger,
	a1004SystemPowerStatus                  	DmiInteger,
	a1004EventLoggingCapability             	DmiInteger,
	a1004WatchdogTimerIncrement             	DmiInteger,
	a1004WatchdogTimerResolution            	DmiInteger,
	a1004WatchdogUpdateInterval             	DmiInteger,
	a1004UseSystemWatchdogFeature           	DmiInteger,
	a1004ResetSystemAfterDelay              	DmiInteger,
	a1004SavePersistentData                 	DmiInteger,
	a1004RestoreFactoryDefaults             	DmiInteger,
	a1004ShutdownOs                         	DmiInteger,
	a1004ShutdownOsAndPowerOff              	DmiInteger,
	a1004ShutdownOsAndHardwareReset         	DmiInteger,
	a1004IssueAHardwareNmi                  	DmiInteger
}

tSystemControl OBJECT-TYPE
	SYNTAX		SEQUENCE OF SSystemControl
	ACCESS		not-accessible
	STATUS		mandatory
	DESCRIPTION	"Status and control of global system control features."
	::= {dmtfGroups 1004}

eSystemControl OBJECT-TYPE
	SYNTAX		SSystemControl
	ACCESS		not-accessible
	STATUS		mandatory
	DESCRIPTION	""
	--INDEX		{DmiComponentIndex, a1004Selfid}
	::= {tSystemControl 1}

a1004Selfid OBJECT-TYPE
	SYNTAX		DmiInteger
	ACCESS		read-only
	STATUS		mandatory
	DESCRIPTION	"A unique number that identifies this row."
	::= {eSystemControl 1}

a1004ResetSystem OBJECT-TYPE
	SYNTAX		INTEGER {
		vDoNotReset                             	(0),
		vInitiateReset                          	(1)
	}
	ACCESS		read-write
	STATUS		mandatory
	DESCRIPTION	"Writing to the attribute initiates an immediate
system hard
reset.  The value for this attribute 
is either Do Not Reset or Initiate
Reset."
	::= {eSystemControl 2}

a1004TimedResetIncrement OBJECT-TYPE
	SYNTAX		DmiInteger
	ACCESS		read-only
	STATUS		mandatory
	DESCRIPTION	"This attribute contains the increments in which a 
timed
reset can be set, in microseconds."
	::= {eSystemControl 3}

a1004TimedResetResolution OBJECT-TYPE
	SYNTAX		DmiInteger
	ACCESS		read-only
	STATUS		mandatory
	DESCRIPTION	"This attribute contains the resolution to which a   
Timed
Reset can be set, in microseconds.  For       
example, a resolution of 1
second and an increment  
of 10 seconds would indicate that a 10 second delay

interval setting produces a 9 to 10 second delay.   
"
	::= {eSystemControl 4}

a1004TimeUntilSystemReset OBJECT-TYPE
	SYNTAX		DmiInteger
	ACCESS		read-write
	STATUS		mandatory
	DESCRIPTION	"This attribute contains the interval for timed resets, 
in
units of the Timed Reset Increment attribute.       
Writing a non-zero value,
and setting the Timed Reset  
Enable on, initiates a timed reset countdown.
         
"
	::= {eSystemControl 5}

a1004SystemPowerCapabilities OBJECT-TYPE
	SYNTAX		INTEGER {
		vUnknown                                	(0),
		vUnsupported                            	(1),
		vOnAndOff                               	(2),
		vOffOnly                                	(3),
		vOnOnly                                 	(4)
	}
	ACCESS		read-only
	STATUS		mandatory
	DESCRIPTION	"This attribute describes the system power control 
capabilities.
 It can have one of the following   
values:  Unknown, On And Off, Off Only,
or On Only."
	::= {eSystemControl 6}

a1004SystemPowerStatus OBJECT-TYPE
	SYNTAX		INTEGER {
		vOff                                    	(0),
		vOn                                     	(1)
	}
	ACCESS		read-write
	STATUS		mandatory
	DESCRIPTION	"This attribute provides access to the status and 
control
of system power.  Its value is either On 
or Off."
	::= {eSystemControl 7}

a1004EventLoggingCapability OBJECT-TYPE
	SYNTAX		INTEGER {
		vUnknown                                	(0),
		vUnsupported                            	(1),
		vActive                                 	(2),
		vInactive                               	(3)
	}
	ACCESS		read-only
	STATUS		mandatory
	DESCRIPTION	"This attribute describes the Event Logging Capabilities.
The
attribute value can be : Unknown, Unsupported,
Active, or Inactive. If the
Event logging capability
is Active, the BIOS logs the system errors to the
FLASH.
The LSC reads this FLASH log and takes appropriate 
actions. If this
feature is Inactive, the LSC will read
the values from the system registers
directly.
The Event logging capability can be set to Active or 
Inactive
using the System Configuration Utility (SCU)."
	::= {eSystemControl 8}

a1004WatchdogTimerIncrement OBJECT-TYPE
	SYNTAX		DmiInteger
	ACCESS		read-only
	STATUS		mandatory
	DESCRIPTION	"This attribute contains the increments in which a
watchdog
update interval can be set. This value is
maintained internally by instrumentati
n code 
in microseconds.
In LSC Local Console, this value is shown in Seconds."
	::= {eSystemControl 9}

a1004WatchdogTimerResolution OBJECT-TYPE
	SYNTAX		DmiInteger
	ACCESS		read-only
	STATUS		mandatory
	DESCRIPTION	"Resolution to which a watchdog update interval can be 
set.
 For example, a watchdog timer resolution of 
R microsecond and an watchdog
timer increment of 
I microseconds would indicate that a watchdog update
interva
 setting of N will produce a (N*I)-R to (N*I)
microseconds delay.
In LSC
Local Console, this value is shown in Seconds."
	::= {eSystemControl 10}

a1004WatchdogUpdateInterval OBJECT-TYPE
	SYNTAX		DmiInteger
	ACCESS		read-write
	STATUS		mandatory
	DESCRIPTION	"This attribute specifies the Interval for watchdog 
resets,
in minutes.
If the system software does not update the watchdog
timer within
this interval, a hard reset will occur.
Selecting a non-zero value for this
attribute and 
setting the Use System Watchdog Feature attribute 
to 'On'
starts the watchdog reset timer countdown.
"
	::= {eSystemControl 11}

a1004UseSystemWatchdogFeature OBJECT-TYPE
	SYNTAX		INTEGER {
		vOff                                    	(0),
		vOn                                     	(1)
	}
	ACCESS		read-write
	STATUS		mandatory
	DESCRIPTION	"If this value is On, then the Watchdog feature is
enabled
and the Watchdog Update Interval value is valid.

If enabled this feature
automatically resets the server
if the LSC software does not reset the watchdog
timer
within the specified Watchdog Update Interval.
NOTE : This is a hard
reset that will immediately reset
the system without taking NetWare down.
This might 
result in some files being corrupted."
	::= {eSystemControl 12}

a1004ResetSystemAfterDelay OBJECT-TYPE
	SYNTAX		INTEGER {
		vOff                                    	(0),
		vOn                                     	(1)
	}
	ACCESS		read-write
	STATUS		mandatory
	DESCRIPTION	"This attribute controls whether or not the timed reset 
function
is enabled.  If the value is On, then the     
system will reset when the
Timed Reset Interval expires."
	::= {eSystemControl 13}

a1004SavePersistentData OBJECT-TYPE
	SYNTAX		INTEGER {
		vOff                                    	(0),
		vOn                                     	(1)
	}
	ACCESS		read-write
	STATUS		mandatory
	DESCRIPTION	"When this attribute value is set to ON all the persistent
data
like thresholds are stored into the persistent 
data Table.
"
	::= {eSystemControl 15}

a1004RestoreFactoryDefaults OBJECT-TYPE
	SYNTAX		INTEGER {
		vOff                                    	(0),
		vOn                                     	(1)
	}
	ACCESS		read-write
	STATUS		mandatory
	DESCRIPTION	"When this attribute value is set to ON all the Factory
default
thresholds are restored.
"
	::= {eSystemControl 16}

a1004ShutdownOs OBJECT-TYPE
	SYNTAX		INTEGER {
		vDoNotShutdown                          	(0),
		vShutdownOs                             	(1)
	}
	ACCESS		read-write
	STATUS		mandatory
	DESCRIPTION	"Writing to this attribute initiates an immediate
OS shutdown.
 The value of this attribute is    
either Do Not Shutdown or Shutdown OS."
	::= {eSystemControl 17}

a1004ShutdownOsAndPowerOff OBJECT-TYPE
	SYNTAX		INTEGER {
		vDoNotShutdownAndPowerOff               	(0),
		vShutdownAndPowerOff                    	(1)
	}
	ACCESS		read-write
	STATUS		mandatory
	DESCRIPTION	"Writing to this attribute initiates an immediate
OS shutdown
and Power Off of the system. The value of
this attribute is either Do Not
Shutdown and Power Off or 
Shutdown OS and Power Off."
	::= {eSystemControl 18}

a1004ShutdownOsAndHardwareReset OBJECT-TYPE
	SYNTAX		INTEGER {
		vDoNotShutdownAndHardwareReset          	(0),
		vShutdownAndHardwareReset               	(1)
	}
	ACCESS		read-write
	STATUS		mandatory
	DESCRIPTION	"Writing to this attribute initiates an immediate
OS shutdown.
 The value of this attribute is either 
Do Not Shutdown and Hardware Reset
or Shutdown OS and 
Hardware Reset."
	::= {eSystemControl 19}

a1004IssueAHardwareNmi OBJECT-TYPE
	SYNTAX		INTEGER {
		vDoNotIssueAnNmi                        	(0),
		vIssueAnNmi                             	(1)
	}
	ACCESS		read-write
	STATUS		mandatory
	DESCRIPTION	"Writing to this attribute causes a hardware NMI 
(Non Maskabale
Interrup). It will have one of the two values. 
Issue an NMI, or Do Not Issue
an NMI
"
	::= {eSystemControl 20}

SSystemEventLog ::= SEQUENCE {
	a1006Selfid                             	DmiInteger,
	a1006Timestamp                          	DmiDateX,
	a1006RecordType                         	DmiInteger,
	a1006RecordLength                       	DmiInteger,
	a1006RecordData                         	DmiOctetstring
}

tSystemEventLog OBJECT-TYPE
	SYNTAX		SEQUENCE OF SSystemEventLog
	ACCESS		not-accessible
	STATUS		mandatory
	DESCRIPTION	"This group provides raw access to System Event Log (SEL)
recordsThis data is intended for use by a Service & Support person"
	::= {dmtfGroups 1006}

eSystemEventLog OBJECT-TYPE
	SYNTAX		SSystemEventLog
	ACCESS		not-accessible
	STATUS		mandatory
	DESCRIPTION	""
	--INDEX		{DmiComponentIndex, a1006Selfid}
	::= {tSystemEventLog 1}

a1006Selfid OBJECT-TYPE
	SYNTAX		DmiInteger
	ACCESS		read-only
	STATUS		mandatory
	DESCRIPTION	"A unique number that identifies this row."
	::= {eSystemEventLog 1}

a1006Timestamp OBJECT-TYPE
	SYNTAX		DmiDateX
	ACCESS		read-only
	STATUS		mandatory
	DESCRIPTION	"The time and date when this record was written."
	::= {eSystemEventLog 2}

a1006RecordType OBJECT-TYPE
	SYNTAX		DmiInteger
	ACCESS		read-only
	STATUS		mandatory
	DESCRIPTION	"Type of this record."
	::= {eSystemEventLog 3}

a1006RecordLength OBJECT-TYPE
	SYNTAX		DmiInteger
	ACCESS		read-only
	STATUS		mandatory
	DESCRIPTION	"Length of this record."
	::= {eSystemEventLog 4}

a1006RecordData OBJECT-TYPE
	SYNTAX		DmiOctetstring
	ACCESS		read-only
	STATUS		mandatory
	DESCRIPTION	"Binary Data associated with this record"
	::= {eSystemEventLog 5}

SEventGenerationForIcmbState ::= SEQUENCE {
	a1007EventType                          	DmiInteger,
	a1007EventSeverity                      	DmiInteger,
	a1007IsEventState-based                 	DmiInteger,
	a1007EventStateKey                      	DmiInteger,
	a1007AssociatedGroup                    	DmiDisplaystring,
	a1007EventSystem                        	DmiInteger,
	a1007EventSubsystem                     	DmiInteger
}

tEventGenerationForIcmbState OBJECT-TYPE
	SYNTAX		SEQUENCE OF SEventGenerationForIcmbState
	ACCESS		not-accessible
	STATUS		mandatory
	DESCRIPTION	""
	::= {dmtfGroups 1007}

eEventGenerationForIcmbState OBJECT-TYPE
	SYNTAX		SEventGenerationForIcmbState
	ACCESS		not-accessible
	STATUS		mandatory
	DESCRIPTION	""
	--INDEX		{DmiComponentIndex, a1007AssociatedGroup}
	::= {tEventGenerationForIcmbState 1}

a1007EventType OBJECT-TYPE
	SYNTAX		INTEGER {
		vChassisAvailabilityChange              	(1)
	}
	ACCESS		read-only
	STATUS		mandatory
	DESCRIPTION	"The type of event that has occurred."
	::= {eEventGenerationForIcmbState 1}

a1007EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForIcmbState 2}

a1007IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForIcmbState 3}

a1007EventStateKey OBJECT-TYPE
	SYNTAX		DmiInteger
	ACCESS		read-only
	STATUS		mandatory
	DESCRIPTION	"A unique, single integer key into the Event State group if
this is a state-based Event. If this is not a state-based Event then this
attribute's value is not defined."
	::= {eEventGenerationForIcmbState 4}

a1007AssociatedGroup OBJECT-TYPE
	SYNTAX		DmiDisplaystring
	ACCESS		read-only
	STATUS		mandatory
	DESCRIPTION	"The class name of the group that is associated with the events
defined in this Event Generation group."
	::= {eEventGenerationForIcmbState 5}

a1007EventSystem OBJECT-TYPE
	SYNTAX		INTEGER {
		vOther                                  	(0),
		vUnknown                                	(1)
	}
	ACCESS		read-only
	STATUS		mandatory
	DESCRIPTION	"The major functional aspect of the product causing the fault."
	::= {eEventGenerationForIcmbState 6}

a1007EventSubsystem OBJECT-TYPE
	SYNTAX		INTEGER {
		vOther                                  	(0),
		vUnknown                                	(1)
	}
	ACCESS		read-only
	STATUS		mandatory
	DESCRIPTION	"The minor functional aspect of the product causing the fault."
	::= {eEventGenerationForIcmbState 7}

SEifControl ::= SEQUENCE {
	a2000Status                             	DmiInteger,
	a2000DimContext                         	DmiOctetstring,
	a2000PersistentDataWriteDelay           	DmiInteger,
	a2000EifInterfaceName                   	DmiDisplaystring
}

tEifControl OBJECT-TYPE
	SYNTAX		SEQUENCE OF SEifControl
	ACCESS		not-accessible
	STATUS		mandatory
	DESCRIPTION	"Special control group for use with EIF"
	::= {dmtfGroups 2000}

eEifControl OBJECT-TYPE
	SYNTAX		SEifControl
	ACCESS		not-accessible
	STATUS		mandatory
	DESCRIPTION	""
	--INDEX		{DmiComponentIndex}
	::= {tEifControl 1}

a2000Status OBJECT-TYPE
	SYNTAX		INTEGER {
		vOther1                                 	(1),
		vUnknown1                               	(2),
		vCreatedOnly                            	(3),
		vConstructedOnly                        	(4),
		vFullyOperational                       	(5),
		vIdle1                                  	(6)
	}
	ACCESS		read-write
	STATUS		mandatory
	DESCRIPTION	"Current status of this component as set by EIF"
	::= {eEifControl 1}

a2000DimContext OBJECT-TYPE
	SYNTAX		DmiOctetstring
	ACCESS		read-write
	STATUS		mandatory
	DESCRIPTION	"Opaque data used by DIM objects to obtain their context informat
on from some invocating source. It is assumed that the DIMs will be able
to usefully parse the information in this attribute, as the 'mainline' DMI
code in the CI makes no attempt to understand it."
	::= {eEifControl 2}

a2000PersistentDataWriteDelay OBJECT-TYPE
	SYNTAX		DmiInteger
	ACCESS		read-write
	STATUS		mandatory
	DESCRIPTION	"Defines the timeout from an attribute set operation until
the presistent write operation is invoked. If another set operation takes
place during this period, the timeout timer is reset back to this value,
so a persistent write operation will only take place after the specified
period has elasped with no set operations. Timeout is specified in 1/10 second
quantity. If set to zero, no persistent write operation will occur."
	::= {eEifControl 3}

a2000EifInterfaceName OBJECT-TYPE
	SYNTAX		DmiDisplaystring
	ACCESS		read-only
	STATUS		mandatory
	DESCRIPTION	"EIF Interface Name used to distinguish the component type
this MIF file represents."
	::= {eEifControl 4}

SEifExtensionList ::= SEQUENCE {
	a2001Index                              	DmiInteger,
	a2001Filename                           	DmiDisplaystring
}

tEifExtensionList OBJECT-TYPE
	SYNTAX		SEQUENCE OF SEifExtensionList
	ACCESS		not-accessible
	STATUS		mandatory
	DESCRIPTION	"A specific extension library specification"
	::= {dmtfGroups 2001}

eEifExtensionList OBJECT-TYPE
	SYNTAX		SEifExtensionList
	ACCESS		not-accessible
	STATUS		mandatory
	DESCRIPTION	""
	--INDEX		{DmiComponentIndex, a2001Index}
	::= {tEifExtensionList 1}

a2001Index OBJECT-TYPE
	SYNTAX		DmiInteger
	ACCESS		read-only
	STATUS		mandatory
	DESCRIPTION	"row index"
	::= {eEifExtensionList 1}

a2001Filename OBJECT-TYPE
	SYNTAX		DmiDisplaystring
	ACCESS		read-only
	STATUS		mandatory
	DESCRIPTION	"name of extension library"
	::= {eEifExtensionList 2}

SEventGenerationForEifControl ::= SEQUENCE {
	a2002EventType                          	DmiInteger,
	a2002EventSeverity                      	DmiInteger,
	a2002IsEventState-based                 	DmiInteger,
	a2002EventStateKey                      	DmiInteger,
	a2002AssociatedGroup                    	DmiDisplaystring,
	a2002EventSystem                        	DmiInteger,
	a2002EventSubsystem                     	DmiInteger
}

tEventGenerationForEifControl OBJECT-TYPE
	SYNTAX		SEQUENCE OF SEventGenerationForEifControl
	ACCESS		not-accessible
	STATUS		mandatory
	DESCRIPTION	""
	::= {dmtfGroups 2002}

eEventGenerationForEifControl OBJECT-TYPE
	SYNTAX		SEventGenerationForEifControl
	ACCESS		not-accessible
	STATUS		mandatory
	DESCRIPTION	""
	--INDEX		{DmiComponentIndex, a2002AssociatedGroup}
	::= {tEventGenerationForEifControl 1}

a2002EventType OBJECT-TYPE
	SYNTAX		INTEGER {
		vNoDimContextsCreated                   	(1)
	}
	ACCESS		read-only
	STATUS		mandatory
	DESCRIPTION	"The type of event that has occurred."
	::= {eEventGenerationForEifControl 1}

a2002EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForEifControl 2}

a2002IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForEifControl 3}

a2002EventStateKey OBJECT-TYPE
	SYNTAX		DmiInteger
	ACCESS		read-only
	STATUS		mandatory
	DESCRIPTION	"A unique, single integer key into the Event State group if
this is a state-based Event. If this is not a state-based Event then this
attribute's value is not defined."
	::= {eEventGenerationForEifControl 4}

a2002AssociatedGroup OBJECT-TYPE
	SYNTAX		DmiDisplaystring
	ACCESS		read-only
	STATUS		mandatory
	DESCRIPTION	"The class name of the group that is associated with the events
defined in this Event Generation group."
	::= {eEventGenerationForEifControl 5}

a2002EventSystem OBJECT-TYPE
	SYNTAX		INTEGER {
		vOther                                  	(0),
		vUnknown                                	(1)
	}
	ACCESS		read-only
	STATUS		mandatory
	DESCRIPTION	"The major functional aspect of the product causing the fault."
	::= {eEventGenerationForEifControl 6}

a2002EventSubsystem OBJECT-TYPE
	SYNTAX		INTEGER {
		vOther                                  	(0),
		vUnknown                                	(1)
	}
	ACCESS		read-only
	STATUS		mandatory
	DESCRIPTION	"The minor functional aspect of the product causing the fault."
	::= {eEventGenerationForEifControl 7}

-- Trap definitions

trap1ForPhysicalContainer TRAP-TYPE
    ENTERPRISE eEventGenerationForPhysicalContainer
    VARIABLES  {
	a116EventType,
	a116EventSeverity,
	a116IsEventState-based,
	a116EventStateKey,
	a116AssociatedGroup,
	a116EventSystem,
	a116EventSubsystem
       }

    DESCRIPTION "Container Security Breached"

    ::= 6

trap2ForPhysicalContainer TRAP-TYPE
    ENTERPRISE eEventGenerationForPhysicalContainer
    VARIABLES  {
	a116EventType,
	a116EventSeverity,
	a116IsEventState-based,
	a116EventStateKey,
	a116AssociatedGroup,
	a116EventSystem,
	a116EventSubsystem
       }

    DESCRIPTION "Container Secured"

    ::= 256


trap1ForIcmbState TRAP-TYPE
    ENTERPRISE eEventGenerationForIcmbState
    VARIABLES  {
	a1007EventType,
	a1007EventSeverity,
	a1007IsEventState-based,
	a1007EventStateKey,
	a1007AssociatedGroup,
	a1007EventSystem,
	a1007EventSubsystem
       }

    DESCRIPTION "Chassis availability change"

    ::= 1

trap1ForEifControl TRAP-TYPE
    ENTERPRISE eEventGenerationForEifControl
    VARIABLES  {
	a2002EventType,
	a2002EventSeverity,
	a2002IsEventState-based,
	a2002EventStateKey,
	a2002AssociatedGroup,
	a2002EventSystem,
	a2002EventSubsystem
       }

    DESCRIPTION "No DIM Context created"

    ::= 1

END
