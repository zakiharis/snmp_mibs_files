IBM-SYSTEM-STORAGE-MIB DEFINITIONS ::= BEGIN

IMPORTS
   OBJECT-TYPE
        FROM RFC-1212

   TRAP-TYPE
        FROM RFC-1215

    DateAndTime, TruthValue
            FROM SNMPv2-TC

   ibmStorage,
   Boolean, Uint8, Sint8, Uint16, Sint16, Uint32,
   Sint32, Uint64, Sint64, Real32, Real64, String, Datetime
      FROM IBM-SYSTEM-MIB;

ibmStorageTrap       OBJECT IDENTIFIER ::= { ibmStorage 1 }
ibmStorageTrapInfo   OBJECT IDENTIFIER ::= { ibmStorage 2 }

--
-- ibmStorageController
--
ibmStorageControllerTable OBJECT-TYPE
   SYNTAX         SEQUENCE OF IbmStorageControllerEntry
   ACCESS         not-accessible
   STATUS         mandatory
   DESCRIPTION    "This table describes the asset information of the
                   Storage Controller objects"
   REFERENCE      "CIM_CARD"
::= { ibmStorage 3 }

ibmStorageControllerEntry OBJECT-TYPE
   SYNTAX         IbmStorageControllerEntry
   ACCESS         not-accessible
   STATUS         mandatory
   DESCRIPTION    "Each entry represents a unique Storage
                   Controller in the system"
   INDEX          { ibmStorageControllerKeyIndex }
::= { ibmStorageControllerTable 1 }

IbmStorageControllerEntry ::= SEQUENCE
{
   ibmStorageControllerKeyIndex String,     
   ibmStorageControllerModel String,
   ibmStorageControllerSerialNumber String
}

ibmStorageControllerKeyIndex OBJECT-TYPE
   SYNTAX         String
   ACCESS         read-only
   STATUS         mandatory
   DESCRIPTION    "The index used by this table"
   REFERENCE      "CIM_CARD.KeyIndex"
::= { ibmStorageControllerEntry 1 }

ibmStorageControllerModel OBJECT-TYPE
   SYNTAX         String
   ACCESS         read-only
   STATUS         mandatory
   DESCRIPTION    "The model of the controller"
   REFERENCE      "CIM_CARD.Model"
::= { ibmStorageControllerEntry 2 }

ibmStorageControllerSerialNumber OBJECT-TYPE
   SYNTAX         String
   ACCESS         read-only
   STATUS         mandatory
   DESCRIPTION    "The serial number of the controller"
   REFERENCE      "CIM_CARD.SerialNumber"
::= { ibmStorageControllerEntry 3 }


--
-- ibmStorageDiskDrive
--
ibmStorageDiskDriveTable OBJECT-TYPE
   SYNTAX         SEQUENCE OF IbmStorageDiskDriveEntry
   ACCESS         not-accessible
   STATUS         mandatory
   DESCRIPTION    "This table describes the physical disk drives
                   attached to the storage controller(s)"
   REFERENCE      "CIM_DiskDrive"
::= { ibmStorage 4 }

ibmStorageDiskDriveTableUp OBJECT-TYPE
   SYNTAX String
   ACCESS read-only
   STATUS mandatory
   DESCRIPTION "Returns Agent Version if Storage DiskDrive data is available."
   ::= { ibmStorageDiskDriveTable 0 }

ibmStorageDiskDriveEntry OBJECT-TYPE
   SYNTAX         IbmStorageDiskDriveEntry
   ACCESS         not-accessible
   STATUS         mandatory
   DESCRIPTION    "Each entry represents a single physcial disk drive in the 
                   system." 
   INDEX          { ibmStorageDiskDriveKeyIndex }
::= { ibmStorageDiskDriveTable 1 }

IbmStorageDiskDriveEntry ::= SEQUENCE
{
   ibmStorageDiskDriveKeyIndex String,
   ibmStorageDiskDriveDeviceID String,
   ibmStorageDiskDriveName String,
   ibmStorageDiskDriveElementName String,
   ibmStorageDiskDriveUnitsUsed String,
   ibmStorageDiskDriveOperationalStatus String
}

ibmStorageDiskDriveKeyIndex OBJECT-TYPE
   SYNTAX         String
   ACCESS         read-only
   STATUS         mandatory
   DESCRIPTION    "The index used by this table"
   REFERENCE      "CIM_DiskDrive.KeyIndex"
::= { ibmStorageDiskDriveEntry 1 }

ibmStorageDiskDriveDeviceID OBJECT-TYPE
   SYNTAX         String
   ACCESS         read-only
   STATUS         mandatory
   DESCRIPTION    "The DeviceID of the physical disk"
   REFERENCE      "CIM_DiskDrive.DeviceID"
::= { ibmStorageDiskDriveEntry 2 }

ibmStorageDiskDriveName OBJECT-TYPE
   SYNTAX         String
   ACCESS         read-only
   STATUS         mandatory
   DESCRIPTION    "A user friendly name assigned to the physical disk"
   REFERENCE      "CIM_DiskDrive.Name"
::= { ibmStorageDiskDriveEntry 3 }

ibmStorageDiskDriveElementName OBJECT-TYPE
   SYNTAX         String
   ACCESS         read-only
   STATUS         mandatory
   DESCRIPTION    "A user friendly name assigned to the physical disk"
   REFERENCE      "CIM_DiskDrive.ElementName"
::= { ibmStorageDiskDriveEntry 4 }

ibmStorageDiskDriveUnitsUsed OBJECT-TYPE
   SYNTAX         String
   ACCESS         read-only
   STATUS         mandatory
   DESCRIPTION    "Number of Units used on the physcial disk"
   REFERENCE      "CIM_DiskDrive.UnitsUsed"
::= { ibmStorageDiskDriveEntry 5 }

ibmStorageDiskDriveOperationalStatus OBJECT-TYPE
   SYNTAX         String
   ACCESS         read-only
   STATUS         mandatory
   DESCRIPTION    "The Operational Status of the physical disk.
                   Possible values are:

                   OK                 = Drive is online 
                   Error              = Drive is not functional
                   Stopped            = Drive is disabled
                   Stopping           = Drive is being disabled
                   Starting           = Drive is becoming enabled
                   Predictive Failure = Drive is functioning but predicting failure in near future"
   REFERENCE      "CIM_DiskDrive.OperationalStatus"
::= { ibmStorageDiskDriveEntry 6 }


--
-- ibmStorageStorageVolume
--
ibmStorageStorageVolumeTable OBJECT-TYPE
   SYNTAX         SEQUENCE OF IbmStorageStorageVolumeEntry
   ACCESS         not-accessible
   STATUS         mandatory
   DESCRIPTION    "This table represents a storage volume which can  
                   consist of one or more physical disk drives"
   REFERENCE      "CIM_StorageVolume"
::= { ibmStorage 5 }

ibmStorageStorageVolumeTableUp OBJECT-TYPE
   SYNTAX String
   ACCESS read-only
   STATUS mandatory
   DESCRIPTION "Returns Agent Version if Storage Volume data is available."
   ::= { ibmStorageStorageVolumeTable 0 }

ibmStorageStorageVolumeEntry OBJECT-TYPE
   SYNTAX         IbmStorageStorageVolumeEntry
   ACCESS         not-accessible
   STATUS         mandatory
   DESCRIPTION    "Each entry defines a single storage volume"
   INDEX          { ibmStorageStorageVolumeKeyIndex }
::= { ibmStorageStorageVolumeTable 1 }

IbmStorageStorageVolumeEntry ::= SEQUENCE
{
   ibmStorageStorageVolumeKeyIndex String,
   ibmStorageStorageVolumeDeviceID String,
   ibmStorageStorageVolumeName String,
   ibmStorageStorageVolumeElementName String,
   ibmStorageStorageVolumeBlockSize String,
   ibmStorageStorageVolumeConsumableBlocks String,
   ibmStorageStorageVolumeDataRedundancy Uint16,
   ibmStorageStorageVolumeNoSinglePointOfFailure Boolean,
   ibmStorageStorageVolumeOperationalStatus String
}

ibmStorageStorageVolumeKeyIndex OBJECT-TYPE
   SYNTAX         String
   ACCESS         read-only
   STATUS         mandatory
   DESCRIPTION    "The index used by this table"
   REFERENCE      "CIM_StorageVolume.KeyIndex"
::= { ibmStorageStorageVolumeEntry 1 }

ibmStorageStorageVolumeDeviceID OBJECT-TYPE
   SYNTAX         String
   ACCESS         read-only
   STATUS         mandatory
   DESCRIPTION    "The DeviceID of the storage volume"
   REFERENCE      "CIM_StorageVolume.DeviceID"
::= { ibmStorageStorageVolumeEntry 2 }

ibmStorageStorageVolumeName OBJECT-TYPE
   SYNTAX         String
   ACCESS         read-only
   STATUS         mandatory
   DESCRIPTION    "A user friendly name assigned to the storage volume"
   REFERENCE      "CIM_StorageVolume.Name"
::= { ibmStorageStorageVolumeEntry 3 }

ibmStorageStorageVolumeElementName OBJECT-TYPE
   SYNTAX         String
   ACCESS         read-only
   STATUS         mandatory
   DESCRIPTION    "A user friendly name assigned to the storage volume"
   REFERENCE      "CIM_StorageVolume.ElementName"
::= { ibmStorageStorageVolumeEntry 4 }

ibmStorageStorageVolumeBlockSize OBJECT-TYPE
   SYNTAX         String
   ACCESS         read-only
   STATUS         mandatory
   DESCRIPTION    "The block size used by the storage volume"
   REFERENCE      "CIM_StorageVolume.BlockSize"
::= { ibmStorageStorageVolumeEntry 5 }

ibmStorageStorageVolumeConsumableBlocks OBJECT-TYPE
   SYNTAX         String
   ACCESS         read-only
   STATUS         mandatory
   DESCRIPTION    "The number of consumable blocks in the storage volume"
   REFERENCE      "CIM_StorageVolume.ConsumableBlocks"
::= { ibmStorageStorageVolumeEntry 6 }

ibmStorageStorageVolumeDataRedundancy OBJECT-TYPE
   SYNTAX         Uint16
   ACCESS         read-only
   STATUS         mandatory
   DESCRIPTION    "Number of complete copies of the data 
                   currently maintained"
   REFERENCE      "CIM_StorageVolume.DataRedundancy"
::= { ibmStorageStorageVolumeEntry 7 }

ibmStorageStorageVolumeNoSinglePointOfFailure OBJECT-TYPE
   SYNTAX         Boolean
   ACCESS         read-only
   STATUS         mandatory
   DESCRIPTION    "Indicates if there is no single point of failure"
   REFERENCE      "CIM_StorageVolume.NoSinglePointOfFailure"
::= { ibmStorageStorageVolumeEntry 8 }

ibmStorageStorageVolumeOperationalStatus OBJECT-TYPE
   SYNTAX         String
   ACCESS         read-only
   STATUS         mandatory
   DESCRIPTION    "Operations Status of the storage volume
                   Possible values are:
                   
                   Degraded = A drive has failed, a rebuild
                   is in process, or a spare drive is in use.

                   Error = The volume has an error, is broken,
                   or there has been data loss."
   REFERENCE      "CIM_StorageVolume.OperationalStatus"
::= { ibmStorageStorageVolumeEntry 9 }


--
-- ibmStorageSoftwareIdentity
--
ibmStorageSoftwareIdentityTable OBJECT-TYPE
   SYNTAX         SEQUENCE OF IbmStorageSoftwareIdentityEntry
   ACCESS         not-accessible
   STATUS         mandatory
   DESCRIPTION    "The table describes the Firmware, BIOS, and driver
                   information for physical components of the storage system."
   REFERENCE      "CIM_SoftwareIdentity"
::= { ibmStorage 6 }

ibmStorageSoftwareIdentityEntry OBJECT-TYPE
   SYNTAX         IbmStorageSoftwareIdentityEntry
   ACCESS         not-accessible
   STATUS         mandatory
   DESCRIPTION    "Each entry represents a unique software identity"
   INDEX          { ibmStorageSoftwareIdentityKeyIndex }
::= { ibmStorageSoftwareIdentityTable 1 }

IbmStorageSoftwareIdentityEntry ::= SEQUENCE
{
   ibmStorageSoftwareIdentityKeyIndex String,
   ibmStorageSoftwareIdentityDescription String,
   ibmStorageSoftwareIdentityCaption String,
   ibmStorageSoftwareIdentityElementName String,
   ibmStorageSoftwareIdentityInstanceID String,
   ibmStorageSoftwareIdentityManufacturer String,
   ibmStorageSoftwareIdentityVersionString String,
   ibmStorageSoftwareIdentitySerialNumber String
}

ibmStorageSoftwareIdentityKeyIndex OBJECT-TYPE
   SYNTAX         String
   ACCESS         read-only
   STATUS         mandatory
   DESCRIPTION    "The index used by this table"
   REFERENCE      "CIM_SoftwareIdentity.KeyIndex"
::= { ibmStorageSoftwareIdentityEntry 1 }

ibmStorageSoftwareIdentityDescription OBJECT-TYPE
   SYNTAX         String
   ACCESS         read-only
   STATUS         mandatory
   DESCRIPTION    "A description of the software item"
   REFERENCE      "CIM_SoftwareIdentity.Description"
::= { ibmStorageSoftwareIdentityEntry 2 }

ibmStorageSoftwareIdentityCaption OBJECT-TYPE
   SYNTAX         String
   ACCESS         read-only
   STATUS         mandatory
   DESCRIPTION    "A user friendly name for the software item"
   REFERENCE      "CIM_SoftwareIdentity.Caption"
::= { ibmStorageSoftwareIdentityEntry 3 }

ibmStorageSoftwareIdentityElementName OBJECT-TYPE
   SYNTAX         String
   ACCESS         read-only
   STATUS         mandatory
   DESCRIPTION    "A user friendly name for the software item"
   REFERENCE      "CIM_SoftwareIdentity.ElementName"
::= { ibmStorageSoftwareIdentityEntry 4 }

ibmStorageSoftwareIdentityInstanceID OBJECT-TYPE
   SYNTAX         String
   ACCESS         read-only
   STATUS         mandatory
   DESCRIPTION    "An instanceID assigned to the software item"
   REFERENCE      "CIM_SoftwareIdentity.InstanceID"
::= { ibmStorageSoftwareIdentityEntry 5 }

ibmStorageSoftwareIdentityManufacturer OBJECT-TYPE
   SYNTAX         String
   ACCESS         read-only
   STATUS         mandatory
   DESCRIPTION    "The manufacturer of the software"
   REFERENCE      "CIM_SoftwareIdentity.Manufacturer"
::= { ibmStorageSoftwareIdentityEntry 6 }

ibmStorageSoftwareIdentityVersionString OBJECT-TYPE
   SYNTAX         String
   ACCESS         read-only
   STATUS         mandatory
   DESCRIPTION    "The current version of the software item"
   REFERENCE      "CIM_SoftwareIdentity.VersionString"
::= { ibmStorageSoftwareIdentityEntry 7 }

ibmStorageSoftwareIdentitySerialNumber OBJECT-TYPE
   SYNTAX         String
   ACCESS         read-only
   STATUS         mandatory
   DESCRIPTION    "The serial number of the device"
   REFERENCE      "CIM_SoftwareIdentity.SerialNumber"
::= { ibmStorageSoftwareIdentityEntry 8 }


--
-- Trap variables
--
ibmStorageTrapProviderName OBJECT-TYPE
    SYNTAX String
    ACCESS not-accessible
    STATUS mandatory
    DESCRIPTION
        "The CIM Provider Name"
    ::= { ibmStorageTrapInfo 1 }

ibmStorageTrapEventID OBJECT-TYPE
    SYNTAX String
    ACCESS not-accessible
    STATUS mandatory
    DESCRIPTION
        "A unique EventID that identifies the item reporting the issue"
    ::= { ibmStorageTrapInfo 2 }

ibmStorageTrapPerceivedSeverity OBJECT-TYPE
    SYNTAX INTEGER
    ACCESS not-accessible
    STATUS mandatory
    DESCRIPTION
        "Severity of the event
         0=Normal / OK 
         1=Warning 
         2=Critical "
    ::= { ibmStorageTrapInfo 3 }

ibmStorageDescription OBJECT-TYPE
    SYNTAX String
    ACCESS not-accessible
    STATUS mandatory
    DESCRIPTION
        "The event message"
    ::= { ibmStorageTrapInfo 4 }

ibmStorageTrapEventTime OBJECT-TYPE
    SYNTAX String
    ACCESS not-accessible
    STATUS mandatory
    DESCRIPTION
        "Time that the event occured"
    ::= { ibmStorageTrapInfo 5 }

--
-- Traps
--

ibmStorageNoControllers TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: No controllers were found in this system."
    ::= 201

ibmStorageControllerFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Commands not responding on the Controller."
    ::= 202

ibmStorageDeadBattery TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: The battery-backup cache device on a Controller needs a new battery."
    ::= 203

ibmStorageDeadBatteryCache TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: The battery-backup cache device on a Controller is defective"
    ::= 204

ibmStoragePollingFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Background polling commands not responding on a Controller"
    ::= 205

ibmStorageConfigFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Cannot read controller configuration."
    ::= 206

ibmStorageControllerAdded TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Controller has been added to the system."
    ::= 207

ibmStorageControllerReplaced TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Controller has been replaced in the system."
    ::= 208

ibmStorageControllerFailover TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Controller failover detected. Passive controller is now active."
    ::= 209

ibmStorageControllerVersionMismatch TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: A Controller version mismatch detected. The BIOS, Firmware, and Driver are not a matched set and are not compatible."
    ::= 210

ibmStorageControllerBatteryOvertemp TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: Controller battery has exceeded normal operating temperature."
    ::= 211

ibmStorageControllerBadStripes TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: One or more logical drives contain a bad stripe."
    ::= 215

ibmStorageControllerBatteryTempNormal TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Controller battery operating temperature is normal."
    ::= 216

ibmStorageControllerStatusChange TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Controller has changed status"
    ::= 217

ibmStorageLogicalDriveCritical TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: A Logical Drive is Critical"
    ::= 301

ibmStorageLogicalDriveBlocked TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: A Logical Drive is Blocked."
    ::= 302

ibmStorageLogicalDriveOffLine TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Logical Drive is Offline"
    ::= 303

ibmStorageRebuildDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Rebuilding Logical Drive."
    ::= 304

ibmStorageRebuildComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Rebuild complete of Logical Drive."
    ::= 305

ibmStorageRebuildFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Rebuild failed of Logical Drive."
    ::= 306

ibmStorageSyncDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Synchronizing Logical Drive."
    ::= 307

ibmStorageSyncComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Synchronization complete of Logical Drive."
    ::= 308

ibmStorageSyncFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Synchronization failed of Logical Drive."
    ::= 309

ibmStorageMigrationDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Migrating Logical Drive."
    ::= 310

ibmStorageMigrationComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Migration complete on Logical Drive %d of Controller %d."
    ::= 311

ibmStorageMigrationFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Migration failed on Logical Drive."
    ::= 312

ibmStorageCompressionDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Compressing Logical Drive."
    ::= 313

ibmStorageCompressionComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Compression complete of Logical Drive."
    ::= 314

ibmStoragecompressionFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Compression failed of Logical Drive."
    ::= 315

ibmStorageDecompressionDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Decompressing Logical Drive."
    ::= 316

ibmStorageDecompressionComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Decompression complete of Logical Drive."
    ::= 317

ibmStorageDecompressionFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Decompression failed of Logical Drive."
    ::= 318

ibmStorageFlashCopyDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: FlashCopying Logical Drive."
    ::= 319

ibmStorageFlashCopyComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: FlashCopy complete on Logical Drive."
    ::= 320

ibmStorageFlashCopyFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: FlashCopy failed on Logical Drive."
    ::= 321

ibmStorageArrayRebuildDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Rebuilding Array."
    ::= 322

ibmStorageArrayRebuildComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Rebuild complete of Array."
    ::= 323

ibmStorageArrayRebuildFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Rebuild failed on Array."
    ::= 324

ibmStorageArraySyncDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Synchronizing Array."
    ::= 325

ibmStorageArraySyncComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Synchronization complete on Array."
    ::= 326

ibmStorageArraySyncFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Synchronization failed on Array."
    ::= 327

ibmStorageArrayFlashCopyDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: FlashCopying Array."
    ::= 328

ibmStorageArrayFlashCopyComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: FlashCopy complete on Array."
    ::= 329

ibmStorageArrayFlashCopyFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: FlashCopy failed on Array."
    ::= 330

ibmStorageLogicalDriveUnblocked TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Logical Drive is unblocked."
    ::= 331

ibmStorageCompactionDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Compacting Logical Drive."
    ::= 332

ibmStorageCompactionComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Compaction complete on Logical Drive."
    ::= 333

ibmStorageCompactionFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Compaction failed on Logical Drive."
    ::= 334

ibmStorageExpansionDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Expanding Logical Drive."
    ::= 335

ibmStorageExpansionComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Expansion complete on Logical Drive."
    ::= 336

ibmStorageExpansionFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Expansion failed on Logical Drive."
    ::= 337
    
ibmStorageLogicalDriveCriticalPeriodic TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: Periodic scan found 1 or more critical logical drives."
    ::= 338

ibmStorageCopyBackDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Copy back in progress on Logical Drive."
    ::= 339

ibmStorageCopyBackComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Copy back complete on Logical Drive."
    ::= 340

ibmStorageCopyBackFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Copy back failed on Logical Drive."
    ::= 341

ibmStorageInitDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Initialization in progress on Logical Drive."
    ::= 342

ibmStorageInitComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Initialization complete on Logical Drive."
    ::= 343

ibmStorageInitFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Initialization failed on Logical Drive."
    ::= 344

ibmStorageLogicalDriveOK TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Logical Drive is normal."
    ::= 345

ibmStorageLogicalDriveAdded TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Added Logical Drive."
    ::= 346

ibmStorageLogicalDriveRemoved TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Removed Logical Drive."
    ::= 347

ibmStorageArrayFlashCopyStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Array Flash Copy has stopped"
    ::= 348

ibmStorageArrayRebuildStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Array Rebuild has stopped"
    ::= 349

ibmStorageArrayStatusChange TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "An Array has had a status change"
    ::= 350

ibmStorageArraySyncStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Array Sync has stopped"
    ::= 351

ibmStorageCompactionStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Compaction has stopped"
    ::= 352

ibmStorageCompressionStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Compression has stopped"
    ::= 353

ibmStorageCopybackStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Copyback has stopped"
    ::= 354

ibmStorageDecompressionStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Decompression has stopped"
    ::= 355

ibmStorageExpansionStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Expansion has stopped"
    ::= 356

ibmStorageFlashCopyStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "FlashCopy has stopped"
    ::= 357

ibmStorageInitStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Initialization has stopped"
    ::= 358

ibmStorageLogicalDriveStatusChange TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        " A Logical Drive has had a status change"
    ::= 359

ibmStorageMigrationStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Migration has stopped"
    ::= 360

ibmStorageRebuildStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Rebuild has stopped"
    ::= 361

ibmStorageSyncStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Synchronization has stopped"
    ::= 362

ibmStorageDefunctDrive TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Defunct drive."
    ::= 401

ibmStoragePfaDrive TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: A Drive reports a PFA."
    ::= 402

ibmStorageDefunctReplaced TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: A drive is set to Hot-Spare."
    ::= 403
    
ibmStorageDefunctDriveFru TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: A Drive reports Defunct stauts."
    ::= 404

ibmStoragePfaDriveFru TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: A Drive reports a PFA."
    ::= 405
    
ibmStorageUnsupportedDrive TRAP-TYPE
 -- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    optional, disable by using -DshowCounterfeitDrives=false on command line
    DESCRIPTION
        "Warning: Unsupported physical drive found."
    ::= 406

ibmStorageDriveAdded TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: A Drive has been added."
    ::= 407

ibmStorageDriveRemoved TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: A Drive has been removed."
    ::= 408

ibmStorageDriveClearDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: A Drive clear is in progress."
    ::= 409

ibmStorageDriveClearComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Clear complete on Drive."
    ::= 410

ibmStorageDriveClearFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Clear failed on Drive."
    ::= 411

ibmStorageDriveSyncDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Synchronization in progress on Drive."
    ::= 412

ibmStorageDriveSyncComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Synchronization complete on Drive."
    ::= 413

ibmStorageDriveSyncFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Synchronization failed on Drive."
    ::= 414

ibmStorageDriveVerifyDetected TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: A Drive Verify is in progress."
    ::= 415

ibmStorageDriveVerifyComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Drive Verify complete."
    ::= 416

ibmStorageDriveVerifyFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Drive Verify failed."
    ::= 417

ibmStorageDriveClearStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Drive Clear has stopped"
    ::= 418

ibmStorageDriveSecureEraseStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Drive Secure Erase has stopped"
    ::= 419

ibmStorageDriveStatusChange TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Drive reports a status change"
    ::= 420

ibmStorageDriveSyncStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Drive Synchronization has stopped"
    ::= 421

ibmStorageDriveVerifyStopped TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Drive Verify has stopped"
    ::= 422

ibmStorageSpareCreated TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Spare Drive has been created"
    ::= 423

ibmStorageSpareDeleted TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Spare Drive has been deleted"
    ::= 424

ibmStorageEnclosureOK TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Enclosure device responding."
    ::= 501

ibmStorageEnclosureFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Enclosure device not responding."
    ::= 502

ibmStorageFanOk TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Enclosure fan is now operational."
    ::= 503

ibmStorageFanFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Enclosure fan is malfunctioning."
    ::= 504

ibmStorageFanInstalled TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Enclosure fan has been installed."
    ::= 505

ibmStorageFanRemoved TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: Enclosure fan has been removed."
    ::= 506

ibmStorageTempOk TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Enclosure temperature is in normal range."
    ::= 507

ibmStorageTempFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Enclosure temperature is out of normal range on Controller."
    ::= 508

ibmStoragePowerSupplyOk TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Enclosure power supply is now operational."
    ::= 509

ibmStoragePowerSupplyFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Error: Enclosure power supply is malfunctioning."
    ::= 510

ibmStoragePowerSupplyInstalled TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: Enclosure power supply has been installed."
    ::= 511

ibmStoragePowerSupplyRemoved TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Warning: Enclosure power supply has been removed."
    ::= 512

ibmStorageTestTrap TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Informational: This is a test trap."
    ::= 601

-- LSI Traps

ibmStorageLsiPDFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Drive has failed"
    ::= 1000

ibmStorageLsiPDPartOfLDFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Part of a Logical Drive has failed"
    ::= 1003

ibmStorageLsiPDPartOfLDAdd TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Drive added to Logical Drive"
    ::= 1004

ibmStorageLsiHSPartOfLD TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Hot Spare has been added"
    ::= 1005

ibmStorageLsiHSFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Hot Spare has failed"
    ::= 1007

ibmStorageLsiPDHS TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Physial Drive has been made a Hot Spare"
    ::= 1008

ibmStorageLsiLDOffline TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Logical Drive is off-line"
    ::= 1009

ibmStorageLsiLDDegraded TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Logical Drive is in degraded state"
    ::= 1011

ibmStorageLsiLDOptimal TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Logical Drive is optimal"
    ::= 1012

ibmStorageLsiSMARTError TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "A Drive is reporting a PFA"
    ::= 1013

ibmStorageLsiStoragePoolStatus TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Indicates a status change or status of the storage pool"
    ::= 1014

ibmStorageLsiRbldStart TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Volume rebuild has started"
    ::= 1015

ibmStorageLsiRbldComplete TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Volume rebuild complete"
    ::= 1016

ibmStorageLsiRbldFail TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Volume rebuild has failed"
    ::= 1017

ibmStorageLsiStorageVolumeStatus TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Indicates a status change or status of the storage volume"
    ::= 1020

ibmStorageLsiControllerStatus TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Indicates a status change or status of the controller"
    ::= 1031

ibmStorageLsiDiskDriveStatus TRAP-TYPE
-- Reverse mappable trap
    ENTERPRISE ibmStorageTrap
    VARIABLES {
        ibmStorageTrapProviderName,   
        ibmStorageTrapEventID, ibmStorageTrapPerceivedSeverity, 
        ibmStorageDescription, ibmStorageTrapEventTime          }
--  Status
--    mandatory
    DESCRIPTION
        "Indicates a status change or status of the disk drive"
    ::= 1032

END
