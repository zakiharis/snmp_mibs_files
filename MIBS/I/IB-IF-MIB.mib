-- extracted from draft-ietf-ipoib-ibif-mib-09.txt
-- at Wed Jul 12 06:06:39 2006

   IB-IF-MIB DEFINITIONS ::= BEGIN 
    
   IMPORTS 
       MODULE-COMPLIANCE, OBJECT-GROUP       FROM SNMPv2-CONF 
       MODULE-IDENTITY, OBJECT-TYPE, 
       Unsigned32, Counter32, Counter64      FROM SNMPv2-SMI  
       InterfaceIndex                        FROM IF-MIB 
       IbVirtualLane, infinibandMIB, 
       IbIpoibClientIdentifier               FROM IB-TC-MIB; 
    
   ibIfMIB MODULE-IDENTITY 
      LAST-UPDATED "200606270000Z"  -- 27 June 2006 00:00:00 GMT 
      ORGANIZATION "IETF IP over IB (IPOIB) Working Group" 
      CONTACT-INFO  
          "Hal Rosenstock 
           Postal: HNR Consulting   
                   200 Old Harvard Road 
                   Boxboro MA 01719-1834 
                   United States 
           Email:  hnrose@earthlink.net 
    
           Email comments to the IPOIB WG Mailing List at 
           ipoverib@ietf.org." 
      DESCRIPTION 
         "Copyright (C) The Internet Society (2006).  The initial  
          version of this MIB module was published in RFC XXXX; for 
          full legal notices see the RFC itself.  Supplementary  
          information may be available on  
          http://www.ietf.org/copyrights/ianamib.html. 
    
          This module contains managed object definitions for  
          managing InfiniBand interfaces." 
      REVISION     
          "200606270000Z"  -- 27 June 2006 00:00:00 EST 
      DESCRIPTION 
         "Initial version published as part of RFC XXXX."  
      ::= { infinibandMIB 2 } 
    
    
      -- 
      --  Top-Level Object Identifier Assignments 
      --    
        ibIfObjects OBJECT IDENTIFIER ::= { ibIfMIB 1 } 
        ibIfNotifications OBJECT IDENTIFIER ::= { ibIfMIB 2 } 
        ibIfConformance OBJECT IDENTIFIER ::= { ibIfMIB 3 } 
        --************************************************************** 
        -- IPoIB Detailed per interface/port statistics  
        -- ibIfPortStat Table 
        --************************************************************** 
    
   ibIfPortStatTable OBJECT-TYPE 
       SYNTAX SEQUENCE OF IbIfPortStatEntry 
       MAX-ACCESS not-accessible 
       STATUS current 
       DESCRIPTION 
          "This table provides detail statistics for all InfiniBand 
           interfaces attached to a particular system.  There will be  
           one row in this table for each InfiniBand interface in the  
           system." 
       ::= { ibIfObjects 1 }  
    
   ibIfPortStatEntry OBJECT-TYPE 
              SYNTAX IbIfPortStatEntry 
              MAX-ACCESS not-accessible 
              STATUS current 
              DESCRIPTION  
                 "Statistics for a particular interface to an  
                  InfiniBand medium." 
              INDEX { ibIfPortStatIfIndex } 
              ::= { ibIfPortStatTable 1 }  
    
   IbIfPortStatEntry ::= SEQUENCE { 
       ibIfPortStatIfIndex InterfaceIndex, 
       ibIfPortSymbolErrs Counter32, 
       ibIfPortLinkErrRecovery Counter32, 
       ibIfPortLinkDowned Counter32, 
       ibIfPortStatLocalPhyErrs Counter32, 
       ibIfPortStatMalPktErrs Counter32, 
       ibIfPortStatRcvRemPhyErrs Counter32, 
       ibIfPortStatRcvConstrErrs Counter32, 
       ibIfPortStatInactDiscards Counter32, 
       ibIfPortStatNeighMTUDiscards Counter32, 
       ibIfPortStatSwLifetimeDiscards Counter32, 
       ibIfPortStatHOQLifetimeDiscards Counter32, 
       ibIfPortStatLinkIntergrityErrs Counter32, 
       ibIfPortStatExcBufOverrunErrs Counter32, 
       ibIfPortStatVL15Dropped Counter32  
   } 
    
   ibIfPortStatIfIndex OBJECT-TYPE 
       SYNTAX InterfaceIndex 
       MAX-ACCESS not-accessible 
       STATUS current 
       DESCRIPTION 
          "The ifIndex value of the InfiniBand interface to which 
           these port statistics apply."   
       ::= { ibIfPortStatEntry 1 }  
    
   ibIfPortSymbolErrs OBJECT-TYPE 
       SYNTAX Counter32 
       MAX-ACCESS read-only 
       STATUS current 
       DESCRIPTION 
          "Total number of minor link errors detected on one or more 
           physical lanes." 
       REFERENCE 
          "InfiniBand Architecture Release 1.2 Vol. 1. Section 
           16.1.3.5; Table 225 PortCounters::SymbolErrorCounter."  
       ::= { ibIfPortStatEntry 2 }  
    
   ibIfPortLinkErrRecovery OBJECT-TYPE 
       SYNTAX Counter32 
       MAX-ACCESS read-only 
       STATUS current 
       DESCRIPTION 
          "Total number of times the Port Training state machine has 
           successfully completed the link error recovery process." 
       REFERENCE 
          "InfiniBand Architecture Release 1.2 Vol. 1. Section  
           16.1.3.5; Table 225 PortCounters::LinkErrorRecoveryCounter."  
       ::= { ibIfPortStatEntry 3 }  
    
   ibIfPortLinkDowned OBJECT-TYPE 
       SYNTAX Counter32 
       MAX-ACCESS read-only 
       STATUS current 
       DESCRIPTION 
          "Total number of times the Port Training state machine 
           has failed the link error recovery process and downed 
           the link." 
       REFERENCE 
          "InfiniBand Architecture Release 1.2 Vol. 1. Section 
           16.1.3.5; Table 225 PortCounters::LinkDownedCounter."  
       ::= { ibIfPortStatEntry 4 }  
    
   ibIfPortStatLocalPhyErrs OBJECT-TYPE 
       SYNTAX Counter32 
       MAX-ACCESS read-only 
       STATUS current 
       DESCRIPTION 
          "Total number of packets received on the port that contain 
           local physical errors (ICRC, VCRC, FCCRC, and 
           all physical errors that cause entry into the BAD 
           PACKET or BAD PACKET DISCARD states of the 
           packet receiver state machine)." 
       REFERENCE 
          "InfiniBand Architecture Release 1.2 Vol. 1. Section 
           16.1.3.5; Table 225 PortCounters::PortRcvErrors."  
       ::= { ibIfPortStatEntry 5 }   
    
   ibIfPortStatMalPktErrs OBJECT-TYPE 
       SYNTAX Counter32 
       MAX-ACCESS read-only 
       STATUS current 
       DESCRIPTION 
          "Total number of packets received on the port that contain 
           malformed packet errors 
           - data packets: LVer, length, VL 
           - link packets: operand, length, VL" 
       REFERENCE 
          "InfiniBand Architecture Release 1.2 Vol. 1. Section 
           16.1.3.5; Table 225 PortCounters::PortRcvErrors."  
       ::= { ibIfPortStatEntry 6 }   
    
   ibIfPortStatRcvRemPhyErrs OBJECT-TYPE 
       SYNTAX Counter32 
       MAX-ACCESS read-only 
       STATUS current 
       DESCRIPTION 
          "Total number of packets marked with the EBP delimiter  
           received on the port." 
       REFERENCE 
          "InfiniBand Architecture Release 1.2 Vol. 1. Section 
           16.1.3.5; Table 225  
           PortCounters::PortRcvRemotePhysicalErrors."  
       ::= { ibIfPortStatEntry 7 }   
    
   ibIfPortStatRcvConstrErrs OBJECT-TYPE 
       SYNTAX Counter32 
       MAX-ACCESS read-only 
       STATUS current 
       DESCRIPTION 
          "Total number of packets received on the port that are 
           discarded for the following reasons: 
           - FilterRawInbound is true and packet is raw 
           - PartitionEnforcementInbound is true and packet fails 
             partition key check or IP version check." 
       REFERENCE 
          "InfiniBand Architecture Release 1.2 Vol. 1. Section 16.1.3.5; 
           Table 225 PortCounters::PortRcvConstraintErrors."  
       ::= { ibIfPortStatEntry 8 }   

   ibIfPortStatInactDiscards OBJECT-TYPE 
       SYNTAX Counter32 
       MAX-ACCESS read-only 
       STATUS current 
       DESCRIPTION 
          "Total number of outbound packets discarded by the port  
           because it is not in the active state." 
       REFERENCE 
          "InfiniBand Architecture Release 1.2 Vol. 1. Section 16.1.4.2; 
           Table 229 PortXmitDiscardDetails::PortInactiveDiscards."  
       ::= { ibIfPortStatEntry 9 }   
    
   ibIfPortStatNeighMTUDiscards OBJECT-TYPE 
       SYNTAX Counter32 
       MAX-ACCESS read-only 
       STATUS current 
       DESCRIPTION 
          "Total number of outbound packets discarded by the 
           port because packet length exceeded the neighbor MTU." 
       REFERENCE 
          "InfiniBand Architecture Release 1.2 Vol. 1. Section 16.1.4.2; 
           Table 229 PortXmitDiscardDetails::PortNeighborMTUDiscards."  
       ::= { ibIfPortStatEntry 10 }   
    
   ibIfPortStatSwLifetimeDiscards OBJECT-TYPE 
       SYNTAX Counter32 
       MAX-ACCESS read-only 
       STATUS current 
       DESCRIPTION 
          "Total number of outbound packets discarded by the port  
           because the Switch Lifetime Limit was exceeded.  Note this  
           object is only incremented for switches." 
       REFERENCE 
          "InfiniBand Architecture Release 1.2 Vol. 1. Section 16.1.4.2; 
           Table 229 
           PortXmitDiscardDetails::PortSwLifetimeLimitDiscards."  
       ::= { ibIfPortStatEntry 11 }   
    
   ibIfPortStatHOQLifetimeDiscards OBJECT-TYPE 
       SYNTAX Counter32 
       MAX-ACCESS read-only 
       STATUS current 
       DESCRIPTION 
          "Total number of outbound packets discarded by the port  
           because the switch HOQ lifetime was exceeded.  Note this  
           object is only incremented for switches." 
       REFERENCE 
          "InfiniBand Architecture Release 1.2 Vol. 1. Section 16.1.4.2; 
           Table 229 PortXmitDiscardDetails::PortSwHOQLimitDiscards."  
       ::= { ibIfPortStatEntry 12 }   
    
   ibIfPortStatLinkIntergrityErrs OBJECT-TYPE 
       SYNTAX Counter32 
       MAX-ACCESS read-only 
       STATUS current 
       DESCRIPTION 
          "The number of times that the count of local physical errors  
           exceeded the LocalPhyErrors threshold." 
       REFERENCE 
          "InfiniBand Architecture Release 1.2 Vol. 1. Section 16.1.3.5; 
           Table 225 PortCounters::LocalLinkIntegrityErrors.; Also see 
           Table 145 PortInfo."  
       ::= { ibIfPortStatEntry 13 }   
    
   ibIfPortStatExcBufOverrunErrs OBJECT-TYPE 
       SYNTAX Counter32 
       MAX-ACCESS read-only 
       STATUS current 
       DESCRIPTION 
          "The number of times that OverrunErrors consecutive 
           flow control update periods occurred with at least one 
           overrun error in each period." 
       REFERENCE 
          "InfiniBand Architecture Release 1.2 Vol. 1. Section 16.1.3.5; 
           Table 225 PortCounters::ExcessiveBufferOverrunErrors.; Also 
           see Table 145 PortInfo."  
       ::= { ibIfPortStatEntry 14 }   
    
   ibIfPortStatVL15Dropped OBJECT-TYPE 
       SYNTAX Counter32 
       MAX-ACCESS read-only 
       STATUS current 
       DESCRIPTION 
          "Number of incoming VL15 packets dropped due to resource 
           limitations on the selected port (e.g., lack of buffers)." 
       REFERENCE 
          "InfiniBand Architecture Release 1.2 Vol. 1. Section 16.1.3.5; 
           Table 225 PortCounters::VL15Dropped." 
       ::= { ibIfPortStatEntry 15 }   
    
    
       --*************************************************************** 
       -- IPoIB per port VL Traffic Objects 
       -- ibIfVLTraffic Table 
       --*************************************************************** 
    
   ibIfVLTrafficTable OBJECT-TYPE 
       SYNTAX SEQUENCE OF IbIfVLTrafficEntry 
       MAX-ACCESS not-accessible 
       STATUS current 
       DESCRIPTION  
          "This table provides traffic statistics for all  
           virtual lanes that are configured on an InfiniBand  
           interface.  There will always be at least one data virtual  
           lane in the range VL0-VL14 configured on an interface,  
           as well as control channel VL15.  Configuration  
           of what VLs are available on a particular interface  
           is done by IBA native management." 
       ::= { ibIfObjects 2 }  
    
   ibIfVLTrafficEntry OBJECT-TYPE 
       SYNTAX IbIfVLTrafficEntry 
       MAX-ACCESS not-accessible 
       STATUS current 
       DESCRIPTION  
          "Information about a particular virtual lane (VL)." 
       INDEX { ibIfVLTrafficIfIndex, ibIfVLIndex } 
       ::= { ibIfVLTrafficTable 1 }   
    
   IbIfVLTrafficEntry ::= SEQUENCE { 
       ibIfVLTrafficIfIndex InterfaceIndex, 
       ibIfVLIndex IbVirtualLane, 
       ibIfVLOutOctets Counter64,        
       ibIfVLOutPkts Counter64,        
       ibIfVLInOctets Counter64,        
       ibIfVLInPkts Counter64 
   } 
             
   ibIfVLTrafficIfIndex OBJECT-TYPE 
       SYNTAX InterfaceIndex 
       MAX-ACCESS not-accessible 
       STATUS current 
       DESCRIPTION 
          "The ifIndex value of the InfiniBand interface to which these  
           virtual lane (VL) traffic statistics apply."   
       ::= { ibIfVLTrafficEntry 1 }  
    
   ibIfVLIndex OBJECT-TYPE 
       SYNTAX IbVirtualLane 
       MAX-ACCESS not-accessible 
       STATUS current 
       DESCRIPTION  
          "Identifies what Virtual Lane (VL) instance is being  
           addressed." 
       ::= { ibIfVLTrafficEntry 2 }  

   ibIfVLOutOctets OBJECT-TYPE 
       SYNTAX Counter64 
       MAX-ACCESS read-only 
       STATUS current 
       DESCRIPTION 
          "The number of octets transmitted in valid data packets on  
           this interface, including the START and END delimiters and  
           the VCRC for this VL." 
       REFERENCE 
          "InfiniBand Architecture Release 1.2 Vol. 1. Section 16.1.3.3; 
           Table 223 CounterSelect::PortXmitDataVL." 
       ::= { ibIfVLTrafficEntry 3 }  
    
   ibIfVLOutPkts OBJECT-TYPE 
       SYNTAX Counter64 
       MAX-ACCESS read-only 
       STATUS current 
       DESCRIPTION 
          "The number of packets successfully sent on this VL." 
       REFERENCE 
          "InfiniBand Architecture Release 1.2 Vol. 1. Section 16.1.3.3; 
           Table 223 CounterSelect::PortXmitPktVL." 
       ::= { ibIfVLTrafficEntry 4 }  
    
   ibIfVLInOctets OBJECT-TYPE 
       SYNTAX Counter64 
       MAX-ACCESS read-only 
       STATUS current 
       DESCRIPTION 
          "The number of octets in valid data packets received on this  
           interface, including the START and END delimiters and the  
           VCRC for this VL." 
       REFERENCE 
          "InfiniBand Architecture Release 1.2 Vol. 1. Section 16.1.3.3; 
           Table 223 CounterSelect::PortRcvDataVL." 
       ::= { ibIfVLTrafficEntry 5 }  
             
   ibIfVLInPkts OBJECT-TYPE 
       SYNTAX Counter64 
       MAX-ACCESS read-only 
       STATUS current 
       DESCRIPTION 
          "The number of packets successfully received on this VL. 
           This does not include link packets, since link packets are 
           generated by the interface layer, and are not passed from any 
           higher layer protocol." 
       REFERENCE 
          "InfiniBand Architecture Release 1.2 Vol. 1. Section 16.1.3.3; 
           Table 223 CounterSelect::PortRcvPktVL." 
       ::= { ibIfVLTrafficEntry 6 }  
    
       --*************************************************************** 
       -- IPoIB Link Layer Address Table 
       -- ibIpoibLinkLayerAddr Table 
       --*************************************************************** 
    
   ibIpoibLinkLayerAddrTable OBJECT-TYPE 
       SYNTAX SEQUENCE OF IbIpoibLinkLayerAddrEntry 
       MAX-ACCESS not-accessible 
       STATUS current 
       DESCRIPTION  
          "This table contains information about all IPOIB link 
           layer addresses associated with this InfiniBand interface 
           (port)." 
       ::= { ibIfObjects 3 }  
    
   ibIpoibLinkLayerAddrEntry OBJECT-TYPE 
       SYNTAX IbIpoibLinkLayerAddrEntry 
       MAX-ACCESS not-accessible 
       STATUS current 
       DESCRIPTION  
          "Information about specific IPOIB link layer addresses 
           associated with this InfiniBand interface (port)." 
       INDEX { ibIpoibLinkLayerIfIndex, ibIpoibLinkLayerIndex } 
       ::= { ibIpoibLinkLayerAddrTable 1 }  
    
   IbIpoibLinkLayerAddrEntry ::= SEQUENCE { 
      ibIpoibLinkLayerIfIndex InterfaceIndex, 
      ibIpoibLinkLayerIndex Unsigned32, 
      ibIpoibLinkLayerAddr IbIpoibClientIdentifier 
      } 
    
   ibIpoibLinkLayerIfIndex OBJECT-TYPE 
       SYNTAX InterfaceIndex 
       MAX-ACCESS not-accessible 
       STATUS current 
       DESCRIPTION  
          "The ifIndex of the IPOIB InfiniBand interface (port)." 
       ::= { ibIpoibLinkLayerAddrEntry 1 }  
    
   ibIpoibLinkLayerIndex OBJECT-TYPE 
       SYNTAX Unsigned32(1..65535) 
       MAX-ACCESS not-accessible 
       STATUS current 
       DESCRIPTION  
          "Index of the IPOIB Link Layer address in the table." 
       ::= { ibIpoibLinkLayerAddrEntry 2 }  

   ibIpoibLinkLayerAddr OBJECT-TYPE 
       SYNTAX IbIpoibClientIdentifier 
       MAX-ACCESS read-only 
       STATUS current 
       DESCRIPTION  
          "A Client Identifier for this interface (port).  An  
           implementation may associate multiple IPOIB interfaces on the  
           same port.  It is up to the implementation to ensure a unique  
           Client Identifier when multiple IPOIB interfaces are defined  
           over the same port and same GID.  A unique, invariant  
           interface-id value must be included in addition to the GID  
           within the Client Identifier definition to achieve this.   
           Note: a port may also be associated with multiple GIDs.   
           Therefore, multiple IPOIB interfaces may exist on the same  
           port while using a different GID from among the GIDs  
           associated with the port.  In either case, the  
           IbIpoibLinkLayerAddr MUST be unique." 
       ::= { ibIpoibLinkLayerAddrEntry 3 }  
    
   ibIfCompliances OBJECT IDENTIFIER ::= { ibIfConformance 1 } 
   ibIfMIBGroups OBJECT IDENTIFIER ::= { ibIfConformance 2 } 
    
   --**************************************************************** 
   -- Compliance Statements 
   --**************************************************************** 
    
   ibIfBasicCompliance MODULE-COMPLIANCE 
              STATUS current 
              DESCRIPTION "The basic implementation requirements for  
                           managed network entities that have InfiniBand  
                           network interfaces." 
              MODULE  -- this module 
              -- ibIfStatOptionalPortStatGroup, ibIfVLTrafficGroup, and 
              -- ibIpoibLinkAddrGroup are not required for basic  
              -- implementation. 
              MANDATORY-GROUPS { ibIfStatMandatoryPortStatGroup } 
        ::= { ibIfCompliances 1 }   
    
   ibIfFullCompliance MODULE-COMPLIANCE 
              STATUS current 
              DESCRIPTION "The full implementation requirements for  
                           managed network entities that have InfiniBand  
                           network interfaces." 
              MODULE  -- this module 
              MANDATORY-GROUPS { ibIfStatMandatoryPortStatGroup, 
                                 ibIfStatOptionalPortStatGroup, 
                                 ibIfVLTrafficGroup,  
                                 ibIpoibLinkAddrGroup } 
        ::= { ibIfCompliances 2 }   
    
   --**************************************************************** 
   -- Units of Conformance 
   --**************************************************************** 
    
   ibIfStatMandatoryPortStatGroup OBJECT-GROUP 
       OBJECTS { 
          ibIfPortSymbolErrs, 
          ibIfPortLinkErrRecovery, 
          ibIfPortLinkDowned, 
          ibIfPortStatRcvRemPhyErrs, 
          ibIfPortStatRcvConstrErrs, 
          ibIfPortStatLinkIntergrityErrs, 
          ibIfPortStatExcBufOverrunErrs, 
          ibIfPortStatVL15Dropped 
      } 
        STATUS current 
        DESCRIPTION 
             "Detailed error statistics group for mandatory  
              InfiniBand-based Port Statistics counters." 
        ::= { ibIfMIBGroups 1 }   
    
   ibIfStatOptionalPortStatGroup OBJECT-GROUP 
       OBJECTS { 
          ibIfPortStatLocalPhyErrs, 
          ibIfPortStatMalPktErrs, 
          ibIfPortStatInactDiscards, 
          ibIfPortStatNeighMTUDiscards, 
          ibIfPortStatSwLifetimeDiscards, 
          ibIfPortStatHOQLifetimeDiscards 
      } 
        STATUS current 
        DESCRIPTION 
             "Detailed error statistics group for optional  
              InfiniBand-based Port Statistics counters." 
        ::= { ibIfMIBGroups 2 }   
    
   ibIfVLTrafficGroup OBJECT-GROUP 
       OBJECTS { 
          ibIfVLOutOctets, 
          ibIfVLOutPkts, 
          ibIfVLInOctets, 
          ibIfVLInPkts 
      } 
        STATUS current 
        DESCRIPTION 
             "Detailed per VL traffic statistics group." 
        ::= { ibIfMIBGroups 3 }   

   ibIpoibLinkAddrGroup OBJECT-GROUP 
       OBJECTS { 
          ibIpoibLinkLayerAddr 
      } 
        STATUS current 
        DESCRIPTION 
             "Detailed per port IPOIB link layer address group." 
        ::= { ibIfMIBGroups 4 }   
    
   END 

--     
--    Copyright (C) The Internet Society (2006). 
--     
--    This document is subject to the rights, licenses and restrictions 
--    contained in BCP 78, and except as set forth therein, the authors 
--    retain all their rights. 
--        
--    This document and the information contained herein are provided 
--    on an "AS IS" basis and THE CONTRIBUTOR, THE ORGANIZATION HE/SHE 
--    REPRESENTS OR IS SPONSORED BY (IF ANY), THE INTERNET SOCIETY AND 
--    THE INTERNET ENGINEERING TASK FORCE DISCLAIM ALL WARRANTIES, 
--    EXPRESS OR IMPLIED, INCLUDING BUT NOT LIMITED TO ANY WARRANTY THAT 
--    THE USE OF THE INFORMATION HEREIN WILL NOT INFRINGE ANY RIGHTS OR 
--    ANY IMPLIED WARRANTIES OF MERCHANTABILITY OR FITNESS FOR A 
--    PARTICULAR PURPOSE. 
--  
--    This document and translations of it may be copied and 
--    furnished to others, and derivative works that comment on 
--    or otherwise explain it or assist in its implementation may 
--    be prepared, copied, published and distributed, in whole or 
--    in part, without restriction of any kind, provided that the 
--    above copyright notice and this paragraph are included on 
--    all such copies and derivative works.  However, this document 
--    itself may not be modified in any way, such as by removing the 
--    copyright notice or references to the Internet Society or other  
--    Internet organizations, except as needed for the purpose of  
--    developing Internet standards in which case the procedures for  
--    copyrights defined in the Internet Standards process must be  
--    followed, or as required to translate it into languages other  
--    than English. 
--        
--    The limited permissions granted above are perpetual and 
--    will not be revoked by the Internet Society or its 
--    successors or assigns.  
--     
-- Acknowledgment 
--     
--    Funding for the RFC Editor function is currently provided by the 
--    Internet Society.
