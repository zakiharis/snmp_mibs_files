IT-WATCHDOGS-MIB DEFINITIONS ::= BEGIN

IMPORTS 


DisplayString, TruthValue					FROM SNMPv2-TC
MODULE-IDENTITY, OBJECT-TYPE, enterprises, Unsigned32		FROM SNMPv2-SMI
TRAP-TYPE							FROM RFC-1215;

itwatchdogs MODULE-IDENTITY
	LAST-UPDATED "200902200000Z"
	ORGANIZATION "I.T. Watchdogs"
	CONTACT-INFO "support@itwatchdogs.com"
	DESCRIPTION "The MIB for I.T. Watchdogs Products"
	::= { enterprises 17373 }

itwatchdogs OBJECT IDENTIFIER
	::= { enterprises 17373 }
	
wxGoos OBJECT IDENTIFIER
	::= { itwatchdogs 2 }

deviceInfo OBJECT IDENTIFIER
	::= { wxGoos 1 }

productTitle OBJECT-TYPE
	SYNTAX DisplayString
	MAX-ACCESS read-only
	STATUS current
	DESCRIPTION "Product name"
	::= { deviceInfo 1 }

productVersion OBJECT-TYPE
	SYNTAX DisplayString
	MAX-ACCESS read-only
	STATUS current
	DESCRIPTION "Product version"
	::= { deviceInfo 2 }

productFriendlyName OBJECT-TYPE
	SYNTAX DisplayString
	MAX-ACCESS read-only
	STATUS current
	DESCRIPTION "User-assigned name"
	::= { deviceInfo 3 }

productMacAddress OBJECT-TYPE
	SYNTAX DisplayString
	MAX-ACCESS read-only
	STATUS current
	DESCRIPTION "Product's unique MAC address"
	::= { deviceInfo 4 }

productUrl OBJECT-TYPE
	SYNTAX DisplayString
	MAX-ACCESS read-only
	STATUS current
	DESCRIPTION "Product's main URL access point"
	::= { deviceInfo 5 }

alarmTripType OBJECT-TYPE
        SYNTAX INTEGER(0..9)
        MAX-ACCESS read-only
        STATUS current
        DESCRIPTION "Type of alarm trip. 0 = None, 1 = Low, 2 = High, 3 = Unplugged"
        ::= { deviceInfo 6 }
        
productHardware OBJECT-TYPE
        SYNTAX DisplayString
        MAX-ACCESS read-only
        STATUS current
        DESCRIPTION "Product's hardware type"
        ::= { deviceInfo 7 }
        
sensorCountsBase OBJECT IDENTIFIER
	::= { deviceInfo 8 }
	
sensorCounts OBJECT IDENTIFIER
	::= { sensorCountsBase 1 }
	
climateCount OBJECT-TYPE
        SYNTAX INTEGER(0..16)
        MAX-ACCESS read-only
        STATUS current
        DESCRIPTION "Number of climate monitors currently plugged in"
        ::= { sensorCounts 2 }
		
powerMonitorCount OBJECT-TYPE
        SYNTAX INTEGER(0..16)
        MAX-ACCESS read-only
        STATUS current
        DESCRIPTION "Number of power monitors currently plugged in"
        ::= { sensorCounts 3 }
		
tempSensorCount OBJECT-TYPE
        SYNTAX INTEGER(0..16)
        MAX-ACCESS read-only
        STATUS current
        DESCRIPTION "Number of temperature sensors currently plugged in"
        ::= { sensorCounts 4 }
		
airflowSensorCount OBJECT-TYPE
        SYNTAX INTEGER(0..16)
        MAX-ACCESS read-only
        STATUS current
        DESCRIPTION "Number of airflow sensors currently plugged in"
        ::= { sensorCounts 5 }
		
powerOnlyCount OBJECT-TYPE
        SYNTAX INTEGER(0..16)
        MAX-ACCESS read-only
        STATUS current
        DESCRIPTION "Number of power only monitors currently plugged in"
        ::= { sensorCounts 6 }
		
doorSensorCount OBJECT-TYPE
        SYNTAX INTEGER(0..16)
        MAX-ACCESS read-only
        STATUS current
        DESCRIPTION "Number of door sensors currently plugged in"
        ::= { sensorCounts 7 }
		
waterSensorCount OBJECT-TYPE
        SYNTAX INTEGER(0..16)
        MAX-ACCESS read-only
        STATUS current
        DESCRIPTION "Number of water sensors currently plugged in"
        ::= { sensorCounts 8 }
		
currentSensorCount OBJECT-TYPE
        SYNTAX INTEGER(0..16)
        MAX-ACCESS read-only
        STATUS current
        DESCRIPTION "Number of current sensors currently plugged in"
        ::= { sensorCounts 9 }
		
millivoltSensorCount OBJECT-TYPE
        SYNTAX INTEGER(0..16)
        MAX-ACCESS read-only
        STATUS current
        DESCRIPTION "Number of millivolt sensors currently plugged in"
        ::= { sensorCounts 10 }
		
power3ChSensorCount OBJECT-TYPE
        SYNTAX INTEGER(0..16)
        MAX-ACCESS read-only
        STATUS current
        DESCRIPTION "Number of 3 channel power monitors currently plugged in"
        ::= { sensorCounts 11 }
		
outletCount OBJECT-TYPE
        SYNTAX INTEGER(0..16)
        MAX-ACCESS read-only
        STATUS current
        DESCRIPTION "Number of outlets currently plugged in"
        ::= { sensorCounts 12 }
		
vsfcCount OBJECT-TYPE
        SYNTAX INTEGER(0..16)
        MAX-ACCESS read-only
        STATUS current
        DESCRIPTION "Number of fan controller monitors currently plugged in"
        ::= { sensorCounts 13 }
		
ctrl3ChCount OBJECT-TYPE
        SYNTAX INTEGER(0..16)
        MAX-ACCESS read-only
        STATUS current
        DESCRIPTION "Number of 3 channel controllers currently plugged in"
        ::= { sensorCounts 14 }
		
ctrlGrpAmpsCount OBJECT-TYPE
        SYNTAX INTEGER(0..16)
        MAX-ACCESS read-only
        STATUS current
        DESCRIPTION "Number of amperage controllers currently plugged in"
        ::= { sensorCounts 15 }
		
ctrlOutputCount OBJECT-TYPE
        SYNTAX INTEGER(0..16)
        MAX-ACCESS read-only
        STATUS current
        DESCRIPTION "Number of output controllers currently plugged in"
        ::= { sensorCounts 16 }
		
dewpointSensorCount OBJECT-TYPE
        SYNTAX INTEGER(0..16)
        MAX-ACCESS read-only
        STATUS current
        DESCRIPTION "Number of dewpoint sensors currently plugged in"
        ::= { sensorCounts 17 }
		
digitalSensorCount OBJECT-TYPE
        SYNTAX INTEGER(0..16)
        MAX-ACCESS read-only
        STATUS current
        DESCRIPTION "Number of digital sensors currently plugged in"
        ::= { sensorCounts 18 }
		
dstsSensorCount OBJECT-TYPE
        SYNTAX INTEGER(0..16)
        MAX-ACCESS read-only
        STATUS current
        DESCRIPTION "Number of DSTS controllers currently plugged in"
        ::= { sensorCounts 19 }
		
cpmSensorCount OBJECT-TYPE
        SYNTAX INTEGER(0..16)
        MAX-ACCESS read-only
        STATUS current
        DESCRIPTION "Number of city power sensors currently plugged in"
        ::= { sensorCounts 20 }
		
smokeAlarmSensorCount OBJECT-TYPE
        SYNTAX INTEGER(0..16)
        MAX-ACCESS read-only
        STATUS current
        DESCRIPTION "Number of smoke alarm sensors currently plugged in"
        ::= { sensorCounts 21 }
		
neg48VdcSensorCount OBJECT-TYPE
        SYNTAX INTEGER(0..16)
        MAX-ACCESS read-only
        STATUS current
        DESCRIPTION "Number of -48Vdc sensors currently plugged in"
        ::= { sensorCounts 22 }
		
pos30VdcSensorCount OBJECT-TYPE
        SYNTAX INTEGER(0..16)
        MAX-ACCESS read-only
        STATUS current
        DESCRIPTION "Number of 30Vdc sensors currently plugged in"
        ::= { sensorCounts 23 }
		
analogSensorCount OBJECT-TYPE
        SYNTAX INTEGER(0..16)
        MAX-ACCESS read-only
        STATUS current
        DESCRIPTION "Number of remote analog inputs currently plugged in"
        ::= { sensorCounts 24 }
		
ctrl3ChIECCount OBJECT-TYPE
        SYNTAX INTEGER(0..16)
        MAX-ACCESS read-only
        STATUS current
        DESCRIPTION "Number of IEC 3 channel controllers currently plugged in"
        ::= { sensorCounts 25 }
		
airSpeedSwitchSensorCount OBJECT-TYPE
        SYNTAX INTEGER(0..16)
        MAX-ACCESS read-only
        STATUS current
        DESCRIPTION "Number of air speed switch sensors currently plugged in"
        ::= { sensorCounts 26 }
		
climateTable OBJECT-TYPE
	SYNTAX SEQUENCE OF ClimateEntry
	MAX-ACCESS  not-accessible
	STATUS current
	DESCRIPTION "Climate sensors (internal sensors for climate units)"
	::= { wxGoos 2 }

powerMonitorTable OBJECT-TYPE
	SYNTAX SEQUENCE OF PowerMonitorEntry
	MAX-ACCESS  not-accessible
	STATUS current
	DESCRIPTION "A table of Power Monitors"
	::= { wxGoos 3 }

tempSensorTable OBJECT-TYPE
	SYNTAX SEQUENCE OF TempSensorEntry
	MAX-ACCESS  not-accessible
	STATUS current
	DESCRIPTION "A table of temperature sensors"
	::= { wxGoos 4 }

airFlowSensorTable OBJECT-TYPE
	SYNTAX SEQUENCE OF AirFlowSensorEntry
	MAX-ACCESS  not-accessible
	STATUS current
	DESCRIPTION "A table of airflow sensors"
	::= { wxGoos 5 }

powerOnlyTable OBJECT-TYPE
	SYNTAX SEQUENCE OF PowerOnlyEntry
	MAX-ACCESS  not-accessible
	STATUS current
	DESCRIPTION "A table of Power-Only devices"
	::= { wxGoos 6 }

doorSensorTable OBJECT-TYPE
	SYNTAX SEQUENCE OF DoorSensorEntry
	MAX-ACCESS  not-accessible
	STATUS current
	DESCRIPTION "A table of door sensors"
	::= { wxGoos 7 }

waterSensorTable OBJECT-TYPE
	SYNTAX SEQUENCE OF WaterSensorEntry
	MAX-ACCESS  not-accessible
	STATUS current
	DESCRIPTION "A table of water sensors"
	::= { wxGoos 8 }

currentMonitorTable OBJECT-TYPE
	SYNTAX SEQUENCE OF CurrentMonitorEntry
	MAX-ACCESS  not-accessible
	STATUS current
	DESCRIPTION "A table of current monitors"
	::= { wxGoos 9 }

millivoltMonitorTable OBJECT-TYPE
	SYNTAX SEQUENCE OF MillivoltMonitorEntry
	MAX-ACCESS  not-accessible
	STATUS current
	DESCRIPTION "A table of millivolt monitors"
	::= { wxGoos 10 }

power3ChTable OBJECT-TYPE
	SYNTAX SEQUENCE OF Power3ChEntry
	MAX-ACCESS  not-accessible
	STATUS current
	DESCRIPTION "A table of Power Monitor 3 Channel"
	::= { wxGoos 11 }

outletTable OBJECT-TYPE
	SYNTAX SEQUENCE OF OutletEntry
	MAX-ACCESS  not-accessible
	STATUS current
	DESCRIPTION "A table of outlets"
	::= { wxGoos 12 }

vsfcTable OBJECT-TYPE
	SYNTAX SEQUENCE OF VsfcEntry
	MAX-ACCESS  not-accessible
	STATUS current
	DESCRIPTION "VSFC sensors (internal sensors for VSFC units)"
	::= { wxGoos 13 }

ctrl3ChTable OBJECT-TYPE
	SYNTAX SEQUENCE OF Ctrl3ChEntry
	MAX-ACCESS  not-accessible
	STATUS current
	DESCRIPTION "A table of a 3 phase outlet control"
	::= { wxGoos 14 }

ctrlGrpAmpsTable OBJECT-TYPE
	SYNTAX SEQUENCE OF CtrlGrpAmpsEntry
	MAX-ACCESS  not-accessible
	STATUS current
	DESCRIPTION "A table of Control Group Amp readings"
	::= { wxGoos 15 }

ctrlOutletTable OBJECT-TYPE
	SYNTAX SEQUENCE OF CtrlOutletEntry
	MAX-ACCESS  not-accessible
	STATUS current
	DESCRIPTION "A table of outlet information"
	::= { wxGoos 16 }

dewPointSensorTable OBJECT-TYPE
	SYNTAX SEQUENCE OF DewPointSensorEntry
	MAX-ACCESS  not-accessible
	STATUS current
	DESCRIPTION "A table of dew point sensors"
	::= { wxGoos 17 }

digitalSensorTable OBJECT-TYPE
	SYNTAX SEQUENCE OF DigitalSensorEntry
	MAX-ACCESS  not-accessible
	STATUS current
	DESCRIPTION "A table of digital sensors"
	::= { wxGoos 18 }

dstsTable OBJECT-TYPE
	SYNTAX SEQUENCE OF DstsEntry
	MAX-ACCESS  not-accessible
	STATUS current
	DESCRIPTION "Digital Static Transfer Switch status"
	::= { wxGoos 19 }

cpmSensorTable OBJECT-TYPE
	SYNTAX SEQUENCE OF CpmSensorEntry
	MAX-ACCESS  not-accessible
	STATUS current
	DESCRIPTION "A table of city power sensors"
	::= { wxGoos 20 }

smokeAlarmTable OBJECT-TYPE
	SYNTAX SEQUENCE OF SmokeAlarmEntry
	MAX-ACCESS  not-accessible
	STATUS current
	DESCRIPTION "A table of smoke alarm sensors"
	::= { wxGoos 21 }

neg48VdcSensorTable OBJECT-TYPE
	SYNTAX SEQUENCE OF Neg48VdcSensorEntry
	MAX-ACCESS  not-accessible
	STATUS current
	DESCRIPTION "A table of -48Vdc sensors"
	::= { wxGoos 22 }

pos30VdcSensorTable OBJECT-TYPE
	SYNTAX SEQUENCE OF Pos30VdcSensorEntry
	MAX-ACCESS  not-accessible
	STATUS current
	DESCRIPTION "A table of 30Vdc sensors"
	::= { wxGoos 23 }

analogSensorTable OBJECT-TYPE
	SYNTAX SEQUENCE OF AnalogSensorEntry
	MAX-ACCESS  not-accessible
	STATUS current
	DESCRIPTION "A table of analog sensors"
	::= { wxGoos 24 }

ctrl3ChIECTable OBJECT-TYPE
	SYNTAX SEQUENCE OF Ctrl3ChIECEntry
	MAX-ACCESS  not-accessible
	STATUS current
	DESCRIPTION "A table of a 3 phase outlet control (IEC)"
	::= { wxGoos 25 }

airSpeedSwitchSensorTable OBJECT-TYPE
	SYNTAX SEQUENCE OF AirSpeedSwitchSensorEntry
	MAX-ACCESS  not-accessible
	STATUS current
	DESCRIPTION "A table of air speed switch sensors"
	::= { wxGoos 26 }

climateEntry OBJECT-TYPE
	SYNTAX  ClimateEntry
	MAX-ACCESS  not-accessible
	STATUS current
	DESCRIPTION 
		"Entry in the climate table: each entry contains
an index (climateIndex) and other details"
	INDEX { climateIndex }
	::= { climateTable 1 }

ClimateEntry ::= SEQUENCE {
	climateIndex		INTEGER(1..1),
	climateSerial		DisplayString,
	climateName		DisplayString,
	climateAvail		Unsigned32,
	climateTempC		INTEGER(-40..123),
	climateHumidity		INTEGER(0..100),
	climateAirflow		INTEGER(0..100),
	climateLight		INTEGER(0..100),
	climateSound		INTEGER(0..100),
	climateIO1		INTEGER(0..100),
	climateIO2		INTEGER(0..100),
	climateIO3		INTEGER(0..100)
}

climateIndex OBJECT-TYPE
	SYNTAX  INTEGER(1..1)
	MAX-ACCESS  not-accessible
	STATUS current
	DESCRIPTION "Table entry index value"
	::= { climateEntry  1 }
	
climateSerial OBJECT-TYPE
	SYNTAX  DisplayString
	MAX-ACCESS  read-only
	STATUS current
	DESCRIPTION "Serial Number"
	::= { climateEntry  2 }
	
climateName OBJECT-TYPE
	SYNTAX  DisplayString
	MAX-ACCESS  read-only
	STATUS current
	DESCRIPTION "Friendly Name"
	::= { climateEntry  3 }
	
climateAvail OBJECT-TYPE
	SYNTAX  Unsigned32
	MAX-ACCESS  read-only
	STATUS current
	DESCRIPTION "Is device currently plugged in?"
	::= { climateEntry  4 }
	
climateTempC OBJECT-TYPE
	SYNTAX  INTEGER(-40..123)
	UNITS "Degrees Celsius"
	MAX-ACCESS  read-only
	STATUS current
	DESCRIPTION "Current reading for Temperature (C)"
	::= { climateEntry  5 }
	
climateHumidity OBJECT-TYPE
	SYNTAX  INTEGER(0..100)
	UNITS "%"
	MAX-ACCESS  read-only
	STATUS current
	DESCRIPTION "Current reading for Humidity"
	::= { climateEntry  6 }
	
climateAirflow OBJECT-TYPE
	SYNTAX  INTEGER(0..100)
	MAX-ACCESS  read-only
	STATUS current
	DESCRIPTION "Current reading for Airflow"
	::= { climateEntry  7 }
	
climateLight OBJECT-TYPE
	SYNTAX  INTEGER(0..100)
	MAX-ACCESS  read-only
	STATUS current
	DESCRIPTION "Current reading for Ambient Light"
	::= { climateEntry  8 }
	
climateSound OBJECT-TYPE
	SYNTAX  INTEGER(0..100)
	MAX-ACCESS  read-only
	STATUS current
	DESCRIPTION "Current reading for Sound"
	::= { climateEntry  9 }
	
climateIO1 OBJECT-TYPE
	SYNTAX  INTEGER(0..100)
	MAX-ACCESS  read-only
	STATUS current
	DESCRIPTION "Current reading for Analog Input 1"
	::= { climateEntry  10 }
	
climateIO2 OBJECT-TYPE
	SYNTAX  INTEGER(0..100)
	MAX-ACCESS  read-only
	STATUS current
	DESCRIPTION "Current reading for Analog Input 2"
	::= { climateEntry  11 }
	
climateIO3 OBJECT-TYPE
	SYNTAX  INTEGER(0..100)
	MAX-ACCESS  read-only
	STATUS current
	DESCRIPTION "Current reading for Analog Input 3"
	::= { climateEntry  12 }
	
powerMonitorEntry OBJECT-TYPE
	SYNTAX  PowerMonitorEntry
	MAX-ACCESS  not-accessible
	STATUS current
	DESCRIPTION 
		"Entry in the power monitor table: each entry contains
an index (powMonIndex) and other power monitoring details"
	INDEX { powMonIndex }
	::= { powerMonitorTable 1 }

PowerMonitorEntry ::= SEQUENCE {
	powMonIndex		INTEGER(1..100),
	powMonSerial		DisplayString,
	powMonName		DisplayString,
	powMonAvail		Unsigned32,
	powMonKWattHrs		Unsigned32,
	powMonVolts		Unsigned32,
	powMonVoltMax		Unsigned32,
	powMonVoltMin		Unsigned32,
	powMonVoltPeak		Unsigned32,
	powMonDeciAmps		Unsigned32,
	powMonRealPower		Unsigned32,
	powMonApparentPower		Unsigned32,
	powMonPowerFactor		INTEGER(0..100),
	powMonDeciAmpsOutlet1		INTEGER(0..100),
	powMonDeciAmpsOutlet2		INTEGER(0..100)
}

powMonIndex OBJECT-TYPE
	SYNTAX  INTEGER(1..100)
	MAX-ACCESS  not-accessible
	STATUS current
	DESCRIPTION "Table entry index value"
	::= { powerMonitorEntry  1 }
	
powMonSerial OBJECT-TYPE
	SYNTAX  DisplayString
	MAX-ACCESS  read-only
	STATUS current
	DESCRIPTION "Serial Number"
	::= { powerMonitorEntry  2 }
	
powMonName OBJECT-TYPE
	SYNTAX  DisplayString
	MAX-ACCESS  read-only
	STATUS current
	DESCRIPTION "Friendly Name"
	::= { powerMonitorEntry  3 }
	
powMonAvail OBJECT-TYPE
	SYNTAX  Unsigned32
	MAX-ACCESS  read-only
	STATUS current
	DESCRIPTION "Is device currently plugged in?"
	::= { powerMonitorEntry  4 }
	
powMonKWattHrs OBJECT-TYPE
	SYNTAX  Unsigned32
	UNITS "KWh"
	MAX-ACCESS  read-only
	STATUS current
	DESCRIPTION "Current reading for KWatt-Hours"
	::= { powerMonitorEntry  5 }
	
powMonVolts OBJECT-TYPE
	SYNTAX  Unsigned32
	UNITS "Volts (rms)"
	MAX-ACCESS  read-only
	STATUS current
	DESCRIPTION "Current reading for Volts"
	::= { powerMonitorEntry  6 }
	
powMonVoltMax OBJECT-TYPE
	SYNTAX  Unsigned32
	UNITS "Volts (rms)"
	MAX-ACCESS  read-only
	STATUS current
	DESCRIPTION "Current reading for Volts (Max)"
	::= { powerMonitorEntry  7 }
	
powMonVoltMin OBJECT-TYPE
	SYNTAX  Unsigned32
	UNITS "Volts (rms)"
	MAX-ACCESS  read-only
	STATUS current
	DESCRIPTION "Current reading for Volts (Min)"
	::= { powerMonitorEntry  8 }
	
powMonVoltPeak OBJECT-TYPE
	SYNTAX  Unsigned32
	UNITS "Volts (rms)"
	MAX-ACCESS  read-only
	STATUS current
	DESCRIPTION "Current reading for Volts (Peak)"
	::= { powerMonitorEntry  9 }
	
powMonDeciAmps OBJECT-TYPE
	SYNTAX  Unsigned32
	UNITS "0.1 Amps (rms)"
	MAX-ACCESS  read-only
	STATUS current
	DESCRIPTION "Current reading for DeciAmps"
	::= { powerMonitorEntry  10 }
	
powMonRealPower OBJECT-TYPE
	SYNTAX  Unsigned32
	UNITS "Watts"
	MAX-ACCESS  read-only
	STATUS current
	DESCRIPTION "Current reading for Real Power"
	::= { powerMonitorEntry  11 }
	
powMonApparentPower OBJECT-TYPE
	SYNTAX  Unsigned32
	UNITS "Volt-Amps"
	MAX-ACCESS  read-only
	STATUS current
	DESCRIPTION "Current reading for Apparent Power"
	::= { powerMonitorEntry  12 }
	
powMonPowerFactor OBJECT-TYPE
	SYNTAX  INTEGER(0..100)
	UNITS "%"
	MAX-ACCESS  read-only
	STATUS current
	DESCRIPTION "Current reading for Power Factor"
	::= { powerMonitorEntry  13 }
	
powMonDeciAmpsOutlet1 OBJECT-TYPE
	SYNTAX  INTEGER(0..100)
	UNITS "0.1 Amps (rms)"
	MAX-ACCESS  read-only
	STATUS current
	DESCRIPTION "Current reading for Outlet 1"
	::= { powerMonitorEntry  14 }
	
powMonDeciAmpsOutlet2 OBJECT-TYPE
	SYNTAX  INTEGER(0..100)
	UNITS "0.1 Amps (rms)"
	MAX-ACCESS  read-only
	STATUS current
	DESCRIPTION "Current reading for Outlet 2"
	::= { powerMonitorEntry  15 }
	
tempSensorEntry OBJECT-TYPE
	SYNTAX  TempSensorEntry
	MAX-ACCESS  not-accessible
	STATUS current
	DESCRIPTION 
		"Entry in the temperature sensor table: each entry contains
an index (tempIndex) and other sensor details"
	INDEX { tempSensorIndex }
	::= { tempSensorTable 1 }

TempSensorEntry ::= SEQUENCE {
	tempSensorIndex		INTEGER(1..100),
	tempSensorSerial		DisplayString,
	tempSensorName		DisplayString,
	tempSensorAvail		Unsigned32,
	tempSensorTempC		INTEGER(-40..123)
}

tempSensorIndex OBJECT-TYPE
	SYNTAX  INTEGER(1..100)
	MAX-ACCESS  not-accessible
	STATUS current
	DESCRIPTION "Table entry index value"
	::= { tempSensorEntry  1 }
	
tempSensorSerial OBJECT-TYPE
	SYNTAX  DisplayString
	MAX-ACCESS  read-only
	STATUS current
	DESCRIPTION "Serial Number"
	::= { tempSensorEntry  2 }
	
tempSensorName OBJECT-TYPE
	SYNTAX  DisplayString
	MAX-ACCESS  read-only
	STATUS current
	DESCRIPTION "Friendly Name"
	::= { tempSensorEntry  3 }
	
tempSensorAvail OBJECT-TYPE
	SYNTAX  Unsigned32
	MAX-ACCESS  read-only
	STATUS current
	DESCRIPTION "Is device currently plugged in?"
	::= { tempSensorEntry  4 }
	
tempSensorTempC OBJECT-TYPE
	SYNTAX  INTEGER(-40..123)
	UNITS "Degrees Celsius"
	MAX-ACCESS  read-only
	STATUS current
	DESCRIPTION "Temperature in Celsius"
	::= { tempSensorEntry  5 }
	
airFlowSensorEntry OBJECT-TYPE
	SYNTAX  AirFlowSensorEntry
	MAX-ACCESS  not-accessible
	STATUS current
	DESCRIPTION 
		"Entry in the air flow sensor table: each entry contains
an index (airFlowSensorIndex) and other sensor details"
	INDEX { airFlowSensorIndex }
	::= { airFlowSensorTable 1 }

AirFlowSensorEntry ::= SEQUENCE {
	airFlowSensorIndex		INTEGER(1..100),
	airFlowSensorSerial		DisplayString,
	airFlowSensorName		DisplayString,
	airFlowSensorAvail		Unsigned32,
	airFlowSensorFlow		INTEGER(0..100),
	airFlowSensorTempC		INTEGER(-50..100),
	airFlowSensorHumidity		INTEGER(0..100),
	airFlowSensorDewPoint		INTEGER(-40..123)
}

airFlowSensorIndex OBJECT-TYPE
	SYNTAX  INTEGER(1..100)
	MAX-ACCESS  not-accessible
	STATUS current
	DESCRIPTION "Table entry index value"
	::= { airFlowSensorEntry  1 }
	
airFlowSensorSerial OBJECT-TYPE
	SYNTAX  DisplayString
	MAX-ACCESS  read-only
	STATUS current
	DESCRIPTION "Serial Number"
	::= { airFlowSensorEntry  2 }
	
airFlowSensorName OBJECT-TYPE
	SYNTAX  DisplayString
	MAX-ACCESS  read-only
	STATUS current
	DESCRIPTION "Friendly Name"
	::= { airFlowSensorEntry  3 }
	
airFlowSensorAvail OBJECT-TYPE
	SYNTAX  Unsigned32
	MAX-ACCESS  read-only
	STATUS current
	DESCRIPTION "Is device currently plugged in?"
	::= { airFlowSensorEntry  4 }
	
airFlowSensorFlow OBJECT-TYPE
	SYNTAX  INTEGER(0..100)
	MAX-ACCESS  read-only
	STATUS current
	DESCRIPTION "Air flow reading"
	::= { airFlowSensorEntry  5 }
	
airFlowSensorTempC OBJECT-TYPE
	SYNTAX  INTEGER(-50..100)
	UNITS "Degrees Celsius"
	MAX-ACCESS  read-only
	STATUS current
	DESCRIPTION "Temperature reading in C"
	::= { airFlowSensorEntry  6 }
	
airFlowSensorHumidity OBJECT-TYPE
	SYNTAX  INTEGER(0..100)
	UNITS "%"
	MAX-ACCESS  read-only
	STATUS current
	DESCRIPTION "Humidity reading"
	::= { airFlowSensorEntry  7 }
	
airFlowSensorDewPoint OBJECT-TYPE
	SYNTAX  INTEGER(-40..123)
	UNITS "Degrees Celsius"
	MAX-ACCESS  read-only
	STATUS current
	DESCRIPTION "Dew point reading in C"
	::= { airFlowSensorEntry  8 }
	
powerOnlyEntry OBJECT-TYPE
	SYNTAX  PowerOnlyEntry
	MAX-ACCESS  not-accessible
	STATUS current
	DESCRIPTION 
		"Entry in the power-only device table: each entry contains
an index (powerIndex) and other power details"
	INDEX { powerIndex }
	::= { powerOnlyTable 1 }

PowerOnlyEntry ::= SEQUENCE {
	powerIndex		INTEGER(1..100),
	powerSerial		DisplayString,
	powerName		DisplayString,
	powerAvail		Unsigned32,
	powerVolts		Unsigned32,
	powerDeciAmps		Unsigned32,
	powerRealPower		Unsigned32,
	powerApparentPower		Unsigned32,
	powerPowerFactor		INTEGER(0..100)
}

powerIndex OBJECT-TYPE
	SYNTAX  INTEGER(1..100)
	MAX-ACCESS  not-accessible
	STATUS current
	DESCRIPTION "Table entry index value"
	::= { powerOnlyEntry  1 }
	
powerSerial OBJECT-TYPE
	SYNTAX  DisplayString
	MAX-ACCESS  read-only
	STATUS current
	DESCRIPTION "Serial Number"
	::= { powerOnlyEntry  2 }
	
powerName OBJECT-TYPE
	SYNTAX  DisplayString
	MAX-ACCESS  read-only
	STATUS current
	DESCRIPTION "Friendly Name"
	::= { powerOnlyEntry  3 }
	
powerAvail OBJECT-TYPE
	SYNTAX  Unsigned32
	MAX-ACCESS  read-only
	STATUS current
	DESCRIPTION "Is device currently plugged in?"
	::= { powerOnlyEntry  4 }
	
powerVolts OBJECT-TYPE
	SYNTAX  Unsigned32
	UNITS "Volts (rms)"
	MAX-ACCESS  read-only
	STATUS current
	DESCRIPTION "Current reading for Volts"
	::= { powerOnlyEntry  5 }
	
powerDeciAmps OBJECT-TYPE
	SYNTAX  Unsigned32
	UNITS "0.1 Amps (rms)"
	MAX-ACCESS  read-only
	STATUS current
	DESCRIPTION "Current reading for DeciAmps"
	::= { powerOnlyEntry  6 }
	
powerRealPower OBJECT-TYPE
	SYNTAX  Unsigned32
	UNITS "Watts"
	MAX-ACCESS  read-only
	STATUS current
	DESCRIPTION "Current reading for Real Power"
	::= { powerOnlyEntry  7 }
	
powerApparentPower OBJECT-TYPE
	SYNTAX  Unsigned32
	UNITS "Volt-Amps"
	MAX-ACCESS  read-only
	STATUS current
	DESCRIPTION "Current reading for Apparent Power"
	::= { powerOnlyEntry  8 }
	
powerPowerFactor OBJECT-TYPE
	SYNTAX  INTEGER(0..100)
	UNITS "%"
	MAX-ACCESS  read-only
	STATUS current
	DESCRIPTION "Current reading for Power Factor"
	::= { powerOnlyEntry  9 }
	
doorSensorEntry OBJECT-TYPE
	SYNTAX  DoorSensorEntry
	MAX-ACCESS  not-accessible
	STATUS current
	DESCRIPTION 
		"Entry in the door sensor table: each entry contains
an index (doorSensorIndex) and other sensor details"
	INDEX { doorSensorIndex }
	::= { doorSensorTable 1 }

DoorSensorEntry ::= SEQUENCE {
	doorSensorIndex		INTEGER(1..100),
	doorSensorSerial		DisplayString,
	doorSensorName		DisplayString,
	doorSensorAvail		Unsigned32,
	doorSensorStatus		INTEGER(0..100)
}

doorSensorIndex OBJECT-TYPE
	SYNTAX  INTEGER(1..100)
	MAX-ACCESS  not-accessible
	STATUS current
	DESCRIPTION "Table entry index value"
	::= { doorSensorEntry  1 }
	
doorSensorSerial OBJECT-TYPE
	SYNTAX  DisplayString
	MAX-ACCESS  read-only
	STATUS current
	DESCRIPTION "Serial Number"
	::= { doorSensorEntry  2 }
	
doorSensorName OBJECT-TYPE
	SYNTAX  DisplayString
	MAX-ACCESS  read-only
	STATUS current
	DESCRIPTION "Friendly Name"
	::= { doorSensorEntry  3 }
	
doorSensorAvail OBJECT-TYPE
	SYNTAX  Unsigned32
	MAX-ACCESS  read-only
	STATUS current
	DESCRIPTION "Is device currently plugged in?"
	::= { doorSensorEntry  4 }
	
doorSensorStatus OBJECT-TYPE
	SYNTAX  INTEGER(0..100)
	MAX-ACCESS  read-only
	STATUS current
	DESCRIPTION "Door sensor status"
	::= { doorSensorEntry  5 }
	
waterSensorEntry OBJECT-TYPE
	SYNTAX  WaterSensorEntry
	MAX-ACCESS  not-accessible
	STATUS current
	DESCRIPTION 
		"Entry in the water sensor table: each entry contains
an index (waterSensorIndex) and other sensor details"
	INDEX { waterSensorIndex }
	::= { waterSensorTable 1 }

WaterSensorEntry ::= SEQUENCE {
	waterSensorIndex		INTEGER(1..100),
	waterSensorSerial		DisplayString,
	waterSensorName		DisplayString,
	waterSensorAvail		Unsigned32,
	waterSensorDampness		INTEGER(0..100)
}

waterSensorIndex OBJECT-TYPE
	SYNTAX  INTEGER(1..100)
	MAX-ACCESS  not-accessible
	STATUS current
	DESCRIPTION "Table entry index value"
	::= { waterSensorEntry  1 }
	
waterSensorSerial OBJECT-TYPE
	SYNTAX  DisplayString
	MAX-ACCESS  read-only
	STATUS current
	DESCRIPTION "Serial Number"
	::= { waterSensorEntry  2 }
	
waterSensorName OBJECT-TYPE
	SYNTAX  DisplayString
	MAX-ACCESS  read-only
	STATUS current
	DESCRIPTION "Friendly Name"
	::= { waterSensorEntry  3 }
	
waterSensorAvail OBJECT-TYPE
	SYNTAX  Unsigned32
	MAX-ACCESS  read-only
	STATUS current
	DESCRIPTION "Is device currently plugged in?"
	::= { waterSensorEntry  4 }
	
waterSensorDampness OBJECT-TYPE
	SYNTAX  INTEGER(0..100)
	MAX-ACCESS  read-only
	STATUS current
	DESCRIPTION "Dampness of the water sensor"
	::= { waterSensorEntry  5 }
	
currentMonitorEntry OBJECT-TYPE
	SYNTAX  CurrentMonitorEntry
	MAX-ACCESS  not-accessible
	STATUS current
	DESCRIPTION 
		"Entry in the current monitor table: each entry contains
an index (currentMonitorIndex) and other sensor details"
	INDEX { currentMonitorIndex }
	::= { currentMonitorTable 1 }

CurrentMonitorEntry ::= SEQUENCE {
	currentMonitorIndex		INTEGER(1..100),
	currentMonitorSerial		DisplayString,
	currentMonitorName		DisplayString,
	currentMonitorAvail		Unsigned32,
	currentMonitorDeciAmps		INTEGER(0..30)
}

currentMonitorIndex OBJECT-TYPE
	SYNTAX  INTEGER(1..100)
	MAX-ACCESS  not-accessible
	STATUS current
	DESCRIPTION "Table entry index value"
	::= { currentMonitorEntry  1 }
	
currentMonitorSerial OBJECT-TYPE
	SYNTAX  DisplayString
	MAX-ACCESS  read-only
	STATUS current
	DESCRIPTION "Serial Number"
	::= { currentMonitorEntry  2 }
	
currentMonitorName OBJECT-TYPE
	SYNTAX  DisplayString
	MAX-ACCESS  read-only
	STATUS current
	DESCRIPTION "Friendly Name"
	::= { currentMonitorEntry  3 }
	
currentMonitorAvail OBJECT-TYPE
	SYNTAX  Unsigned32
	MAX-ACCESS  read-only
	STATUS current
	DESCRIPTION "Is device currently plugged in?"
	::= { currentMonitorEntry  4 }
	
currentMonitorDeciAmps OBJECT-TYPE
	SYNTAX  INTEGER(0..30)
	UNITS "0.1 Amps"
	MAX-ACCESS  read-only
	STATUS current
	DESCRIPTION "Current in deciamps"
	::= { currentMonitorEntry  5 }
	
millivoltMonitorEntry OBJECT-TYPE
	SYNTAX  MillivoltMonitorEntry
	MAX-ACCESS  not-accessible
	STATUS current
	DESCRIPTION 
		"Entry in the millivolt monitor table: each entry contains
an index (millivoltMonitorIndex) and other sensor details"
	INDEX { millivoltMonitorIndex }
	::= { millivoltMonitorTable 1 }

MillivoltMonitorEntry ::= SEQUENCE {
	millivoltMonitorIndex		INTEGER(1..100),
	millivoltMonitorSerial		DisplayString,
	millivoltMonitorName		DisplayString,
	millivoltMonitorAvail		Unsigned32,
	millivoltMonitorMV		INTEGER(0..5000)
}

millivoltMonitorIndex OBJECT-TYPE
	SYNTAX  INTEGER(1..100)
	MAX-ACCESS  not-accessible
	STATUS current
	DESCRIPTION "Table entry index value"
	::= { millivoltMonitorEntry  1 }
	
millivoltMonitorSerial OBJECT-TYPE
	SYNTAX  DisplayString
	MAX-ACCESS  read-only
	STATUS current
	DESCRIPTION "Serial Number"
	::= { millivoltMonitorEntry  2 }
	
millivoltMonitorName OBJECT-TYPE
	SYNTAX  DisplayString
	MAX-ACCESS  read-only
	STATUS current
	DESCRIPTION "Friendly Name"
	::= { millivoltMonitorEntry  3 }
	
millivoltMonitorAvail OBJECT-TYPE
	SYNTAX  Unsigned32
	MAX-ACCESS  read-only
	STATUS current
	DESCRIPTION "Is device currently plugged in?"
	::= { millivoltMonitorEntry  4 }
	
millivoltMonitorMV OBJECT-TYPE
	SYNTAX  INTEGER(0..5000)
	UNITS "millivolts"
	MAX-ACCESS  read-only
	STATUS current
	DESCRIPTION "millivolts"
	::= { millivoltMonitorEntry  5 }
	
power3ChEntry OBJECT-TYPE
	SYNTAX  Power3ChEntry
	MAX-ACCESS  not-accessible
	STATUS current
	DESCRIPTION 
		"Entry in the power monitor 3 channel table: each entry contains
an index (pow3ChIndex) and other power monitoring details"
	INDEX { pow3ChIndex }
	::= { power3ChTable 1 }

Power3ChEntry ::= SEQUENCE {
	pow3ChIndex		INTEGER(1..100),
	pow3ChSerial		DisplayString,
	pow3ChName		DisplayString,
	pow3ChAvail		Unsigned32,
	pow3ChKWattHrsA		Unsigned32,
	pow3ChVoltsA		Unsigned32,
	pow3ChVoltMaxA		Unsigned32,
	pow3ChVoltMinA		Unsigned32,
	pow3ChVoltPeakA		Unsigned32,
	pow3ChDeciAmpsA		Unsigned32,
	pow3ChRealPowerA		Unsigned32,
	pow3ChApparentPowerA		Unsigned32,
	pow3ChPowerFactorA		INTEGER(0..100),
	pow3ChKWattHrsB		Unsigned32,
	pow3ChVoltsB		Unsigned32,
	pow3ChVoltMaxB		Unsigned32,
	pow3ChVoltMinB		Unsigned32,
	pow3ChVoltPeakB		Unsigned32,
	pow3ChDeciAmpsB		Unsigned32,
	pow3ChRealPowerB		Unsigned32,
	pow3ChApparentPowerB		Unsigned32,
	pow3ChPowerFactorB		INTEGER(0..100),
	pow3ChKWattHrsC		Unsigned32,
	pow3ChVoltsC		Unsigned32,
	pow3ChVoltMaxC		Unsigned32,
	pow3ChVoltMinC		Unsigned32,
	pow3ChVoltPeakC		Unsigned32,
	pow3ChDeciAmpsC		Unsigned32,
	pow3ChRealPowerC		Unsigned32,
	pow3ChApparentPowerC		Unsigned32,
	pow3ChPowerFactorC		INTEGER(0..100)
}

pow3ChIndex OBJECT-TYPE
	SYNTAX  INTEGER(1..100)
	MAX-ACCESS  not-accessible
	STATUS current
	DESCRIPTION "Table entry index value"
	::= { power3ChEntry  1 }
	
pow3ChSerial OBJECT-TYPE
	SYNTAX  DisplayString
	MAX-ACCESS  read-only
	STATUS current
	DESCRIPTION "Serial Number"
	::= { power3ChEntry  2 }
	
pow3ChName OBJECT-TYPE
	SYNTAX  DisplayString
	MAX-ACCESS  read-only
	STATUS current
	DESCRIPTION "Friendly Name"
	::= { power3ChEntry  3 }
	
pow3ChAvail OBJECT-TYPE
	SYNTAX  Unsigned32
	MAX-ACCESS  read-only
	STATUS current
	DESCRIPTION "Is device currently plugged in?"
	::= { power3ChEntry  4 }
	
pow3ChKWattHrsA OBJECT-TYPE
	SYNTAX  Unsigned32
	UNITS "KWh"
	MAX-ACCESS  read-only
	STATUS current
	DESCRIPTION "Current reading for KWatt-Hours (Phase A)"
	::= { power3ChEntry  5 }
	
pow3ChVoltsA OBJECT-TYPE
	SYNTAX  Unsigned32
	UNITS "Volts (rms)"
	MAX-ACCESS  read-only
	STATUS current
	DESCRIPTION "Current reading for Volts (Phase A)"
	::= { power3ChEntry  6 }
	
pow3ChVoltMaxA OBJECT-TYPE
	SYNTAX  Unsigned32
	UNITS "Volts (rms)"
	MAX-ACCESS  read-only
	STATUS current
	DESCRIPTION "Current reading for Max-Volts (Phase A)"
	::= { power3ChEntry  7 }
	
pow3ChVoltMinA OBJECT-TYPE
	SYNTAX  Unsigned32
	UNITS "Volts (rms)"
	MAX-ACCESS  read-only
	STATUS current
	DESCRIPTION "Current reading for Min-Volts (Phase A)"
	::= { power3ChEntry  8 }
	
pow3ChVoltPeakA OBJECT-TYPE
	SYNTAX  Unsigned32
	UNITS "Volts"
	MAX-ACCESS  read-only
	STATUS current
	DESCRIPTION "Current reading for Peak-Volts (Phase A)"
	::= { power3ChEntry  9 }
	
pow3ChDeciAmpsA OBJECT-TYPE
	SYNTAX  Unsigned32
	UNITS "0.1 Amps (rms)"
	MAX-ACCESS  read-only
	STATUS current
	DESCRIPTION "Current reading for DeciAmps (Phase A)"
	::= { power3ChEntry  10 }
	
pow3ChRealPowerA OBJECT-TYPE
	SYNTAX  Unsigned32
	UNITS "Watts"
	MAX-ACCESS  read-only
	STATUS current
	DESCRIPTION "Current reading for Real Power (Phase A)"
	::= { power3ChEntry  11 }
	
pow3ChApparentPowerA OBJECT-TYPE
	SYNTAX  Unsigned32
	UNITS "Volt-Amps"
	MAX-ACCESS  read-only
	STATUS current
	DESCRIPTION "Current reading for Apparent Power (Phase A)"
	::= { power3ChEntry  12 }
	
pow3ChPowerFactorA OBJECT-TYPE
	SYNTAX  INTEGER(0..100)
	UNITS "%"
	MAX-ACCESS  read-only
	STATUS current
	DESCRIPTION "Current reading for Power Factor (Phase A)"
	::= { power3ChEntry  13 }
	
pow3ChKWattHrsB OBJECT-TYPE
	SYNTAX  Unsigned32
	UNITS "KWh"
	MAX-ACCESS  read-only
	STATUS current
	DESCRIPTION "Current reading for KWatt-Hours (Phase B)"
	::= { power3ChEntry  14 }
	
pow3ChVoltsB OBJECT-TYPE
	SYNTAX  Unsigned32
	UNITS "Volts (rms)"
	MAX-ACCESS  read-only
	STATUS current
	DESCRIPTION "Current reading for Volts (Phase B)"
	::= { power3ChEntry  15 }
	
pow3ChVoltMaxB OBJECT-TYPE
	SYNTAX  Unsigned32
	UNITS "Volts (rms)"
	MAX-ACCESS  read-only
	STATUS current
	DESCRIPTION "Current reading for Max-Volts (Phase B)"
	::= { power3ChEntry  16 }
	
pow3ChVoltMinB OBJECT-TYPE
	SYNTAX  Unsigned32
	UNITS "Volts (rms)"
	MAX-ACCESS  read-only
	STATUS current
	DESCRIPTION "Current reading for Min-Volts (Phase B)"
	::= { power3ChEntry  17 }
	
pow3ChVoltPeakB OBJECT-TYPE
	SYNTAX  Unsigned32
	UNITS "Volts"
	MAX-ACCESS  read-only
	STATUS current
	DESCRIPTION "Current reading for Peak-Volts (Phase B)"
	::= { power3ChEntry  18 }
	
pow3ChDeciAmpsB OBJECT-TYPE
	SYNTAX  Unsigned32
	UNITS "0.1 Amps (rms)"
	MAX-ACCESS  read-only
	STATUS current
	DESCRIPTION "Current reading for DeciAmps (Phase B)"
	::= { power3ChEntry  19 }
	
pow3ChRealPowerB OBJECT-TYPE
	SYNTAX  Unsigned32
	UNITS "Watts"
	MAX-ACCESS  read-only
	STATUS current
	DESCRIPTION "Current reading for Real Power (Phase B)"
	::= { power3ChEntry  20 }
	
pow3ChApparentPowerB OBJECT-TYPE
	SYNTAX  Unsigned32
	UNITS "Volt-Amps"
	MAX-ACCESS  read-only
	STATUS current
	DESCRIPTION "Current reading for Apparent Power (Phase B)"
	::= { power3ChEntry  21 }
	
pow3ChPowerFactorB OBJECT-TYPE
	SYNTAX  INTEGER(0..100)
	UNITS "%"
	MAX-ACCESS  read-only
	STATUS current
	DESCRIPTION "Current reading for Power Factor (Phase B)"
	::= { power3ChEntry  22 }
	
pow3ChKWattHrsC OBJECT-TYPE
	SYNTAX  Unsigned32
	UNITS "KWh"
	MAX-ACCESS  read-only
	STATUS current
	DESCRIPTION "Current reading for KWatt-Hours (Phase C)"
	::= { power3ChEntry  23 }
	
pow3ChVoltsC OBJECT-TYPE
	SYNTAX  Unsigned32
	UNITS "Volts (rms)"
	MAX-ACCESS  read-only
	STATUS current
	DESCRIPTION "Current reading for Volts (Phase C)"
	::= { power3ChEntry  24 }
	
pow3ChVoltMaxC OBJECT-TYPE
	SYNTAX  Unsigned32
	UNITS "Volts (rms)"
	MAX-ACCESS  read-only
	STATUS current
	DESCRIPTION "Current reading for Max-Volts (Phase C)"
	::= { power3ChEntry  25 }
	
pow3ChVoltMinC OBJECT-TYPE
	SYNTAX  Unsigned32
	UNITS "Volts (rms)"
	MAX-ACCESS  read-only
	STATUS current
	DESCRIPTION "Current reading for Min-Volts (Phase C)"
	::= { power3ChEntry  26 }
	
pow3ChVoltPeakC OBJECT-TYPE
	SYNTAX  Unsigned32
	UNITS "Volts"
	MAX-ACCESS  read-only
	STATUS current
	DESCRIPTION "Current reading for Peak-Volts (Phase C)"
	::= { power3ChEntry  27 }
	
pow3ChDeciAmpsC OBJECT-TYPE
	SYNTAX  Unsigned32
	UNITS "0.1 Amps (rms)"
	MAX-ACCESS  read-only
	STATUS current
	DESCRIPTION "Current reading for DeciAmps (Phase C)"
	::= { power3ChEntry  28 }
	
pow3ChRealPowerC OBJECT-TYPE
	SYNTAX  Unsigned32
	UNITS "Watts"
	MAX-ACCESS  read-only
	STATUS current
	DESCRIPTION "Current reading for Real Power (Phase C)"
	::= { power3ChEntry  29 }
	
pow3ChApparentPowerC OBJECT-TYPE
	SYNTAX  Unsigned32
	UNITS "Volt-Amps"
	MAX-ACCESS  read-only
	STATUS current
	DESCRIPTION "Current reading for Apparent Power (Phase C)"
	::= { power3ChEntry  30 }
	
pow3ChPowerFactorC OBJECT-TYPE
	SYNTAX  INTEGER(0..100)
	UNITS "%"
	MAX-ACCESS  read-only
	STATUS current
	DESCRIPTION "Current reading for Power Factor (Phase C)"
	::= { power3ChEntry  31 }
	
outletEntry OBJECT-TYPE
	SYNTAX  OutletEntry
	MAX-ACCESS  not-accessible
	STATUS current
	DESCRIPTION 
		"Entry in the outlet table: each entry contains
an index (outletIndex) and other sensor details"
	INDEX { outletIndex }
	::= { outletTable 1 }

OutletEntry ::= SEQUENCE {
	outletIndex		INTEGER(1..100),
	outletSerial		DisplayString,
	outletName		DisplayString,
	outletAvail		Unsigned32,
	outlet1Status		INTEGER(0..100),
	outlet2Status		INTEGER(0..100)
}

outletIndex OBJECT-TYPE
	SYNTAX  INTEGER(1..100)
	MAX-ACCESS  not-accessible
	STATUS current
	DESCRIPTION "Table entry index value"
	::= { outletEntry  1 }
	
outletSerial OBJECT-TYPE
	SYNTAX  DisplayString
	MAX-ACCESS  read-only
	STATUS current
	DESCRIPTION "Serial Number"
	::= { outletEntry  2 }
	
outletName OBJECT-TYPE
	SYNTAX  DisplayString
	MAX-ACCESS  read-only
	STATUS current
	DESCRIPTION "Friendly Name"
	::= { outletEntry  3 }
	
outletAvail OBJECT-TYPE
	SYNTAX  Unsigned32
	MAX-ACCESS  read-only
	STATUS current
	DESCRIPTION "Is device currently plugged in?"
	::= { outletEntry  4 }
	
outlet1Status OBJECT-TYPE
	SYNTAX  INTEGER(0..100)
	MAX-ACCESS  read-only
	STATUS current
	DESCRIPTION "Outlet 1 status"
	::= { outletEntry  5 }
	
outlet2Status OBJECT-TYPE
	SYNTAX  INTEGER(0..100)
	MAX-ACCESS  read-only
	STATUS current
	DESCRIPTION "Outlet 2 status"
	::= { outletEntry  6 }
	
vsfcEntry OBJECT-TYPE
	SYNTAX  VsfcEntry
	MAX-ACCESS  not-accessible
	STATUS current
	DESCRIPTION 
		"Entry in the vsfc table: each entry contains
an index (vsfcIndex) and other details"
	INDEX { vsfcIndex }
	::= { vsfcTable 1 }

VsfcEntry ::= SEQUENCE {
	vsfcIndex		INTEGER(1..1),
	vsfcSerial		DisplayString,
	vsfcName		DisplayString,
	vsfcAvail		Unsigned32,
	vsfcSetPointC		INTEGER(18..38),
	vsfcIntTempC		INTEGER(-20..50),
	vsfcExt1TempC		INTEGER(-20..50),
	vsfcExt2TempC		INTEGER(-20..50),
	vsfcExt3TempC		INTEGER(-20..50),
	vsfcExt4TempC		INTEGER(-20..50),
	vsfcFanSpeed		INTEGER(0..100)
}

vsfcIndex OBJECT-TYPE
	SYNTAX  INTEGER(1..1)
	MAX-ACCESS  not-accessible
	STATUS current
	DESCRIPTION "Table entry index value"
	::= { vsfcEntry  1 }
	
vsfcSerial OBJECT-TYPE
	SYNTAX  DisplayString
	MAX-ACCESS  read-only
	STATUS current
	DESCRIPTION "Serial Number"
	::= { vsfcEntry  2 }
	
vsfcName OBJECT-TYPE
	SYNTAX  DisplayString
	MAX-ACCESS  read-only
	STATUS current
	DESCRIPTION "Friendly Name"
	::= { vsfcEntry  3 }
	
vsfcAvail OBJECT-TYPE
	SYNTAX  Unsigned32
	MAX-ACCESS  read-only
	STATUS current
	DESCRIPTION "Is device currently plugged in?"
	::= { vsfcEntry  4 }
	
vsfcSetPointC OBJECT-TYPE
	SYNTAX  INTEGER(18..38)
	UNITS "Degrees Celsius"
	MAX-ACCESS  read-only
	STATUS current
	DESCRIPTION "Current temperature set point in C"
	::= { vsfcEntry  5 }
	
vsfcIntTempC OBJECT-TYPE
	SYNTAX  INTEGER(-20..50)
	UNITS "Degrees Celsius"
	MAX-ACCESS  read-only
	STATUS current
	DESCRIPTION "Current internal temperature reading in C"
	::= { vsfcEntry  6 }
	
vsfcExt1TempC OBJECT-TYPE
	SYNTAX  INTEGER(-20..50)
	UNITS "Degrees Celsius"
	MAX-ACCESS  read-only
	STATUS current
	DESCRIPTION "Current reading for external temp 1 in C"
	::= { vsfcEntry  7 }
	
vsfcExt2TempC OBJECT-TYPE
	SYNTAX  INTEGER(-20..50)
	UNITS "Degrees Celsius"
	MAX-ACCESS  read-only
	STATUS current
	DESCRIPTION "Current reading for external temp 2 in C"
	::= { vsfcEntry  8 }
	
vsfcExt3TempC OBJECT-TYPE
	SYNTAX  INTEGER(-20..50)
	UNITS "Degrees Celsius"
	MAX-ACCESS  read-only
	STATUS current
	DESCRIPTION "Current reading for external temp 3 in C"
	::= { vsfcEntry  9 }
	
vsfcExt4TempC OBJECT-TYPE
	SYNTAX  INTEGER(-20..50)
	UNITS "Degrees Celsius"
	MAX-ACCESS  read-only
	STATUS current
	DESCRIPTION "Current reading for external temp 4 in C"
	::= { vsfcEntry  10 }
	
vsfcFanSpeed OBJECT-TYPE
	SYNTAX  INTEGER(0..100)
	UNITS "%"
	MAX-ACCESS  read-only
	STATUS current
	DESCRIPTION "Current reading for Fan Speed"
	::= { vsfcEntry  11 }
	
ctrl3ChEntry OBJECT-TYPE
	SYNTAX  Ctrl3ChEntry
	MAX-ACCESS  not-accessible
	STATUS current
	DESCRIPTION 
		"Entry in the 3 phase outlet control table: each entry contains
an index (ctrl3ChIndex) and other outlet control monitoring details"
	INDEX { ctrl3ChIndex }
	::= { ctrl3ChTable 1 }

Ctrl3ChEntry ::= SEQUENCE {
	ctrl3ChIndex		INTEGER(1..1),
	ctrl3ChSerial		DisplayString,
	ctrl3ChName		DisplayString,
	ctrl3ChAvail		Unsigned32,
	ctrl3ChVoltsA		Unsigned32,
	ctrl3ChVoltPeakA		Unsigned32,
	ctrl3ChDeciAmpsA		Unsigned32,
	ctrl3ChDeciAmpsPeakA		Unsigned32,
	ctrl3ChRealPowerA		Unsigned32,
	ctrl3ChApparentPowerA		Unsigned32,
	ctrl3ChPowerFactorA		INTEGER(0..100),
	ctrl3ChVoltsB		Unsigned32,
	ctrl3ChVoltPeakB		Unsigned32,
	ctrl3ChDeciAmpsB		Unsigned32,
	ctrl3ChDeciAmpsPeakB		Unsigned32,
	ctrl3ChRealPowerB		Unsigned32,
	ctrl3ChApparentPowerB		Unsigned32,
	ctrl3ChPowerFactorB		INTEGER(0..100),
	ctrl3ChVoltsC		Unsigned32,
	ctrl3ChVoltPeakC		Unsigned32,
	ctrl3ChDeciAmpsC		Unsigned32,
	ctrl3ChDeciAmpsPeakC		Unsigned32,
	ctrl3ChRealPowerC		Unsigned32,
	ctrl3ChApparentPowerC		Unsigned32,
	ctrl3ChPowerFactorC		INTEGER(0..100)
}

ctrl3ChIndex OBJECT-TYPE
	SYNTAX  INTEGER(1..1)
	MAX-ACCESS  not-accessible
	STATUS current
	DESCRIPTION "Table entry index value"
	::= { ctrl3ChEntry  1 }
	
ctrl3ChSerial OBJECT-TYPE
	SYNTAX  DisplayString
	MAX-ACCESS  read-only
	STATUS current
	DESCRIPTION "Serial Number"
	::= { ctrl3ChEntry  2 }
	
ctrl3ChName OBJECT-TYPE
	SYNTAX  DisplayString
	MAX-ACCESS  read-only
	STATUS current
	DESCRIPTION "Friendly Name"
	::= { ctrl3ChEntry  3 }
	
ctrl3ChAvail OBJECT-TYPE
	SYNTAX  Unsigned32
	MAX-ACCESS  read-only
	STATUS current
	DESCRIPTION "Is device currently plugged in?"
	::= { ctrl3ChEntry  4 }
	
ctrl3ChVoltsA OBJECT-TYPE
	SYNTAX  Unsigned32
	UNITS "Volts (rms)"
	MAX-ACCESS  read-only
	STATUS current
	DESCRIPTION "Current reading for Volts (Phase A)"
	::= { ctrl3ChEntry  5 }
	
ctrl3ChVoltPeakA OBJECT-TYPE
	SYNTAX  Unsigned32
	UNITS "Volts (rms)"
	MAX-ACCESS  read-only
	STATUS current
	DESCRIPTION "Current reading for Peak-Volts (Phase A)"
	::= { ctrl3ChEntry  6 }
	
ctrl3ChDeciAmpsA OBJECT-TYPE
	SYNTAX  Unsigned32
	UNITS "0.1 Amps (rms)"
	MAX-ACCESS  read-only
	STATUS current
	DESCRIPTION "Current reading for DeciAmps (Phase A)"
	::= { ctrl3ChEntry  7 }
	
ctrl3ChDeciAmpsPeakA OBJECT-TYPE
	SYNTAX  Unsigned32
	UNITS "0.1 Amps (rms)"
	MAX-ACCESS  read-only
	STATUS current
	DESCRIPTION "Current reading for Peak-DeciAmps (Phase A)"
	::= { ctrl3ChEntry  8 }
	
ctrl3ChRealPowerA OBJECT-TYPE
	SYNTAX  Unsigned32
	UNITS "Watts"
	MAX-ACCESS  read-only
	STATUS current
	DESCRIPTION "Current reading for Real Power (Phase A)"
	::= { ctrl3ChEntry  9 }
	
ctrl3ChApparentPowerA OBJECT-TYPE
	SYNTAX  Unsigned32
	UNITS "Volt-Amps"
	MAX-ACCESS  read-only
	STATUS current
	DESCRIPTION "Current reading for Apparent Power (Phase A)"
	::= { ctrl3ChEntry  10 }
	
ctrl3ChPowerFactorA OBJECT-TYPE
	SYNTAX  INTEGER(0..100)
	UNITS "%"
	MAX-ACCESS  read-only
	STATUS current
	DESCRIPTION "Current reading for Power Factor (Phase A)"
	::= { ctrl3ChEntry  11 }
	
ctrl3ChVoltsB OBJECT-TYPE
	SYNTAX  Unsigned32
	UNITS "Volts (rms)"
	MAX-ACCESS  read-only
	STATUS current
	DESCRIPTION "Current reading for Volts (Phase B)"
	::= { ctrl3ChEntry  12 }
	
ctrl3ChVoltPeakB OBJECT-TYPE
	SYNTAX  Unsigned32
	UNITS "Volts (rms)"
	MAX-ACCESS  read-only
	STATUS current
	DESCRIPTION "Current reading for Peak-Volts (Phase B)"
	::= { ctrl3ChEntry  13 }
	
ctrl3ChDeciAmpsB OBJECT-TYPE
	SYNTAX  Unsigned32
	UNITS "0.1 Amps (rms)"
	MAX-ACCESS  read-only
	STATUS current
	DESCRIPTION "Current reading for DeciAmps (Phase B)"
	::= { ctrl3ChEntry  14 }
	
ctrl3ChDeciAmpsPeakB OBJECT-TYPE
	SYNTAX  Unsigned32
	UNITS "0.1 Amps (rms)"
	MAX-ACCESS  read-only
	STATUS current
	DESCRIPTION "Current reading for Peak-DeciAmps (Phase B)"
	::= { ctrl3ChEntry  15 }
	
ctrl3ChRealPowerB OBJECT-TYPE
	SYNTAX  Unsigned32
	UNITS "Watts"
	MAX-ACCESS  read-only
	STATUS current
	DESCRIPTION "Current reading for Real Power (Phase B)"
	::= { ctrl3ChEntry  16 }
	
ctrl3ChApparentPowerB OBJECT-TYPE
	SYNTAX  Unsigned32
	UNITS "Volt-Amps"
	MAX-ACCESS  read-only
	STATUS current
	DESCRIPTION "Current reading for Apparent Power (Phase B)"
	::= { ctrl3ChEntry  17 }
	
ctrl3ChPowerFactorB OBJECT-TYPE
	SYNTAX  INTEGER(0..100)
	UNITS "%"
	MAX-ACCESS  read-only
	STATUS current
	DESCRIPTION "Current reading for Power Factor (Phase B)"
	::= { ctrl3ChEntry  18 }
	
ctrl3ChVoltsC OBJECT-TYPE
	SYNTAX  Unsigned32
	UNITS "Volts (rms)"
	MAX-ACCESS  read-only
	STATUS current
	DESCRIPTION "Current reading for Volts (Phase C)"
	::= { ctrl3ChEntry  19 }
	
ctrl3ChVoltPeakC OBJECT-TYPE
	SYNTAX  Unsigned32
	UNITS "Volts (rms)"
	MAX-ACCESS  read-only
	STATUS current
	DESCRIPTION "Current reading for Peak-Volts (Phase C)"
	::= { ctrl3ChEntry  20 }
	
ctrl3ChDeciAmpsC OBJECT-TYPE
	SYNTAX  Unsigned32
	UNITS "0.1 Amps (rms)"
	MAX-ACCESS  read-only
	STATUS current
	DESCRIPTION "Current reading for DeciAmps (Phase C)"
	::= { ctrl3ChEntry  21 }
	
ctrl3ChDeciAmpsPeakC OBJECT-TYPE
	SYNTAX  Unsigned32
	UNITS "0.1 Amps (rms)"
	MAX-ACCESS  read-only
	STATUS current
	DESCRIPTION "Current reading for Peak-DeciAmps (Phase C)"
	::= { ctrl3ChEntry  22 }
	
ctrl3ChRealPowerC OBJECT-TYPE
	SYNTAX  Unsigned32
	UNITS "Watts"
	MAX-ACCESS  read-only
	STATUS current
	DESCRIPTION "Current reading for Real Power (Phase C)"
	::= { ctrl3ChEntry  23 }
	
ctrl3ChApparentPowerC OBJECT-TYPE
	SYNTAX  Unsigned32
	UNITS "Volt-Amps"
	MAX-ACCESS  read-only
	STATUS current
	DESCRIPTION "Current reading for Apparent Power (Phase C)"
	::= { ctrl3ChEntry  24 }
	
ctrl3ChPowerFactorC OBJECT-TYPE
	SYNTAX  INTEGER(0..100)
	UNITS "%"
	MAX-ACCESS  read-only
	STATUS current
	DESCRIPTION "Current reading for Power Factor (Phase C)"
	::= { ctrl3ChEntry  25 }
	
ctrlGrpAmpsEntry OBJECT-TYPE
	SYNTAX  CtrlGrpAmpsEntry
	MAX-ACCESS  not-accessible
	STATUS current
	DESCRIPTION 
		"Entry in the Control Group Amps table: each entry contains
an index (ctrlGrpAmpsIndex) and other sensor details"
	INDEX { ctrlGrpAmpsIndex }
	::= { ctrlGrpAmpsTable 1 }

CtrlGrpAmpsEntry ::= SEQUENCE {
	ctrlGrpAmpsIndex		INTEGER(1..1),
	ctrlGrpAmpsSerial		DisplayString,
	ctrlGrpAmpsName		DisplayString,
	ctrlGrpAmpsAvail		Unsigned32,
	ctrlGrpAmpsA		Unsigned32,
	ctrlGrpAmpsB		Unsigned32,
	ctrlGrpAmpsC		Unsigned32,
	ctrlGrpAmpsD		Unsigned32,
	ctrlGrpAmpsE		Unsigned32,
	ctrlGrpAmpsF		Unsigned32
}

ctrlGrpAmpsIndex OBJECT-TYPE
	SYNTAX  INTEGER(1..1)
	MAX-ACCESS  not-accessible
	STATUS current
	DESCRIPTION "Table entry index value"
	::= { ctrlGrpAmpsEntry  1 }
	
ctrlGrpAmpsSerial OBJECT-TYPE
	SYNTAX  DisplayString
	MAX-ACCESS  read-only
	STATUS current
	DESCRIPTION "Serial Number"
	::= { ctrlGrpAmpsEntry  2 }
	
ctrlGrpAmpsName OBJECT-TYPE
	SYNTAX  DisplayString
	MAX-ACCESS  read-only
	STATUS current
	DESCRIPTION "Friendly Name"
	::= { ctrlGrpAmpsEntry  3 }
	
ctrlGrpAmpsAvail OBJECT-TYPE
	SYNTAX  Unsigned32
	MAX-ACCESS  read-only
	STATUS current
	DESCRIPTION "Is device currently plugged in?"
	::= { ctrlGrpAmpsEntry  4 }
	
ctrlGrpAmpsA OBJECT-TYPE
	SYNTAX  Unsigned32
	UNITS "0.1 Amps (rms)"
	MAX-ACCESS  read-only
	STATUS current
	DESCRIPTION "DeciAmps Group A"
	::= { ctrlGrpAmpsEntry  5 }
	
ctrlGrpAmpsB OBJECT-TYPE
	SYNTAX  Unsigned32
	UNITS "0.1 Amps (rms)"
	MAX-ACCESS  read-only
	STATUS current
	DESCRIPTION "DeciAmps Group B"
	::= { ctrlGrpAmpsEntry  6 }
	
ctrlGrpAmpsC OBJECT-TYPE
	SYNTAX  Unsigned32
	UNITS "0.1 Amps (rms)"
	MAX-ACCESS  read-only
	STATUS current
	DESCRIPTION "DeciAmps Group C"
	::= { ctrlGrpAmpsEntry  7 }
	
ctrlGrpAmpsD OBJECT-TYPE
	SYNTAX  Unsigned32
	UNITS "0.1 Amps (rms)"
	MAX-ACCESS  read-only
	STATUS current
	DESCRIPTION "DeciAmps Group D"
	::= { ctrlGrpAmpsEntry  8 }
	
ctrlGrpAmpsE OBJECT-TYPE
	SYNTAX  Unsigned32
	UNITS "0.1 Amps (rms)"
	MAX-ACCESS  read-only
	STATUS current
	DESCRIPTION "DeciAmps Group E"
	::= { ctrlGrpAmpsEntry  9 }
	
ctrlGrpAmpsF OBJECT-TYPE
	SYNTAX  Unsigned32
	UNITS "0.1 Amps (rms)"
	MAX-ACCESS  read-only
	STATUS current
	DESCRIPTION "DeciAmps Group F"
	::= { ctrlGrpAmpsEntry  10 }
	
ctrlOutletEntry OBJECT-TYPE
	SYNTAX  CtrlOutletEntry
	MAX-ACCESS  not-accessible
	STATUS current
	DESCRIPTION 
		"Entry in the control outlet table: each entry contains
an index (ctrlOutletIndex) and other sensor details"
	INDEX { ctrlOutletIndex }
	::= { ctrlOutletTable 1 }

CtrlOutletEntry ::= SEQUENCE {
	ctrlOutletIndex		INTEGER(1..100),
	ctrlOutletName		DisplayString,
	ctrlOutletStatus		Unsigned32,
	ctrlOutletFeedback		Unsigned32,
	ctrlOutletPending		Unsigned32,
	ctrlOutletDeciAmps		Unsigned32,
	ctrlOutletGroup		DisplayString,
	ctrlOutletUpDelay		Unsigned32,
	ctrlOutletDwnDelay		Unsigned32,
	ctrlOutletRbtDelay		Unsigned32,
	ctrlOutletURL		DisplayString,
	ctrlOutletPOAAction		Unsigned32,
	ctrlOutletPOADelay		Unsigned32
}

ctrlOutletIndex OBJECT-TYPE
	SYNTAX  INTEGER(1..100)
	MAX-ACCESS  not-accessible
	STATUS current
	DESCRIPTION "Outlet Number"
	::= { ctrlOutletEntry  1 }
	
ctrlOutletName OBJECT-TYPE
	SYNTAX  DisplayString
	MAX-ACCESS  read-only
	STATUS current
	DESCRIPTION "Outlet Friendly Name"
	::= { ctrlOutletEntry  2 }
	
ctrlOutletStatus OBJECT-TYPE
	SYNTAX  Unsigned32
	MAX-ACCESS  read-only
	STATUS current
	DESCRIPTION "Current Outlet Status: 0 = Off, 1 = On"
	::= { ctrlOutletEntry  3 }
	
ctrlOutletFeedback OBJECT-TYPE
	SYNTAX  Unsigned32
	MAX-ACCESS  read-only
	STATUS current
	DESCRIPTION "Outlet Feedback Value, should be equal to status"
	::= { ctrlOutletEntry  4 }
	
ctrlOutletPending OBJECT-TYPE
	SYNTAX  Unsigned32
	MAX-ACCESS  read-only
	STATUS current
	DESCRIPTION "Outlet Status to change to: 0 = Off, 1 = On"
	::= { ctrlOutletEntry  5 }
	
ctrlOutletDeciAmps OBJECT-TYPE
	SYNTAX  Unsigned32
	UNITS "0.1 Amps (rms)"
	MAX-ACCESS  read-only
	STATUS current
	DESCRIPTION "Outlet DeciAmps reading"
	::= { ctrlOutletEntry  6 }
	
ctrlOutletGroup OBJECT-TYPE
	SYNTAX  DisplayString
	MAX-ACCESS  read-only
	STATUS current
	DESCRIPTION "Outlet Group (A to F)"
	::= { ctrlOutletEntry  7 }
	
ctrlOutletUpDelay OBJECT-TYPE
	SYNTAX  Unsigned32
	UNITS "seconds"
	MAX-ACCESS  read-only
	STATUS current
	DESCRIPTION "Outlet Power Up Delay"
	::= { ctrlOutletEntry  8 }
	
ctrlOutletDwnDelay OBJECT-TYPE
	SYNTAX  Unsigned32
	UNITS "seconds"
	MAX-ACCESS  read-only
	STATUS current
	DESCRIPTION "Outlet Power Down Delay"
	::= { ctrlOutletEntry  9 }
	
ctrlOutletRbtDelay OBJECT-TYPE
	SYNTAX  Unsigned32
	UNITS "seconds"
	MAX-ACCESS  read-only
	STATUS current
	DESCRIPTION "Outlet Reboot Delay"
	::= { ctrlOutletEntry  10 }
	
ctrlOutletURL OBJECT-TYPE
	SYNTAX  DisplayString
	MAX-ACCESS  read-only
	STATUS current
	DESCRIPTION "Outlet URL"
	::= { ctrlOutletEntry  11 }
	
ctrlOutletPOAAction OBJECT-TYPE
	SYNTAX  Unsigned32
	MAX-ACCESS  read-only
	STATUS current
	DESCRIPTION "POA Action: 1 = Off, 2 = On, 4 = Last, 0 = POA not supported on this unit type"
	::= { ctrlOutletEntry  12 }
	
ctrlOutletPOADelay OBJECT-TYPE
	SYNTAX  Unsigned32
	UNITS "seconds"
	MAX-ACCESS  read-only
	STATUS current
	DESCRIPTION "POA Delay"
	::= { ctrlOutletEntry  13 }
	
dewPointSensorEntry OBJECT-TYPE
	SYNTAX  DewPointSensorEntry
	MAX-ACCESS  not-accessible
	STATUS current
	DESCRIPTION 
		"Entry in the dew point sensor table: each entry contains
an index (dewPointSensorIndex) and other sensor details"
	INDEX { dewPointSensorIndex }
	::= { dewPointSensorTable 1 }

DewPointSensorEntry ::= SEQUENCE {
	dewPointSensorIndex		INTEGER(1..100),
	dewPointSensorSerial		DisplayString,
	dewPointSensorName		DisplayString,
	dewPointSensorAvail		Unsigned32,
	dewPointSensorDewPoint		INTEGER(-40..123),
	dewPointSensorTempC		INTEGER(-40..123),
	dewPointSensorHumidity		INTEGER(0..100)
}

dewPointSensorIndex OBJECT-TYPE
	SYNTAX  INTEGER(1..100)
	MAX-ACCESS  not-accessible
	STATUS current
	DESCRIPTION "Table entry index value"
	::= { dewPointSensorEntry  1 }
	
dewPointSensorSerial OBJECT-TYPE
	SYNTAX  DisplayString
	MAX-ACCESS  read-only
	STATUS current
	DESCRIPTION "Serial Number"
	::= { dewPointSensorEntry  2 }
	
dewPointSensorName OBJECT-TYPE
	SYNTAX  DisplayString
	MAX-ACCESS  read-only
	STATUS current
	DESCRIPTION "Friendly Name"
	::= { dewPointSensorEntry  3 }
	
dewPointSensorAvail OBJECT-TYPE
	SYNTAX  Unsigned32
	MAX-ACCESS  read-only
	STATUS current
	DESCRIPTION "Is device currently plugged in?"
	::= { dewPointSensorEntry  4 }
	
dewPointSensorDewPoint OBJECT-TYPE
	SYNTAX  INTEGER(-40..123)
	UNITS "Degrees Celsius"
	MAX-ACCESS  read-only
	STATUS current
	DESCRIPTION "Dew point reading in C"
	::= { dewPointSensorEntry  5 }
	
dewPointSensorTempC OBJECT-TYPE
	SYNTAX  INTEGER(-40..123)
	UNITS "Degrees Celsius"
	MAX-ACCESS  read-only
	STATUS current
	DESCRIPTION "Temperature reading in C"
	::= { dewPointSensorEntry  6 }
	
dewPointSensorHumidity OBJECT-TYPE
	SYNTAX  INTEGER(0..100)
	UNITS "%"
	MAX-ACCESS  read-only
	STATUS current
	DESCRIPTION "Humidity reading"
	::= { dewPointSensorEntry  7 }
	
digitalSensorEntry OBJECT-TYPE
	SYNTAX  DigitalSensorEntry
	MAX-ACCESS  not-accessible
	STATUS current
	DESCRIPTION 
		"Entry in the digital sensor table: each entry contains
an index (digitalSensorIndex) and other sensor details"
	INDEX { digitalSensorIndex }
	::= { digitalSensorTable 1 }

DigitalSensorEntry ::= SEQUENCE {
	digitalSensorIndex		INTEGER(1..100),
	digitalSensorSerial		DisplayString,
	digitalSensorName		DisplayString,
	digitalSensorAvail		Unsigned32,
	digitalSensorDigital		INTEGER(0..100)
}

digitalSensorIndex OBJECT-TYPE
	SYNTAX  INTEGER(1..100)
	MAX-ACCESS  not-accessible
	STATUS current
	DESCRIPTION "Table entry index value"
	::= { digitalSensorEntry  1 }
	
digitalSensorSerial OBJECT-TYPE
	SYNTAX  DisplayString
	MAX-ACCESS  read-only
	STATUS current
	DESCRIPTION "Serial Number"
	::= { digitalSensorEntry  2 }
	
digitalSensorName OBJECT-TYPE
	SYNTAX  DisplayString
	MAX-ACCESS  read-only
	STATUS current
	DESCRIPTION "Friendly Name"
	::= { digitalSensorEntry  3 }
	
digitalSensorAvail OBJECT-TYPE
	SYNTAX  Unsigned32
	MAX-ACCESS  read-only
	STATUS current
	DESCRIPTION "Is device currently plugged in?"
	::= { digitalSensorEntry  4 }
	
digitalSensorDigital OBJECT-TYPE
	SYNTAX  INTEGER(0..100)
	MAX-ACCESS  read-only
	STATUS current
	DESCRIPTION "Digital sensor status"
	::= { digitalSensorEntry  5 }
	
dstsEntry OBJECT-TYPE
	SYNTAX  DstsEntry
	MAX-ACCESS  not-accessible
	STATUS current
	DESCRIPTION 
		"Entry in the DSTS table: each entry contains
an index (dstsIndex) and other details"
	INDEX { dstsIndex }
	::= { dstsTable 1 }

DstsEntry ::= SEQUENCE {
	dstsIndex		INTEGER(1..1),
	dstsSerial		DisplayString,
	dstsName		DisplayString,
	dstsAvail		Unsigned32,
	dstsVoltsA		Unsigned32,
	dstsAmpsA		Unsigned32,
	dstsVoltsB		Unsigned32,
	dstsAmpsB		Unsigned32,
	dstsSourceAActive		Unsigned32,
	dstsSourceBActive		Unsigned32,
	dstsPowerStatusA		Unsigned32,
	dstsPowerStatusB		Unsigned32,
	dstsSourceATempC		INTEGER(-20..50),
	dstsSourceBTempC		INTEGER(-20..50)
}

dstsIndex OBJECT-TYPE
	SYNTAX  INTEGER(1..1)
	MAX-ACCESS  not-accessible
	STATUS current
	DESCRIPTION "Table entry index value"
	::= { dstsEntry  1 }
	
dstsSerial OBJECT-TYPE
	SYNTAX  DisplayString
	MAX-ACCESS  read-only
	STATUS current
	DESCRIPTION "Serial Number"
	::= { dstsEntry  2 }
	
dstsName OBJECT-TYPE
	SYNTAX  DisplayString
	MAX-ACCESS  read-only
	STATUS current
	DESCRIPTION "Friendly Name"
	::= { dstsEntry  3 }
	
dstsAvail OBJECT-TYPE
	SYNTAX  Unsigned32
	MAX-ACCESS  read-only
	STATUS current
	DESCRIPTION "Is device currently plugged in?"
	::= { dstsEntry  4 }
	
dstsVoltsA OBJECT-TYPE
	SYNTAX  Unsigned32
	UNITS "Volts (rms)"
	MAX-ACCESS  read-only
	STATUS current
	DESCRIPTION "RMS Voltage of Side A"
	::= { dstsEntry  5 }
	
dstsAmpsA OBJECT-TYPE
	SYNTAX  Unsigned32
	UNITS "0.1 Amps (rms)"
	MAX-ACCESS  read-only
	STATUS current
	DESCRIPTION "RMS Current of Side A in deciamps"
	::= { dstsEntry  6 }
	
dstsVoltsB OBJECT-TYPE
	SYNTAX  Unsigned32
	UNITS "Volts (rms)"
	MAX-ACCESS  read-only
	STATUS current
	DESCRIPTION "RMS Voltage of Side B"
	::= { dstsEntry  7 }
	
dstsAmpsB OBJECT-TYPE
	SYNTAX  Unsigned32
	UNITS "0.1 Amps (rms)"
	MAX-ACCESS  read-only
	STATUS current
	DESCRIPTION "RMS Current of Side B in deciamps"
	::= { dstsEntry  8 }
	
dstsSourceAActive OBJECT-TYPE
	SYNTAX  Unsigned32
	MAX-ACCESS  read-only
	STATUS current
	DESCRIPTION "If 99, source A active"
	::= { dstsEntry  9 }
	
dstsSourceBActive OBJECT-TYPE
	SYNTAX  Unsigned32
	MAX-ACCESS  read-only
	STATUS current
	DESCRIPTION "If 99, source B active"
	::= { dstsEntry  10 }
	
dstsPowerStatusA OBJECT-TYPE
	SYNTAX  Unsigned32
	MAX-ACCESS  read-only
	STATUS current
	DESCRIPTION "Power Quality of source A"
	::= { dstsEntry  11 }
	
dstsPowerStatusB OBJECT-TYPE
	SYNTAX  Unsigned32
	MAX-ACCESS  read-only
	STATUS current
	DESCRIPTION "Power Quality of Source B"
	::= { dstsEntry  12 }
	
dstsSourceATempC OBJECT-TYPE
	SYNTAX  INTEGER(-20..50)
	UNITS "Degrees Celsius"
	MAX-ACCESS  read-only
	STATUS current
	DESCRIPTION "Current reading for Source A temp in C"
	::= { dstsEntry  13 }
	
dstsSourceBTempC OBJECT-TYPE
	SYNTAX  INTEGER(-20..50)
	UNITS "Degrees Celsius"
	MAX-ACCESS  read-only
	STATUS current
	DESCRIPTION "Current reading for Source B temp in C"
	::= { dstsEntry  14 }
	
cpmSensorEntry OBJECT-TYPE
	SYNTAX  CpmSensorEntry
	MAX-ACCESS  not-accessible
	STATUS current
	DESCRIPTION 
		"Entry in the city power sensor table: each entry contains
an index (cpmSensorIndex) and other sensor details"
	INDEX { cpmSensorIndex }
	::= { cpmSensorTable 1 }

CpmSensorEntry ::= SEQUENCE {
	cpmSensorIndex		INTEGER(1..100),
	cpmSensorSerial		DisplayString,
	cpmSensorName		DisplayString,
	cpmSensorAvail		Unsigned32,
	cpmSensorStatus		INTEGER(0..100)
}

cpmSensorIndex OBJECT-TYPE
	SYNTAX  INTEGER(1..100)
	MAX-ACCESS  not-accessible
	STATUS current
	DESCRIPTION "Table entry index value"
	::= { cpmSensorEntry  1 }
	
cpmSensorSerial OBJECT-TYPE
	SYNTAX  DisplayString
	MAX-ACCESS  read-only
	STATUS current
	DESCRIPTION "Serial Number"
	::= { cpmSensorEntry  2 }
	
cpmSensorName OBJECT-TYPE
	SYNTAX  DisplayString
	MAX-ACCESS  read-only
	STATUS current
	DESCRIPTION "Friendly Name"
	::= { cpmSensorEntry  3 }
	
cpmSensorAvail OBJECT-TYPE
	SYNTAX  Unsigned32
	MAX-ACCESS  read-only
	STATUS current
	DESCRIPTION "Is device currently plugged in?"
	::= { cpmSensorEntry  4 }
	
cpmSensorStatus OBJECT-TYPE
	SYNTAX  INTEGER(0..100)
	MAX-ACCESS  read-only
	STATUS current
	DESCRIPTION "City Power sensor status"
	::= { cpmSensorEntry  5 }
	
smokeAlarmEntry OBJECT-TYPE
	SYNTAX  SmokeAlarmEntry
	MAX-ACCESS  not-accessible
	STATUS current
	DESCRIPTION 
		"Entry in the smoke alarm sensor table: each entry contains
an index (smokeAlarmIndex) and other sensor details"
	INDEX { smokeAlarmIndex }
	::= { smokeAlarmTable 1 }

SmokeAlarmEntry ::= SEQUENCE {
	smokeAlarmIndex		INTEGER(1..100),
	smokeAlarmSerial		DisplayString,
	smokeAlarmName		DisplayString,
	smokeAlarmAvail		Unsigned32,
	smokeAlarmStatus		INTEGER(0..100)
}

smokeAlarmIndex OBJECT-TYPE
	SYNTAX  INTEGER(1..100)
	MAX-ACCESS  not-accessible
	STATUS current
	DESCRIPTION "Table entry index value"
	::= { smokeAlarmEntry  1 }
	
smokeAlarmSerial OBJECT-TYPE
	SYNTAX  DisplayString
	MAX-ACCESS  read-only
	STATUS current
	DESCRIPTION "Serial Number"
	::= { smokeAlarmEntry  2 }
	
smokeAlarmName OBJECT-TYPE
	SYNTAX  DisplayString
	MAX-ACCESS  read-only
	STATUS current
	DESCRIPTION "Friendly Name"
	::= { smokeAlarmEntry  3 }
	
smokeAlarmAvail OBJECT-TYPE
	SYNTAX  Unsigned32
	MAX-ACCESS  read-only
	STATUS current
	DESCRIPTION "Is device currently plugged in?"
	::= { smokeAlarmEntry  4 }
	
smokeAlarmStatus OBJECT-TYPE
	SYNTAX  INTEGER(0..100)
	MAX-ACCESS  read-only
	STATUS current
	DESCRIPTION "Smoke alarm status"
	::= { smokeAlarmEntry  5 }
	
neg48VdcSensorEntry OBJECT-TYPE
	SYNTAX  Neg48VdcSensorEntry
	MAX-ACCESS  not-accessible
	STATUS current
	DESCRIPTION 
		"Entry in the -48Vdc sensor table: each entry contains
an index (neg48VdcSensorIndex) and other sensor details"
	INDEX { neg48VdcSensorIndex }
	::= { neg48VdcSensorTable 1 }

Neg48VdcSensorEntry ::= SEQUENCE {
	neg48VdcSensorIndex		INTEGER(1..100),
	neg48VdcSensorSerial		DisplayString,
	neg48VdcSensorName		DisplayString,
	neg48VdcSensorAvail		Unsigned32,
	neg48VdcSensorVoltage		INTEGER(-100..10)
}

neg48VdcSensorIndex OBJECT-TYPE
	SYNTAX  INTEGER(1..100)
	MAX-ACCESS  not-accessible
	STATUS current
	DESCRIPTION "Table entry index value"
	::= { neg48VdcSensorEntry  1 }
	
neg48VdcSensorSerial OBJECT-TYPE
	SYNTAX  DisplayString
	MAX-ACCESS  read-only
	STATUS current
	DESCRIPTION "Serial Number"
	::= { neg48VdcSensorEntry  2 }
	
neg48VdcSensorName OBJECT-TYPE
	SYNTAX  DisplayString
	MAX-ACCESS  read-only
	STATUS current
	DESCRIPTION "Friendly Name"
	::= { neg48VdcSensorEntry  3 }
	
neg48VdcSensorAvail OBJECT-TYPE
	SYNTAX  Unsigned32
	MAX-ACCESS  read-only
	STATUS current
	DESCRIPTION "Is device currently plugged in?"
	::= { neg48VdcSensorEntry  4 }
	
neg48VdcSensorVoltage OBJECT-TYPE
	SYNTAX  INTEGER(-100..10)
	UNITS "Volts"
	MAX-ACCESS  read-only
	STATUS current
	DESCRIPTION "-48Vdc Sensor value"
	::= { neg48VdcSensorEntry  5 }
	
pos30VdcSensorEntry OBJECT-TYPE
	SYNTAX  Pos30VdcSensorEntry
	MAX-ACCESS  not-accessible
	STATUS current
	DESCRIPTION 
		"Entry in the 30Vdc sensor table: each entry contains
an index (pos30VdcSensorIndex) and other sensor details"
	INDEX { pos30VdcSensorIndex }
	::= { pos30VdcSensorTable 1 }

Pos30VdcSensorEntry ::= SEQUENCE {
	pos30VdcSensorIndex		INTEGER(1..100),
	pos30VdcSensorSerial		DisplayString,
	pos30VdcSensorName		DisplayString,
	pos30VdcSensorAvail		Unsigned32,
	pos30VdcSensorVoltage		INTEGER(-10..100)
}

pos30VdcSensorIndex OBJECT-TYPE
	SYNTAX  INTEGER(1..100)
	MAX-ACCESS  not-accessible
	STATUS current
	DESCRIPTION "Table entry index value"
	::= { pos30VdcSensorEntry  1 }
	
pos30VdcSensorSerial OBJECT-TYPE
	SYNTAX  DisplayString
	MAX-ACCESS  read-only
	STATUS current
	DESCRIPTION "Serial Number"
	::= { pos30VdcSensorEntry  2 }
	
pos30VdcSensorName OBJECT-TYPE
	SYNTAX  DisplayString
	MAX-ACCESS  read-only
	STATUS current
	DESCRIPTION "Friendly Name"
	::= { pos30VdcSensorEntry  3 }
	
pos30VdcSensorAvail OBJECT-TYPE
	SYNTAX  Unsigned32
	MAX-ACCESS  read-only
	STATUS current
	DESCRIPTION "Is device currently plugged in?"
	::= { pos30VdcSensorEntry  4 }
	
pos30VdcSensorVoltage OBJECT-TYPE
	SYNTAX  INTEGER(-10..100)
	UNITS "Volts"
	MAX-ACCESS  read-only
	STATUS current
	DESCRIPTION "30Vdc Sensor value"
	::= { pos30VdcSensorEntry  5 }
	
analogSensorEntry OBJECT-TYPE
	SYNTAX  AnalogSensorEntry
	MAX-ACCESS  not-accessible
	STATUS current
	DESCRIPTION 
		"Entry in the analog input table: each entry contains
an index (analogSensorIndex) and other sensor details"
	INDEX { analogSensorIndex }
	::= { analogSensorTable 1 }

AnalogSensorEntry ::= SEQUENCE {
	analogSensorIndex		INTEGER(1..100),
	analogSensorSerial		DisplayString,
	analogSensorName		DisplayString,
	analogSensorAvail		Unsigned32,
	analogSensorAnalog		INTEGER(0..100)
}

analogSensorIndex OBJECT-TYPE
	SYNTAX  INTEGER(1..100)
	MAX-ACCESS  not-accessible
	STATUS current
	DESCRIPTION "Table entry index value"
	::= { analogSensorEntry  1 }
	
analogSensorSerial OBJECT-TYPE
	SYNTAX  DisplayString
	MAX-ACCESS  read-only
	STATUS current
	DESCRIPTION "Serial Number"
	::= { analogSensorEntry  2 }
	
analogSensorName OBJECT-TYPE
	SYNTAX  DisplayString
	MAX-ACCESS  read-only
	STATUS current
	DESCRIPTION "Friendly Name"
	::= { analogSensorEntry  3 }
	
analogSensorAvail OBJECT-TYPE
	SYNTAX  Unsigned32
	MAX-ACCESS  read-only
	STATUS current
	DESCRIPTION "Is device currently plugged in?"
	::= { analogSensorEntry  4 }
	
analogSensorAnalog OBJECT-TYPE
	SYNTAX  INTEGER(0..100)
	MAX-ACCESS  read-only
	STATUS current
	DESCRIPTION "Analog Sensor Value"
	::= { analogSensorEntry  5 }
	
ctrl3ChIECEntry OBJECT-TYPE
	SYNTAX  Ctrl3ChIECEntry
	MAX-ACCESS  not-accessible
	STATUS current
	DESCRIPTION 
		"Entry in the 3 phase outlet control table: each entry contains
an index (ctrl3ChIECIndex) and other outlet control monitoring details"
	INDEX { ctrl3ChIECIndex }
	::= { ctrl3ChIECTable 1 }

Ctrl3ChIECEntry ::= SEQUENCE {
	ctrl3ChIECIndex		INTEGER(1..100),
	ctrl3ChIECSerial		DisplayString,
	ctrl3ChIECName		DisplayString,
	ctrl3ChIECAvail		Unsigned32,
	ctrl3ChIECKWattHrsA		Unsigned32,
	ctrl3ChIECVoltsA		Unsigned32,
	ctrl3ChIECVoltPeakA		Unsigned32,
	ctrl3ChIECDeciAmpsA		Unsigned32,
	ctrl3ChIECDeciAmpsPeakA		Unsigned32,
	ctrl3ChIECRealPowerA		Unsigned32,
	ctrl3ChIECApparentPowerA		Unsigned32,
	ctrl3ChIECPowerFactorA		INTEGER(0..100),
	ctrl3ChIECKWattHrsB		Unsigned32,
	ctrl3ChIECVoltsB		Unsigned32,
	ctrl3ChIECVoltPeakB		Unsigned32,
	ctrl3ChIECDeciAmpsB		Unsigned32,
	ctrl3ChIECDeciAmpsPeakB		Unsigned32,
	ctrl3ChIECRealPowerB		Unsigned32,
	ctrl3ChIECApparentPowerB		Unsigned32,
	ctrl3ChIECPowerFactorB		INTEGER(0..100),
	ctrl3ChIECKWattHrsC		Unsigned32,
	ctrl3ChIECVoltsC		Unsigned32,
	ctrl3ChIECVoltPeakC		Unsigned32,
	ctrl3ChIECDeciAmpsC		Unsigned32,
	ctrl3ChIECDeciAmpsPeakC		Unsigned32,
	ctrl3ChIECRealPowerC		Unsigned32,
	ctrl3ChIECApparentPowerC		Unsigned32,
	ctrl3ChIECPowerFactorC		INTEGER(0..100)
}

ctrl3ChIECIndex OBJECT-TYPE
	SYNTAX  INTEGER(1..100)
	MAX-ACCESS  not-accessible
	STATUS current
	DESCRIPTION "Table entry index value"
	::= { ctrl3ChIECEntry  1 }
	
ctrl3ChIECSerial OBJECT-TYPE
	SYNTAX  DisplayString
	MAX-ACCESS  read-only
	STATUS current
	DESCRIPTION "Serial Number"
	::= { ctrl3ChIECEntry  2 }
	
ctrl3ChIECName OBJECT-TYPE
	SYNTAX  DisplayString
	MAX-ACCESS  read-only
	STATUS current
	DESCRIPTION "Friendly Name"
	::= { ctrl3ChIECEntry  3 }
	
ctrl3ChIECAvail OBJECT-TYPE
	SYNTAX  Unsigned32
	MAX-ACCESS  read-only
	STATUS current
	DESCRIPTION "Is device currently plugged in?"
	::= { ctrl3ChIECEntry  4 }
	
ctrl3ChIECKWattHrsA OBJECT-TYPE
	SYNTAX  Unsigned32
	UNITS "KWh"
	MAX-ACCESS  read-only
	STATUS current
	DESCRIPTION "Current Reading for KWatt-Hours (Phase A)"
	::= { ctrl3ChIECEntry  5 }
	
ctrl3ChIECVoltsA OBJECT-TYPE
	SYNTAX  Unsigned32
	UNITS "Volts (rms)"
	MAX-ACCESS  read-only
	STATUS current
	DESCRIPTION "Current reading for Volts (Phase A)"
	::= { ctrl3ChIECEntry  6 }
	
ctrl3ChIECVoltPeakA OBJECT-TYPE
	SYNTAX  Unsigned32
	UNITS "Volts (rms)"
	MAX-ACCESS  read-only
	STATUS current
	DESCRIPTION "Current reading for Peak-Volts (Phase A)"
	::= { ctrl3ChIECEntry  7 }
	
ctrl3ChIECDeciAmpsA OBJECT-TYPE
	SYNTAX  Unsigned32
	UNITS "0.1 Amps (rms)"
	MAX-ACCESS  read-only
	STATUS current
	DESCRIPTION "Current reading for DeciAmps (Phase A)"
	::= { ctrl3ChIECEntry  8 }
	
ctrl3ChIECDeciAmpsPeakA OBJECT-TYPE
	SYNTAX  Unsigned32
	UNITS "0.1 Amps (rms)"
	MAX-ACCESS  read-only
	STATUS current
	DESCRIPTION "Current reading for Peak-DeciAmps (Phase A)"
	::= { ctrl3ChIECEntry  9 }
	
ctrl3ChIECRealPowerA OBJECT-TYPE
	SYNTAX  Unsigned32
	UNITS "Watts"
	MAX-ACCESS  read-only
	STATUS current
	DESCRIPTION "Current reading for Real Power (Phase A)"
	::= { ctrl3ChIECEntry  10 }
	
ctrl3ChIECApparentPowerA OBJECT-TYPE
	SYNTAX  Unsigned32
	UNITS "Volt-Amps"
	MAX-ACCESS  read-only
	STATUS current
	DESCRIPTION "Current reading for Apparent Power (Phase A)"
	::= { ctrl3ChIECEntry  11 }
	
ctrl3ChIECPowerFactorA OBJECT-TYPE
	SYNTAX  INTEGER(0..100)
	UNITS "%"
	MAX-ACCESS  read-only
	STATUS current
	DESCRIPTION "Current reading for Power Factor (Phase A)"
	::= { ctrl3ChIECEntry  12 }
	
ctrl3ChIECKWattHrsB OBJECT-TYPE
	SYNTAX  Unsigned32
	UNITS "KWh"
	MAX-ACCESS  read-only
	STATUS current
	DESCRIPTION "Current Reading for KWatt-Hours (Phase B)"
	::= { ctrl3ChIECEntry  13 }
	
ctrl3ChIECVoltsB OBJECT-TYPE
	SYNTAX  Unsigned32
	UNITS "Volts (rms)"
	MAX-ACCESS  read-only
	STATUS current
	DESCRIPTION "Current reading for Volts (Phase B)"
	::= { ctrl3ChIECEntry  14 }
	
ctrl3ChIECVoltPeakB OBJECT-TYPE
	SYNTAX  Unsigned32
	UNITS "Volts (rms)"
	MAX-ACCESS  read-only
	STATUS current
	DESCRIPTION "Current reading for Peak-Volts (Phase B)"
	::= { ctrl3ChIECEntry  15 }
	
ctrl3ChIECDeciAmpsB OBJECT-TYPE
	SYNTAX  Unsigned32
	UNITS "0.1 Amps (rms)"
	MAX-ACCESS  read-only
	STATUS current
	DESCRIPTION "Current reading for DeciAmps (Phase B)"
	::= { ctrl3ChIECEntry  16 }
	
ctrl3ChIECDeciAmpsPeakB OBJECT-TYPE
	SYNTAX  Unsigned32
	UNITS "0.1 Amps (rms)"
	MAX-ACCESS  read-only
	STATUS current
	DESCRIPTION "Current reading for Peak-DeciAmps (Phase B)"
	::= { ctrl3ChIECEntry  17 }
	
ctrl3ChIECRealPowerB OBJECT-TYPE
	SYNTAX  Unsigned32
	UNITS "Watts"
	MAX-ACCESS  read-only
	STATUS current
	DESCRIPTION "Current reading for Real Power (Phase B)"
	::= { ctrl3ChIECEntry  18 }
	
ctrl3ChIECApparentPowerB OBJECT-TYPE
	SYNTAX  Unsigned32
	UNITS "Volt-Amps"
	MAX-ACCESS  read-only
	STATUS current
	DESCRIPTION "Current reading for Apparent Power (Phase B)"
	::= { ctrl3ChIECEntry  19 }
	
ctrl3ChIECPowerFactorB OBJECT-TYPE
	SYNTAX  INTEGER(0..100)
	UNITS "%"
	MAX-ACCESS  read-only
	STATUS current
	DESCRIPTION "Current reading for Power Factor (Phase B)"
	::= { ctrl3ChIECEntry  20 }
	
ctrl3ChIECKWattHrsC OBJECT-TYPE
	SYNTAX  Unsigned32
	UNITS "KWh"
	MAX-ACCESS  read-only
	STATUS current
	DESCRIPTION "Current Reading for KWatt-Hours (Phase C)"
	::= { ctrl3ChIECEntry  21 }
	
ctrl3ChIECVoltsC OBJECT-TYPE
	SYNTAX  Unsigned32
	UNITS "Volts (rms)"
	MAX-ACCESS  read-only
	STATUS current
	DESCRIPTION "Current reading for Volts (Phase C)"
	::= { ctrl3ChIECEntry  22 }
	
ctrl3ChIECVoltPeakC OBJECT-TYPE
	SYNTAX  Unsigned32
	UNITS "Volts (rms)"
	MAX-ACCESS  read-only
	STATUS current
	DESCRIPTION "Current reading for Peak-Volts (Phase C)"
	::= { ctrl3ChIECEntry  23 }
	
ctrl3ChIECDeciAmpsC OBJECT-TYPE
	SYNTAX  Unsigned32
	UNITS "0.1 Amps (rms)"
	MAX-ACCESS  read-only
	STATUS current
	DESCRIPTION "Current reading for DeciAmps (Phase C)"
	::= { ctrl3ChIECEntry  24 }
	
ctrl3ChIECDeciAmpsPeakC OBJECT-TYPE
	SYNTAX  Unsigned32
	UNITS "0.1 Amps (rms)"
	MAX-ACCESS  read-only
	STATUS current
	DESCRIPTION "Current reading for Peak-DeciAmps (Phase C)"
	::= { ctrl3ChIECEntry  25 }
	
ctrl3ChIECRealPowerC OBJECT-TYPE
	SYNTAX  Unsigned32
	UNITS "Watts"
	MAX-ACCESS  read-only
	STATUS current
	DESCRIPTION "Current reading for Real Power (Phase C)"
	::= { ctrl3ChIECEntry  26 }
	
ctrl3ChIECApparentPowerC OBJECT-TYPE
	SYNTAX  Unsigned32
	UNITS "Volt-Amps"
	MAX-ACCESS  read-only
	STATUS current
	DESCRIPTION "Current reading for Apparent Power (Phase C)"
	::= { ctrl3ChIECEntry  27 }
	
ctrl3ChIECPowerFactorC OBJECT-TYPE
	SYNTAX  INTEGER(0..100)
	UNITS "%"
	MAX-ACCESS  read-only
	STATUS current
	DESCRIPTION "Current reading for Power Factor (Phase C)"
	::= { ctrl3ChIECEntry  28 }
	
airSpeedSwitchSensorEntry OBJECT-TYPE
	SYNTAX  AirSpeedSwitchSensorEntry
	MAX-ACCESS  not-accessible
	STATUS current
	DESCRIPTION 
		"Entry in the air speed switch sensor table: each entry contains
an index (airSpeedSwitchIndex) and other sensor details"
	INDEX { airSpeedSwitchSensorIndex }
	::= { airSpeedSwitchSensorTable 1 }

AirSpeedSwitchSensorEntry ::= SEQUENCE {
	airSpeedSwitchSensorIndex		INTEGER(1..100),
	airSpeedSwitchSensorSerial		DisplayString,
	airSpeedSwitchSensorName		DisplayString,
	airSpeedSwitchSensorAvail		Unsigned32,
	airSpeedSwitchSensorAirSpeed		INTEGER(0..100)
}

airSpeedSwitchSensorIndex OBJECT-TYPE
	SYNTAX  INTEGER(1..100)
	MAX-ACCESS  not-accessible
	STATUS current
	DESCRIPTION "Table entry index value"
	::= { airSpeedSwitchSensorEntry  1 }
	
airSpeedSwitchSensorSerial OBJECT-TYPE
	SYNTAX  DisplayString
	MAX-ACCESS  read-only
	STATUS current
	DESCRIPTION "Serial Number"
	::= { airSpeedSwitchSensorEntry  2 }
	
airSpeedSwitchSensorName OBJECT-TYPE
	SYNTAX  DisplayString
	MAX-ACCESS  read-only
	STATUS current
	DESCRIPTION "Friendly Name"
	::= { airSpeedSwitchSensorEntry  3 }
	
airSpeedSwitchSensorAvail OBJECT-TYPE
	SYNTAX  Unsigned32
	MAX-ACCESS  read-only
	STATUS current
	DESCRIPTION "Is device currently plugged in?"
	::= { airSpeedSwitchSensorEntry  4 }
	
airSpeedSwitchSensorAirSpeed OBJECT-TYPE
	SYNTAX  INTEGER(0..100)
	MAX-ACCESS  read-only
	STATUS current
	DESCRIPTION "Air Speed Switch Status"
	::= { airSpeedSwitchSensorEntry  5 }
	
cmTestTRAP TRAP-TYPE
	ENTERPRISE itwatchdogs
	DESCRIPTION "Test SNMP Trap"
	::= 10101
	
cmClimateTempCTRAP TRAP-TYPE
ENTERPRISE itwatchdogs
VARIABLES { climateTempC, climateName, productFriendlyName, alarmTripType }
DESCRIPTION "Climate Temperature Sensor Trap"
::= 10205

cmClimateHumidityTRAP TRAP-TYPE
ENTERPRISE itwatchdogs
VARIABLES { climateHumidity, climateName, productFriendlyName, alarmTripType }
DESCRIPTION "Climate Humidity Sensor Trap"
::= 10206

cmClimateAirflowTRAP TRAP-TYPE
ENTERPRISE itwatchdogs
VARIABLES { climateAirflow, climateName, productFriendlyName, alarmTripType }
DESCRIPTION "Climate Air Flow Sensor Trap"
::= 10207

cmClimateLightTRAP TRAP-TYPE
ENTERPRISE itwatchdogs
VARIABLES { climateLight, climateName, productFriendlyName, alarmTripType }
DESCRIPTION "Climate Light Sensor Trap"
::= 10208

cmClimateSoundTRAP TRAP-TYPE
ENTERPRISE itwatchdogs
VARIABLES { climateSound, climateName, productFriendlyName, alarmTripType }
DESCRIPTION "Climate Sound Sensor Trap"
::= 10209

cmClimateIO1TRAP TRAP-TYPE
ENTERPRISE itwatchdogs
VARIABLES { climateIO1, climateName, productFriendlyName, alarmTripType }
DESCRIPTION "Climate IO1 Sensor Trap"
::= 10210

cmClimateIO2TRAP TRAP-TYPE
ENTERPRISE itwatchdogs
VARIABLES { climateIO2, climateName, productFriendlyName, alarmTripType }
DESCRIPTION "Climate IO2 Sensor Trap"
::= 10211

cmClimateIO3TRAP TRAP-TYPE
ENTERPRISE itwatchdogs
VARIABLES { climateIO3, climateName, productFriendlyName, alarmTripType }
DESCRIPTION "Climate IO3 Sensor Trap"
::= 10212

cmPowMonKWattHrsTRAP TRAP-TYPE
ENTERPRISE itwatchdogs
VARIABLES { powMonKWattHrs, powMonName, productFriendlyName, alarmTripType }
DESCRIPTION "Kilo Watt Hours Trap"
::= 10305

cmPowMonVoltsTRAP TRAP-TYPE
ENTERPRISE itwatchdogs
VARIABLES { powMonVolts, powMonName, productFriendlyName, alarmTripType }
DESCRIPTION "Volts Trap"
::= 10306

cmPowMonVoltMaxTRAP TRAP-TYPE
ENTERPRISE itwatchdogs
VARIABLES { powMonVoltMax, powMonName, productFriendlyName, alarmTripType }
DESCRIPTION "Volts Max Trap"
::= 10307

cmPowMonVoltMinTRAP TRAP-TYPE
ENTERPRISE itwatchdogs
VARIABLES { powMonVoltMin, powMonName, productFriendlyName, alarmTripType }
DESCRIPTION "Volts Min Trap"
::= 10308

cmPowMonVoltPeakTRAP TRAP-TYPE
ENTERPRISE itwatchdogs
VARIABLES { powMonVoltPeak, powMonName, productFriendlyName, alarmTripType }
DESCRIPTION "Volt Peak Trap"
::= 10309

cmPowMonDeciAmpsTRAP TRAP-TYPE
ENTERPRISE itwatchdogs
VARIABLES { powMonDeciAmps, powMonName, productFriendlyName, alarmTripType }
DESCRIPTION "DeciAmps Trap"
::= 10310

cmPowMonRealPowerTRAP TRAP-TYPE
ENTERPRISE itwatchdogs
VARIABLES { powMonRealPower, powMonName, productFriendlyName, alarmTripType }
DESCRIPTION "Real Power Trap"
::= 10311

cmPowMonApparentPowerTRAP TRAP-TYPE
ENTERPRISE itwatchdogs
VARIABLES { powMonApparentPower, powMonName, productFriendlyName, alarmTripType }
DESCRIPTION "Apparent Power Trap"
::= 10312

cmPowMonPowerFactorTRAP TRAP-TYPE
ENTERPRISE itwatchdogs
VARIABLES { powMonPowerFactor, powMonName, productFriendlyName, alarmTripType }
DESCRIPTION "Power Factor Trap"
::= 10313

cmPowMonDeciAmpsOutlet1TRAP TRAP-TYPE
ENTERPRISE itwatchdogs
VARIABLES { powMonDeciAmpsOutlet1, powMonName, productFriendlyName, alarmTripType }
DESCRIPTION "Outlet 1 Trap"
::= 10314

cmPowMonDeciAmpsOutlet2TRAP TRAP-TYPE
ENTERPRISE itwatchdogs
VARIABLES { powMonDeciAmpsOutlet2, powMonName, productFriendlyName, alarmTripType }
DESCRIPTION "Outlet 2 Trap"
::= 10315

cmTempSensorTempCTRAP TRAP-TYPE
ENTERPRISE itwatchdogs
VARIABLES { tempSensorTempC, tempSensorName, productFriendlyName, alarmTripType }
DESCRIPTION "Remote Temp Sensor - Temperature Trap"
::= 10405

cmAirFlowSensorFlowTRAP TRAP-TYPE
ENTERPRISE itwatchdogs
VARIABLES { airFlowSensorFlow, airFlowSensorName, productFriendlyName, alarmTripType }
DESCRIPTION "Remote Air Flow Sensor - Air Flow Trap"
::= 10505

cmAirFlowSensorTempCTRAP TRAP-TYPE
ENTERPRISE itwatchdogs
VARIABLES { airFlowSensorTempC, airFlowSensorName, productFriendlyName, alarmTripType }
DESCRIPTION "Remote Air Flow Sensor - Temperature Trap"
::= 10506

cmAirFlowSensorHumidityTRAP TRAP-TYPE
ENTERPRISE itwatchdogs
VARIABLES { airFlowSensorHumidity, airFlowSensorName, productFriendlyName, alarmTripType }
DESCRIPTION "Remote Air Flow Sensor - Humidity"
::= 10507

cmAirFlowSensorDewPointTRAP TRAP-TYPE
ENTERPRISE itwatchdogs
VARIABLES { airFlowSensorDewPoint, airFlowSensorName, productFriendlyName, alarmTripType }
DESCRIPTION "Remote Dew Point Sensor - Dew Point Trap"
::= 10508

cmPowerVoltsTRAP TRAP-TYPE
ENTERPRISE itwatchdogs
VARIABLES { powerVolts, powerName, productFriendlyName, alarmTripType }
DESCRIPTION "Power-Only Volts Trap"
::= 10605

cmPowerDeciAmpsTRAP TRAP-TYPE
ENTERPRISE itwatchdogs
VARIABLES { powerDeciAmps, powerName, productFriendlyName, alarmTripType }
DESCRIPTION "Power-Only Amps Trap"
::= 10606

cmPowerRealPowerTRAP TRAP-TYPE
ENTERPRISE itwatchdogs
VARIABLES { powerRealPower, powerName, productFriendlyName, alarmTripType }
DESCRIPTION "Power-Only Watts Trap"
::= 10607

cmPowerApparentPowerTRAP TRAP-TYPE
ENTERPRISE itwatchdogs
VARIABLES { powerApparentPower, powerName, productFriendlyName, alarmTripType }
DESCRIPTION "Power-Only Volt Amps Trap"
::= 10608

cmPowerPowerFactorTRAP TRAP-TYPE
ENTERPRISE itwatchdogs
VARIABLES { powerPowerFactor, powerName, productFriendlyName, alarmTripType }
DESCRIPTION "Power-Only Power Factor Trap"
::= 10609

cmDoorSensorStatusTRAP TRAP-TYPE
ENTERPRISE itwatchdogs
VARIABLES { doorSensorStatus, doorSensorName, productFriendlyName, alarmTripType }
DESCRIPTION "Door sensor Trap"
::= 10705

cmWaterSensorDampnessTRAP TRAP-TYPE
ENTERPRISE itwatchdogs
VARIABLES { waterSensorDampness, waterSensorName, productFriendlyName, alarmTripType }
DESCRIPTION "Water sensor Trap"
::= 10805

cmCurrentMonitorDeciAmpsTRAP TRAP-TYPE
ENTERPRISE itwatchdogs
VARIABLES { currentMonitorDeciAmps, currentMonitorName, productFriendlyName, alarmTripType }
DESCRIPTION "Current Monitor Amps Trap"
::= 10905

cmMillivoltMonitorMVTRAP TRAP-TYPE
ENTERPRISE itwatchdogs
VARIABLES { millivoltMonitorMV, millivoltMonitorName, productFriendlyName, alarmTripType }
DESCRIPTION "Millivolt Monitor Trap"
::= 11005

cmPow3ChKWattHrsATRAP TRAP-TYPE
ENTERPRISE itwatchdogs
VARIABLES { pow3ChKWattHrsA, pow3ChName, productFriendlyName, alarmTripType }
DESCRIPTION "Kilo Watt Hours A Trap"
::= 11105

cmPow3ChVoltsATRAP TRAP-TYPE
ENTERPRISE itwatchdogs
VARIABLES { pow3ChVoltsA, pow3ChName, productFriendlyName, alarmTripType }
DESCRIPTION "Volts A Trap"
::= 11106

cmPow3ChVoltMaxATRAP TRAP-TYPE
ENTERPRISE itwatchdogs
VARIABLES { pow3ChVoltMaxA, pow3ChName, productFriendlyName, alarmTripType }
DESCRIPTION "Volts Max A Trap"
::= 11107

cmPow3ChVoltMinATRAP TRAP-TYPE
ENTERPRISE itwatchdogs
VARIABLES { pow3ChVoltMinA, pow3ChName, productFriendlyName, alarmTripType }
DESCRIPTION "Volts Min A Trap"
::= 11108

cmPow3ChVoltPeakATRAP TRAP-TYPE
ENTERPRISE itwatchdogs
VARIABLES { pow3ChVoltPeakA, pow3ChName, productFriendlyName, alarmTripType }
DESCRIPTION "Volt Peak A Trap"
::= 11109

cmPow3ChDeciAmpsATRAP TRAP-TYPE
ENTERPRISE itwatchdogs
VARIABLES { pow3ChDeciAmpsA, pow3ChName, productFriendlyName, alarmTripType }
DESCRIPTION "Deciamps A Trap"
::= 11110

cmPow3ChRealPowerATRAP TRAP-TYPE
ENTERPRISE itwatchdogs
VARIABLES { pow3ChRealPowerA, pow3ChName, productFriendlyName, alarmTripType }
DESCRIPTION "Real Power A Trap"
::= 11111

cmPow3ChApparentPowerATRAP TRAP-TYPE
ENTERPRISE itwatchdogs
VARIABLES { pow3ChApparentPowerA, pow3ChName, productFriendlyName, alarmTripType }
DESCRIPTION "Apparent Power A Trap"
::= 11112

cmPow3ChPowerFactorATRAP TRAP-TYPE
ENTERPRISE itwatchdogs
VARIABLES { pow3ChPowerFactorA, pow3ChName, productFriendlyName, alarmTripType }
DESCRIPTION "Power Factor A Trap"
::= 11113

cmPow3ChKWattHrsBTRAP TRAP-TYPE
ENTERPRISE itwatchdogs
VARIABLES { pow3ChKWattHrsB, pow3ChName, productFriendlyName, alarmTripType }
DESCRIPTION "Kilo Watt Hours B Trap"
::= 11114

cmPow3ChVoltsBTRAP TRAP-TYPE
ENTERPRISE itwatchdogs
VARIABLES { pow3ChVoltsB, pow3ChName, productFriendlyName, alarmTripType }
DESCRIPTION "Volts B Trap"
::= 11115

cmPow3ChVoltMaxBTRAP TRAP-TYPE
ENTERPRISE itwatchdogs
VARIABLES { pow3ChVoltMaxB, pow3ChName, productFriendlyName, alarmTripType }
DESCRIPTION "Volts Max B Trap"
::= 11116

cmPow3ChVoltMinBTRAP TRAP-TYPE
ENTERPRISE itwatchdogs
VARIABLES { pow3ChVoltMinB, pow3ChName, productFriendlyName, alarmTripType }
DESCRIPTION "Volts Min B Trap"
::= 11117

cmPow3ChVoltPeakBTRAP TRAP-TYPE
ENTERPRISE itwatchdogs
VARIABLES { pow3ChVoltPeakB, pow3ChName, productFriendlyName, alarmTripType }
DESCRIPTION "Volt Peak B Trap"
::= 11118

cmPow3ChDeciAmpsBTRAP TRAP-TYPE
ENTERPRISE itwatchdogs
VARIABLES { pow3ChDeciAmpsB, pow3ChName, productFriendlyName, alarmTripType }
DESCRIPTION "Deciamps B Trap"
::= 11119

cmPow3ChRealPowerBTRAP TRAP-TYPE
ENTERPRISE itwatchdogs
VARIABLES { pow3ChRealPowerB, pow3ChName, productFriendlyName, alarmTripType }
DESCRIPTION "Real Power B Trap"
::= 11120

cmPow3ChApparentPowerBTRAP TRAP-TYPE
ENTERPRISE itwatchdogs
VARIABLES { pow3ChApparentPowerB, pow3ChName, productFriendlyName, alarmTripType }
DESCRIPTION "Apparent Power B Trap"
::= 11121

cmPow3ChPowerFactorBTRAP TRAP-TYPE
ENTERPRISE itwatchdogs
VARIABLES { pow3ChPowerFactorB, pow3ChName, productFriendlyName, alarmTripType }
DESCRIPTION "Power Factor B Trap"
::= 11122

cmPow3ChKWattHrsCTRAP TRAP-TYPE
ENTERPRISE itwatchdogs
VARIABLES { pow3ChKWattHrsC, pow3ChName, productFriendlyName, alarmTripType }
DESCRIPTION "Kilo Watt Hours C Trap"
::= 11123

cmPow3ChVoltsCTRAP TRAP-TYPE
ENTERPRISE itwatchdogs
VARIABLES { pow3ChVoltsC, pow3ChName, productFriendlyName, alarmTripType }
DESCRIPTION "Volts C Trap"
::= 11124

cmPow3ChVoltMaxCTRAP TRAP-TYPE
ENTERPRISE itwatchdogs
VARIABLES { pow3ChVoltMaxC, pow3ChName, productFriendlyName, alarmTripType }
DESCRIPTION "Volts Max C Trap"
::= 11125

cmPow3ChVoltMinCTRAP TRAP-TYPE
ENTERPRISE itwatchdogs
VARIABLES { pow3ChVoltMinC, pow3ChName, productFriendlyName, alarmTripType }
DESCRIPTION "Volts Min C Trap"
::= 11126

cmPow3ChVoltPeakCTRAP TRAP-TYPE
ENTERPRISE itwatchdogs
VARIABLES { pow3ChVoltPeakC, pow3ChName, productFriendlyName, alarmTripType }
DESCRIPTION "Volt Peak C Trap"
::= 11127

cmPow3ChDeciAmpsCTRAP TRAP-TYPE
ENTERPRISE itwatchdogs
VARIABLES { pow3ChDeciAmpsC, pow3ChName, productFriendlyName, alarmTripType }
DESCRIPTION "Deciamps C Trap"
::= 11128

cmPow3ChRealPowerCTRAP TRAP-TYPE
ENTERPRISE itwatchdogs
VARIABLES { pow3ChRealPowerC, pow3ChName, productFriendlyName, alarmTripType }
DESCRIPTION "Real Power C Trap"
::= 11129

cmPow3ChApparentPowerCTRAP TRAP-TYPE
ENTERPRISE itwatchdogs
VARIABLES { pow3ChApparentPowerC, pow3ChName, productFriendlyName, alarmTripType }
DESCRIPTION "Apparent Power C Trap"
::= 11130

cmPow3ChPowerFactorCTRAP TRAP-TYPE
ENTERPRISE itwatchdogs
VARIABLES { pow3ChPowerFactorC, pow3ChName, productFriendlyName, alarmTripType }
DESCRIPTION "Power Factor C Trap"
::= 11131

cmOutlet1StatusTRAP TRAP-TYPE
ENTERPRISE itwatchdogs
VARIABLES { outlet1Status, outletName, productFriendlyName, alarmTripType }
DESCRIPTION "Outlet 1 Status Trap"
::= 11205

cmOutlet2StatusTRAP TRAP-TYPE
ENTERPRISE itwatchdogs
VARIABLES { outlet2Status, outletName, productFriendlyName, alarmTripType }
DESCRIPTION "Outlet 2 Status Trap"
::= 11206

cmVsfcSetPointCTRAP TRAP-TYPE
ENTERPRISE itwatchdogs
VARIABLES { vsfcSetPointC, vsfcName, productFriendlyName, alarmTripType }
DESCRIPTION "Vsfc Temp Set Point Sensor Trap"
::= 11305

cmVsfcIntTempCTRAP TRAP-TYPE
ENTERPRISE itwatchdogs
VARIABLES { vsfcIntTempC, vsfcName, productFriendlyName, alarmTripType }
DESCRIPTION "Vsfc Internal Temp Sensor Trap"
::= 11306

cmVsfcExt1TempCTRAP TRAP-TYPE
ENTERPRISE itwatchdogs
VARIABLES { vsfcExt1TempC, vsfcName, productFriendlyName, alarmTripType }
DESCRIPTION "Vsfc External Temp 1 Sensor Trap"
::= 11307

cmVsfcExt2TempCTRAP TRAP-TYPE
ENTERPRISE itwatchdogs
VARIABLES { vsfcExt2TempC, vsfcName, productFriendlyName, alarmTripType }
DESCRIPTION "Vsfc External Temp 2 Sensor Trap"
::= 11308

cmVsfcExt3TempCTRAP TRAP-TYPE
ENTERPRISE itwatchdogs
VARIABLES { vsfcExt3TempC, vsfcName, productFriendlyName, alarmTripType }
DESCRIPTION "Vsfc External Temp 3 Sensor Trap"
::= 11309

cmVsfcExt4TempCTRAP TRAP-TYPE
ENTERPRISE itwatchdogs
VARIABLES { vsfcExt4TempC, vsfcName, productFriendlyName, alarmTripType }
DESCRIPTION "Vsfc External Temp 4 Sensor Trap"
::= 11310

cmVsfcFanSpeedTRAP TRAP-TYPE
ENTERPRISE itwatchdogs
VARIABLES { vsfcFanSpeed, vsfcName, productFriendlyName, alarmTripType }
DESCRIPTION "Vsfc Fan Speed Sensor Trap"
::= 11311

cmCtrl3ChVoltsATRAP TRAP-TYPE
ENTERPRISE itwatchdogs
VARIABLES { ctrl3ChVoltsA, ctrl3ChName, productFriendlyName, alarmTripType }
DESCRIPTION "Volts A Trap"
::= 11405

cmCtrl3ChVoltPeakATRAP TRAP-TYPE
ENTERPRISE itwatchdogs
VARIABLES { ctrl3ChVoltPeakA, ctrl3ChName, productFriendlyName, alarmTripType }
DESCRIPTION "Volts Peak A Trap"
::= 11406

cmCtrl3ChDeciAmpsATRAP TRAP-TYPE
ENTERPRISE itwatchdogs
VARIABLES { ctrl3ChDeciAmpsA, ctrl3ChName, productFriendlyName, alarmTripType }
DESCRIPTION "Deciamps A Trap"
::= 11407

cmCtrl3ChDeciAmpsPeakATRAP TRAP-TYPE
ENTERPRISE itwatchdogs
VARIABLES { ctrl3ChDeciAmpsPeakA, ctrl3ChName, productFriendlyName, alarmTripType }
DESCRIPTION "Deciamps Peak A Trap"
::= 11408

cmCtrl3ChRealPowerATRAP TRAP-TYPE
ENTERPRISE itwatchdogs
VARIABLES { ctrl3ChRealPowerA, ctrl3ChName, productFriendlyName, alarmTripType }
DESCRIPTION "Real Power A Trap"
::= 11409

cmCtrl3ChApparentPowerATRAP TRAP-TYPE
ENTERPRISE itwatchdogs
VARIABLES { ctrl3ChApparentPowerA, ctrl3ChName, productFriendlyName, alarmTripType }
DESCRIPTION "Apparent Power A Trap"
::= 11410

cmCtrl3ChPowerFactorATRAP TRAP-TYPE
ENTERPRISE itwatchdogs
VARIABLES { ctrl3ChPowerFactorA, ctrl3ChName, productFriendlyName, alarmTripType }
DESCRIPTION "Power Factor A Trap"
::= 11411

cmCtrl3ChVoltsBTRAP TRAP-TYPE
ENTERPRISE itwatchdogs
VARIABLES { ctrl3ChVoltsB, ctrl3ChName, productFriendlyName, alarmTripType }
DESCRIPTION "Volts B Trap"
::= 11412

cmCtrl3ChVoltPeakBTRAP TRAP-TYPE
ENTERPRISE itwatchdogs
VARIABLES { ctrl3ChVoltPeakB, ctrl3ChName, productFriendlyName, alarmTripType }
DESCRIPTION "Volts Peak B Trap"
::= 11413

cmCtrl3ChDeciAmpsBTRAP TRAP-TYPE
ENTERPRISE itwatchdogs
VARIABLES { ctrl3ChDeciAmpsB, ctrl3ChName, productFriendlyName, alarmTripType }
DESCRIPTION "Deciamps B Trap"
::= 11414

cmCtrl3ChDeciAmpsPeakBTRAP TRAP-TYPE
ENTERPRISE itwatchdogs
VARIABLES { ctrl3ChDeciAmpsPeakB, ctrl3ChName, productFriendlyName, alarmTripType }
DESCRIPTION "Deciamps Peak B Trap"
::= 11415

cmCtrl3ChRealPowerBTRAP TRAP-TYPE
ENTERPRISE itwatchdogs
VARIABLES { ctrl3ChRealPowerB, ctrl3ChName, productFriendlyName, alarmTripType }
DESCRIPTION "Real Power B Trap"
::= 11416

cmCtrl3ChApparentPowerBTRAP TRAP-TYPE
ENTERPRISE itwatchdogs
VARIABLES { ctrl3ChApparentPowerB, ctrl3ChName, productFriendlyName, alarmTripType }
DESCRIPTION "Apparent Power B Trap"
::= 11417

cmCtrl3ChPowerFactorBTRAP TRAP-TYPE
ENTERPRISE itwatchdogs
VARIABLES { ctrl3ChPowerFactorB, ctrl3ChName, productFriendlyName, alarmTripType }
DESCRIPTION "Power Factor B Trap"
::= 11418

cmCtrl3ChVoltsCTRAP TRAP-TYPE
ENTERPRISE itwatchdogs
VARIABLES { ctrl3ChVoltsC, ctrl3ChName, productFriendlyName, alarmTripType }
DESCRIPTION "Volts C Trap"
::= 11419

cmCtrl3ChVoltPeakCTRAP TRAP-TYPE
ENTERPRISE itwatchdogs
VARIABLES { ctrl3ChVoltPeakC, ctrl3ChName, productFriendlyName, alarmTripType }
DESCRIPTION "Volts Peak C Trap"
::= 11420

cmCtrl3ChDeciAmpsCTRAP TRAP-TYPE
ENTERPRISE itwatchdogs
VARIABLES { ctrl3ChDeciAmpsC, ctrl3ChName, productFriendlyName, alarmTripType }
DESCRIPTION "Deciamps C Trap"
::= 11421

cmCtrl3ChDeciAmpsPeakCTRAP TRAP-TYPE
ENTERPRISE itwatchdogs
VARIABLES { ctrl3ChDeciAmpsPeakC, ctrl3ChName, productFriendlyName, alarmTripType }
DESCRIPTION "Deciamps Peak C Trap"
::= 11422

cmCtrl3ChRealPowerCTRAP TRAP-TYPE
ENTERPRISE itwatchdogs
VARIABLES { ctrl3ChRealPowerC, ctrl3ChName, productFriendlyName, alarmTripType }
DESCRIPTION "Real Power C Trap"
::= 11423

cmCtrl3ChApparentPowerCTRAP TRAP-TYPE
ENTERPRISE itwatchdogs
VARIABLES { ctrl3ChApparentPowerC, ctrl3ChName, productFriendlyName, alarmTripType }
DESCRIPTION "Apparent Power C Trap"
::= 11424

cmCtrl3ChPowerFactorCTRAP TRAP-TYPE
ENTERPRISE itwatchdogs
VARIABLES { ctrl3ChPowerFactorC, ctrl3ChName, productFriendlyName, alarmTripType }
DESCRIPTION "Power Factor C Trap"
::= 11425

cmCtrlGrpAmpsATRAP TRAP-TYPE
ENTERPRISE itwatchdogs
VARIABLES { ctrlGrpAmpsA, ctrlGrpAmpsName, productFriendlyName, alarmTripType }
DESCRIPTION "Group A DeciAmps Trap"
::= 11505

cmCtrlGrpAmpsBTRAP TRAP-TYPE
ENTERPRISE itwatchdogs
VARIABLES { ctrlGrpAmpsB, ctrlGrpAmpsName, productFriendlyName, alarmTripType }
DESCRIPTION "Group B DeciAmps Trap"
::= 11506

cmCtrlGrpAmpsCTRAP TRAP-TYPE
ENTERPRISE itwatchdogs
VARIABLES { ctrlGrpAmpsC, ctrlGrpAmpsName, productFriendlyName, alarmTripType }
DESCRIPTION "Group C DeciAmps Trap"
::= 11507

cmCtrlGrpAmpsDTRAP TRAP-TYPE
ENTERPRISE itwatchdogs
VARIABLES { ctrlGrpAmpsD, ctrlGrpAmpsName, productFriendlyName, alarmTripType }
DESCRIPTION "Group D DeciAmps Trap"
::= 11508

cmCtrlGrpAmpsETRAP TRAP-TYPE
ENTERPRISE itwatchdogs
VARIABLES { ctrlGrpAmpsE, ctrlGrpAmpsName, productFriendlyName, alarmTripType }
DESCRIPTION "Group E DeciAmps Trap"
::= 11509

cmCtrlGrpAmpsFTRAP TRAP-TYPE
ENTERPRISE itwatchdogs
VARIABLES { ctrlGrpAmpsF, ctrlGrpAmpsName, productFriendlyName, alarmTripType }
DESCRIPTION "Group F DeciAmps Trap"
::= 11510

cmDewPointSensorDewPointTRAP TRAP-TYPE
ENTERPRISE itwatchdogs
VARIABLES { dewPointSensorDewPoint, dewPointSensorName, productFriendlyName, alarmTripType }
DESCRIPTION "Remote Dew Point Sensor - Dew Point Trap"
::= 11705

cmDewPointSensorTempCTRAP TRAP-TYPE
ENTERPRISE itwatchdogs
VARIABLES { dewPointSensorTempC, dewPointSensorName, productFriendlyName, alarmTripType }
DESCRIPTION "Remote Dew Point Sensor - Temperature Trap"
::= 11706

cmDewPointSensorHumidityTRAP TRAP-TYPE
ENTERPRISE itwatchdogs
VARIABLES { dewPointSensorHumidity, dewPointSensorName, productFriendlyName, alarmTripType }
DESCRIPTION "Remote Dew Point Sensor - Humidity"
::= 11707

cmDigitalSensorDigitalTRAP TRAP-TYPE
ENTERPRISE itwatchdogs
VARIABLES { digitalSensorDigital, digitalSensorName, productFriendlyName, alarmTripType }
DESCRIPTION "Digital sensor Trap"
::= 11805

cmDstsVoltsATRAP TRAP-TYPE
ENTERPRISE itwatchdogs
VARIABLES { dstsVoltsA, dstsName, productFriendlyName, alarmTripType }
DESCRIPTION "RMS Voltage of Side A Set Point Sensor Trap"
::= 11905

cmDstsAmpsATRAP TRAP-TYPE
ENTERPRISE itwatchdogs
VARIABLES { dstsAmpsA, dstsName, productFriendlyName, alarmTripType }
DESCRIPTION "RMS Current of Side A Set Point Sensor Trap"
::= 11906

cmDstsVoltsBTRAP TRAP-TYPE
ENTERPRISE itwatchdogs
VARIABLES { dstsVoltsB, dstsName, productFriendlyName, alarmTripType }
DESCRIPTION "RMS Voltage of Side B Set Point Sensor Trap"
::= 11907

cmDstsAmpsBTRAP TRAP-TYPE
ENTERPRISE itwatchdogs
VARIABLES { dstsAmpsB, dstsName, productFriendlyName, alarmTripType }
DESCRIPTION "RMS Current of Side B Set Point Sensor Trap"
::= 11908

cmDstsSourceAActiveTRAP TRAP-TYPE
ENTERPRISE itwatchdogs
VARIABLES { dstsSourceAActive, dstsName, productFriendlyName, alarmTripType }
DESCRIPTION "Source A Active Set Point Sensor Trap"
::= 11909

cmDstsSourceBActiveTRAP TRAP-TYPE
ENTERPRISE itwatchdogs
VARIABLES { dstsSourceBActive, dstsName, productFriendlyName, alarmTripType }
DESCRIPTION "Source B Active Set Point Sensor Trap"
::= 11910

cmDstsPowerStatusATRAP TRAP-TYPE
ENTERPRISE itwatchdogs
VARIABLES { dstsPowerStatusA, dstsName, productFriendlyName, alarmTripType }
DESCRIPTION "Source A Power Qualilty Active Set Point Sensor Trap"
::= 11911

cmDstsPowerStatusBTRAP TRAP-TYPE
ENTERPRISE itwatchdogs
VARIABLES { dstsPowerStatusB, dstsName, productFriendlyName, alarmTripType }
DESCRIPTION "Source B Power Qualilty Active Set Point Sensor Trap"
::= 11912

cmDstsSourceATempCTRAP TRAP-TYPE
ENTERPRISE itwatchdogs
VARIABLES { dstsSourceATempC, dstsName, productFriendlyName, alarmTripType }
DESCRIPTION "Source A Temp Sensor Trap"
::= 11913

cmDstsSourceBTempCTRAP TRAP-TYPE
ENTERPRISE itwatchdogs
VARIABLES { dstsSourceBTempC, dstsName, productFriendlyName, alarmTripType }
DESCRIPTION "Source B Temp Sensor Trap"
::= 11914

cmCpmSensorStatusTRAP TRAP-TYPE
ENTERPRISE itwatchdogs
VARIABLES { cpmSensorStatus, cpmSensorName, productFriendlyName, alarmTripType }
DESCRIPTION "City Power sensor Trap"
::= 12005

cmSmokeAlarmStatusTRAP TRAP-TYPE
ENTERPRISE itwatchdogs
VARIABLES { smokeAlarmStatus, smokeAlarmName, productFriendlyName, alarmTripType }
DESCRIPTION "Smoke alarm Trap"
::= 12105

cmNeg48VdcSensorVoltageTRAP TRAP-TYPE
ENTERPRISE itwatchdogs
VARIABLES { neg48VdcSensorVoltage, neg48VdcSensorName, productFriendlyName, alarmTripType }
DESCRIPTION "-48Vdc Sensor Trap"
::= 12205

cmPos30VdcSensorVoltageTRAP TRAP-TYPE
ENTERPRISE itwatchdogs
VARIABLES { pos30VdcSensorVoltage, pos30VdcSensorName, productFriendlyName, alarmTripType }
DESCRIPTION "30Vdc Sensor Trap"
::= 12305

cmAnalogSensorAnalogTRAP TRAP-TYPE
ENTERPRISE itwatchdogs
VARIABLES { analogSensorAnalog, analogSensorName, productFriendlyName, alarmTripType }
DESCRIPTION "Analog Sensor Trap"
::= 12405

cmCtrl3ChIECKWattHrsATRAP TRAP-TYPE
ENTERPRISE itwatchdogs
VARIABLES { ctrl3ChIECKWattHrsA, ctrl3ChIECName, productFriendlyName, alarmTripType }
DESCRIPTION "Kilo Watt Hours A Trap"
::= 12505

cmCtrl3ChIECVoltsATRAP TRAP-TYPE
ENTERPRISE itwatchdogs
VARIABLES { ctrl3ChIECVoltsA, ctrl3ChIECName, productFriendlyName, alarmTripType }
DESCRIPTION "Volts A Trap"
::= 12506

cmCtrl3ChIECVoltPeakATRAP TRAP-TYPE
ENTERPRISE itwatchdogs
VARIABLES { ctrl3ChIECVoltPeakA, ctrl3ChIECName, productFriendlyName, alarmTripType }
DESCRIPTION "Volts Peak A Trap"
::= 12507

cmCtrl3ChIECDeciAmpsATRAP TRAP-TYPE
ENTERPRISE itwatchdogs
VARIABLES { ctrl3ChIECDeciAmpsA, ctrl3ChIECName, productFriendlyName, alarmTripType }
DESCRIPTION "Deciamps A Trap"
::= 12508

cmCtrl3ChIECDeciAmpsPeakATRAP TRAP-TYPE
ENTERPRISE itwatchdogs
VARIABLES { ctrl3ChIECDeciAmpsPeakA, ctrl3ChIECName, productFriendlyName, alarmTripType }
DESCRIPTION "Deciamps Peak A Trap"
::= 12509

cmCtrl3ChIECRealPowerATRAP TRAP-TYPE
ENTERPRISE itwatchdogs
VARIABLES { ctrl3ChIECRealPowerA, ctrl3ChIECName, productFriendlyName, alarmTripType }
DESCRIPTION "Real Power A Trap"
::= 12510

cmCtrl3ChIECApparentPowerATRAP TRAP-TYPE
ENTERPRISE itwatchdogs
VARIABLES { ctrl3ChIECApparentPowerA, ctrl3ChIECName, productFriendlyName, alarmTripType }
DESCRIPTION "Apparent Power A Trap"
::= 12511

cmCtrl3ChIECPowerFactorATRAP TRAP-TYPE
ENTERPRISE itwatchdogs
VARIABLES { ctrl3ChIECPowerFactorA, ctrl3ChIECName, productFriendlyName, alarmTripType }
DESCRIPTION "Power Factor A Trap"
::= 12512

cmCtrl3ChIECKWattHrsBTRAP TRAP-TYPE
ENTERPRISE itwatchdogs
VARIABLES { ctrl3ChIECKWattHrsB, ctrl3ChIECName, productFriendlyName, alarmTripType }
DESCRIPTION "Kilo Watt Hours B Trap"
::= 12513

cmCtrl3ChIECVoltsBTRAP TRAP-TYPE
ENTERPRISE itwatchdogs
VARIABLES { ctrl3ChIECVoltsB, ctrl3ChIECName, productFriendlyName, alarmTripType }
DESCRIPTION "Volts B Trap"
::= 12514

cmCtrl3ChIECVoltPeakBTRAP TRAP-TYPE
ENTERPRISE itwatchdogs
VARIABLES { ctrl3ChIECVoltPeakB, ctrl3ChIECName, productFriendlyName, alarmTripType }
DESCRIPTION "Volts Peak B Trap"
::= 12515

cmCtrl3ChIECDeciAmpsBTRAP TRAP-TYPE
ENTERPRISE itwatchdogs
VARIABLES { ctrl3ChIECDeciAmpsB, ctrl3ChIECName, productFriendlyName, alarmTripType }
DESCRIPTION "Deciamps B Trap"
::= 12516

cmCtrl3ChIECDeciAmpsPeakBTRAP TRAP-TYPE
ENTERPRISE itwatchdogs
VARIABLES { ctrl3ChIECDeciAmpsPeakB, ctrl3ChIECName, productFriendlyName, alarmTripType }
DESCRIPTION "Deciamps Peak B Trap"
::= 12517

cmCtrl3ChIECRealPowerBTRAP TRAP-TYPE
ENTERPRISE itwatchdogs
VARIABLES { ctrl3ChIECRealPowerB, ctrl3ChIECName, productFriendlyName, alarmTripType }
DESCRIPTION "Real Power B Trap"
::= 12518

cmCtrl3ChIECApparentPowerBTRAP TRAP-TYPE
ENTERPRISE itwatchdogs
VARIABLES { ctrl3ChIECApparentPowerB, ctrl3ChIECName, productFriendlyName, alarmTripType }
DESCRIPTION "Apparent Power B Trap"
::= 12519

cmCtrl3ChIECPowerFactorBTRAP TRAP-TYPE
ENTERPRISE itwatchdogs
VARIABLES { ctrl3ChIECPowerFactorB, ctrl3ChIECName, productFriendlyName, alarmTripType }
DESCRIPTION "Power Factor B Trap"
::= 12520

cmCtrl3ChIECKWattHrsCTRAP TRAP-TYPE
ENTERPRISE itwatchdogs
VARIABLES { ctrl3ChIECKWattHrsC, ctrl3ChIECName, productFriendlyName, alarmTripType }
DESCRIPTION "Kilo Watt Hours C Trap"
::= 12521

cmCtrl3ChIECVoltsCTRAP TRAP-TYPE
ENTERPRISE itwatchdogs
VARIABLES { ctrl3ChIECVoltsC, ctrl3ChIECName, productFriendlyName, alarmTripType }
DESCRIPTION "Volts C Trap"
::= 12522

cmCtrl3ChIECVoltPeakCTRAP TRAP-TYPE
ENTERPRISE itwatchdogs
VARIABLES { ctrl3ChIECVoltPeakC, ctrl3ChIECName, productFriendlyName, alarmTripType }
DESCRIPTION "Volts Peak C Trap"
::= 12523

cmCtrl3ChIECDeciAmpsCTRAP TRAP-TYPE
ENTERPRISE itwatchdogs
VARIABLES { ctrl3ChIECDeciAmpsC, ctrl3ChIECName, productFriendlyName, alarmTripType }
DESCRIPTION "Deciamps C Trap"
::= 12524

cmCtrl3ChIECDeciAmpsPeakCTRAP TRAP-TYPE
ENTERPRISE itwatchdogs
VARIABLES { ctrl3ChIECDeciAmpsPeakC, ctrl3ChIECName, productFriendlyName, alarmTripType }
DESCRIPTION "Deciamps Peak C Trap"
::= 12525

cmCtrl3ChIECRealPowerCTRAP TRAP-TYPE
ENTERPRISE itwatchdogs
VARIABLES { ctrl3ChIECRealPowerC, ctrl3ChIECName, productFriendlyName, alarmTripType }
DESCRIPTION "Real Power C Trap"
::= 12526

cmCtrl3ChIECApparentPowerCTRAP TRAP-TYPE
ENTERPRISE itwatchdogs
VARIABLES { ctrl3ChIECApparentPowerC, ctrl3ChIECName, productFriendlyName, alarmTripType }
DESCRIPTION "Apparent Power C Trap"
::= 12527

cmCtrl3ChIECPowerFactorCTRAP TRAP-TYPE
ENTERPRISE itwatchdogs
VARIABLES { ctrl3ChIECPowerFactorC, ctrl3ChIECName, productFriendlyName, alarmTripType }
DESCRIPTION "Power Factor C Trap"
::= 12528

cmAirSpeedSwitchSensorAirSpeedTRAP TRAP-TYPE
ENTERPRISE itwatchdogs
VARIABLES { airSpeedSwitchSensorAirSpeed, airSpeedSwitchSensorName, productFriendlyName, alarmTripType }
DESCRIPTION "Air Speed Switch Trap"
::= 12605

cmClimateTempCCLEAR TRAP-TYPE
ENTERPRISE itwatchdogs
VARIABLES { climateTempC, climateName, productFriendlyName, alarmTripType }
DESCRIPTION "Climate Temperature Sensor Clear Trap"
::= 20205

cmClimateHumidityCLEAR TRAP-TYPE
ENTERPRISE itwatchdogs
VARIABLES { climateHumidity, climateName, productFriendlyName, alarmTripType }
DESCRIPTION "Climate Humidity Sensor Clear Trap"
::= 20206

cmClimateAirflowCLEAR TRAP-TYPE
ENTERPRISE itwatchdogs
VARIABLES { climateAirflow, climateName, productFriendlyName, alarmTripType }
DESCRIPTION "Climate Air Flow Sensor Clear Trap"
::= 20207

cmClimateLightCLEAR TRAP-TYPE
ENTERPRISE itwatchdogs
VARIABLES { climateLight, climateName, productFriendlyName, alarmTripType }
DESCRIPTION "Climate Light Sensor Clear Trap"
::= 20208

cmClimateSoundCLEAR TRAP-TYPE
ENTERPRISE itwatchdogs
VARIABLES { climateSound, climateName, productFriendlyName, alarmTripType }
DESCRIPTION "Climate Sound Sensor Clear Trap"
::= 20209

cmClimateIO1CLEAR TRAP-TYPE
ENTERPRISE itwatchdogs
VARIABLES { climateIO1, climateName, productFriendlyName, alarmTripType }
DESCRIPTION "Climate IO1 Sensor Clear Trap"
::= 20210

cmClimateIO2CLEAR TRAP-TYPE
ENTERPRISE itwatchdogs
VARIABLES { climateIO2, climateName, productFriendlyName, alarmTripType }
DESCRIPTION "Climate IO2 Sensor Clear Trap"
::= 20211

cmClimateIO3CLEAR TRAP-TYPE
ENTERPRISE itwatchdogs
VARIABLES { climateIO3, climateName, productFriendlyName, alarmTripType }
DESCRIPTION "Climate IO3 Sensor Clear Trap"
::= 20212

cmPowMonKWattHrsCLEAR TRAP-TYPE
ENTERPRISE itwatchdogs
VARIABLES { powMonKWattHrs, powMonName, productFriendlyName, alarmTripType }
DESCRIPTION "Kilo Watt Hours Clear Trap"
::= 20305

cmPowMonVoltsCLEAR TRAP-TYPE
ENTERPRISE itwatchdogs
VARIABLES { powMonVolts, powMonName, productFriendlyName, alarmTripType }
DESCRIPTION "Volts Clear Trap"
::= 20306

cmPowMonVoltMaxCLEAR TRAP-TYPE
ENTERPRISE itwatchdogs
VARIABLES { powMonVoltMax, powMonName, productFriendlyName, alarmTripType }
DESCRIPTION "Volts Max Clear Trap"
::= 20307

cmPowMonVoltMinCLEAR TRAP-TYPE
ENTERPRISE itwatchdogs
VARIABLES { powMonVoltMin, powMonName, productFriendlyName, alarmTripType }
DESCRIPTION "Volts Min Clear Trap"
::= 20308

cmPowMonVoltPeakCLEAR TRAP-TYPE
ENTERPRISE itwatchdogs
VARIABLES { powMonVoltPeak, powMonName, productFriendlyName, alarmTripType }
DESCRIPTION "Volt Peak Clear Trap"
::= 20309

cmPowMonDeciAmpsCLEAR TRAP-TYPE
ENTERPRISE itwatchdogs
VARIABLES { powMonDeciAmps, powMonName, productFriendlyName, alarmTripType }
DESCRIPTION "DeciAmps Clear Trap"
::= 20310

cmPowMonRealPowerCLEAR TRAP-TYPE
ENTERPRISE itwatchdogs
VARIABLES { powMonRealPower, powMonName, productFriendlyName, alarmTripType }
DESCRIPTION "Real Power Clear Trap"
::= 20311

cmPowMonApparentPowerCLEAR TRAP-TYPE
ENTERPRISE itwatchdogs
VARIABLES { powMonApparentPower, powMonName, productFriendlyName, alarmTripType }
DESCRIPTION "Apparent Power Clear Trap"
::= 20312

cmPowMonPowerFactorCLEAR TRAP-TYPE
ENTERPRISE itwatchdogs
VARIABLES { powMonPowerFactor, powMonName, productFriendlyName, alarmTripType }
DESCRIPTION "Power Factor Clear Trap"
::= 20313

cmPowMonDeciAmpsOutlet1CLEAR TRAP-TYPE
ENTERPRISE itwatchdogs
VARIABLES { powMonDeciAmpsOutlet1, powMonName, productFriendlyName, alarmTripType }
DESCRIPTION "Outlet 1 Clear Trap"
::= 20314

cmPowMonDeciAmpsOutlet2CLEAR TRAP-TYPE
ENTERPRISE itwatchdogs
VARIABLES { powMonDeciAmpsOutlet2, powMonName, productFriendlyName, alarmTripType }
DESCRIPTION "Outlet 2 Clear Trap"
::= 20315

cmTempSensorTempCCLEAR TRAP-TYPE
ENTERPRISE itwatchdogs
VARIABLES { tempSensorTempC, tempSensorName, productFriendlyName, alarmTripType }
DESCRIPTION "Remote Temp Sensor - Temperature Clear Trap"
::= 20405

cmAirFlowSensorFlowCLEAR TRAP-TYPE
ENTERPRISE itwatchdogs
VARIABLES { airFlowSensorFlow, airFlowSensorName, productFriendlyName, alarmTripType }
DESCRIPTION "Remote Air Flow Sensor - Air Flow Clear Trap"
::= 20505

cmAirFlowSensorTempCCLEAR TRAP-TYPE
ENTERPRISE itwatchdogs
VARIABLES { airFlowSensorTempC, airFlowSensorName, productFriendlyName, alarmTripType }
DESCRIPTION "Remote Air Flow Sensor - Temperature Clear Trap"
::= 20506

cmAirFlowSensorHumidityCLEAR TRAP-TYPE
ENTERPRISE itwatchdogs
VARIABLES { airFlowSensorHumidity, airFlowSensorName, productFriendlyName, alarmTripType }
DESCRIPTION "Remote Air Flow Sensor - Humidity Clear Trap"
::= 20507

cmAirFlowSensorDewPointCLEAR TRAP-TYPE
ENTERPRISE itwatchdogs
VARIABLES { airFlowSensorDewPoint, airFlowSensorName, productFriendlyName, alarmTripType }
DESCRIPTION "Remote Dew Point Sensor - Dew Point Clear Trap"
::= 20508

cmPowerVoltsCLEAR TRAP-TYPE
ENTERPRISE itwatchdogs
VARIABLES { powerVolts, powerName, productFriendlyName, alarmTripType }
DESCRIPTION "Power-Only Volts Clear Trap"
::= 20605

cmPowerDeciAmpsCLEAR TRAP-TYPE
ENTERPRISE itwatchdogs
VARIABLES { powerDeciAmps, powerName, productFriendlyName, alarmTripType }
DESCRIPTION "Power-Only Amps Clear Trap"
::= 20606

cmPowerRealPowerCLEAR TRAP-TYPE
ENTERPRISE itwatchdogs
VARIABLES { powerRealPower, powerName, productFriendlyName, alarmTripType }
DESCRIPTION "Power-Only Watts Clear Trap"
::= 20607

cmPowerApparentPowerCLEAR TRAP-TYPE
ENTERPRISE itwatchdogs
VARIABLES { powerApparentPower, powerName, productFriendlyName, alarmTripType }
DESCRIPTION "Power-Only Volt Amps Clear Trap"
::= 20608

cmPowerPowerFactorCLEAR TRAP-TYPE
ENTERPRISE itwatchdogs
VARIABLES { powerPowerFactor, powerName, productFriendlyName, alarmTripType }
DESCRIPTION "Power-Only Power Factor Clear Trap"
::= 20609

cmDoorSensorStatusCLEAR TRAP-TYPE
ENTERPRISE itwatchdogs
VARIABLES { doorSensorStatus, doorSensorName, productFriendlyName, alarmTripType }
DESCRIPTION "Door sensor Clear Trap"
::= 20705

cmWaterSensorDampnessCLEAR TRAP-TYPE
ENTERPRISE itwatchdogs
VARIABLES { waterSensorDampness, waterSensorName, productFriendlyName, alarmTripType }
DESCRIPTION "Water sensor Clear Trap"
::= 20805

cmCurrentMonitorDeciAmpsCLEAR TRAP-TYPE
ENTERPRISE itwatchdogs
VARIABLES { currentMonitorDeciAmps, currentMonitorName, productFriendlyName, alarmTripType }
DESCRIPTION "Current Monitor Amps Clear Trap"
::= 20905

cmMillivoltMonitorMVCLEAR TRAP-TYPE
ENTERPRISE itwatchdogs
VARIABLES { millivoltMonitorMV, millivoltMonitorName, productFriendlyName, alarmTripType }
DESCRIPTION "Millivolt Monitor Clear Trap"
::= 21005

cmPow3ChKWattHrsACLEAR TRAP-TYPE
ENTERPRISE itwatchdogs
VARIABLES { pow3ChKWattHrsA, pow3ChName, productFriendlyName, alarmTripType }
DESCRIPTION "Kilo Watt Hours A Clear Trap"
::= 21105

cmPow3ChVoltsACLEAR TRAP-TYPE
ENTERPRISE itwatchdogs
VARIABLES { pow3ChVoltsA, pow3ChName, productFriendlyName, alarmTripType }
DESCRIPTION "Volts A Clear Trap"
::= 21106

cmPow3ChVoltMaxACLEAR TRAP-TYPE
ENTERPRISE itwatchdogs
VARIABLES { pow3ChVoltMaxA, pow3ChName, productFriendlyName, alarmTripType }
DESCRIPTION "Volts Max A Clear Trap"
::= 21107

cmPow3ChVoltMinACLEAR TRAP-TYPE
ENTERPRISE itwatchdogs
VARIABLES { pow3ChVoltMinA, pow3ChName, productFriendlyName, alarmTripType }
DESCRIPTION "Volts Min A Clear Trap"
::= 21108

cmPow3ChVoltPeakACLEAR TRAP-TYPE
ENTERPRISE itwatchdogs
VARIABLES { pow3ChVoltPeakA, pow3ChName, productFriendlyName, alarmTripType }
DESCRIPTION "Volt Peak A Clear Trap"
::= 21109

cmPow3ChDeciAmpsACLEAR TRAP-TYPE
ENTERPRISE itwatchdogs
VARIABLES { pow3ChDeciAmpsA, pow3ChName, productFriendlyName, alarmTripType }
DESCRIPTION "Deciamps A Clear Trap"
::= 21110

cmPow3ChRealPowerACLEAR TRAP-TYPE
ENTERPRISE itwatchdogs
VARIABLES { pow3ChRealPowerA, pow3ChName, productFriendlyName, alarmTripType }
DESCRIPTION "Real Power A Clear Trap"
::= 21111

cmPow3ChApparentPowerACLEAR TRAP-TYPE
ENTERPRISE itwatchdogs
VARIABLES { pow3ChApparentPowerA, pow3ChName, productFriendlyName, alarmTripType }
DESCRIPTION "Apparent Power A Clear Trap"
::= 21112

cmPow3ChPowerFactorACLEAR TRAP-TYPE
ENTERPRISE itwatchdogs
VARIABLES { pow3ChPowerFactorA, pow3ChName, productFriendlyName, alarmTripType }
DESCRIPTION "Power Factor A Clear Trap"
::= 21113

cmPow3ChKWattHrsBCLEAR TRAP-TYPE
ENTERPRISE itwatchdogs
VARIABLES { pow3ChKWattHrsB, pow3ChName, productFriendlyName, alarmTripType }
DESCRIPTION "Kilo Watt Hours B Clear Trap"
::= 21114

cmPow3ChVoltsBCLEAR TRAP-TYPE
ENTERPRISE itwatchdogs
VARIABLES { pow3ChVoltsB, pow3ChName, productFriendlyName, alarmTripType }
DESCRIPTION "Volts B Clear Trap"
::= 21115

cmPow3ChVoltMaxBCLEAR TRAP-TYPE
ENTERPRISE itwatchdogs
VARIABLES { pow3ChVoltMaxB, pow3ChName, productFriendlyName, alarmTripType }
DESCRIPTION "Volts Max B Clear Trap"
::= 21116

cmPow3ChVoltMinBCLEAR TRAP-TYPE
ENTERPRISE itwatchdogs
VARIABLES { pow3ChVoltMinB, pow3ChName, productFriendlyName, alarmTripType }
DESCRIPTION "Volts Min B Clear Trap"
::= 21117

cmPow3ChVoltPeakBCLEAR TRAP-TYPE
ENTERPRISE itwatchdogs
VARIABLES { pow3ChVoltPeakB, pow3ChName, productFriendlyName, alarmTripType }
DESCRIPTION "Volt Peak B Clear Trap"
::= 21118

cmPow3ChDeciAmpsBCLEAR TRAP-TYPE
ENTERPRISE itwatchdogs
VARIABLES { pow3ChDeciAmpsB, pow3ChName, productFriendlyName, alarmTripType }
DESCRIPTION "Deciamps B Clear Trap"
::= 21119

cmPow3ChRealPowerBCLEAR TRAP-TYPE
ENTERPRISE itwatchdogs
VARIABLES { pow3ChRealPowerB, pow3ChName, productFriendlyName, alarmTripType }
DESCRIPTION "Real Power B Clear Trap"
::= 21120

cmPow3ChApparentPowerBCLEAR TRAP-TYPE
ENTERPRISE itwatchdogs
VARIABLES { pow3ChApparentPowerB, pow3ChName, productFriendlyName, alarmTripType }
DESCRIPTION "Apparent Power B Clear Trap"
::= 21121

cmPow3ChPowerFactorBCLEAR TRAP-TYPE
ENTERPRISE itwatchdogs
VARIABLES { pow3ChPowerFactorB, pow3ChName, productFriendlyName, alarmTripType }
DESCRIPTION "Power Factor B Clear Trap"
::= 21122

cmPow3ChKWattHrsCCLEAR TRAP-TYPE
ENTERPRISE itwatchdogs
VARIABLES { pow3ChKWattHrsC, pow3ChName, productFriendlyName, alarmTripType }
DESCRIPTION "Kilo Watt Hours C Clear Trap"
::= 21123

cmPow3ChVoltsCCLEAR TRAP-TYPE
ENTERPRISE itwatchdogs
VARIABLES { pow3ChVoltsC, pow3ChName, productFriendlyName, alarmTripType }
DESCRIPTION "Volts C Clear Trap"
::= 21124

cmPow3ChVoltMaxCCLEAR TRAP-TYPE
ENTERPRISE itwatchdogs
VARIABLES { pow3ChVoltMaxC, pow3ChName, productFriendlyName, alarmTripType }
DESCRIPTION "Volts Max C Clear Trap"
::= 21125

cmPow3ChVoltMinCCLEAR TRAP-TYPE
ENTERPRISE itwatchdogs
VARIABLES { pow3ChVoltMinC, pow3ChName, productFriendlyName, alarmTripType }
DESCRIPTION "Volts Min C Clear Trap"
::= 21126

cmPow3ChVoltPeakCCLEAR TRAP-TYPE
ENTERPRISE itwatchdogs
VARIABLES { pow3ChVoltPeakC, pow3ChName, productFriendlyName, alarmTripType }
DESCRIPTION "Volt Peak C Clear Trap"
::= 21127

cmPow3ChDeciAmpsCCLEAR TRAP-TYPE
ENTERPRISE itwatchdogs
VARIABLES { pow3ChDeciAmpsC, pow3ChName, productFriendlyName, alarmTripType }
DESCRIPTION "Deciamps C Clear Trap"
::= 21128

cmPow3ChRealPowerCCLEAR TRAP-TYPE
ENTERPRISE itwatchdogs
VARIABLES { pow3ChRealPowerC, pow3ChName, productFriendlyName, alarmTripType }
DESCRIPTION "Real Power C Clear Trap"
::= 21129

cmPow3ChApparentPowerCCLEAR TRAP-TYPE
ENTERPRISE itwatchdogs
VARIABLES { pow3ChApparentPowerC, pow3ChName, productFriendlyName, alarmTripType }
DESCRIPTION "Apparent Power C Clear Trap"
::= 21130

cmPow3ChPowerFactorCCLEAR TRAP-TYPE
ENTERPRISE itwatchdogs
VARIABLES { pow3ChPowerFactorC, pow3ChName, productFriendlyName, alarmTripType }
DESCRIPTION "Power Factor C Clear Trap"
::= 21131

cmOutlet1StatusCLEAR TRAP-TYPE
ENTERPRISE itwatchdogs
VARIABLES { outlet1Status, outletName, productFriendlyName, alarmTripType }
DESCRIPTION "Outlet 1 Status Clear Trap"
::= 21205

cmOutlet2StatusCLEAR TRAP-TYPE
ENTERPRISE itwatchdogs
VARIABLES { outlet2Status, outletName, productFriendlyName, alarmTripType }
DESCRIPTION "Outlet 2 Status Clear Trap"
::= 21206

cmVsfcSetPointCCLEAR TRAP-TYPE
ENTERPRISE itwatchdogs
VARIABLES { vsfcSetPointC, vsfcName, productFriendlyName, alarmTripType }
DESCRIPTION "Vsfc Temp Set Point Sensor Clear"
::= 21305

cmVsfcIntTempCCLEAR TRAP-TYPE
ENTERPRISE itwatchdogs
VARIABLES { vsfcIntTempC, vsfcName, productFriendlyName, alarmTripType }
DESCRIPTION "Vsfc Internal Temp Sensor Clear"
::= 21306

cmVsfcExt1TempCCLEAR TRAP-TYPE
ENTERPRISE itwatchdogs
VARIABLES { vsfcExt1TempC, vsfcName, productFriendlyName, alarmTripType }
DESCRIPTION "Vsfc External Temp 1 Sensor Clear"
::= 21307

cmVsfcExt2TempCCLEAR TRAP-TYPE
ENTERPRISE itwatchdogs
VARIABLES { vsfcExt2TempC, vsfcName, productFriendlyName, alarmTripType }
DESCRIPTION "Vsfc External Temp 2 Sensor Clear"
::= 21308

cmVsfcExt3TempCCLEAR TRAP-TYPE
ENTERPRISE itwatchdogs
VARIABLES { vsfcExt3TempC, vsfcName, productFriendlyName, alarmTripType }
DESCRIPTION "Vsfc External Temp 3 Sensor Clear"
::= 21309

cmVsfcExt4TempCCLEAR TRAP-TYPE
ENTERPRISE itwatchdogs
VARIABLES { vsfcExt4TempC, vsfcName, productFriendlyName, alarmTripType }
DESCRIPTION "Vsfc External Temp 4 Sensor Clear"
::= 21310

cmVsfcFanSpeedCLEAR TRAP-TYPE
ENTERPRISE itwatchdogs
VARIABLES { vsfcFanSpeed, vsfcName, productFriendlyName, alarmTripType }
DESCRIPTION "Vsfc Fan Speed Sensor Clear"
::= 21311

cmCtrl3ChVoltsACLEAR TRAP-TYPE
ENTERPRISE itwatchdogs
VARIABLES { ctrl3ChVoltsA, ctrl3ChName, productFriendlyName, alarmTripType }
DESCRIPTION "Volts A Clear Trap"
::= 21405

cmCtrl3ChVoltPeakACLEAR TRAP-TYPE
ENTERPRISE itwatchdogs
VARIABLES { ctrl3ChVoltPeakA, ctrl3ChName, productFriendlyName, alarmTripType }
DESCRIPTION "Volts Peak A Clear Trap"
::= 21406

cmCtrl3ChDeciAmpsACLEAR TRAP-TYPE
ENTERPRISE itwatchdogs
VARIABLES { ctrl3ChDeciAmpsA, ctrl3ChName, productFriendlyName, alarmTripType }
DESCRIPTION "Deciamps A Clear Trap"
::= 21407

cmCtrl3ChDeciAmpsPeakACLEAR TRAP-TYPE
ENTERPRISE itwatchdogs
VARIABLES { ctrl3ChDeciAmpsPeakA, ctrl3ChName, productFriendlyName, alarmTripType }
DESCRIPTION "Deciamps Peak A Clear Trap"
::= 21408

cmCtrl3ChRealPowerACLEAR TRAP-TYPE
ENTERPRISE itwatchdogs
VARIABLES { ctrl3ChRealPowerA, ctrl3ChName, productFriendlyName, alarmTripType }
DESCRIPTION "Real Power A Clear Trap"
::= 21409

cmCtrl3ChApparentPowerACLEAR TRAP-TYPE
ENTERPRISE itwatchdogs
VARIABLES { ctrl3ChApparentPowerA, ctrl3ChName, productFriendlyName, alarmTripType }
DESCRIPTION "Apparent Power A Clear Trap"
::= 21410

cmCtrl3ChPowerFactorACLEAR TRAP-TYPE
ENTERPRISE itwatchdogs
VARIABLES { ctrl3ChPowerFactorA, ctrl3ChName, productFriendlyName, alarmTripType }
DESCRIPTION "Power Factor A Clear Trap"
::= 21411

cmCtrl3ChVoltsBCLEAR TRAP-TYPE
ENTERPRISE itwatchdogs
VARIABLES { ctrl3ChVoltsB, ctrl3ChName, productFriendlyName, alarmTripType }
DESCRIPTION "Volts B Clear Trap"
::= 21412

cmCtrl3ChVoltPeakBCLEAR TRAP-TYPE
ENTERPRISE itwatchdogs
VARIABLES { ctrl3ChVoltPeakB, ctrl3ChName, productFriendlyName, alarmTripType }
DESCRIPTION "Volts Peak B Clear Trap"
::= 21413

cmCtrl3ChDeciAmpsBCLEAR TRAP-TYPE
ENTERPRISE itwatchdogs
VARIABLES { ctrl3ChDeciAmpsB, ctrl3ChName, productFriendlyName, alarmTripType }
DESCRIPTION "Deciamps B Clear Trap"
::= 21414

cmCtrl3ChDeciAmpsPeakBCLEAR TRAP-TYPE
ENTERPRISE itwatchdogs
VARIABLES { ctrl3ChDeciAmpsPeakB, ctrl3ChName, productFriendlyName, alarmTripType }
DESCRIPTION "Deciamps Peak B Clear Trap"
::= 21415

cmCtrl3ChRealPowerBCLEAR TRAP-TYPE
ENTERPRISE itwatchdogs
VARIABLES { ctrl3ChRealPowerB, ctrl3ChName, productFriendlyName, alarmTripType }
DESCRIPTION "Real Power B Clear Trap"
::= 21416

cmCtrl3ChApparentPowerBCLEAR TRAP-TYPE
ENTERPRISE itwatchdogs
VARIABLES { ctrl3ChApparentPowerB, ctrl3ChName, productFriendlyName, alarmTripType }
DESCRIPTION "Apparent Power B Clear Trap"
::= 21417

cmCtrl3ChPowerFactorBCLEAR TRAP-TYPE
ENTERPRISE itwatchdogs
VARIABLES { ctrl3ChPowerFactorB, ctrl3ChName, productFriendlyName, alarmTripType }
DESCRIPTION "Power Factor B Clear Trap"
::= 21418

cmCtrl3ChVoltsCCLEAR TRAP-TYPE
ENTERPRISE itwatchdogs
VARIABLES { ctrl3ChVoltsC, ctrl3ChName, productFriendlyName, alarmTripType }
DESCRIPTION "Volts C Clear Trap"
::= 21419

cmCtrl3ChVoltPeakCCLEAR TRAP-TYPE
ENTERPRISE itwatchdogs
VARIABLES { ctrl3ChVoltPeakC, ctrl3ChName, productFriendlyName, alarmTripType }
DESCRIPTION "Volts Peak C Clear Trap"
::= 21420

cmCtrl3ChDeciAmpsCCLEAR TRAP-TYPE
ENTERPRISE itwatchdogs
VARIABLES { ctrl3ChDeciAmpsC, ctrl3ChName, productFriendlyName, alarmTripType }
DESCRIPTION "Deciamps C Clear Trap"
::= 21421

cmCtrl3ChDeciAmpsPeakCCLEAR TRAP-TYPE
ENTERPRISE itwatchdogs
VARIABLES { ctrl3ChDeciAmpsPeakC, ctrl3ChName, productFriendlyName, alarmTripType }
DESCRIPTION "Deciamps Peak C Clear Trap"
::= 21422

cmCtrl3ChRealPowerCCLEAR TRAP-TYPE
ENTERPRISE itwatchdogs
VARIABLES { ctrl3ChRealPowerC, ctrl3ChName, productFriendlyName, alarmTripType }
DESCRIPTION "Real Power C Clear Trap"
::= 21423

cmCtrl3ChApparentPowerCCLEAR TRAP-TYPE
ENTERPRISE itwatchdogs
VARIABLES { ctrl3ChApparentPowerC, ctrl3ChName, productFriendlyName, alarmTripType }
DESCRIPTION "Apparent Power C Clear Trap"
::= 21424

cmCtrl3ChPowerFactorCCLEAR TRAP-TYPE
ENTERPRISE itwatchdogs
VARIABLES { ctrl3ChPowerFactorC, ctrl3ChName, productFriendlyName, alarmTripType }
DESCRIPTION "Power Factor C Clear Trap"
::= 21425

cmCtrlGrpAmpsACLEAR TRAP-TYPE
ENTERPRISE itwatchdogs
VARIABLES { ctrlGrpAmpsA, ctrlGrpAmpsName, productFriendlyName, alarmTripType }
DESCRIPTION "Group A DeciAmps Clear Trap"
::= 21505

cmCtrlGrpAmpsBCLEAR TRAP-TYPE
ENTERPRISE itwatchdogs
VARIABLES { ctrlGrpAmpsB, ctrlGrpAmpsName, productFriendlyName, alarmTripType }
DESCRIPTION "Group B DeciAmps Clear Trap"
::= 21506

cmCtrlGrpAmpsCCLEAR TRAP-TYPE
ENTERPRISE itwatchdogs
VARIABLES { ctrlGrpAmpsC, ctrlGrpAmpsName, productFriendlyName, alarmTripType }
DESCRIPTION "Group C DeciAmps Clear Trap"
::= 21507

cmCtrlGrpAmpsDCLEAR TRAP-TYPE
ENTERPRISE itwatchdogs
VARIABLES { ctrlGrpAmpsD, ctrlGrpAmpsName, productFriendlyName, alarmTripType }
DESCRIPTION "Group D DeciAmps Clear Trap"
::= 21508

cmCtrlGrpAmpsECLEAR TRAP-TYPE
ENTERPRISE itwatchdogs
VARIABLES { ctrlGrpAmpsE, ctrlGrpAmpsName, productFriendlyName, alarmTripType }
DESCRIPTION "Group E DeciAmps Clear Trap"
::= 21509

cmCtrlGrpAmpsFCLEAR TRAP-TYPE
ENTERPRISE itwatchdogs
VARIABLES { ctrlGrpAmpsF, ctrlGrpAmpsName, productFriendlyName, alarmTripType }
DESCRIPTION "Group F DeciAmps Clear Trap"
::= 21510

cmDewPointSensorDewPointCLEAR TRAP-TYPE
ENTERPRISE itwatchdogs
VARIABLES { dewPointSensorDewPoint, dewPointSensorName, productFriendlyName, alarmTripType }
DESCRIPTION "Remote Dew Point Sensor - Dew Point Clear Trap"
::= 21705

cmDewPointSensorTempCCLEAR TRAP-TYPE
ENTERPRISE itwatchdogs
VARIABLES { dewPointSensorTempC, dewPointSensorName, productFriendlyName, alarmTripType }
DESCRIPTION "Remote Dew Point Sensor - Temperature Clear Trap"
::= 21706

cmDewPointSensorHumidityCLEAR TRAP-TYPE
ENTERPRISE itwatchdogs
VARIABLES { dewPointSensorHumidity, dewPointSensorName, productFriendlyName, alarmTripType }
DESCRIPTION "Remote Dew Point Sensor - Humidity Clear Trap"
::= 21707

cmDigitalSensorDigitalCLEAR TRAP-TYPE
ENTERPRISE itwatchdogs
VARIABLES { digitalSensorDigital, digitalSensorName, productFriendlyName, alarmTripType }
DESCRIPTION "Digital sensor Clear Trap"
::= 21805

cmDstsVoltsACLEAR TRAP-TYPE
ENTERPRISE itwatchdogs
VARIABLES { dstsVoltsA, dstsName, productFriendlyName, alarmTripType }
DESCRIPTION "RMS Voltage of Side A Set Point Sensor Clear"
::= 21905

cmDstsAmpsACLEAR TRAP-TYPE
ENTERPRISE itwatchdogs
VARIABLES { dstsAmpsA, dstsName, productFriendlyName, alarmTripType }
DESCRIPTION "RMS Current of Side A Set Point Sensor Clear"
::= 21906

cmDstsVoltsBCLEAR TRAP-TYPE
ENTERPRISE itwatchdogs
VARIABLES { dstsVoltsB, dstsName, productFriendlyName, alarmTripType }
DESCRIPTION "RMS Voltage of Side B Set Point Sensor Clear"
::= 21907

cmDstsAmpsBCLEAR TRAP-TYPE
ENTERPRISE itwatchdogs
VARIABLES { dstsAmpsB, dstsName, productFriendlyName, alarmTripType }
DESCRIPTION "RMS Current of Side B Set Point Sensor Clear"
::= 21908

cmDstsSourceAActiveCLEAR TRAP-TYPE
ENTERPRISE itwatchdogs
VARIABLES { dstsSourceAActive, dstsName, productFriendlyName, alarmTripType }
DESCRIPTION "Source A Active Set Point Sensor Clear"
::= 21909

cmDstsSourceBActiveCLEAR TRAP-TYPE
ENTERPRISE itwatchdogs
VARIABLES { dstsSourceBActive, dstsName, productFriendlyName, alarmTripType }
DESCRIPTION "Source B Active Set Point Sensor Clear"
::= 21910

cmDstsPowerStatusACLEAR TRAP-TYPE
ENTERPRISE itwatchdogs
VARIABLES { dstsPowerStatusA, dstsName, productFriendlyName, alarmTripType }
DESCRIPTION "Source A Power Qualilty Active Set Point Sensor Clear"
::= 21911

cmDstsPowerStatusBCLEAR TRAP-TYPE
ENTERPRISE itwatchdogs
VARIABLES { dstsPowerStatusB, dstsName, productFriendlyName, alarmTripType }
DESCRIPTION "Source B Power Qualilty Active Set Point Sensor Clear"
::= 21912

cmDstsSourceATempCCLEAR TRAP-TYPE
ENTERPRISE itwatchdogs
VARIABLES { dstsSourceATempC, dstsName, productFriendlyName, alarmTripType }
DESCRIPTION "Source A Temp Sensor Clear"
::= 21913

cmDstsSourceBTempCCLEAR TRAP-TYPE
ENTERPRISE itwatchdogs
VARIABLES { dstsSourceBTempC, dstsName, productFriendlyName, alarmTripType }
DESCRIPTION "Source B Temp Sensor Clear"
::= 21914

cmCpmSensorStatusCLEAR TRAP-TYPE
ENTERPRISE itwatchdogs
VARIABLES { cpmSensorStatus, cpmSensorName, productFriendlyName, alarmTripType }
DESCRIPTION "City Power sensor Clear Trap"
::= 22005

cmSmokeAlarmStatusCLEAR TRAP-TYPE
ENTERPRISE itwatchdogs
VARIABLES { smokeAlarmStatus, smokeAlarmName, productFriendlyName, alarmTripType }
DESCRIPTION "Smoke alarm Clear Trap"
::= 22105

cmNeg48VdcSensorVoltageCLEAR TRAP-TYPE
ENTERPRISE itwatchdogs
VARIABLES { neg48VdcSensorVoltage, neg48VdcSensorName, productFriendlyName, alarmTripType }
DESCRIPTION "-48Vdc Sensor Clear Trap"
::= 22205

cmPos30VdcSensorVoltageCLEAR TRAP-TYPE
ENTERPRISE itwatchdogs
VARIABLES { pos30VdcSensorVoltage, pos30VdcSensorName, productFriendlyName, alarmTripType }
DESCRIPTION "30Vdc Sensor Clear Trap"
::= 22305

cmAnalogSensorAnalogCLEAR TRAP-TYPE
ENTERPRISE itwatchdogs
VARIABLES { analogSensorAnalog, analogSensorName, productFriendlyName, alarmTripType }
DESCRIPTION "Analog Sensor Clear Trap"
::= 22405

cmCtrl3ChIECKWattHrsACLEAR TRAP-TYPE
ENTERPRISE itwatchdogs
VARIABLES { ctrl3ChIECKWattHrsA, ctrl3ChIECName, productFriendlyName, alarmTripType }
DESCRIPTION "Kilo Watt Hours A Clear Trap"
::= 22505

cmCtrl3ChIECVoltsACLEAR TRAP-TYPE
ENTERPRISE itwatchdogs
VARIABLES { ctrl3ChIECVoltsA, ctrl3ChIECName, productFriendlyName, alarmTripType }
DESCRIPTION "Volts A Clear Trap"
::= 22506

cmCtrl3ChIECVoltPeakACLEAR TRAP-TYPE
ENTERPRISE itwatchdogs
VARIABLES { ctrl3ChIECVoltPeakA, ctrl3ChIECName, productFriendlyName, alarmTripType }
DESCRIPTION "Volts Peak A Clear Trap"
::= 22507

cmCtrl3ChIECDeciAmpsACLEAR TRAP-TYPE
ENTERPRISE itwatchdogs
VARIABLES { ctrl3ChIECDeciAmpsA, ctrl3ChIECName, productFriendlyName, alarmTripType }
DESCRIPTION "Deciamps A Clear Trap"
::= 22508

cmCtrl3ChIECDeciAmpsPeakACLEAR TRAP-TYPE
ENTERPRISE itwatchdogs
VARIABLES { ctrl3ChIECDeciAmpsPeakA, ctrl3ChIECName, productFriendlyName, alarmTripType }
DESCRIPTION "Deciamps Peak A Clear Trap"
::= 22509

cmCtrl3ChIECRealPowerACLEAR TRAP-TYPE
ENTERPRISE itwatchdogs
VARIABLES { ctrl3ChIECRealPowerA, ctrl3ChIECName, productFriendlyName, alarmTripType }
DESCRIPTION "Real Power A Clear Trap"
::= 22510

cmCtrl3ChIECApparentPowerACLEAR TRAP-TYPE
ENTERPRISE itwatchdogs
VARIABLES { ctrl3ChIECApparentPowerA, ctrl3ChIECName, productFriendlyName, alarmTripType }
DESCRIPTION "Apparent Power A Clear Trap"
::= 22511

cmCtrl3ChIECPowerFactorACLEAR TRAP-TYPE
ENTERPRISE itwatchdogs
VARIABLES { ctrl3ChIECPowerFactorA, ctrl3ChIECName, productFriendlyName, alarmTripType }
DESCRIPTION "Power Factor A Clear Trap"
::= 22512

cmCtrl3ChIECKWattHrsBCLEAR TRAP-TYPE
ENTERPRISE itwatchdogs
VARIABLES { ctrl3ChIECKWattHrsB, ctrl3ChIECName, productFriendlyName, alarmTripType }
DESCRIPTION "Kilo Watt Hours B Clear Trap"
::= 22513

cmCtrl3ChIECVoltsBCLEAR TRAP-TYPE
ENTERPRISE itwatchdogs
VARIABLES { ctrl3ChIECVoltsB, ctrl3ChIECName, productFriendlyName, alarmTripType }
DESCRIPTION "Volts B Clear Trap"
::= 22514

cmCtrl3ChIECVoltPeakBCLEAR TRAP-TYPE
ENTERPRISE itwatchdogs
VARIABLES { ctrl3ChIECVoltPeakB, ctrl3ChIECName, productFriendlyName, alarmTripType }
DESCRIPTION "Volts Peak B Clear Trap"
::= 22515

cmCtrl3ChIECDeciAmpsBCLEAR TRAP-TYPE
ENTERPRISE itwatchdogs
VARIABLES { ctrl3ChIECDeciAmpsB, ctrl3ChIECName, productFriendlyName, alarmTripType }
DESCRIPTION "Deciamps B Clear Trap"
::= 22516

cmCtrl3ChIECDeciAmpsPeakBCLEAR TRAP-TYPE
ENTERPRISE itwatchdogs
VARIABLES { ctrl3ChIECDeciAmpsPeakB, ctrl3ChIECName, productFriendlyName, alarmTripType }
DESCRIPTION "Deciamps Peak B Clear Trap"
::= 22517

cmCtrl3ChIECRealPowerBCLEAR TRAP-TYPE
ENTERPRISE itwatchdogs
VARIABLES { ctrl3ChIECRealPowerB, ctrl3ChIECName, productFriendlyName, alarmTripType }
DESCRIPTION "Real Power B Clear Trap"
::= 22518

cmCtrl3ChIECApparentPowerBCLEAR TRAP-TYPE
ENTERPRISE itwatchdogs
VARIABLES { ctrl3ChIECApparentPowerB, ctrl3ChIECName, productFriendlyName, alarmTripType }
DESCRIPTION "Apparent Power B Clear Trap"
::= 22519

cmCtrl3ChIECPowerFactorBCLEAR TRAP-TYPE
ENTERPRISE itwatchdogs
VARIABLES { ctrl3ChIECPowerFactorB, ctrl3ChIECName, productFriendlyName, alarmTripType }
DESCRIPTION "Power Factor B Clear Trap"
::= 22520

cmCtrl3ChIECKWattHrsCCLEAR TRAP-TYPE
ENTERPRISE itwatchdogs
VARIABLES { ctrl3ChIECKWattHrsC, ctrl3ChIECName, productFriendlyName, alarmTripType }
DESCRIPTION "Kilo Watt Hours C Clear Trap"
::= 22521

cmCtrl3ChIECVoltsCCLEAR TRAP-TYPE
ENTERPRISE itwatchdogs
VARIABLES { ctrl3ChIECVoltsC, ctrl3ChIECName, productFriendlyName, alarmTripType }
DESCRIPTION "Volts C Clear Trap"
::= 22522

cmCtrl3ChIECVoltPeakCCLEAR TRAP-TYPE
ENTERPRISE itwatchdogs
VARIABLES { ctrl3ChIECVoltPeakC, ctrl3ChIECName, productFriendlyName, alarmTripType }
DESCRIPTION "Volts Peak C Clear Trap"
::= 22523

cmCtrl3ChIECDeciAmpsCCLEAR TRAP-TYPE
ENTERPRISE itwatchdogs
VARIABLES { ctrl3ChIECDeciAmpsC, ctrl3ChIECName, productFriendlyName, alarmTripType }
DESCRIPTION "Deciamps C Clear Trap"
::= 22524

cmCtrl3ChIECDeciAmpsPeakCCLEAR TRAP-TYPE
ENTERPRISE itwatchdogs
VARIABLES { ctrl3ChIECDeciAmpsPeakC, ctrl3ChIECName, productFriendlyName, alarmTripType }
DESCRIPTION "Deciamps Peak C Clear Trap"
::= 22525

cmCtrl3ChIECRealPowerCCLEAR TRAP-TYPE
ENTERPRISE itwatchdogs
VARIABLES { ctrl3ChIECRealPowerC, ctrl3ChIECName, productFriendlyName, alarmTripType }
DESCRIPTION "Real Power C Clear Trap"
::= 22526

cmCtrl3ChIECApparentPowerCCLEAR TRAP-TYPE
ENTERPRISE itwatchdogs
VARIABLES { ctrl3ChIECApparentPowerC, ctrl3ChIECName, productFriendlyName, alarmTripType }
DESCRIPTION "Apparent Power C Clear Trap"
::= 22527

cmCtrl3ChIECPowerFactorCCLEAR TRAP-TYPE
ENTERPRISE itwatchdogs
VARIABLES { ctrl3ChIECPowerFactorC, ctrl3ChIECName, productFriendlyName, alarmTripType }
DESCRIPTION "Power Factor C Clear Trap"
::= 22528

cmAirSpeedSwitchSensorAirSpeedCLEAR TRAP-TYPE
ENTERPRISE itwatchdogs
VARIABLES { airSpeedSwitchSensorAirSpeed, airSpeedSwitchSensorName, productFriendlyName, alarmTripType }
DESCRIPTION "Air Speed Switch Clear Trap"
::= 22605

END
