IBM-SYSTEM-SMART-MIB DEFINITIONS ::= BEGIN

IMPORTS
   OBJECT-TYPE
        FROM RFC-1212

   TRAP-TYPE
        FROM RFC-1215

   ibmSystemSmartDisk,
   Boolean, Uint8, Sint8, Uint16, Sint16, Uint32,
   Sint32, Uint64, Sint64, Real32, Real64, String, Datetime
      FROM IBM-SYSTEM-MIB;
      
ibmSystemSmartDiskTable OBJECT-TYPE
   SYNTAX         SEQUENCE OF IbmSystemSmartDiskEntry
   ACCESS         not-accessible
   STATUS         mandatory
   DESCRIPTION    "The IBMPSG_StorageFailurePredictionSettings class represents SMART enabled disk"
   REFERENCE      "IBMPSG_StorageFailurePredictionSettings"
::= { ibmSystemSmartDisk 1 }

ibmSystemSmartDiskEntry OBJECT-TYPE
   SYNTAX         IbmSystemSmartDiskEntry
   ACCESS         not-accessible
   STATUS         mandatory
   DESCRIPTION    "This class defines an entry for each IBMPSG_StorageFailurePredictionSettings
                    instance. Each instance of the IBMPSG_StorageFailurePredictionSettings class 
                    contains status and descriptive information for each disk 
                    recognized by the Director SMART provider."
   INDEX          { ibmSystemSmartDiskKeyIndex }
::= { ibmSystemSmartDiskTable 1 }

IbmSystemSmartDiskEntry ::= SEQUENCE
{
   ibmSystemSmartDiskKeyIndex String,
   ibmSystemSmartDiskDeviceId String,
   ibmSystemSmartDiskDefunct Boolean,
   ibmSystemSmartDiskEventAutoClearEnabled Boolean,
   ibmSystemSmartDiskEventsEnabled Boolean, 
   ibmSystemSmartDiskOutOfSync Boolean,
   ibmSystemSmartDiskPeriod Uint32,
   ibmSystemSmartDiskPredictsFailure Boolean,
   ibmSystemSmartDiskSmartEnabled Boolean
}

ibmSystemSmartDiskKeyIndex OBJECT-TYPE
   SYNTAX         String
   ACCESS         read-only
   STATUS         mandatory
   DESCRIPTION    "The index used by this table"
   REFERENCE      "IBMPSG_StorageFailurePredictionSettings.KeyIndex"
::= { ibmSystemSmartDiskEntry 1 }

ibmSystemSmartDiskDeviceId OBJECT-TYPE
   SYNTAX         String
   ACCESS         read-only
   STATUS         mandatory
   DESCRIPTION    "The DeviceID that identifies the disk"
   REFERENCE      "IBMPSG_StorageFailurePredictionSettings.DeviceID"
::= { ibmSystemSmartDiskEntry 2 }

ibmSystemSmartDiskDefunct OBJECT-TYPE
   SYNTAX         Boolean
   ACCESS         read-only
   STATUS         mandatory
   DESCRIPTION    "TRUE if drive is defunct."
   REFERENCE      "IBMPSG_StorageFailurePredictionSettings.Defunct"
::= { ibmSystemSmartDiskEntry 3 }

ibmSystemSmartDiskEventAutoClearEnabled OBJECT-TYPE
   SYNTAX         Boolean
   ACCESS         read-only
   STATUS         mandatory
   DESCRIPTION    "TRUE if auto-clear is enabled for events."
   REFERENCE      "IBMPSG_StorageFailurePredictionSettings.EventAutoClearEnabled"
::= { ibmSystemSmartDiskEntry 4 }

ibmSystemSmartDiskEventsEnabled OBJECT-TYPE
   SYNTAX         Boolean
   ACCESS         read-only
   STATUS         mandatory
   DESCRIPTION    "TRUE if events are enabled"
   REFERENCE      "IBMPSG_StorageFailurePredictionSettings.EventsEnabled"
::= { ibmSystemSmartDiskEntry 5 }

ibmSystemSmartDiskOutOfSync OBJECT-TYPE
   SYNTAX         Boolean
   ACCESS         read-only
   STATUS         mandatory
   DESCRIPTION    "TRUE if drive is Out of Sync."
   REFERENCE      "IBMPSG_StorageFailurePredictionSettings.OutOfSync"
::= { ibmSystemSmartDiskEntry 6 }

ibmSystemSmartDiskPeriod OBJECT-TYPE
   SYNTAX         Uint32
   ACCESS         read-only
   STATUS         mandatory
   DESCRIPTION    "Period in seconds to poll for failure prediction."
   REFERENCE      "IBMPSG_StorageFailurePredictionSettings.Period"
::= { ibmSystemSmartDiskEntry 7 }

ibmSystemSmartDiskPredictsFailure OBJECT-TYPE
   SYNTAX         Boolean
   ACCESS         read-only
   STATUS         mandatory
   DESCRIPTION    "TRUE if drive is predicting a failure."
   REFERENCE      "IBMPSG_StorageFailurePredictionSettings.PredictsFailure"
::= { ibmSystemSmartDiskEntry 8 }

ibmSystemSmartDiskSmartEnabled OBJECT-TYPE
   SYNTAX         Boolean
   ACCESS         read-only
   STATUS         mandatory
   DESCRIPTION    "TRUE if drive is SMART capable."
   REFERENCE      "IBMPSG_StorageFailurePredictionSettings.SmartEnabled"
::= { ibmSystemSmartDiskEntry 9 }


END
