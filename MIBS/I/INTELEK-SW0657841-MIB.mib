INTELEK-SW0657841-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;


intelek MODULE-IDENTITY
        LAST-UPDATED "200607030000Z"
        ORGANIZATION "Intelek Tech Corp."
        CONTACT-INFO
            ""
        DESCRIPTION
            ""
        ::= { enterprises 5205 }

switch                       OBJECT IDENTIFIER ::= { intelek 2 }

sw0657841ProductID	        OBJECT IDENTIFIER ::= { switch 34 }

sw0657841Produces            OBJECT IDENTIFIER ::= { sw0657841ProductID 1 }

sw0657841System           	OBJECT IDENTIFIER ::= { sw0657841Produces 1 }

sw0657841CommonSys           	OBJECT IDENTIFIER ::= { sw0657841System 1 }

sw0657841Reboot OBJECT-TYPE
	SYNTAX		INTEGER(0|1|2)
	MAX-ACCESS	    read-write
	STATUS		current
	DESCRIPTION
		"Reboot the system. Get this OID always return zero.
            0 - do nothing
			1 - Reboot without saving start
			2 - Reboot with saving start"
	::= { sw0657841CommonSys 1 }

sw0657841BiosVsersion	OBJECT-TYPE
	SYNTAX		DisplayString
	MAX-ACCESS	    read-only
	STATUS		current
	DESCRIPTION
		"Get the BIOS version of the system."
	::= { sw0657841CommonSys 2 }

sw0657841FirmwareVersion	OBJECT-TYPE
	SYNTAX		DisplayString
	MAX-ACCESS	    read-only
	STATUS		current
	DESCRIPTION
		"Get the firmware version of the system."
	::= { sw0657841CommonSys 3 }

sw0657841HardwareVersion	OBJECT-TYPE
	SYNTAX		DisplayString
	MAX-ACCESS	    read-only
	STATUS		current
	DESCRIPTION
		"Get the hardware version of the system."
	::= { sw0657841CommonSys 4 }

sw0657841MechanicalVersion OBJECT-TYPE
	SYNTAX		DisplayString
	MAX-ACCESS 	    read-only
	STATUS		current
	DESCRIPTION
		"Get the mechanical version of the system."
	::= { sw0657841CommonSys 5 }

sw0657841SerialNumber	OBJECT-TYPE
	SYNTAX		DisplayString
	MAX-ACCESS	    read-only
	STATUS		current
	DESCRIPTION
		"Get the Serial number of the system."
	::= { sw0657841CommonSys 6 }

sw0657841HostMacAddress	OBJECT-TYPE
	SYNTAX		DisplayString
	MAX-ACCESS	    read-only
	STATUS		current
	DESCRIPTION
		"Get the MAC address of the system."
	::= { sw0657841CommonSys 7 }

sw0657841DevicePort	OBJECT-TYPE
	SYNTAX		DisplayString
	MAX-ACCESS  	read-only
	STATUS		current
	DESCRIPTION
		"Get the quantity of ports that this system owns now."
	::= { sw0657841CommonSys 8 }

sw0657841RamSize  OBJECT-TYPE
    SYNTAX      DisplayString
    MAX-ACCESS      read-only
    STATUS      current
    DESCRIPTION
        "Get the RAM size of the system."
	::= { sw0657841CommonSys 9 }

sw0657841FlashSize  OBJECT-TYPE
    SYNTAX      DisplayString
    MAX-ACCESS      read-only
    STATUS      current
    DESCRIPTION
        "Get the flash size of the system."
	::= { sw0657841CommonSys 10 }

sw0657841DeviceName  OBJECT-TYPE
    SYNTAX      DisplayString
    MAX-ACCESS      read-write
    STATUS      current
    DESCRIPTION
        "Get the flash size of the Device Name."
	::= { sw0657841CommonSys 11 }

sw0657841SystemDescription  OBJECT-TYPE
    SYNTAX      DisplayString
    MAX-ACCESS      read-only
    STATUS      current
    DESCRIPTION
        "Get the flash size of the System Description."
	::= { sw0657841CommonSys 12 }

sw0657841IP           	OBJECT IDENTIFIER ::= { sw0657841System 2 }

sw0657841DhcpSetting OBJECT-TYPE
	SYNTAX		    INTEGER(0|1)
	MAX-ACCESS	        read-write
	STATUS		    current
	DESCRIPTION
		"Get/Set DHCP status of the system.
			0 - DHCP disable
			1 - DHCP enable"
	::= { sw0657841IP 1 }

sw0657841IPAddress OBJECT-TYPE
	SYNTAX      IpAddress
	MAX-ACCESS	    read-write
	STATUS		current
	DESCRIPTION
		"Get/Set the IP address of the system.
		 You can't set this OID if DHCP status is enabled."
	::= { sw0657841IP 2 }

sw0657841NetMask OBJECT-TYPE
	SYNTAX      IpAddress
	MAX-ACCESS	    read-write
	STATUS		current
	DESCRIPTION
		"Get/Set the subnet mask of the system.
		 You can't set this OID if DHCP status is enabled."
	::= { sw0657841IP 3 }

sw0657841DefaultGateway OBJECT-TYPE
	SYNTAX      IpAddress
	MAX-ACCESS	    read-write
	STATUS		current
	DESCRIPTION
		"Get/Set the default gateway of the system.
		 You can't set this OID if DHCP status is enabled."
	::= { sw0657841IP 4 }

sw0657841DnsSetting OBJECT-TYPE
	SYNTAX      INTEGER(0|1)
	MAX-ACCESS	    read-write
	STATUS		current
	DESCRIPTION
		"Get/Set the source of DNS server.
		 You can't set this OID if DHCP status is disabled.
			0 - manual, the DNS server is from manual setting
            1 - auto, the DNS server is assigned by DHCP server."
	::= { sw0657841IP 5 }

sw0657841DnsServer OBJECT-TYPE
	SYNTAX      IpAddress
	MAX-ACCESS	    read-write
	STATUS		current
	DESCRIPTION
		"Get/Set the DNS server of the system."
	::= { sw0657841IP 6 }

sw0657841Time           	OBJECT IDENTIFIER ::= { sw0657841System 3 }

sw0657841SystemCurrentTime OBJECT-TYPE
	SYNTAX      DisplayString
	MAX-ACCESS	    read-only
	STATUS		current
	DESCRIPTION
		"Get the current time of the system."
	::= { sw0657841Time 1 }

sw0657841ManualTimeSetting OBJECT-TYPE
	SYNTAX      DisplayString
	MAX-ACCESS	    read-write
	STATUS		current
	DESCRIPTION
		"Get/Set the system time of the device.
        The input format is 'Year/Month/Day/Hour/Minute/Second'.
        ex: 2004/1/1/12/34/25  means 2004/1/1 - 12:24:25 .
        The value range:
        Year    : 2000 - 2036,
        Mouth   : 1 - 12,
        Day     : 1 - 31,
        Hour    : 0 - 23,
        Minute  : 0 - 59,
        Sec     : 0 - 59."
	::= { sw0657841Time 2 }

sw0657841NTPServer OBJECT-TYPE
	SYNTAX      DisplayString
	MAX-ACCESS	    read-write
	STATUS		current
	DESCRIPTION
		"Get/Set the NTP Time Server. You can use the IP address or domain name."
	::= { sw0657841Time 3 }

sw0657841NTPTimeZone OBJECT-TYPE
	SYNTAX      INTEGER(-12..13)
	MAX-ACCESS	    read-write
	STATUS		current
	DESCRIPTION
		"Get/Set the NTP Time Zone.
		The value range is between -12 and 13
		-12 - GMT -12:00,
		-11 - GMT -11:00,
		-10 - GMT -10:00,
		 -9 - GMT -09:00,
		 -8 - GMT -08:00,
		 -7 - GMT -07:00,
		 -6 - GMT -06:00,
		 -5 - GMT -05:00,
		 -4 - GMT -04:00,
		 -3 - GMT -03:00,
		 -2 - GMT -02:00,
		 -1 - GMT -01:00,
		  0 - GMT +00:00,
		  1 - GMT +01:00,
		  2 - GMT +02:00,
		  3 - GMT +03:00,
		  4 - GMT +04:00,
		  5 - GMT +05:00,
		  6 - GMT +06:00,
		  7 - GMT +07:00,
		  8 - GMT +08:00,
		  9 - GMT +09:00,
		 10 - GMT +10:00,
		 11 - GMT +11:00,
		 12 - GMT +12:00,
		 13 - GMT +13:00. "
	::= { sw0657841Time 4 }

sw0657841NTPTimeSync OBJECT-TYPE
	SYNTAX      INTEGER(0|1)
	MAX-ACCESS	    read-write
	STATUS		current
	DESCRIPTION
		"Sync time from NTP Server. Get this OID always return zero.
		Set the Time Server and Time Zone before doing time sync.
		Notice that time server must be correct!
		The value range (0|1):
		1 - sync.
        0 - do nothing."
	::= { sw0657841Time 5 }

sw0657841DaylightSavingTime OBJECT-TYPE
	SYNTAX      INTEGER(-5..5)
	MAX-ACCESS	    read-write
	STATUS		current
	DESCRIPTION
		"Get/Set the daylight saving time.
		The value range is between -5 and 5. (Unit: hour)"
	::= { sw0657841Time 6 }

sw0657841DaylightStartTime OBJECT-TYPE
	SYNTAX      DisplayString
	MAX-ACCESS	    read-write
	STATUS		current
	DESCRIPTION
		"Get/Set the Start time of Daylight Saving.
		The input format is 'MM/DD/HH',
		and daylight saving start month can't equal end month.
		example: month/day/hour   10/01/00
		month: 01~12, day: 01~31, hour: 00~23 ."
	::= { sw0657841Time 7 }

sw0657841DaylightEndTime OBJECT-TYPE
	SYNTAX      DisplayString
	MAX-ACCESS	    read-write
	STATUS		current
	DESCRIPTION
		"Get/Set the End time of Daylight Saving.
		The input format is 'MM/DD/HH',
		and daylight saving start month can't equal end month.
		example: month/day/hour   04/01/00
		month: 01~12, day: 01~31, hour: 00~23 ."
	::= { sw0657841Time 8 }


sw0657841Account           	OBJECT IDENTIFIER ::= { sw0657841System 4 }

sw0657841AccountNumber OBJECT-TYPE
	SYNTAX      INTEGER(1..5)
	MAX-ACCESS	    read-only
	STATUS		current
	DESCRIPTION
		"Get the current account number(s) of the system."
	::= { sw0657841Account 1 }

sw0657841AccountTable	OBJECT-TYPE
	SYNTAX		SEQUENCE OF SW0657841AccountEntry
	MAX-ACCESS	not-accessible
	STATUS		current
	DESCRIPTION
		"This is a list of SW0657841AccountEntry. The numbers of entries are given by
		the value of sw0657841AccountNumber."
	::= { sw0657841Account 2 }

SW0657841AccountEntry ::=
SEQUENCE {
    sw0657841AccountIndex		    INTEGER,
    sw0657841AccountAuthorization	DisplayString,
    sw0657841AccountName             DisplayString,
    sw0657841AccountPassword         DisplayString
}

sw0657841AccountEntry	OBJECT-TYPE
	SYNTAX		SW0657841AccountEntry
	MAX-ACCESS	    not-accessible
	STATUS		current
	DESCRIPTION
		"This is the Entry(s) for account information."
	INDEX {sw0657841AccountIndex}
	::= { sw0657841AccountTable 1 }

sw0657841AccountIndex	OBJECT-TYPE
	SYNTAX		INTEGER(1..5)
	MAX-ACCESS	    read-only
	STATUS		current
	DESCRIPTION
		"This is the index of the account entry."
	::= { sw0657841AccountEntry 1 }

sw0657841AccountAuthorization	OBJECT-TYPE
	SYNTAX		DisplayString
	MAX-ACCESS	    read-only
	STATUS		current
	DESCRIPTION
		"This is the authorization of the account entry."
	::= { sw0657841AccountEntry 2 }

sw0657841AccountName	OBJECT-TYPE
	SYNTAX		DisplayString
	MAX-ACCESS	    read-write
	STATUS		current
	DESCRIPTION
		"This is the username of the account entry."
	::= { sw0657841AccountEntry 3 }

sw0657841AccountPassword	OBJECT-TYPE
	SYNTAX		DisplayString
	MAX-ACCESS	    read-write
	STATUS		current
	DESCRIPTION
		"This is the password of the account entry. The return value is always '********'."
	::= { sw0657841AccountEntry 4 }

sw0657841AccountAddName OBJECT-TYPE
	SYNTAX      DisplayString
	MAX-ACCESS	    read-write
	STATUS		current
	DESCRIPTION
		"This is the account name for adding operation."
	::= { sw0657841Account 3 }

sw0657841AccountAddPassword OBJECT-TYPE
	SYNTAX      DisplayString
	MAX-ACCESS	    read-write
	STATUS		current
	DESCRIPTION
		"This is the account password for adding operation. The return value is always '********'."
	::= { sw0657841Account 4 }

sw0657841DoAccountAdd OBJECT-TYPE
	SYNTAX      INTEGER(0|1)
	MAX-ACCESS	    read-write
	STATUS		current
	DESCRIPTION
		"Add account name. OID sw0657841AccountAddName and sw0657841AccountAddPassword must be
        filled first. Get this OID always return zero.
            1 - add account.
            0 - do nothing."
	::= { sw0657841Account 5 }

sw0657841AccountDel	OBJECT-TYPE
	SYNTAX		INTEGER(2..5)
	MAX-ACCESS	    read-write
	STATUS		current
	DESCRIPTION
		"Delete account. The value is valid sw0657841AccountIndex(Can't delete administrator)."
	::= { sw0657841Account 6 }




sw0657841Snmp           	OBJECT IDENTIFIER ::= { sw0657841Produces 2 }

sw0657841GetCommunity OBJECT-TYPE
	SYNTAX      DisplayString
	MAX-ACCESS	    read-write
	STATUS		current
	DESCRIPTION
		"Get/Set the get-community of the SNMP."
	::= { sw0657841Snmp 1 }

sw0657841SetCommunity OBJECT-TYPE
	SYNTAX      DisplayString
	MAX-ACCESS	    read-write
	STATUS		current
	DESCRIPTION
		"Get/Set the set-community of the SNMP."
	::= { sw0657841Snmp 2 }

sw0657841TrapHostNumber OBJECT-TYPE
	SYNTAX      INTEGER(1..6)
	MAX-ACCESS	    read-only
	STATUS		current
	DESCRIPTION
		"Get the number of trap hosts."
	::= { sw0657841Snmp 3 }

sw0657841TrapHostTable	OBJECT-TYPE
	SYNTAX		SEQUENCE OF SW0657841TrapHostEntry
	MAX-ACCESS	not-accessible
	STATUS		current
	DESCRIPTION
		"A list of trap host entry. The numbers of entries are given by the value of sw0657841TrapHostNumber."
    ::= { sw0657841Snmp 4 }

SW0657841TrapHostEntry ::=
SEQUENCE {
    sw0657841TrapHostIndex		    INTEGER,
    sw0657841TrapHostIP          	IpAddress,
    sw0657841TrapHostPort            INTEGER,
    sw0657841TrapHostCommunity       DisplayString
}

sw0657841TrapHostEntry	OBJECT-TYPE
	SYNTAX		SW0657841TrapHostEntry
	MAX-ACCESS	    not-accessible
	STATUS		current
	DESCRIPTION
		"This is the entry information for trap host."
	INDEX {sw0657841TrapHostIndex}
	::= { sw0657841TrapHostTable 1 }

sw0657841TrapHostIndex	OBJECT-TYPE
	SYNTAX		INTEGER(1..6)
	MAX-ACCESS	    read-only
	STATUS		current
	DESCRIPTION
		"The index of the trap host entry."
	::= { sw0657841TrapHostEntry 1 }

sw0657841TrapHostIP	OBJECT-TYPE
	SYNTAX		IpAddress
	MAX-ACCESS	    read-write
	STATUS		current
	DESCRIPTION
		"This is the IP of the trap host."
	::= { sw0657841TrapHostEntry 2 }


sw0657841TrapHostPort	OBJECT-TYPE
	SYNTAX		INTEGER(1..65535)
	MAX-ACCESS	    read-write
	STATUS		current
	DESCRIPTION
		"This is the receiving-port number of the trap host."
	::= { sw0657841TrapHostEntry 3 }


sw0657841TrapHostCommunity	OBJECT-TYPE
	SYNTAX		DisplayString
	MAX-ACCESS	    read-write
	STATUS		current
	DESCRIPTION
		"The community name for the trap PDU."
	::= { sw0657841TrapHostEntry 4 }



sw0657841Alarm           	OBJECT IDENTIFIER ::= { sw0657841Produces 3 }

sw0657841Event           	OBJECT IDENTIFIER ::= { sw0657841Alarm 1 }

sw0657841EventNumber OBJECT-TYPE
	SYNTAX      INTEGER(1..2147483647)
	MAX-ACCESS	    read-only
	STATUS		current
	DESCRIPTION
		"Get the total number of alarm events."
	::= { sw0657841Event 1 }

sw0657841EventTable	OBJECT-TYPE
	SYNTAX		SEQUENCE OF SW0657841EventEntry
	MAX-ACCESS	not-accessible
	STATUS		current
    DESCRIPTION
        "This is a list of alarm event entry. The numbers of entries are given by the value of sw0657841EventNumber."
	::= { sw0657841Event 2 }

SW0657841EventEntry ::=
SEQUENCE {
    sw0657841EventIndex		    INTEGER,
    sw0657841EventName          	DisplayString,
    sw0657841EventSendEmail      INTEGER,
    sw0657841EventSendTrap       INTEGER
}

sw0657841EventEntry	OBJECT-TYPE
	SYNTAX		SW0657841EventEntry
	MAX-ACCESS	    not-accessible
	STATUS		current
	DESCRIPTION
		"This is the entry information for alarm event."
	INDEX {sw0657841EventIndex}
	::= { sw0657841EventTable 1 }

sw0657841EventIndex	OBJECT-TYPE
	SYNTAX		INTEGER(1..2147483647)
	MAX-ACCESS	    read-only
	STATUS		current
	DESCRIPTION
		"This is the index of the alarm event entry."
	::= { sw0657841EventEntry 1 }

sw0657841EventName	OBJECT-TYPE
	SYNTAX		DisplayString
	MAX-ACCESS	    read-only
	STATUS		current
	DESCRIPTION
		"This is the alarm event name."
	::= { sw0657841EventEntry 2 }

sw0657841EventSendEmail	OBJECT-TYPE
	SYNTAX		INTEGER(0|1)
	MAX-ACCESS	    read-write
	STATUS		current
	DESCRIPTION
		"Send email when alarm event is triggered."
	::= { sw0657841EventEntry 3 }

sw0657841EventSendTrap	OBJECT-TYPE
	SYNTAX		INTEGER(0|1)
	MAX-ACCESS	    read-write
	STATUS		current
	DESCRIPTION
		"Send trap when alarm event is triggered."
	::= { sw0657841EventEntry 4 }




sw0657841Email           	OBJECT IDENTIFIER ::= { sw0657841Alarm 2 }

sw0657841EmailServer OBJECT-TYPE
	SYNTAX      DisplayString
	MAX-ACCESS	    read-write
	STATUS		current
	DESCRIPTION
		"This is the SMTP server for alarm event."
	::= { sw0657841Email 1 }

sw0657841EmailUsername OBJECT-TYPE
	SYNTAX      DisplayString
	MAX-ACCESS	    read-write
	STATUS		current
	DESCRIPTION
		"This is the Username of SMTP server."
	::= { sw0657841Email 2 }

sw0657841EmailPassword OBJECT-TYPE
	SYNTAX      DisplayString
	MAX-ACCESS	    read-write
	STATUS		current
	DESCRIPTION
		"This is the User Password of SMTP server."
	::= { sw0657841Email 3 }

sw0657841EmailUserNumber OBJECT-TYPE
	SYNTAX      INTEGER(1..6)
	MAX-ACCESS	    read-only
	STATUS		current
	DESCRIPTION
		"The number of the email users that you want to send the alarm notification."
	::= { sw0657841Email 4 }

sw0657841EmailUserTable	OBJECT-TYPE
	SYNTAX		SEQUENCE OF SW0657841EmailUserEntry
	MAX-ACCESS	not-accessible
	STATUS		current
    DESCRIPTION
        "This is a list of email user entry. The numbers of entries are given by the value of sw0657841EmailUserNumber."
	::= { sw0657841Email 5 }

SW0657841EmailUserEntry ::=
SEQUENCE {
    sw0657841EmailUserIndex		    INTEGER,
    sw0657841EmailUserAddress       	DisplayString
}

sw0657841EmailUserEntry	OBJECT-TYPE
	SYNTAX		SW0657841EmailUserEntry
	MAX-ACCESS	    not-accessible
	STATUS		current
	DESCRIPTION
		"This is the Entry information for email user entry."
	INDEX {sw0657841EmailUserIndex}
	::= { sw0657841EmailUserTable 1 }

sw0657841EmailUserIndex	OBJECT-TYPE
	SYNTAX		INTEGER(1..6)
	MAX-ACCESS	    read-only
	STATUS		current
	DESCRIPTION
		"This is the index of the email user entry."
	::= { sw0657841EmailUserEntry 1 }

sw0657841EmailUserAddress	OBJECT-TYPE
	SYNTAX		DisplayString
	MAX-ACCESS	    read-write
	STATUS		current
	DESCRIPTION
		"This is the email address of the email user entry."
	::= { sw0657841EmailUserEntry 2 }

sw0657841Configuration           	OBJECT IDENTIFIER ::= { sw0657841Produces 5 }

sw0657841SaveRestore           	OBJECT IDENTIFIER ::= { sw0657841Configuration 1 }

sw0657841SaveStart OBJECT-TYPE
	SYNTAX      INTEGER(0|1)
	MAX-ACCESS	    read-write
	STATUS		current
	DESCRIPTION
		"Save current configuration into flash memory (Save as Start Configuration).
        Get this OID always return zero.
            1 - save.
            0 - do nothing. "
	::= { sw0657841SaveRestore 1 }

sw0657841SaveUser OBJECT-TYPE
	SYNTAX      INTEGER(0|1)
	MAX-ACCESS	    read-write
	STATUS		current
	DESCRIPTION
		"Save current configuration into flash memory (Save as User Configuration).
        Get this OID always return zero.
            1 - save.
            0 - do nothing. "
	::= { sw0657841SaveRestore 2 }

sw0657841RestoreDefault OBJECT-TYPE
	SYNTAX      INTEGER(0|1|2)
	MAX-ACCESS	    read-write
	STATUS		current
	DESCRIPTION
		"Restore factory default configuration.
        Get this OID always return zero.
            2 - restore default included default ip address.
            1 - restore default without changing current ip address.
            0 - do nothing. "
	::= { sw0657841SaveRestore 3 }

sw0657841RestoreUser OBJECT-TYPE
	SYNTAX      INTEGER(0|1)
	MAX-ACCESS	    read-write
	STATUS		current
	DESCRIPTION
		"Restore user configuration.
        Get this OID always return zero.
            1 - restore.
            0 - do nothing. "
	::= { sw0657841SaveRestore 4 }




sw0657841ConfigFile           	OBJECT IDENTIFIER ::= { sw0657841Configuration 2 }

sw0657841ExportIpAddress OBJECT-TYPE
	SYNTAX      IpAddress
	MAX-ACCESS	    read-write
	STATUS		current
	DESCRIPTION
		"Get/Set the export tftp server."
	::= { sw0657841ConfigFile 1 }

sw0657841DoExportConfig OBJECT-TYPE
	SYNTAX      INTEGER(1|2)
	MAX-ACCESS	    read-write
	STATUS		current
	DESCRIPTION
		"Do export-config.
        Get this OID always return zero.
			1	-	export current section.
			2	-	export user section."
	::= { sw0657841ConfigFile 2 }

sw0657841ImportIpAddress OBJECT-TYPE
	SYNTAX      IpAddress
	MAX-ACCESS	    read-write
	STATUS		current
	DESCRIPTION
		"Get/Set the import tftp server."
	::= { sw0657841ConfigFile 3 }

sw0657841ImportConfigName OBJECT-TYPE
	SYNTAX      DisplayString
	MAX-ACCESS	    read-write
	STATUS		current
	DESCRIPTION
        "Get/Set the import file path and name."
	::= { sw0657841ConfigFile 4 }

sw0657841DoImportConfig OBJECT-TYPE
	SYNTAX      INTEGER(1|2)
	MAX-ACCESS	    read-write
	STATUS		current
	DESCRIPTION
		"Do import-config.
        Get this OID always return zero.
			1	-	import current section.
			2	-	import user section."
	::= { sw0657841ConfigFile 5 }




sw0657841Log           	OBJECT IDENTIFIER ::= { sw0657841Produces 7 }

sw0657841ClearLog OBJECT-TYPE
	SYNTAX      INTEGER(0|1)
	MAX-ACCESS	    read-write
	STATUS		current
	DESCRIPTION
		"Clear system log.
        Get this OID always return zero.
            1 - clear log.
            0 - do nothing. "
	::= { sw0657841Log 1 }


sw0657841LogNumber OBJECT-TYPE
	SYNTAX      INTEGER(0..120)
	MAX-ACCESS	    read-only
	STATUS		current
	DESCRIPTION
		"Get the number of current system log. "
	::= { sw0657841Log 4 }

sw0657841LogTable	OBJECT-TYPE
	SYNTAX		SEQUENCE OF SW0657841LogEntry
	MAX-ACCESS	not-accessible
	STATUS		current
    DESCRIPTION
        "This is a list of log entry. The numbers of entries are given by the value of sw0657841LogNumber."
	::= { sw0657841Log 5 }

SW0657841LogEntry ::=
SEQUENCE {
    sw0657841LogIndex		    INTEGER,
    sw0657841LogEvent           	DisplayString
}

sw0657841LogEntry	OBJECT-TYPE
	SYNTAX		SW0657841LogEntry
	MAX-ACCESS	    not-accessible
	STATUS		current
	DESCRIPTION
		"This is the Entry information for system log."
	INDEX {sw0657841LogIndex}
	::= { sw0657841LogTable 1 }

sw0657841LogIndex	OBJECT-TYPE
	SYNTAX		INTEGER(1..120)
	MAX-ACCESS	    not-accessible
	STATUS		current
	DESCRIPTION
		"This is the index of the log entry."
	::= { sw0657841LogEntry 1 }

sw0657841LogEvent	OBJECT-TYPE
	SYNTAX		DisplayString
	MAX-ACCESS	    read-only
	STATUS		current
	DESCRIPTION
		"This is the detail information of the log entry."
	::= { sw0657841LogEntry 2 }



sw0657841Firmware           	OBJECT IDENTIFIER ::= { sw0657841Produces 8 }

sw0657841FirmwareIpAddress OBJECT-TYPE
	SYNTAX      IpAddress
	MAX-ACCESS	    read-write
	STATUS		current
	DESCRIPTION
		"Get/Set the firmware tftp server."
	::= { sw0657841Firmware 1 }

sw0657841FirmwareFileName OBJECT-TYPE
	SYNTAX      DisplayString
	MAX-ACCESS	    read-write
	STATUS		current
	DESCRIPTION
		"Get/Set the path and filename for firmware upgrading."
	::= { sw0657841Firmware 2 }

sw0657841DoFirmwareUpgrade OBJECT-TYPE
	SYNTAX      INTEGER(0|1)
	MAX-ACCESS	    read-write
	STATUS		current
	DESCRIPTION
		"Do firmware upgrade. Get this OID always return zero.
            1 - do firmware upgrade.
            0 - do nothing."
	::= { sw0657841Firmware 3 }



sw0657841Port           	OBJECT IDENTIFIER ::= { sw0657841Produces 9 }

sw0657841PortStatus           	OBJECT IDENTIFIER ::= { sw0657841Port 1 }

sw0657841PortStatusNumber OBJECT-TYPE
	SYNTAX      INTEGER(1..2147483647)
	MAX-ACCESS	    read-only
	STATUS		current
	DESCRIPTION
		"Get the number of port."
	::= { sw0657841PortStatus 1 }

sw0657841PortStatusTable	OBJECT-TYPE
	SYNTAX		SEQUENCE OF SW0657841PortStatusEntry
	MAX-ACCESS	not-accessible
	STATUS		current
    DESCRIPTION
        "This is a list of port status entry. The numbers of entries are given by the value of sw0657841PortStatusNumber."
	::= { sw0657841PortStatus 2 }

SW0657841PortStatusEntry ::=
SEQUENCE {
    sw0657841PortStatusIndex		    INTEGER,
    sw0657841PortStatusMedia          DisplayString,
    sw0657841PortStatusLink           DisplayString,
    sw0657841PortStatusSpdDpx         DisplayString,
    sw0657841PortStatusFlwCtrlRx      DisplayString,
    sw0657841PortStatusFlwCtrlTx      DisplayString,
    sw0657841PortStatuDescription     DisplayString
}

sw0657841PortStatusEntry	OBJECT-TYPE
	SYNTAX		SW0657841PortStatusEntry
	MAX-ACCESS	    not-accessible
	STATUS		current
	DESCRIPTION
		"This is the entry(s) for port status information."
	INDEX {sw0657841PortStatusIndex}
	::= { sw0657841PortStatusTable 1 }

sw0657841PortStatusIndex	OBJECT-TYPE
	SYNTAX		INTEGER(1..2147483647)
	MAX-ACCESS	    read-only
	STATUS		current
	DESCRIPTION
		"This is the index of the port status entry."
	::= { sw0657841PortStatusEntry 1 }

sw0657841PortStatusMedia	OBJECT-TYPE
	SYNTAX		DisplayString
	MAX-ACCESS	    read-only
	STATUS		current
	DESCRIPTION
		"The port media type of the port status entry."
	::= { sw0657841PortStatusEntry 2 }

sw0657841PortStatusLink	OBJECT-TYPE
	SYNTAX		DisplayString
	MAX-ACCESS	    read-only
	STATUS		current
	DESCRIPTION
		"This is the port link of the port status entry."
	::= { sw0657841PortStatusEntry 3 }

sw0657841PortStatusSpdDpx 	OBJECT-TYPE
	SYNTAX		DisplayString
	MAX-ACCESS	    read-only
	STATUS		current
	DESCRIPTION
		"This is the speed/duplex of the port status entry."
	::= { sw0657841PortStatusEntry 4 }

sw0657841PortStatusFlwCtrlRx 	OBJECT-TYPE
	SYNTAX		DisplayString
	MAX-ACCESS	    read-only
	STATUS		current
	DESCRIPTION
		"This is the Rx flow control of the port status entry."
	::= { sw0657841PortStatusEntry 5 }

sw0657841PortStatusFlwCtrlTx 	OBJECT-TYPE
	SYNTAX		DisplayString
	MAX-ACCESS	    read-only
	STATUS		current
	DESCRIPTION
		"This is the Tx flow control of the port status entry."
	::= { sw0657841PortStatusEntry 6 }

sw0657841PortStatuDescription	OBJECT-TYPE
	SYNTAX		DisplayString
	MAX-ACCESS	    read-only
	STATUS		current
	DESCRIPTION
		"This is the description of port."
	::= { sw0657841PortStatusEntry 7 }

sw0657841PortConf           	OBJECT IDENTIFIER ::= { sw0657841Port 2 }

sw0657841PortConfNumber OBJECT-TYPE
	SYNTAX      INTEGER(1..2147483647)
	MAX-ACCESS	    read-only
	STATUS		current
	DESCRIPTION
		"Get the number of port configuration."
	::= { sw0657841PortConf 1 }

sw0657841PortConfTable	OBJECT-TYPE
	SYNTAX		SEQUENCE OF SW0657841PortConfEntry
	MAX-ACCESS	not-accessible
	STATUS		current
    DESCRIPTION
        "This is a list of port configuration entry. The numbers of entries are given by the value of sw0657841PortConfNumber."
	::= { sw0657841PortConf 2 }

SW0657841PortConfEntry ::=
SEQUENCE {
    sw0657841PortConfIndex		    INTEGER,
    sw0657841PortConfPortState        INTEGER,
    sw0657841PortConfSpdDpx           INTEGER,
    sw0657841PortConfFlwCtrl          INTEGER,
    sw0657841PortConfExcessiveCollisionMode      INTEGER,
    sw0657841PortConfDescription      DisplayString
}

sw0657841PortConfEntry	OBJECT-TYPE
	SYNTAX		SW0657841PortConfEntry
	MAX-ACCESS	    not-accessible
	STATUS		current
	DESCRIPTION
		"This is the Entry(s) for port configuration information."
	INDEX {sw0657841PortConfIndex}
	::= { sw0657841PortConfTable 1 }

sw0657841PortConfIndex	OBJECT-TYPE
	SYNTAX		INTEGER(1..2147483647)
	MAX-ACCESS	    read-only
	STATUS		current
	DESCRIPTION
		"This is the index of the port configuration entry."
	::= { sw0657841PortConfEntry 1 }

sw0657841PortConfPortState	OBJECT-TYPE
	SYNTAX		INTEGER(0|1)
	MAX-ACCESS	    read-write
	STATUS		current
	DESCRIPTION
		"This is the port state of the port configuration entry.
		 0 - disabled.
		 1 - enabled. "
	::= { sw0657841PortConfEntry 2 }

sw0657841PortConfSpdDpx	OBJECT-TYPE
	SYNTAX		INTEGER(0..5)
	MAX-ACCESS	    read-write
	STATUS		current
	DESCRIPTION
		"This is the speed/duplex of the port configuration entry.
		 0 - auto.
		 1 - 10M/Half.
		 2 - 10M/Full.
		 3 - 100M/Half.
		 4 - 100M/Full.
		 5 - 1G/Full.  "
	::= { sw0657841PortConfEntry 3 }

sw0657841PortConfFlwCtrl	OBJECT-TYPE
	SYNTAX		INTEGER(0|1)
	MAX-ACCESS	    read-write
	STATUS		current
	DESCRIPTION
		"This is the flow control of the port configuration entry.
		 0 - disabled.
		 1 - enabled.  "
	::= { sw0657841PortConfEntry 4 }

sw0657841PortConfExcessiveCollisionMode	OBJECT-TYPE
	SYNTAX		INTEGER(0|1)
	MAX-ACCESS	    read-write
	STATUS		current
	DESCRIPTION
		"
		 0 - Discard.
		 1 - Restart.  "
	::= { sw0657841PortConfEntry 5 }

sw0657841PortConfDescription	OBJECT-TYPE
	SYNTAX		DisplayString
	MAX-ACCESS	    read-write
	STATUS		current
	DESCRIPTION
		"This is the description of port."
	::= { sw0657841PortConfEntry 6 }

sw0657841SFPInfo           	OBJECT IDENTIFIER ::= { sw0657841Port 3 }

sw0657841SFPInfoNumber OBJECT-TYPE
	SYNTAX      INTEGER(1..2147483647)
	MAX-ACCESS	    read-only
	STATUS		current
	DESCRIPTION
		"Get the number of sfp info entry."
	::= { sw0657841SFPInfo 1 }

sw0657841SFPInfoTable	OBJECT-TYPE
	SYNTAX		SEQUENCE OF SW0657841SFPInfoEntry
	MAX-ACCESS	not-accessible
	STATUS		current
    DESCRIPTION
        "A list of sfp info entry. The numbers of entries are given by the value of sw0657841SFPInfoNumber."
	::= { sw0657841SFPInfo 2 }

SW0657841SFPInfoEntry ::=
SEQUENCE {
    sw0657841SFPInfoIndex INTEGER,
    sw0657841SFPConnectorType DisplayString,
    sw0657841SFPFiberType DisplayString,
    sw0657841SFPWavelength DisplayString,
    sw0657841SFPBaudRate DisplayString,
    sw0657841SFPVendorOUI DisplayString,
    sw0657841SFPVendorName DisplayString,
    sw0657841SFPVendorPN DisplayString,
    sw0657841SFPVendorRev DisplayString,
    sw0657841SFPVendorSN DisplayString,
    sw0657841SFPDateCode DisplayString,
    sw0657841SFPTemperature DisplayString,
    sw0657841SFPVcc DisplayString,
    sw0657841SFPTxBias DisplayString,
    sw0657841SFPTxPWR DisplayString,
    sw0657841SFPRxPWR DisplayString
}

sw0657841SFPInfoEntry	OBJECT-TYPE
	SYNTAX		SW0657841SFPInfoEntry
	MAX-ACCESS	    not-accessible
	STATUS		current
	DESCRIPTION
		"Entry(s) for SFP information."
	INDEX {sw0657841SFPInfoIndex}
	::= { sw0657841SFPInfoTable 1 }

sw0657841SFPInfoIndex	OBJECT-TYPE
	SYNTAX		INTEGER(1..2147483647)
	MAX-ACCESS	    read-only
	STATUS		current
	DESCRIPTION
		"The index of the sfp info entry."
	::= { sw0657841SFPInfoEntry 1 }

sw0657841SFPConnectorType	OBJECT-TYPE
	SYNTAX		DisplayString
	MAX-ACCESS	    read-only
	STATUS		current
	DESCRIPTION
		"Get connector type of the sfp."
	::= { sw0657841SFPInfoEntry 2 }

sw0657841SFPFiberType	OBJECT-TYPE
	SYNTAX		DisplayString
	MAX-ACCESS	    read-only
	STATUS		current
	DESCRIPTION
		"Get fiber type of the sfp."
	::= { sw0657841SFPInfoEntry 3 }

sw0657841SFPWavelength	OBJECT-TYPE
	SYNTAX		DisplayString
	MAX-ACCESS	    read-only
	STATUS		current
	DESCRIPTION
		"Get tx central wavelength of the sfp."
	::= { sw0657841SFPInfoEntry 4 }

sw0657841SFPBaudRate	OBJECT-TYPE
	SYNTAX		DisplayString
	MAX-ACCESS	    read-only
	STATUS		current
	DESCRIPTION
		"Get baud rate of the sfp."
	::= { sw0657841SFPInfoEntry 5 }

sw0657841SFPVendorOUI	OBJECT-TYPE
	SYNTAX		DisplayString
	MAX-ACCESS	    read-only
	STATUS		current
	DESCRIPTION
		"Get vendor OUI of the sfp."
	::= { sw0657841SFPInfoEntry 6 }

sw0657841SFPVendorName	OBJECT-TYPE
	SYNTAX		DisplayString
	MAX-ACCESS	    read-only
	STATUS		current
	DESCRIPTION
		"Get vendor name of the sfp."
	::= { sw0657841SFPInfoEntry 7 }

sw0657841SFPVendorPN	OBJECT-TYPE
	SYNTAX		DisplayString
	MAX-ACCESS	    read-only
	STATUS		current
	DESCRIPTION
		"Get vendor part number of the sfp."
	::= { sw0657841SFPInfoEntry 8 }

sw0657841SFPVendorRev	OBJECT-TYPE
	SYNTAX		DisplayString
	MAX-ACCESS	    read-only
	STATUS		current
	DESCRIPTION
		"Get vendor revision number of the sfp."
	::= { sw0657841SFPInfoEntry 9 }

sw0657841SFPVendorSN	OBJECT-TYPE
	SYNTAX		DisplayString
	MAX-ACCESS	    read-only
	STATUS		current
	DESCRIPTION
		"Get vendor serial number of the sfp."
	::= { sw0657841SFPInfoEntry 10 }

sw0657841SFPDateCode	OBJECT-TYPE
	SYNTAX		DisplayString
	MAX-ACCESS	    read-only
	STATUS		current
	DESCRIPTION
		"Get data code of the sfp."
	::= { sw0657841SFPInfoEntry 11 }

sw0657841SFPTemperature	OBJECT-TYPE
	SYNTAX		DisplayString
	MAX-ACCESS	    read-only
	STATUS		current
	DESCRIPTION
		"Get current temperature of the sfp."
	::= { sw0657841SFPInfoEntry 12 }

sw0657841SFPVcc	OBJECT-TYPE
	SYNTAX		DisplayString
	MAX-ACCESS	    read-only
	STATUS		current
	DESCRIPTION
		"Get current internal supply voltage of the sfp."
	::= { sw0657841SFPInfoEntry 13 }

sw0657841SFPTxBias	OBJECT-TYPE
	SYNTAX		DisplayString
	MAX-ACCESS	    read-only
	STATUS		current
	DESCRIPTION
		"Get current TX Bias of the sfp."
	::= { sw0657841SFPInfoEntry 14 }

sw0657841SFPTxPWR	OBJECT-TYPE
	SYNTAX		DisplayString
	MAX-ACCESS	    read-only
	STATUS		current
	DESCRIPTION
		"Get current TX output power of the sfp."
	::= { sw0657841SFPInfoEntry 15 }

sw0657841SFPRxPWR	OBJECT-TYPE
	SYNTAX		DisplayString
	MAX-ACCESS	    read-only
	STATUS		current
	DESCRIPTION
		"Get current Received Power of the sfp."
	::= { sw0657841SFPInfoEntry 16 }

sw0657841Mirror           	OBJECT IDENTIFIER ::= { sw0657841Produces 10 }

sw0657841MirroringPort OBJECT-TYPE
	SYNTAX      INTEGER(0..2147483647)
	MAX-ACCESS	    read-write
	STATUS		current
	DESCRIPTION
		"Get/Set the mirroring port.
		 The port range is from 1 to 16."
	::= { sw0657841Mirror 1 }

sw0657841MirroredPortsTable	OBJECT-TYPE
	SYNTAX		SEQUENCE OF SW0657841MirroredPortsEntry
	MAX-ACCESS	not-accessible
	STATUS		current
    DESCRIPTION
        "This is a list of port configuration entry. The numbers of entries are given by the value of sw0657841PortConfNumber."
	::= { sw0657841Mirror 2 }

SW0657841MirroredPortsEntry ::=
SEQUENCE {
    sw0657841MirroredPortIndex		    	INTEGER,
    sw0657841MirroredPortSrouceEnable        	INTEGER,
    sw0657841MirroredPortDestinationEnable        INTEGER
}

sw0657841MirroredPortsEntry	OBJECT-TYPE
	SYNTAX		SW0657841MirroredPortsEntry
	MAX-ACCESS	    not-accessible
	STATUS		current
	DESCRIPTION
		"This is the Entry(s) for port configuration information."
	INDEX {sw0657841MirroredPortIndex}
	::= { sw0657841MirroredPortsTable 1 }

sw0657841MirroredPortIndex	OBJECT-TYPE
	SYNTAX		INTEGER(1..24)
	MAX-ACCESS	    read-only
	STATUS		current
	DESCRIPTION
		"This is the index of the mirrored port."
	::= { sw0657841MirroredPortsEntry 1 }

sw0657841MirroredPortSrouceEnable	OBJECT-TYPE
	SYNTAX		INTEGER(0|1)
	MAX-ACCESS	    read-write
	STATUS		current
	DESCRIPTION
		"0 - disabled.
		 1 - enabled."
	::= { sw0657841MirroredPortsEntry 2 }
	
sw0657841MirroredPortDestinationEnable	OBJECT-TYPE
	SYNTAX		INTEGER(0|1)
	MAX-ACCESS	    read-write
	STATUS		current
	DESCRIPTION
		"0 - disabled.
		 1 - enabled."
	::= { sw0657841MirroredPortsEntry 3 }

sw0657841MaxPktLen           	OBJECT IDENTIFIER ::= { sw0657841Produces 11 }

sw0657841MaxPktLenPortNumber OBJECT-TYPE
	SYNTAX      INTEGER(1..24)
	MAX-ACCESS	    read-only
	STATUS		current
	DESCRIPTION
		"Get the number of Max. packet length."
	::= { sw0657841MaxPktLen 1 }

sw0657841MaxPktLenConfTable	OBJECT-TYPE
	SYNTAX		SEQUENCE OF SW0657841MaxPktLenConfEntry
	MAX-ACCESS	not-accessible
	STATUS		current
    DESCRIPTION
        "This is a list of Max. packet length entry. The numbers of entries are given by the value of sw0657841MaxPktLenPortNumber."
	::= { sw0657841MaxPktLen 2 }

SW0657841MaxPktLenConfEntry ::=
SEQUENCE {
    sw0657841MaxPktLenConfIndex		    INTEGER,
    sw0657841MaxPktLenConfSetting         INTEGER
}

sw0657841MaxPktLenConfEntry	OBJECT-TYPE
	SYNTAX		SW0657841MaxPktLenConfEntry
	MAX-ACCESS	    not-accessible
	STATUS		current
	DESCRIPTION
		"Entry(s) for Max. packet length information."
	INDEX {sw0657841MaxPktLenConfIndex}
	::= { sw0657841MaxPktLenConfTable 1 }

sw0657841MaxPktLenConfIndex	OBJECT-TYPE
	SYNTAX		INTEGER(1..24)
	MAX-ACCESS	    read-only
	STATUS		current
	DESCRIPTION
		"This is the index of the Max. packet length entry."
	::= { sw0657841MaxPktLenConfEntry 1 }

sw0657841MaxPktLenConfSetting	OBJECT-TYPE
	SYNTAX		INTEGER(1518..9600)
	MAX-ACCESS	    read-write
	STATUS		current
	DESCRIPTION
		"Get/Set the Max. packet length.
		 The Max. packet length is 1518~9600.  "
	::= { sw0657841MaxPktLenConfEntry 2 }

sw0657841LoopDetectedConf           	OBJECT IDENTIFIER ::= { sw0657841Produces 12 }

sw0657841LoopDetectedNumber OBJECT-TYPE
	SYNTAX      INTEGER(1..2147483647)
	MAX-ACCESS	    read-only
	STATUS		current
	DESCRIPTION
		"Get the number of loop detected entry."
	::= { sw0657841LoopDetectedConf 1 }

sw0657841LoopDetectedTable	OBJECT-TYPE
	SYNTAX		SEQUENCE OF SW0657841LoopDetectedEntry
	MAX-ACCESS	not-accessible
	STATUS		current
    DESCRIPTION
        "A list of loop detected entry. The numbers of entries are given by the value of sw0657841LoopDetectedNumber."
	::= { sw0657841LoopDetectedConf 2 }

SW0657841LoopDetectedEntry ::=
SEQUENCE {
    sw0657841LoopDetectedfIndex           INTEGER,
    sw0657841LoopDetectedPort             INTEGER,
    sw0657841LoopDetectedLockedPort       INTEGER
}

sw0657841LoopDetectedEntry	OBJECT-TYPE
	SYNTAX		SW0657841LoopDetectedEntry
	MAX-ACCESS	    not-accessible
	STATUS		current
	DESCRIPTION
		"Entry(s) for loop detected information."
	INDEX {sw0657841LoopDetectedfIndex}
	::= { sw0657841LoopDetectedTable 1 }

sw0657841LoopDetectedfIndex	OBJECT-TYPE
	SYNTAX		INTEGER(1..2147483647)
	MAX-ACCESS	    read-only
	STATUS		current
	DESCRIPTION
		"The index of the loop detected entry."
	::= { sw0657841LoopDetectedEntry 1 }

sw0657841LoopDetectedPort	OBJECT-TYPE
	SYNTAX		INTEGER(0|1)
	MAX-ACCESS	    read-write
	STATUS		current
	DESCRIPTION
		"The state of the loop detected entry.
		 0 - disabled.
		 1 - enabled. "
	::= { sw0657841LoopDetectedEntry 2 }

sw0657841LoopDetectedLockedPort	OBJECT-TYPE
	SYNTAX		INTEGER(0|1)
	MAX-ACCESS	    read-write
	STATUS		current
	DESCRIPTION
		"The current status of the loop detected port.
		 Get:
         0 - unlocked
         1 - locked due to the loop condition 
         Set:
         0 - unlock the port
         1 - do nothing"
	::= { sw0657841LoopDetectedEntry 3 }


sw0657841ManagementPolicy           	OBJECT IDENTIFIER ::= { sw0657841Produces 13 }

sw0657841ManagementSecurityNumber OBJECT-TYPE
	SYNTAX      INTEGER(0..64)
	MAX-ACCESS	    read-only
	STATUS		current
	DESCRIPTION
		"This is the index of the management security entry."
	::= { sw0657841ManagementPolicy 1 }

sw0657841ManagementSecurityEntryCreate OBJECT-TYPE
	SYNTAX      INTEGER(0..64)
	MAX-ACCESS	    read-write
	STATUS		current
	DESCRIPTION
		"Create management security entry"
	::= { sw0657841ManagementPolicy 2 }

sw0657841ManagementSecurityTable	OBJECT-TYPE
	SYNTAX		SEQUENCE OF SW0657841ManagementSecurityEntry
	MAX-ACCESS	not-accessible
	STATUS		current
    DESCRIPTION
        "This is a list of SW0657841ManagementSecurityEntry. The numbers of entries are given by ManagementSecurityNumber."
	::= { sw0657841ManagementPolicy 3 }

SW0657841ManagementSecurityEntry ::=
SEQUENCE {
    sw0657841ManagementSecurityIndex		       INTEGER,
    sw0657841ManagementSecurityName            DisplayString,
    sw0657841ManagementSecurityIpRange         DisplayString,
    sw0657841ManagementSecurityIncomigPort     DisplayString,
    sw0657841ManagementSecurityAccessType      DisplayString,
    sw0657841ManagementSecurityAction          INTEGER,
    sw0657841ManagementSecurityEntryAction     INTEGER
}

sw0657841ManagementSecurityEntry	OBJECT-TYPE
	SYNTAX		SW0657841ManagementSecurityEntry
	MAX-ACCESS	    not-accessible
	STATUS		current
	DESCRIPTION
		"This is the Entry(s) for Management Security configuration information."
	INDEX {sw0657841ManagementSecurityIndex}
	::= { sw0657841ManagementSecurityTable 1 }

sw0657841ManagementSecurityIndex	OBJECT-TYPE
	SYNTAX		INTEGER(1..64)
	MAX-ACCESS	    read-only
	STATUS		current
	DESCRIPTION
		"This is the index of the management policy configuration entry."
	::= { sw0657841ManagementSecurityEntry 1 }

sw0657841ManagementSecurityName	OBJECT-TYPE
	SYNTAX		DisplayString
	MAX-ACCESS	    read-write
	STATUS		current
	DESCRIPTION
		"This is the username of the management security entry."
	::= { sw0657841ManagementSecurityEntry 2 }

sw0657841ManagementSecurityIpRange	OBJECT-TYPE
	SYNTAX		DisplayString
	MAX-ACCESS	    read-write
	STATUS		current
	DESCRIPTION
		"This is the ip range of the management security entry."
	::= { sw0657841ManagementSecurityEntry 3 }

sw0657841ManagementSecurityIncomigPort	OBJECT-TYPE
	SYNTAX		DisplayString
	MAX-ACCESS	    read-write
	STATUS		current
	DESCRIPTION
		"This is the incoming port of the management security entry."
	::= { sw0657841ManagementSecurityEntry 4 }

sw0657841ManagementSecurityAccessType	OBJECT-TYPE
	SYNTAX		DisplayString
	MAX-ACCESS	    read-write
	STATUS		current
	DESCRIPTION
		"
		 0 - any.
		 1 - http. 
		 2 - telnet
		 3 - snmp"
	::= { sw0657841ManagementSecurityEntry 5 }
	
sw0657841ManagementSecurityAction	OBJECT-TYPE
	SYNTAX		INTEGER(0|1)
	MAX-ACCESS	    read-write
	STATUS		current
	DESCRIPTION
		"
		 0 - deny.
		 1 - accept."
	::= { sw0657841ManagementSecurityEntry 6 }
	
sw0657841ManagementSecurityEntryAction	OBJECT-TYPE
	SYNTAX		INTEGER(1..3)
	MAX-ACCESS	    read-write
	STATUS		current
	DESCRIPTION
		"
		 1 - active.
		 2 - notInService.
		 3 - delete."
	::= { sw0657841ManagementSecurityEntry 7 }



sw0657841VLAN           	OBJECT IDENTIFIER ::= { sw0657841Produces 14 }

sw0657841VlanConf           	OBJECT IDENTIFIER ::= { sw0657841VLAN 1 }

sw0657841VlanMode OBJECT-TYPE
	SYNTAX      INTEGER(0|1)
	MAX-ACCESS	    read-write
	STATUS		current
	DESCRIPTION
		"This is the VLAN Mode configuration, default is tag base.
		 0 - tag-base
		 1 - port-base"
	::= { sw0657841VlanConf 1 }
	
sw0657841ManagementVlan OBJECT-TYPE
	SYNTAX      INTEGER(1..4094)
	MAX-ACCESS	    read-write
	STATUS		current
	DESCRIPTION
		"To specify a vlan id that can communicate with the device."
	::= { sw0657841VlanConf 2 }
	
sw0657841PortIsolation OBJECT-TYPE
	SYNTAX      DisplayString
	MAX-ACCESS	    read-write
	STATUS		current
	DESCRIPTION
		"Selected port(s) only can communicate with unselected port(s).
		Selected port(s) will be isolated with each other."
	::= { sw0657841VlanConf 3 }

sw0657841TagBaseVlanGroup        	OBJECT IDENTIFIER ::= { sw0657841VLAN 2 }

sw0657841TagBaseVlanNumber OBJECT-TYPE
	SYNTAX      INTEGER(1..4094)
	MAX-ACCESS	    read-write
	STATUS		current
	DESCRIPTION
		"The number of tagged-based VLAN."
	::= { sw0657841TagBaseVlanGroup 1 }

sw0657841TagBaseVlanGroupEntryCreate OBJECT-TYPE
	SYNTAX      INTEGER(0..4094)
	MAX-ACCESS	    read-write
	STATUS		current
	DESCRIPTION
		"To create a VLAN entry in the tagged-based VLAN table.
         0 : none,
         1~4094 : specify the vid of the created VLAN."
	::= { sw0657841TagBaseVlanGroup 2 }

sw0657841TagBaseVlanGroupTable	OBJECT-TYPE
	SYNTAX		SEQUENCE OF SW0657841TagBaseVlanGroupEntry
	MAX-ACCESS	not-accessible
	STATUS		current
    DESCRIPTION
        "A list of tagged-based VLAN group entry. The number of entries can be taked from sw0657841TagBaseVlanNumber."
	::= { sw0657841TagBaseVlanGroup 3 }

SW0657841TagBaseVlanGroupEntry ::=
SEQUENCE {
    sw0657841TagBaseVlanVid		        INTEGER,
    sw0657841TagBaseVlanName          DisplayString,
    sw0657841TagBaseVlanIgmpProxy     INTEGER,
    sw0657841TagBaseVlanPrivateVlan   INTEGER,
    sw0657841TagBaseVlanGvrp   		INTEGER,    
    sw0657841TagBaseVlanMemberPort    DisplayString,
    sw0657841TagBaseVlanEntryAction   INTEGER
}

sw0657841TagBaseVlanGroupEntry	OBJECT-TYPE
	SYNTAX		SW0657841TagBaseVlanGroupEntry
	MAX-ACCESS	    not-accessible
	STATUS		current
	DESCRIPTION
		"This is the entry(s) for tagged-based VLAN group configuration."
	INDEX {sw0657841TagBaseVlanVid}
	::= { sw0657841TagBaseVlanGroupTable 1 }

sw0657841TagBaseVlanVid	OBJECT-TYPE
	SYNTAX		INTEGER(1..4094)
	MAX-ACCESS	    not-accessible
	STATUS		current
	DESCRIPTION
		"This is the index of the tagged-based VLAN group configuration entry."
	::= { sw0657841TagBaseVlanGroupEntry 1 }

sw0657841TagBaseVlanName	OBJECT-TYPE
	SYNTAX		DisplayString
	MAX-ACCESS	    read-write
	STATUS		current
	DESCRIPTION
		"This is the name of the VLAN."
	::= { sw0657841TagBaseVlanGroupEntry 2 }

sw0657841TagBaseVlanIgmpProxy	OBJECT-TYPE
	SYNTAX		INTEGER(0|1)
	MAX-ACCESS	    read-write
	STATUS		current
	DESCRIPTION
		"To support IGMP proxy in this VLAN.
		 0 - Disable
		 1 - Enable"

	::= { sw0657841TagBaseVlanGroupEntry 3 }

sw0657841TagBaseVlanPrivateVlan	OBJECT-TYPE
	SYNTAX		INTEGER(0|1)
	MAX-ACCESS	    read-write
	STATUS		current
	DESCRIPTION
		"To apply the port isolation configuration.
		 0 - Disable
		 1 - Enable"
	::= { sw0657841TagBaseVlanGroupEntry 4 }
	
sw0657841TagBaseVlanGvrp	OBJECT-TYPE
	SYNTAX		INTEGER(0|1)
	MAX-ACCESS	    read-write
	STATUS		current
	DESCRIPTION
		"This VLAN can be propagated by gvrp.
		 0 - Disable
		 1 - Enable"
	::= { sw0657841TagBaseVlanGroupEntry 5 }	

sw0657841TagBaseVlanMemberPort	OBJECT-TYPE
	SYNTAX		DisplayString
	MAX-ACCESS	    read-write
	STATUS		current
	DESCRIPTION
		"The member port(s) of this VLAN."
	::= { sw0657841TagBaseVlanGroupEntry 6 }

sw0657841TagBaseVlanEntryAction	OBJECT-TYPE
	SYNTAX		INTEGER(1..3)
	MAX-ACCESS	    read-write
	STATUS		current
	DESCRIPTION
		"The row status of VLAN.
		 1 - active 
		 2 - notInService 
		 3 - delete"
	::= { sw0657841TagBaseVlanGroupEntry 7 }

sw0657841VlanPortConfTable	OBJECT-TYPE
	SYNTAX		SEQUENCE OF SW0657841VlanPortConfEntry
	MAX-ACCESS	not-accessible
	STATUS		current
    DESCRIPTION
        "This is the port parameters for tagged-based VLAN."
	::= { sw0657841VLAN 3 }
	
SW0657841VlanPortConfEntry ::=
SEQUENCE {
    sw0657841VlanPortConfIndex		            INTEGER,
    sw0657841VlanPortConfVlanAware            INTEGER,
    sw0657841VlanPortConfIngressFiltering     INTEGER,
    sw0657841VlanPortConfFrameType            INTEGER,
    sw0657841VlanPortConfPvid                 INTEGER,
    sw0657841VlanPortConfRole                 INTEGER,
    sw0657841VlanPortConfUntagVid             INTEGER,
    sw0657841VlanPortConfDoubleTag            INTEGER
}
	
sw0657841VlanPortConfEntry	OBJECT-TYPE
	SYNTAX		SW0657841VlanPortConfEntry
	MAX-ACCESS	    not-accessible
	STATUS		current
	DESCRIPTION
		"These are the tagged-based VLAN parameters for each ports."
	INDEX {sw0657841VlanPortConfIndex}
	::= { sw0657841VlanPortConfTable 1 }
	
sw0657841VlanPortConfIndex	OBJECT-TYPE
	SYNTAX		INTEGER(1..24)
	MAX-ACCESS	    not-accessible
	STATUS		current
	DESCRIPTION
		"This is the index of the tagged-based vlan port parameters."
	::= { sw0657841VlanPortConfEntry 1 }

sw0657841VlanPortConfVlanAware	OBJECT-TYPE
	SYNTAX		INTEGER(0|1)
	MAX-ACCESS	    read-write
	STATUS		current
	DESCRIPTION
		"
		 0 - Ignore incoming VLAN tag, using pvid as VLAN classification.
		 1 - Using VLAN tag information first."
	::= { sw0657841VlanPortConfEntry 2 }

sw0657841VlanPortConfIngressFiltering	OBJECT-TYPE
	SYNTAX		INTEGER(0|1)
	MAX-ACCESS	    read-write
	STATUS		current
	DESCRIPTION
		"If the packet is tagged with VLAN information, the ingress port will first determine if the
		 ingress port itself is a member of the tagged VLAN.
		 0 - Disable, don't care about the VLAN information of the packet.
		 1 - Enable."
	::= { sw0657841VlanPortConfEntry 3 }

sw0657841VlanPortConfFrameType	OBJECT-TYPE
	SYNTAX		INTEGER(0|1)
	MAX-ACCESS	    read-write
	STATUS		current
	DESCRIPTION
		"To determine what kind of packet the port should accept.
		 0 - All
		 1 - Only tagged packet"
	::= { sw0657841VlanPortConfEntry 4 }

sw0657841VlanPortConfPvid	OBJECT-TYPE
	SYNTAX		INTEGER(1..4094)
	MAX-ACCESS	    read-write
	STATUS		current
	DESCRIPTION
		"Each physical port has a parameter called PVID.
		All untagged frames are assigned to the LAN specified in the PVID parameter.
		When a tagged frame is received by a port, the tag is respected.
		If the frame is untagged, the value contained in the PVID is considered as a tag. "
	::= { sw0657841VlanPortConfEntry 5 }

sw0657841VlanPortConfRole	OBJECT-TYPE
	SYNTAX		INTEGER(0..2)
	MAX-ACCESS	    read-write
	STATUS		current
	DESCRIPTION
		"
		 0 - Access: won't send packet with tag.
		 1 - Trunk: always send packet with tag.
		 2 - Hybrid: always send packet with tag but one."
	::= { sw0657841VlanPortConfEntry 6 }

sw0657841VlanPortConfUntagVid	OBJECT-TYPE
	SYNTAX		INTEGER(1..4094)
	MAX-ACCESS	    read-write
	STATUS		current
	DESCRIPTION
		"Won't send packet with tag in one specific vid. Only available in hybrid mode.
		 "
	::= { sw0657841VlanPortConfEntry 7 }
	
sw0657841VlanPortConfDoubleTag	OBJECT-TYPE
	SYNTAX		INTEGER(0..2)
	MAX-ACCESS	    read-write
	STATUS		current
	DESCRIPTION
		"This is the double tag configuration for ports.
		 0 -- Disable,
		  1 -- Service,
		  2 -- Customer		 
		 "
	::= { sw0657841VlanPortConfEntry 8 }	

sw0657841PortBaseVlanGroup        	OBJECT IDENTIFIER ::= { sw0657841VLAN 4 }

sw0657841PortBaseVlanNumber OBJECT-TYPE
	SYNTAX      INTEGER(1..24)
	MAX-ACCESS	    read-write
	STATUS		current
	DESCRIPTION
		"Total numbers for port based vlan."
	::= { sw0657841PortBaseVlanGroup 1 }
	
sw0657841PortBaseVlanGroupEntryCreate OBJECT-TYPE
	SYNTAX      INTEGER(0..24)
	MAX-ACCESS	    read-write
	STATUS		current
	DESCRIPTION
		"Create a temp vlan in port-based vlan table.
         0 : none,
         1 : create a new port-based vlan."
	::= { sw0657841PortBaseVlanGroup 2 }

sw0657841PortBaseVlanGroupTable	OBJECT-TYPE
	SYNTAX		SEQUENCE OF SW0657841PortBaseVlanGroupEntry
	MAX-ACCESS	not-accessible
	STATUS		current
    DESCRIPTION
        "A list of port base vlan group entry. The numbers of entries are given by the value of sw0657841PortBaseVlanNumber."
	::= { sw0657841PortBaseVlanGroup 3 }

SW0657841PortBaseVlanGroupEntry ::=
SEQUENCE {
    sw0657841PortBaseVlanGroupIndex		      INTEGER,
    sw0657841PortBaseVlanGroupName          DisplayString,
    sw0657841PortBaseVlanGroupMembers       DisplayString,
    sw0657841PortBaseVlanGroupEntryAction   INTEGER
}

sw0657841PortBaseVlanGroupEntry	OBJECT-TYPE
	SYNTAX		SW0657841PortBaseVlanGroupEntry
	MAX-ACCESS	    not-accessible
	STATUS		current
	DESCRIPTION
		"This is the Entry(s) for Port Base VLAN Group configuration information."
	INDEX {sw0657841PortBaseVlanGroupIndex}
	::= { sw0657841PortBaseVlanGroupTable 1 }

sw0657841PortBaseVlanGroupIndex	OBJECT-TYPE
	SYNTAX		INTEGER(1..24)
	MAX-ACCESS	    not-accessible
	STATUS		current
	DESCRIPTION
		"This is the index of the Port Base VLAN Group configuration entry."
	::= { sw0657841PortBaseVlanGroupEntry 1 }
	
sw0657841PortBaseVlanGroupName	OBJECT-TYPE
	SYNTAX		DisplayString
	MAX-ACCESS	    read-write
	STATUS		current
	DESCRIPTION
		"The name of vlan."
	::= { sw0657841PortBaseVlanGroupEntry 2 }

sw0657841PortBaseVlanGroupMembers	OBJECT-TYPE
	SYNTAX		DisplayString
	MAX-ACCESS	    read-write
	STATUS		current
	DESCRIPTION
		"The member of vlan."
	::= { sw0657841PortBaseVlanGroupEntry 3 }

sw0657841PortBaseVlanGroupEntryAction	OBJECT-TYPE
	SYNTAX		INTEGER(1..3)
	MAX-ACCESS	    read-write
	STATUS		current
	DESCRIPTION
		"The row status of vlan.
         1 : active,
         2 : not-inService,
         3 : delete	"
	::= { sw0657841PortBaseVlanGroupEntry 4 }

sw0657841MacTableInfo           	OBJECT IDENTIFIER ::= { sw0657841Produces 15 }

sw0657841MacTableConf           	OBJECT IDENTIFIER ::= { sw0657841MacTableInfo 1 }

sw0657841MacAgeTime OBJECT-TYPE
	SYNTAX      INTEGER(10..1000000)
	MAX-ACCESS	    read-write
	STATUS		current
	DESCRIPTION
		"Set the Mac Table Aging Time (10~1000000 Secs).
         0 : Disable."
	::= { sw0657841MacTableConf 1 }
	
sw0657841MacTableLearningConfTable	OBJECT-TYPE
	SYNTAX		SEQUENCE OF SW0657841MacTableLearningConfEntry
	MAX-ACCESS	not-accessible
	STATUS		current
    DESCRIPTION
        "A list of Mac Learning entry."
	::= { sw0657841MacTableConf 2 }

SW0657841MacTableLearningConfEntry ::=
SEQUENCE {
    sw0657841MacTableLearningConfIndex   INTEGER,
    sw0657841MacTableLearningConfstate   INTEGER
}

sw0657841MacTableLearningConfEntry	OBJECT-TYPE
	SYNTAX		SW0657841MacTableLearningConfEntry
	MAX-ACCESS	    not-accessible
	STATUS		current
	DESCRIPTION
		"This is the Entry(s) for Mac Learning table information."
	INDEX {sw0657841MacTableLearningConfIndex}
	::= { sw0657841MacTableLearningConfTable 1 }
	
sw0657841MacTableLearningConfIndex	OBJECT-TYPE
	SYNTAX		INTEGER(1..24)
	MAX-ACCESS	    not-accessible
	STATUS		current
	DESCRIPTION
		"This is the index of the Learning MAC Table Group configuration entry."
	::= { sw0657841MacTableLearningConfEntry 1 }
	
sw0657841MacTableLearningConfstate	OBJECT-TYPE
	SYNTAX		INTEGER(0|1|2)
	MAX-ACCESS	    read-write
	STATUS		current
	DESCRIPTION
		"
		 0 - Auto 
		 1 - Disable
		 2 - Secure"
	::= { sw0657841MacTableLearningConfEntry 2 }

sw0657841MacTableStaticFilter           	OBJECT IDENTIFIER ::= { sw0657841MacTableInfo 2 }

sw0657841MacTableStaticFilterNumber OBJECT-TYPE
	SYNTAX      INTEGER(0..512)
	MAX-ACCESS	    read-only
	STATUS		current
	DESCRIPTION
		"Total numbers for static filter entry of Mac Table."
	::= { sw0657841MacTableStaticFilter 1 }
	
sw0657841MacTableStaticFilterEntryCreate OBJECT-TYPE
	SYNTAX      INTEGER(0..512)
	MAX-ACCESS	    read-write
	STATUS		current
	DESCRIPTION
		"Create a temp Filter entry in Mac Table.
         0 : none,
         1 : create a new entry"
	::= { sw0657841MacTableStaticFilter 2 }

sw0657841MacTableStaticFilterTable	OBJECT-TYPE
	SYNTAX		SEQUENCE OF SW0657841MacTableStaticFilterEntry
	MAX-ACCESS	not-accessible
	STATUS		current
    DESCRIPTION
        "A list of static filter entry. The numbers of entries are given by the value of sw0657841MacTableStaticFilterNumber."
	::= { sw0657841MacTableStaticFilter 3 }

SW0657841MacTableStaticFilterEntry ::=
SEQUENCE {
    sw0657841MacTableStaticFilterIndex         INTEGER,
    sw0657841MacTableStaticFilterMac           DisplayString,
    sw0657841MacTableStaticFilterVid           INTEGER,
    sw0657841MacTableStaticFilterAlias         DisplayString,
    sw0657841MacTableStaticFilterEntryAction   INTEGER
}

sw0657841MacTableStaticFilterEntry	OBJECT-TYPE
	SYNTAX		SW0657841MacTableStaticFilterEntry
	MAX-ACCESS	    not-accessible
	STATUS		current
	DESCRIPTION
		"This is the Entry(s) for static filter information."
	INDEX {sw0657841MacTableStaticFilterIndex}
	::= { sw0657841MacTableStaticFilterTable 1 }
	
sw0657841MacTableStaticFilterIndex	OBJECT-TYPE
	SYNTAX		INTEGER(1..512)
	MAX-ACCESS	    not-accessible
	STATUS		current
	DESCRIPTION
		"This is the index of the Static Filter MAC Table Group configuration entry."
	::= { sw0657841MacTableStaticFilterEntry 1 }

sw0657841MacTableStaticFilterMac	OBJECT-TYPE
	SYNTAX		DisplayString
	MAX-ACCESS	    read-write
	STATUS		current
	DESCRIPTION
		"The static filter mac in Mac Table"
	::= { sw0657841MacTableStaticFilterEntry 2 }

sw0657841MacTableStaticFilterVid	OBJECT-TYPE
	SYNTAX		INTEGER(1..4094)
	MAX-ACCESS	    read-write
	STATUS		current
	DESCRIPTION
		"The filter vid in Mac Table"
	::= { sw0657841MacTableStaticFilterEntry 3 }

sw0657841MacTableStaticFilterAlias	OBJECT-TYPE
	SYNTAX		DisplayString
	MAX-ACCESS	    read-write
	STATUS		current
	DESCRIPTION
		"The filter alias name in Mac Table"
	::= { sw0657841MacTableStaticFilterEntry 4 }

sw0657841MacTableStaticFilterEntryAction	OBJECT-TYPE
	SYNTAX		INTEGER(1..3)
	MAX-ACCESS	    read-write
	STATUS		current
	DESCRIPTION
		"The row status of filter entry.
		 1 - active
		 2 - notInService
		 3 - delete"
	::= { sw0657841MacTableStaticFilterEntry 5 }

sw0657841MacTableStaticForward           	OBJECT IDENTIFIER ::= { sw0657841MacTableInfo 3 }

sw0657841MacTableStaticForwardNumber OBJECT-TYPE
	SYNTAX      INTEGER(0..512)
	MAX-ACCESS	    read-only
	STATUS		current
	DESCRIPTION
		"Total numbers for static forward entry of Mac Table."
	::= { sw0657841MacTableStaticForward 1 }
	
sw0657841MacTableStaticForwardEntryCreate OBJECT-TYPE
	SYNTAX      INTEGER(0..512)
	MAX-ACCESS	    read-write
	STATUS		current
	DESCRIPTION
		"Create a temp forward entry in Mac Table.
         0 : none,
         1 : create a new entry"
	::= { sw0657841MacTableStaticForward 2 }
	
sw0657841MacTableStaticForwardTable	OBJECT-TYPE
	SYNTAX		SEQUENCE OF SW0657841MacTableStaticForwardEntry
	MAX-ACCESS	not-accessible
	STATUS		current
    DESCRIPTION
        "A list of static forward entry. The numbers of entries are given by the value of sw0657841MacTableStaticForwardNumber."
	::= { sw0657841MacTableStaticForward 3 }

SW0657841MacTableStaticForwardEntry ::=
SEQUENCE {
    sw0657841MacTableStaticForwardIndex         INTEGER,
    sw0657841MacTableStaticForwardMac           DisplayString,
    sw0657841MacTableStaticForwardPort          INTEGER,
    sw0657841MacTableStaticForwardVid           INTEGER,
    sw0657841MacTableStaticForwardAlias         DisplayString,
    sw0657841MacTableStaticForwardEntryAction   INTEGER
}

sw0657841MacTableStaticForwardEntry	OBJECT-TYPE
	SYNTAX		SW0657841MacTableStaticForwardEntry
	MAX-ACCESS	    not-accessible
	STATUS		current
	DESCRIPTION
		" "
	INDEX {sw0657841MacTableStaticForwardIndex}
	::= { sw0657841MacTableStaticForwardTable 1 }

sw0657841MacTableStaticForwardIndex	OBJECT-TYPE
	SYNTAX		INTEGER(1..512)
	MAX-ACCESS	    not-accessible
	STATUS		current
	DESCRIPTION
		"This is the index of the Static Forward MAC Table Group configuration entry."
	::= { sw0657841MacTableStaticForwardEntry 1 }

sw0657841MacTableStaticForwardMac	OBJECT-TYPE
	SYNTAX		DisplayString
	MAX-ACCESS	    read-write
	STATUS		current
	DESCRIPTION
		"The static forwarding Mac in Mac Table"

	::= { sw0657841MacTableStaticForwardEntry 2 }

sw0657841MacTableStaticForwardPort	OBJECT-TYPE
	SYNTAX		INTEGER(1..24)
	MAX-ACCESS	    read-write
	STATUS		current
	DESCRIPTION
		"To specify a destination port for a mac address in mac table."
	::= { sw0657841MacTableStaticForwardEntry 3 }

sw0657841MacTableStaticForwardVid	OBJECT-TYPE
	SYNTAX		INTEGER(1..4094)
	MAX-ACCESS	    read-write
	STATUS		current
	DESCRIPTION
		"To specify a VLAN ID for a mac address in mac table."
	::= { sw0657841MacTableStaticForwardEntry 4 }

sw0657841MacTableStaticForwardAlias	OBJECT-TYPE
	SYNTAX		DisplayString
	MAX-ACCESS	    read-write
	STATUS		current
	DESCRIPTION
		"To specify an alias for a mac address in mac table."
	::= { sw0657841MacTableStaticForwardEntry 5 }

sw0657841MacTableStaticForwardEntryAction	OBJECT-TYPE
	SYNTAX		INTEGER(1..3)
	MAX-ACCESS	    read-write
	STATUS		current
	DESCRIPTION
		"The row status of filter entry.
		 1 - active
		 2 - notInService
		 3 - delete"
	::= { sw0657841MacTableStaticForwardEntry 6 }

sw0657841MacAlias           	OBJECT IDENTIFIER ::= { sw0657841MacTableInfo 4 }

sw0657841MacAliasNumber OBJECT-TYPE
	SYNTAX      INTEGER(0..1024)
	MAX-ACCESS	    read-only
	STATUS		current
	DESCRIPTION
		"Mac Alias Total Nnumber(0~1024)."
	::= { sw0657841MacAlias 1 }

sw0657841MacAliasEntryCreate OBJECT-TYPE
	SYNTAX      INTEGER(0..1024)
	MAX-ACCESS	    read-only
	STATUS		current
	DESCRIPTION
		"Create a temp Mac alias entry in Mac Table.
         0 : none,
         1 : create a new entry"
	::= { sw0657841MacAlias 2 }
	
sw0657841MacAliasTable	OBJECT-TYPE
	SYNTAX		SEQUENCE OF SW0657841MacAliasEntry
	MAX-ACCESS	not-accessible
	STATUS		current
    DESCRIPTION
        "A list of Mac Alias entry. The numbers of entries are given by the value of sw0657841MacAliasNumber."
	::= { sw0657841MacAlias 3 }

SW0657841MacAliasEntry ::=
SEQUENCE {
    sw0657841MacAliasIndex         INTEGER,
    sw0657841AliasMac              DisplayString,
    sw0657841AliasName             DisplayString,
    sw0657841MacAliasEntryAction   INTEGER
}

sw0657841MacAliasEntry	OBJECT-TYPE
	SYNTAX		SW0657841MacAliasEntry
	MAX-ACCESS	    not-accessible
	STATUS		current
	DESCRIPTION
		"Entry(s) for Mac Alias."
	INDEX {sw0657841MacAliasIndex}
	::= { sw0657841MacAliasTable 1 }

sw0657841MacAliasIndex	OBJECT-TYPE
	SYNTAX		INTEGER(1..1024)
	MAX-ACCESS	    not-accessible
	STATUS		current
	DESCRIPTION
		"The index of the static mac alias entry."
	::= { sw0657841MacAliasEntry 1 }
	
sw0657841AliasMac	OBJECT-TYPE
	SYNTAX		DisplayString
	MAX-ACCESS	    read-write
	STATUS		current
	DESCRIPTION
		"The Mac of the static mac alias entry."
	::= { sw0657841MacAliasEntry 2 }
	
sw0657841AliasName	OBJECT-TYPE
	SYNTAX		DisplayString
	MAX-ACCESS	    read-write
	STATUS		current
	DESCRIPTION
		"The alias name of the static mac alias entry."
	::= { sw0657841MacAliasEntry 3 }
	
sw0657841MacAliasEntryAction	OBJECT-TYPE
	SYNTAX		INTEGER(1..3)
	MAX-ACCESS	    read-write
	STATUS		current
	DESCRIPTION
		"The row status of mac alias entry.
		 1 - active
		 2 - notInService
		 3 - delete"
	::= { sw0657841MacAliasEntry 4 }
	

sw0657841GVRPInfo           	OBJECT IDENTIFIER ::= { sw0657841Produces 16 }

sw0657841GvrpConf           	OBJECT IDENTIFIER ::= { sw0657841GVRPInfo 1 }

sw0657841GvrpConfState OBJECT-TYPE
	SYNTAX      INTEGER(0|1)
	MAX-ACCESS	    read-write
	STATUS		current
	DESCRIPTION
		"The GVRP state
		 0 - Disable
		 1 - Enable
    "
	::= { sw0657841GvrpConf 1 }

sw0657841GvrpConfTable	OBJECT-TYPE
	SYNTAX		SEQUENCE OF SW0657841GvrpConfEntry
	MAX-ACCESS	not-accessible
	STATUS		current
    DESCRIPTION
        "A list of GVRP entry."
	::= { sw0657841GvrpConf 2 }

SW0657841GvrpConfEntry ::=
SEQUENCE {
    sw0657841GvrpConfIndex             INTEGER,
    sw0657841GvrpConfJoinTime          INTEGER,
    sw0657841GvrpConfLeaveTime         INTEGER,
    sw0657841GvrpConfLeaveAllTime      INTEGER,
    sw0657841GvrpConfDefaultAppMode    INTEGER,
    sw0657841GvrpConfDefaultRegMode    INTEGER,
    sw0657841GvrpConfRestrictedMode    INTEGER
}

sw0657841GvrpConfEntry	OBJECT-TYPE
	SYNTAX		SW0657841GvrpConfEntry
	MAX-ACCESS	    not-accessible
	STATUS		current
	DESCRIPTION
		"This is the Entry(s) for gvrp information."
	INDEX {sw0657841GvrpConfIndex}
	::= { sw0657841GvrpConfTable 1 }

sw0657841GvrpConfIndex	OBJECT-TYPE
	SYNTAX		INTEGER(1..24)
	MAX-ACCESS	    not-accessible
	STATUS		current
	DESCRIPTION
		"This is the index of the gvrp entry."
	::= { sw0657841GvrpConfEntry 1 }
	
sw0657841GvrpConfJoinTime	OBJECT-TYPE
	SYNTAX		INTEGER(20..100)
	MAX-ACCESS	    read-write
	STATUS		current
	DESCRIPTION
		"This is the join-time of the gvrp entry."
	::= { sw0657841GvrpConfEntry 2 }

sw0657841GvrpConfLeaveTime	OBJECT-TYPE
	SYNTAX		INTEGER(60..300)
	MAX-ACCESS	    read-write
	STATUS		current
	DESCRIPTION
		"This is the leave-time of the gvrp entry.
		default:60 centisecond"
	::= { sw0657841GvrpConfEntry 3 }

sw0657841GvrpConfLeaveAllTime	OBJECT-TYPE
	SYNTAX		INTEGER(1000..5000)
	MAX-ACCESS	    read-write
	STATUS		current
	DESCRIPTION
		" default: 1000 unit time"
	::= { sw0657841GvrpConfEntry 4 }

sw0657841GvrpConfDefaultAppMode	OBJECT-TYPE
	SYNTAX		INTEGER(0|1)
	MAX-ACCESS	    read-write
	STATUS		current
	DESCRIPTION
		"    [default: Normal]
		 0 - Normal
		 1 - Non-Participant"
	::= { sw0657841GvrpConfEntry 5 }

sw0657841GvrpConfDefaultRegMode	OBJECT-TYPE
	SYNTAX		INTEGER(0|1|2)
	MAX-ACCESS	    read-write
	STATUS		current
	DESCRIPTION
		"    [default: Normal]
		 0 - Normal 
		 1 - Fixed
		 2 - Forbidden"
	::= { sw0657841GvrpConfEntry 6 }
	
sw0657841GvrpConfRestrictedMode	OBJECT-TYPE
	SYNTAX		INTEGER(0|1)
	MAX-ACCESS	    read-write
	STATUS		current
	DESCRIPTION
		"    [default: Disable]
		 0 - Disable
		 1 - Enable"
	::= { sw0657841GvrpConfEntry 7 }

sw0657841GvrpCounter           	OBJECT IDENTIFIER ::= { sw0657841GVRPInfo 2 }

sw0657841GvrpCounterTable	OBJECT-TYPE
	SYNTAX		SEQUENCE OF SW0657841GvrpCounterEntry
	MAX-ACCESS	not-accessible
	STATUS		current
    DESCRIPTION
        "This is a list of SW0657841GvrpCounterEntry."
	::= { sw0657841GvrpCounter 1 }

SW0657841GvrpCounterEntry ::=
SEQUENCE {
    sw0657841GvrpCounterIndex              INTEGER,
    sw0657841GvrpCounterRxTotalGvrpPkts    Counter32,
    sw0657841GvrpCounterRxInvalidGvrpPkts  Counter32,
    sw0657841GvrpCounterRxLeaveAllMsg      Counter32,
    sw0657841GvrpCounterRxJoinEmptyMsg     Counter32,
    sw0657841GvrpCounterRxJoinInMsg        Counter32,
    sw0657841GvrpCounterRxLeaveEmptyMsg    Counter32,
    sw0657841GvrpCounterRxEmptyMsg         Counter32,
    sw0657841GvrpCounterTxTotalGvrpPkts    Counter32,
    sw0657841GvrpCounterTxLeaveAllMsg      Counter32,
    sw0657841GvrpCounterTxJoinEmptyMsg     Counter32,
    sw0657841GvrpCounterTxJoinInMsg        Counter32,
    sw0657841GvrpCounterTxLeaveEmptyMsg    Counter32,
    sw0657841GvrpCounterTxEmptyMsg         Counter32
}

sw0657841GvrpCounterEntry	OBJECT-TYPE
	SYNTAX		SW0657841GvrpCounterEntry
	MAX-ACCESS	    not-accessible
	STATUS		current
	DESCRIPTION
		"This is the Entry(s) for gvrp counter information."
	INDEX {sw0657841GvrpCounterIndex}
	::= { sw0657841GvrpCounterTable 1 }

sw0657841GvrpCounterIndex	OBJECT-TYPE
	SYNTAX		INTEGER(1..24)
	MAX-ACCESS	    not-accessible
	STATUS		current
	DESCRIPTION
		"This is the index of the gvrp counter entry."
	::= { sw0657841GvrpCounterEntry 1 }

sw0657841GvrpCounterRxTotalGvrpPkts	OBJECT-TYPE
	SYNTAX		Counter32
	MAX-ACCESS	    read-only
	STATUS		current
	DESCRIPTION
		"Get the amount of all received gvrp packets of the gvrp counter entry."
	::= { sw0657841GvrpCounterEntry 2 }

sw0657841GvrpCounterRxInvalidGvrpPkts	OBJECT-TYPE
	SYNTAX		Counter32
	MAX-ACCESS	    read-only
	STATUS		current
	DESCRIPTION
		"Get the amount of received invalid gvrp packets of the gvrp counter entry."
	::= { sw0657841GvrpCounterEntry 3 }

sw0657841GvrpCounterRxLeaveAllMsg	OBJECT-TYPE
	SYNTAX		Counter32
	MAX-ACCESS	    read-only
	STATUS		current
	DESCRIPTION
		"Get the amount of received leave-all-message of the gvrp counter entry."
	::= { sw0657841GvrpCounterEntry 4 }

sw0657841GvrpCounterRxJoinEmptyMsg	OBJECT-TYPE
	SYNTAX		Counter32
	MAX-ACCESS	    read-only
	STATUS		current
	DESCRIPTION
		"Get the amount of received join-empty-message of the gvrp counter entry."
	::= { sw0657841GvrpCounterEntry 5 }

sw0657841GvrpCounterRxJoinInMsg	OBJECT-TYPE
	SYNTAX		Counter32
	MAX-ACCESS	    read-only
	STATUS		current
	DESCRIPTION
		"Get the amount of received join-in-message of the gvrp counter entry."
	::= { sw0657841GvrpCounterEntry 6 }

sw0657841GvrpCounterRxLeaveEmptyMsg	OBJECT-TYPE
	SYNTAX		Counter32
	MAX-ACCESS	    read-only
	STATUS		current
	DESCRIPTION
		"Get the amount of received leave-empty-message of the gvrp counter entry."
	::= { sw0657841GvrpCounterEntry 7 }

sw0657841GvrpCounterRxEmptyMsg	OBJECT-TYPE
	SYNTAX		Counter32
	MAX-ACCESS	    read-only
	STATUS		current
	DESCRIPTION
		"Get the amount of received empty-message of the gvrp counter entry."
	::= { sw0657841GvrpCounterEntry 8 }

sw0657841GvrpCounterTxTotalGvrpPkts	OBJECT-TYPE
	SYNTAX		Counter32
	MAX-ACCESS	    read-only
	STATUS		current
	DESCRIPTION
		"Get the amount of all transmitted gvrp packets of the gvrp counter entry."
	::= { sw0657841GvrpCounterEntry 9 }

sw0657841GvrpCounterTxLeaveAllMsg	OBJECT-TYPE
	SYNTAX		Counter32
	MAX-ACCESS	    read-only
	STATUS		current
	DESCRIPTION
		"Get the amount of transmitted leave-all-message of the gvrp counter entry."
	::= { sw0657841GvrpCounterEntry 10 }

sw0657841GvrpCounterTxJoinEmptyMsg	OBJECT-TYPE
	SYNTAX		Counter32
	MAX-ACCESS	    read-only
	STATUS		current
	DESCRIPTION
		"Get the amount of transmitted join-empty-message of the gvrp counter entry."
	::= { sw0657841GvrpCounterEntry 11 }

sw0657841GvrpCounterTxJoinInMsg	OBJECT-TYPE
	SYNTAX		Counter32
	MAX-ACCESS	    read-only
	STATUS		current
	DESCRIPTION
		"Get the amount of transmitted join-in-message of the gvrp counter entry."
	::= { sw0657841GvrpCounterEntry 12 }

sw0657841GvrpCounterTxLeaveEmptyMsg	OBJECT-TYPE
	SYNTAX		Counter32
	MAX-ACCESS	    read-only
	STATUS		current
	DESCRIPTION
		"Get the amount of transmitted leave-empty-message of the gvrp counter entry."
	::= { sw0657841GvrpCounterEntry 13 }

sw0657841GvrpCounterTxEmptyMsg	OBJECT-TYPE
	SYNTAX		Counter32
	MAX-ACCESS	    read-only
	STATUS		current
	DESCRIPTION
		"Get the amount of transmitted empty-message of the gvrp counter entry."
	::= { sw0657841GvrpCounterEntry 14 }

sw0657841GvrpGroup           	OBJECT IDENTIFIER ::= { sw0657841GVRPInfo 3 }

sw0657841GvrpGroupNumber	OBJECT-TYPE
	SYNTAX		INTEGER(0..4094)
	MAX-ACCESS	    read-only
	STATUS		current
	DESCRIPTION
		"Get the number of the gvrp group entry."
	::= { sw0657841GvrpGroup 1 }

sw0657841GvrpGroupTable	OBJECT-TYPE
	SYNTAX		SEQUENCE OF SW0657841GvrpGroupEntry
	MAX-ACCESS	not-accessible
	STATUS		current
    DESCRIPTION
        "This is a list of SW0657841GvrpGroupEntry."
	::= { sw0657841GvrpGroup 2 }
	
SW0657841GvrpGroupEntry ::=
SEQUENCE {
    sw0657841GvrpGroupId            INTEGER,
    sw0657841GvrpGroupVid           INTEGER,
    sw0657841GvrpGroupMemberPort    DisplayString
}

sw0657841GvrpGroupEntry	OBJECT-TYPE
	SYNTAX		SW0657841GvrpGroupEntry
	MAX-ACCESS	    not-accessible
	STATUS		current
	DESCRIPTION
		"This is the Entry(s) for gvrp group information."
	INDEX {sw0657841GvrpGroupId}
	::= { sw0657841GvrpGroupTable 1 }

sw0657841GvrpGroupId	OBJECT-TYPE
	SYNTAX		INTEGER(1..4094)	
	MAX-ACCESS	    read-only
	STATUS		current
	DESCRIPTION
		"This is the index of the gvrp group entry."
	::= { sw0657841GvrpGroupEntry 1 }

sw0657841GvrpGroupVid	OBJECT-TYPE
	SYNTAX		INTEGER(1..4094)	
	MAX-ACCESS	    read-only
	STATUS		current
	DESCRIPTION
		"This is the vlan id of the gvrp grout entry."
	::= { sw0657841GvrpGroupEntry 2 }

sw0657841GvrpGroupMemberPort	OBJECT-TYPE
	SYNTAX		DisplayString
	MAX-ACCESS	    read-only
	STATUS		current
	DESCRIPTION
		"The member ports of the gvrp grout entry."
	::= { sw0657841GvrpGroupEntry 3 }

sw0657841GvrpGroupAdministrativeCtrlTable	OBJECT-TYPE
	SYNTAX		SEQUENCE OF SW0657841GvrpGroupAdministrativeCtrlEntry
	MAX-ACCESS	not-accessible
	STATUS		current
    DESCRIPTION
        "This is a list of SW0657841GvrpGroupAdministrativeCtrlEntry."
	::= { sw0657841GvrpGroup 3 }

SW0657841GvrpGroupAdministrativeCtrlEntry ::=
SEQUENCE {
    sw0657841GvrpGroupAdministrativeCtrlVid    INTEGER,
    sw0657841GvrpGroupAdministrativeCtrlPort   INTEGER,
    sw0657841GvrpGroupAdministrativeCtrlApp    INTEGER,
    sw0657841GvrpGroupAdministrativeCtrlReg    INTEGER
}

sw0657841GvrpGroupAdministrativeCtrlEntry	OBJECT-TYPE
	SYNTAX		SW0657841GvrpGroupAdministrativeCtrlEntry
	MAX-ACCESS	    not-accessible
	STATUS		current
	DESCRIPTION
		"This is the Entry(s) for gvrp group administrative information."
	INDEX {sw0657841GvrpGroupAdministrativeCtrlVid, sw0657841GvrpGroupAdministrativeCtrlPort}
	::= { sw0657841GvrpGroupAdministrativeCtrlTable 1 }

sw0657841GvrpGroupAdministrativeCtrlVid	OBJECT-TYPE
	SYNTAX		INTEGER(1..4094)	
	MAX-ACCESS	    read-only
	STATUS		current
	DESCRIPTION
		"This is the vlan id of the gvrp-group-admin entry."
	::= { sw0657841GvrpGroupAdministrativeCtrlEntry 1 }

sw0657841GvrpGroupAdministrativeCtrlPort	OBJECT-TYPE
	SYNTAX		INTEGER(1..24)	
	MAX-ACCESS	    read-only
	STATUS		current
	DESCRIPTION
		"This is the port number of the gvrp-group-admin entry."
	::= { sw0657841GvrpGroupAdministrativeCtrlEntry 2 }

sw0657841GvrpGroupAdministrativeCtrlApp	OBJECT-TYPE
	SYNTAX		INTEGER(0|1)	
	MAX-ACCESS	    read-write
	STATUS		current
	DESCRIPTION
		"Set gvrp applicant. 
		 0 - Normal
		 1 - Non-Participant"
	::= { sw0657841GvrpGroupAdministrativeCtrlEntry 3 }

sw0657841GvrpGroupAdministrativeCtrlReg	OBJECT-TYPE
	SYNTAX		INTEGER(0..2)	
	MAX-ACCESS	    read-write
	STATUS		current
	DESCRIPTION
		"Set gvrp registrar. 
		 0 - Normal
		 1 - Fixed
		 2 - Forbidden"
	::= { sw0657841GvrpGroupAdministrativeCtrlEntry 4 }
	
sw0657841QosInfo           	OBJECT IDENTIFIER ::= { sw0657841Produces 17 }

sw0657841QosPortConf           	OBJECT IDENTIFIER ::= { sw0657841QosInfo 1 }

sw0657841QosNumOfClasses OBJECT-TYPE
	SYNTAX      INTEGER(1|2|4)
	MAX-ACCESS	    read-write
	STATUS		current
	DESCRIPTION
		"Effective class number, it can be set 1, 2, or 4.
		1 means only one class available, all packets will be treat the same.
		2 means two classes available, packets will be divided into high and low queue.
		4 means for classes available, packets will be divided into low/normal/medium/high queue"
	::= { sw0657841QosPortConf 1 }

sw0657841QosPortConfTable	OBJECT-TYPE
	SYNTAX		SEQUENCE OF SW0657841QosPortConfEntry
	MAX-ACCESS	not-accessible
	STATUS		current
    DESCRIPTION
        "QoS parameter for ports."
	::= { sw0657841QosPortConf 2 }

SW0657841QosPortConfEntry ::=
SEQUENCE {
    sw0657841QosPortConfIndex                INTEGER,
    sw0657841QosPortConfDefaultClasses       INTEGER,
    sw0657841QosPortConfQCL                  INTEGER,
    sw0657841QosPortConfUserPriority         INTEGER,
    sw0657841QosPortConfQueuingMode          INTEGER,
    sw0657841QosPortConfQueueWeightedLow     INTEGER,
    sw0657841QosPortConfQueueWeightedNormal  INTEGER,
    sw0657841QosPortConfQueueWeightedMedium  INTEGER,
    sw0657841QosPortConfQueueWeightedHigh    INTEGER
}

sw0657841QosPortConfEntry	OBJECT-TYPE
	SYNTAX		SW0657841QosPortConfEntry
	MAX-ACCESS	    not-accessible
	STATUS		current
	DESCRIPTION
		"QoS parameter for ports."
	INDEX {sw0657841QosPortConfIndex}
	::= { sw0657841QosPortConfTable 1 }

sw0657841QosPortConfIndex	OBJECT-TYPE
	SYNTAX		INTEGER(1..24)	
	MAX-ACCESS	    not-accessible
	STATUS		current
	DESCRIPTION
		"This is the port number for QoS configuration."
	::= { sw0657841QosPortConfEntry 1 }
	
sw0657841QosPortConfDefaultClasses	OBJECT-TYPE
	SYNTAX		INTEGER(0..3)	
	MAX-ACCESS	    read-write
	STATUS		current
	DESCRIPTION
		"This is the default class for packets mismatch the specified QCL setting.
		 0 - Low 
		 1 - Normal 
		 2 - Medium 
		 3 - High"
	::= { sw0657841QosPortConfEntry 2 }

sw0657841QosPortConfQCL	OBJECT-TYPE
	SYNTAX		INTEGER(1..24)	
	MAX-ACCESS	    read-write
	STATUS		current
	DESCRIPTION
		"This is where to specify the QoS Control List the port should apply."
	::= { sw0657841QosPortConfEntry 3 }

sw0657841QosPortConfUserPriority	OBJECT-TYPE
	SYNTAX		INTEGER(0..7)	
	MAX-ACCESS	    read-write
	STATUS		current
	DESCRIPTION
		"This is the default ingress VLAN tag priority"
	::= { sw0657841QosPortConfEntry 4 }

sw0657841QosPortConfQueuingMode	OBJECT-TYPE
	SYNTAX		INTEGER(0|1)	
	MAX-ACCESS	    read-write
	STATUS		current
	DESCRIPTION
		" 
		 0 - Strict Priority 
		 1 - Weighted Fair"
	::= { sw0657841QosPortConfEntry 5 }

sw0657841QosPortConfQueueWeightedLow	OBJECT-TYPE
	SYNTAX		INTEGER(1|2|4|8)
	MAX-ACCESS	    read-write
	STATUS		current
	DESCRIPTION
		"To specify how many quotas the low queue can be distributed.
		 Only available when the queueing mode is Weighted Fair."
	::= { sw0657841QosPortConfEntry 6 }

sw0657841QosPortConfQueueWeightedNormal	OBJECT-TYPE
	SYNTAX		INTEGER(1|2|4|8)
	MAX-ACCESS	    read-write
	STATUS		current
	DESCRIPTION
		"To specify how many quotas the normal queue can be distributed.
		 Only available when the queueing mode is Weighted Fair."
	::= { sw0657841QosPortConfEntry 7 }

sw0657841QosPortConfQueueWeightedMedium	OBJECT-TYPE
	SYNTAX		INTEGER(1|2|4|8)
	MAX-ACCESS	    read-write
	STATUS		current
	DESCRIPTION
		"To specify how many quotas the medium queue can be distributed.
		 Only available when the queueing mode is Weighted Fair."
	::= { sw0657841QosPortConfEntry 8 }

sw0657841QosPortConfQueueWeightedHigh	OBJECT-TYPE
	SYNTAX		INTEGER(1|2|4|8)
	MAX-ACCESS	    read-write
	STATUS		current
	DESCRIPTION
		"To specify how many quotas the high queue can be distributed.
		 Only available when the queueing mode is Weighted Fair."
	::= { sw0657841QosPortConfEntry 9 }

sw0657841QosRateLimiters          	OBJECT IDENTIFIER ::= { sw0657841QosInfo 3 }

sw0657841QosRateLimitersTable	OBJECT-TYPE
	SYNTAX		SEQUENCE OF SW0657841QosRateLimitersEntry
	MAX-ACCESS	not-accessible
	STATUS		current
    DESCRIPTION
        "This is the port bandwidth configuration."
	::= { sw0657841QosRateLimiters 1 }

SW0657841QosRateLimitersEntry ::=
SEQUENCE {
    sw0657841QosRateLimitersIndex         INTEGER,
    sw0657841QosRateLimitersPolicer       INTEGER,
    sw0657841QosRateLimitersPolicerRate   INTEGER,
    sw0657841QosRateLimitersShaper        INTEGER,
    sw0657841QosRateLimitersShaperRate    INTEGER
}

sw0657841QosRateLimitersEntry	OBJECT-TYPE
	SYNTAX		SW0657841QosRateLimitersEntry
	MAX-ACCESS	    not-accessible
	STATUS		current
	DESCRIPTION
		"This is the port bandwidth configuration."
	INDEX {sw0657841QosRateLimitersIndex}
	::= { sw0657841QosRateLimitersTable 1 }

sw0657841QosRateLimitersIndex	OBJECT-TYPE
	SYNTAX		INTEGER(1..24)	
	MAX-ACCESS	    not-accessible
	STATUS		current
	DESCRIPTION
		"This is the port number for rate limit configuration"
	::= { sw0657841QosRateLimitersEntry 1 }

sw0657841QosRateLimitersPolicer	OBJECT-TYPE
	SYNTAX		INTEGER(0|1)
	MAX-ACCESS	    read-write
	STATUS		current
	DESCRIPTION
		"This is the ingress bandwidth function for specific port.
		 0 - Disable 
		 1 - Enable"
	::= { sw0657841QosRateLimitersEntry 2 }

sw0657841QosRateLimitersPolicerRate	OBJECT-TYPE
	SYNTAX		INTEGER(1..1000000)
	MAX-ACCESS	    read-write
	STATUS		current
	DESCRIPTION
		"To set the ingress bandwidth for specific port.
		 Available value is from 500k to 1000000k"
	::= { sw0657841QosRateLimitersEntry 3 }

	
sw0657841QosRateLimitersShaper	OBJECT-TYPE
	SYNTAX		INTEGER(0|1)
	MAX-ACCESS	    read-write
	STATUS		current
	DESCRIPTION
		"This is the egress bandwidth function for specific port.
		 0 - Disable 
		 1 - Enable"
	::= { sw0657841QosRateLimitersEntry 4 }
	
sw0657841QosRateLimitersShaperRate	OBJECT-TYPE
	SYNTAX		INTEGER(1..1000000)
	MAX-ACCESS	    read-write
	STATUS		current
	DESCRIPTION
		"To set the ingress bandwidth for specific port.
		 Available value is from 500k to 1000000k"
	::= { sw0657841QosRateLimitersEntry 5 }
	

sw0657841QosStormCtrl          	OBJECT IDENTIFIER ::= { sw0657841QosInfo 4 }

sw0657841QosStromCtrlFloodedUnicastStatus OBJECT-TYPE
	SYNTAX      INTEGER(0|1)
	MAX-ACCESS	    read-write
	STATUS		current
	DESCRIPTION
		"This is the flooded unicast suppression function for this device.
		 0 - Disable
		 1 - Enable"
	::= { sw0657841QosStormCtrl 1 }

sw0657841QosStromCtrlFloodedUnicastRate OBJECT-TYPE
	SYNTAX      DisplayString
	MAX-ACCESS	    read-write
	STATUS		current
	DESCRIPTION
		"To set the flooded unicast suppression for this device.
		 1 | 2 | 4 | 8 | 16 | 32 | 64 | 128 | 256 | 512 | 1k | 2k | 4k | 8k | 16k | 32k |64k | 128k | 256k | 512k | 1024k(Rate:pps)
    "
	::= { sw0657841QosStormCtrl 2 }
	
sw0657841QosStromCtrlMulticastStatus OBJECT-TYPE
	SYNTAX      INTEGER(0|1)
	MAX-ACCESS	    read-write
	STATUS		current
	DESCRIPTION
		"This is the multicast suppression function for this device.
		 0 - Disable
		 1 - Enable"
	::= { sw0657841QosStormCtrl 3 }
	
sw0657841QosStromCtrlMulticastRate OBJECT-TYPE
	SYNTAX      DisplayString
	MAX-ACCESS	    read-write
	STATUS		current
	DESCRIPTION
		"To set the multicast suppression for this device.
		 1 | 2 | 4 | 8 | 16 | 32 | 64 | 128 | 256 | 512 | 1k | 2k | 4k | 8k | 16k | 32k |64k | 128k | 256k | 512k | 1024k(Rate:pps)
    "
	::= { sw0657841QosStormCtrl 4 }
	
sw0657841QosStromCtrlBroadcastStatus OBJECT-TYPE
	SYNTAX      INTEGER(0|1)
	MAX-ACCESS	    read-write
	STATUS		current
	DESCRIPTION
		"This is the broadcast suppression function for this device.
		 0 - Disable
		 1 - Enable"
	::= { sw0657841QosStormCtrl 5 }
	
sw0657841QosStromCtrlBroadcastRate OBJECT-TYPE
	SYNTAX      DisplayString
	MAX-ACCESS	    read-write
	STATUS		current
	DESCRIPTION
		"To set the broadcast suppression for this device.
		 1 | 2 | 4 | 8 | 16 | 32 | 64 | 128 | 256 | 512 | 1k | 2k | 4k | 8k | 16k | 32k |64k | 128k | 256k | 512k | 1024k(Rate:pps)
    "
	::= { sw0657841QosStormCtrl 6 }
	
sw0657841AclInfo           	OBJECT IDENTIFIER ::= { sw0657841Produces 18 }

sw0657841AclPortsConfTable	OBJECT-TYPE
	SYNTAX		SEQUENCE OF SW0657841AclPortsConfEntry
	MAX-ACCESS	not-accessible
	STATUS		current
    DESCRIPTION
        "This is a list of port configuration entry. "
	::= { sw0657841AclInfo 1 }

SW0657841AclPortsConfEntry ::=
SEQUENCE {
    sw0657841AclPortsConfIndex           INTEGER,
    sw0657841AclPortsConfPolicyId        INTEGER,
    sw0657841AclPortsConfAction          INTEGER,
    sw0657841AclPortsConfRateLimiterId   INTEGER,
    sw0657841AclPortsConfPortCopy        INTEGER,
    sw0657841AclPortsConfCounter         Counter32
}

sw0657841AclPortsConfEntry	OBJECT-TYPE
	SYNTAX		SW0657841AclPortsConfEntry
	MAX-ACCESS	    not-accessible
	STATUS		current
	DESCRIPTION
		"This is the Entry(s) for ACL port information."
	INDEX {sw0657841AclPortsConfIndex}
	::= { sw0657841AclPortsConfTable 1 }

sw0657841AclPortsConfIndex	OBJECT-TYPE
	SYNTAX		INTEGER(1..24)	
	MAX-ACCESS	    not-accessible
	STATUS		current
	DESCRIPTION
		"This is the port number of the ACL port entry."
	::= { sw0657841AclPortsConfEntry 1 }

sw0657841AclPortsConfPolicyId	OBJECT-TYPE
	SYNTAX		INTEGER(1..8)	
	MAX-ACCESS	    read-write
	STATUS		current
	DESCRIPTION
		"This is the policy id of the ACL port entry."
	::= { sw0657841AclPortsConfEntry 2 }

sw0657841AclPortsConfAction	OBJECT-TYPE
	SYNTAX		INTEGER(0|1)
	MAX-ACCESS	    read-write
	STATUS		current
	DESCRIPTION
		"Set the action of the ACL port entry. 
		 0 - Deny
		 1 - Permit"
	::= { sw0657841AclPortsConfEntry 3 }

sw0657841AclPortsConfRateLimiterId	OBJECT-TYPE
	SYNTAX		INTEGER(0..16)	
	MAX-ACCESS	    read-write
	STATUS		current
	DESCRIPTION
		" Set the rate limiter id of the ACL port entry. 
		 0 - Disable"
	::= { sw0657841AclPortsConfEntry 4 }

sw0657841AclPortsConfPortCopy	OBJECT-TYPE
	SYNTAX		INTEGER(0..24)	
	MAX-ACCESS	    read-write
	STATUS		current
	DESCRIPTION
		"Set the mirror port of the ACL port entry.
		 0 - Disable"
	::= { sw0657841AclPortsConfEntry 5 }
	
sw0657841AclPortsConfCounter	OBJECT-TYPE
	SYNTAX		Counter32
	MAX-ACCESS	    read-only	
	STATUS		current
	DESCRIPTION
		"This is the port counter of the ACL port entry.  
		 0 - Disable"
	::= { sw0657841AclPortsConfEntry 6 }

sw0657841AclRateLimiter          	OBJECT IDENTIFIER ::= { sw0657841AclInfo 2 }

sw0657841AclRateLimiterTable	OBJECT-TYPE
	SYNTAX		SEQUENCE OF SW0657841AclRateLimiterEntry
	MAX-ACCESS	not-accessible
	STATUS		current
    DESCRIPTION
        "This is a list of SW0657841RateLimiterEntry."
	::= { sw0657841AclRateLimiter 1 }
	
SW0657841AclRateLimiterEntry ::=
SEQUENCE {
    sw0657841AclRateLimiterIndex        INTEGER,
    sw0657841AclRateLimiterRate         DisplayString
}

sw0657841AclRateLimiterEntry	OBJECT-TYPE
	SYNTAX		SW0657841AclRateLimiterEntry
	MAX-ACCESS	    not-accessible
	STATUS		current
	DESCRIPTION
		"This is the Entry(s) for rate limiter information."
	INDEX {sw0657841AclRateLimiterIndex}
	::= { sw0657841AclRateLimiterTable 1 }

sw0657841AclRateLimiterIndex	OBJECT-TYPE
	SYNTAX		INTEGER(1..16)	
	MAX-ACCESS	    not-accessible
	STATUS		current
	DESCRIPTION
		"This is the index of the rate limiter entry."
	::= { sw0657841AclRateLimiterEntry 1 }

sw0657841AclRateLimiterRate	OBJECT-TYPE
	SYNTAX		DisplayString
	MAX-ACCESS	    read-write
	STATUS		current
	DESCRIPTION
		" 
		(pps) 1 | 2 | 4 | 8 | 16 | 32 | 64 | 128 | 256 | 512 | 1k | 2k | 4k | 8k | 16k | 32k |64k | 128k | 256k | 512k | 1024k"
	::= { sw0657841AclRateLimiterEntry 2 }

sw0657841IpMacBind           	OBJECT IDENTIFIER ::= { sw0657841Produces 19 }

sw0657841IpMacBindConf          	OBJECT IDENTIFIER ::= { sw0657841IpMacBind 1 }

sw0657841IpMacBindstate	OBJECT-TYPE
	SYNTAX		INTEGER(0|1)	
	MAX-ACCESS	    read-write
	STATUS		current
	DESCRIPTION
		" Set ip mac binding state.
		 0 - Disable
		 1 - Enable"
	::= { sw0657841IpMacBindConf 1 }

sw0657841IpMacBindTrustPort	OBJECT-TYPE
	SYNTAX		DisplayString
	MAX-ACCESS	    read-write
	STATUS		current
	DESCRIPTION
		"Set trustport,
		 Port range : 1,5-7, available from 1 to 16"
	::= { sw0657841IpMacBindConf 2 }

sw0657841IpMacBindSetting          	OBJECT IDENTIFIER ::= { sw0657841IpMacBind 2 }

sw0657841IpMacBindSettingNumber	OBJECT-TYPE
	SYNTAX		INTEGER(0..1024)	
	MAX-ACCESS	    read-write
	STATUS		current
	DESCRIPTION
		"Get the amount of ip_mac_binding entry."
	::= { sw0657841IpMacBindSetting 1 }
	
sw0657841IpMacBindSettingEntryCreate	OBJECT-TYPE
	SYNTAX		INTEGER(0..1024)	
	MAX-ACCESS	    read-write
	STATUS		current
	DESCRIPTION
		"Create ip_mac_binding entry.
		 0: none
		 1-1024: creat with this index."
	::= { sw0657841IpMacBindSetting 2 }

sw0657841IpMacBindSettingTable	OBJECT-TYPE
	SYNTAX		SEQUENCE OF SW0657841IpMacBindSettingEntry
	MAX-ACCESS	not-accessible
	STATUS		current
    DESCRIPTION
        "This is a list of SW0657841IpMacBindSettingEntry."
	::= { sw0657841IpMacBindSetting 3 }

SW0657841IpMacBindSettingEntry ::=
SEQUENCE {
    sw0657841IpMacBindSettingIndex        INTEGER,
    sw0657841IpMacBindSettingMAC          DisplayString,
    sw0657841IpMacBindSettingIP           IpAddress,
    sw0657841IpMacBindSettingPort         INTEGER,
    sw0657841IpMacBindSettingVID          INTEGER,
    sw0657841IpMacBindSettingEntryAction  INTEGER
}

sw0657841IpMacBindSettingEntry	OBJECT-TYPE
	SYNTAX		SW0657841IpMacBindSettingEntry
	MAX-ACCESS	    not-accessible
	STATUS		current
	DESCRIPTION
		"This is the entry of the ip_mac_binding information."
	INDEX {sw0657841IpMacBindSettingIndex}
	::= { sw0657841IpMacBindSettingTable 1 }

sw0657841IpMacBindSettingIndex	OBJECT-TYPE
	SYNTAX		INTEGER(1..1024)
	MAX-ACCESS	    not-accessible
	STATUS		current
	DESCRIPTION
		"This is the index of the ip_mac_binding entry."
	::= { sw0657841IpMacBindSettingEntry 1 }

sw0657841IpMacBindSettingMAC	OBJECT-TYPE
	SYNTAX		DisplayString
	MAX-ACCESS	    read-write	
	STATUS		current
	DESCRIPTION
		"This is the mac address of the ip_mac_binding entry."
	::= { sw0657841IpMacBindSettingEntry 2 }

sw0657841IpMacBindSettingIP	OBJECT-TYPE
	SYNTAX		IpAddress
	MAX-ACCESS	    read-write	
	STATUS		current
	DESCRIPTION
		"This is the ip address of the ip_mac_binding entry."
	::= { sw0657841IpMacBindSettingEntry 3 }

sw0657841IpMacBindSettingPort	OBJECT-TYPE
	SYNTAX		INTEGER(1..24)	
	MAX-ACCESS	    read-write	
	STATUS		current
	DESCRIPTION
		"This is the port number of the ip_mac_binding entry."
	::= { sw0657841IpMacBindSettingEntry 4 }
	
sw0657841IpMacBindSettingVID	OBJECT-TYPE
	SYNTAX		INTEGER(1..4094)
	MAX-ACCESS	    read-write	
	STATUS		current
	DESCRIPTION
		"This is the vid of the ip_mac_binding entry."
	::= { sw0657841IpMacBindSettingEntry 5 }
	
sw0657841IpMacBindSettingEntryAction	OBJECT-TYPE
	SYNTAX		INTEGER(1..3)
	MAX-ACCESS	    read-write	
	STATUS		current
	DESCRIPTION
		" 
		 1 - active
		 2 - notInService 
		 3 - delete"
	::= { sw0657841IpMacBindSettingEntry 6 }

sw0657841Dot1X           	OBJECT IDENTIFIER ::= { sw0657841Produces 23 }

sw0657841Dot1XServerConf          	OBJECT IDENTIFIER ::= { sw0657841Dot1X 1 }

sw0657841Dot1XServerConfAuthenticationServerIp	OBJECT-TYPE
	SYNTAX		IpAddress
	MAX-ACCESS	    read-write
	STATUS		current
	DESCRIPTION
		"Get/Set authentication server ip"
	::= { sw0657841Dot1XServerConf 1 }

sw0657841Dot1XServerConfAuthenticationUdpPort	OBJECT-TYPE
	SYNTAX		INTEGER(1..65535)
	MAX-ACCESS	    read-write
	STATUS		current
	DESCRIPTION
		"Get/Set IEEE 802.1X authentication UDP port number"
	::= { sw0657841Dot1XServerConf 2 }

sw0657841Dot1XServerConfAuthenticationSecretKey	OBJECT-TYPE
	SYNTAX		DisplayString
	MAX-ACCESS	    read-write
	STATUS		current
	DESCRIPTION
		"Get/Set IEEE 802.1X authentication secret key"
	::= { sw0657841Dot1XServerConf 3 }

sw0657841Dot1XServerConfAccountingServerIp	OBJECT-TYPE
	SYNTAX		IpAddress
	MAX-ACCESS	    read-write
	STATUS		current
	DESCRIPTION
		"Get/Set IEEE 802.1X accounting service IP"
	::= { sw0657841Dot1XServerConf 4 }
	
sw0657841Dot1XServerConfAccountingUdpPort	OBJECT-TYPE
	SYNTAX		INTEGER(1..65535)
	MAX-ACCESS	    read-write
	STATUS		current
	DESCRIPTION
		"Get/Set IEEE 802.1X accounting UDP port number"
	::= { sw0657841Dot1XServerConf 5 }
	
sw0657841Dot1XServerConfAccountingSecretKey	OBJECT-TYPE
	SYNTAX		DisplayString
	MAX-ACCESS	    read-write
	STATUS		current
	DESCRIPTION
		"Get/Set IEEE 802.1X accounting secret key"
	::= { sw0657841Dot1XServerConf 6 }

sw0657841Dot1XPortConfTable	OBJECT-TYPE
	SYNTAX		SEQUENCE OF SW0657841Dot1XPortConfEntry
	MAX-ACCESS	not-accessible
	STATUS		current
    DESCRIPTION
        "A table that contains the configuration objects for the
         Authenticator PAE associated with each port."
	::= { sw0657841Dot1X 2 }

SW0657841Dot1XPortConfEntry ::=
SEQUENCE {
    sw0657841Dot1XPort                INTEGER,
    sw0657841Dot1XPortMode            INTEGER,
    sw0657841Dot1XPortControl         INTEGER,
    sw0657841Dot1XPortreAuthMax       INTEGER,
    sw0657841Dot1XPorttxPeriod        INTEGER,
    sw0657841Dot1XPortquietPeriod     INTEGER,
    sw0657841Dot1XPortreAuthEnabled   INTEGER,
    sw0657841Dot1XPortreAuthPeriod    INTEGER,
    sw0657841Dot1XPortmaxReq          INTEGER,
    sw0657841Dot1XPortsuppTimeout     INTEGER,
    sw0657841Dot1XPortserverTimeout   INTEGER
}

sw0657841Dot1XPortConfEntry	OBJECT-TYPE
	SYNTAX		SW0657841Dot1XPortConfEntry
	MAX-ACCESS	    not-accessible
	STATUS		current
	DESCRIPTION
		"The configuration information for an Authenticator PAE."
	INDEX {sw0657841Dot1XPort}
	::= { sw0657841Dot1XPortConfTable 1 }

sw0657841Dot1XPort	OBJECT-TYPE
	SYNTAX		INTEGER(1..24)	
	MAX-ACCESS	    read-write
	STATUS		current
	DESCRIPTION
		 "The port index of 802.1X port configuration table."
	::= { sw0657841Dot1XPortConfEntry 1 }
	
sw0657841Dot1XPortMode	OBJECT-TYPE
	SYNTAX		INTEGER(0..3)
	MAX-ACCESS	    read-write
	STATUS		current
	DESCRIPTION
		"Get/Set IEEE 802.1X port mode.
		 0 - Disable 
		 1 - Normal 
		 2 - Advanced 
		 3 - Clientless"
	::= { sw0657841Dot1XPortConfEntry 2 }

sw0657841Dot1XPortControl	OBJECT-TYPE
	SYNTAX		INTEGER(0..2)
	MAX-ACCESS	    read-write
	STATUS		current
	DESCRIPTION
		"The current value of the controlled Port
		 control parameter of the Port.
	 0 : ForceUnauthorized, 
	 1 : ForceAuthorized, 
	 2 : Auto	
        "
	::= { sw0657841Dot1XPortConfEntry 3 }

sw0657841Dot1XPortreAuthMax	OBJECT-TYPE
	SYNTAX		INTEGER(1..10)	
	MAX-ACCESS	    read-write
	STATUS		current
	DESCRIPTION
		"The value of the reAuthMax constant currently in use by
		 the Authenticator PAE state machine."
	::= { sw0657841Dot1XPortConfEntry 4 }
	
	
sw0657841Dot1XPorttxPeriod	OBJECT-TYPE
	SYNTAX		INTEGER(1..65535)
	MAX-ACCESS	    read-write
	STATUS		current
	DESCRIPTION
		"The value, in seconds, of the txPeriod constant
		 currently in use by the Authenticator PAE state
		 machine."
	::= { sw0657841Dot1XPortConfEntry 5 }

sw0657841Dot1XPortquietPeriod	OBJECT-TYPE
	SYNTAX		INTEGER(0..65535)
	MAX-ACCESS	    read-write
	STATUS		current
	DESCRIPTION
		"The value, in seconds, of the quietPeriod constant
		 currently in use by the Authenticator PAE state
		 machine."
	::= { sw0657841Dot1XPortConfEntry 6 }

sw0657841Dot1XPortreAuthEnabled	OBJECT-TYPE
	SYNTAX		INTEGER(0|1)
	MAX-ACCESS	    read-write
	STATUS		current
	DESCRIPTION
		"The enable/disable control used by the Reauthentication
		 Timer state machine.
		 0 - Disable 
		 1 - Enable"
	::= { sw0657841Dot1XPortConfEntry 7 }

sw0657841Dot1XPortreAuthPeriod	OBJECT-TYPE
	SYNTAX		INTEGER(1..65535)
	MAX-ACCESS	    read-write
	STATUS		current
	DESCRIPTION
		"The value, in seconds, of the reAuthPeriod constant
		 currently in use by the Reauthentication Timer state
		 machine."
	::= { sw0657841Dot1XPortConfEntry 8 }

sw0657841Dot1XPortmaxReq	OBJECT-TYPE
	SYNTAX		INTEGER(1..10)
	MAX-ACCESS	    read-write
	STATUS		current
	DESCRIPTION
		"The value of the maxReq constant currently in use by
		 the Backend Authentication state machine."
	::= { sw0657841Dot1XPortConfEntry 9 }

sw0657841Dot1XPortsuppTimeout	OBJECT-TYPE
	SYNTAX		INTEGER(1..255)
	MAX-ACCESS	    read-write
	STATUS		current
	DESCRIPTION
		"The value, in seconds, of the suppTimeout constant
		 currently in use by the Backend Authentication state
		 machine."
	::= { sw0657841Dot1XPortConfEntry 10 }
	
sw0657841Dot1XPortserverTimeout	OBJECT-TYPE
	SYNTAX		INTEGER(1..255)
	MAX-ACCESS	    read-write
	STATUS		current
	DESCRIPTION
		"The value, in seconds, of the serverTimeout constant
		 currently in use by the Backend Authentication state
		 machine."
	::= { sw0657841Dot1XPortConfEntry 11 }


sw0657841Dot1XStatusTable	OBJECT-TYPE
	SYNTAX		SEQUENCE OF SW0657841Dot1XStatusEntry
	MAX-ACCESS	not-accessible
	STATUS		current
    DESCRIPTION
        "A table that contains the status objects for the
         Authenticator PAE associated with each port."
	::= { sw0657841Dot1X 3 }
	
SW0657841Dot1XStatusEntry ::=
SEQUENCE {
    sw0657841Dot1XStatusIndex   INTEGER,
    sw0657841Dot1XStatusMode    DisplayString,
    sw0657841Dot1XStatusStatus  DisplayString
}

sw0657841Dot1XStatusEntry	OBJECT-TYPE
	SYNTAX		SW0657841Dot1XStatusEntry
	MAX-ACCESS	    not-accessible
	STATUS		current
	DESCRIPTION
		"The status information for an Authenticator PAE."
	INDEX {sw0657841Dot1XStatusIndex}
	::= { sw0657841Dot1XStatusTable 1 }

sw0657841Dot1XStatusIndex	OBJECT-TYPE
	SYNTAX		INTEGER(1..24)
	MAX-ACCESS	    not-accessible
	STATUS		current
	DESCRIPTION
		"The port index of 802.1X status table."
	::= { sw0657841Dot1XStatusEntry 1 }
	
sw0657841Dot1XStatusMode	OBJECT-TYPE
	SYNTAX		DisplayString
	MAX-ACCESS	    read-only
	STATUS		current
	DESCRIPTION
		"The current mode of the controlled port."
	::= { sw0657841Dot1XStatusEntry 2 }

sw0657841Dot1XStatusStatus	OBJECT-TYPE
	SYNTAX		DisplayString
	MAX-ACCESS	    read-only
	STATUS		current
	DESCRIPTION
		"The current status of the controlled port."
	::= { sw0657841Dot1XStatusEntry 3 }

sw0657841Dot1XStatisticsTable	OBJECT-TYPE
	SYNTAX		SEQUENCE OF SW0657841Dot1XStatisticsEntry
	MAX-ACCESS	not-accessible
	STATUS		current
    DESCRIPTION
        "A table that contains the statistics objects for the
         Authenticator PAE associated with each port."
	::= { sw0657841Dot1X 4 }

SW0657841Dot1XStatisticsEntry ::=
SEQUENCE {
    sw0657841Dot1XStatisticsIndex                        INTEGER,
    sw0657841Dot1XClearCounter                           INTEGER,
    sw0657841Dot1XAuthEntersConnecting                   Counter32,
    sw0657841Dot1XauthEapLogoffsWhileConnecting          Counter32,
    sw0657841Dot1XAuthEntersAuthenticating               Counter32,
    sw0657841Dot1XAuthAuthSuccessesWhileAuthenticating   Counter32,
    sw0657841Dot1XAuthAuthTimeoutsWhileAuthenticating    Counter32,
    sw0657841Dot1XAuthAuthFailWhileAuthenticating        Counter32,
    sw0657841Dot1XAuthAuthEapStartsWhileAuthenticating   Counter32,
    sw0657841Dot1XAuthAuthEapLogoffWhileAuthenticating   Counter32,
    sw0657841Dot1XAuthAuthReauthsWhileAuthenticated      Counter32,
    sw0657841Dot1XAuthAuthEapStartsWhileAuthenticated    Counter32,
    sw0657841Dot1XAuthAuthEapLogoffWhileAuthenticated    Counter32,
    sw0657841Dot1XBackendResponses                       Counter32,
    sw0657841Dot1XBackendAccessChallenges                Counter32,
    sw0657841Dot1XBackendOtherRequestsToSupplicant       Counter32,
    sw0657841Dot1XBackendAuthSuccesses                   Counter32,
    sw0657841Dot1XBackendAuthFails                       Counter32,
    sw0657841Dot1XAuthEapolFramesRx                      Counter32,
    sw0657841Dot1XAuthEapolFramesTx                      Counter32,
    sw0657841Dot1XAuthEapolStartFramesRx                 Counter32,
    sw0657841Dot1XAuthEapolLogoffFramesRx                Counter32,
    sw0657841Dot1XAuthEapolRespIdFramesRx                Counter32,
    sw0657841Dot1XAuthEapolRespFramesRx                  Counter32,
    sw0657841Dot1XAuthEapolReqIdFramesTx                 Counter32,
    sw0657841Dot1XAuthEapolReqFramesTx                   Counter32,
    sw0657841Dot1XAuthInvalidEapolFramesRx               Counter32,
    sw0657841Dot1XAuthEapLengthErrorFramesRx             Counter32,
    sw0657841Dot1XAuthLastEapolFrameVersion              Counter32,
    sw0657841Dot1XAuthLastEapolFrameSource               DisplayString
}

sw0657841Dot1XStatisticsEntry	OBJECT-TYPE
	SYNTAX		SW0657841Dot1XStatisticsEntry
	MAX-ACCESS	    not-accessible
	STATUS		current
	DESCRIPTION
		"The statistics information for an Authenticator PAE."
	INDEX {sw0657841Dot1XStatisticsIndex}
	::= { sw0657841Dot1XStatisticsTable 1 }

sw0657841Dot1XStatisticsIndex	OBJECT-TYPE
	SYNTAX		INTEGER(1..24)
	MAX-ACCESS	    not-accessible
	STATUS		current
	DESCRIPTION
		"The port index of the 802.1X statistics table."
	::= { sw0657841Dot1XStatisticsEntry 1 }

sw0657841Dot1XClearCounter	OBJECT-TYPE
	SYNTAX		INTEGER(0|1)
	MAX-ACCESS	    read-write
	STATUS		current
	DESCRIPTION
		"Reset the 802.1X counter associated with this port.
		 0 - do nothing 
		 1 - clear "
	::= { sw0657841Dot1XStatisticsEntry 2 }

sw0657841Dot1XAuthEntersConnecting	OBJECT-TYPE
	SYNTAX		Counter32
	MAX-ACCESS	    read-only
	STATUS		current
	DESCRIPTION
		"Counts the number of times that the state machine
		 transitions to the CONNECTING state from any other
		 state."
	::= { sw0657841Dot1XStatisticsEntry 3 }

sw0657841Dot1XauthEapLogoffsWhileConnecting	OBJECT-TYPE
	SYNTAX		Counter32
	MAX-ACCESS	    read-only
	STATUS		current
	DESCRIPTION
		"Counts the number of times that the state machine
		 transitions from CONNECTING to DISCONNECTED as a result
		 of receiving an EAPOL-Logoff message."

	::= { sw0657841Dot1XStatisticsEntry 4 }

sw0657841Dot1XAuthEntersAuthenticating	OBJECT-TYPE
	SYNTAX		Counter32
	MAX-ACCESS	    read-only
	STATUS		current
	DESCRIPTION
		"Counts the number of times that the state machine
		 transitions from CONNECTING to AUTHENTICATING, as a
		 result of an EAP-Response/Identity message being
		 received from the Supplicant."
	::= { sw0657841Dot1XStatisticsEntry 5 }

sw0657841Dot1XAuthAuthSuccessesWhileAuthenticating	OBJECT-TYPE
	SYNTAX		Counter32
	MAX-ACCESS	    read-only
	STATUS		current
	DESCRIPTION
		"Counts the number of times that the state machine
		 transitions from AUTHENTICATING to AUTHENTICATED, as a
		 result of the Backend Authentication state machine
		 indicating successful authentication of the Supplicant."
	::= { sw0657841Dot1XStatisticsEntry 6 }

sw0657841Dot1XAuthAuthTimeoutsWhileAuthenticating	OBJECT-TYPE
	SYNTAX		Counter32
	MAX-ACCESS	    read-only
	STATUS		current
	DESCRIPTION
		"Counts the number of times that the state machine
		 transitions from AUTHENTICATING to ABORTING, as a result
		 of the Backend Authentication state machine indicating
		 authentication timeout."
	::= { sw0657841Dot1XStatisticsEntry 7 }

sw0657841Dot1XAuthAuthFailWhileAuthenticating	OBJECT-TYPE
	SYNTAX		Counter32
	MAX-ACCESS	    read-only
	STATUS		current
	DESCRIPTION
		"Counts the number of times that the state machine
		 transitions from AUTHENTICATING to HELD, as a result
		 of the Backend Authentication state machine indicating
		 authentication failure."
	::= { sw0657841Dot1XStatisticsEntry 8 }

sw0657841Dot1XAuthAuthEapStartsWhileAuthenticating	OBJECT-TYPE
	SYNTAX		Counter32
	MAX-ACCESS	    read-only
	STATUS		current
	DESCRIPTION
		"Counts the number of times that the state machine
		 transitions from AUTHENTICATING to ABORTING, as a result
		 of an EAPOL-Start message being received from the
		 Supplicant."
	::= { sw0657841Dot1XStatisticsEntry 9 }

sw0657841Dot1XAuthAuthEapLogoffWhileAuthenticating	OBJECT-TYPE
	SYNTAX		Counter32
	MAX-ACCESS	    read-only
	STATUS		current
	DESCRIPTION
		"Counts the number of times that the state machine
		 transitions from AUTHENTICATING to ABORTING, as a result
		 of an EAPOL-Logoff message being received from the
		 Supplicant."
	::= { sw0657841Dot1XStatisticsEntry 10 }

sw0657841Dot1XAuthAuthReauthsWhileAuthenticated	OBJECT-TYPE
	SYNTAX		Counter32
	MAX-ACCESS	    read-only
	STATUS		current
	DESCRIPTION
		"Counts the number of times that the state machine
		 transitions from AUTHENTICATED to CONNECTING, as a
		 result of a reauthentication request."
	::= { sw0657841Dot1XStatisticsEntry 11 }

sw0657841Dot1XAuthAuthEapStartsWhileAuthenticated	OBJECT-TYPE
	SYNTAX		Counter32
	MAX-ACCESS	    read-only
	STATUS		current
	DESCRIPTION
		"Counts the number of times that the state machine
		 transitions from AUTHENTICATED to CONNECTING, as a
		 result of an EAPOL-Start message being received from
		 the Supplicant."
	::= { sw0657841Dot1XStatisticsEntry 12 }

sw0657841Dot1XAuthAuthEapLogoffWhileAuthenticated	OBJECT-TYPE
	SYNTAX		Counter32
	MAX-ACCESS	    read-only
	STATUS		current
	DESCRIPTION
		"Counts the number of times that the state machine
		 transitions from AUTHENTICATED to DISCONNECTED, as a
		 result of an EAPOL-Logoff message being received from
		 the Supplicant."
	::= { sw0657841Dot1XStatisticsEntry 13 }

sw0657841Dot1XBackendResponses	OBJECT-TYPE
	SYNTAX		Counter32
	MAX-ACCESS	    read-only
	STATUS		current
	DESCRIPTION
		"Counts the number of times that the state machine sends
		 an initial Access-Request packet to the Authentication
		 server (i.e., executes sendRespToServer on entry to the
		 RESPONSE state). Indicates that the Authenticator
		 attempted communication with the Authentication Server."
	::= { sw0657841Dot1XStatisticsEntry 14 }

sw0657841Dot1XBackendAccessChallenges	OBJECT-TYPE
	SYNTAX		Counter32
	MAX-ACCESS	    read-only
	STATUS		current
	DESCRIPTION
		"Counts the number of times that the state machine receives
		 an initial Access-Challenge packet from the Authentication
		 server (i.e., aReq becomes TRUE, causing exit from the
		 RESPONSE state). Indicates that the Authentication Server
		 has communication with the Authenticator."
	::= { sw0657841Dot1XStatisticsEntry 15 }

sw0657841Dot1XBackendOtherRequestsToSupplicant	OBJECT-TYPE
	SYNTAX		Counter32
	MAX-ACCESS	    read-only
	STATUS		current
	DESCRIPTION
		"Counts the number of times that the state machine sends
		 an EAP-Request packet (other than Indentity, Notification,
		 Faluire or Success message) to the Supplicant (i.e.,
		 executes txReq on entry to the REQUEST state). Indicates
		 that Authenticator chose an EAP-method."
	::= { sw0657841Dot1XStatisticsEntry 16 }

sw0657841Dot1XBackendAuthSuccesses	OBJECT-TYPE
	SYNTAX		Counter32
	MAX-ACCESS	    read-only
	STATUS		current
	DESCRIPTION
		"Counts the number of times that the state machine receives
		 an EAP-Success message from the Authentication Server (i.e.,
		 aSuccess becomes TRUE, causing a transitions from RESPONSE to
		 SUCCESS). Indicates that the Supplicant has successfully
		 authenticated to the Authentication Server."
	::= { sw0657841Dot1XStatisticsEntry 17 }

sw0657841Dot1XBackendAuthFails	OBJECT-TYPE
	SYNTAX		Counter32
	MAX-ACCESS	    read-only
	STATUS		current
	DESCRIPTION
		"Counts the number of times that the state machine receives
		 an EAP-Failure message from the Authentication Server (i.e.,
		 aFail becomes TRUE, causing a transitions from RESPONSE to
		 FAIL). Indicates that the Supplicant has not authenticated
		 to the Authentication Server."
	::= { sw0657841Dot1XStatisticsEntry 18 }

sw0657841Dot1XAuthEapolFramesRx	OBJECT-TYPE
	SYNTAX		Counter32
	MAX-ACCESS	    read-only
	STATUS		current
	DESCRIPTION
		"The number of valid EAPOL frames of any type
		 that have been received by this Authenticator."
	::= { sw0657841Dot1XStatisticsEntry 19 }

sw0657841Dot1XAuthEapolFramesTx	OBJECT-TYPE
	SYNTAX		Counter32
	MAX-ACCESS	    read-only
	STATUS		current
	DESCRIPTION
		"The number of valid EAPOL frames of any type
		 that have been transmitted by this Authenticator."
	::= { sw0657841Dot1XStatisticsEntry 20 }

sw0657841Dot1XAuthEapolStartFramesRx	OBJECT-TYPE
	SYNTAX		Counter32
	MAX-ACCESS	    read-only
	STATUS		current
	DESCRIPTION
		"The number of EAPOL Start frames that have
		 been received by this Authenticator."
	::= { sw0657841Dot1XStatisticsEntry 21 }

sw0657841Dot1XAuthEapolLogoffFramesRx	OBJECT-TYPE
	SYNTAX		Counter32
	MAX-ACCESS	    read-only
	STATUS		current
	DESCRIPTION
		"The number of EAPOL Logoff frames that have
		 been received by this Authenticator."
	::= { sw0657841Dot1XStatisticsEntry 22 }

sw0657841Dot1XAuthEapolRespIdFramesRx	OBJECT-TYPE
	SYNTAX		Counter32
	MAX-ACCESS	    read-only
	STATUS		current
	DESCRIPTION
		"The number of EAP Resp/Id frames that have
		 been received by this Authenticator."
	::= { sw0657841Dot1XStatisticsEntry 23 }

sw0657841Dot1XAuthEapolRespFramesRx	OBJECT-TYPE
	SYNTAX		Counter32
	MAX-ACCESS	    read-only
	STATUS		current
	DESCRIPTION
		"The number of valid EAP Response frames
		 (other than Resp/Id frames) that have been
		 received by this Authenticator."
	::= { sw0657841Dot1XStatisticsEntry 24 }

sw0657841Dot1XAuthEapolReqIdFramesTx	OBJECT-TYPE
	SYNTAX		Counter32
	MAX-ACCESS	    read-only
	STATUS		current
	DESCRIPTION
		"The number of EAP Req/Id frames that have
		 been transmitted by this Authenticator."
	::= { sw0657841Dot1XStatisticsEntry 25 }
	
sw0657841Dot1XAuthEapolReqFramesTx	OBJECT-TYPE
	SYNTAX		Counter32
	MAX-ACCESS	    read-only
	STATUS		current
	DESCRIPTION
		"The number of valid EAP Request frames
		 (other than Req/Id frames) that have been
		 transmitted by this Authenticator."
	::= { sw0657841Dot1XStatisticsEntry 26 }

sw0657841Dot1XAuthInvalidEapolFramesRx	OBJECT-TYPE
	SYNTAX		Counter32
	MAX-ACCESS	    read-only
	STATUS		current
	DESCRIPTION
		"The number of EAPOL frames that have been
		 received by this Authenticator in which the
		 frame type is not recognized."
	::= { sw0657841Dot1XStatisticsEntry 27 }

sw0657841Dot1XAuthEapLengthErrorFramesRx	OBJECT-TYPE
	SYNTAX		Counter32
	MAX-ACCESS	    read-only
	STATUS		current
	DESCRIPTION
		"The number of EAPOL frames that have been
		 received by this Authenticator in which the
		 Packet Body Length field is invalid."
	::= { sw0657841Dot1XStatisticsEntry 28 }

sw0657841Dot1XAuthLastEapolFrameVersion	OBJECT-TYPE
	SYNTAX		Counter32
	MAX-ACCESS	    read-only
	STATUS		current
	DESCRIPTION
		"The protocol version number carried in the
		 most recently received EAPOL frames."
	::= { sw0657841Dot1XStatisticsEntry 29 }

sw0657841Dot1XAuthLastEapolFrameSource	OBJECT-TYPE
	SYNTAX		DisplayString
	MAX-ACCESS	    read-only
	STATUS		current
	DESCRIPTION
		"The source MAC address carried in the
		 most recently received EAPOL frames."
	::= { sw0657841Dot1XStatisticsEntry 30 }


sw0657841TrunkInfo       OBJECT IDENTIFIER ::= { sw0657841Produces 24 }     

sw0657841TrunkPort      OBJECT IDENTIFIER ::= { sw0657841TrunkInfo 1 }  

sw0657841TrunkPortTable	OBJECT-TYPE
	SYNTAX		SEQUENCE OF SW0657841TrunkPortEntry
	MAX-ACCESS	not-accessible
	STATUS		current
    DESCRIPTION
        "This is a list of SW0657841TrunkPortEntry."
	::= { sw0657841TrunkPort 1 }

SW0657841TrunkPortEntry ::=
SEQUENCE {
    sw0657841TrunkPortIndex	INTEGER,
    sw0657841TrunkPortMethod   	INTEGER,
    sw0657841TrunkPortGroup 	INTEGER,
    sw0657841TrunkPortActiveLacp	INTEGER,
    sw0657841TrunkPortAggtr	INTEGER,
    sw0657841TrunkPortStatus	INTEGER,
    sw0657841TrunkPortCurrentMode	INTEGER
}

sw0657841TrunkPortEntry	OBJECT-TYPE
	SYNTAX		SW0657841TrunkPortEntry
	MAX-ACCESS	    not-accessible
	STATUS		current
	DESCRIPTION
        "Entry(s) for trunk table."
	INDEX {sw0657841TrunkPortIndex}
	::= { sw0657841TrunkPortTable 1 }

sw0657841TrunkPortIndex	OBJECT-TYPE
	SYNTAX		INTEGER(1..24)
	MAX-ACCESS	    not-accessible
	STATUS		current
	DESCRIPTION
        "The port index of trunk table."
	::= { sw0657841TrunkPortEntry 1 }

sw0657841TrunkPortMethod  OBJECT-TYPE
    SYNTAX      INTEGER(0..2)
    MAX-ACCESS  read-write
    STATUS      current
    DESCRIPTION
        "The method of trunk port.
	 0 : None, 
	 1 : LACP, 
	 2 : Static.	
        "
    ::= { sw0657841TrunkPortEntry 2 }   
    
sw0657841TrunkPortGroup  OBJECT-TYPE
    SYNTAX      INTEGER(0..12)
    MAX-ACCESS  read-write
    STATUS      current
    DESCRIPTION
        "The group(0~12) of trunk port."
    ::= { sw0657841TrunkPortEntry 3 }     
    
sw0657841TrunkPortActiveLacp  OBJECT-TYPE
    SYNTAX      INTEGER(0|1)
    MAX-ACCESS  read-write
    STATUS      current
    DESCRIPTION
        "The active lacp mode of trunk port.
	 0 : Passive, 
	 1 : Active.
        "
    ::= { sw0657841TrunkPortEntry 4 }   
    
sw0657841TrunkPortAggtr  OBJECT-TYPE
    SYNTAX      INTEGER(1..24)
    MAX-ACCESS  read-only
    STATUS      current
    DESCRIPTION
        "The Aggtr of trunk port."
    ::= { sw0657841TrunkPortEntry 5 }      
    
sw0657841TrunkPortStatus  OBJECT-TYPE
    SYNTAX      INTEGER(0|1)
    MAX-ACCESS  read-only
    STATUS      current
    DESCRIPTION
        "The status of trunk port.
         0 : None,
         1 : Ready.
        "
    ::= { sw0657841TrunkPortEntry 6 }  
    
sw0657841TrunkPortCurrentMode  OBJECT-TYPE
    SYNTAX      INTEGER(0..2)
    MAX-ACCESS  read-write
    STATUS      current
    DESCRIPTION
        "The current mode of trunk port entry.
	 0 : Active mode, 
	 1 : Edit mode, 
	 2 : Do edit.
        "
    ::= { sw0657841TrunkPortEntry 7 }        
    
sw0657841AggregatorView      OBJECT IDENTIFIER ::= { sw0657841TrunkInfo 2 }  

sw0657841AggregatorViewTable  OBJECT-TYPE
    SYNTAX      SEQUENCE OF SW0657841AggregatorViewEntry
    MAX-ACCESS  not-accessible
    STATUS      current
    DESCRIPTION
        "This is a list of SW0657841AggregatorViewEntry."
    ::= { sw0657841AggregatorView 1 }

SW0657841AggregatorViewEntry ::=
SEQUENCE {
    sw0657841AggregatorViewIndex		INTEGER,
    sw0657841AggregatorViewMethod 	INTEGER,
    sw0657841AggregatorViewMemberPorts 	DisplayString,
    sw0657841AggregatorViewReadyPorts	DisplayString
}

sw0657841AggregatorViewEntry OBJECT-TYPE
    SYNTAX      SW0657841AggregatorViewEntry
    MAX-ACCESS  not-accessible
    STATUS      current
    DESCRIPTION
        "Entry(s) for aggregator view table."
    INDEX {sw0657841AggregatorViewIndex}
    ::= { sw0657841AggregatorViewTable 1 }

sw0657841AggregatorViewIndex  OBJECT-TYPE
    SYNTAX      INTEGER(1..24)
    MAX-ACCESS  not-accessible
    STATUS      current
    DESCRIPTION  
        "The port index of aggregator view table."
    ::= { sw0657841AggregatorViewEntry 1 } 
    
sw0657841AggregatorViewMethod  OBJECT-TYPE
    SYNTAX      INTEGER(0..2)
    MAX-ACCESS  read-only
    STATUS      current
    DESCRIPTION
        "The method of aggregator view table.
         0 : None, 
	 1 : LACP, 
	 2 : Static.
        "
    ::= { sw0657841AggregatorViewEntry 2 }  
    
sw0657841AggregatorViewMemberPorts  OBJECT-TYPE
    SYNTAX      DisplayString
    MAX-ACCESS  read-only
    STATUS      current
    DESCRIPTION
        "The member ports of aggregator view table."
    ::= { sw0657841AggregatorViewEntry 3 }   
    
sw0657841AggregatorViewReadyPorts  OBJECT-TYPE
    SYNTAX      DisplayString
    MAX-ACCESS  read-only
    STATUS      current
    DESCRIPTION
        "The ready ports of aggregator view table."
    ::= { sw0657841AggregatorViewEntry 4 }         

sw0657841LacpSystemPriority	OBJECT-TYPE
	SYNTAX		INTEGER(1..65535)	
	MAX-ACCESS	    read-write
	STATUS		current
	DESCRIPTION
		"Set lacp system priority."
	::= { sw0657841TrunkInfo 3 }

sw0657841IGMPInfo           	OBJECT IDENTIFIER ::= { sw0657841Produces 25 }

sw0657841IgmpProxyConfState OBJECT-TYPE
	SYNTAX      INTEGER(0|1)
	MAX-ACCESS	    read-write
	STATUS		current
	DESCRIPTION
		"Get/Set IGMP Proxy state, 0 - disable, 1 - enable."
	::= { sw0657841IGMPInfo 1 }

sw0657841IgmpProxyConfUnregIPMCFlooding OBJECT-TYPE
	SYNTAX      INTEGER(0|1)
	MAX-ACCESS	    read-write
	STATUS		current
	DESCRIPTION
		"Get/Set unregistered IP multicast flooding state, 0 - disable, 1 - enable."
	::= { sw0657841IGMPInfo 2 }

sw0657841IgmpProxyConfGeneralQueuyInterval OBJECT-TYPE
	SYNTAX      INTEGER(1..3600)
	MAX-ACCESS	    read-write
	STATUS		current
	DESCRIPTION
		"Get/Set IGMP general query interval(Unit: second)."
	::= { sw0657841IGMPInfo 3 }

sw0657841IgmpProxyConfGeneralQueuyRepTimeout OBJECT-TYPE
	SYNTAX      INTEGER(1..25)
	MAX-ACCESS	    read-write
	STATUS		current
	DESCRIPTION
		"Get/Set IGMP general query response timeout(Unit: second)."
	::= { sw0657841IGMPInfo 4 }

sw0657841IgmpProxyConfGeneralQueuyMaxRepTime OBJECT-TYPE
	SYNTAX      INTEGER(1..25)
	MAX-ACCESS	    read-write
	STATUS		current
	DESCRIPTION
		"Get/Set IGMP general query maximum response time(Unit: second)."
	::= { sw0657841IGMPInfo 5 }
	
sw0657841IgmpProxyConfLastMemberQueuyCount OBJECT-TYPE
	SYNTAX      INTEGER(1..16)
	MAX-ACCESS	    read-write
	STATUS		current
	DESCRIPTION
		"Get/Set IGMP specific query robust count."
	::= { sw0657841IGMPInfo 6 }

sw0657841IgmpProxyConfLastMemberQueuyInterval OBJECT-TYPE
	SYNTAX      INTEGER(1..25)
	MAX-ACCESS	    read-write
	STATUS		current
	DESCRIPTION
		"Get/Set IGMP specific query interval(Unit: second)."
	::= { sw0657841IGMPInfo 7 }

sw0657841IgmpProxyConfLastMemberQueuyMaxRepTime OBJECT-TYPE
	SYNTAX      INTEGER(1..25)
	MAX-ACCESS	    read-write
	STATUS		current
	DESCRIPTION
		"Get/Set IGMP specific query maximum response time(Unit: second)."
	::= { sw0657841IGMPInfo 8 }

sw0657841IgmpProxyConfRouterPorts OBJECT-TYPE
	SYNTAX      DisplayString
	MAX-ACCESS	    read-write
	STATUS		current
	DESCRIPTION
		" Get/Set IGMP router port(s)."
	::= { sw0657841IGMPInfo 9 }

sw0657841IgmpGroupMembershipNumber OBJECT-TYPE
	SYNTAX      INTEGER(0..1024)
	MAX-ACCESS	    read-write
	STATUS		current
	DESCRIPTION
		"Get the amount of multicast group membership."
	::= { sw0657841IGMPInfo 10 }

sw0657841IgmpGroupMembershipTable  OBJECT-TYPE
    SYNTAX      SEQUENCE OF SW0657841IgmpGroupMembershipEntry
    MAX-ACCESS  not-accessible
    STATUS      current
    DESCRIPTION
        "Get multicast group membership."
    ::= { sw0657841IGMPInfo 11 }
    
SW0657841IgmpGroupMembershipEntry ::=
SEQUENCE {
    sw0657841IgmpGroupNo		       INTEGER,
    sw0657841IgmpGroupAddress 	   DisplayString,
    sw0657841IgmpGroupVLANId	     INTEGER,
    sw0657841IgmpGroupPortMembers	 DisplayString
}

sw0657841IgmpGroupMembershipEntry OBJECT-TYPE
    SYNTAX      SW0657841IgmpGroupMembershipEntry
    MAX-ACCESS  not-accessible
    STATUS      current
    DESCRIPTION
        "Multicast group membership entry."
    INDEX {sw0657841IgmpGroupNo}
    ::= { sw0657841IgmpGroupMembershipTable 1 }

sw0657841IgmpGroupNo  OBJECT-TYPE
    SYNTAX      INTEGER(1..1024)
    MAX-ACCESS  not-accessible
    STATUS      current
    DESCRIPTION  
        "The index of multicast group membership entry."
    ::= { sw0657841IgmpGroupMembershipEntry 1 } 

sw0657841IgmpGroupAddress  OBJECT-TYPE
    SYNTAX      DisplayString
    MAX-ACCESS  read-only
    STATUS      current
    DESCRIPTION  
        "The group address of multicast group membership entry."
    ::= { sw0657841IgmpGroupMembershipEntry 2 } 

sw0657841IgmpGroupVLANId  OBJECT-TYPE
    SYNTAX      INTEGER(1..4094)
    MAX-ACCESS  read-only
    STATUS      current
    DESCRIPTION  
        "The vlan id of multicast group membership entry."
    ::= { sw0657841IgmpGroupMembershipEntry 3 } 

sw0657841IgmpGroupPortMembers  OBJECT-TYPE
    SYNTAX      DisplayString
    MAX-ACCESS  read-only
    STATUS      current
    DESCRIPTION  
        "The port member of multicast group membership entry."
    ::= { sw0657841IgmpGroupMembershipEntry 4 } 


sw0657841TrapEntry	       OBJECT IDENTIFIER ::= { sw0657841Produces 20 }

sw0657841UserLogin NOTIFICATION-TYPE
    OBJECTS   {username}
	STATUS		current
	DESCRIPTION
	   "Send the trap when one user logins the system."
	::= { sw0657841TrapEntry 1 }

sw0657841UserLogout NOTIFICATION-TYPE
    OBJECTS   {username}
	STATUS		current
	DESCRIPTION
	   "Send the trap when one user logouts the system."
	::= { sw0657841TrapEntry 2 }

sw0657841ModuleInserted NOTIFICATION-TYPE
    OBJECTS { ifIndex }
	STATUS    current
	DESCRIPTION
	    "Send the trap when a module is inserted to the system. The OID value means
	     the port number."
	::= { sw0657841TrapEntry 3 }

sw0657841ModuleRemoved NOTIFICATION-TYPE
    OBJECTS { ifIndex }
	STATUS    current
	DESCRIPTION
	    "Send the trap when a module is removed from the system. The OID value means
	     the port number."
	::= { sw0657841TrapEntry 4 }

sw0657841DualMediaSwapped NOTIFICATION-TYPE
    OBJECTS { ifIndex }
	STATUS    current
	DESCRIPTION
	    "Send the trap when the dual media port changed. The OID value means the port number."
	::= { sw0657841TrapEntry 5 }

sw0657841LoopDetected NOTIFICATION-TYPE
    OBJECTS { ifIndex }
	STATUS    current
	DESCRIPTION
	    "Send the trap when loop condition has been detected. The OID value means the port number."
	::= { sw0657841TrapEntry 6 }

sw0657841StpStateDisabled NOTIFICATION-TYPE
	STATUS		current
	DESCRIPTION
	   "Send the trap when the operational state of STP is from enabled to disabled. "
	::= { sw0657841TrapEntry 7 }

sw0657841StpStateEnabled NOTIFICATION-TYPE
	STATUS		current
	DESCRIPTION
	   "Send the trap when the operational state of STP is from disabled to enabled. "
	::= { sw0657841TrapEntry 8 }

sw0657841StpTopologyChanged NOTIFICATION-TYPE
    OBJECTS { ifIndex }
	STATUS		current
	DESCRIPTION
	   "Send the trap when RSTP determines a port should enter the FORWARDING state
	    (a topology change occurs). The OID value is the ifIndex of the port that
	    produces the topology change."
	::= { sw0657841TrapEntry 9 }

sw0657841LacpStateDisabled NOTIFICATION-TYPE
    OBJECTS {ifIndex, groupId}
	STATUS		current
	DESCRIPTION
	   "Send the trap when the operational state of LACP is from enabled to disabled.
	    The OID value means the disabled Group ID."
	::= { sw0657841TrapEntry 10 }

sw0657841LacpStateEnabled NOTIFICATION-TYPE
    OBJECTS {ifIndex, groupId}
	STATUS		current
	DESCRIPTION
	   "Send the trap when the operational state of LACP is from disabled to enabled.
	    The OID value means the disabled Group ID."
	::= { sw0657841TrapEntry 11 }

sw0657841LacpPortAdded NOTIFICATION-TYPE
    OBJECTS   { ifIndex, actorkey, partnerkey }
	STATUS		current
	DESCRIPTION
	   "Send the trap when the state of port is in 'trunk ready'."
	::= { sw0657841TrapEntry 12 }

sw0657841LacpPortTrunkFailure NOTIFICATION-TYPE
    OBJECTS   { ifIndex, actorkey, partnerkey}
	STATUS		current
	DESCRIPTION
	   "Send the trap when one port is not able to be aggregated
	    due to duplex-mode of the port."
	::= { sw0657841TrapEntry 13 }

sw0657841GvrpStateDisabled NOTIFICATION-TYPE
	STATUS		current
	DESCRIPTION
	   "Send the trap when the operational state of GVRP is from enabled to disabled."
	::= { sw0657841TrapEntry 14 }

sw0657841GvrpStateEnabled NOTIFICATION-TYPE
	STATUS		current
	DESCRIPTION
	   "Send the trap when the operational state of LACP is from disabled to enabled. "
	::= { sw0657841TrapEntry 15 }

sw0657841VlanStateDisabled NOTIFICATION-TYPE
	STATUS		current
	DESCRIPTION
	   "Send the trap when the operational state of vlan is from enabled to disabled.
	    The OID value means the enabled Group ID. "
	::= { sw0657841TrapEntry 16 }

sw0657841VlanPortBaseEnabled NOTIFICATION-TYPE
	STATUS		current
	DESCRIPTION
	   "Send the trap when the operational state of vlan is changed to port-based vlan."
	::= { sw0657841TrapEntry 17 }

sw0657841VlanTagBaseEnabled NOTIFICATION-TYPE
	STATUS		current
	DESCRIPTION
	   "Send the trap when the operational state of vlan is changed to tag-based vlan."
	::= { sw0657841TrapEntry 18 }
	
sw0657841IpmbStateEnabled NOTIFICATION-TYPE
	STATUS		current
	DESCRIPTION
	   "Send trap when ip_mac_binding is enabled."
	::= { sw0657841TrapEntry 19 }

sw0657841IpmbStateDisabled NOTIFICATION-TYPE
	STATUS		current
	DESCRIPTION
	   "Send trap when ip_mac_binding is disabled."
	::= { sw0657841TrapEntry 20 }
	
sw0657841IpmbClientFailure NOTIFICATION-TYPE
    OBJECTS   { ipmacIp, ipmacMac, ifIndex}
	STATUS		current
	DESCRIPTION
	   "Send trap when ip_mac_binding entry not exist."
	::= { sw0657841TrapEntry 21 }	
	
sw0657841IpmbServerFailure NOTIFICATION-TYPE
    OBJECTS   { ipmacClientIp, ipmacClientMac, ifIndex, ipmacServerIp}
	STATUS		current
	DESCRIPTION
	   "Send trap when ip_mac_binding entry not exist."
	::= { sw0657841TrapEntry 22 }	

sw0657841TrapVariable	OBJECT IDENTIFIER ::= { sw0657841Produces 22 }

username OBJECT-TYPE
    SYNTAX      DisplayString
	MAX-ACCESS  read-only
	STATUS      current
	DESCRIPTION
	    "System account name."
	::= { sw0657841TrapVariable 1 }

groupId OBJECT-TYPE
    SYNTAX      INTEGER(1..2147483647)
	MAX-ACCESS  read-only
	STATUS      current
	DESCRIPTION
	    "The Trunk group ID of LACP."
	::= { sw0657841TrapVariable 2 }

actorkey OBJECT-TYPE
    SYNTAX	INTEGER(1..2147483647)
	MAX-ACCESS  read-only
	STATUS      current
	DESCRIPTION
	    "This is the actor key information for LACP."
	::= { sw0657841TrapVariable 3 }

partnerkey OBJECT-TYPE
    SYNTAX	INTEGER(1..2147483647)
	MAX-ACCESS  read-only
	STATUS      current
	DESCRIPTION
	    "This is the partner key information for LACP."
	::= { sw0657841TrapVariable 4 }

uplink OBJECT-TYPE
    SYNTAX	DisplayString
	MAX-ACCESS  read-only
	STATUS      current
	DESCRIPTION
	    "Uplink port(s) in the metro-mode vlan."
	::= { sw0657841TrapVariable 5 }
	
ipmacIp OBJECT-TYPE
    SYNTAX	DisplayString
	MAX-ACCESS  read-only
	STATUS      current
	DESCRIPTION
	    "IP address of the ip_mac_binding entry."
	::= { sw0657841TrapVariable 7 }	
	
ipmacMac OBJECT-TYPE
    SYNTAX	DisplayString
	MAX-ACCESS  read-only
	STATUS      current
	DESCRIPTION
	    "MAC address of the ip_mac_binding entry."
	::= { sw0657841TrapVariable 8 }			
	
ipmacClientIp OBJECT-TYPE
    SYNTAX	DisplayString
	MAX-ACCESS  read-only
	STATUS      current
	DESCRIPTION
	    "IP address of the ip_mac_binding entry."
	::= { sw0657841TrapVariable 9 }		

ipmacClientMac OBJECT-TYPE
    SYNTAX	DisplayString
	MAX-ACCESS  read-only
	STATUS      current
	DESCRIPTION
	    "MAC address of the ip_mac_binding entry."
	::= { sw0657841TrapVariable 10 }	
	
ipmacServerIp OBJECT-TYPE
    SYNTAX	DisplayString
	MAX-ACCESS  read-only
	STATUS      current
	DESCRIPTION
	    "IP address of the ip_mac_binding entry."
	::= { sw0657841TrapVariable 11 }	
		
END
