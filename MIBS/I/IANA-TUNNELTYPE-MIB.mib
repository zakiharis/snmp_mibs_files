-- extracted from draft-thaler-inet-tunnel-mib-00.txt
-- at Fri May 14 06:21:14 2004

IANA-TUNNELTYPE-MIB DEFINITIONS ::= BEGIN

IMPORTS
    MODULE-IDENTITY, mib-2           FROM SNMPv2-SMI
    TEXTUAL-CONVENTION               FROM SNMPv2-TC;

ianaTunnelTypeMIB MODULE-IDENTITY
    LAST-UPDATED "200310071200Z" -- October 7, 2003
    ORGANIZATION "IANA"
    CONTACT-INFO
            " Internet Assigned Numbers Authority
              Internet Corporation for Assigned Names and Numbers
              4676 Admiralty Way, Suite 330
              Marina del Rey, CA 90292-6601

              Phone: +1 310 823 9358
              EMail: iana@iana.org"
    DESCRIPTION
            "This MIB module defines the IANAtunnelType textual
            convention for use in MIBs which need to identify
            types of IP tunnels.

            To assign new tunnel type values, IANA should apply
            the same requirements as it applies to IANAifType
            values.  Requests for IANAifType values to be assigned
            for new IP tunnel types should instead result in
            assignments of new tunnel type values."
    REVISION     "200310071200Z" -- October 7, 2003
    DESCRIPTION
            "Initial version."
    ::= { mib-2 1 } -- TO BE ASSIGNED BY IANA

IANAtunnelType ::= TEXTUAL-CONVENTION
    STATUS     current
    DESCRIPTION
            "The encapsulation method used by a tunnel. The value
            direct indicates that a packet is encapsulated
            directly within a normal IP header, with no
            intermediate header, and unicast to the remote tunnel
            endpoint (e.g., an RFC 2003 IP-in-IP tunnel, or an RFC
            1933 IPv6-in-IPv4 tunnel). The value minimal indicates
            that a Minimal Forwarding Header (RFC 2004) is
            inserted between the outer header and the payload
            packet. The value UDP indicates that the payload
            packet is encapsulated within a normal UDP packet
            (e.g., RFC 1234).

            The values sixToFour, sixOverFour, and isatap
            indicates that an IPv6 packet is encapsulated directly
            within an IPv4 header, with no intermediate header,
            and unicast to the destination determined by the 6to4,
            6over4, or ISATAP protocol.

            The remaining protocol-specific values indicate that a
            header of the protocol of that name is inserted
            between the outer header and the payload header."
    SYNTAX     INTEGER {
                   other(1),        -- none of the following
                   direct(2),       -- no intermediate header
                   gre(3),          -- GRE encapsulation
                   minimal(4),      -- Minimal encapsulation
                   l2tp(5),         -- L2TP encapsulation
                   pptp(6),         -- PPTP encapsulation
                   l2f(7),          -- L2F encapsulation
                   udp(8),          -- UDP encapsulation
                   atmp(9),         -- ATMP encapsulation
                   msdp(10),        -- MSDP encapsulation
                   sixToFour(11),   -- 6to4 encapsulation
                   sixOverFour(12), -- 6over4 encapsulation
                   isatap(13),      -- ISATAP encapsulation
                   teredo(14)       -- Teredo encapsulation
               }

END

-- 
-- Copyright (C) The Internet Society (2003).  All Rights Reserved.
-- 
-- This document and translations of it may be copied and furnished
-- to others, and derivative works that comment on or otherwise
-- explain it or assist in its implmentation may be prepared, copied,
-- published and distributed, in whole or in part, without
-- restriction of any kind, provided that the above copyright notice
-- and this paragraph are included on all such copies and derivative
-- works.  However, this document itself may not be modified in any
-- way, such as by removing the copyright notice or references to the
-- Internet Society or other Internet organizations, except as needed
-- for the purpose of developing Internet standards in which case the
-- procedures for copyrights defined in the Internet Standards
-- process must be followed, or as required to translate it into
-- languages other than English.
-- 
-- The limited permissions granted above are perpetual and will not
-- be revoked by the Internet Society or its successors or assigns.
-- 
-- This document and the information contained herein is provided on
-- an "AS IS" basis and THE INTERNET SOCIETY AND THE INTERNET
-- ENGINEERING TASK FORCE DISCLAIMS ALL WARRANTIES, EXPRESS OR
-- IMPLIED, INCLUDING BUT NOT LIMITED TO ANY WARRANTY THAT THE USE OF
-- THE INFORMATION HEREIN WILL NOT INFRINGE ANY RIGHTS OR ANY IMPLIED
-- WARRANTIES OF MERCHANTABILITY OR FITNESS FOR A PARTICULAR PURPOSE.
-- 
--
