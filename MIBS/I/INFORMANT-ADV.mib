INFORMANT-ADV DEFINITIONS ::= BEGIN

IMPORTS
    MODULE-IDENTITY, OBJECT-TYPE, OBJECT-IDENTITY, Gauge32
        FROM SNMPv2-SMI
    InstanceName, informant
        FROM WTCS;

advanced MODULE-IDENTITY
    LAST-UPDATED "200606122258Z"
    ORGANIZATION "Informant Systems, Inc."
    CONTACT-INFO
            "        Garth Williams
                Tel: +1 780 433 7973
             E-mail: garth.williams@wtcs.org"
    DESCRIPTION
            "The MIB module for SNMP Informant Advanced
             performance counter entries."
    REVISION      "200606122258Z"
    DESCRIPTION
            ".NET CLR Data is an instance type
	     counter. Changed dotNETCLRData to a
	     SNMP table."
    REVISION      "200506182315Z"
    DESCRIPTION
            ".NET CLR Networking is an instance type
	     counter. Changed dotNETCLRNetworking to a
	     SNMP table."
    REVISION      "200402290703Z"
    DESCRIPTION
            "Changed the syntax of the datapoints from
			 integer to gauge."
    REVISION      "200401200850Z"
    DESCRIPTION
            "The initial revision of this MIB module."
    ::= { informant 2 }

acsPerRsvpServiceTable OBJECT-TYPE
    SYNTAX     SEQUENCE OF ACSPerRSVPServiceEntry
    MAX-ACCESS not-accessible
    STATUS     current
    DESCRIPTION
	    "The ACS/RSVP Service performance object
	    counters report statistics about Resource
	    Reservation Protocol (RSVP) and Quality of
	    Service (QoS) Admission Control (ACS) activity,
	    flow, bandwidth, RSVP messages sent, and so on.
	    The ACS/RSVP Service object is available if QoS
	    Admission Control is installed, even if the
	    service is not running."
    ::= { advanced 1 }

acsPerRsvpServiceEntry OBJECT-TYPE
    SYNTAX     ACSPerRSVPServiceEntry
    MAX-ACCESS not-accessible
    STATUS     current
    DESCRIPTION
	    "Performance information for one particular
	    instance of 'ACS/RSVP Service' object."
    INDEX      { acsPerRsvpSvcInstance }
    ::= { acsPerRsvpServiceTable 1 }

ACSPerRSVPServiceEntry ::= SEQUENCE {
    acsPerRsvpSvcInstance InstanceName,
    acsPerRsvpSvcBytesInQoSNotify Gauge32,
    acsPerRsvpSvcFailedQoSRequests Gauge32,
    acsPerRsvpSvcFailedQoSSends Gauge32,
    acsPerRsvpSvcNetworkInterfaces Gauge32,
    acsPerRsvpSvcNetworkSockets Gauge32,
    acsPerRsvpSvcQoSNotifications Gauge32,
    acsPerRsvpSvcQoSSockets Gauge32,
    acsPerRsvpSvcQoSEnabledReceivers Gauge32,
    acsPerRsvpSvcQoSEnabledSenders Gauge32,
    acsPerRsvpSvcRSVPSessions Gauge32,
    acsPerRsvpSvcTimers Gauge32
}

acsPerRsvpSvcInstance OBJECT-TYPE
    SYNTAX     InstanceName
    MAX-ACCESS read-only
    STATUS     current
    DESCRIPTION
	    "Instance name."
    ::= { acsPerRsvpServiceEntry 1 }

acsPerRsvpSvcBytesInQoSNotify OBJECT-TYPE
    SYNTAX     Gauge32
    MAX-ACCESS read-only
    STATUS     current
    DESCRIPTION
	    "A running total of the number of bytes
	    delivered in QoS Notifications to QoS-enabled
	    applications."
    ::= { acsPerRsvpServiceEntry 2 }

acsPerRsvpSvcFailedQoSRequests OBJECT-TYPE
    SYNTAX     Gauge32
    MAX-ACCESS read-only
    STATUS     current
    DESCRIPTION
	    "The number of QoS requests generated by
	    QoS-enabled applications that have been
	    rejected by the ACS/RSVP service. Failed QoS
	    requests can be caused by invalid QoS
	    requests."
    ::= { acsPerRsvpServiceEntry 3 }

acsPerRsvpSvcFailedQoSSends OBJECT-TYPE
    SYNTAX     Gauge32
    MAX-ACCESS read-only
    STATUS     current
    DESCRIPTION
	    "The number of QoS notifications the ACS/RSVP
	    service that could not be sent to the QoS
	    applications. Failed QoS sends can be caused by
	    terminated applications."
    ::= { acsPerRsvpServiceEntry 4 }

acsPerRsvpSvcNetworkInterfaces OBJECT-TYPE
    SYNTAX     Gauge32
    MAX-ACCESS read-only
    STATUS     current
    DESCRIPTION
	    "The number of local network interfaces visible
	    to, and used by the RSVP service."
    ::= { acsPerRsvpServiceEntry 5 }

acsPerRsvpSvcNetworkSockets OBJECT-TYPE
    SYNTAX     Gauge32
    MAX-ACCESS read-only
    STATUS     current
    DESCRIPTION
	    "The total number of raw sockets opened for the
	    purpose of RSVP signaling."
    ::= { acsPerRsvpServiceEntry 6 }

acsPerRsvpSvcQoSNotifications OBJECT-TYPE
    SYNTAX     Gauge32
    MAX-ACCESS read-only
    STATUS     current
    DESCRIPTION
	    "The number of QoS notifications delivered to
	    QoS-enabled applications by the QoS RSVP
	    service."
    ::= { acsPerRsvpServiceEntry 7 }

acsPerRsvpSvcQoSSockets OBJECT-TYPE
    SYNTAX     Gauge32
    MAX-ACCESS read-only
    STATUS     current
    DESCRIPTION
	    "The number of sockets that are currently QoS
	    enabled."
    ::= { acsPerRsvpServiceEntry 8 }

acsPerRsvpSvcQoSEnabledReceivers OBJECT-TYPE
    SYNTAX     Gauge32
    MAX-ACCESS read-only
    STATUS     current
    DESCRIPTION
	    "Indicates the number of RESV messages sent for
	    QoS-enabled receivers. This number increments
	    each time a RESV is refreshed."
    ::= { acsPerRsvpServiceEntry 9 }

acsPerRsvpSvcQoSEnabledSenders OBJECT-TYPE
    SYNTAX     Gauge32
    MAX-ACCESS read-only
    STATUS     current
    DESCRIPTION
	    "Indicates the number of PATH messages sent for
	    QoS-enabled senders. This number increments
	    each time a PATH is refreshed."
    ::= { acsPerRsvpServiceEntry 10 }

acsPerRsvpSvcRSVPSessions OBJECT-TYPE
    SYNTAX     Gauge32
    MAX-ACCESS read-only
    STATUS     current
    DESCRIPTION
	    "The current number of active RSVP sessions on
	    the ACS/RSVP service."
    ::= { acsPerRsvpServiceEntry 11 }

acsPerRsvpSvcTimers OBJECT-TYPE
    SYNTAX     Gauge32
    MAX-ACCESS read-only
    STATUS     current
    DESCRIPTION
	    "The number of timer events scheduled to take
	    place. Shows the activity level of the ACS/RSVP
	    service."
    ::= { acsPerRsvpServiceEntry 12 }

activeServerPages OBJECT-IDENTITY
    STATUS     current
    DESCRIPTION
	    "The Active Server Pages performance object
	    monitors errors, requests, sessions, or other
	    data generated from Active Server Pages (ASP)
	    applications."
    ::= { advanced 2 }

aspDebuggingRequests OBJECT-TYPE
    SYNTAX     Gauge32
    MAX-ACCESS read-only
    STATUS     current
    DESCRIPTION
	    "Number of debugging document requests."
    ::= { activeServerPages 1 }

aspEngineFlushNotifications OBJECT-TYPE
    SYNTAX     Gauge32
    MAX-ACCESS read-only
    STATUS     current
    DESCRIPTION
	    "The number of engines invalidated in the cache
	    due to change notification."
    ::= { activeServerPages 2 }

aspErrorsDuringScriptRuntime OBJECT-TYPE
    SYNTAX     Gauge32
    MAX-ACCESS read-only
    STATUS     current
    DESCRIPTION
	    "Number of requests failed due to runtime
	    errors."
    ::= { activeServerPages 3 }

aspErrorsFromASPPreprocessor OBJECT-TYPE
    SYNTAX     Gauge32
    MAX-ACCESS read-only
    STATUS     current
    DESCRIPTION
	    "Number of requests failed due to preprocessor
	    errors."
    ::= { activeServerPages 4 }

aspErrorsFromScriptCompilers OBJECT-TYPE
    SYNTAX     Gauge32
    MAX-ACCESS read-only
    STATUS     current
    DESCRIPTION
	    "Number of requests failed due to script
	    compilation errors."
    ::= { activeServerPages 5 }

aspErrorsPerSec OBJECT-TYPE
    SYNTAX     Gauge32
    MAX-ACCESS read-only
    STATUS     current
    DESCRIPTION
	    "The number of errors per second."
    ::= { activeServerPages 6 }

aspInMemoryTemplateCacheHitRate OBJECT-TYPE
    SYNTAX     Gauge32
    MAX-ACCESS read-only
    STATUS     current
    DESCRIPTION
	    "Percent of requests found in cached in
	    memory."
    ::= { activeServerPages 7 }

aspInMemoryTemplatesCached OBJECT-TYPE
    SYNTAX     Gauge32
    MAX-ACCESS read-only
    STATUS     current
    DESCRIPTION
	    "The number of compiled templates cached in
	    memory."
    ::= { activeServerPages 8 }

aspRequestBytesInTotal OBJECT-TYPE
    SYNTAX     Gauge32
    MAX-ACCESS read-only
    STATUS     current
    DESCRIPTION
	    "The total size, in bytes, of all requests."
    ::= { activeServerPages 9 }

aspRequestBytesOutTotal OBJECT-TYPE
    SYNTAX     Gauge32
    MAX-ACCESS read-only
    STATUS     current
    DESCRIPTION
	    "The total size, in bytes, of responses sent to
	    clients. This does not include standard HTTP
	    response headers."
    ::= { activeServerPages 10 }

aspRequestExecutionTime OBJECT-TYPE
    SYNTAX     Gauge32
    MAX-ACCESS read-only
    STATUS     current
    DESCRIPTION
	    "The number of milliseconds that it took to
	    execute the most recent request."
    ::= { activeServerPages 11 }

aspRequestWaitTime OBJECT-TYPE
    SYNTAX     Gauge32
    MAX-ACCESS read-only
    STATUS     current
    DESCRIPTION
	    "The number of milliseconds the most recent
	    request was waiting in the queue."
    ::= { activeServerPages 12 }

aspRequestsDisconnected OBJECT-TYPE
    SYNTAX     Gauge32
    MAX-ACCESS read-only
    STATUS     current
    DESCRIPTION
	    "The number of requests that were disconnected
	    due to communication failure."
    ::= { activeServerPages 13 }

aspRequestsExecuting OBJECT-TYPE
    SYNTAX     Gauge32
    MAX-ACCESS read-only
    STATUS     current
    DESCRIPTION
	    "The number of requests currently executing."
    ::= { activeServerPages 14 }

aspRequestsFailedTotal OBJECT-TYPE
    SYNTAX     Gauge32
    MAX-ACCESS read-only
    STATUS     current
    DESCRIPTION
	    "The total number of requests failed due to
	    errors, authorization failure, and rejections."
    ::= { activeServerPages 15 }

aspRequestsNotAuthorized OBJECT-TYPE
    SYNTAX     Gauge32
    MAX-ACCESS read-only
    STATUS     current
    DESCRIPTION
	    "Number of requests failed due to insufficient
	    access rights."
    ::= { activeServerPages 16 }

aspRequestsNotFound OBJECT-TYPE
    SYNTAX     Gauge32
    MAX-ACCESS read-only
    STATUS     current
    DESCRIPTION
	    "The number of requests for files that were no
	    found."
    ::= { activeServerPages 17 }

aspRequestsQueued OBJECT-TYPE
    SYNTAX     Gauge32
    MAX-ACCESS read-only
    STATUS     current
    DESCRIPTION
	    "The number of requests waiting for service
	    from the queue."
    ::= { activeServerPages 18 }

aspRequestsRejected OBJECT-TYPE
    SYNTAX     Gauge32
    MAX-ACCESS read-only
    STATUS     current
    DESCRIPTION
	    "The total number of requests not executed
	    because there were insufficient resources to
	    process them."
    ::= { activeServerPages 19 }

aspRequestsSucceeded OBJECT-TYPE
    SYNTAX     Gauge32
    MAX-ACCESS read-only
    STATUS     current
    DESCRIPTION
	    "The number of requests that executed
	    successfully."
    ::= { activeServerPages 20 }

aspRequestsTimedOut OBJECT-TYPE
    SYNTAX     Gauge32
    MAX-ACCESS read-only
    STATUS     current
    DESCRIPTION
	    "The number of requests that timed out."
    ::= { activeServerPages 21 }

aspRequestsTotal OBJECT-TYPE
    SYNTAX     Gauge32
    MAX-ACCESS read-only
    STATUS     current
    DESCRIPTION
	    "The total number of requests since the service
	    was started."
    ::= { activeServerPages 22 }

aspRequestsPerSec OBJECT-TYPE
    SYNTAX     Gauge32
    MAX-ACCESS read-only
    STATUS     current
    DESCRIPTION
	    "The number of requests executed per second."
    ::= { activeServerPages 23 }

aspScriptEngineCacheHitRate OBJECT-TYPE
    SYNTAX     Gauge32
    MAX-ACCESS read-only
    STATUS     current
    DESCRIPTION
	    "Percent of requests found in script engine
	    cache."
    ::= { activeServerPages 24 }

aspScriptEnginesCached OBJECT-TYPE
    SYNTAX     Gauge32
    MAX-ACCESS read-only
    STATUS     current
    DESCRIPTION
	    "The number of script engines in cache."
    ::= { activeServerPages 25 }

aspSessionDuration OBJECT-TYPE
    SYNTAX     Gauge32
    MAX-ACCESS read-only
    STATUS     current
    DESCRIPTION
	    "The number of milliseconds that the most
	    recent session persisted."
    ::= { activeServerPages 26 }

aspSessionsCurrent OBJECT-TYPE
    SYNTAX     Gauge32
    MAX-ACCESS read-only
    STATUS     current
    DESCRIPTION
	    "The current number of sessions being
	    serviced."
    ::= { activeServerPages 27 }

aspSessionsTimedOut OBJECT-TYPE
    SYNTAX     Gauge32
    MAX-ACCESS read-only
    STATUS     current
    DESCRIPTION
	    "The number of sessions timed out."
    ::= { activeServerPages 28 }

aspSessionsTotal OBJECT-TYPE
    SYNTAX     Gauge32
    MAX-ACCESS read-only
    STATUS     current
    DESCRIPTION
	    "The total number of sessions since the service
	    was started."
    ::= { activeServerPages 29 }

aspTemplateCacheHitRate OBJECT-TYPE
    SYNTAX     Gauge32
    MAX-ACCESS read-only
    STATUS     current
    DESCRIPTION
	    "Percent of requests found in template cache."
    ::= { activeServerPages 30 }

aspTemplateNotifications OBJECT-TYPE
    SYNTAX     Gauge32
    MAX-ACCESS read-only
    STATUS     current
    DESCRIPTION
	    "The number of templates invalidated in the
	    cache due to change notification."
    ::= { activeServerPages 31 }

aspTemplatesCached OBJECT-TYPE
    SYNTAX     Gauge32
    MAX-ACCESS read-only
    STATUS     current
    DESCRIPTION
	    "The number of templates currently cached."
    ::= { activeServerPages 32 }

aspTransactionsAborted OBJECT-TYPE
    SYNTAX     Gauge32
    MAX-ACCESS read-only
    STATUS     current
    DESCRIPTION
	    "The number of transactions aborted."
    ::= { activeServerPages 33 }

aspTransactionsCommitted OBJECT-TYPE
    SYNTAX     Gauge32
    MAX-ACCESS read-only
    STATUS     current
    DESCRIPTION
	    "The number of transactions committed."
    ::= { activeServerPages 34 }

aspTransactionsPending OBJECT-TYPE
    SYNTAX     Gauge32
    MAX-ACCESS read-only
    STATUS     current
    DESCRIPTION
	    "Number of transactions in progress."
    ::= { activeServerPages 35 }

aspTransactionsTotal OBJECT-TYPE
    SYNTAX     Gauge32
    MAX-ACCESS read-only
    STATUS     current
    DESCRIPTION
	    "The total number of transactions since the
	    service was started."
    ::= { activeServerPages 36 }

aspTransactionsPerSec OBJECT-TYPE
    SYNTAX     Gauge32
    MAX-ACCESS read-only
    STATUS     current
    DESCRIPTION
	    "Transactions started per second."
    ::= { activeServerPages 37 }

appleTalkTable OBJECT-TYPE
    SYNTAX     SEQUENCE OF AppleTalkEntry
    MAX-ACCESS not-accessible
    STATUS     current
    DESCRIPTION
	    "The AppleTalk performance object consists of
	    counters that monitor traffic on the AppleTalk
	    network."
    ::= { advanced 3 }

appleTalkEntry OBJECT-TYPE
    SYNTAX     AppleTalkEntry
    MAX-ACCESS not-accessible
    STATUS     current
    DESCRIPTION
	    "Performance information for one particular
	    instance of 'AppleTalk' object."
    INDEX      { atInstance }
    ::= { appleTalkTable 1 }

AppleTalkEntry ::= SEQUENCE {
    atInstance InstanceName,
    atAARPPacketsPerSec Gauge32,
    atATPALOResponsePerSec Gauge32,
    atATPPacketsPerSec Gauge32,
    atATPRecvdReleasePerSec Gauge32,
    atATPResponseTimouts Gauge32,
    atATPRetriesLocal Gauge32,
    atATPRetriesRemote Gauge32,
    atATPXOResponsePerSec Gauge32,
    atAverageTimePerAARPPacket Gauge32,
    atAverageTimePerATPPacket Gauge32,
    atAverageTimePerDDPPacket Gauge32,
    atAverageTimePerNBPPacket Gauge32,
    atAverageTimePerRTMPPacket Gauge32,
    atAverageTimePerZIPPacket Gauge32,
    atBytesInPerSec Gauge32,
    atBytesOutPerSec Gauge32,
    atCurrentNonPagedPool Gauge32,
    atDDPPacketsPerSec Gauge32,
    atNBPPacketsPerSec Gauge32,
    atPacketsInPerSec Gauge32,
    atPacketsOutPerSec Gauge32,
    atPacketsRoutedInPerSec Gauge32,
    atPacketsRoutedOutPerSec Gauge32,
    atPacketsDropped Gauge32,
    atRTMPPacketsPerSec Gauge32,
    atZIPPacketsPerSec Gauge32
}

atInstance OBJECT-TYPE
    SYNTAX     InstanceName
    MAX-ACCESS read-only
    STATUS     current
    DESCRIPTION
	    "Instance name."
    ::= { appleTalkEntry 1 }

atAARPPacketsPerSec OBJECT-TYPE
    SYNTAX     Gauge32
    MAX-ACCESS read-only
    STATUS     current
    DESCRIPTION
	    "Number of AARP packets per second received by
	    Appletalk on this port."
    ::= { appleTalkEntry 2 }

atATPALOResponsePerSec OBJECT-TYPE
    SYNTAX     Gauge32
    MAX-ACCESS read-only
    STATUS     current
    DESCRIPTION
	    "Number of ATP At-least-once transaction
	    responses per second on this port."
    ::= { appleTalkEntry 3 }

atATPPacketsPerSec OBJECT-TYPE
    SYNTAX     Gauge32
    MAX-ACCESS read-only
    STATUS     current
    DESCRIPTION
	    "Number of ATP packets per second received by
	    Appletalk on this port."
    ::= { appleTalkEntry 4 }

atATPRecvdReleasePerSec OBJECT-TYPE
    SYNTAX     Gauge32
    MAX-ACCESS read-only
    STATUS     current
    DESCRIPTION
	    "Number of ATP transaction release packets per
	    second received on this port."
    ::= { appleTalkEntry 5 }

atATPResponseTimouts OBJECT-TYPE
    SYNTAX     Gauge32
    MAX-ACCESS read-only
    STATUS     current
    DESCRIPTION
	    "Number of ATP release timers that have expired
	    on this port."
    ::= { appleTalkEntry 6 }

atATPRetriesLocal OBJECT-TYPE
    SYNTAX     Gauge32
    MAX-ACCESS read-only
    STATUS     current
    DESCRIPTION
	    "Number of ATP requests retransmitted on this
	    port."
    ::= { appleTalkEntry 7 }

atATPRetriesRemote OBJECT-TYPE
    SYNTAX     Gauge32
    MAX-ACCESS read-only
    STATUS     current
    DESCRIPTION
	    "Number of ATP requests retransmitted to this
	    port."
    ::= { appleTalkEntry 8 }

atATPXOResponsePerSec OBJECT-TYPE
    SYNTAX     Gauge32
    MAX-ACCESS read-only
    STATUS     current
    DESCRIPTION
	    "Number of ATP Exactly-once transaction
	    responses per second on this port."
    ::= { appleTalkEntry 9 }

atAverageTimePerAARPPacket OBJECT-TYPE
    SYNTAX     Gauge32
    MAX-ACCESS read-only
    STATUS     current
    DESCRIPTION
	    "Average time in milliseconds to process an
	    AARP packet on this port."
    ::= { appleTalkEntry 10 }

atAverageTimePerATPPacket OBJECT-TYPE
    SYNTAX     Gauge32
    MAX-ACCESS read-only
    STATUS     current
    DESCRIPTION
	    "Average time in milliseconds to process an ATP
	    packet on this port."
    ::= { appleTalkEntry 11 }

atAverageTimePerDDPPacket OBJECT-TYPE
    SYNTAX     Gauge32
    MAX-ACCESS read-only
    STATUS     current
    DESCRIPTION
	    "Average time in milliseconds to process a DDP
	    packet on this port."
    ::= { appleTalkEntry 12 }

atAverageTimePerNBPPacket OBJECT-TYPE
    SYNTAX     Gauge32
    MAX-ACCESS read-only
    STATUS     current
    DESCRIPTION
	    "Average time in milliseconds to process an NBP
	    packet on this port."
    ::= { appleTalkEntry 13 }

atAverageTimePerRTMPPacket OBJECT-TYPE
    SYNTAX     Gauge32
    MAX-ACCESS read-only
    STATUS     current
    DESCRIPTION
	    "Average time in milliseconds to process an
	    RTMP packet on this port."
    ::= { appleTalkEntry 14 }

atAverageTimePerZIPPacket OBJECT-TYPE
    SYNTAX     Gauge32
    MAX-ACCESS read-only
    STATUS     current
    DESCRIPTION
	    "Average time in milliseconds to process a ZIP
	    packet on this port."
    ::= { appleTalkEntry 15 }

atBytesInPerSec OBJECT-TYPE
    SYNTAX     Gauge32
    MAX-ACCESS read-only
    STATUS     current
    DESCRIPTION
	    "Number of bytes received per second by
	    Appletalk on this port."
    ::= { appleTalkEntry 16 }

atBytesOutPerSec OBJECT-TYPE
    SYNTAX     Gauge32
    MAX-ACCESS read-only
    STATUS     current
    DESCRIPTION
	    "Number of bytes sent per second by Appletalk
	    on this port."
    ::= { appleTalkEntry 17 }

atCurrentNonPagedPool OBJECT-TYPE
    SYNTAX     Gauge32
    MAX-ACCESS read-only
    STATUS     current
    DESCRIPTION
	    "The current amount of nonpaged memory
	    resources used by AppleTalk."
    ::= { appleTalkEntry 18 }

atDDPPacketsPerSec OBJECT-TYPE
    SYNTAX     Gauge32
    MAX-ACCESS read-only
    STATUS     current
    DESCRIPTION
	    "Number of DDP packets per second received by
	    Appletalk on this port."
    ::= { appleTalkEntry 19 }

atNBPPacketsPerSec OBJECT-TYPE
    SYNTAX     Gauge32
    MAX-ACCESS read-only
    STATUS     current
    DESCRIPTION
	    "Number of NBP packets per second received by
	    Appletalk on this port."
    ::= { appleTalkEntry 20 }

atPacketsInPerSec OBJECT-TYPE
    SYNTAX     Gauge32
    MAX-ACCESS read-only
    STATUS     current
    DESCRIPTION
	    "Number of packets received per second by
	    Appletalk on this port."
    ::= { appleTalkEntry 21 }

atPacketsOutPerSec OBJECT-TYPE
    SYNTAX     Gauge32
    MAX-ACCESS read-only
    STATUS     current
    DESCRIPTION
	    "Number of packets sent per second by Appletalk
	    on this port."
    ::= { appleTalkEntry 22 }

atPacketsRoutedInPerSec OBJECT-TYPE
    SYNTAX     Gauge32
    MAX-ACCESS read-only
    STATUS     current
    DESCRIPTION
	    "Number of packets routed in on this port."
    ::= { appleTalkEntry 23 }

atPacketsRoutedOutPerSec OBJECT-TYPE
    SYNTAX     Gauge32
    MAX-ACCESS read-only
    STATUS     current
    DESCRIPTION
	    "Number of packets routed out on this port."
    ::= { appleTalkEntry 24 }

atPacketsDropped OBJECT-TYPE
    SYNTAX     Gauge32
    MAX-ACCESS read-only
    STATUS     current
    DESCRIPTION
	    "Number of packets dropped due to resource
	    limitations on this port."
    ::= { appleTalkEntry 25 }

atRTMPPacketsPerSec OBJECT-TYPE
    SYNTAX     Gauge32
    MAX-ACCESS read-only
    STATUS     current
    DESCRIPTION
	    "Number of RTMP packets per second received by
	    Appletalk on this port."
    ::= { appleTalkEntry 26 }

atZIPPacketsPerSec OBJECT-TYPE
    SYNTAX     Gauge32
    MAX-ACCESS read-only
    STATUS     current
    DESCRIPTION
	    "Number of ZIP packets per second received by
	    Appletalk on this port."
    ::= { appleTalkEntry 27 }

aspDotNET OBJECT-IDENTITY
    STATUS     current
    DESCRIPTION
	    "ASP.NET supports the following ASP.NET system
	    performance counters. These aggregate
	    information for all ASP.NET applications on a
	    Web server computer, or they apply generally to
	    a system of ASP.NET servers running the same
	    applications. These can include Web farms and
	    Web gardens."
    ::= { advanced 4 }

adnApplicationRestarts OBJECT-TYPE
    SYNTAX     Gauge32
    MAX-ACCESS read-only
    STATUS     current
    DESCRIPTION
	    "Number of times the application has been
	    restarted during the web server's lifetime."
    ::= { aspDotNET 1 }

adnApplicationsRunning OBJECT-TYPE
    SYNTAX     Gauge32
    MAX-ACCESS read-only
    STATUS     current
    DESCRIPTION
	    "Number of currently running web applications."
    ::= { aspDotNET 2 }

adnRequestExecutionTime OBJECT-TYPE
    SYNTAX     Gauge32
    MAX-ACCESS read-only
    STATUS     current
    DESCRIPTION
	    "The number of milliseconds that it took to
	    execute the most recent request."
    ::= { aspDotNET 3 }

adnRequestWaitTime OBJECT-TYPE
    SYNTAX     Gauge32
    MAX-ACCESS read-only
    STATUS     current
    DESCRIPTION
	    "The number of milliseconds the most recent
	    request was waiting in the queue."
    ::= { aspDotNET 4 }

adnRequestsCurrent OBJECT-TYPE
    SYNTAX     Gauge32
    MAX-ACCESS read-only
    STATUS     current
    DESCRIPTION
	    "The current number of requests, including
	    those that are queued, currently executing, or
	    waiting to be written to the client.  Under the
	    ASP.NET process model, when this counter
	    exceeds the requestQueueLimit defined in the
	    processModel configuration section, ASP.NET
	    will begin rejecting requests."
    ::= { aspDotNET 5 }

adnRequestsDisconnected OBJECT-TYPE
    SYNTAX     Gauge32
    MAX-ACCESS read-only
    STATUS     current
    DESCRIPTION
	    "The number of requests disconnected due to
	    communication errors or user terminated."
    ::= { aspDotNET 6 }

adnRequestsQueued OBJECT-TYPE
    SYNTAX     Gauge32
    MAX-ACCESS read-only
    STATUS     current
    DESCRIPTION
	    "The number of requests waiting to be
	    processed."
    ::= { aspDotNET 7 }

adnRequestsRejected OBJECT-TYPE
    SYNTAX     Gauge32
    MAX-ACCESS read-only
    STATUS     current
    DESCRIPTION
	    "The number of requests rejected because the
	    request queue was full."
    ::= { aspDotNET 8 }

adnStateServerSessionsAbandoned OBJECT-TYPE
    SYNTAX     Gauge32
    MAX-ACCESS read-only
    STATUS     current
    DESCRIPTION
	    "The number of sessions that have been
	    explicitly abandoned."
    ::= { aspDotNET 9 }

adnStateServerSessionsActive OBJECT-TYPE
    SYNTAX     Gauge32
    MAX-ACCESS read-only
    STATUS     current
    DESCRIPTION
	    "The current number of sessions currently
	    active."
    ::= { aspDotNET 10 }

adnStateServerSessionsTimedOut OBJECT-TYPE
    SYNTAX     Gauge32
    MAX-ACCESS read-only
    STATUS     current
    DESCRIPTION
	    "The number of sessions timed out."
    ::= { aspDotNET 11 }

adnStateServerSessionsTotal OBJECT-TYPE
    SYNTAX     Gauge32
    MAX-ACCESS read-only
    STATUS     current
    DESCRIPTION
	    "The number of sessions total."
    ::= { aspDotNET 12 }

adnWorkerProcessRestarts OBJECT-TYPE
    SYNTAX     Gauge32
    MAX-ACCESS read-only
    STATUS     current
    DESCRIPTION
	    "Number of times a worker process has restarted
	    on the machine."
    ::= { aspDotNET 13 }

adnWorkerProcessesRunning OBJECT-TYPE
    SYNTAX     Gauge32
    MAX-ACCESS read-only
    STATUS     current
    DESCRIPTION
	    "Number of worker processes running on the
	    machine."
    ::= { aspDotNET 14 }

aspDotNETApplicationsTable OBJECT-TYPE
    SYNTAX     SEQUENCE OF ASPNETApplicationsEntry
    MAX-ACCESS not-accessible
    STATUS     current
    DESCRIPTION
	    "ASP.NET supports the following application
	    performance counters, which you can use to
	    monitor the performance of a single instance of
	    an ASP.NET application. A unique instance
	    appears for these counters, named __Total__,
	    which aggregates counters for all applications
	    on a Web server (similar to the global counters
	    described in the first section of this topic).
	    The __Total__ instance is always available. The
	    counters will display zero when no applications
	    are present on the server."
    ::= { advanced 5 }

aspDotNETApplicationsEntry OBJECT-TYPE
    SYNTAX     ASPNETApplicationsEntry
    MAX-ACCESS not-accessible
    STATUS     current
    DESCRIPTION
	    "Performance information for one particular
	    instance of 'ASP.NET Applications' object."
    INDEX      { adnApplInstance }
    ::= { aspDotNETApplicationsTable 1 }

ASPNETApplicationsEntry ::= SEQUENCE {
    adnApplInstance InstanceName,
    adnApplAnonymousRequests Gauge32,
    adnApplAnonymousRequestsPerSec Gauge32,
    adnApplCacheAPIEntries Gauge32,
    adnApplCacheAPIHitRatio Gauge32,
    adnApplCacheAPIHits Gauge32,
    adnApplCacheAPIMisses Gauge32,
    adnApplCacheAPITurnoverRate Gauge32,
    adnApplCacheTotalEntries Gauge32,
    adnApplCacheTotalHitRatio Gauge32,
    adnApplCacheTotalHits Gauge32,
    adnApplCacheTotalMisses Gauge32,
    adnApplCacheTotalTurnoverRate Gauge32,
    adnApplCompilationsTotal Gauge32,
    adnApplDebuggingRequests Gauge32,
    adnApplErrorsCompilation Gauge32,
    adnApplErrorsExecution Gauge32,
    adnApplErrorsPreprocessing Gauge32,
    adnApplErrorsTotal Gauge32,
    adnApplErrorsTotalPerSec Gauge32,
    adnApplErrorsUnhandledExec Gauge32,
    adnApplErrorsUnhandledExecPerSec Gauge32,
    adnApplOutputCacheEntries Gauge32,
    adnApplOutputCacheHitRatio Gauge32,
    adnApplOutputCacheHits Gauge32,
    adnApplOutputCacheMisses Gauge32,
    adnApplOutputCacheTurnoverRate Gauge32,
    adnApplPipelineInstanceCount Gauge32,
    adnApplRequestBytesInTotal Gauge32,
    adnApplRequestBytesOutTotal Gauge32,
    adnApplRequestsExecuting Gauge32,
    adnApplRequestsFailed Gauge32,
    adnApplRequestsInApplQueue Gauge32,
    adnApplRequestsNotAuthorized Gauge32,
    adnApplRequestsNotFound Gauge32,
    adnApplRequestsSucceeded Gauge32,
    adnApplRequestsTimedOut Gauge32,
    adnApplRequestsTotal Gauge32,
    adnApplRequestsPerSec Gauge32,
    adnApplSessionSQLSrvrConnTotal Gauge32,
    adnApplSessionStateSrvrConnTotal Gauge32,
    adnApplSessionsAbandoned Gauge32,
    adnApplSessionsActive Gauge32,
    adnApplSessionsTimedOut Gauge32,
    adnApplSessionsTotal Gauge32,
    adnApplTransactionsAborted Gauge32,
    adnApplTransactionsCommitted Gauge32,
    adnApplTransactionsPending Gauge32,
    adnApplTransactionsTotal Gauge32,
    adnApplTransactionsPerSec Gauge32
}

adnApplInstance OBJECT-TYPE
    SYNTAX     InstanceName
    MAX-ACCESS read-only
    STATUS     current
    DESCRIPTION
	    "Instance name."
    ::= { aspDotNETApplicationsEntry 1 }

adnApplAnonymousRequests OBJECT-TYPE
    SYNTAX     Gauge32
    MAX-ACCESS read-only
    STATUS     current
    DESCRIPTION
	    "Number of requests utilizing anonymous
	    authentication."
    ::= { aspDotNETApplicationsEntry 2 }

adnApplAnonymousRequestsPerSec OBJECT-TYPE
    SYNTAX     Gauge32
    MAX-ACCESS read-only
    STATUS     current
    DESCRIPTION
	    "Number of Authentication Anonymous
	    Requests/Sec"
    ::= { aspDotNETApplicationsEntry 3 }

adnApplCacheAPIEntries OBJECT-TYPE
    SYNTAX     Gauge32
    MAX-ACCESS read-only
    STATUS     current
    DESCRIPTION
	    "Total number of entries within the cache added
	    by the user."
    ::= { aspDotNETApplicationsEntry 4 }

adnApplCacheAPIHitRatio OBJECT-TYPE
    SYNTAX     Gauge32
    MAX-ACCESS read-only
    STATUS     current
    DESCRIPTION
	    "Ratio of hits called from user code."
    ::= { aspDotNETApplicationsEntry 5 }

adnApplCacheAPIHits OBJECT-TYPE
    SYNTAX     Gauge32
    MAX-ACCESS read-only
    STATUS     current
    DESCRIPTION
	    "Number of cache hits from user code."
    ::= { aspDotNETApplicationsEntry 6 }

adnApplCacheAPIMisses OBJECT-TYPE
    SYNTAX     Gauge32
    MAX-ACCESS read-only
    STATUS     current
    DESCRIPTION
	    "Number of cache misses called from user code."
    ::= { aspDotNETApplicationsEntry 7 }

adnApplCacheAPITurnoverRate OBJECT-TYPE
    SYNTAX     Gauge32
    MAX-ACCESS read-only
    STATUS     current
    DESCRIPTION
	    "Number of additions and removals to the API
	    cache per second."
    ::= { aspDotNETApplicationsEntry 8 }

adnApplCacheTotalEntries OBJECT-TYPE
    SYNTAX     Gauge32
    MAX-ACCESS read-only
    STATUS     current
    DESCRIPTION
	    "Total number of entries within the cache (both
	    internal and user added)"
    ::= { aspDotNETApplicationsEntry 9 }

adnApplCacheTotalHitRatio OBJECT-TYPE
    SYNTAX     Gauge32
    MAX-ACCESS read-only
    STATUS     current
    DESCRIPTION
	    "Ratio of hits from all cache calls."
    ::= { aspDotNETApplicationsEntry 10 }

adnApplCacheTotalHits OBJECT-TYPE
    SYNTAX     Gauge32
    MAX-ACCESS read-only
    STATUS     current
    DESCRIPTION
	    "Total number of hits from the cache."
    ::= { aspDotNETApplicationsEntry 11 }

adnApplCacheTotalMisses OBJECT-TYPE
    SYNTAX     Gauge32
    MAX-ACCESS read-only
    STATUS     current
    DESCRIPTION
	    "Total number of cache misses."
    ::= { aspDotNETApplicationsEntry 12 }

adnApplCacheTotalTurnoverRate OBJECT-TYPE
    SYNTAX     Gauge32
    MAX-ACCESS read-only
    STATUS     current
    DESCRIPTION
	    "Number of additions and removals to the total
	    cache per second."
    ::= { aspDotNETApplicationsEntry 13 }

adnApplCompilationsTotal OBJECT-TYPE
    SYNTAX     Gauge32
    MAX-ACCESS read-only
    STATUS     current
    DESCRIPTION
	    "Number of .asax, .ascx, .ashx, .asmx, or .aspx
	    source files dynamically compiled."
    ::= { aspDotNETApplicationsEntry 14 }

adnApplDebuggingRequests OBJECT-TYPE
    SYNTAX     Gauge32
    MAX-ACCESS read-only
    STATUS     current
    DESCRIPTION
	    "Number of debugging requests processed."
    ::= { aspDotNETApplicationsEntry 15 }

adnApplErrorsCompilation OBJECT-TYPE
    SYNTAX     Gauge32
    MAX-ACCESS read-only
    STATUS     current
    DESCRIPTION
	    "Number of errors that have occurred during
	    compilation."
    ::= { aspDotNETApplicationsEntry 16 }

adnApplErrorsExecution OBJECT-TYPE
    SYNTAX     Gauge32
    MAX-ACCESS read-only
    STATUS     current
    DESCRIPTION
	    "Number of errors that have occurred during the
	    processing of a request."
    ::= { aspDotNETApplicationsEntry 17 }

adnApplErrorsPreprocessing OBJECT-TYPE
    SYNTAX     Gauge32
    MAX-ACCESS read-only
    STATUS     current
    DESCRIPTION
	    "Number of errors that have occurred during
	    parsing and configuration."
    ::= { aspDotNETApplicationsEntry 18 }

adnApplErrorsTotal OBJECT-TYPE
    SYNTAX     Gauge32
    MAX-ACCESS read-only
    STATUS     current
    DESCRIPTION
	    "Total number of errors occurred."
    ::= { aspDotNETApplicationsEntry 19 }

adnApplErrorsTotalPerSec OBJECT-TYPE
    SYNTAX     Gauge32
    MAX-ACCESS read-only
    STATUS     current
    DESCRIPTION
	    "Rate of errors occurred."
    ::= { aspDotNETApplicationsEntry 20 }

adnApplErrorsUnhandledExec OBJECT-TYPE
    SYNTAX     Gauge32
    MAX-ACCESS read-only
    STATUS     current
    DESCRIPTION
	    "Number of errors not handled by user code, but
	    by the default error handler."
    ::= { aspDotNETApplicationsEntry 21 }

adnApplErrorsUnhandledExecPerSec OBJECT-TYPE
    SYNTAX     Gauge32
    MAX-ACCESS read-only
    STATUS     current
    DESCRIPTION
	    "Rate of unhandled errors."
    ::= { aspDotNETApplicationsEntry 22 }

adnApplOutputCacheEntries OBJECT-TYPE
    SYNTAX     Gauge32
    MAX-ACCESS read-only
    STATUS     current
    DESCRIPTION
	    "Current number of entries in the output
	    cache."
    ::= { aspDotNETApplicationsEntry 23 }

adnApplOutputCacheHitRatio OBJECT-TYPE
    SYNTAX     Gauge32
    MAX-ACCESS read-only
    STATUS     current
    DESCRIPTION
	    "Ratio of hits to requests for output cacheable
	    requests."
    ::= { aspDotNETApplicationsEntry 24 }

adnApplOutputCacheHits OBJECT-TYPE
    SYNTAX     Gauge32
    MAX-ACCESS read-only
    STATUS     current
    DESCRIPTION
	    "Total number of ouput cacheable requests
	    served from the output cache."
    ::= { aspDotNETApplicationsEntry 25 }

adnApplOutputCacheMisses OBJECT-TYPE
    SYNTAX     Gauge32
    MAX-ACCESS read-only
    STATUS     current
    DESCRIPTION
	    "Total number of ouput cacheable requests not
	    served from the output cache."
    ::= { aspDotNETApplicationsEntry 26 }

adnApplOutputCacheTurnoverRate OBJECT-TYPE
    SYNTAX     Gauge32
    MAX-ACCESS read-only
    STATUS     current
    DESCRIPTION
	    "Number of additions and removals to the output
	    cache per second."
    ::= { aspDotNETApplicationsEntry 27 }

adnApplPipelineInstanceCount OBJECT-TYPE
    SYNTAX     Gauge32
    MAX-ACCESS read-only
    STATUS     current
    DESCRIPTION
	    "Number of active pipeline instances."
    ::= { aspDotNETApplicationsEntry 28 }

adnApplRequestBytesInTotal OBJECT-TYPE
    SYNTAX     Gauge32
    MAX-ACCESS read-only
    STATUS     current
    DESCRIPTION
	    "The total size, in bytes, of all requests."
    ::= { aspDotNETApplicationsEntry 29 }

adnApplRequestBytesOutTotal OBJECT-TYPE
    SYNTAX     Gauge32
    MAX-ACCESS read-only
    STATUS     current
    DESCRIPTION
	    "The total size, in bytes, of responses sent to
	    a client.  This does not include standard HTTP
	    response headers."
    ::= { aspDotNETApplicationsEntry 30 }

adnApplRequestsExecuting OBJECT-TYPE
    SYNTAX     Gauge32
    MAX-ACCESS read-only
    STATUS     current
    DESCRIPTION
	    "The number of requests currently executing."
    ::= { aspDotNETApplicationsEntry 31 }

adnApplRequestsFailed OBJECT-TYPE
    SYNTAX     Gauge32
    MAX-ACCESS read-only
    STATUS     current
    DESCRIPTION
	    "Total number of failed requests."
    ::= { aspDotNETApplicationsEntry 32 }

adnApplRequestsInApplQueue OBJECT-TYPE
    SYNTAX     Gauge32
    MAX-ACCESS read-only
    STATUS     current
    DESCRIPTION
	    "The number of requests in the application
	    request queue."
    ::= { aspDotNETApplicationsEntry 33 }

adnApplRequestsNotAuthorized OBJECT-TYPE
    SYNTAX     Gauge32
    MAX-ACCESS read-only
    STATUS     current
    DESCRIPTION
	    "Number of requests failed due to unauthorized
	    access."
    ::= { aspDotNETApplicationsEntry 34 }

adnApplRequestsNotFound OBJECT-TYPE
    SYNTAX     Gauge32
    MAX-ACCESS read-only
    STATUS     current
    DESCRIPTION
	    "The number of requests for resources that were
	    not found."
    ::= { aspDotNETApplicationsEntry 35 }

adnApplRequestsSucceeded OBJECT-TYPE
    SYNTAX     Gauge32
    MAX-ACCESS read-only
    STATUS     current
    DESCRIPTION
	    "The number of requests that executed
	    successfully."
    ::= { aspDotNETApplicationsEntry 36 }

adnApplRequestsTimedOut OBJECT-TYPE
    SYNTAX     Gauge32
    MAX-ACCESS read-only
    STATUS     current
    DESCRIPTION
	    "The number of requests that timed out."
    ::= { aspDotNETApplicationsEntry 37 }

adnApplRequestsTotal OBJECT-TYPE
    SYNTAX     Gauge32
    MAX-ACCESS read-only
    STATUS     current
    DESCRIPTION
	    "The total number of requests since the
	    application was started."
    ::= { aspDotNETApplicationsEntry 38 }

adnApplRequestsPerSec OBJECT-TYPE
    SYNTAX     Gauge32
    MAX-ACCESS read-only
    STATUS     current
    DESCRIPTION
	    "The number of requests executed per second."
    ::= { aspDotNETApplicationsEntry 39 }

adnApplSessionSQLSrvrConnTotal OBJECT-TYPE
    SYNTAX     Gauge32
    MAX-ACCESS read-only
    STATUS     current
    DESCRIPTION
	    "The total number of connections to the SQL
	    Server used by session state."
    ::= { aspDotNETApplicationsEntry 40 }

adnApplSessionStateSrvrConnTotal OBJECT-TYPE
    SYNTAX     Gauge32
    MAX-ACCESS read-only
    STATUS     current
    DESCRIPTION
	    "The total number of connections to the State
	    Server used by session state."
    ::= { aspDotNETApplicationsEntry 41 }

adnApplSessionsAbandoned OBJECT-TYPE
    SYNTAX     Gauge32
    MAX-ACCESS read-only
    STATUS     current
    DESCRIPTION
	    "The number of sessions that have been
	    explicitly abandoned."
    ::= { aspDotNETApplicationsEntry 42 }

adnApplSessionsActive OBJECT-TYPE
    SYNTAX     Gauge32
    MAX-ACCESS read-only
    STATUS     current
    DESCRIPTION
	    "The current number of sessions currently
	    active."
    ::= { aspDotNETApplicationsEntry 43 }

adnApplSessionsTimedOut OBJECT-TYPE
    SYNTAX     Gauge32
    MAX-ACCESS read-only
    STATUS     current
    DESCRIPTION
	    "The number of sessions timed out."
    ::= { aspDotNETApplicationsEntry 44 }

adnApplSessionsTotal OBJECT-TYPE
    SYNTAX     Gauge32
    MAX-ACCESS read-only
    STATUS     current
    DESCRIPTION
	    "Total number of sessions since the application
	    was started."
    ::= { aspDotNETApplicationsEntry 45 }

adnApplTransactionsAborted OBJECT-TYPE
    SYNTAX     Gauge32
    MAX-ACCESS read-only
    STATUS     current
    DESCRIPTION
	    "The number of transactions aborted."
    ::= { aspDotNETApplicationsEntry 46 }

adnApplTransactionsCommitted OBJECT-TYPE
    SYNTAX     Gauge32
    MAX-ACCESS read-only
    STATUS     current
    DESCRIPTION
	    "The number of transactions committed."
    ::= { aspDotNETApplicationsEntry 47 }

adnApplTransactionsPending OBJECT-TYPE
    SYNTAX     Gauge32
    MAX-ACCESS read-only
    STATUS     current
    DESCRIPTION
	    "Number of transactions in progress."
    ::= { aspDotNETApplicationsEntry 48 }

adnApplTransactionsTotal OBJECT-TYPE
    SYNTAX     Gauge32
    MAX-ACCESS read-only
    STATUS     current
    DESCRIPTION
	    "The total number of transactions since the
	    application was started."
    ::= { aspDotNETApplicationsEntry 49 }

adnApplTransactionsPerSec OBJECT-TYPE
    SYNTAX     Gauge32
    MAX-ACCESS read-only
    STATUS     current
    DESCRIPTION
	    "Transactions started per second."
    ::= { aspDotNETApplicationsEntry 50 }

browser OBJECT-IDENTITY
    STATUS     current
    DESCRIPTION
	    "The Browser performance object consists of
	    counters that measure the rates of
	    announcements, enumerations, and other browser
	    transmissions."
    ::= { advanced 6 }

browserAnnouncementsDomainPerSec OBJECT-TYPE
    SYNTAX     Gauge32
    MAX-ACCESS read-only
    STATUS     current
    DESCRIPTION
	    "Announcements Domain/sec is the rate at which
	    a Domain has announced itself to the network."
    ::= { browser 1 }

browserAnnouncementsServerPerSec OBJECT-TYPE
    SYNTAX     Gauge32
    MAX-ACCESS read-only
    STATUS     current
    DESCRIPTION
	    "Announcements Server/sec is the rate at which
	    the servers in this domain have announced
	    themselves to this server."
    ::= { browser 2 }

browserAnnouncementsTotalPerSec OBJECT-TYPE
    SYNTAX     Gauge32
    MAX-ACCESS read-only
    STATUS     current
    DESCRIPTION
	    "Announcements Total/sec is the sum of
	    Announcements Server/sec and Announcements
	    Domain/sec."
    ::= { browser 3 }

browserDuplicateMasterAnnounce OBJECT-TYPE
    SYNTAX     Gauge32
    MAX-ACCESS read-only
    STATUS     current
    DESCRIPTION
	    "Duplicate Master Announcements indicates the
	    number of times that the master browser has
	    detected another master browser on the same
	    domain."
    ::= { browser 4 }

browserElectionPacketsPerSec OBJECT-TYPE
    SYNTAX     Gauge32
    MAX-ACCESS read-only
    STATUS     current
    DESCRIPTION
	    "Election Packets/sec is the rate of Browser
	    election packets that have been received by
	    this workstation."
    ::= { browser 5 }

browserEnumerationsDomainPerSec OBJECT-TYPE
    SYNTAX     Gauge32
    MAX-ACCESS read-only
    STATUS     current
    DESCRIPTION
	    "Enumerations Domain/sec is the rate of Domain
	    browse requests that have been processed by
	    this workstation."
    ::= { browser 6 }

browserEnumerationsOtherPerSec OBJECT-TYPE
    SYNTAX     Gauge32
    MAX-ACCESS read-only
    STATUS     current
    DESCRIPTION
	    "Enumerations Other/sec is the rate of browse
	    requests processed by this workstation that
	    were not domain or server browse requests."
    ::= { browser 7 }

browserEnumerationsServerPerSec OBJECT-TYPE
    SYNTAX     Gauge32
    MAX-ACCESS read-only
    STATUS     current
    DESCRIPTION
	    "Enumerations Server/sec is the rate of Server
	    browse requests that have been processed by
	    this workstation."
    ::= { browser 8 }

browserEnumerationsTotalPerSec OBJECT-TYPE
    SYNTAX     Gauge32
    MAX-ACCESS read-only
    STATUS     current
    DESCRIPTION
	    "Enumerations Total/sec is the rate of browse
	    requests that have been processed by this
	    workstation.  This is the sum of Enumerations
	    Server, Enumerations Domain, and Enumerations
	    Other."
    ::= { browser 9 }

browserIllegalDatagramsPerSec OBJECT-TYPE
    SYNTAX     Gauge32
    MAX-ACCESS read-only
    STATUS     current
    DESCRIPTION
	    "Illegal Datagrams/sec is the rate of
	    incorrectly formatted datagrams that have been
	    received by the workstation."
    ::= { browser 10 }

browserMailslotAllocationsFailed OBJECT-TYPE
    SYNTAX     Gauge32
    MAX-ACCESS read-only
    STATUS     current
    DESCRIPTION
	    "Mailslot Allocations Failed is the number of
	    times the datagram receiver has failed to
	    allocate a buffer to hold a user mailslot
	    write."
    ::= { browser 11 }

browserMailslotOpensFailedPerSec OBJECT-TYPE
    SYNTAX     Gauge32
    MAX-ACCESS read-only
    STATUS     current
    DESCRIPTION
	    "Mailslot Opens Failed/sec indicates the rate
	    of mailslot messages received by this
	    workstation that were to be delivered to
	    mailslots that are not present on this
	    workstation."
    ::= { browser 12 }

browserMailslotReceivesFailed OBJECT-TYPE
    SYNTAX     Gauge32
    MAX-ACCESS read-only
    STATUS     current
    DESCRIPTION
	    "Mailslot Receives Failed indicates the number
	    of mailslot messages that couldn't be received
	    due to transport failures."
    ::= { browser 13 }

browserMailslotWritesFailed OBJECT-TYPE
    SYNTAX     Gauge32
    MAX-ACCESS read-only
    STATUS     current
    DESCRIPTION
	    "Mailslot Writes Failed is the total number of
	    mailslot messages that have been successfully
	    received, but that were unable to be written to
	    the mailslot."
    ::= { browser 14 }

browserMailslotWritesPerSec OBJECT-TYPE
    SYNTAX     Gauge32
    MAX-ACCESS read-only
    STATUS     current
    DESCRIPTION
	    "Mailslot Writes/sec is the rate of mailslot
	    messages that have been successfully received."
    ::= { browser 15 }

browserMissedMailslotDatagrams OBJECT-TYPE
    SYNTAX     Gauge32
    MAX-ACCESS read-only
    STATUS     current
    DESCRIPTION
	    "Missed Mailslot Datagrams is the number of
	    Mailslot Datagrams that have been discarded due
	    to configuration or allocation limits."
    ::= { browser 16 }

browserMissedServerAnnouncements OBJECT-TYPE
    SYNTAX     Gauge32
    MAX-ACCESS read-only
    STATUS     current
    DESCRIPTION
	    "Missed Server Announcements is the number of
	    server announcements that have been missed due
	    to configuration or allocation limits."
    ::= { browser 17 }

browserMissedServerListRequests OBJECT-TYPE
    SYNTAX     Gauge32
    MAX-ACCESS read-only
    STATUS     current
    DESCRIPTION
	    "Missed Server List Requests is the number of
	    requests to retrieve a list of browser servers
	    that were received by this workstation, but
	    could not be processed."
    ::= { browser 18 }

browserServerAllocFailedPerSec OBJECT-TYPE
    SYNTAX     Gauge32
    MAX-ACCESS read-only
    STATUS     current
    DESCRIPTION
	    "Server Announce Allocations Failed/sec is the
	    rate of server (or domain) announcements that
	    have failed due to lack of memory."
    ::= { browser 19 }

browserServerListRequestsPerSec OBJECT-TYPE
    SYNTAX     Gauge32
    MAX-ACCESS read-only
    STATUS     current
    DESCRIPTION
	    "Server List Requests/sec is the rate of
	    requests to retrieve a list of browser servers
	    that have been processed by this workstation."
    ::= { browser 20 }

cache OBJECT-IDENTITY
    STATUS     current
    DESCRIPTION
	    "The Cache performance object consists of
	    counters that monitor the file system cache, an
	    area of physical memory that stores recently
	    used data as long as possible to permit access
	    to the data without having to read from the
	    disk. Because applications typically use the
	    cache, the cache is monitored as an indicator
	    of application input/output (I/O) operations.
	    When memory is plentiful, the cache can grow,
	    but when memory is scarce, the cache can become
	    too small to be effective."
    ::= { advanced 7 }

cacheAsyncCopyReadsPerSec OBJECT-TYPE
    SYNTAX     Gauge32
    MAX-ACCESS read-only
    STATUS     current
    DESCRIPTION
	    "Async Copy Reads/sec is the frequency of reads
	    from pages of the file system cache that
	    involve a memory copy of the data from the
	    cache to the application's buffer.	The
	    application will regain control immediately
	    even if the disk must be accessed to retrieve
	    the page."
    ::= { cache 1 }

cacheAsyncDataMapsPerSec OBJECT-TYPE
    SYNTAX     Gauge32
    MAX-ACCESS read-only
    STATUS     current
    DESCRIPTION
	    "Async Data Maps/sec is the frequency that an
	    application using a file system, such as NTFS,
	    to map a page of a file into the file system
	    cache to read the page, and does not wait for
	    the page to be retrieved if it is not in main
	    memory."
    ::= { cache 2 }

cacheAsyncFastReadsPerSec OBJECT-TYPE
    SYNTAX     Gauge32
    MAX-ACCESS read-only
    STATUS     current
    DESCRIPTION
	    "Async Fast Reads/sec is the frequency of reads
	    from the file system cache that bypass the
	    installed file system and retrieve the data
	    directly from the cache.  Normally, file I/O
	    requests will invoke the appropriate file
	    system to retrieve data from a file, but this
	    path permits data to be retrieved from the
	    cache directly (without file system
	    involvement) if the data is in the cache.  Even
	    if the data is not in the cache, one invocation
	    of the file system is avoided.  If the data is
	    not in the cache, the request (application
	    program call) will not wait until the data has
	    been retrieved from disk, but will get control
	    immediately."
    ::= { cache 3 }

cacheAsyncMDLReadsPerSec OBJECT-TYPE
    SYNTAX     Gauge32
    MAX-ACCESS read-only
    STATUS     current
    DESCRIPTION
	    "Async MDL Reads/sec is the frequency of reads
	    from the file system cache that use a Memory
	    Descriptor List (MDL) to access the pages.	The
	    MDL contains the physical address of each page
	    in the transfer, thus permitting Direct Memory
	    Access (DMA) of the pages.	If the accessed
	    page(s) are not in main memory, the calling
	    application program will not wait for the pages
	    to fault in from disk."
    ::= { cache 4 }

cacheAsyncPinReadsPerSec OBJECT-TYPE
    SYNTAX     Gauge32
    MAX-ACCESS read-only
    STATUS     current
    DESCRIPTION
	    "Async Pin Reads/sec is the frequency of
	    reading data into the file system cache
	    preparatory to writing the data back to disk. 
	    Pages read in this fashion are pinned in memory
	    at the completion of the read.  The file system
	    will regain control immediately even if the
	    disk must be accessed to retrieve the page. 
	    While pinned, a page's physical address will
	    not be altered."
    ::= { cache 5 }

cacheCopyReadHitsPercent OBJECT-TYPE
    SYNTAX     Gauge32
    MAX-ACCESS read-only
    STATUS     current
    DESCRIPTION
	    "Copy Read Hits is the percentage of cache copy
	    read requests that hit the cache, that is, they
	    did not require a disk read in order to provide
	    access to the page in the cache.  A copy read
	    is a file read operation that is satisfied by a
	    memory copy from a page in the cache to the
	    application's buffer.  The LAN Redirector uses
	    this method for retrieving information from the
	    cache, as does the LAN Server for small
	    transfers.	This is a method used by the disk
	    file systems as well."
    ::= { cache 6 }

cacheCopyReadsPerSec OBJECT-TYPE
    SYNTAX     Gauge32
    MAX-ACCESS read-only
    STATUS     current
    DESCRIPTION
	    "Copy Reads/sec is the frequency of reads from
	    pages of the file system cache that involve a
	    memory copy of the data from the cache to the
	    application's buffer.  The LAN Redirector uses
	    this method for retrieving information from the
	    file system cache, as does the LAN Server for
	    small transfers.  This is a method used by the
	    disk file systems as well."
    ::= { cache 7 }

cacheDataFlushPagesPerSec OBJECT-TYPE
    SYNTAX     Gauge32
    MAX-ACCESS read-only
    STATUS     current
    DESCRIPTION
	    "Data Flush Pages/sec is the number of pages
	    the file system cache has flushed to disk as a
	    result of a request to flush or to satisfy a
	    write-through file write request.  More than
	    one page can be transferred on each flush
	    operation."
    ::= { cache 8 }

cacheDataFlushesPerSec OBJECT-TYPE
    SYNTAX     Gauge32
    MAX-ACCESS read-only
    STATUS     current
    DESCRIPTION
	    "Data Flushes/sec is the rate at which the file
	    system cache has flushed its contents to disk
	    as the result of a request to flush or to
	    satisfy a write-through file write request. 
	    More than one page can be transferred on each
	    flush operation."
    ::= { cache 9 }

cacheDataMapHitsPercent OBJECT-TYPE
    SYNTAX     Gauge32
    MAX-ACCESS read-only
    STATUS     current
    DESCRIPTION
	    "Data Map Hits is the percentage of data maps
	    in the file system cache that could be resolved
	    without having to retrieve a page from the
	    disk, because the page was already in physical
	    memory."
    ::= { cache 10 }

cacheDataMapPinsPerSec OBJECT-TYPE
    SYNTAX     Gauge32
    MAX-ACCESS read-only
    STATUS     current
    DESCRIPTION
	    "Data Map Pins/sec is the frequency of data
	    maps in the file system cache that resulted in
	    pinning a page in main memory, an action
	    usually preparatory to writing to the file on
	    disk.   While pinned, a page's physical address
	    in main memory and virtual address in the file
	    system cache will not be altered."
    ::= { cache 11 }

cacheDataMapsPerSec OBJECT-TYPE
    SYNTAX     Gauge32
    MAX-ACCESS read-only
    STATUS     current
    DESCRIPTION
	    "Data Maps/sec is the frequency that a file
	    system such as NTFS, maps a page of a file into
	    the file system cache to read the page."
    ::= { cache 12 }

cacheFastReadNotPossiblesPerSec OBJECT-TYPE
    SYNTAX     Gauge32
    MAX-ACCESS read-only
    STATUS     current
    DESCRIPTION
	    "Fast Read Not Possibles/sec is the frequency
	    of attempts by an Application Program Interface
	    (API) function call to bypass the file system
	    to get to data in the file system cache that
	    could not be honored without invoking the file
	    system."
    ::= { cache 13 }

cacheFastReadResourceMissPerSec OBJECT-TYPE
    SYNTAX     Gauge32
    MAX-ACCESS read-only
    STATUS     current
    DESCRIPTION
	    "Fast Read Resource Misses/sec is the frequency
	    of cache misses necessitated by the lack of
	    available resources to satisfy the request."
    ::= { cache 14 }

cacheFastReadsPerSec OBJECT-TYPE
    SYNTAX     Gauge32
    MAX-ACCESS read-only
    STATUS     current
    DESCRIPTION
	    "Fast Reads/sec is the frequency of reads from
	    the file system cache that bypass the installed
	    file system and retrieve the data directly from
	    the cache.	Normally, file I/O requests invoke
	    the appropriate file system to retrieve data
	    from a file, but this path permits direct
	    retrieval of data from the cache without file
	    system involvement if the data is in the cache.
	     Even if the data is not in the cache, one
	    invocation of the file system is avoided."
    ::= { cache 15 }

cacheLazyWriteFlushesPerSec OBJECT-TYPE
    SYNTAX     Gauge32
    MAX-ACCESS read-only
    STATUS     current
    DESCRIPTION
	    "Lazy Write Flushes/sec is the rate at which
	    the Lazy Writer thread has written to disk. 
	    Lazy Writing is the process of updating the
	    disk after the page has been changed in memory,
	    so that the application that changed the file
	    does not have to wait for the disk write to be
	    complete before proceeding.  More than one page
	    can be transferred by each write operation."
    ::= { cache 16 }

cacheLazyWritePagesPerSec OBJECT-TYPE
    SYNTAX     Gauge32
    MAX-ACCESS read-only
    STATUS     current
    DESCRIPTION
	    "Lazy Write Pages/sec is the rate at which the
	    Lazy Writer thread has written to disk.  Lazy
	    Writing is the process of updating the disk
	    after the page has been changed in memory, so
	    that the application that changed the file does
	    not have to wait for the disk write to be
	    complete before proceeding.  More than one page
	    can be transferred on a single disk write
	    operation."
    ::= { cache 17 }

cacheMDLReadHitsPercent OBJECT-TYPE
    SYNTAX     Gauge32
    MAX-ACCESS read-only
    STATUS     current
    DESCRIPTION
	    "MDL Read Hits is the percentage of Memory
	    Descriptor List (MDL) Read requests to the file
	    system cache that hit the cache, i.e., did not
	    require disk accesses in order to provide
	    memory access to the page(s) in the cache."
    ::= { cache 18 }

cacheMDLReadsPerSec OBJECT-TYPE
    SYNTAX     Gauge32
    MAX-ACCESS read-only
    STATUS     current
    DESCRIPTION
	    "MDL Reads/sec is the frequency of reads from
	    the file system cache that use a Memory
	    Descriptor List (MDL) to access the data.  The
	    MDL contains the physical address of each page
	    involved in the transfer, and thus can employ a
	    hardware Direct Memory Access (DMA) device to
	    effect the copy.  The LAN Server uses this
	    method for large transfers out of the server."
    ::= { cache 19 }

cachePinReadHitsPercent OBJECT-TYPE
    SYNTAX     Gauge32
    MAX-ACCESS read-only
    STATUS     current
    DESCRIPTION
	    "Pin Read Hits is the percentage of pin read
	    requests that hit the file system cache, i.e.,
	    did not require a disk read in order to provide
	    access to the page in the file system cache. 
	    While pinned, a page's physical address in the
	    file system cache will not be altered.  The LAN
	    Redirector uses this method for retrieving data
	    from the cache, as does the LAN Server for
	    small transfers.  This is usually the method
	    used by the disk file systems as well."
    ::= { cache 20 }

cachePinReadsPerSec OBJECT-TYPE
    SYNTAX     Gauge32
    MAX-ACCESS read-only
    STATUS     current
    DESCRIPTION
	    "Pin Reads/sec is the frequency of reading data
	    into the file system cache preparatory to
	    writing the data back to disk.  Pages read in
	    this fashion are pinned in memory at the
	    completion of the read.  While pinned, a page's
	    physical address in the file system cache will
	    not be altered."
    ::= { cache 21 }

cacheReadAheadsPerSec OBJECT-TYPE
    SYNTAX     Gauge32
    MAX-ACCESS read-only
    STATUS     current
    DESCRIPTION
	    "Read Aheads/sec is the frequency of reads from
	    the file system cache in which the Cache
	    detects sequential access to a file.  The read
	    aheads permit the data to be transferred in
	    larger blocks than those being requested by the
	    application, reducing the overhead per access."
    ::= { cache 22 }

cacheSyncCopyReadsPerSec OBJECT-TYPE
    SYNTAX     Gauge32
    MAX-ACCESS read-only
    STATUS     current
    DESCRIPTION
	    "Sync Copy Reads/sec is the frequency of reads
	    from pages of the file system cache that
	    involve a memory copy of the data from the
	    cache to the application's buffer.	The file
	    system will not regain control until the copy
	    operation is complete, even if the disk must be
	    accessed to retrieve the page."
    ::= { cache 23 }

cacheSyncDataMapsPerSec OBJECT-TYPE
    SYNTAX     Gauge32
    MAX-ACCESS read-only
    STATUS     current
    DESCRIPTION
	    "Sync Data Maps/sec counts the frequency that a
	    file system, such as NTFS, maps a page of a
	    file into the file system cache to read the
	    page, and wishes to wait for the page to be
	    retrieved if it is not in main memory."
    ::= { cache 24 }

cacheSyncFastReadsPerSec OBJECT-TYPE
    SYNTAX     Gauge32
    MAX-ACCESS read-only
    STATUS     current
    DESCRIPTION
	    "Sync Fast Reads/sec is the frequency of reads
	    from the file system cache that bypass the
	    installed file system and retrieve the data
	    directly from the cache.  Normally, file I/O
	    requests invoke the appropriate file system to
	    retrieve data from a file, but this path
	    permits direct retrieval of data from the cache
	    without file system involvement if the data is
	    in the cache.  Even if the data is not in the
	    cache, one invocation of the file system is
	    avoided.  If the data is not in the cache, the
	    request (application program call) will wait
	    until the data has been retrieved from disk."
    ::= { cache 25 }

cacheSyncMDLReadsPerSec OBJECT-TYPE
    SYNTAX     Gauge32
    MAX-ACCESS read-only
    STATUS     current
    DESCRIPTION
	    "Sync MDL Reads/sec is the frequency of reads
	    from the file system cache that use a Memory
	    Descriptor List (MDL) to access the pages.	The
	    MDL contains the physical address of each page
	    in the transfer, thus permitting Direct Memory
	    Access (DMA) of the pages.	If the accessed
	    page(s) are not in main memory, the caller will
	    wait for the pages to fault in from the disk."
    ::= { cache 26 }

cacheSyncPinReadsPerSec OBJECT-TYPE
    SYNTAX     Gauge32
    MAX-ACCESS read-only
    STATUS     current
    DESCRIPTION
	    "Sync Pin Reads/sec is the frequency of reading
	    data into the file system cache preparatory to
	    writing the data back to disk.  Pages read in
	    this fashion are pinned in memory at the
	    completion of the read.  The file system will
	    not regain control until the page is pinned in
	    the file system cache, in particular if the
	    disk must be accessed to retrieve the page. 
	    While pinned, a page's physical address in the
	    file system cache will not be altered."
    ::= { cache 27 }

dhcpServer OBJECT-IDENTITY
    STATUS     current
    DESCRIPTION
	    "The DHCP Server performance object provides
	    counters for monitoring DHCP service activity.
	    The DHCP service enables the server to perform
	    as a DHCP server and configure DHCP-enabled
	    client computers on your network as described
	    in the DHCP standard. This object is available
	    when the service is running. The following
	    table describes the counters provided by the
	    DHCP Server object and how to interpret the
	    values when monitoring DHCP service
	    performance."
    ::= { advanced 8 }

dhcpSrvAcksPerSec OBJECT-TYPE
    SYNTAX     Gauge32
    MAX-ACCESS read-only
    STATUS     current
    DESCRIPTION
	    "Rate of DHCP Acks sent by the DHCP server."
    ::= { dhcpServer 1 }

dhcpSrvActiveQueueLength OBJECT-TYPE
    SYNTAX     Gauge32
    MAX-ACCESS read-only
    STATUS     current
    DESCRIPTION
	    "The Number of packets in the processing queue
	    of the DHCP server."
    ::= { dhcpServer 2 }

dhcpSrvConflictCheckQueueLength OBJECT-TYPE
    SYNTAX     Gauge32
    MAX-ACCESS read-only
    STATUS     current
    DESCRIPTION
	    "The Number of packets in the DHCP server queue
	    waiting on conflict detection (ping)."
    ::= { dhcpServer 3 }

dhcpSrvDeclinesPerSec OBJECT-TYPE
    SYNTAX     Gauge32
    MAX-ACCESS read-only
    STATUS     current
    DESCRIPTION
	    "Rate of DHCP Declines received by the DHCP
	    server."
    ::= { dhcpServer 4 }

dhcpSrvDiscoversPerSec OBJECT-TYPE
    SYNTAX     Gauge32
    MAX-ACCESS read-only
    STATUS     current
    DESCRIPTION
	    "Rate of DHCP Discovers received by the DHCP
	    server."
    ::= { dhcpServer 5 }

dhcpSrvDuplicatesDroppedPerSec OBJECT-TYPE
    SYNTAX     Gauge32
    MAX-ACCESS read-only
    STATUS     current
    DESCRIPTION
	    "Duplicates Dropped/sec is the rate at which
	    the DHCP server received duplicate packets."
    ::= { dhcpServer 6 }

dhcpSrvInformsPerSec OBJECT-TYPE
    SYNTAX     Gauge32
    MAX-ACCESS read-only
    STATUS     current
    DESCRIPTION
	    "Rate of DHCP Informs received by the DHCP
	    server."
    ::= { dhcpServer 7 }

dhcpSrvMillisecondsPerPacketAvg OBJECT-TYPE
    SYNTAX     Gauge32
    MAX-ACCESS read-only
    STATUS     current
    DESCRIPTION
	    "The average time per packet taken by the DHCP
	    server to send a response."
    ::= { dhcpServer 8 }

dhcpSrvNacksPerSec OBJECT-TYPE
    SYNTAX     Gauge32
    MAX-ACCESS read-only
    STATUS     current
    DESCRIPTION
	    "Rate of DHCP Nacks sent by the DHCP server."
    ::= { dhcpServer 9 }

dhcpSrvOffersPerSec OBJECT-TYPE
    SYNTAX     Gauge32
    MAX-ACCESS read-only
    STATUS     current
    DESCRIPTION
	    "Rate of DHCP Offers sent out by the DHCP
	    server."
    ::= { dhcpServer 10 }

dhcpSrvPacketsExpiredPerSec OBJECT-TYPE
    SYNTAX     Gauge32
    MAX-ACCESS read-only
    STATUS     current
    DESCRIPTION
	    "Packets Expired/sec is the rate at which
	    packets get expired in the DHCP server message
	    queue."
    ::= { dhcpServer 11 }

dhcpSrvPacketsReceivedPerSec OBJECT-TYPE
    SYNTAX     Gauge32
    MAX-ACCESS read-only
    STATUS     current
    DESCRIPTION
	    "Packets Received/sec is the rate at which
	    packets are received by the DHCP server."
    ::= { dhcpServer 12 }

dhcpSrvReleasesPerSec OBJECT-TYPE
    SYNTAX     Gauge32
    MAX-ACCESS read-only
    STATUS     current
    DESCRIPTION
	    "Rate of DHCP Releases received by the DHCP
	    server."
    ::= { dhcpServer 13 }

dhcpSrvRequestsPerSec OBJECT-TYPE
    SYNTAX     Gauge32
    MAX-ACCESS read-only
    STATUS     current
    DESCRIPTION
	    "Rate of DHCP Requests received by the DHCP
	    server."
    ::= { dhcpServer 14 }

distributedTransactionCoordinator OBJECT-IDENTITY
    STATUS     current
    DESCRIPTION
	    "The Distributed Transaction Coordinator
	    performance object provides statistics about
	    Distributed Transaction Coordinator (MS DTC),
	    part of Component Services (formerly known as
	    Transaction Server) that coordinates external,
	    or two-phase transactions. Among other things,
	    MS DTC is used to coordinate two-phase
	    transactions by Message Queuing."
    ::= { advanced 9 }

dtcAbortedTransactions OBJECT-TYPE
    SYNTAX     Gauge32
    MAX-ACCESS read-only
    STATUS     current
    DESCRIPTION
	    "Number of aborted transactions"
    ::= { distributedTransactionCoordinator 1 }

dtcAbortedTransactionsPerSec OBJECT-TYPE
    SYNTAX     Gauge32
    MAX-ACCESS read-only
    STATUS     current
    DESCRIPTION
	    "Transactions aborted per second"
    ::= { distributedTransactionCoordinator 2 }

dtcActiveTransactions OBJECT-TYPE
    SYNTAX     Gauge32
    MAX-ACCESS read-only
    STATUS     current
    DESCRIPTION
	    "Number of currently active transactions"
    ::= { distributedTransactionCoordinator 3 }

dtcActiveTransactionsMaximum OBJECT-TYPE
    SYNTAX     Gauge32
    MAX-ACCESS read-only
    STATUS     current
    DESCRIPTION
	    "Maximum number of transactions ever
	    concurrently active"
    ::= { distributedTransactionCoordinator 4 }

dtcCommittedTransactions OBJECT-TYPE
    SYNTAX     Gauge32
    MAX-ACCESS read-only
    STATUS     current
    DESCRIPTION
	    "Number of committed transactions"
    ::= { distributedTransactionCoordinator 5 }

dtcCommittedTransactionsPerSec OBJECT-TYPE
    SYNTAX     Gauge32
    MAX-ACCESS read-only
    STATUS     current
    DESCRIPTION
	    "Transactions committed per second"
    ::= { distributedTransactionCoordinator 6 }

dtcForceAbortedTransactions OBJECT-TYPE
    SYNTAX     Gauge32
    MAX-ACCESS read-only
    STATUS     current
    DESCRIPTION
	    "Number of transactions aborted by the system
	    administrator"
    ::= { distributedTransactionCoordinator 7 }

dtcForceCommittedTransactions OBJECT-TYPE
    SYNTAX     Gauge32
    MAX-ACCESS read-only
    STATUS     current
    DESCRIPTION
	    "Number of transactions committed by the system
	    administrator"
    ::= { distributedTransactionCoordinator 8 }

dtcInDoubtTransactions OBJECT-TYPE
    SYNTAX     Gauge32
    MAX-ACCESS read-only
    STATUS     current
    DESCRIPTION
	    "Number of in doubt transactions"
    ::= { distributedTransactionCoordinator 9 }

dtcResponseTimeAverage OBJECT-TYPE
    SYNTAX     Gauge32
    MAX-ACCESS read-only
    STATUS     current
    DESCRIPTION
	    "Average time delta between transaction begin
	    and commit"
    ::= { distributedTransactionCoordinator 10 }

dtcResponseTimeMaximum OBJECT-TYPE
    SYNTAX     Gauge32
    MAX-ACCESS read-only
    STATUS     current
    DESCRIPTION
	    "Maximum time delta between transaction begin
	    and commit"
    ::= { distributedTransactionCoordinator 11 }

dtcResponseTimeMinimum OBJECT-TYPE
    SYNTAX     Gauge32
    MAX-ACCESS read-only
    STATUS     current
    DESCRIPTION
	    "Minimum time delta between transaction begin
	    and commit"
    ::= { distributedTransactionCoordinator 12 }

dtcTransactionsPerSec OBJECT-TYPE
    SYNTAX     Gauge32
    MAX-ACCESS read-only
    STATUS     current
    DESCRIPTION
	    "Transactions performed per second"
    ::= { distributedTransactionCoordinator 13 }

dns OBJECT-IDENTITY
    STATUS     current
    DESCRIPTION
	    "The DNS performance object provides counters
	    for monitoring various areas of performance of
	    the DNS service that enables client computers
	    on your network to register and resolve DNS
	    domain names. These names are used to find and
	    access resources offered by other computers on
	    your network or other networks, such as the
	    Internet. The data reported by the DNS object
	    includes the number of overall queries and
	    responses processed by a DNS server, the number
	    of DNS queries and responses processed using
	    either the User Datagram Protocol (UDP) or the
	    Transmission Control Protocol (TCP), the number
	    of queries and responses that used recursion to
	    look up and fully resolve DNS names on behalf
	    of requesting clients, and the number of
	    queries and responses made to servers using the
	    WINS lookup integration features of the DNS
	    service."
    ::= { advanced 10 }

dnsAXFRRequestReceived OBJECT-TYPE
    SYNTAX     Gauge32
    MAX-ACCESS read-only
    STATUS     current
    DESCRIPTION
	    "AXFR Request Received is the total number of
	    full zone transfer requests received by the
	    master DNS server."
    ::= { dns 1 }

dnsAXFRRequestSent OBJECT-TYPE
    SYNTAX     Gauge32
    MAX-ACCESS read-only
    STATUS     current
    DESCRIPTION
	    "AXFR Request Sent is the total number of full
	    zone transfer requests sent by the secondary
	    DNS server."
    ::= { dns 2 }

dnsAXFRResponseReceived OBJECT-TYPE
    SYNTAX     Gauge32
    MAX-ACCESS read-only
    STATUS     current
    DESCRIPTION
	    "AXFR Response Received is the total number of
	    full zone transfer responses received by the
	    secondary DNS server."
    ::= { dns 3 }

dnsAXFRSuccessReceived OBJECT-TYPE
    SYNTAX     Gauge32
    MAX-ACCESS read-only
    STATUS     current
    DESCRIPTION
	    "AXFR Success Received is the total number of
	    successful full zone transfers received by the
	    secondary DNS server."
    ::= { dns 4 }

dnsAXFRSuccessSent OBJECT-TYPE
    SYNTAX     Gauge32
    MAX-ACCESS read-only
    STATUS     current
    DESCRIPTION
	    "AXFR Success Sent is the total number of
	    successful full zone transfers of the master
	    DNS server."
    ::= { dns 5 }

dnsCachingMemory OBJECT-TYPE
    SYNTAX     Gauge32
    MAX-ACCESS read-only
    STATUS     current
    DESCRIPTION
	    "Caching Memory is the total caching memory
	    used by DNS server."
    ::= { dns 6 }

dnsDatabaseNodeMemory OBJECT-TYPE
    SYNTAX     Gauge32
    MAX-ACCESS read-only
    STATUS     current
    DESCRIPTION
	    "Database Node Memory is the total database
	    node memory used by DNS server."
    ::= { dns 7 }

dnsDynamicUpdateNoOperation OBJECT-TYPE
    SYNTAX     Gauge32
    MAX-ACCESS read-only
    STATUS     current
    DESCRIPTION
	    "Dynamic Update NoOperation is the total number
	    of No-operation/Empty dynamic update requests
	    received by the DNS server."
    ::= { dns 8 }

dnsDynamicUpdateNoOpPerSec OBJECT-TYPE
    SYNTAX     Gauge32
    MAX-ACCESS read-only
    STATUS     current
    DESCRIPTION
	    "Dynamic Update NoOperation/sec is the average
	    number of No-operation/Empty dynamic update
	    requests received by the DNS server in each
	    second."
    ::= { dns 9 }

dnsDynamicUpdateQueued OBJECT-TYPE
    SYNTAX     Gauge32
    MAX-ACCESS read-only
    STATUS     current
    DESCRIPTION
	    "Dynamic Update Queued is the total number of
	    dynamic updates queued by the DNS server."
    ::= { dns 10 }

dnsDynamicUpdateReceived OBJECT-TYPE
    SYNTAX     Gauge32
    MAX-ACCESS read-only
    STATUS     current
    DESCRIPTION
	    "Dynamic Update Received is the total number of
	    dynamic update requests received by the DNS
	    server."
    ::= { dns 11 }

dnsDynamicUpdateReceivedPerSec OBJECT-TYPE
    SYNTAX     Gauge32
    MAX-ACCESS read-only
    STATUS     current
    DESCRIPTION
	    "Dynamic Update Received/sec is the average
	    number of dynamic update requests received by
	    the DNS server in each second."
    ::= { dns 12 }

dnsDynamicUpdateRejected OBJECT-TYPE
    SYNTAX     Gauge32
    MAX-ACCESS read-only
    STATUS     current
    DESCRIPTION
	    "Dynamic Update Rejected is the total number of
	    dynamic updates rejected by the DNS server."
    ::= { dns 13 }

dnsDynamicUpdateTimeOuts OBJECT-TYPE
    SYNTAX     Gauge32
    MAX-ACCESS read-only
    STATUS     current
    DESCRIPTION
	    "Dynamic Update TimeOuts is the total number of
	    dynamic update timeouts of the DNS server."
    ::= { dns 14 }

dnsDynamicUpdateWriteToDB OBJECT-TYPE
    SYNTAX     Gauge32
    MAX-ACCESS read-only
    STATUS     current
    DESCRIPTION
	    "Dynamic Update Written to Database is the
	    total number of dynamic updates written to the
	    database by the DNS server."
    ::= { dns 15 }

dnsDynamicUpdateWriteToDBPerSec OBJECT-TYPE
    SYNTAX     Gauge32
    MAX-ACCESS read-only
    STATUS     current
    DESCRIPTION
	    "Dynamic Update Written to Database/sec is the
	    average number of dynamic updates written to
	    the database by the DNS server in each second."
    ::= { dns 16 }

dnsIXFRRequestReceived OBJECT-TYPE
    SYNTAX     Gauge32
    MAX-ACCESS read-only
    STATUS     current
    DESCRIPTION
	    "IXFR Request Received is the total number of
	    incremental zone transfer requests received by
	    the master DNS server."
    ::= { dns 17 }

dnsIXFRRequestSent OBJECT-TYPE
    SYNTAX     Gauge32
    MAX-ACCESS read-only
    STATUS     current
    DESCRIPTION
	    "IXFR Request Sent is the total number of
	    incremental zone transfer requests sent by the
	    secondary DNS server."
    ::= { dns 18 }

dnsIXFRResponseReceived OBJECT-TYPE
    SYNTAX     Gauge32
    MAX-ACCESS read-only
    STATUS     current
    DESCRIPTION
	    "IXFR Response Received is the total number of
	    incrementalzone transfer responses received by
	    the secondary DNS server."
    ::= { dns 19 }

dnsIXFRSuccessReceived OBJECT-TYPE
    SYNTAX     Gauge32
    MAX-ACCESS read-only
    STATUS     current
    DESCRIPTION
	    "IXFR Success Received is the total number of
	    successful incremental zone transfers received
	    by the secondary DNS server."
    ::= { dns 20 }

dnsIXFRSuccessSent OBJECT-TYPE
    SYNTAX     Gauge32
    MAX-ACCESS read-only
    STATUS     current
    DESCRIPTION
	    "IXFR Success Sent is the total number of
	    successful incremental zone transfers of the
	    master DNS server."
    ::= { dns 21 }

dnsIXFRTCPSuccessReceived OBJECT-TYPE
    SYNTAX     Gauge32
    MAX-ACCESS read-only
    STATUS     current
    DESCRIPTION
	    "IXFR TCP Success Received is the total number
	    of successful TCP incremental zone transfers
	    received by the secondary DNS server."
    ::= { dns 22 }

dnsIXFRUDPSuccessReceived OBJECT-TYPE
    SYNTAX     Gauge32
    MAX-ACCESS read-only
    STATUS     current
    DESCRIPTION
	    "IXFR UDP Success Received is the total number
	    of successful UDP incremental zone transfers
	    received by the secondary DNS server."
    ::= { dns 23 }

dnsNbstatMemory OBJECT-TYPE
    SYNTAX     Gauge32
    MAX-ACCESS read-only
    STATUS     current
    DESCRIPTION
	    "Nbstat Memory is the total Nbstat memory used
	    by DNS server."
    ::= { dns 24 }

dnsNotifyReceived OBJECT-TYPE
    SYNTAX     Gauge32
    MAX-ACCESS read-only
    STATUS     current
    DESCRIPTION
	    "Notify Received is the total number of
	    notifies received by the secondary DNS server."
    ::= { dns 25 }

dnsNotifySent OBJECT-TYPE
    SYNTAX     Gauge32
    MAX-ACCESS read-only
    STATUS     current
    DESCRIPTION
	    "Notify Sent is the total number of notifies
	    sent by the master DNS server."
    ::= { dns 26 }

dnsRecordFlowMemory OBJECT-TYPE
    SYNTAX     Gauge32
    MAX-ACCESS read-only
    STATUS     current
    DESCRIPTION
	    "Record Flow Memory is the total record flow
	    memory used by DNS server."
    ::= { dns 27 }

dnsRecursiveQueries OBJECT-TYPE
    SYNTAX     Gauge32
    MAX-ACCESS read-only
    STATUS     current
    DESCRIPTION
	    "Recursive Queries is the total number of
	    recursive queries received by DNS server."
    ::= { dns 28 }

dnsRecursiveQueriesPerSec OBJECT-TYPE
    SYNTAX     Gauge32
    MAX-ACCESS read-only
    STATUS     current
    DESCRIPTION
	    "Recursive Queries/sec is the average number of
	    recursive queries received by DNS server in
	    each sencond."
    ::= { dns 29 }

dnsRecursiveQueryFailure OBJECT-TYPE
    SYNTAX     Gauge32
    MAX-ACCESS read-only
    STATUS     current
    DESCRIPTION
	    "Recursive Query Failure is the total number of
	    recursive query failures."
    ::= { dns 30 }

dnsRecursiveQueryFailurePerSec OBJECT-TYPE
    SYNTAX     Gauge32
    MAX-ACCESS read-only
    STATUS     current
    DESCRIPTION
	    "Recursive Query Failure/sec is the average
	    number of recursive query failures in each
	    second."
    ::= { dns 31 }

dnsRecursiveSendTimeOuts OBJECT-TYPE
    SYNTAX     Gauge32
    MAX-ACCESS read-only
    STATUS     current
    DESCRIPTION
	    "Recursive TimeOuts is the total number of
	    recursive query sending timeouts."
    ::= { dns 32 }

dnsRecursiveTimeOutPerSec OBJECT-TYPE
    SYNTAX     Gauge32
    MAX-ACCESS read-only
    STATUS     current
    DESCRIPTION
	    "Recursive TimeOut/sec is the average number of
	    recursive query sending timeouts in each
	    second."
    ::= { dns 33 }

dnsSecureUpdateFailure OBJECT-TYPE
    SYNTAX     Gauge32
    MAX-ACCESS read-only
    STATUS     current
    DESCRIPTION
	    "Secure Update Failure is the total number of
	    secure updates failed of the DNS server."
    ::= { dns 34 }

dnsSecureUpdateReceived OBJECT-TYPE
    SYNTAX     Gauge32
    MAX-ACCESS read-only
    STATUS     current
    DESCRIPTION
	    "Secure Update Received is the total number of
	    secure update requests received by the DNS
	    server."
    ::= { dns 35 }

dnsSecureUpdateReceivedPerSec OBJECT-TYPE
    SYNTAX     Gauge32
    MAX-ACCESS read-only
    STATUS     current
    DESCRIPTION
	    "Secure Update Received/sec is the average
	    number of secure update requests received by
	    the DNS server in each second."
    ::= { dns 36 }

dnsTCPMessageMemory OBJECT-TYPE
    SYNTAX     Gauge32
    MAX-ACCESS read-only
    STATUS     current
    DESCRIPTION
	    "TCP Message Memory is the total TCP message
	    memory used by DNS server."
    ::= { dns 37 }

dnsTCPQueryReceived OBJECT-TYPE
    SYNTAX     Gauge32
    MAX-ACCESS read-only
    STATUS     current
    DESCRIPTION
	    "TCP Query Received is the total number of TCP
	    queries received by DNS server."
    ::= { dns 38 }

dnsTCPQueryReceivedPerSec OBJECT-TYPE
    SYNTAX     Gauge32
    MAX-ACCESS read-only
    STATUS     current
    DESCRIPTION
	    "TCP Query Received/sec is the average number
	    of TCP queries received by DNS server in each
	    second."
    ::= { dns 39 }

dnsTCPResponseSent OBJECT-TYPE
    SYNTAX     Gauge32
    MAX-ACCESS read-only
    STATUS     current
    DESCRIPTION
	    "TCP Response Sent is the total number of TCP
	    reponses sent by DNS server."
    ::= { dns 40 }

dnsTCPResponseSentPerSec OBJECT-TYPE
    SYNTAX     Gauge32
    MAX-ACCESS read-only
    STATUS     current
    DESCRIPTION
	    "TCP Response Sent/sec is the average number of
	    TCP reponses sent by DNS server in each
	    second."
    ::= { dns 41 }

dnsTotalQueryReceived OBJECT-TYPE
    SYNTAX     Gauge32
    MAX-ACCESS read-only
    STATUS     current
    DESCRIPTION
	    "Total Query Received is the total number of
	    queries received by DNS server."
    ::= { dns 42 }

dnsTotalQueryReceivedPerSec OBJECT-TYPE
    SYNTAX     Gauge32
    MAX-ACCESS read-only
    STATUS     current
    DESCRIPTION
	    "Total Query Received/sec is the average number
	    of queries received by DNS server in each
	    second."
    ::= { dns 43 }

dnsTotalResponseSent OBJECT-TYPE
    SYNTAX     Gauge32
    MAX-ACCESS read-only
    STATUS     current
    DESCRIPTION
	    "Total Response Sent is the total number of
	    reponses sent by DNS server."
    ::= { dns 44 }

dnsTotalResponseSentPerSec OBJECT-TYPE
    SYNTAX     Gauge32
    MAX-ACCESS read-only
    STATUS     current
    DESCRIPTION
	    "Total Response Sent/sec is the average number
	    of reponses sent by DNS server in each second."
    ::= { dns 45 }

dnsUDPMessageMemory OBJECT-TYPE
    SYNTAX     Gauge32
    MAX-ACCESS read-only
    STATUS     current
    DESCRIPTION
	    "UDP Message Memory is the total UDP message
	    memory used by DNS server."
    ::= { dns 46 }

dnsUDPQueryReceived OBJECT-TYPE
    SYNTAX     Gauge32
    MAX-ACCESS read-only
    STATUS     current
    DESCRIPTION
	    "UDP Query Received is the total number of UDP
	    queries received by DNS server."
    ::= { dns 47 }

dnsUDPQueryReceivedPerSec OBJECT-TYPE
    SYNTAX     Gauge32
    MAX-ACCESS read-only
    STATUS     current
    DESCRIPTION
	    "UDP Query Received/sec is the average number
	    of UDP queries received by DNS server in each
	    second."
    ::= { dns 48 }

dnsUDPResponseSent OBJECT-TYPE
    SYNTAX     Gauge32
    MAX-ACCESS read-only
    STATUS     current
    DESCRIPTION
	    "UDP Response Sent is the total number of UDP
	    reponses sent by DNS server."
    ::= { dns 49 }

dnsUDPResponseSentPerSec OBJECT-TYPE
    SYNTAX     Gauge32
    MAX-ACCESS read-only
    STATUS     current
    DESCRIPTION
	    "UDP Response Sent/sec is the average number of
	    UDP reponses sent by DNS server in each
	    second."
    ::= { dns 50 }

dnsWINSLookupReceived OBJECT-TYPE
    SYNTAX     Gauge32
    MAX-ACCESS read-only
    STATUS     current
    DESCRIPTION
	    "WINS Lookup Received is the total number of
	    WINS lookup requests received by the server."
    ::= { dns 51 }

dnsWINSLookupReceivedPerSec OBJECT-TYPE
    SYNTAX     Gauge32
    MAX-ACCESS read-only
    STATUS     current
    DESCRIPTION
	    "WINS Lookup Received/sec is the average number
	    of WINS lookup requests received by the server
	    in each second."
    ::= { dns 52 }

dnsWINSResponseSent OBJECT-TYPE
    SYNTAX     Gauge32
    MAX-ACCESS read-only
    STATUS     current
    DESCRIPTION
	    "WINS Response Sent is the total number of WINS
	    lookup responses sent by the server."
    ::= { dns 53 }

dnsWINSResponseSentPerSec OBJECT-TYPE
    SYNTAX     Gauge32
    MAX-ACCESS read-only
    STATUS     current
    DESCRIPTION
	    "WINS Response Sent/sec is the average number
	    of WINS lookup responses sent by the server in
	    each second."
    ::= { dns 54 }

dnsWINSReverseLookupReceived OBJECT-TYPE
    SYNTAX     Gauge32
    MAX-ACCESS read-only
    STATUS     current
    DESCRIPTION
	    "WINS Reverse Lookup Received is the total
	    number of WINS reverse lookup requests received
	    by the server."
    ::= { dns 55 }

dnsWINSReverseLookupRcvPerSec OBJECT-TYPE
    SYNTAX     Gauge32
    MAX-ACCESS read-only
    STATUS     current
    DESCRIPTION
	    "WINS Reverse Lookup Received/sec is the
	    average number of WINS reverse lookup requests
	    received by the server in each second."
    ::= { dns 56 }

dnsWINSReverseResponseSent OBJECT-TYPE
    SYNTAX     Gauge32
    MAX-ACCESS read-only
    STATUS     current
    DESCRIPTION
	    "WINS Reverse Response Sent is the total number
	    of WINS Reverse lookup responses sent by the
	    server."
    ::= { dns 57 }

dnsWINSReverseResponseSentPerSec OBJECT-TYPE
    SYNTAX     Gauge32
    MAX-ACCESS read-only
    STATUS     current
    DESCRIPTION
	    "WINS Reverse Response Sent/sec is the average
	    number of WINS Reverse lookup responses sent by
	    the server in each second."
    ::= { dns 58 }

dnsZoneTransferFailure OBJECT-TYPE
    SYNTAX     Gauge32
    MAX-ACCESS read-only
    STATUS     current
    DESCRIPTION
	    "Zone Transfer Failure is the total number of
	    failed zone transfers of the master DNS
	    server."
    ::= { dns 59 }

dnsZoneTransferRequestReceived OBJECT-TYPE
    SYNTAX     Gauge32
    MAX-ACCESS read-only
    STATUS     current
    DESCRIPTION
	    "Zone Transfer Request Received is the total
	    number of zone transfer requests received by
	    the master DNS server."
    ::= { dns 60 }

dnsZoneTransferSOARequestSent OBJECT-TYPE
    SYNTAX     Gauge32
    MAX-ACCESS read-only
    STATUS     current
    DESCRIPTION
	    "Zone Transfer SOA Request Sent is the total
	    number of zone transfer SOA requests sent by
	    the  secondary DNS server."
    ::= { dns 61 }

dnsZoneTransferSuccess OBJECT-TYPE
    SYNTAX     Gauge32
    MAX-ACCESS read-only
    STATUS     current
    DESCRIPTION
	    "Zone Transfer Success is the total number of
	    successful zone transfers of the master DNS
	    server."
    ::= { dns 62 }

dotNETCLRDataTable OBJECT-TYPE
    SYNTAX     SEQUENCE OF DotNETCLRDataEntry
    MAX-ACCESS not-accessible
    STATUS     current
    DESCRIPTION
	    "The Performance console .NET CLR Data category
	    includes counters that provide information
	    about the exceptions thrown by an application."
    ::= { advanced 11 }

dotNETCLRDataEntry OBJECT-TYPE
    SYNTAX     DotNETCLRDataEntry
    MAX-ACCESS not-accessible
    STATUS     current
    DESCRIPTION
	    "Performance information for one particular
	    instance of '.NET CLR Data' object."
    INDEX      { ncdInstance }
    ::= { dotNETCLRDataTable 1 }

DotNETCLRDataEntry ::= SEQUENCE {
    ncdInstance InstanceName,
    ncdSQLClntCurNumConnPools Gauge32,
    ncdSQLClntCurNumConns Gauge32,
    ncdSQLClntCurNumPoolConns Gauge32,
    ncdSQLClntPeakNumPoolConns Gauge32,
    ncdSQLClntTotalNumFailedCommands Gauge32,
    ncdSQLClntTotalNumFailedConnects Gauge32
}

ncdInstance OBJECT-TYPE
    SYNTAX     InstanceName
    MAX-ACCESS read-only
    STATUS     current
    DESCRIPTION
	    "Instance name."
    ::= { dotNETCLRDataEntry 1 }

ncdSQLClntCurNumConnPools OBJECT-TYPE
    SYNTAX     Gauge32
    MAX-ACCESS read-only
    STATUS     current
    DESCRIPTION
	    "Current number of pools associated with the
	    process."
    ::= { dotNETCLRDataEntry 2 }

ncdSQLClntCurNumConns OBJECT-TYPE
    SYNTAX     Gauge32
    MAX-ACCESS read-only
    STATUS     current
    DESCRIPTION
	    "Current number of connections, pooled or not."
    ::= { dotNETCLRDataEntry 3 }

ncdSQLClntCurNumPoolConns OBJECT-TYPE
    SYNTAX     Gauge32
    MAX-ACCESS read-only
    STATUS     current
    DESCRIPTION
	    "Current number of connections in all pools
	    associated with the process."
    ::= { dotNETCLRDataEntry 4 }

ncdSQLClntPeakNumPoolConns OBJECT-TYPE
    SYNTAX     Gauge32
    MAX-ACCESS read-only
    STATUS     current
    DESCRIPTION
	    "The highest number of connections in all pools
	    since the process started."
    ::= { dotNETCLRDataEntry 5 }

ncdSQLClntTotalNumFailedCommands OBJECT-TYPE
    SYNTAX     Gauge32
    MAX-ACCESS read-only
    STATUS     current
    DESCRIPTION
	    "The total number of command executes that have
	    failed for any reason."
    ::= { dotNETCLRDataEntry 6 }

ncdSQLClntTotalNumFailedConnects OBJECT-TYPE
    SYNTAX     Gauge32
    MAX-ACCESS read-only
    STATUS     current
    DESCRIPTION
	    "The total number of connection open attempts
	    that have failed for any reason."
    ::= { dotNETCLRDataEntry 7 }

dotNETCLRExceptionsTable OBJECT-TYPE
    SYNTAX     SEQUENCE OF DotNETCLRExceptionsEntry
    MAX-ACCESS not-accessible
    STATUS     current
    DESCRIPTION
	    "The Performance console .NET CLR Exceptions
	    category includes counters that provide
	    information about the exceptions thrown by an
	    application."
    ::= { advanced 12 }

dotNETCLRExceptionsEntry OBJECT-TYPE
    SYNTAX     DotNETCLRExceptionsEntry
    MAX-ACCESS not-accessible
    STATUS     current
    DESCRIPTION
	    "Performance information for one particular
	    instance of '.NET CLR Exceptions' object."
    INDEX      { nceInstance }
    ::= { dotNETCLRExceptionsTable 1 }

DotNETCLRExceptionsEntry ::= SEQUENCE {
    nceInstance InstanceName,
    nceNumOfExcepsThrown Gauge32,
    nceNumOfExcepsThrownPerSec Gauge32,
    nceNumOfFiltersPerSec Gauge32,
    nceNumOfFinallysPerSec Gauge32,
    nceThrowToCatchDepthPerSec Gauge32
}

nceInstance OBJECT-TYPE
    SYNTAX     InstanceName
    MAX-ACCESS read-only
    STATUS     current
    DESCRIPTION
	    "Instance name."
    ::= { dotNETCLRExceptionsEntry 1 }

nceNumOfExcepsThrown OBJECT-TYPE
    SYNTAX     Gauge32
    MAX-ACCESS read-only
    STATUS     current
    DESCRIPTION
	    "This counter displays the total number of
	    exceptions thrown since the start of the
	    application. These include both .NET exceptions
	    and unmanaged exceptions that get converted
	    into .NET exceptions e.g. null pointer
	    reference exception in unmanaged code would get
	    re-thrown in managed code as a .NET
	    System.NullReferenceException; this counter
	    includes both handled and unhandled exceptions.
	    Exceptions that are re-thrown would get counted
	    again. Exceptions should only occur in rare
	    situations and not in the normal control flow
	    of the program."
    ::= { dotNETCLRExceptionsEntry 2 }

nceNumOfExcepsThrownPerSec OBJECT-TYPE
    SYNTAX     Gauge32
    MAX-ACCESS read-only
    STATUS     current
    DESCRIPTION
	    "This counter displays the number of exceptions
	    thrown per second. These include both .NET
	    exceptions and unmanaged exceptions that get
	    converted into .NET exceptions e.g. null
	    pointer reference exception in unmanaged code
	    would get re-thrown in managed code as a .NET
	    System.NullReferenceException; this counter
	    includes both handled and unhandled exceptions.
	    Exceptions should only occur in rare situations
	    and not in the normal control flow of the
	    program; this counter was designed as an
	    indicator of potential performance problems due
	    to large (>100s) rate of exceptions thrown.
	    This counter is not an average over time; it
	    displays the difference between the values
	    observed in the last two samples divided by the
	    duration of the sample interval."
    ::= { dotNETCLRExceptionsEntry 3 }

nceNumOfFiltersPerSec OBJECT-TYPE
    SYNTAX     Gauge32
    MAX-ACCESS read-only
    STATUS     current
    DESCRIPTION
	    "This counter displays the number of .NET
	    exception filters executed per second. An
	    exception filter evaluates whether an exception
	    should be handled or not. This counter tracks
	    the rate of exception filters evaluated;
	    irrespective of whether the exception was
	    handled or not. This counter is not an average
	    over time; it displays the difference between
	    the values observed in the last two samples
	    divided by the duration of the sample
	    interval."
    ::= { dotNETCLRExceptionsEntry 4 }

nceNumOfFinallysPerSec OBJECT-TYPE
    SYNTAX     Gauge32
    MAX-ACCESS read-only
    STATUS     current
    DESCRIPTION
	    "This counter displays the number of finally
	    blocks executed per second. A finally block is
	    guaranteed to be executed regardless of how the
	    try block was exited. Only the finally blocks
	    that are executed for an exception are counted;
	    finally blocks on normal code paths are not
	    counted by this counter. This counter is not an
	    average over time; it displays the difference
	    between the values observed in the last two
	    samples divided by the duration of the sample
	    interval."
    ::= { dotNETCLRExceptionsEntry 5 }

nceThrowToCatchDepthPerSec OBJECT-TYPE
    SYNTAX     Gauge32
    MAX-ACCESS read-only
    STATUS     current
    DESCRIPTION
	    "This counter displays the number of stack
	    frames traversed from the frame that threw the
	    .NET exception to the frame that handled the
	    exception per second. This counter resets to 0
	    when an exception handler is entered; so nested
	    exceptions would show the handler to handler
	    stack depth. This counter is not an average
	    over time; it displays the difference between
	    the values observed in the last two samples
	    divided by the duration of the sample
	    interval."
    ::= { dotNETCLRExceptionsEntry 6 }

dotNETCLRInteropTable OBJECT-TYPE
    SYNTAX     SEQUENCE OF DotNETCLRInteropEntry
    MAX-ACCESS not-accessible
    STATUS     current
    DESCRIPTION
	    "The Performance console .NET CLR Interop
	    category includes counters that provide
	    information about an application's interaction
	    with COM components, COM+ services, and
	    external type libraries."
    ::= { advanced 13 }

dotNETCLRInteropEntry OBJECT-TYPE
    SYNTAX     DotNETCLRInteropEntry
    MAX-ACCESS not-accessible
    STATUS     current
    DESCRIPTION
	    "Performance information for one particular
	    instance of '.NET CLR Interop' object."
    INDEX      { nciInstance }
    ::= { dotNETCLRInteropTable 1 }

DotNETCLRInteropEntry ::= SEQUENCE {
    nciInstance InstanceName,
    nciNumOfCCWs Gauge32,
    nciNumOfStubs Gauge32,
    nciNumOfTLBExportsPerSec Gauge32,
    nciNumOfTLBImportsPerSec Gauge32,
    nciNumOfMarshalling Gauge32
}

nciInstance OBJECT-TYPE
    SYNTAX     InstanceName
    MAX-ACCESS read-only
    STATUS     current
    DESCRIPTION
	    "Instance name."
    ::= { dotNETCLRInteropEntry 1 }

nciNumOfCCWs OBJECT-TYPE
    SYNTAX     Gauge32
    MAX-ACCESS read-only
    STATUS     current
    DESCRIPTION
	    "This counter displays the current number of
	    Com-Callable-Wrappers (CCWs). A CCW is a proxy
	    for the .NET managed object being referenced
	    from unmanaged COM client(s). This counter was
	    designed to indicate the number of managed
	    objects being referenced by unmanaged COM
	    code."
    ::= { dotNETCLRInteropEntry 2 }

nciNumOfStubs OBJECT-TYPE
    SYNTAX     Gauge32
    MAX-ACCESS read-only
    STATUS     current
    DESCRIPTION
	    "This counter displays the current number of
	    stubs created by the CLR. Stubs are responsible
	    for marshalling arguments and return values
	    from managed to unmanaged code and vice versa;
	    during a COM Interop call or PInvoke call."
    ::= { dotNETCLRInteropEntry 3 }

nciNumOfTLBExportsPerSec OBJECT-TYPE
    SYNTAX     Gauge32
    MAX-ACCESS read-only
    STATUS     current
    DESCRIPTION
	    "Reserved for future use."
    ::= { dotNETCLRInteropEntry 4 }

nciNumOfTLBImportsPerSec OBJECT-TYPE
    SYNTAX     Gauge32
    MAX-ACCESS read-only
    STATUS     current
    DESCRIPTION
	    "Reserved for future use."
    ::= { dotNETCLRInteropEntry 5 }

nciNumOfMarshalling OBJECT-TYPE
    SYNTAX     Gauge32
    MAX-ACCESS read-only
    STATUS     current
    DESCRIPTION
	    "This counter displays the total number of
	    times arguments and return values have been
	    marshaled from managed to unmanaged code and
	    vice versa since the start of the application.
	    This counter is not incremented if the stubs
	    are inlined. (Stubs are responsible for
	    marshalling arguments and return values). Stubs
	    usually get inlined if the marshalling overhead
	    is small."
    ::= { dotNETCLRInteropEntry 6 }

dotNETCLRJitTable OBJECT-TYPE
    SYNTAX     SEQUENCE OF DotNETCLRJitEntry
    MAX-ACCESS not-accessible
    STATUS     current
    DESCRIPTION
	    "The Performance console .NET CLR JIT category
	    includes counters that provide information
	    about code that has been JIT-compiled."
    ::= { advanced 14 }

dotNETCLRJitEntry OBJECT-TYPE
    SYNTAX     DotNETCLRJitEntry
    MAX-ACCESS not-accessible
    STATUS     current
    DESCRIPTION
	    "Performance information for one particular
	    instance of '.NET CLR Jit' object."
    INDEX      { ncjInstance }
    ::= { dotNETCLRJitTable 1 }

DotNETCLRJitEntry ::= SEQUENCE {
    ncjInstance InstanceName,
    ncjNumOfILBytesJitted Gauge32,
    ncjNumOfMethodsJitted Gauge32,
    ncjPercentTimeInJit Gauge32,
    ncjILBytesJittedPerSec Gauge32,
    ncjStandardJitFailures Gauge32,
    ncjTotalNumOfILBytesJitted Gauge32
}

ncjInstance OBJECT-TYPE
    SYNTAX     InstanceName
    MAX-ACCESS read-only
    STATUS     current
    DESCRIPTION
	    "Instance name."
    ::= { dotNETCLRJitEntry 1 }

ncjNumOfILBytesJitted OBJECT-TYPE
    SYNTAX     Gauge32
    MAX-ACCESS read-only
    STATUS     current
    DESCRIPTION
	    "This counter displays the total IL bytes
	    jitted since the start of the application. This
	    counter is exactly equivalent to the 'Total #
	    of IL Bytes Jitted' counter."
    ::= { dotNETCLRJitEntry 2 }

ncjNumOfMethodsJitted OBJECT-TYPE
    SYNTAX     Gauge32
    MAX-ACCESS read-only
    STATUS     current
    DESCRIPTION
	    "This counter displays the total number of
	    methods compiled Just-In-Time (JIT) by the CLR
	    JIT compiler since the start of the
	    application. This counter does not include the
	    pre-jitted methods."
    ::= { dotNETCLRJitEntry 3 }

ncjPercentTimeInJit OBJECT-TYPE
    SYNTAX     Gauge32
    MAX-ACCESS read-only
    STATUS     current
    DESCRIPTION
	    "This counter displays the percentage of
	    elapsed time spent in JIT compilation since the
	    last JIT compilation phase. This counter is
	    updated at the end of every JIT compilation
	    phase. A JIT compilation phase is the phase
	    when a method and its dependencies are being
	    compiled."
    ::= { dotNETCLRJitEntry 4 }

ncjILBytesJittedPerSec OBJECT-TYPE
    SYNTAX     Gauge32
    MAX-ACCESS read-only
    STATUS     current
    DESCRIPTION
	    "This counter displays the rate at which IL
	    bytes are jitted per second. This counter is
	    not an average over time; it displays the
	    difference between the values observed in the
	    last two samples divided by the duration of the
	    sample interval."
    ::= { dotNETCLRJitEntry 5 }

ncjStandardJitFailures OBJECT-TYPE
    SYNTAX     Gauge32
    MAX-ACCESS read-only
    STATUS     current
    DESCRIPTION
	    "This counter displays the peak number of
	    methods the JIT compiler has failed to JIT
	    since the start of the application. This
	    failure can occur if the IL cannot be verified
	    or if there was an internal error in the JIT
	    compiler."
    ::= { dotNETCLRJitEntry 6 }

ncjTotalNumOfILBytesJitted OBJECT-TYPE
    SYNTAX     Gauge32
    MAX-ACCESS read-only
    STATUS     current
    DESCRIPTION
	    "This counter displays the total IL bytes
	    jitted since the start of the application. This
	    counter is exactly equivalent to the '# of IL
	    Bytes Jitted' counter."
    ::= { dotNETCLRJitEntry 7 }

dotNETCLRLoadingTable OBJECT-TYPE
    SYNTAX     SEQUENCE OF DotNETCLRLoadingEntry
    MAX-ACCESS not-accessible
    STATUS     current
    DESCRIPTION
	    "The Performance console .NET CLR Loading
	    category includes counters that provide
	    information about assemblies, classes, and
	    application domains that are loaded."
    ::= { advanced 15 }

dotNETCLRLoadingEntry OBJECT-TYPE
    SYNTAX     DotNETCLRLoadingEntry
    MAX-ACCESS not-accessible
    STATUS     current
    DESCRIPTION
	    "Performance information for one particular
	    instance of '.NET CLR Loading' object."
    INDEX      { nclInstance }
    ::= { dotNETCLRLoadingTable 1 }

DotNETCLRLoadingEntry ::= SEQUENCE {
    nclInstance InstanceName,
    nclPercentTimeLoading Gauge32,
    nclAssemblySearchLength Gauge32,
    nclBytesInLoaderHeap Gauge32,
    nclCurrentAssemblies Gauge32,
    nclCurrentClassesLoaded Gauge32,
    nclCurrentAppdomains Gauge32,
    nclRateOfAssemblies Gauge32,
    nclRateOfClassesLoaded Gauge32,
    nclRateOfLoadFailures Gauge32,
    nclRateOfAppdomains Gauge32,
    nclRateOfAppdomainsUnloaded Gauge32,
    nclTotalNumOfLoadFailures Gauge32,
    nclTotalAppdomains Gauge32,
    nclTotalAssemblies Gauge32,
    nclTotalClassesLoaded Gauge32,
    nclTotalAppdomainsUnloaded Gauge32
}

nclInstance OBJECT-TYPE
    SYNTAX     InstanceName
    MAX-ACCESS read-only
    STATUS     current
    DESCRIPTION
	    "Instance name."
    ::= { dotNETCLRLoadingEntry 1 }

nclPercentTimeLoading OBJECT-TYPE
    SYNTAX     Gauge32
    MAX-ACCESS read-only
    STATUS     current
    DESCRIPTION
	    "Reserved for future use."
    ::= { dotNETCLRLoadingEntry 2 }

nclAssemblySearchLength OBJECT-TYPE
    SYNTAX     Gauge32
    MAX-ACCESS read-only
    STATUS     current
    DESCRIPTION
	    "Reserved for future use."
    ::= { dotNETCLRLoadingEntry 3 }

nclBytesInLoaderHeap OBJECT-TYPE
    SYNTAX     Gauge32
    MAX-ACCESS read-only
    STATUS     current
    DESCRIPTION
	    "This counter displays the current size (in
	    bytes) of the memory committed by the class
	    loader across all AppDomains. (Committed memory
	    is the physical memory for which space has been
	    reserved on the disk paging file.)"
    ::= { dotNETCLRLoadingEntry 4 }

nclCurrentAssemblies OBJECT-TYPE
    SYNTAX     Gauge32
    MAX-ACCESS read-only
    STATUS     current
    DESCRIPTION
	    "This counter displays the current number of
	    Assemblies loaded across all AppDomains in this
	    application. If the Assembly is loaded as
	    domain-neutral from multiple AppDomains then
	    this counter is incremented once only.
	    Assemblies can be loaded as domain-neutral when
	    their code can be shared by all AppDomains or
	    they can be loaded as domain-specific when
	    their code is private to the AppDomain."
    ::= { dotNETCLRLoadingEntry 5 }

nclCurrentClassesLoaded OBJECT-TYPE
    SYNTAX     Gauge32
    MAX-ACCESS read-only
    STATUS     current
    DESCRIPTION
	    "This counter displays the current number of
	    classes loaded in all Assemblies."
    ::= { dotNETCLRLoadingEntry 6 }

nclCurrentAppdomains OBJECT-TYPE
    SYNTAX     Gauge32
    MAX-ACCESS read-only
    STATUS     current
    DESCRIPTION
	    "This counter displays the current number of
	    AppDomains loaded in this application.
	    AppDomains (application domains) provide a
	    secure and versatile unit of processing that
	    the CLR can use to provide isolation between
	    applications running in the same process."
    ::= { dotNETCLRLoadingEntry 7 }

nclRateOfAssemblies OBJECT-TYPE
    SYNTAX     Gauge32
    MAX-ACCESS read-only
    STATUS     current
    DESCRIPTION
	    "This counter displays the number of Assemblies
	    loaded across all AppDomains per second. If the
	    Assembly is loaded as domain-neutral from
	    multiple AppDomains then this counter is
	    incremented once only. Assemblies can be loaded
	    as domain-neutral when their code can be shared
	    by all AppDomains or they can be loaded as
	    domain-specific when their code is private to
	    the AppDomain. This counter is not an average
	    over time; it displays the difference between
	    the values observed in the last two samples
	    divided by the duration of the sample
	    interval."
    ::= { dotNETCLRLoadingEntry 8 }

nclRateOfClassesLoaded OBJECT-TYPE
    SYNTAX     Gauge32
    MAX-ACCESS read-only
    STATUS     current
    DESCRIPTION
	    "This counter displays the number of classes
	    loaded per second in all Assemblies. This
	    counter is not an average over time; it
	    displays the difference between the values
	    observed in the last two samples divided by the
	    duration of the sample interval."
    ::= { dotNETCLRLoadingEntry 9 }

nclRateOfLoadFailures OBJECT-TYPE
    SYNTAX     Gauge32
    MAX-ACCESS read-only
    STATUS     current
    DESCRIPTION
	    "This counter displays the number of classes
	    that failed to load per second. This counter is
	    not an average over time; it displays the
	    difference between the values observed in the
	    last two samples divided by the duration of the
	    sample interval. These load failures could be
	    due to many reasons like inadequate security or
	    illegal format. Full details can be found in
	    the profiling services help."
    ::= { dotNETCLRLoadingEntry 10 }

nclRateOfAppdomains OBJECT-TYPE
    SYNTAX     Gauge32
    MAX-ACCESS read-only
    STATUS     current
    DESCRIPTION
	    "This counter displays the number of AppDomains
	    loaded per second. AppDomains (application
	    domains) provide a secure and versatile unit of
	    processing that the CLR can use to provide
	    isolation between applications running in the
	    same process. This counter is not an average
	    over time; it displays the difference between
	    the values observed in the last two samples
	    divided by the duration of the sample
	    interval."
    ::= { dotNETCLRLoadingEntry 11 }

nclRateOfAppdomainsUnloaded OBJECT-TYPE
    SYNTAX     Gauge32
    MAX-ACCESS read-only
    STATUS     current
    DESCRIPTION
	    "This counter displays the number of AppDomains
	    unloaded per second. This counter is not an
	    average over time; it displays the difference
	    between the values observed in the last two
	    samples divided by the duration of the sample
	    interval."
    ::= { dotNETCLRLoadingEntry 12 }

nclTotalNumOfLoadFailures OBJECT-TYPE
    SYNTAX     Gauge32
    MAX-ACCESS read-only
    STATUS     current
    DESCRIPTION
	    "This counter displays the peak number of
	    classes that have failed to load since the
	    start of the application. These load failures
	    could be due to many reasons like inadequate
	    security or illegal format. Full details can be
	    found in the profiling services help."
    ::= { dotNETCLRLoadingEntry 13 }

nclTotalAppdomains OBJECT-TYPE
    SYNTAX     Gauge32
    MAX-ACCESS read-only
    STATUS     current
    DESCRIPTION
	    "This counter displays the peak number of
	    AppDomains loaded since the start of this
	    application. AppDomains (application domains)
	    provide a secure and versatile unit of
	    processing that the CLR can use to provide
	    isolation between applications running in the
	    same process."
    ::= { dotNETCLRLoadingEntry 14 }

nclTotalAssemblies OBJECT-TYPE
    SYNTAX     Gauge32
    MAX-ACCESS read-only
    STATUS     current
    DESCRIPTION
	    "This counter displays the total number of
	    Assemblies loaded since the start of this
	    application. If the Assembly is loaded as
	    domain-neutral from multiple AppDomains then
	    this counter is incremented once only.
	    Assemblies can be loaded as domain-neutral when
	    their code can be shared by all AppDomains or
	    they can be loaded as domain-specific when
	    their code is private to the AppDomain."
    ::= { dotNETCLRLoadingEntry 15 }

nclTotalClassesLoaded OBJECT-TYPE
    SYNTAX     Gauge32
    MAX-ACCESS read-only
    STATUS     current
    DESCRIPTION
	    "This counter displays the cumulative number of
	    classes loaded in all Assemblies since the
	    start of this application."
    ::= { dotNETCLRLoadingEntry 16 }

nclTotalAppdomainsUnloaded OBJECT-TYPE
    SYNTAX     Gauge32
    MAX-ACCESS read-only
    STATUS     current
    DESCRIPTION
	    "This counter displays the total number of
	    AppDomains unloaded since the start of the
	    application. If an AppDomain is loaded and
	    unloaded multiple times this counter would
	    count each of those unloads as separate."
    ::= { dotNETCLRLoadingEntry 17 }

dotNETCLRLocksAndThreadsTable OBJECT-TYPE
    SYNTAX     SEQUENCE OF DotNETCLRLocksAndThreadsEntry
    MAX-ACCESS not-accessible
    STATUS     current
    DESCRIPTION
	    "The Performance console .NET CLR
	    LocksAndThreads category includes counters that
	    provide information about managed locks and
	    threads that an application uses."
    ::= { advanced 16 }

dotNETCLRLocksAndThreadsEntry OBJECT-TYPE
    SYNTAX     DotNETCLRLocksAndThreadsEntry
    MAX-ACCESS not-accessible
    STATUS     current
    DESCRIPTION
	    "Performance information for one particular
	    instance of '.NET CLR LocksAndThreads' object."
    INDEX      { ncltInstance }
    ::= { dotNETCLRLocksAndThreadsTable 1 }

DotNETCLRLocksAndThreadsEntry ::= SEQUENCE {
    ncltInstance InstanceName,
    ncltNumOfCurrentLogicalThread Gauge32,
    ncltNumOfCurrentPhysicalThread Gauge32,
    ncltNumOfCurrentRecognizedThread Gauge32,
    ncltNumOfTotalRecognizedThread Gauge32,
    ncltContentionRatePerSec Gauge32,
    ncltCurrentQueueLength Gauge32,
    ncltQueueLengthPerSec Gauge32,
    ncltQueueLengthPeak Gauge32,
    ncltTotalNumOfContentions Gauge32,
    ncltRateOfRecognizedThreadPerSec Gauge32
}

ncltInstance OBJECT-TYPE
    SYNTAX     InstanceName
    MAX-ACCESS read-only
    STATUS     current
    DESCRIPTION
	    "Instance name."
    ::= { dotNETCLRLocksAndThreadsEntry 1 }

ncltNumOfCurrentLogicalThread OBJECT-TYPE
    SYNTAX     Gauge32
    MAX-ACCESS read-only
    STATUS     current
    DESCRIPTION
	    "This counter displays the number of current
	    .NET thread objects in the application. A .NET
	    thread object is created either by new
	    System.Threading.Thread or when an unmanaged
	    thread enters the managed environment. This
	    counters maintains the count of both running
	    and stopped threads. This counter is not an
	    average over time; it just displays the last
	    observed value."
    ::= { dotNETCLRLocksAndThreadsEntry 2 }

ncltNumOfCurrentPhysicalThread OBJECT-TYPE
    SYNTAX     Gauge32
    MAX-ACCESS read-only
    STATUS     current
    DESCRIPTION
	    "This counter displays the number of native OS
	    threads created and owned by the CLR to act as
	    underlying threads for .NET thread objects.
	    This counters value does not include the
	    threads used by the CLR in its internal
	    operations; it is a subset of the threads in
	    the OS process."
    ::= { dotNETCLRLocksAndThreadsEntry 3 }

ncltNumOfCurrentRecognizedThread OBJECT-TYPE
    SYNTAX     Gauge32
    MAX-ACCESS read-only
    STATUS     current
    DESCRIPTION
	    "This counter displays the number of threads
	    that are currently recognized by the CLR; they
	    have a corresponding .NET thread object
	    associated with them. These threads are not
	    created by the CLR; they are created outside
	    the CLR but have since run inside the CLR at
	    least once. Only unique threads are tracked;
	    threads with same thread ID re-entering the CLR
	    or recreated after thread exit are not counted
	    twice."
    ::= { dotNETCLRLocksAndThreadsEntry 4 }

ncltNumOfTotalRecognizedThread OBJECT-TYPE
    SYNTAX     Gauge32
    MAX-ACCESS read-only
    STATUS     current
    DESCRIPTION
	    "This counter displays the total number of
	    threads that have been recognized by the CLR
	    since the start of this application; these
	    threads have a corresponding .NET thread object
	    associated with them. These threads are not
	    created by the CLR; they are created outside
	    the CLR but have since run inside the CLR at
	    least once. Only unique threads are tracked;
	    threads with same thread ID re-entering the CLR
	    or recreated after thread exit are not counted
	    twice."
    ::= { dotNETCLRLocksAndThreadsEntry 5 }

ncltContentionRatePerSec OBJECT-TYPE
    SYNTAX     Gauge32
    MAX-ACCESS read-only
    STATUS     current
    DESCRIPTION
	    "Rate at which threads in the runtime attempt
	    to acquire a managed lock unsuccessfully.
	    Managed locks can be acquired in many ways; by
	    the 'lock' statement in C# or by calling
	    System.Monitor.Enter or by using
	    MethodImplOptions.Synchronized custom
	    attribute."
    ::= { dotNETCLRLocksAndThreadsEntry 6 }

ncltCurrentQueueLength OBJECT-TYPE
    SYNTAX     Gauge32
    MAX-ACCESS read-only
    STATUS     current
    DESCRIPTION
	    "This counter displays the total number of
	    threads currently waiting to acquire some
	    managed lock in the application. This counter
	    is not an average over time; it displays the
	    last observed value."
    ::= { dotNETCLRLocksAndThreadsEntry 7 }

ncltQueueLengthPerSec OBJECT-TYPE
    SYNTAX     Gauge32
    MAX-ACCESS read-only
    STATUS     current
    DESCRIPTION
	    "This counter displays the number of threads
	    per second waiting to acquire some lock in the
	    application. This counter is not an average
	    over time; it displays the difference between
	    the values observed in the last two samples
	    divided by the duration of the sample
	    interval."
    ::= { dotNETCLRLocksAndThreadsEntry 8 }

ncltQueueLengthPeak OBJECT-TYPE
    SYNTAX     Gauge32
    MAX-ACCESS read-only
    STATUS     current
    DESCRIPTION
	    "This counter displays the total number of
	    threads that waited to acquire some managed
	    lock since the start of the application."
    ::= { dotNETCLRLocksAndThreadsEntry 9 }

ncltTotalNumOfContentions OBJECT-TYPE
    SYNTAX     Gauge32
    MAX-ACCESS read-only
    STATUS     current
    DESCRIPTION
	    "This counter displays the total number of
	    times threads in the CLR have attempted to
	    acquire a managed lock unsuccessfully. Managed
	    locks can be acquired in many ways; by the
	    'lock' statement in C# or by calling
	    System.Monitor.Enter or by using
	    MethodImplOptions.Synchronized custom
	    attribute."
    ::= { dotNETCLRLocksAndThreadsEntry 10 }

ncltRateOfRecognizedThreadPerSec OBJECT-TYPE
    SYNTAX     Gauge32
    MAX-ACCESS read-only
    STATUS     current
    DESCRIPTION
	    "This counter displays the number of threads
	    per second that have been recognized by the
	    CLR; these threads have a corresponding .NET
	    thread object associated with them. These
	    threads are not created by the CLR; they are
	    created outside the CLR but have since run
	    inside the CLR at least once. Only unique
	    threads are tracked; threads with same thread
	    ID re-entering the CLR or recreated after
	    thread exit are not counted twice. This counter
	    is not an average over time; it displays the
	    difference between the values observed in the
	    last two samples divided by the duration of the
	    sample interval."
    ::= { dotNETCLRLocksAndThreadsEntry 11 }

dotNETCLRMemoryTable OBJECT-TYPE
    SYNTAX     SEQUENCE OF DotNETCLRMemoryEntry
    MAX-ACCESS not-accessible
    STATUS     current
    DESCRIPTION
	    "The Performance console .NET CLR Memory
	    category includes counters that provide
	    information about the garbage collector."
    ::= { advanced 17 }

dotNETCLRMemoryEntry OBJECT-TYPE
    SYNTAX     DotNETCLRMemoryEntry
    MAX-ACCESS not-accessible
    STATUS     current
    DESCRIPTION
	    "Performance information for one particular
	    instance of '.NET CLR Memory' object."
    INDEX      { ncmInstance }
    ::= { dotNETCLRMemoryTable 1 }

DotNETCLRMemoryEntry ::= SEQUENCE {
    ncmInstance InstanceName,
    ncmNumBytesInAllHeaps Gauge32,
    ncmNumGCHandles Gauge32,
    ncmNumGen0Collections Gauge32,
    ncmNumGen1Collections Gauge32,
    ncmNumGen2Collections Gauge32,
    ncmNumInducedGC Gauge32,
    ncmNumTotalCommittedBytes Gauge32,
    ncmNumTotalReservedBytes Gauge32,
    ncmNumOfPinnedObjects Gauge32,
    ncmNumOfSinkBlocksInUse Gauge32,
    ncmPercentTimeInGC Gauge32,
    ncmAllocatedBytesPerSec Gauge32,
    ncmFinalizationSurvivors Gauge32,
    ncmGen0PromotedBytesPerSec Gauge32,
    ncmGen0HeapSize Gauge32,
    ncmGen1PromotedBytesPerSec Gauge32,
    ncmGen1HeapSize Gauge32,
    ncmGen2HeapSize Gauge32,
    ncmLargeObjectHeapSize Gauge32,
    ncmPromotFinalizationMemoryGen0 Gauge32,
    ncmPromotFinalizationMemoryGen1 Gauge32,
    ncmPromotedMemoryFromGen0 Gauge32,
    ncmPromotedMemoryFromGen1 Gauge32
}

ncmInstance OBJECT-TYPE
    SYNTAX     InstanceName
    MAX-ACCESS read-only
    STATUS     current
    DESCRIPTION
	    "Instance name."
    ::= { dotNETCLRMemoryEntry 1 }

ncmNumBytesInAllHeaps OBJECT-TYPE
    SYNTAX     Gauge32
    MAX-ACCESS read-only
    STATUS     current
    DESCRIPTION
	    "This counter is the sum of four other
	    counters; Gen 0 Heap Size; Gen 1 Heap Size; Gen
	    2 Heap Size and the Large Object Heap Size.
	    This counter indicates the current memory
	    allocated in bytes on the GC Heaps."
    ::= { dotNETCLRMemoryEntry 2 }

ncmNumGCHandles OBJECT-TYPE
    SYNTAX     Gauge32
    MAX-ACCESS read-only
    STATUS     current
    DESCRIPTION
	    "This counter displays the current number of GC
	    Handles in use. GCHandles are handles to
	    resources external to the CLR and the managed
	    environment. Handles occupy small amounts of
	    memory in the GCHeap but potentially expensive
	    unmanaged resources."
    ::= { dotNETCLRMemoryEntry 3 }

ncmNumGen0Collections OBJECT-TYPE
    SYNTAX     Gauge32
    MAX-ACCESS read-only
    STATUS     current
    DESCRIPTION
	    "This counter displays the number of times the
	    generation 0 objects (youngest; most recently
	    allocated) are garbage collected (Gen 0 GC)
	    since the start of the application. Gen 0 GC
	    occurs when the available memory in generation
	    0 is not sufficient to satisfy an allocation
	    request. This counter is incremented at the end
	    of a Gen 0 GC. Higher generation GCs include
	    all lower generation GCs. This counter is
	    explicitly incremented when a higher generation
	    (Gen 1 or Gen 2) GC occurs. _Global_ counter
	    value is not accurate and should be ignored.
	    This counter displays the last observed value."
    ::= { dotNETCLRMemoryEntry 4 }

ncmNumGen1Collections OBJECT-TYPE
    SYNTAX     Gauge32
    MAX-ACCESS read-only
    STATUS     current
    DESCRIPTION
	    "This counter displays the number of times the
	    generation 1 objects are garbage collected
	    since the start of the application. The counter
	    is incremented at the end of a Gen 1 GC. Higher
	    generation GCs include all lower generation
	    GCs. This counter is explicitly incremented
	    when a higher generation (Gen 2) GC occurs.
	    _Global_ counter value is not accurate and
	    should be ignored. This counter displays the
	    last observed value."
    ::= { dotNETCLRMemoryEntry 5 }

ncmNumGen2Collections OBJECT-TYPE
    SYNTAX     Gauge32
    MAX-ACCESS read-only
    STATUS     current
    DESCRIPTION
	    "This counter displays the number of times the
	    generation 2 objects (older) are garbage
	    collected since the start of the application.
	    The counter is incremented at the end of a Gen
	    2 GC (also called full GC). _Global_ counter
	    value is not accurate and should be ignored.
	    This counter displays the last observed value."
    ::= { dotNETCLRMemoryEntry 6 }

ncmNumInducedGC OBJECT-TYPE
    SYNTAX     Gauge32
    MAX-ACCESS read-only
    STATUS     current
    DESCRIPTION
	    "This counter displays the peak number of times
	    a garbage collection was performed because of
	    an explicit call to GC.Collect. Its a good
	    practice to let the GC tune the frequency of
	    its collections."
    ::= { dotNETCLRMemoryEntry 7 }

ncmNumTotalCommittedBytes OBJECT-TYPE
    SYNTAX     Gauge32
    MAX-ACCESS read-only
    STATUS     current
    DESCRIPTION
	    "This counter displays the amount of virtual
	    memory (in bytes) currently committed by the
	    Garbage Collector. (Committed memory is the
	    physical memory for which space has been
	    reserved on the disk paging file)."
    ::= { dotNETCLRMemoryEntry 8 }

ncmNumTotalReservedBytes OBJECT-TYPE
    SYNTAX     Gauge32
    MAX-ACCESS read-only
    STATUS     current
    DESCRIPTION
	    "This counter displays the amount of virtual
	    memory (in bytes) currently reserved by the
	    Garbage Collector. (Reserved memory is the
	    virtual memory space reserved for the
	    application but no disk or main memory pages
	    have been used.)"
    ::= { dotNETCLRMemoryEntry 9 }

ncmNumOfPinnedObjects OBJECT-TYPE
    SYNTAX     Gauge32
    MAX-ACCESS read-only
    STATUS     current
    DESCRIPTION
	    "This counter displays the number of pinned
	    objects encountered in the last GC. This
	    counter tracks the pinned objects only in the
	    heaps that were garbage collected e.g. a Gen 0
	    GC would cause enumeration of pinned objects in
	    the generation 0 heap only. A pinned object is
	    one that the Garbage Collector cannot move in
	    memory."
    ::= { dotNETCLRMemoryEntry 10 }

ncmNumOfSinkBlocksInUse OBJECT-TYPE
    SYNTAX     Gauge32
    MAX-ACCESS read-only
    STATUS     current
    DESCRIPTION
	    "This counter displays the current number of
	    sync blocks in use. Sync blocks are per-object
	    data structures allocated for storing
	    synchronization information. Sync blocks hold
	    weak references to managed objects and need to
	    be scanned by the Garbage Collector. Sync
	    blocks are not limited to storing
	    synchronization information and can also store
	    COM interop metadata. This counter was designed
	    to indicate performance problems with heavy use
	    of synchronization primitives."
    ::= { dotNETCLRMemoryEntry 11 }

ncmPercentTimeInGC OBJECT-TYPE
    SYNTAX     Gauge32
    MAX-ACCESS read-only
    STATUS     current
    DESCRIPTION
	    "% Time in GC is the percentage of elapsed time
	    that was spent in performing a garbage
	    collection (GC) since the last GC cycle. This
	    counter is usually an indicator of the work
	    done by the Garbage Collector on behalf of the
	    application to collect and compact memory. This
	    counter is updated only at the end of every GC
	    and the counter value reflects the last
	    observed value; its not an average."
    ::= { dotNETCLRMemoryEntry 12 }

ncmAllocatedBytesPerSec OBJECT-TYPE
    SYNTAX     Gauge32
    MAX-ACCESS read-only
    STATUS     current
    DESCRIPTION
	    "This counter displays the rate of bytes per
	    second allocated on the GC Heap. This counter
	    is updated at the end of every GC; not at each
	    allocation. This counter is not an average over
	    time; it displays the difference between the
	    values observed in the last two samples divided
	    by the duration of the sample interval."
    ::= { dotNETCLRMemoryEntry 13 }

ncmFinalizationSurvivors OBJECT-TYPE
    SYNTAX     Gauge32
    MAX-ACCESS read-only
    STATUS     current
    DESCRIPTION
	    "This counter displays the number of garbage
	    collected objects that survive a collection
	    because they are waiting to be finalized. If
	    these objects hold references to other objects
	    then those objects also survive but are not
	    counted by this counter; the 'Promoted
	    Finalization-Memory from Gen 0' and 'Promoted
	    Finalization-Memory from Gen 1' counters
	    represent all the memory that survived due to
	    finalization. This counter is not a cumulative
	    counter; its updated at the end of every GC
	    with count of the survivors during that
	    particular GC only. This counter was designed
	    to indicate the extra overhead that the
	    application might incur because of
	    finalization."
    ::= { dotNETCLRMemoryEntry 14 }

ncmGen0PromotedBytesPerSec OBJECT-TYPE
    SYNTAX     Gauge32
    MAX-ACCESS read-only
    STATUS     current
    DESCRIPTION
	    "This counter displays the bytes per second
	    that are promoted from generation 0 (youngest)
	    to generation 1; objects that are promoted just
	    because they are waiting to be finalized are
	    not included in this counter. Memory is
	    promoted when it survives a garbage collection.
	    This counter was designed as an indicator of
	    relatively long-lived objects being created per
	    sec. This counter displays the difference
	    between the values observed in the last two
	    samples divided by the duration of the sample
	    interval."
    ::= { dotNETCLRMemoryEntry 15 }

ncmGen0HeapSize OBJECT-TYPE
    SYNTAX     Gauge32
    MAX-ACCESS read-only
    STATUS     current
    DESCRIPTION
	    "This counter displays the maximum bytes that
	    can be allocated in generation 0 (Gen 0); its
	    does not indicate the current number of bytes
	    allocated in Gen 0. A Gen 0 GC is triggered
	    when the allocations since the last GC exceed
	    this size. The Gen 0 size is tuned by the
	    Garbage Collector and can change during the
	    execution of the application. At the end of a
	    Gen 0 collection the size of the Gen 0 heap is
	    infact 0 bytes; this counter displays the size
	    (in bytes) of allocations that would trigger
	    the next Gen 0 GC. This counter is updated at
	    the end of a GC; its not updated on every
	    allocation."
    ::= { dotNETCLRMemoryEntry 16 }

ncmGen1PromotedBytesPerSec OBJECT-TYPE
    SYNTAX     Gauge32
    MAX-ACCESS read-only
    STATUS     current
    DESCRIPTION
	    "This counter displays the bytes per second
	    that are promoted from generation 1 to
	    generation 2 (oldest); objects that are
	    promoted just because they are waiting to be
	    finalized are not included in this counter.
	    Memory is promoted when it survives a garbage
	    collection. Nothing is promoted from generation
	    2 since it is the oldest. This counter was
	    designed as an indicator of very long-lived
	    objects being created per sec. This counter
	    displays the difference between the values
	    observed in the last two samples divided by the
	    duration of the sample interval."
    ::= { dotNETCLRMemoryEntry 17 }

ncmGen1HeapSize OBJECT-TYPE
    SYNTAX     Gauge32
    MAX-ACCESS read-only
    STATUS     current
    DESCRIPTION
	    "This counter displays the current number of
	    bytes in generation 1 (Gen 1); this counter
	    does not display the maximum size of Gen 1.
	    Objects are not directly allocated in this
	    generation; they are promoted from previous Gen
	    0 GCs. This counter is updated at the end of a
	    GC; its not updated on every allocation."
    ::= { dotNETCLRMemoryEntry 18 }

ncmGen2HeapSize OBJECT-TYPE
    SYNTAX     Gauge32
    MAX-ACCESS read-only
    STATUS     current
    DESCRIPTION
	    "This counter displays the current number of
	    bytes in generation 2 (Gen 2). Objects are not
	    directly allocated in this generation; they are
	    promoted from Gen 1 during previous Gen 1 GCs.
	    This counter is updated at the end of a GC; its
	    not updated on every allocation."
    ::= { dotNETCLRMemoryEntry 19 }

ncmLargeObjectHeapSize OBJECT-TYPE
    SYNTAX     Gauge32
    MAX-ACCESS read-only
    STATUS     current
    DESCRIPTION
	    "This counter displays the current size of the
	    Large Object Heap in bytes. Objects greater
	    than 20 KBytes are treated as large objects by
	    the Garbage Collector and are directly
	    allocated in a special heap; they are not
	    promoted through the generations. This counter
	    is updated at the end of a GC; its not updated
	    on every allocation."
    ::= { dotNETCLRMemoryEntry 20 }

ncmPromotFinalizationMemoryGen0 OBJECT-TYPE
    SYNTAX     Gauge32
    MAX-ACCESS read-only
    STATUS     current
    DESCRIPTION
	    "This counter displays the bytes of memory that
	    are promoted from generation 0 to generation 1
	    just because they are waiting to be finalized.
	    This counter displays the value observed at the
	    end of the last GC; its not a cumulative
	    counter."
    ::= { dotNETCLRMemoryEntry 21 }

ncmPromotFinalizationMemoryGen1 OBJECT-TYPE
    SYNTAX     Gauge32
    MAX-ACCESS read-only
    STATUS     current
    DESCRIPTION
	    "This counter displays the bytes of memory that
	    are promoted from generation 1 to generation 2
	    just because they are waiting to be finalized.
	    This counter displays the value observed at the
	    end of the last GC; its not a cumulative
	    counter. This counter is reset to 0 if the last
	    GC was a Gen 0 GC only."
    ::= { dotNETCLRMemoryEntry 22 }

ncmPromotedMemoryFromGen0 OBJECT-TYPE
    SYNTAX     Gauge32
    MAX-ACCESS read-only
    STATUS     current
    DESCRIPTION
	    "This counter displays the bytes of memory that
	    survive garbage collection (GC) and are
	    promoted from generation 0 to generation 1;
	    objects that are promoted just because they are
	    waiting to be finalized are not included in
	    this counter. This counter displays the value
	    observed at the end of the last GC; its not a
	    cumulative counter."
    ::= { dotNETCLRMemoryEntry 23 }

ncmPromotedMemoryFromGen1 OBJECT-TYPE
    SYNTAX     Gauge32
    MAX-ACCESS read-only
    STATUS     current
    DESCRIPTION
	    "This counter displays the bytes of memory that
	    survive garbage collection (GC) and are
	    promoted from generation 1 to generation 2;
	    objects that are promoted just because they are
	    waiting to be finalized are not included in
	    this counter. This counter displays the value
	    observed at the end of the last GC; its not a
	    cumulative counter. This counter is reset to 0
	    if the last GC was a Gen 0 GC only."
    ::= { dotNETCLRMemoryEntry 24 }

dotNETCLRNetworkingTable OBJECT-TYPE
    SYNTAX     SEQUENCE OF DotNETCLRNetworkingEntry
    MAX-ACCESS not-accessible
    STATUS     current
    DESCRIPTION
	    "The Performance console .NET CLR Networking
	    category includes counters that provide
	    information about data that an application
	    sends and receives over the network."
    ::= { advanced 18 }

dotNETCLRNetworkingEntry OBJECT-TYPE
    SYNTAX     DotNETCLRNetworkingEntry
    MAX-ACCESS not-accessible
    STATUS     current
    DESCRIPTION
	    "Performance information for one particular
	    instance of '.NET CLR Networking' object."
    INDEX      { ncnInstance }
    ::= { dotNETCLRNetworkingTable 1 }

DotNETCLRNetworkingEntry ::= SEQUENCE {
    ncnInstance InstanceName,
    ncnBytesReceived Gauge32,
    ncnBytesSent Gauge32,
    ncnConnectionsEstablished Gauge32,
    ncnDatagramsReceived Gauge32,
    ncnDatagramsSent Gauge32
}

ncnInstance OBJECT-TYPE
    SYNTAX     InstanceName
    MAX-ACCESS read-only
    STATUS     current
    DESCRIPTION
	    "Instance name."
    ::= { dotNETCLRNetworkingEntry 1 }

ncnBytesReceived OBJECT-TYPE
    SYNTAX     Gauge32
    MAX-ACCESS read-only
    STATUS     current
    DESCRIPTION
	    "The cumulative total number of bytes received
	    over all open socket connections since the
	    process was started. This number includes data
	    and any protocol information that is not
	    defined by the TCP/IP protocol."
    ::= { dotNETCLRNetworkingEntry 2 }

ncnBytesSent OBJECT-TYPE
    SYNTAX     Gauge32
    MAX-ACCESS read-only
    STATUS     current
    DESCRIPTION
	    "The cumulative total number of bytes sent over
	    all open socket connections since the process
	    was started. This number includes data and any
	    protocol information that is not defined by the
	    TCP/IP protocol."
    ::= { dotNETCLRNetworkingEntry 3 }

ncnConnectionsEstablished OBJECT-TYPE
    SYNTAX     Gauge32
    MAX-ACCESS read-only
    STATUS     current
    DESCRIPTION
	    "The cumulative total number of socket
	    connections established for this process since
	    the process was started."
    ::= { dotNETCLRNetworkingEntry 4 }

ncnDatagramsReceived OBJECT-TYPE
    SYNTAX     Gauge32
    MAX-ACCESS read-only
    STATUS     current
    DESCRIPTION
	    "The cumulative total number of datagram
	    packets received since the process was
	    started."
    ::= { dotNETCLRNetworkingEntry 5 }

ncnDatagramsSent OBJECT-TYPE
    SYNTAX     Gauge32
    MAX-ACCESS read-only
    STATUS     current
    DESCRIPTION
	    "The cumulative total number of datagram
	    packets sent since the process was started."
    ::= { dotNETCLRNetworkingEntry 6 }

dotNETCLRRemotingTable OBJECT-TYPE
    SYNTAX     SEQUENCE OF DotNETCLRRemotingEntry
    MAX-ACCESS not-accessible
    STATUS     current
    DESCRIPTION
	    "The Performance console .NET CLR Remoting
	    category includes counters that provide
	    information about the remoted objects that an
	    application uses."
    ::= { advanced 19 }

dotNETCLRRemotingEntry OBJECT-TYPE
    SYNTAX     DotNETCLRRemotingEntry
    MAX-ACCESS not-accessible
    STATUS     current
    DESCRIPTION
	    "Performance information for one particular
	    instance of '.NET CLR Remoting' object."
    INDEX      { ncrInstance }
    ::= { dotNETCLRRemotingTable 1 }

DotNETCLRRemotingEntry ::= SEQUENCE {
    ncrInstance InstanceName,
    ncrChannels Gauge32,
    ncrContextProxies Gauge32,
    ncrContextBoundClassesLoaded Gauge32,
    ncrContextBoundObjsAllocPerSec Gauge32,
    ncrContexts Gauge32,
    ncrRemoteCallsPerSec Gauge32,
    ncrTotalRemoteCalls Gauge32
}

ncrInstance OBJECT-TYPE
    SYNTAX     InstanceName
    MAX-ACCESS read-only
    STATUS     current
    DESCRIPTION
	    "Instance name."
    ::= { dotNETCLRRemotingEntry 1 }

ncrChannels OBJECT-TYPE
    SYNTAX     Gauge32
    MAX-ACCESS read-only
    STATUS     current
    DESCRIPTION
	    "This counter displays the total number of
	    remoting channels registered across all
	    AppDomains since the start of the application.
	    Channels are used to transport messages to and
	    from remote objects."
    ::= { dotNETCLRRemotingEntry 2 }

ncrContextProxies OBJECT-TYPE
    SYNTAX     Gauge32
    MAX-ACCESS read-only
    STATUS     current
    DESCRIPTION
	    "This counter displays the total number of
	    remoting proxy objects created in this process
	    since the start of the process. Proxy object
	    acts as a representative of the remote objects
	    and ensures that all calls made on the proxy
	    are forwarded to the correct remote object
	    instance."
    ::= { dotNETCLRRemotingEntry 3 }

ncrContextBoundClassesLoaded OBJECT-TYPE
    SYNTAX     Gauge32
    MAX-ACCESS read-only
    STATUS     current
    DESCRIPTION
	    "This counter displays the current number of
	    context-bound classes loaded. Classes that can
	    be bound to a context are called context-bound
	    classes; context-bound classes are marked with
	    Context Attributes which provide usage rules
	    for synchronization; thread affinity;
	    transactions etc."
    ::= { dotNETCLRRemotingEntry 4 }

ncrContextBoundObjsAllocPerSec OBJECT-TYPE
    SYNTAX     Gauge32
    MAX-ACCESS read-only
    STATUS     current
    DESCRIPTION
	    "This counter displays the number of
	    context-bound objects allocated per second.
	    Instances of classes that can be bound to a
	    context are called context-bound objects;
	    context-bound classes are marked with Context
	    Attributes which provide usage rules for
	    synchronization; thread affinity; transactions
	    etc. This counter is not an average over time;
	    it displays the difference between the values
	    observed in the last two samples divided by the
	    duration of the sample interval."
    ::= { dotNETCLRRemotingEntry 5 }

ncrContexts OBJECT-TYPE
    SYNTAX     Gauge32
    MAX-ACCESS read-only
    STATUS     current
    DESCRIPTION
	    "This counter displays the current number of
	    remoting contexts in the application. A context
	    is a boundary containing a collection of
	    objects with the same usage rules like
	    synchronization; thread affinity; transactions
	    etc."
    ::= { dotNETCLRRemotingEntry 6 }

ncrRemoteCallsPerSec OBJECT-TYPE
    SYNTAX     Gauge32
    MAX-ACCESS read-only
    STATUS     current
    DESCRIPTION
	    "This counter displays the number of remote
	    procedure calls invoked per second. A remote
	    procedure call is a call on any object outside
	    the caller;s AppDomain. This counter is not an
	    average over time; it displays the difference
	    between the values observed in the last two
	    samples divided by the duration of the sample
	    interval."
    ::= { dotNETCLRRemotingEntry 7 }

ncrTotalRemoteCalls OBJECT-TYPE
    SYNTAX     Gauge32
    MAX-ACCESS read-only
    STATUS     current
    DESCRIPTION
	    "This counter displays the total number of
	    remote procedure calls invoked since the start
	    of this application. A remote procedure call is
	    a call on any object outside the caller;s
	    AppDomain."
    ::= { dotNETCLRRemotingEntry 8 }

dotNETCLRSecurityTable OBJECT-TYPE
    SYNTAX     SEQUENCE OF DotNETCLRSecurityEntry
    MAX-ACCESS not-accessible
    STATUS     current
    DESCRIPTION
	    "The Performance console .NET CLR Security
	    category includes counters that provide
	    information about the security checks that the
	    common language runtime performs for an
	    application."
    ::= { advanced 20 }

dotNETCLRSecurityEntry OBJECT-TYPE
    SYNTAX     DotNETCLRSecurityEntry
    MAX-ACCESS not-accessible
    STATUS     current
    DESCRIPTION
	    "Performance information for one particular
	    instance of '.NET CLR Security' object."
    INDEX      { ncsInstance }
    ::= { dotNETCLRSecurityTable 1 }

DotNETCLRSecurityEntry ::= SEQUENCE {
    ncsInstance InstanceName,
    ncsNumLinkTimeChecks Gauge32,
    ncsPercentTimeSigAuthenticating Gauge32,
    ncsPercentTimeInRTChecks Gauge32,
    ncsStackWalkDepth Gauge32,
    ncsTotalRuntimeChecks Gauge32
}

ncsInstance OBJECT-TYPE
    SYNTAX     InstanceName
    MAX-ACCESS read-only
    STATUS     current
    DESCRIPTION
	    "Instance name."
    ::= { dotNETCLRSecurityEntry 1 }

ncsNumLinkTimeChecks OBJECT-TYPE
    SYNTAX     Gauge32
    MAX-ACCESS read-only
    STATUS     current
    DESCRIPTION
	    "This counter displays the total number of
	    linktime Code Access Security (CAS) checks
	    since the start of the application. Linktime
	    CAS checks are performed when a caller makes a
	    call to a callee demanding a particular
	    permission at JIT compile time; linktime check
	    is performed once per caller. This count is not
	    indicative of serious performance issues; its
	    indicative of the security system activity."
    ::= { dotNETCLRSecurityEntry 2 }

ncsPercentTimeSigAuthenticating OBJECT-TYPE
    SYNTAX     Gauge32
    MAX-ACCESS read-only
    STATUS     current
    DESCRIPTION
	    "Reserved for future use."
    ::= { dotNETCLRSecurityEntry 3 }

ncsPercentTimeInRTChecks OBJECT-TYPE
    SYNTAX     Gauge32
    MAX-ACCESS read-only
    STATUS     current
    DESCRIPTION
	    "This counter displays the percentage of
	    elapsed time spent in performing runtime Code
	    Access Security (CAS) checks since the last
	    such check. CAS allows code to be trusted to
	    varying degrees and enforces these varying
	    levels of trust depending on code identity.
	    This counter is updated at the end of a runtime
	    security check; it represents the last observed
	    value; its not an average."
    ::= { dotNETCLRSecurityEntry 4 }

ncsStackWalkDepth OBJECT-TYPE
    SYNTAX     Gauge32
    MAX-ACCESS read-only
    STATUS     current
    DESCRIPTION
	    "This counter displays the depth of the stack
	    during that last runtime Code Access Security
	    check. Runtime Code Access Security check is
	    performed by crawling the stack. This counter
	    is not an average; it just displays the last
	    observed value."
    ::= { dotNETCLRSecurityEntry 5 }

ncsTotalRuntimeChecks OBJECT-TYPE
    SYNTAX     Gauge32
    MAX-ACCESS read-only
    STATUS     current
    DESCRIPTION
	    "This counter displays the total number of
	    runtime Code Access Security (CAS) checks
	    performed since the start of the application.
	    Runtime CAS checks are performed when a caller
	    makes a call to a callee demanding a particular
	    permission; the runtime check is made on every
	    call by the caller; the check is done by
	    examining the current thread stack of the
	    caller. This counter used together with 'Stack
	    Walk Depth' is indicative of performance
	    penalty for security checks."
    ::= { dotNETCLRSecurityEntry 6 }

fileReplicaConnTable OBJECT-TYPE
    SYNTAX     SEQUENCE OF FileReplicaConnEntry
    MAX-ACCESS not-accessible
    STATUS     current
    DESCRIPTION
	    "The FileReplicaConn performance object
	    displays performance statistics of the
	    REPLICACONN object that defines replica
	    connections to distributed file system (Dfs)
	    roots."
    ::= { advanced 21 }

fileReplicaConnEntry OBJECT-TYPE
    SYNTAX     FileReplicaConnEntry
    MAX-ACCESS not-accessible
    STATUS     current
    DESCRIPTION
	    "Performance information for one particular
	    instance of 'FileReplicaConn' object."
    INDEX      { frcInstance }
    ::= { fileReplicaConnTable 1 }

FileReplicaConnEntry ::= SEQUENCE {
    frcInstance InstanceName,
    frcAuthentications Gauge32,
    frcAuthenticationsInError Gauge32,
    frcBindings Gauge32,
    frcBindingsInError Gauge32,
    frcCommunicationTimeouts Gauge32,
    frcFetchBlocksReceived Gauge32,
    frcFetchBlocksReceivedInBytes Gauge32,
    frcFetchBlocksSent Gauge32,
    frcFetchBlocksSentInBytes Gauge32,
    frcFetchRequestsReceived Gauge32,
    frcFetchRequestsSent Gauge32,
    frcInboundChangeOrdersDampened Gauge32,
    frcJoinNotificationsReceived Gauge32,
    frcJoinNotificationsSent Gauge32,
    frcJoins Gauge32,
    frcLocalChangeOrdersSent Gauge32,
    frcLocalChangeOrdersSentAtJoin Gauge32,
    frcOutboundChangeOrdersDampened Gauge32,
    frcPacketsSent Gauge32,
    frcPacketsSentInBytes Gauge32,
    frcPacketsSentInError Gauge32,
    frcRemoteChangeOrdersReceived Gauge32,
    frcRemoteChangeOrdersSent Gauge32,
    frcUnjoins Gauge32
}

frcInstance OBJECT-TYPE
    SYNTAX     InstanceName
    MAX-ACCESS read-only
    STATUS     current
    DESCRIPTION
	    "Instance name."
    ::= { fileReplicaConnEntry 1 }

frcAuthentications OBJECT-TYPE
    SYNTAX     Gauge32
    MAX-ACCESS read-only
    STATUS     current
    DESCRIPTION
	    "The number of successful authentication checks
	    made on packets received from the partner
	    associated with this connection."
    ::= { fileReplicaConnEntry 2 }

frcAuthenticationsInError OBJECT-TYPE
    SYNTAX     Gauge32
    MAX-ACCESS read-only
    STATUS     current
    DESCRIPTION
	    "The cumulative number of authentication check
	    failures detected on packets received from the
	    partner associated with this connection."
    ::= { fileReplicaConnEntry 3 }

frcBindings OBJECT-TYPE
    SYNTAX     Gauge32
    MAX-ACCESS read-only
    STATUS     current
    DESCRIPTION
	    "The number of successful RPC bind requests to
	    the FRS server on the partner associated with
	    this connection."
    ::= { fileReplicaConnEntry 4 }

frcBindingsInError OBJECT-TYPE
    SYNTAX     Gauge32
    MAX-ACCESS read-only
    STATUS     current
    DESCRIPTION
	    "The cumulative number of unsuccessful RPC bind
	    requests to the FRS server on the partner
	    associated with this connection."
    ::= { fileReplicaConnEntry 5 }

frcCommunicationTimeouts OBJECT-TYPE
    SYNTAX     Gauge32
    MAX-ACCESS read-only
    STATUS     current
    DESCRIPTION
	    "The cumulative number of times a communication
	    request has taken too long to the partner
	    associated with this connection."
    ::= { fileReplicaConnEntry 6 }

frcFetchBlocksReceived OBJECT-TYPE
    SYNTAX     Gauge32
    MAX-ACCESS read-only
    STATUS     current
    DESCRIPTION
	    "The number of blocks of staging file data
	    received from the partner associated with this
	    connection.  The underlying transport may break
	    a block into a smaller number of packets on the
	    wire."
    ::= { fileReplicaConnEntry 7 }

frcFetchBlocksReceivedInBytes OBJECT-TYPE
    SYNTAX     Gauge32
    MAX-ACCESS read-only
    STATUS     current
    DESCRIPTION
	    "The number of bytes of staging file data
	    received from the partner associated with this
	    connection."
    ::= { fileReplicaConnEntry 8 }

frcFetchBlocksSent OBJECT-TYPE
    SYNTAX     Gauge32
    MAX-ACCESS read-only
    STATUS     current
    DESCRIPTION
	    "The number of blocks of staging file data sent
	    to the partner associated with this connection.
	     The underlying transport may break a block
	    into a smaller number of packets on the wire."
    ::= { fileReplicaConnEntry 9 }

frcFetchBlocksSentInBytes OBJECT-TYPE
    SYNTAX     Gauge32
    MAX-ACCESS read-only
    STATUS     current
    DESCRIPTION
	    "The number of bytes of staging file data sent
	    to the partner associated with this
	    connection."
    ::= { fileReplicaConnEntry 10 }

frcFetchRequestsReceived OBJECT-TYPE
    SYNTAX     Gauge32
    MAX-ACCESS read-only
    STATUS     current
    DESCRIPTION
	    "The number of staging files received from the
	    partner associated with this connection."
    ::= { fileReplicaConnEntry 11 }

frcFetchRequestsSent OBJECT-TYPE
    SYNTAX     Gauge32
    MAX-ACCESS read-only
    STATUS     current
    DESCRIPTION
	    "The number of staging files requested from the
	    partner associated with this connection."
    ::= { fileReplicaConnEntry 12 }

frcInboundChangeOrdersDampened OBJECT-TYPE
    SYNTAX     Gauge32
    MAX-ACCESS read-only
    STATUS     current
    DESCRIPTION
	    "The number of change orders received from the
	    partner associated with this connection that
	    have been filtered out by the inbound dampening
	    check."
    ::= { fileReplicaConnEntry 13 }

frcJoinNotificationsReceived OBJECT-TYPE
    SYNTAX     Gauge32
    MAX-ACCESS read-only
    STATUS     current
    DESCRIPTION
	    "The number of partner join notifications
	    received from the partner associated with this
	    connection."
    ::= { fileReplicaConnEntry 14 }

frcJoinNotificationsSent OBJECT-TYPE
    SYNTAX     Gauge32
    MAX-ACCESS read-only
    STATUS     current
    DESCRIPTION
	    "The number of partner join requests (if this
	    is an inbound connection) or ready-to-join
	    notifications (if this is an outbound
	    connection) sent to the partner associated with
	    this connection."
    ::= { fileReplicaConnEntry 15 }

frcJoins OBJECT-TYPE
    SYNTAX     Gauge32
    MAX-ACCESS read-only
    STATUS     current
    DESCRIPTION
	    "The number of successful joins with the
	    partner associated with this connection."
    ::= { fileReplicaConnEntry 16 }

frcLocalChangeOrdersSent OBJECT-TYPE
    SYNTAX     Gauge32
    MAX-ACCESS read-only
    STATUS     current
    DESCRIPTION
	    "The number of locally originated replication
	    change orders that have been sent to the
	    partner associated with this connection."
    ::= { fileReplicaConnEntry 17 }

frcLocalChangeOrdersSentAtJoin OBJECT-TYPE
    SYNTAX     Gauge32
    MAX-ACCESS read-only
    STATUS     current
    DESCRIPTION
	    "The number of locally originated replication
	    change orders produced by a partner induced
	    version vector scan that have been sent to the
	    partner associated with this connection."
    ::= { fileReplicaConnEntry 18 }

frcOutboundChangeOrdersDampened OBJECT-TYPE
    SYNTAX     Gauge32
    MAX-ACCESS read-only
    STATUS     current
    DESCRIPTION
	    "The number of change orders sent to the
	    partner associated with this connection that
	    have been filtered out by the outbound
	    dampening check and thus were never sent."
    ::= { fileReplicaConnEntry 19 }

frcPacketsSent OBJECT-TYPE
    SYNTAX     Gauge32
    MAX-ACCESS read-only
    STATUS     current
    DESCRIPTION
	    "The total number of FRS data and control
	    packets sent to the partner associated with
	    this connection."
    ::= { fileReplicaConnEntry 20 }

frcPacketsSentInBytes OBJECT-TYPE
    SYNTAX     Gauge32
    MAX-ACCESS read-only
    STATUS     current
    DESCRIPTION
	    "The total number of FRS data and control bytes
	    sent to the partner associated with this
	    connection."
    ::= { fileReplicaConnEntry 21 }

frcPacketsSentInError OBJECT-TYPE
    SYNTAX     Gauge32
    MAX-ACCESS read-only
    STATUS     current
    DESCRIPTION
	    "The cumulative number of FRS data or control
	    packets not sent because of some error
	    condition associated with this connection."
    ::= { fileReplicaConnEntry 22 }

frcRemoteChangeOrdersReceived OBJECT-TYPE
    SYNTAX     Gauge32
    MAX-ACCESS read-only
    STATUS     current
    DESCRIPTION
	    "The number of change orders received from the
	    partner associated with this connection that
	    have passed the inbound dampening check."
    ::= { fileReplicaConnEntry 23 }

frcRemoteChangeOrdersSent OBJECT-TYPE
    SYNTAX     Gauge32
    MAX-ACCESS read-only
    STATUS     current
    DESCRIPTION
	    "The number of replication change orders
	    originating upstream from this member (i.e.
	    remote) that have been sent to the partner
	    associated with this connection."
    ::= { fileReplicaConnEntry 24 }

frcUnjoins OBJECT-TYPE
    SYNTAX     Gauge32
    MAX-ACCESS read-only
    STATUS     current
    DESCRIPTION
	    "The number of unjoins with the partner
	    associated with this connection."
    ::= { fileReplicaConnEntry 25 }

fileReplicaSetTable OBJECT-TYPE
    SYNTAX     SEQUENCE OF FileReplicaSetEntry
    MAX-ACCESS not-accessible
    STATUS     current
    DESCRIPTION
	    "The FileReplicaSet performance object displays
	    performance statistics of the REPLICASET object
	    that defines a replica set (one or more
	    replicas, shared volumes or directories that
	    store duplicates of the contents of an original
	    share). The object reports statistics for the
	    computer that constitutes the original share.
	    For example, in a bidirectional ring topology
	    of three computers A, B, and C, where computer
	    A and computer C both replicate from computer
	    B, the FileReplicaSet counters would provide
	    data for computer B."
    ::= { advanced 22 }

fileReplicaSetEntry OBJECT-TYPE
    SYNTAX     FileReplicaSetEntry
    MAX-ACCESS not-accessible
    STATUS     current
    DESCRIPTION
	    "Performance information for one particular
	    instance of 'FileReplicaSet' object."
    INDEX      { frsInstance }
    ::= { fileReplicaSetTable 1 }

FileReplicaSetEntry ::= SEQUENCE {
    frsInstance InstanceName,
    frsAuthentications Gauge32,
    frsAuthenticationsInError Gauge32,
    frsBindings Gauge32,
    frsBindingsInError Gauge32,
    frsBytesOfFilesInstalled Gauge32,
    frsBytesOfStagingFetched Gauge32,
    frsBytesOfStagingGenerated Gauge32,
    frsBytesOfStagingRegenerated Gauge32,
    frsChgOrdersAborted Gauge32,
    frsChgOrdersEvaporated Gauge32,
    frsChgOrdersIssued Gauge32,
    frsChgOrdersMorphed Gauge32,
    frsChgOrdersPropagated Gauge32,
    frsChgOrdersReceived Gauge32,
    frsChgOrdersRetired Gauge32,
    frsChgOrdersRetried Gauge32,
    frsChgOrdersRetriedFetch Gauge32,
    frsChgOrdersRetriedGenerate Gauge32,
    frsChgOrdersRetriedInstall Gauge32,
    frsChgOrdersRetriedRename Gauge32,
    frsChgOrdersSent Gauge32,
    frsCommunicationTimeouts Gauge32,
    frsDSBindings Gauge32,
    frsDSBindingsInError Gauge32,
    frsDSObjects Gauge32,
    frsDSObjectsInError Gauge32,
    frsDSPolls Gauge32,
    frsDSPollsWithChgs Gauge32,
    frsDSPollsWithoutChgs Gauge32,
    frsDSSearches Gauge32,
    frsDSSearchesInError Gauge32,
    frsFetchBlocksReceived Gauge32,
    frsFetchBlocksReceivedInBytes Gauge32,
    frsFetchBlocksSent Gauge32,
    frsFetchBlocksSentInBytes Gauge32,
    frsFetchRequestsReceived Gauge32,
    frsFetchRequestsSent Gauge32,
    frsFilesInstalled Gauge32,
    frsFilesInstalledWithError Gauge32,
    frsInboundChgOrdersDampened Gauge32,
    frsJoinNotificationsReceived Gauge32,
    frsJoinNotificationsSent Gauge32,
    frsJoins Gauge32,
    frsKBOfStagingSpaceFree Gauge32,
    frsKBOfStagingSpaceInUse Gauge32,
    frsLocalChgOrdersAborted Gauge32,
    frsLocalChgOrdersIssued Gauge32,
    frsLocalChgOrdersMorphed Gauge32,
    frsLocalChgOrdersPropagated Gauge32,
    frsLocalChgOrdersRetired Gauge32,
    frsLocalChgOrdersRetried Gauge32,
    frsLocalChgOrdersRetriedFetch Gauge32,
    frsLocalChgOrdersRetriedGenerate Gauge32,
    frsLocalChgOrdersRetriedInstall Gauge32,
    frsLocalChgOrdersRetriedRename Gauge32,
    frsLocalChgOrdersSent Gauge32,
    frsLocalChgOrdersSentJoin Gauge32,
    frsOutboundChgOrdersDampened Gauge32,
    frsPacketsReceived Gauge32,
    frsPacketsReceivedInBytes Gauge32,
    frsPacketsReceivedInError Gauge32,
    frsPacketsSent Gauge32,
    frsPacketsSentInBytes Gauge32,
    frsPacketsSentInError Gauge32,
    frsRemoteChgOrdersAborted Gauge32,
    frsRemoteChgOrdersIssued Gauge32,
    frsRemoteChgOrdersMorphed Gauge32,
    frsRemoteChgOrdersPropagated Gauge32,
    frsRemoteChgOrdersReceived Gauge32,
    frsRemoteChgOrdersRetired Gauge32,
    frsRemoteChgOrdersRetried Gauge32,
    frsRemoteChgOrdersRetriedFetch Gauge32,
    frsRemoteChgOrdersRetriedGenerat Gauge32,
    frsRemoteChgOrdersRetriedInstall Gauge32,
    frsRemoteChgOrdersRetriedRename Gauge32,
    frsRemoteChgOrdersSent Gauge32,
    frsReplicaSetsCreated Gauge32,
    frsReplicaSetsDeleted Gauge32,
    frsReplicaSetsRemoved Gauge32,
    frsReplicaSetsStarted Gauge32,
    frsStagingFilesFetched Gauge32,
    frsStagingFilesGenerated Gauge32,
    frsStagingFilesGeneratedWithErr Gauge32,
    frsStagingFilesRegenerated Gauge32,
    frsThreadsExited Gauge32,
    frsThreadsStarted Gauge32,
    frsUnjoins Gauge32,
    frsUsnReads Gauge32,
    frsUsnRecordsAccepted Gauge32,
    frsUsnRecordsExamined Gauge32,
    frsUsnRecordsRejected Gauge32
}

frsInstance OBJECT-TYPE
    SYNTAX     InstanceName
    MAX-ACCESS read-only
    STATUS     current
    DESCRIPTION
	    "Instance name."
    ::= { fileReplicaSetEntry 1 }

frsAuthentications OBJECT-TYPE
    SYNTAX     Gauge32
    MAX-ACCESS read-only
    STATUS     current
    DESCRIPTION
	    "The number of successful authentication checks
	    made on packets received from any partner
	    associated with this replica set member."
    ::= { fileReplicaSetEntry 2 }

frsAuthenticationsInError OBJECT-TYPE
    SYNTAX     Gauge32
    MAX-ACCESS read-only
    STATUS     current
    DESCRIPTION
	    "The cumulative number of authentication check
	    failures detected on packets received from any
	    partner associated with this replica set
	    member."
    ::= { fileReplicaSetEntry 3 }

frsBindings OBJECT-TYPE
    SYNTAX     Gauge32
    MAX-ACCESS read-only
    STATUS     current
    DESCRIPTION
	    "The number of successful RPC bind requests to
	    the FRS server on any partner associated with
	    this replica set member."
    ::= { fileReplicaSetEntry 4 }

frsBindingsInError OBJECT-TYPE
    SYNTAX     Gauge32
    MAX-ACCESS read-only
    STATUS     current
    DESCRIPTION
	    "The cumulative number of unsuccessful RPC bind
	    requests to the FRS server on any partner
	    associated with this replica set member."
    ::= { fileReplicaSetEntry 5 }

frsBytesOfFilesInstalled OBJECT-TYPE
    SYNTAX     Gauge32
    MAX-ACCESS read-only
    STATUS     current
    DESCRIPTION
	    "The total number of bytes of staging file data
	    that have been installed on this replica set
	    member."
    ::= { fileReplicaSetEntry 6 }

frsBytesOfStagingFetched OBJECT-TYPE
    SYNTAX     Gauge32
    MAX-ACCESS read-only
    STATUS     current
    DESCRIPTION
	    "The total number of bytes of staging file data
	    received by this replica set member from its
	    inbound partners."
    ::= { fileReplicaSetEntry 7 }

frsBytesOfStagingGenerated OBJECT-TYPE
    SYNTAX     Gauge32
    MAX-ACCESS read-only
    STATUS     current
    DESCRIPTION
	    "The total number of bytes of staging file data
	    generated by this replica set member not
	    including the number of bytes produced as part
	    of regeneration."
    ::= { fileReplicaSetEntry 8 }

frsBytesOfStagingRegenerated OBJECT-TYPE
    SYNTAX     Gauge32
    MAX-ACCESS read-only
    STATUS     current
    DESCRIPTION
	    "The total number of bytes of staging file data
	    regenerated by this replica set member for a
	    specific outbound partner request."
    ::= { fileReplicaSetEntry 9 }

frsChgOrdersAborted OBJECT-TYPE
    SYNTAX     Gauge32
    MAX-ACCESS read-only
    STATUS     current
    DESCRIPTION
	    "The number of local plus remote file updates
	    that were aborted on this replica set member."
    ::= { fileReplicaSetEntry 10 }

frsChgOrdersEvaporated OBJECT-TYPE
    SYNTAX     Gauge32
    MAX-ACCESS read-only
    STATUS     current
    DESCRIPTION
	    "The number of local file updates that were
	    never processed because the underlying file was
	    deleted first."
    ::= { fileReplicaSetEntry 11 }

frsChgOrdersIssued OBJECT-TYPE
    SYNTAX     Gauge32
    MAX-ACCESS read-only
    STATUS     current
    DESCRIPTION
	    "The number of local plus remote file updates
	    initiated on this replica set member."
    ::= { fileReplicaSetEntry 12 }

frsChgOrdersMorphed OBJECT-TYPE
    SYNTAX     Gauge32
    MAX-ACCESS read-only
    STATUS     current
    DESCRIPTION
	    "The number of local plus remote file updates
	    that encountered a name space collision on this
	    replica set member."
    ::= { fileReplicaSetEntry 13 }

frsChgOrdersPropagated OBJECT-TYPE
    SYNTAX     Gauge32
    MAX-ACCESS read-only
    STATUS     current
    DESCRIPTION
	    "The number of local plus remote file updates
	    that were propagated to the outbound log of
	    this replica set member.   The update remains
	    pending in the outbound log until it has been
	    delivered to all outbound partners."
    ::= { fileReplicaSetEntry 14 }

frsChgOrdersReceived OBJECT-TYPE
    SYNTAX     Gauge32
    MAX-ACCESS read-only
    STATUS     current
    DESCRIPTION
	    "The number of local plus remote file updates
	    that have been received by this replica set
	    member.  Note that depending on the replication
	    topology it is possible for the same remote
	    file update to be sent from multiple inbound
	    partners.  However, only one will send the
	    actual file data."
    ::= { fileReplicaSetEntry 15 }

frsChgOrdersRetired OBJECT-TYPE
    SYNTAX     Gauge32
    MAX-ACCESS read-only
    STATUS     current
    DESCRIPTION
	    "The number of local plus remote file updates
	    retired on this replica set member."
    ::= { fileReplicaSetEntry 16 }

frsChgOrdersRetried OBJECT-TYPE
    SYNTAX     Gauge32
    MAX-ACCESS read-only
    STATUS     current
    DESCRIPTION
	    "The number of local plus remote file updates
	    that were retried for any reason on this
	    replica set member."
    ::= { fileReplicaSetEntry 17 }

frsChgOrdersRetriedFetch OBJECT-TYPE
    SYNTAX     Gauge32
    MAX-ACCESS read-only
    STATUS     current
    DESCRIPTION
	    "The number of local plus remote file updates
	    that were retried due to a stage file fetch
	    problem on this replica set member."
    ::= { fileReplicaSetEntry 18 }

frsChgOrdersRetriedGenerate OBJECT-TYPE
    SYNTAX     Gauge32
    MAX-ACCESS read-only
    STATUS     current
    DESCRIPTION
	    "The number of local plus remote file updates
	    that were retried due to a stage file
	    generation problem on this replica set member."
    ::= { fileReplicaSetEntry 19 }

frsChgOrdersRetriedInstall OBJECT-TYPE
    SYNTAX     Gauge32
    MAX-ACCESS read-only
    STATUS     current
    DESCRIPTION
	    "The number of local plus remote file updates
	    that were retried due to a stage file install
	    problem on this replica set member.   Most
	    likely caused by a sharing conflict trying to
	    access the target file or directory."
    ::= { fileReplicaSetEntry 20 }

frsChgOrdersRetriedRename OBJECT-TYPE
    SYNTAX     Gauge32
    MAX-ACCESS read-only
    STATUS     current
    DESCRIPTION
	    "The number of local plus remote file updates
	    that were retried due to a problem during the
	    final target file rename or delete operation on
	    this replica set member.  Most likely caused by
	    a sharing conflict trying to access the target
	    file or directory."
    ::= { fileReplicaSetEntry 21 }

frsChgOrdersSent OBJECT-TYPE
    SYNTAX     Gauge32
    MAX-ACCESS read-only
    STATUS     current
    DESCRIPTION
	    "The number of local plus remote file updates
	    that have been sent to the outbound partners of
	    this replica set member."
    ::= { fileReplicaSetEntry 22 }

frsCommunicationTimeouts OBJECT-TYPE
    SYNTAX     Gauge32
    MAX-ACCESS read-only
    STATUS     current
    DESCRIPTION
	    "The cumulative number of FRS data or control
	    packets not sent to an outbound partner because
	    the send request timed out."
    ::= { fileReplicaSetEntry 23 }

frsDSBindings OBJECT-TYPE
    SYNTAX     Gauge32
    MAX-ACCESS read-only
    STATUS     current
    DESCRIPTION
	    "The number of times FRS has attempted to
	    acquire a binding handle to the active
	    directory."
    ::= { fileReplicaSetEntry 24 }

frsDSBindingsInError OBJECT-TYPE
    SYNTAX     Gauge32
    MAX-ACCESS read-only
    STATUS     current
    DESCRIPTION
	    "The cumulative number of attempts to acquire a
	    binding handle to the active directory that
	    failed with some error status."
    ::= { fileReplicaSetEntry 25 }

frsDSObjects OBJECT-TYPE
    SYNTAX     Gauge32
    MAX-ACCESS read-only
    STATUS     current
    DESCRIPTION
	    "The number of FRS configuration Objects
	    retreived from the directory service."
    ::= { fileReplicaSetEntry 26 }

frsDSObjectsInError OBJECT-TYPE
    SYNTAX     Gauge32
    MAX-ACCESS read-only
    STATUS     current
    DESCRIPTION
	    "The cumulative count of FRS configuration
	    objects retreived from the directory service
	    that were missing either the distinguished
	    name, object GUID or the relative distinguished
	    name attributes."
    ::= { fileReplicaSetEntry 27 }

frsDSPolls OBJECT-TYPE
    SYNTAX     Gauge32
    MAX-ACCESS read-only
    STATUS     current
    DESCRIPTION
	    "The number of times FRS has polled the active
	    directory for FRS configuration information on
	    this computer."
    ::= { fileReplicaSetEntry 28 }

frsDSPollsWithChgs OBJECT-TYPE
    SYNTAX     Gauge32
    MAX-ACCESS read-only
    STATUS     current
    DESCRIPTION
	    "The number of times FRS has polled the active
	    directory for FRS configuration information and
	    configuration changes were found."
    ::= { fileReplicaSetEntry 29 }

frsDSPollsWithoutChgs OBJECT-TYPE
    SYNTAX     Gauge32
    MAX-ACCESS read-only
    STATUS     current
    DESCRIPTION
	    "The number of times FRS has polled the active
	    directory for FRS configuration information and
	    no configuration changes were found."
    ::= { fileReplicaSetEntry 30 }

frsDSSearches OBJECT-TYPE
    SYNTAX     Gauge32
    MAX-ACCESS read-only
    STATUS     current
    DESCRIPTION
	    "The number of times FRS has made a search
	    request to the active directory."
    ::= { fileReplicaSetEntry 31 }

frsDSSearchesInError OBJECT-TYPE
    SYNTAX     Gauge32
    MAX-ACCESS read-only
    STATUS     current
    DESCRIPTION
	    "The cumulative number of times FRS has made a
	    search request to the active directory and the
	    request returned with an error condition."
    ::= { fileReplicaSetEntry 32 }

frsFetchBlocksReceived OBJECT-TYPE
    SYNTAX     Gauge32
    MAX-ACCESS read-only
    STATUS     current
    DESCRIPTION
	    "The number of blocks of staging file data
	    received from all inbound partners associated
	    with this replica set member.  The underlying
	    transport may break a block into a smaller
	    number of packets on the wire."
    ::= { fileReplicaSetEntry 33 }

frsFetchBlocksReceivedInBytes OBJECT-TYPE
    SYNTAX     Gauge32
    MAX-ACCESS read-only
    STATUS     current
    DESCRIPTION
	    "The total number of bytes of staging file data
	    received by this replica set member from all
	    inbound partners."
    ::= { fileReplicaSetEntry 34 }

frsFetchBlocksSent OBJECT-TYPE
    SYNTAX     Gauge32
    MAX-ACCESS read-only
    STATUS     current
    DESCRIPTION
	    "The number of blocks of staging file data sent
	    to any outbound partner associated with this
	    replica set member.  The underlying transport
	    may break a block into a smaller number of
	    packets on the wire."
    ::= { fileReplicaSetEntry 35 }

frsFetchBlocksSentInBytes OBJECT-TYPE
    SYNTAX     Gauge32
    MAX-ACCESS read-only
    STATUS     current
    DESCRIPTION
	    "The total number of bytes of staging file data
	    sent to the outbound partners of this replica
	    set member."
    ::= { fileReplicaSetEntry 36 }

frsFetchRequestsReceived OBJECT-TYPE
    SYNTAX     Gauge32
    MAX-ACCESS read-only
    STATUS     current
    DESCRIPTION
	    "The number of staging files received from all
	    inbound partners associated with this replica
	    set member."
    ::= { fileReplicaSetEntry 37 }

frsFetchRequestsSent OBJECT-TYPE
    SYNTAX     Gauge32
    MAX-ACCESS read-only
    STATUS     current
    DESCRIPTION
	    "The number of staging files requested from any
	    inbound partner associated with this replica
	    set member."
    ::= { fileReplicaSetEntry 38 }

frsFilesInstalled OBJECT-TYPE
    SYNTAX     Gauge32
    MAX-ACCESS read-only
    STATUS     current
    DESCRIPTION
	    "The number of file updates and deletes
	    performed on this replica set member."
    ::= { fileReplicaSetEntry 39 }

frsFilesInstalledWithError OBJECT-TYPE
    SYNTAX     Gauge32
    MAX-ACCESS read-only
    STATUS     current
    DESCRIPTION
	    "The cumulative number of file updates that
	    were aborted because of some non-recoverable
	    error."
    ::= { fileReplicaSetEntry 40 }

frsInboundChgOrdersDampened OBJECT-TYPE
    SYNTAX     Gauge32
    MAX-ACCESS read-only
    STATUS     current
    DESCRIPTION
	    "The number of remotely originated file updates
	    that were dampened because the update was
	    already delivered by another member."
    ::= { fileReplicaSetEntry 41 }

frsJoinNotificationsReceived OBJECT-TYPE
    SYNTAX     Gauge32
    MAX-ACCESS read-only
    STATUS     current
    DESCRIPTION
	    "The number of partner join notifications
	    received from all inbound partners associated
	    with this replica set member."
    ::= { fileReplicaSetEntry 42 }

frsJoinNotificationsSent OBJECT-TYPE
    SYNTAX     Gauge32
    MAX-ACCESS read-only
    STATUS     current
    DESCRIPTION
	    "The number of inbound partner join requests or
	    outbound partner ready-to-join notifications
	    sent to all partners associated with this
	    replica set member."
    ::= { fileReplicaSetEntry 43 }

frsJoins OBJECT-TYPE
    SYNTAX     Gauge32
    MAX-ACCESS read-only
    STATUS     current
    DESCRIPTION
	    "The number of successful joins with any
	    partner associated with this replica set
	    member."
    ::= { fileReplicaSetEntry 44 }

frsKBOfStagingSpaceFree OBJECT-TYPE
    SYNTAX     Gauge32
    MAX-ACCESS read-only
    STATUS     current
    DESCRIPTION
	    "The amount of staging space (in Kilobyte
	    units) currently available within the staging
	    space limit.  Note that there may not actually
	    be this amount of free space left on the
	    staging volume."
    ::= { fileReplicaSetEntry 45 }

frsKBOfStagingSpaceInUse OBJECT-TYPE
    SYNTAX     Gauge32
    MAX-ACCESS read-only
    STATUS     current
    DESCRIPTION
	    "The amount of staging space (in Kilobyte
	    units) currently in use."
    ::= { fileReplicaSetEntry 46 }

frsLocalChgOrdersAborted OBJECT-TYPE
    SYNTAX     Gauge32
    MAX-ACCESS read-only
    STATUS     current
    DESCRIPTION
	    "The number of locally originated file updates
	    that were aborted.	Most likely because a file
	    was deleted before a change to it could be
	    propagated so no stage file could be
	    generated."
    ::= { fileReplicaSetEntry 47 }

frsLocalChgOrdersIssued OBJECT-TYPE
    SYNTAX     Gauge32
    MAX-ACCESS read-only
    STATUS     current
    DESCRIPTION
	    "The number of locally originated file updates
	    initiated on this replica set member."
    ::= { fileReplicaSetEntry 48 }

frsLocalChgOrdersMorphed OBJECT-TYPE
    SYNTAX     Gauge32
    MAX-ACCESS read-only
    STATUS     current
    DESCRIPTION
	    "The number of locally originated file updates
	    that encountered a name space collision on this
	    replica set member.   Most likely caused by the
	    reanimation of a parent dir."
    ::= { fileReplicaSetEntry 49 }

frsLocalChgOrdersPropagated OBJECT-TYPE
    SYNTAX     Gauge32
    MAX-ACCESS read-only
    STATUS     current
    DESCRIPTION
	    "The number of locally originated file updates
	    that were propagated to the outbound log of
	    this replica set member.   The update remains
	    pending in the outbound log until it has been
	    delivered to all outbound partners."
    ::= { fileReplicaSetEntry 50 }

frsLocalChgOrdersRetired OBJECT-TYPE
    SYNTAX     Gauge32
    MAX-ACCESS read-only
    STATUS     current
    DESCRIPTION
	    "The number of locally originated file updates
	    retired on this replica set member."
    ::= { fileReplicaSetEntry 51 }

frsLocalChgOrdersRetried OBJECT-TYPE
    SYNTAX     Gauge32
    MAX-ACCESS read-only
    STATUS     current
    DESCRIPTION
	    "The number of locally originated file updates
	    that were retried for any reason on this
	    replica set member."
    ::= { fileReplicaSetEntry 52 }

frsLocalChgOrdersRetriedFetch OBJECT-TYPE
    SYNTAX     Gauge32
    MAX-ACCESS read-only
    STATUS     current
    DESCRIPTION
	    "The number of locally originated file updates
	    that were retried due to a stage file fetch
	    problem on this replica set member."
    ::= { fileReplicaSetEntry 53 }

frsLocalChgOrdersRetriedGenerate OBJECT-TYPE
    SYNTAX     Gauge32
    MAX-ACCESS read-only
    STATUS     current
    DESCRIPTION
	    "The number of locally originated file updates
	    that were retried due to a stage file
	    generation problem on this replica set member. 
	    Most likely caused by a sharing conflict trying
	    to access the target file."
    ::= { fileReplicaSetEntry 54 }

frsLocalChgOrdersRetriedInstall OBJECT-TYPE
    SYNTAX     Gauge32
    MAX-ACCESS read-only
    STATUS     current
    DESCRIPTION
	    "The number of locally originated file updates
	    that were retried due to a stage file install
	    problem on this replica set member.   Most
	    likely caused by a sharing conflict trying to
	    access the target file or directory."
    ::= { fileReplicaSetEntry 55 }

frsLocalChgOrdersRetriedRename OBJECT-TYPE
    SYNTAX     Gauge32
    MAX-ACCESS read-only
    STATUS     current
    DESCRIPTION
	    "The number of locally originated file updates
	    that were retried due to a problem during the
	    final target file rename or delete operation on
	    this replica set member.  Most likely caused by
	    a sharing conflict trying to access the target
	    file or directory."
    ::= { fileReplicaSetEntry 56 }

frsLocalChgOrdersSent OBJECT-TYPE
    SYNTAX     Gauge32
    MAX-ACCESS read-only
    STATUS     current
    DESCRIPTION
	    "The number of locally originated file updates
	    that have been sent to the outbound partners of
	    this replica set member."
    ::= { fileReplicaSetEntry 57 }

frsLocalChgOrdersSentJoin OBJECT-TYPE
    SYNTAX     Gauge32
    MAX-ACCESS read-only
    STATUS     current
    DESCRIPTION
	    "The number of locally originated file updates
	    which were created by a partner induced version
	    vector scan that have been sent to the outbound
	    partners of this replica set member."
    ::= { fileReplicaSetEntry 58 }

frsOutboundChgOrdersDampened OBJECT-TYPE
    SYNTAX     Gauge32
    MAX-ACCESS read-only
    STATUS     current
    DESCRIPTION
	    "The number of pending outbound file updates
	    that were dampened because the outbound partner
	    has already received it from another source."
    ::= { fileReplicaSetEntry 59 }

frsPacketsReceived OBJECT-TYPE
    SYNTAX     Gauge32
    MAX-ACCESS read-only
    STATUS     current
    DESCRIPTION
	    "The number of FRS data or control packets (RPC
	    calls) received by FRS."
    ::= { fileReplicaSetEntry 60 }

frsPacketsReceivedInBytes OBJECT-TYPE
    SYNTAX     Gauge32
    MAX-ACCESS read-only
    STATUS     current
    DESCRIPTION
	    "The total number of FRS data and control bytes
	    received by all replica sets on this computer."
    ::= { fileReplicaSetEntry 61 }

frsPacketsReceivedInError OBJECT-TYPE
    SYNTAX     Gauge32
    MAX-ACCESS read-only
    STATUS     current
    DESCRIPTION
	    "The cumulative number of FRS data or control
	    packets received that were out of rev or
	    otherwise malformed."
    ::= { fileReplicaSetEntry 62 }

frsPacketsSent OBJECT-TYPE
    SYNTAX     Gauge32
    MAX-ACCESS read-only
    STATUS     current
    DESCRIPTION
	    "The number of FRS data and control packets
	    sent to all outbound partners associated with
	    this replica set member."
    ::= { fileReplicaSetEntry 63 }

frsPacketsSentInBytes OBJECT-TYPE
    SYNTAX     Gauge32
    MAX-ACCESS read-only
    STATUS     current
    DESCRIPTION
	    "The total number of FRS data and control bytes
	    sent by this replica set member to other
	    members."
    ::= { fileReplicaSetEntry 64 }

frsPacketsSentInError OBJECT-TYPE
    SYNTAX     Gauge32
    MAX-ACCESS read-only
    STATUS     current
    DESCRIPTION
	    "The cumulative number of FRS data or control
	    packets not sent to an outbound partner because
	    of some error condition."
    ::= { fileReplicaSetEntry 65 }

frsRemoteChgOrdersAborted OBJECT-TYPE
    SYNTAX     Gauge32
    MAX-ACCESS read-only
    STATUS     current
    DESCRIPTION
	    "The number of remotely originated file updates
	    that were aborted.	Most likely because of an
	    attempt to fetch a staging file from an inbound
	    partner and the partner no longer has the file
	    because it has been deleted."
    ::= { fileReplicaSetEntry 66 }

frsRemoteChgOrdersIssued OBJECT-TYPE
    SYNTAX     Gauge32
    MAX-ACCESS read-only
    STATUS     current
    DESCRIPTION
	    "The number of remotely originated file updates
	    initiated on this replica set member."
    ::= { fileReplicaSetEntry 67 }

frsRemoteChgOrdersMorphed OBJECT-TYPE
    SYNTAX     Gauge32
    MAX-ACCESS read-only
    STATUS     current
    DESCRIPTION
	    "The number of remotely originated file updates
	    that encountered a name space collision on this
	    replica set member.   Most likely caused by
	    simultaneous create of a file or directory with
	    the same name on more than one replica set
	    member."
    ::= { fileReplicaSetEntry 68 }

frsRemoteChgOrdersPropagated OBJECT-TYPE
    SYNTAX     Gauge32
    MAX-ACCESS read-only
    STATUS     current
    DESCRIPTION
	    "The number of remotely originated file updates
	    that were propagated to the outbound log of
	    this replica set member.   The update remains
	    pending in the outbound log until it has been
	    delivered to all outbound partners."
    ::= { fileReplicaSetEntry 69 }

frsRemoteChgOrdersReceived OBJECT-TYPE
    SYNTAX     Gauge32
    MAX-ACCESS read-only
    STATUS     current
    DESCRIPTION
	    "The number of remotely originated file updates
	    that have been received by this replica set
	    member.  Note that depending on the replication
	    topology it is possible for the same file
	    update to be sent from multiple inbound
	    partners.  However, only one will send the
	    actual file data."
    ::= { fileReplicaSetEntry 70 }

frsRemoteChgOrdersRetired OBJECT-TYPE
    SYNTAX     Gauge32
    MAX-ACCESS read-only
    STATUS     current
    DESCRIPTION
	    "The number of remotely originated file updates
	    retired on this replica set member."
    ::= { fileReplicaSetEntry 71 }

frsRemoteChgOrdersRetried OBJECT-TYPE
    SYNTAX     Gauge32
    MAX-ACCESS read-only
    STATUS     current
    DESCRIPTION
	    "The number of remotely originated file updates
	    that were retried for any reason on this
	    replica set member."
    ::= { fileReplicaSetEntry 72 }

frsRemoteChgOrdersRetriedFetch OBJECT-TYPE
    SYNTAX     Gauge32
    MAX-ACCESS read-only
    STATUS     current
    DESCRIPTION
	    "The number of remotely originated file updates
	    that were retried due to a stage file fetch
	    problem on this replica set member."
    ::= { fileReplicaSetEntry 73 }

frsRemoteChgOrdersRetriedGenerat OBJECT-TYPE
    SYNTAX     Gauge32
    MAX-ACCESS read-only
    STATUS     current
    DESCRIPTION
	    "The number of remotely originated file updates
	    that were retried due to a stage file
	    generation problem on this replica set member."
    ::= { fileReplicaSetEntry 74 }

frsRemoteChgOrdersRetriedInstall OBJECT-TYPE
    SYNTAX     Gauge32
    MAX-ACCESS read-only
    STATUS     current
    DESCRIPTION
	    "The number of remotely originated file updates
	    that were retried due to a stage file install
	    problem on this replica set member.   Most
	    likely caused by a sharing conflict trying to
	    access the target file or directory."
    ::= { fileReplicaSetEntry 75 }

frsRemoteChgOrdersRetriedRename OBJECT-TYPE
    SYNTAX     Gauge32
    MAX-ACCESS read-only
    STATUS     current
    DESCRIPTION
	    "The number of remotely originated file updates
	    that were retried due to a problem during the
	    final target file rename or delete operation on
	    this replica set member.  Most likely caused by
	    a sharing conflict trying to access the target
	    file or directory."
    ::= { fileReplicaSetEntry 76 }

frsRemoteChgOrdersSent OBJECT-TYPE
    SYNTAX     Gauge32
    MAX-ACCESS read-only
    STATUS     current
    DESCRIPTION
	    "The number of remotely originated file updates
	    that have been sent to the outbound partners of
	    this replica set member."
    ::= { fileReplicaSetEntry 77 }

frsReplicaSetsCreated OBJECT-TYPE
    SYNTAX     Gauge32
    MAX-ACCESS read-only
    STATUS     current
    DESCRIPTION
	    "The cumulative number of replica sets to which
	    this computer has been added as a member."
    ::= { fileReplicaSetEntry 78 }

frsReplicaSetsDeleted OBJECT-TYPE
    SYNTAX     Gauge32
    MAX-ACCESS read-only
    STATUS     current
    DESCRIPTION
	    "The cumulative number of replica sets from
	    which this computer's membership has been
	    provisionally deleted, but could still be
	    reanimated."
    ::= { fileReplicaSetEntry 79 }

frsReplicaSetsRemoved OBJECT-TYPE
    SYNTAX     Gauge32
    MAX-ACCESS read-only
    STATUS     current
    DESCRIPTION
	    "The cumulative number of replica sets from
	    which this computer's membership has been
	    permanently deleted."
    ::= { fileReplicaSetEntry 80 }

frsReplicaSetsStarted OBJECT-TYPE
    SYNTAX     Gauge32
    MAX-ACCESS read-only
    STATUS     current
    DESCRIPTION
	    "The number of replica sets for which
	    processing has been started."
    ::= { fileReplicaSetEntry 81 }

frsStagingFilesFetched OBJECT-TYPE
    SYNTAX     Gauge32
    MAX-ACCESS read-only
    STATUS     current
    DESCRIPTION
	    "The number of staging files requested by this
	    replica set member."
    ::= { fileReplicaSetEntry 82 }

frsStagingFilesGenerated OBJECT-TYPE
    SYNTAX     Gauge32
    MAX-ACCESS read-only
    STATUS     current
    DESCRIPTION
	    "The number of staging files generated by this
	    replica set member."
    ::= { fileReplicaSetEntry 83 }

frsStagingFilesGeneratedWithErr OBJECT-TYPE
    SYNTAX     Gauge32
    MAX-ACCESS read-only
    STATUS     current
    DESCRIPTION
	    "The cumulative number of staging files
	    generated by this replica set member where an
	    error was detected during generation."
    ::= { fileReplicaSetEntry 84 }

frsStagingFilesRegenerated OBJECT-TYPE
    SYNTAX     Gauge32
    MAX-ACCESS read-only
    STATUS     current
    DESCRIPTION
	    "The number of staging files regenerated by
	    this replica set member for a specific outbound
	    partner request."
    ::= { fileReplicaSetEntry 85 }

frsThreadsExited OBJECT-TYPE
    SYNTAX     Gauge32
    MAX-ACCESS read-only
    STATUS     current
    DESCRIPTION
	    "The number of execution threads that have
	    terminated."
    ::= { fileReplicaSetEntry 86 }

frsThreadsStarted OBJECT-TYPE
    SYNTAX     Gauge32
    MAX-ACCESS read-only
    STATUS     current
    DESCRIPTION
	    "The number of new execution threads started."
    ::= { fileReplicaSetEntry 87 }

frsUnjoins OBJECT-TYPE
    SYNTAX     Gauge32
    MAX-ACCESS read-only
    STATUS     current
    DESCRIPTION
	    "The number of unjoins with any partner
	    associated with this replica set member."
    ::= { fileReplicaSetEntry 88 }

frsUsnReads OBJECT-TYPE
    SYNTAX     Gauge32
    MAX-ACCESS read-only
    STATUS     current
    DESCRIPTION
	    "The number of times FRS has initiated a read
	    on the NTFRS change log.  Each volume has its
	    own change log."
    ::= { fileReplicaSetEntry 89 }

frsUsnRecordsAccepted OBJECT-TYPE
    SYNTAX     Gauge32
    MAX-ACCESS read-only
    STATUS     current
    DESCRIPTION
	    "The number of NTFS change log records accepted
	    by FRS for further processing."
    ::= { fileReplicaSetEntry 90 }

frsUsnRecordsExamined OBJECT-TYPE
    SYNTAX     Gauge32
    MAX-ACCESS read-only
    STATUS     current
    DESCRIPTION
	    "The number of NTFS change log records examined
	    by FRS."
    ::= { fileReplicaSetEntry 91 }

frsUsnRecordsRejected OBJECT-TYPE
    SYNTAX     Gauge32
    MAX-ACCESS read-only
    STATUS     current
    DESCRIPTION
	    "The number of NTFS change log records skipped
	    by FRS.  Most likely because the change log
	    record was for a file not part of any active
	    replica set."
    ::= { fileReplicaSetEntry 92 }

ftpServiceTable OBJECT-TYPE
    SYNTAX     SEQUENCE OF FTPServiceEntry
    MAX-ACCESS not-accessible
    STATUS     current
    DESCRIPTION
	    "The FTP Service performance object consists of
	    counters that show data about the Internet
	    Information Services FTP service."
    ::= { advanced 23 }

ftpServiceEntry OBJECT-TYPE
    SYNTAX     FTPServiceEntry
    MAX-ACCESS not-accessible
    STATUS     current
    DESCRIPTION
	    "Performance information for one particular
	    instance of 'FTP Service' object."
    INDEX      { ftpSvcInstance }
    ::= { ftpServiceTable 1 }

FTPServiceEntry ::= SEQUENCE {
    ftpSvcInstance InstanceName,
    ftpSvcBytesReceivedPerSec Gauge32,
    ftpSvcBytesSentPerSec Gauge32,
    ftpSvcBytesTotalPerSec Gauge32,
    ftpSvcCurrentAnonymousUsers Gauge32,
    ftpSvcCurrentConnections Gauge32,
    ftpSvcCurrentNonAnonymousUsers Gauge32,
    ftpSvcFTPServiceUptime Gauge32,
    ftpSvcMaximumAnonymousUsers Gauge32,
    ftpSvcMaximumConnections Gauge32,
    ftpSvcMaximumNonAnonymousUsers Gauge32,
    ftpSvcTotalAnonymousUsers Gauge32,
    ftpSvcTotalConnAttemptsAllInst Gauge32,
    ftpSvcTotalFilesReceived Gauge32,
    ftpSvcTotalFilesSent Gauge32,
    ftpSvcTotalFilesTransferred Gauge32,
    ftpSvcTotalLogonAttempts Gauge32,
    ftpSvcTotalNonAnonymousUsers Gauge32
}

ftpSvcInstance OBJECT-TYPE
    SYNTAX     InstanceName
    MAX-ACCESS read-only
    STATUS     current
    DESCRIPTION
	    "Instance name."
    ::= { ftpServiceEntry 1 }

ftpSvcBytesReceivedPerSec OBJECT-TYPE
    SYNTAX     Gauge32
    MAX-ACCESS read-only
    STATUS     current
    DESCRIPTION
	    "Bytes Received/sec is the rate that data bytes
	    are received by the FTP service."
    ::= { ftpServiceEntry 2 }

ftpSvcBytesSentPerSec OBJECT-TYPE
    SYNTAX     Gauge32
    MAX-ACCESS read-only
    STATUS     current
    DESCRIPTION
	    "Bytes Sent/sec is the rate that data bytes are
	    sent by the FTP service."
    ::= { ftpServiceEntry 3 }

ftpSvcBytesTotalPerSec OBJECT-TYPE
    SYNTAX     Gauge32
    MAX-ACCESS read-only
    STATUS     current
    DESCRIPTION
	    "Bytes Total/sec is the sum of Bytes Sent/sec
	    and Bytes Received/sec.  This is the total rate
	    of bytes transferred by the FTP service."
    ::= { ftpServiceEntry 4 }

ftpSvcCurrentAnonymousUsers OBJECT-TYPE
    SYNTAX     Gauge32
    MAX-ACCESS read-only
    STATUS     current
    DESCRIPTION
	    "Current Anonymous Users is the number of users
	    who currently have an anonymous connection
	    using the FTP service."
    ::= { ftpServiceEntry 5 }

ftpSvcCurrentConnections OBJECT-TYPE
    SYNTAX     Gauge32
    MAX-ACCESS read-only
    STATUS     current
    DESCRIPTION
	    "Current Connections is the current number of
	    connections established with the FTP service."
    ::= { ftpServiceEntry 6 }

ftpSvcCurrentNonAnonymousUsers OBJECT-TYPE
    SYNTAX     Gauge32
    MAX-ACCESS read-only
    STATUS     current
    DESCRIPTION
	    "Current NonAnonymous Users is the number of
	    users who currently have a non-anonymous
	    connection using the FTP service."
    ::= { ftpServiceEntry 7 }

ftpSvcFTPServiceUptime OBJECT-TYPE
    SYNTAX     Gauge32
    MAX-ACCESS read-only
    STATUS     current
    DESCRIPTION
	    "FTP Serive and FTP site uptime in seconds."
    ::= { ftpServiceEntry 8 }

ftpSvcMaximumAnonymousUsers OBJECT-TYPE
    SYNTAX     Gauge32
    MAX-ACCESS read-only
    STATUS     current
    DESCRIPTION
	    "Maximum Anonymous Users is the maximum number
	    of users who established concurrent anonymous
	    connections using the FTP service (since
	    service startup)."
    ::= { ftpServiceEntry 9 }

ftpSvcMaximumConnections OBJECT-TYPE
    SYNTAX     Gauge32
    MAX-ACCESS read-only
    STATUS     current
    DESCRIPTION
	    "Maximum Connections is the maximum number of
	    simultaneous connections established with the
	    FTP service."
    ::= { ftpServiceEntry 10 }

ftpSvcMaximumNonAnonymousUsers OBJECT-TYPE
    SYNTAX     Gauge32
    MAX-ACCESS read-only
    STATUS     current
    DESCRIPTION
	    "Maximum NonAnonymous Users is the maximum
	    number of users who established concurrent
	    non-anonymous connections using the FTP service
	    (since service startup)."
    ::= { ftpServiceEntry 11 }

ftpSvcTotalAnonymousUsers OBJECT-TYPE
    SYNTAX     Gauge32
    MAX-ACCESS read-only
    STATUS     current
    DESCRIPTION
	    "Total Anonymous Users is the total number of
	    users who established an anonymous connection
	    with the FTP service (since service startup)."
    ::= { ftpServiceEntry 12 }

ftpSvcTotalConnAttemptsAllInst OBJECT-TYPE
    SYNTAX     Gauge32
    MAX-ACCESS read-only
    STATUS     current
    DESCRIPTION
	    "Total Connection Attempts is the number of
	    connections that have been attempted using the
	    FTP service (since service startup).  This
	    counter is for all instances listed."
    ::= { ftpServiceEntry 13 }

ftpSvcTotalFilesReceived OBJECT-TYPE
    SYNTAX     Gauge32
    MAX-ACCESS read-only
    STATUS     current
    DESCRIPTION
	    "Total Files Received is the total number of
	    files received by the FTP service since service
	    startup."
    ::= { ftpServiceEntry 14 }

ftpSvcTotalFilesSent OBJECT-TYPE
    SYNTAX     Gauge32
    MAX-ACCESS read-only
    STATUS     current
    DESCRIPTION
	    "Total Files Sent is the total number of files
	    sent by the FTP service since service startup."
    ::= { ftpServiceEntry 15 }

ftpSvcTotalFilesTransferred OBJECT-TYPE
    SYNTAX     Gauge32
    MAX-ACCESS read-only
    STATUS     current
    DESCRIPTION
	    "Total Files Transferred is the sum of Files
	    Sent and Files Received.  This is the total
	    number of files transferred by the FTP service
	    since service startup."
    ::= { ftpServiceEntry 16 }

ftpSvcTotalLogonAttempts OBJECT-TYPE
    SYNTAX     Gauge32
    MAX-ACCESS read-only
    STATUS     current
    DESCRIPTION
	    "Total Logon Attempts is the number of logons
	    that have been attempted using the FTP service
	    (since service startup)."
    ::= { ftpServiceEntry 17 }

ftpSvcTotalNonAnonymousUsers OBJECT-TYPE
    SYNTAX     Gauge32
    MAX-ACCESS read-only
    STATUS     current
    DESCRIPTION
	    "Total NonAnonymous Users is the total number
	    of users who established a non-anonymous
	    connection with the FTP service (since service
	    startup)."
    ::= { ftpServiceEntry 18 }

gatewayServiceForNetWare OBJECT-IDENTITY
    STATUS     current
    DESCRIPTION
	    "The Gateway for NetWare Service performance
	    object consists of counters that measure packet
	    transmission rates and activity of the Gateway
	    for NetWare service."
    ::= { advanced 24 }

nwBytesReceivedPerSec OBJECT-TYPE
    SYNTAX     Gauge32
    MAX-ACCESS read-only
    STATUS     current
    DESCRIPTION
	    "Bytes Received/sec is the rate of bytes coming
	    in to the Redirector from the network.  It
	    includes all application data as well as
	    network protocol information (such as packet
	    headers)."
    ::= { gatewayServiceForNetWare 1 }

nwBytesTotalPerSec OBJECT-TYPE
    SYNTAX     Gauge32
    MAX-ACCESS read-only
    STATUS     current
    DESCRIPTION
	    "Bytes Total/sec is the rate the Redirector is
	    processing data bytes.  This includes all
	    application and file data in addition to
	    protocol information such as packet headers."
    ::= { gatewayServiceForNetWare 2 }

nwBytesTransmittedPerSec OBJECT-TYPE
    SYNTAX     Gauge32
    MAX-ACCESS read-only
    STATUS     current
    DESCRIPTION
	    "Bytes Transmitted/sec is the rate at which
	    bytes are leaving the Redirector to the
	    network.  It includes all application data as
	    well as network protocol information (such as
	    packet headers and the like)."
    ::= { gatewayServiceForNetWare 3 }

nwConnectNetWare2X OBJECT-TYPE
    SYNTAX     Gauge32
    MAX-ACCESS read-only
    STATUS     current
    DESCRIPTION
	    "Connect NetWare 2.x counts connections to
	    NetWare 2.x servers."
    ::= { gatewayServiceForNetWare 4 }

nwConnectNetWare3X OBJECT-TYPE
    SYNTAX     Gauge32
    MAX-ACCESS read-only
    STATUS     current
    DESCRIPTION
	    "Connect NetWare 3.x counts connections to
	    NetWare 3.x servers."
    ::= { gatewayServiceForNetWare 5 }

nwConnectNetWare4X OBJECT-TYPE
    SYNTAX     Gauge32
    MAX-ACCESS read-only
    STATUS     current
    DESCRIPTION
	    "Connect NetWare 4.x counts connections to
	    NetWare 4.x servers."
    ::= { gatewayServiceForNetWare 6 }

nwFileDataOperationsPerSec OBJECT-TYPE
    SYNTAX     Gauge32
    MAX-ACCESS read-only
    STATUS     current
    DESCRIPTION
	    "File Data Operations/sec is the rate the
	    Redirector is processing data operations.  One
	    operation includes (hopefully) many bytes.	We
	    say hopefully here because each operation has
	    overhead.  You can determine the efficiency of
	    this path by dividing the Bytes/sec by this
	    counter to determine the average number of
	    bytes transferred/operation."
    ::= { gatewayServiceForNetWare 7 }

nwFileReadOperationsPerSec OBJECT-TYPE
    SYNTAX     Gauge32
    MAX-ACCESS read-only
    STATUS     current
    DESCRIPTION
	    "File Read Operations/sec is the rate at which
	    applications are asking the Redirector for
	    data.  Each call to a file system or similar
	    Application Program Interface (API) call counts
	    as one operation."
    ::= { gatewayServiceForNetWare 8 }

nwFileWriteOperationsPerSec OBJECT-TYPE
    SYNTAX     Gauge32
    MAX-ACCESS read-only
    STATUS     current
    DESCRIPTION
	    "File Write Operations/sec is the rate at which
	    applications are sending data to the
	    Redirector.  Each call to a file system or
	    similar Application Program Interface (API)
	    call counts as one operation."
    ::= { gatewayServiceForNetWare 9 }

nwPacketBurstIOPerSec OBJECT-TYPE
    SYNTAX     Gauge32
    MAX-ACCESS read-only
    STATUS     current
    DESCRIPTION
	    "Packet Burst IO/sec is the sum of Packet Burst
	    Read NCPs/sec and Packet Burst Write NCPs/sec."
    ::= { gatewayServiceForNetWare 10 }

nwPacketBurstReadNCPCountPerSec OBJECT-TYPE
    SYNTAX     Gauge32
    MAX-ACCESS read-only
    STATUS     current
    DESCRIPTION
	    "Packet Burst Read NCP Count/sec is the rate of
	    NetWare Core Protocol requests for Packet Burst
	    Read.  Packet Burst is a windowing protocol
	    that improves performance."
    ::= { gatewayServiceForNetWare 11 }

nwPacketBurstReadTimeoutsPerSec OBJECT-TYPE
    SYNTAX     Gauge32
    MAX-ACCESS read-only
    STATUS     current
    DESCRIPTION
	    "Packet Burst Read Timeouts/sec is the rate the
	    NetWare Service needs to retransmit a Burst
	    Read Request because the NetWare server took
	    too long to respond."
    ::= { gatewayServiceForNetWare 12 }

nwPacketBurstWriteNCPCountPerSec OBJECT-TYPE
    SYNTAX     Gauge32
    MAX-ACCESS read-only
    STATUS     current
    DESCRIPTION
	    "Packet Burst Write NCP Count/sec is the rate
	    of NetWare Core Protocol requests for Packet
	    Burst Write.  Packet Burst is a windowing
	    protocol that improves performance."
    ::= { gatewayServiceForNetWare 13 }

nwPacketBurstWriteTimeoutsPerSec OBJECT-TYPE
    SYNTAX     Gauge32
    MAX-ACCESS read-only
    STATUS     current
    DESCRIPTION
	    "Packet Burst Write Timeouts/sec is the rate
	    the NetWare Service needs to retransmit a Burst
	    Write Request because the NetWare server took
	    too long to respond."
    ::= { gatewayServiceForNetWare 14 }

nwPacketsReceivedPerSec OBJECT-TYPE
    SYNTAX     Gauge32
    MAX-ACCESS read-only
    STATUS     current
    DESCRIPTION
	    "Packets Received/sec is the rate at which the
	    Redirector is receiving packets (also called
	    SMBs or Server Message Blocks).  Network
	    transmissions are divided into packets.  The
	    average number of bytes received in a packet
	    can be obtained by dividing Bytes Received/sec
	    by this counter.  Some packets received might
	    not contain incoming data, for example an
	    acknowledgment to a write made by the
	    Redirector would count as an incoming packet."
    ::= { gatewayServiceForNetWare 15 }

nwPacketsTransmittedPerSec OBJECT-TYPE
    SYNTAX     Gauge32
    MAX-ACCESS read-only
    STATUS     current
    DESCRIPTION
	    "Packets Transmitted/sec is the rate at which
	    the Redirector is sending packets (also called
	    SMBs or Server Message Blocks).  Network
	    transmissions are divided into packets.  The
	    average number of bytes transmitted in a packet
	    can be obtained by dividing Bytes
	    Transmitted/sec by this counter."
    ::= { gatewayServiceForNetWare 16 }

nwPacketsPerSec OBJECT-TYPE
    SYNTAX     Gauge32
    MAX-ACCESS read-only
    STATUS     current
    DESCRIPTION
	    "Packets/sec is the rate the Redirector is
	    processing data packets.  One packet includes
	    (hopefully) many bytes.  We say hopefully here
	    because each packet has protocol overhead.	You
	    can determine the efficiency of this path by
	    dividing the Bytes/sec by this counter to
	    determine the average number of bytes
	    transferred/packet.  You can also divide this
	    counter by Operations/sec to determine the
	    average number of packets per operation,
	    another measure of efficiency."
    ::= { gatewayServiceForNetWare 17 }

nwReadOperationsRandomPerSec OBJECT-TYPE
    SYNTAX     Gauge32
    MAX-ACCESS read-only
    STATUS     current
    DESCRIPTION
	    "Read Operations Random/sec counts the rate at
	    which, on a file-by-file basis, reads are made
	    that are not sequential.  If a read is made
	    using a particular file handle, and then is
	    followed by another read that is not
	    immediately the contiguous next byte, this
	    counter is incremented by one."
    ::= { gatewayServiceForNetWare 18 }

nwReadPacketsPerSec OBJECT-TYPE
    SYNTAX     Gauge32
    MAX-ACCESS read-only
    STATUS     current
    DESCRIPTION
	    "Read Packets/sec is the rate at which read
	    packets are being placed on the network.  Each
	    time a single packet is sent with a request to
	    read data remotely, this counter is incremented
	    by one."
    ::= { gatewayServiceForNetWare 19 }

nwServerDisconnects OBJECT-TYPE
    SYNTAX     Gauge32
    MAX-ACCESS read-only
    STATUS     current
    DESCRIPTION
	    "Server Disconnects counts the number of times
	    a Server has disconnected your Redirector.	See
	    also Server Reconnects."
    ::= { gatewayServiceForNetWare 20 }

nwServerReconnects OBJECT-TYPE
    SYNTAX     Gauge32
    MAX-ACCESS read-only
    STATUS     current
    DESCRIPTION
	    "Server Reconnects counts the number of times
	    your Redirector has had to reconnect to a
	    server in order to complete a new active
	    request.  You can be disconnected by the Server
	    if you remain inactive for too long.  Locally
	    even if all your remote files are closed, the
	    Redirector will keep your connections intact
	    for (nominally) ten minutes.  Such inactive
	    connections are called Dormant Connections. 
	    Reconnecting is expensive in time."
    ::= { gatewayServiceForNetWare 21 }

nwServerSessions OBJECT-TYPE
    SYNTAX     Gauge32
    MAX-ACCESS read-only
    STATUS     current
    DESCRIPTION
	    "Server Sessions counts the total number of
	    security objects the Redirector has managed. 
	    For example, a logon to a server followed by a
	    network access to the same server will
	    establish one connection, but two sessions."
    ::= { gatewayServiceForNetWare 22 }

nwWriteOperationsRandomPerSec OBJECT-TYPE
    SYNTAX     Gauge32
    MAX-ACCESS read-only
    STATUS     current
    DESCRIPTION
	    "Write Operations Random/sec is the rate at
	    which, on a file-by-file basis, writes are made
	    that are not sequential.  If a write is made
	    using a particular file handle, and then is
	    followed by another write that is not
	    immediately the next contiguous byte, this
	    counter is incremented by one."
    ::= { gatewayServiceForNetWare 23 }

nwWritePacketsPerSec OBJECT-TYPE
    SYNTAX     Gauge32
    MAX-ACCESS read-only
    STATUS     current
    DESCRIPTION
	    "Write Packets/sec is the rate at which writes
	    are being sent to the network.  Each time a
	    single packet is sent with a request to write
	    remote data, this counter is incremented by
	    one."
    ::= { gatewayServiceForNetWare 24 }

iasAccountingClientsTable OBJECT-TYPE
    SYNTAX     SEQUENCE OF IASAccountingClientsEntry
    MAX-ACCESS not-accessible
    STATUS     current
    DESCRIPTION
	    "The IAS Accounting Clients performance object
	    is installed by the Internet Authentication
	    Service (IAS). IAS uses the Remote
	    Authentication Dial-In User Service (RADIUS)
	    protocol to perform remote authentication. IAS
	    performance objects report activity for servers
	    or clients, including user authentication,
	    authorization, and accounting (usage)."
    ::= { advanced 25 }

iasAccountingClientsEntry OBJECT-TYPE
    SYNTAX     IASAccountingClientsEntry
    MAX-ACCESS not-accessible
    STATUS     current
    DESCRIPTION
	    "Performance information for one particular
	    instance of 'IAS Accounting Clients' object."
    INDEX      { iccInstance }
    ::= { iasAccountingClientsTable 1 }

IASAccountingClientsEntry ::= SEQUENCE {
    iccInstance InstanceName,
    iccAccountingRequests Gauge32,
    iccAccountingRequestsPerSec Gauge32,
    iccAccountingResponses Gauge32,
    iccAccountingResponsesPerSec Gauge32,
    iccBadAuthenticators Gauge32,
    iccBadAuthenticatorsPerSec Gauge32,
    iccDroppedPackets Gauge32,
    iccDroppedPacketsPerSec Gauge32,
    iccDuplicateAccountingRequests Gauge32,
    iccDuplicateAccountingRqstPerSec Gauge32,
    iccMalformedPackets Gauge32,
    iccMalformedPacketsPerSec Gauge32,
    iccNoRecord Gauge32,
    iccNoRecordPerSec Gauge32,
    iccPacketsReceived Gauge32,
    iccPacketsReceivedPerSec Gauge32,
    iccPacketsSent Gauge32,
    iccPacketsSentPerSec Gauge32,
    iccUnknownType Gauge32,
    iccUnknownTypePerSec Gauge32
}

iccInstance OBJECT-TYPE
    SYNTAX     InstanceName
    MAX-ACCESS read-only
    STATUS     current
    DESCRIPTION
	    "Instance name."
    ::= { iasAccountingClientsEntry 1 }

iccAccountingRequests OBJECT-TYPE
    SYNTAX     Gauge32
    MAX-ACCESS read-only
    STATUS     current
    DESCRIPTION
	    "Shows the number of packets received from this
	    client on the accounting port."
    ::= { iasAccountingClientsEntry 2 }

iccAccountingRequestsPerSec OBJECT-TYPE
    SYNTAX     Gauge32
    MAX-ACCESS read-only
    STATUS     current
    DESCRIPTION
	    "Shows the rate, in seconds, at which packets
	    were received from this client on the
	    accounting port."
    ::= { iasAccountingClientsEntry 3 }

iccAccountingResponses OBJECT-TYPE
    SYNTAX     Gauge32
    MAX-ACCESS read-only
    STATUS     current
    DESCRIPTION
	    "Shows the number of RADIUS Accounting-Response
	    packets sent to this client."
    ::= { iasAccountingClientsEntry 4 }

iccAccountingResponsesPerSec OBJECT-TYPE
    SYNTAX     Gauge32
    MAX-ACCESS read-only
    STATUS     current
    DESCRIPTION
	    "Shows the rate in seconds at which duplicate
	    RADIUS Accounting-Request packets were received
	    from this client."
    ::= { iasAccountingClientsEntry 5 }

iccBadAuthenticators OBJECT-TYPE
    SYNTAX     Gauge32
    MAX-ACCESS read-only
    STATUS     current
    DESCRIPTION
	    "Shows the number of packets that contained
	    invalid Signature attributes."
    ::= { iasAccountingClientsEntry 6 }

iccBadAuthenticatorsPerSec OBJECT-TYPE
    SYNTAX     Gauge32
    MAX-ACCESS read-only
    STATUS     current
    DESCRIPTION
	    "Shows the rate, in seconds, at which packets
	    that contained invalid Signature attributes
	    were received."
    ::= { iasAccountingClientsEntry 7 }

iccDroppedPackets OBJECT-TYPE
    SYNTAX     Gauge32
    MAX-ACCESS read-only
    STATUS     current
    DESCRIPTION
	    "Shows the number of incoming packets silently
	    discarded for a reason other than being
	    malformed, bad authenticators, or unknown
	    types."
    ::= { iasAccountingClientsEntry 8 }

iccDroppedPacketsPerSec OBJECT-TYPE
    SYNTAX     Gauge32
    MAX-ACCESS read-only
    STATUS     current
    DESCRIPTION
	    "Shows the rate in seconds at which incoming
	    packets were silently discarded for a reason
	    other than being malformed, bad authenticators,
	    or unknown types."
    ::= { iasAccountingClientsEntry 9 }

iccDuplicateAccountingRequests OBJECT-TYPE
    SYNTAX     Gauge32
    MAX-ACCESS read-only
    STATUS     current
    DESCRIPTION
	    "Shows the number of duplicate RADIUS
	    Accounting-Request packets received from this
	    client."
    ::= { iasAccountingClientsEntry 10 }

iccDuplicateAccountingRqstPerSec OBJECT-TYPE
    SYNTAX     Gauge32
    MAX-ACCESS read-only
    STATUS     current
    DESCRIPTION
	    "Shows the rate, in seconds, at which duplicate
	    RADIUS Accounting-Request packets were received
	    from this client."
    ::= { iasAccountingClientsEntry 11 }

iccMalformedPackets OBJECT-TYPE
    SYNTAX     Gauge32
    MAX-ACCESS read-only
    STATUS     current
    DESCRIPTION
	    "Shows the number of malformed packets
	    received. Bad authenticators or unknown types
	    are not included."
    ::= { iasAccountingClientsEntry 12 }

iccMalformedPacketsPerSec OBJECT-TYPE
    SYNTAX     Gauge32
    MAX-ACCESS read-only
    STATUS     current
    DESCRIPTION
	    "Shows the rate, in seconds, at which malformed
	    packets were received."
    ::= { iasAccountingClientsEntry 13 }

iccNoRecord OBJECT-TYPE
    SYNTAX     Gauge32
    MAX-ACCESS read-only
    STATUS     current
    DESCRIPTION
	    "Shows the number of RADIUS Accounting-Request
	    packets that were received and responded to but
	    not recorded."
    ::= { iasAccountingClientsEntry 14 }

iccNoRecordPerSec OBJECT-TYPE
    SYNTAX     Gauge32
    MAX-ACCESS read-only
    STATUS     current
    DESCRIPTION
	    "Shows the rate, in seconds, at which RADIUS
	    Accounting-Request packets were received and
	    responded to but not recorded."
    ::= { iasAccountingClientsEntry 15 }

iccPacketsReceived OBJECT-TYPE
    SYNTAX     Gauge32
    MAX-ACCESS read-only
    STATUS     current
    DESCRIPTION
	    "Shows the number of packets received."
    ::= { iasAccountingClientsEntry 16 }

iccPacketsReceivedPerSec OBJECT-TYPE
    SYNTAX     Gauge32
    MAX-ACCESS read-only
    STATUS     current
    DESCRIPTION
	    "Shows the rate, in seconds, at which packets
	    were received."
    ::= { iasAccountingClientsEntry 17 }

iccPacketsSent OBJECT-TYPE
    SYNTAX     Gauge32
    MAX-ACCESS read-only
    STATUS     current
    DESCRIPTION
	    "Shows the number of packets sent."
    ::= { iasAccountingClientsEntry 18 }

iccPacketsSentPerSec OBJECT-TYPE
    SYNTAX     Gauge32
    MAX-ACCESS read-only
    STATUS     current
    DESCRIPTION
	    "Shows the rate, in seconds, at which packets
	    were sent."
    ::= { iasAccountingClientsEntry 19 }

iccUnknownType OBJECT-TYPE
    SYNTAX     Gauge32
    MAX-ACCESS read-only
    STATUS     current
    DESCRIPTION
	    "Shows the number of packets of unknown type
	    that were received. An unknown type is a RADIUS
	    packet that contains an unrecognized entry in
	    the Code field, used to identify the packet
	    type. Consequently IAS does not support packets
	    of unknown type."
    ::= { iasAccountingClientsEntry 20 }

iccUnknownTypePerSec OBJECT-TYPE
    SYNTAX     Gauge32
    MAX-ACCESS read-only
    STATUS     current
    DESCRIPTION
	    "Shows the rate, in seconds, at which packets
	    of unknown type were received."
    ::= { iasAccountingClientsEntry 21 }

iasAccountingProxy OBJECT IDENTIFIER
    ::= { advanced 26 }

icpAccountingRequests OBJECT-TYPE
    SYNTAX     Gauge32
    MAX-ACCESS read-only
    STATUS     current
    DESCRIPTION
	    "The number of RADIUS Accounting-Request
	    packets received on the accounting port."
    ::= { iasAccountingProxy 1 }

icpAccountingRequestsPerSec OBJECT-TYPE
    SYNTAX     Gauge32
    MAX-ACCESS read-only
    STATUS     current
    DESCRIPTION
	    "The average number of RADIUS
	    Accounting-Request packets sent per second to
	    the accounting port."
    ::= { iasAccountingProxy 2 }

icpAccountingResponses OBJECT-TYPE
    SYNTAX     Gauge32
    MAX-ACCESS read-only
    STATUS     current
    DESCRIPTION
	    "The number of RADIUS Accounting-Response
	    packets received on the accounting port."
    ::= { iasAccountingProxy 3 }

icpAccountingResponsesPerSec OBJECT-TYPE
    SYNTAX     Gauge32
    MAX-ACCESS read-only
    STATUS     current
    DESCRIPTION
	    "The average number of RADIUS
	    Accounting-Response packets received per second
	    on the accounting port."
    ::= { iasAccountingProxy 4 }

icpBadAuthenticators OBJECT-TYPE
    SYNTAX     Gauge32
    MAX-ACCESS read-only
    STATUS     current
    DESCRIPTION
	    "The number of RADIUS packets that contain an
	    invalid Message Authenticator attribute."
    ::= { iasAccountingProxy 5 }

icpBadAuthenticatorsPerSec OBJECT-TYPE
    SYNTAX     Gauge32
    MAX-ACCESS read-only
    STATUS     current
    DESCRIPTION
	    "The average number of RADIUS packets  per
	    second that contain an invalid Message
	    Authenticator attribute."
    ::= { iasAccountingProxy 6 }

icpDroppedPackets OBJECT-TYPE
    SYNTAX     Gauge32
    MAX-ACCESS read-only
    STATUS     current
    DESCRIPTION
	    "The number of incoming packets that are
	    silently discarded for a reason other than
	    'malformed,' 'invalid Message Authenticator,'
	    or 'unknown type'."
    ::= { iasAccountingProxy 7 }

icpDroppedPacketsPerSec OBJECT-TYPE
    SYNTAX     Gauge32
    MAX-ACCESS read-only
    STATUS     current
    DESCRIPTION
	    "The average number of incoming packets per
	    second that are silently discarded for a reason
	    other than 'malformed,' 'invalid Message
	    Authenticator,' or 'unknown type'."
    ::= { iasAccountingProxy 8 }

icpInvalidAddresses OBJECT-TYPE
    SYNTAX     Gauge32
    MAX-ACCESS read-only
    STATUS     current
    DESCRIPTION
	    "The number of packets received from unknown
	    addresses."
    ::= { iasAccountingProxy 9 }

icpInvalidAddressesPerSec OBJECT-TYPE
    SYNTAX     Gauge32
    MAX-ACCESS read-only
    STATUS     current
    DESCRIPTION
	    "The average number of packets per second
	    received from unknown addresses."
    ::= { iasAccountingProxy 10 }

icpMalformedPackets OBJECT-TYPE
    SYNTAX     Gauge32
    MAX-ACCESS read-only
    STATUS     current
    DESCRIPTION
	    "The number of packets containing malformed
	    data received."
    ::= { iasAccountingProxy 11 }

icpMalformedPacketsPerSec OBJECT-TYPE
    SYNTAX     Gauge32
    MAX-ACCESS read-only
    STATUS     current
    DESCRIPTION
	    "The average number of packets containing
	    malformed data received per second."
    ::= { iasAccountingProxy 12 }

icpPacketsReceived OBJECT-TYPE
    SYNTAX     Gauge32
    MAX-ACCESS read-only
    STATUS     current
    DESCRIPTION
	    "The number of packets received."
    ::= { iasAccountingProxy 13 }

icpPacketsReceivedPerSec OBJECT-TYPE
    SYNTAX     Gauge32
    MAX-ACCESS read-only
    STATUS     current
    DESCRIPTION
	    "The average number of packets received per
	    second."
    ::= { iasAccountingProxy 14 }

icpPendingRequests OBJECT-TYPE
    SYNTAX     Gauge32
    MAX-ACCESS read-only
    STATUS     current
    DESCRIPTION
	    "The number of requests destined for this
	    server that have not yet timed out or received
	    a response."
    ::= { iasAccountingProxy 15 }

icpRequestTimeouts OBJECT-TYPE
    SYNTAX     Gauge32
    MAX-ACCESS read-only
    STATUS     current
    DESCRIPTION
	    "The number of request timeouts to this
	    server."
    ::= { iasAccountingProxy 16 }

icpRequestTimeoutsPerSec OBJECT-TYPE
    SYNTAX     Gauge32
    MAX-ACCESS read-only
    STATUS     current
    DESCRIPTION
	    "The average number of request timeouts per
	    second to this server."
    ::= { iasAccountingProxy 17 }

icpRetransmissions OBJECT-TYPE
    SYNTAX     Gauge32
    MAX-ACCESS read-only
    STATUS     current
    DESCRIPTION
	    "The number of requests retransmitted to this
	    server."
    ::= { iasAccountingProxy 18 }

icpRetransmissionsPerSec OBJECT-TYPE
    SYNTAX     Gauge32
    MAX-ACCESS read-only
    STATUS     current
    DESCRIPTION
	    "The average number of requests retransmitted
	    per second to this server."
    ::= { iasAccountingProxy 19 }

icpUnknownType OBJECT-TYPE
    SYNTAX     Gauge32
    MAX-ACCESS read-only
    STATUS     current
    DESCRIPTION
	    "The number of unknown type (non-RADIUS)
	    packets received."
    ::= { iasAccountingProxy 20 }

icpUnknownTypePerSec OBJECT-TYPE
    SYNTAX     Gauge32
    MAX-ACCESS read-only
    STATUS     current
    DESCRIPTION
	    "The average number of unknown type
	    (non-RADIUS) packets received per second."
    ::= { iasAccountingProxy 21 }

iasAccountingServer OBJECT-IDENTITY
    STATUS     current
    DESCRIPTION
	    "The IAS Accounting Server performance object
	    is installed by the IAS. IAS uses the RADIUS
	    protocol to perform remote authentication. IAS
	    performance objects report activity for servers
	    or clients, including user authentication,
	    authorization, and accounting (usage)."
    ::= { advanced 27 }

icsAccountingRequests OBJECT-TYPE
    SYNTAX     Gauge32
    MAX-ACCESS read-only
    STATUS     current
    DESCRIPTION
	    "The number of packets received from this
	    client on the accounting port."
    ::= { iasAccountingServer 1 }

icsAccountingRequestsPerSec OBJECT-TYPE
    SYNTAX     Gauge32
    MAX-ACCESS read-only
    STATUS     current
    DESCRIPTION
	    "The number of packets per second received from
	    this client on the accounting port."
    ::= { iasAccountingServer 2 }

icsAccountingResponses OBJECT-TYPE
    SYNTAX     Gauge32
    MAX-ACCESS read-only
    STATUS     current
    DESCRIPTION
	    "The number of RADIUS Accounting-Response
	    packets sent to this client."
    ::= { iasAccountingServer 3 }

icsAccountingResponsesPerSec OBJECT-TYPE
    SYNTAX     Gauge32
    MAX-ACCESS read-only
    STATUS     current
    DESCRIPTION
	    "The number of RADIUS Accounting-Response
	    packets per second sent to this client."
    ::= { iasAccountingServer 4 }

icsBadAuthenticators OBJECT-TYPE
    SYNTAX     Gauge32
    MAX-ACCESS read-only
    STATUS     current
    DESCRIPTION
	    "The number of packets which contained invalid
	    Signature attributes."
    ::= { iasAccountingServer 5 }

icsBadAuthenticatorsPerSec OBJECT-TYPE
    SYNTAX     Gauge32
    MAX-ACCESS read-only
    STATUS     current
    DESCRIPTION
	    "The number of packets per second which
	    contained invalid Signature attributes."
    ::= { iasAccountingServer 6 }

icsDroppedPackets OBJECT-TYPE
    SYNTAX     Gauge32
    MAX-ACCESS read-only
    STATUS     current
    DESCRIPTION
	    "The number of incoming packets silently
	    discarded for a reason other than malformed,
	    bad authenticators, or unknown types."
    ::= { iasAccountingServer 7 }

icsDroppedPacketsPerSec OBJECT-TYPE
    SYNTAX     Gauge32
    MAX-ACCESS read-only
    STATUS     current
    DESCRIPTION
	    "The number of incoming packets per second
	    silently discarded for a reason other than
	    malformed, bad authenticators, or unknown
	    types."
    ::= { iasAccountingServer 8 }

icsDuplicateAccountingRequests OBJECT-TYPE
    SYNTAX     Gauge32
    MAX-ACCESS read-only
    STATUS     current
    DESCRIPTION
	    "The number of duplicate RADIUS
	    Accounting-Request packets received from this
	    client."
    ::= { iasAccountingServer 9 }

icsDuplicateAccountingRqstPerSec OBJECT-TYPE
    SYNTAX     Gauge32
    MAX-ACCESS read-only
    STATUS     current
    DESCRIPTION
	    "The number of duplicate RADIUS
	    Accounting-Request packets per second received
	    from this client."
    ::= { iasAccountingServer 10 }

icsInvalidRequests OBJECT-TYPE
    SYNTAX     Gauge32
    MAX-ACCESS read-only
    STATUS     current
    DESCRIPTION
	    "The number of packets received from unknown
	    addresses."
    ::= { iasAccountingServer 11 }

icsInvalidRequestsPerSec OBJECT-TYPE
    SYNTAX     Gauge32
    MAX-ACCESS read-only
    STATUS     current
    DESCRIPTION
	    "The number of packets received per second from
	    unknown addresses."
    ::= { iasAccountingServer 12 }

icsMalformedPackets OBJECT-TYPE
    SYNTAX     Gauge32
    MAX-ACCESS read-only
    STATUS     current
    DESCRIPTION
	    "The number of malformed packets received. Bad
	    authenticators or unknown types are not
	    included."
    ::= { iasAccountingServer 13 }

icsMalformedPacketsPerSec OBJECT-TYPE
    SYNTAX     Gauge32
    MAX-ACCESS read-only
    STATUS     current
    DESCRIPTION
	    "The number of malformed packets per second
	    received. Bad authenticators or unknown types
	    are not included."
    ::= { iasAccountingServer 14 }

icsNoRecord OBJECT-TYPE
    SYNTAX     Gauge32
    MAX-ACCESS read-only
    STATUS     current
    DESCRIPTION
	    "The number of RADIUS Accounting-Request
	    packets which were received and responded to
	    but not recorded."
    ::= { iasAccountingServer 15 }

icsNoRecordPerSec OBJECT-TYPE
    SYNTAX     Gauge32
    MAX-ACCESS read-only
    STATUS     current
    DESCRIPTION
	    "The number of RADIUS Accounting-Request
	    packets per second which were received and
	    responded to but not recorded."
    ::= { iasAccountingServer 16 }

icsPacketsReceived OBJECT-TYPE
    SYNTAX     Gauge32
    MAX-ACCESS read-only
    STATUS     current
    DESCRIPTION
	    "The number of packets received."
    ::= { iasAccountingServer 17 }

icsPacketsReceivedPerSec OBJECT-TYPE
    SYNTAX     Gauge32
    MAX-ACCESS read-only
    STATUS     current
    DESCRIPTION
	    "The number of packets per second received."
    ::= { iasAccountingServer 18 }

icsPacketsSent OBJECT-TYPE
    SYNTAX     Gauge32
    MAX-ACCESS read-only
    STATUS     current
    DESCRIPTION
	    "The number of packets sent."
    ::= { iasAccountingServer 19 }

icsPacketsSentPerSec OBJECT-TYPE
    SYNTAX     Gauge32
    MAX-ACCESS read-only
    STATUS     current
    DESCRIPTION
	    "The number of packets sent per second."
    ::= { iasAccountingServer 20 }

icsServerResetTime OBJECT-TYPE
    SYNTAX     Gauge32
    MAX-ACCESS read-only
    STATUS     current
    DESCRIPTION
	    "The time elapsed (in hundredths of a second)
	    since the server configuration was reset."
    ::= { iasAccountingServer 21 }

icsServerUpTime OBJECT-TYPE
    SYNTAX     Gauge32
    MAX-ACCESS read-only
    STATUS     current
    DESCRIPTION
	    "The time elapsed (in hundredths of a second)
	    since the server process was started."
    ::= { iasAccountingServer 22 }

icsUnknownType OBJECT-TYPE
    SYNTAX     Gauge32
    MAX-ACCESS read-only
    STATUS     current
    DESCRIPTION
	    "The number of packets of unknown type which
	    were received."
    ::= { iasAccountingServer 23 }

icsUnknownTypePerSec OBJECT-TYPE
    SYNTAX     Gauge32
    MAX-ACCESS read-only
    STATUS     current
    DESCRIPTION
	    "The number of packets per second of unknown
	    type which were received."
    ::= { iasAccountingServer 24 }

iasAuthenticationClientsTable OBJECT-TYPE
    SYNTAX     SEQUENCE OF IASAuthenticationClientsEntry
    MAX-ACCESS not-accessible
    STATUS     current
    DESCRIPTION
	    "The IAS Authentication Clients performance
	    object is installed by IAS. IAS uses the RADIUS
	    protocol to perform remote authentication. IAS
	    performance objects report activity for servers
	    or clients, including user authentication,
	    authorization, and accounting (usage)."
    ::= { advanced 28 }

iasAuthenticationClientsEntry OBJECT-TYPE
    SYNTAX     IASAuthenticationClientsEntry
    MAX-ACCESS not-accessible
    STATUS     current
    DESCRIPTION
	    "Performance information for one particular
	    instance of 'IAS Authentication Clients'
	    object."
    INDEX      { iucInstance }
    ::= { iasAuthenticationClientsTable 1 }

IASAuthenticationClientsEntry ::= SEQUENCE {
    iucInstance InstanceName,
    iucAccessAccepts Gauge32,
    iucAccessAcceptsPerSec Gauge32,
    iucAccessChallenges Gauge32,
    iucAccessChallengesPerSec Gauge32,
    iucAccessRejects Gauge32,
    iucAccessRejectsPerSec Gauge32,
    iucAccessRequests Gauge32,
    iucAccessRequestsPerSec Gauge32,
    iucBadAuthenticators Gauge32,
    iucBadAuthenticatorsPerSec Gauge32,
    iucDroppedPackets Gauge32,
    iucDroppedPacketsPerSec Gauge32,
    iucDuplicateAccessRequests Gauge32,
    iucDuplicateAccessRequestsPerSec Gauge32,
    iucMalformedPackets Gauge32,
    iucMalformedPacketsPerSec Gauge32,
    iucPacketsReceived Gauge32,
    iucPacketsReceivedPerSec Gauge32,
    iucPacketsSent Gauge32,
    iucPacketsSentPerSec Gauge32,
    iucUnknownType Gauge32,
    iucUnknownTypePerSec Gauge32
}

iucInstance OBJECT-TYPE
    SYNTAX     InstanceName
    MAX-ACCESS read-only
    STATUS     current
    DESCRIPTION
	    "Instance name."
    ::= { iasAuthenticationClientsEntry 1 }

iucAccessAccepts OBJECT-TYPE
    SYNTAX     Gauge32
    MAX-ACCESS read-only
    STATUS     current
    DESCRIPTION
	    "Access-Accepts"
    ::= { iasAuthenticationClientsEntry 2 }

iucAccessAcceptsPerSec OBJECT-TYPE
    SYNTAX     Gauge32
    MAX-ACCESS read-only
    STATUS     current
    DESCRIPTION
	    "Access-Accepts / sec."
    ::= { iasAuthenticationClientsEntry 3 }

iucAccessChallenges OBJECT-TYPE
    SYNTAX     Gauge32
    MAX-ACCESS read-only
    STATUS     current
    DESCRIPTION
	    "Access-Challenges"
    ::= { iasAuthenticationClientsEntry 4 }

iucAccessChallengesPerSec OBJECT-TYPE
    SYNTAX     Gauge32
    MAX-ACCESS read-only
    STATUS     current
    DESCRIPTION
	    "Access-Challenges / sec."
    ::= { iasAuthenticationClientsEntry 5 }

iucAccessRejects OBJECT-TYPE
    SYNTAX     Gauge32
    MAX-ACCESS read-only
    STATUS     current
    DESCRIPTION
	    "Access-Rejects"
    ::= { iasAuthenticationClientsEntry 6 }

iucAccessRejectsPerSec OBJECT-TYPE
    SYNTAX     Gauge32
    MAX-ACCESS read-only
    STATUS     current
    DESCRIPTION
	    "Access-Rejects / sec."
    ::= { iasAuthenticationClientsEntry 7 }

iucAccessRequests OBJECT-TYPE
    SYNTAX     Gauge32
    MAX-ACCESS read-only
    STATUS     current
    DESCRIPTION
	    "Access-Requests"
    ::= { iasAuthenticationClientsEntry 8 }

iucAccessRequestsPerSec OBJECT-TYPE
    SYNTAX     Gauge32
    MAX-ACCESS read-only
    STATUS     current
    DESCRIPTION
	    "Access-Requests / sec."
    ::= { iasAuthenticationClientsEntry 9 }

iucBadAuthenticators OBJECT-TYPE
    SYNTAX     Gauge32
    MAX-ACCESS read-only
    STATUS     current
    DESCRIPTION
	    "Bad Authenticators"
    ::= { iasAuthenticationClientsEntry 10 }

iucBadAuthenticatorsPerSec OBJECT-TYPE
    SYNTAX     Gauge32
    MAX-ACCESS read-only
    STATUS     current
    DESCRIPTION
	    "Bad Authenticators / sec."
    ::= { iasAuthenticationClientsEntry 11 }

iucDroppedPackets OBJECT-TYPE
    SYNTAX     Gauge32
    MAX-ACCESS read-only
    STATUS     current
    DESCRIPTION
	    "Dropped Packets"
    ::= { iasAuthenticationClientsEntry 12 }

iucDroppedPacketsPerSec OBJECT-TYPE
    SYNTAX     Gauge32
    MAX-ACCESS read-only
    STATUS     current
    DESCRIPTION
	    "Dropped Packets / sec."
    ::= { iasAuthenticationClientsEntry 13 }

iucDuplicateAccessRequests OBJECT-TYPE
    SYNTAX     Gauge32
    MAX-ACCESS read-only
    STATUS     current
    DESCRIPTION
	    "Duplicate Access-Requests"
    ::= { iasAuthenticationClientsEntry 14 }

iucDuplicateAccessRequestsPerSec OBJECT-TYPE
    SYNTAX     Gauge32
    MAX-ACCESS read-only
    STATUS     current
    DESCRIPTION
	    "Duplicate Access-Requests / sec."
    ::= { iasAuthenticationClientsEntry 15 }

iucMalformedPackets OBJECT-TYPE
    SYNTAX     Gauge32
    MAX-ACCESS read-only
    STATUS     current
    DESCRIPTION
	    "Malformed Packets"
    ::= { iasAuthenticationClientsEntry 16 }

iucMalformedPacketsPerSec OBJECT-TYPE
    SYNTAX     Gauge32
    MAX-ACCESS read-only
    STATUS     current
    DESCRIPTION
	    "Malformed Packets / sec."
    ::= { iasAuthenticationClientsEntry 17 }

iucPacketsReceived OBJECT-TYPE
    SYNTAX     Gauge32
    MAX-ACCESS read-only
    STATUS     current
    DESCRIPTION
	    "Packets Received"
    ::= { iasAuthenticationClientsEntry 18 }

iucPacketsReceivedPerSec OBJECT-TYPE
    SYNTAX     Gauge32
    MAX-ACCESS read-only
    STATUS     current
    DESCRIPTION
	    "Packets Received / sec."
    ::= { iasAuthenticationClientsEntry 19 }

iucPacketsSent OBJECT-TYPE
    SYNTAX     Gauge32
    MAX-ACCESS read-only
    STATUS     current
    DESCRIPTION
	    "Packets Sent"
    ::= { iasAuthenticationClientsEntry 20 }

iucPacketsSentPerSec OBJECT-TYPE
    SYNTAX     Gauge32
    MAX-ACCESS read-only
    STATUS     current
    DESCRIPTION
	    "Packets Sent / sec."
    ::= { iasAuthenticationClientsEntry 21 }

iucUnknownType OBJECT-TYPE
    SYNTAX     Gauge32
    MAX-ACCESS read-only
    STATUS     current
    DESCRIPTION
	    "Unknown Type"
    ::= { iasAuthenticationClientsEntry 22 }

iucUnknownTypePerSec OBJECT-TYPE
    SYNTAX     Gauge32
    MAX-ACCESS read-only
    STATUS     current
    DESCRIPTION
	    "Unknown Type / sec."
    ::= { iasAuthenticationClientsEntry 23 }

iasAuthenticationProxy OBJECT IDENTIFIER
    ::= { advanced 29 }

iupAccessAccepts OBJECT-TYPE
    SYNTAX     Gauge32
    MAX-ACCESS read-only
    STATUS     current
    DESCRIPTION
	    "The number of RADIUS Access-Accept packets
	    received from this server."
    ::= { iasAuthenticationProxy 1 }

iupAccessAcceptsPerSec OBJECT-TYPE
    SYNTAX     Gauge32
    MAX-ACCESS read-only
    STATUS     current
    DESCRIPTION
	    "The average number of RADIUS Access-Accept
	    packets per second received from this server."
    ::= { iasAuthenticationProxy 2 }

iupAccessChallenges OBJECT-TYPE
    SYNTAX     Gauge32
    MAX-ACCESS read-only
    STATUS     current
    DESCRIPTION
	    "The number of RADIUS Access-Challenge packets
	    received from this server."
    ::= { iasAuthenticationProxy 3 }

iupAccessChallengesPerSec OBJECT-TYPE
    SYNTAX     Gauge32
    MAX-ACCESS read-only
    STATUS     current
    DESCRIPTION
	    "The average number of RADIUS Access-Challenge
	    packets per second received from this server."
    ::= { iasAuthenticationProxy 4 }

iupAccessRejects OBJECT-TYPE
    SYNTAX     Gauge32
    MAX-ACCESS read-only
    STATUS     current
    DESCRIPTION
	    "The number of RADIUS Access-Reject packets
	    received from this server."
    ::= { iasAuthenticationProxy 5 }

iupAccessRejectsPerSec OBJECT-TYPE
    SYNTAX     Gauge32
    MAX-ACCESS read-only
    STATUS     current
    DESCRIPTION
	    "The average number of RADIUS Access-Reject
	    packets per second received from this server."
    ::= { iasAuthenticationProxy 6 }

iupAccessRequests OBJECT-TYPE
    SYNTAX     Gauge32
    MAX-ACCESS read-only
    STATUS     current
    DESCRIPTION
	    "The number of RADIUS Access-Request packets
	    sent to this server."
    ::= { iasAuthenticationProxy 7 }

iupAccessRequestsPerSec OBJECT-TYPE
    SYNTAX     Gauge32
    MAX-ACCESS read-only
    STATUS     current
    DESCRIPTION
	    "The average number of RADIUS Access-Request
	    packets per second sent to this server."
    ::= { iasAuthenticationProxy 8 }

iupBadAuthenticators OBJECT-TYPE
    SYNTAX     Gauge32
    MAX-ACCESS read-only
    STATUS     current
    DESCRIPTION
	    "The number of RADIUS packets that contain an
	    invalid Message Authenticator attribute."
    ::= { iasAuthenticationProxy 9 }

iupBadAuthenticatorsPerSec OBJECT-TYPE
    SYNTAX     Gauge32
    MAX-ACCESS read-only
    STATUS     current
    DESCRIPTION
	    "The average number of RADIUS packets  per
	    second that contain an invalid Message
	    Authenticator attribute."
    ::= { iasAuthenticationProxy 10 }

iupDroppedPackets OBJECT-TYPE
    SYNTAX     Gauge32
    MAX-ACCESS read-only
    STATUS     current
    DESCRIPTION
	    "The number of incoming packets that are
	    silently discarded for a reason other than
	    'malformed,' 'invalid Message Authenticator,'
	    or 'unknown type'."
    ::= { iasAuthenticationProxy 11 }

iupDroppedPacketsPerSec OBJECT-TYPE
    SYNTAX     Gauge32
    MAX-ACCESS read-only
    STATUS     current
    DESCRIPTION
	    "The average number of incoming packets per
	    second that are silently discarded for a reason
	    other than 'malformed,' 'invalid Message
	    Authenticator,' or 'unknown type'."
    ::= { iasAuthenticationProxy 12 }

iupInvalidAddresses OBJECT-TYPE
    SYNTAX     Gauge32
    MAX-ACCESS read-only
    STATUS     current
    DESCRIPTION
	    "The number of packets received from unknown
	    addresses."
    ::= { iasAuthenticationProxy 13 }

iupInvalidAddressesPerSec OBJECT-TYPE
    SYNTAX     Gauge32
    MAX-ACCESS read-only
    STATUS     current
    DESCRIPTION
	    "The average number of packets per second
	    received from unknown addresses."
    ::= { iasAuthenticationProxy 14 }

iupMalformedPackets OBJECT-TYPE
    SYNTAX     Gauge32
    MAX-ACCESS read-only
    STATUS     current
    DESCRIPTION
	    "The number of packets containing malformed
	    data received."
    ::= { iasAuthenticationProxy 15 }

iupMalformedPacketsPerSec OBJECT-TYPE
    SYNTAX     Gauge32
    MAX-ACCESS read-only
    STATUS     current
    DESCRIPTION
	    "The average number of packets containing
	    malformed data received per second."
    ::= { iasAuthenticationProxy 16 }

iupPacketsReceived OBJECT-TYPE
    SYNTAX     Gauge32
    MAX-ACCESS read-only
    STATUS     current
    DESCRIPTION
	    "The number of packets received."
    ::= { iasAuthenticationProxy 17 }

iupPacketsReceivedPerSec OBJECT-TYPE
    SYNTAX     Gauge32
    MAX-ACCESS read-only
    STATUS     current
    DESCRIPTION
	    "The average number of packets received per
	    second."
    ::= { iasAuthenticationProxy 18 }

iupPendingRequests OBJECT-TYPE
    SYNTAX     Gauge32
    MAX-ACCESS read-only
    STATUS     current
    DESCRIPTION
	    "The number of requests destined for this
	    server that have not yet timed out or received
	    a response."
    ::= { iasAuthenticationProxy 19 }

iupRequestTimeouts OBJECT-TYPE
    SYNTAX     Gauge32
    MAX-ACCESS read-only
    STATUS     current
    DESCRIPTION
	    "The number of request timeouts to this
	    server."
    ::= { iasAuthenticationProxy 20 }

iupRequestTimeoutsPerSec OBJECT-TYPE
    SYNTAX     Gauge32
    MAX-ACCESS read-only
    STATUS     current
    DESCRIPTION
	    "The average number of request timeouts per
	    second to this server."
    ::= { iasAuthenticationProxy 21 }

iupRetransmissions OBJECT-TYPE
    SYNTAX     Gauge32
    MAX-ACCESS read-only
    STATUS     current
    DESCRIPTION
	    "The number of requests retransmitted to this
	    server."
    ::= { iasAuthenticationProxy 22 }

iupRetransmissionsPerSec OBJECT-TYPE
    SYNTAX     Gauge32
    MAX-ACCESS read-only
    STATUS     current
    DESCRIPTION
	    "The average number of requests retransmitted
	    per second to this server."
    ::= { iasAuthenticationProxy 23 }

iupUnknownType OBJECT-TYPE
    SYNTAX     Gauge32
    MAX-ACCESS read-only
    STATUS     current
    DESCRIPTION
	    "The number of unknown type (non-RADIUS)
	    packets received."
    ::= { iasAuthenticationProxy 24 }

iupUnknownTypePerSec OBJECT-TYPE
    SYNTAX     Gauge32
    MAX-ACCESS read-only
    STATUS     current
    DESCRIPTION
	    "The average number of unknown type
	    (non-RADIUS) packets received per second."
    ::= { iasAuthenticationProxy 25 }

iasAuthenticationServer OBJECT-IDENTITY
    STATUS     current
    DESCRIPTION
	    "The IAS Authentication Server performance
	    object is installed by IAS. IAS uses the RADIUS
	    protocol to perform remote authentication. IAS
	    performance objects report activity for servers
	    or clients, including user authentication,
	    authorization, and accounting (usage)."
    ::= { advanced 30 }

iusAccessAccepts OBJECT-TYPE
    SYNTAX     Gauge32
    MAX-ACCESS read-only
    STATUS     current
    DESCRIPTION
	    "The number of RADIUS Access-Accept packets
	    sent to this client."
    ::= { iasAuthenticationServer 1 }

iusAccessAcceptsPerSec OBJECT-TYPE
    SYNTAX     Gauge32
    MAX-ACCESS read-only
    STATUS     current
    DESCRIPTION
	    "The number of RADIUS Access-Accept packets per
	    second sent to this client."
    ::= { iasAuthenticationServer 2 }

iusAccessChallenges OBJECT-TYPE
    SYNTAX     Gauge32
    MAX-ACCESS read-only
    STATUS     current
    DESCRIPTION
	    "The number of RADIUS Access-Challenge packets
	    sent to this client."
    ::= { iasAuthenticationServer 3 }

iusAccessChallengesPerSec OBJECT-TYPE
    SYNTAX     Gauge32
    MAX-ACCESS read-only
    STATUS     current
    DESCRIPTION
	    "The number of RADIUS Access-Challenge packets
	    per second sent to this client."
    ::= { iasAuthenticationServer 4 }

iusAccessRejects OBJECT-TYPE
    SYNTAX     Gauge32
    MAX-ACCESS read-only
    STATUS     current
    DESCRIPTION
	    "The number of RADIUS Access-Reject packets
	    sent to this client."
    ::= { iasAuthenticationServer 5 }

iusAccessRejectsPerSec OBJECT-TYPE
    SYNTAX     Gauge32
    MAX-ACCESS read-only
    STATUS     current
    DESCRIPTION
	    "The number of RADIUS Access-Reject packets per
	    second sent to this client."
    ::= { iasAuthenticationServer 6 }

iusAccessRequests OBJECT-TYPE
    SYNTAX     Gauge32
    MAX-ACCESS read-only
    STATUS     current
    DESCRIPTION
	    "The number of packets received on the
	    authentication port from this client."
    ::= { iasAuthenticationServer 7 }

iusAccessRequestsPerSec OBJECT-TYPE
    SYNTAX     Gauge32
    MAX-ACCESS read-only
    STATUS     current
    DESCRIPTION
	    "The number of packets per second received on
	    the authentication port from this client."
    ::= { iasAuthenticationServer 8 }

iusBadAuthenticators OBJECT-TYPE
    SYNTAX     Gauge32
    MAX-ACCESS read-only
    STATUS     current
    DESCRIPTION
	    "The number of packets which contained invalid
	    Signature attributes."
    ::= { iasAuthenticationServer 9 }

iusBadAuthenticatorsPerSec OBJECT-TYPE
    SYNTAX     Gauge32
    MAX-ACCESS read-only
    STATUS     current
    DESCRIPTION
	    "The number of packets per second which
	    contained invalid Signature attributes."
    ::= { iasAuthenticationServer 10 }

iusDroppedPackets OBJECT-TYPE
    SYNTAX     Gauge32
    MAX-ACCESS read-only
    STATUS     current
    DESCRIPTION
	    "The number of incoming packets silently
	    discarded for a reason other than malformed,
	    bad authenticators, or unknown types."
    ::= { iasAuthenticationServer 11 }

iusDroppedPacketsPerSec OBJECT-TYPE
    SYNTAX     Gauge32
    MAX-ACCESS read-only
    STATUS     current
    DESCRIPTION
	    "The number of incoming packets per second
	    silently discarded for a reason other than
	    malformed, bad authenticators, or unknown
	    types."
    ::= { iasAuthenticationServer 12 }

iusDuplicateAccessRequests OBJECT-TYPE
    SYNTAX     Gauge32
    MAX-ACCESS read-only
    STATUS     current
    DESCRIPTION
	    "The number of duplicate RADIUS Access-Request
	    packets received from this client."
    ::= { iasAuthenticationServer 13 }

iusDuplicateAccessRequestsPerSec OBJECT-TYPE
    SYNTAX     Gauge32
    MAX-ACCESS read-only
    STATUS     current
    DESCRIPTION
	    "The number of duplicate RADIUS Access-Request
	    packets per second received from this client."
    ::= { iasAuthenticationServer 14 }

iusInvalidRequests OBJECT-TYPE
    SYNTAX     Gauge32
    MAX-ACCESS read-only
    STATUS     current
    DESCRIPTION
	    "The number of packets received from unknown
	    addresses."
    ::= { iasAuthenticationServer 15 }

iusInvalidRequestsPerSec OBJECT-TYPE
    SYNTAX     Gauge32
    MAX-ACCESS read-only
    STATUS     current
    DESCRIPTION
	    "The number of packets received per second from
	    unknown addresses."
    ::= { iasAuthenticationServer 16 }

iusMalformedPackets OBJECT-TYPE
    SYNTAX     Gauge32
    MAX-ACCESS read-only
    STATUS     current
    DESCRIPTION
	    "The number of malformed packets received. Bad
	    authenticators or unknown types are not
	    included."
    ::= { iasAuthenticationServer 17 }

iusMalformedPacketsPerSec OBJECT-TYPE
    SYNTAX     Gauge32
    MAX-ACCESS read-only
    STATUS     current
    DESCRIPTION
	    "The number of malformed packets per second
	    received. Bad authenticators or unknown types
	    are not included."
    ::= { iasAuthenticationServer 18 }

iusPacketsReceived OBJECT-TYPE
    SYNTAX     Gauge32
    MAX-ACCESS read-only
    STATUS     current
    DESCRIPTION
	    "The number of packets received."
    ::= { iasAuthenticationServer 19 }

iusPacketsReceivedPerSec OBJECT-TYPE
    SYNTAX     Gauge32
    MAX-ACCESS read-only
    STATUS     current
    DESCRIPTION
	    "The number of packets per second received."
    ::= { iasAuthenticationServer 20 }

iusPacketsSent OBJECT-TYPE
    SYNTAX     Gauge32
    MAX-ACCESS read-only
    STATUS     current
    DESCRIPTION
	    "The number of packets sent."
    ::= { iasAuthenticationServer 21 }

iusPacketsSentPerSec OBJECT-TYPE
    SYNTAX     Gauge32
    MAX-ACCESS read-only
    STATUS     current
    DESCRIPTION
	    "The number of packets sent per second."
    ::= { iasAuthenticationServer 22 }

iusServerResetTime OBJECT-TYPE
    SYNTAX     Gauge32
    MAX-ACCESS read-only
    STATUS     current
    DESCRIPTION
	    "The time elapsed (in hundredths of a second)
	    since the server configuration was reset."
    ::= { iasAuthenticationServer 23 }

iusServerUpTime OBJECT-TYPE
    SYNTAX     Gauge32
    MAX-ACCESS read-only
    STATUS     current
    DESCRIPTION
	    "The time elapsed (in hundredths of a second)
	    since the server process was started."
    ::= { iasAuthenticationServer 24 }

iusUnknownType OBJECT-TYPE
    SYNTAX     Gauge32
    MAX-ACCESS read-only
    STATUS     current
    DESCRIPTION
	    "The number of packets of unknown type which
	    were received."
    ::= { iasAuthenticationServer 25 }

iusUnknownTypePerSec OBJECT-TYPE
    SYNTAX     Gauge32
    MAX-ACCESS read-only
    STATUS     current
    DESCRIPTION
	    "The number of packets per second of unknown
	    type which were received."
    ::= { iasAuthenticationServer 26 }

iasRemoteAccountingServersTable OBJECT-TYPE
    SYNTAX     SEQUENCE OF IASRemoteAccountingServersEntry
    MAX-ACCESS not-accessible
    STATUS     current
    DESCRIPTION
	    "A table containing performance information for
	    instances of 'IAS Remote Accounting Servers'
	    objects."
    ::= { advanced 31 }

iasRemoteAccountingServersEntry OBJECT-TYPE
    SYNTAX     IASRemoteAccountingServersEntry
    MAX-ACCESS not-accessible
    STATUS     current
    DESCRIPTION
	    "Performance information for one particular
	    instance of 'IAS Remote Accounting Servers'
	    object."
    INDEX      { ircsInstance }
    ::= { iasRemoteAccountingServersTable 1 }

IASRemoteAccountingServersEntry ::= SEQUENCE {
    ircsInstance InstanceName,
    ircsAccountingRequests Gauge32,
    ircsAccountingRequestsPerSec Gauge32,
    ircsAccountingResponses Gauge32,
    ircsAccountingResponsesPerSec Gauge32,
    ircsBadAuthenticators Gauge32,
    ircsBadAuthenticatorsPerSec Gauge32,
    ircsDroppedPackets Gauge32,
    ircsDroppedPacketsPerSec Gauge32,
    ircsLastRoundTripTime Gauge32,
    ircsMalformedPackets Gauge32,
    ircsMalformedPacketsPerSec Gauge32,
    ircsPacketsReceived Gauge32,
    ircsPacketsReceivedPerSec Gauge32,
    ircsPendingRequests Gauge32,
    ircsPortNumber Gauge32,
    ircsRequestTimeouts Gauge32,
    ircsRequestTimeoutsPerSec Gauge32,
    ircsRetransmissions Gauge32,
    ircsRetransmissionsPerSec Gauge32,
    ircsUnknownType Gauge32,
    ircsUnknownTypePerSec Gauge32
}

ircsInstance OBJECT-TYPE
    SYNTAX     InstanceName
    MAX-ACCESS read-only
    STATUS     current
    DESCRIPTION
	    "Instance name."
    ::= { iasRemoteAccountingServersEntry 1 }

ircsAccountingRequests OBJECT-TYPE
    SYNTAX     Gauge32
    MAX-ACCESS read-only
    STATUS     current
    DESCRIPTION
	    "The number of RADIUS Accounting-Request
	    packets received on the accounting port."
    ::= { iasRemoteAccountingServersEntry 2 }

ircsAccountingRequestsPerSec OBJECT-TYPE
    SYNTAX     Gauge32
    MAX-ACCESS read-only
    STATUS     current
    DESCRIPTION
	    "The average number of RADIUS
	    Accounting-Requests received per second on the
	    accounting port."
    ::= { iasRemoteAccountingServersEntry 3 }

ircsAccountingResponses OBJECT-TYPE
    SYNTAX     Gauge32
    MAX-ACCESS read-only
    STATUS     current
    DESCRIPTION
	    "The number of RADIUS Accounting-Response
	    packets sent from this IAS server."
    ::= { iasRemoteAccountingServersEntry 4 }

ircsAccountingResponsesPerSec OBJECT-TYPE
    SYNTAX     Gauge32
    MAX-ACCESS read-only
    STATUS     current
    DESCRIPTION
	    "The average number of RADIUS
	    Accounting-Responses sent per second."
    ::= { iasRemoteAccountingServersEntry 5 }

ircsBadAuthenticators OBJECT-TYPE
    SYNTAX     Gauge32
    MAX-ACCESS read-only
    STATUS     current
    DESCRIPTION
	    "The number of RADIUS packets that contain an
	    invalid Message Authenticator attribute."
    ::= { iasRemoteAccountingServersEntry 6 }

ircsBadAuthenticatorsPerSec OBJECT-TYPE
    SYNTAX     Gauge32
    MAX-ACCESS read-only
    STATUS     current
    DESCRIPTION
	    "The average number of RADIUS packets  per
	    second that contain an invalid Message
	    Authenticator attribute."
    ::= { iasRemoteAccountingServersEntry 7 }

ircsDroppedPackets OBJECT-TYPE
    SYNTAX     Gauge32
    MAX-ACCESS read-only
    STATUS     current
    DESCRIPTION
	    "The number of incoming packets that are
	    silently discarded for a reason other than
	    'malformed,' 'invalid Message Authenticator,'
	    or 'unknown type'."
    ::= { iasRemoteAccountingServersEntry 8 }

ircsDroppedPacketsPerSec OBJECT-TYPE
    SYNTAX     Gauge32
    MAX-ACCESS read-only
    STATUS     current
    DESCRIPTION
	    "The average number of incoming packets per
	    second that are silently discarded for a reason
	    other than 'malformed,' 'invalid Message
	    Authenticator,' or 'unknown type'."
    ::= { iasRemoteAccountingServersEntry 9 }

ircsLastRoundTripTime OBJECT-TYPE
    SYNTAX     Gauge32
    MAX-ACCESS read-only
    STATUS     current
    DESCRIPTION
	    "The interval (in hundredths of a second)
	    between the most recent request from a remote
	    IAS server and its response."
    ::= { iasRemoteAccountingServersEntry 10 }

ircsMalformedPackets OBJECT-TYPE
    SYNTAX     Gauge32
    MAX-ACCESS read-only
    STATUS     current
    DESCRIPTION
	    "The number of packets containing malformed
	    data received."
    ::= { iasRemoteAccountingServersEntry 11 }

ircsMalformedPacketsPerSec OBJECT-TYPE
    SYNTAX     Gauge32
    MAX-ACCESS read-only
    STATUS     current
    DESCRIPTION
	    "The average number of packets containing
	    malformed data received per second."
    ::= { iasRemoteAccountingServersEntry 12 }

ircsPacketsReceived OBJECT-TYPE
    SYNTAX     Gauge32
    MAX-ACCESS read-only
    STATUS     current
    DESCRIPTION
	    "The number of packets received."
    ::= { iasRemoteAccountingServersEntry 13 }

ircsPacketsReceivedPerSec OBJECT-TYPE
    SYNTAX     Gauge32
    MAX-ACCESS read-only
    STATUS     current
    DESCRIPTION
	    "The average number of packets received per
	    second."
    ::= { iasRemoteAccountingServersEntry 14 }

ircsPendingRequests OBJECT-TYPE
    SYNTAX     Gauge32
    MAX-ACCESS read-only
    STATUS     current
    DESCRIPTION
	    "The number of requests destined for this
	    server that have not yet timed out or received
	    a response."
    ::= { iasRemoteAccountingServersEntry 15 }

ircsPortNumber OBJECT-TYPE
    SYNTAX     Gauge32
    MAX-ACCESS read-only
    STATUS     current
    DESCRIPTION
	    "The UDP port the proxy is using to send
	    requests to this server."
    ::= { iasRemoteAccountingServersEntry 16 }

ircsRequestTimeouts OBJECT-TYPE
    SYNTAX     Gauge32
    MAX-ACCESS read-only
    STATUS     current
    DESCRIPTION
	    "The number of request timeouts to this
	    server."
    ::= { iasRemoteAccountingServersEntry 17 }

ircsRequestTimeoutsPerSec OBJECT-TYPE
    SYNTAX     Gauge32
    MAX-ACCESS read-only
    STATUS     current
    DESCRIPTION
	    "The average number of request timeouts per
	    second to this server."
    ::= { iasRemoteAccountingServersEntry 18 }

ircsRetransmissions OBJECT-TYPE
    SYNTAX     Gauge32
    MAX-ACCESS read-only
    STATUS     current
    DESCRIPTION
	    "The number of requests retransmitted to this
	    server."
    ::= { iasRemoteAccountingServersEntry 19 }

ircsRetransmissionsPerSec OBJECT-TYPE
    SYNTAX     Gauge32
    MAX-ACCESS read-only
    STATUS     current
    DESCRIPTION
	    "The average number of requests retransmitted
	    per second to this server."
    ::= { iasRemoteAccountingServersEntry 20 }

ircsUnknownType OBJECT-TYPE
    SYNTAX     Gauge32
    MAX-ACCESS read-only
    STATUS     current
    DESCRIPTION
	    "The number of unknown type (non-RADIUS)
	    packets received."
    ::= { iasRemoteAccountingServersEntry 21 }

ircsUnknownTypePerSec OBJECT-TYPE
    SYNTAX     Gauge32
    MAX-ACCESS read-only
    STATUS     current
    DESCRIPTION
	    "The average number of unknown type
	    (non-RADIUS) packets received per second. "
    ::= { iasRemoteAccountingServersEntry 22 }

iasRemoteAuthenticationSrvrTable OBJECT-TYPE
    SYNTAX     SEQUENCE OF IASRemoteAuthenticationServers
    MAX-ACCESS not-accessible
    STATUS     current
    DESCRIPTION
	    "A table containing performance information for
	    instances of 'IAS Remote Authentication
	    Servers' objects."
    ::= { advanced 32 }

iasRemoteAuthenticationSrvrEntry OBJECT-TYPE
    SYNTAX     IASRemoteAuthenticationServers
    MAX-ACCESS not-accessible
    STATUS     current
    DESCRIPTION
	    "Performance information for one particular
	    instance of 'IAS Remote Authentication Servers'
	    object."
    INDEX      { irusInstance }
    ::= { iasRemoteAuthenticationSrvrTable 1 }

IASRemoteAuthenticationServers ::= SEQUENCE {
    irusInstance InstanceName,
    irusAccessAccepts Gauge32,
    irusAccessAcceptsPerSec Gauge32,
    irusAccessChallenges Gauge32,
    irusAccessChallengesPerSec Gauge32,
    irusAccessRejects Gauge32,
    irusAccessRejectsPerSec Gauge32,
    irusAccessRequests Gauge32,
    irusAccessRequestsPerSec Gauge32,
    irusBadAuthenticators Gauge32,
    irusBadAuthenticatorsPerSec Gauge32,
    irusDroppedPackets Gauge32,
    irusDroppedPacketsPerSec Gauge32,
    irusLastRoundTripTime Gauge32,
    irusMalformedPackets Gauge32,
    irusMalformedPacketsPerSec Gauge32,
    irusPacketsReceived Gauge32,
    irusPacketsReceivedPerSec Gauge32,
    irusPendingRequests Gauge32,
    irusPortNumber Gauge32,
    irusRequestTimeouts Gauge32,
    irusRequestTimeoutsPerSec Gauge32,
    irusRetransmissions Gauge32,
    irusRetransmissionsPerSec Gauge32,
    irusUnknownType Gauge32,
    irusUnknownTypePerSec Gauge32
}

irusInstance OBJECT-TYPE
    SYNTAX     InstanceName
    MAX-ACCESS read-only
    STATUS     current
    DESCRIPTION
	    "Instance name."
    ::= { iasRemoteAuthenticationSrvrEntry 1 }

irusAccessAccepts OBJECT-TYPE
    SYNTAX     Gauge32
    MAX-ACCESS read-only
    STATUS     current
    DESCRIPTION
	    "The number of RADIUS Access-Accept packets
	    sent."
    ::= { iasRemoteAuthenticationSrvrEntry 2 }

irusAccessAcceptsPerSec OBJECT-TYPE
    SYNTAX     Gauge32
    MAX-ACCESS read-only
    STATUS     current
    DESCRIPTION
	    "The average number of RADIUS Access-Accept
	    packets per second sent."
    ::= { iasRemoteAuthenticationSrvrEntry 3 }

irusAccessChallenges OBJECT-TYPE
    SYNTAX     Gauge32
    MAX-ACCESS read-only
    STATUS     current
    DESCRIPTION
	    "The number of RADIUS Access-Challenge packets
	    sent."
    ::= { iasRemoteAuthenticationSrvrEntry 4 }

irusAccessChallengesPerSec OBJECT-TYPE
    SYNTAX     Gauge32
    MAX-ACCESS read-only
    STATUS     current
    DESCRIPTION
	    "The average number of RADIUS Access-Challenge
	    packets per second sent."
    ::= { iasRemoteAuthenticationSrvrEntry 5 }

irusAccessRejects OBJECT-TYPE
    SYNTAX     Gauge32
    MAX-ACCESS read-only
    STATUS     current
    DESCRIPTION
	    "The number of RADIUS Access-Reject packets
	    sent to this client."
    ::= { iasRemoteAuthenticationSrvrEntry 6 }

irusAccessRejectsPerSec OBJECT-TYPE
    SYNTAX     Gauge32
    MAX-ACCESS read-only
    STATUS     current
    DESCRIPTION
	    "The average number of RADIUS Access-Reject
	    packets per second sent."
    ::= { iasRemoteAuthenticationSrvrEntry 7 }

irusAccessRequests OBJECT-TYPE
    SYNTAX     Gauge32
    MAX-ACCESS read-only
    STATUS     current
    DESCRIPTION
	    "The number of packets received on the
	    authentication port."
    ::= { iasRemoteAuthenticationSrvrEntry 8 }

irusAccessRequestsPerSec OBJECT-TYPE
    SYNTAX     Gauge32
    MAX-ACCESS read-only
    STATUS     current
    DESCRIPTION
	    "The average number of packets per second
	    received on the authentication port."
    ::= { iasRemoteAuthenticationSrvrEntry 9 }

irusBadAuthenticators OBJECT-TYPE
    SYNTAX     Gauge32
    MAX-ACCESS read-only
    STATUS     current
    DESCRIPTION
	    "The number of RADIUS packets that contain an
	    invalid Message Authenticator attribute."
    ::= { iasRemoteAuthenticationSrvrEntry 10 }

irusBadAuthenticatorsPerSec OBJECT-TYPE
    SYNTAX     Gauge32
    MAX-ACCESS read-only
    STATUS     current
    DESCRIPTION
	    "The average number of RADIUS packets  per
	    second that contain an invalid Message
	    Authenticator attribute."
    ::= { iasRemoteAuthenticationSrvrEntry 11 }

irusDroppedPackets OBJECT-TYPE
    SYNTAX     Gauge32
    MAX-ACCESS read-only
    STATUS     current
    DESCRIPTION
	    "The number of incoming packets that are
	    silently discarded for a reason other than
	    'malformed,' 'invalid Message Authenticator,'
	    or 'unknown type'."
    ::= { iasRemoteAuthenticationSrvrEntry 12 }

irusDroppedPacketsPerSec OBJECT-TYPE
    SYNTAX     Gauge32
    MAX-ACCESS read-only
    STATUS     current
    DESCRIPTION
	    "The average number of incoming packets per
	    second that are silently discarded for a reason
	    other than 'malformed,' 'invalid Message
	    Authenticator,' or 'unknown type'."
    ::= { iasRemoteAuthenticationSrvrEntry 13 }

irusLastRoundTripTime OBJECT-TYPE
    SYNTAX     Gauge32
    MAX-ACCESS read-only
    STATUS     current
    DESCRIPTION
	    "The interval (in hundredths of a second)
	    between the most recent request from a remote
	    IAS server and its response."
    ::= { iasRemoteAuthenticationSrvrEntry 14 }

irusMalformedPackets OBJECT-TYPE
    SYNTAX     Gauge32
    MAX-ACCESS read-only
    STATUS     current
    DESCRIPTION
	    "The number of packets containing malformed
	    data received."
    ::= { iasRemoteAuthenticationSrvrEntry 15 }

irusMalformedPacketsPerSec OBJECT-TYPE
    SYNTAX     Gauge32
    MAX-ACCESS read-only
    STATUS     current
    DESCRIPTION
	    "The average number of packets containing
	    malformed data received per second."
    ::= { iasRemoteAuthenticationSrvrEntry 16 }

irusPacketsReceived OBJECT-TYPE
    SYNTAX     Gauge32
    MAX-ACCESS read-only
    STATUS     current
    DESCRIPTION
	    "The number of packets received."
    ::= { iasRemoteAuthenticationSrvrEntry 17 }

irusPacketsReceivedPerSec OBJECT-TYPE
    SYNTAX     Gauge32
    MAX-ACCESS read-only
    STATUS     current
    DESCRIPTION
	    "The average number of packets received per
	    second."
    ::= { iasRemoteAuthenticationSrvrEntry 18 }

irusPendingRequests OBJECT-TYPE
    SYNTAX     Gauge32
    MAX-ACCESS read-only
    STATUS     current
    DESCRIPTION
	    "The number of requests destined for this
	    server that have not yet timed out or received
	    a response."
    ::= { iasRemoteAuthenticationSrvrEntry 19 }

irusPortNumber OBJECT-TYPE
    SYNTAX     Gauge32
    MAX-ACCESS read-only
    STATUS     current
    DESCRIPTION
	    "The UDP port the proxy is using to send
	    requests to this server."
    ::= { iasRemoteAuthenticationSrvrEntry 20 }

irusRequestTimeouts OBJECT-TYPE
    SYNTAX     Gauge32
    MAX-ACCESS read-only
    STATUS     current
    DESCRIPTION
	    "The number of request timeouts to this
	    server."
    ::= { iasRemoteAuthenticationSrvrEntry 21 }

irusRequestTimeoutsPerSec OBJECT-TYPE
    SYNTAX     Gauge32
    MAX-ACCESS read-only
    STATUS     current
    DESCRIPTION
	    "The average number of request timeouts per
	    second to this server."
    ::= { iasRemoteAuthenticationSrvrEntry 22 }

irusRetransmissions OBJECT-TYPE
    SYNTAX     Gauge32
    MAX-ACCESS read-only
    STATUS     current
    DESCRIPTION
	    "The number of requests retransmitted to this
	    server."
    ::= { iasRemoteAuthenticationSrvrEntry 23 }

irusRetransmissionsPerSec OBJECT-TYPE
    SYNTAX     Gauge32
    MAX-ACCESS read-only
    STATUS     current
    DESCRIPTION
	    "The average number of requests retransmitted
	    per second to this server."
    ::= { iasRemoteAuthenticationSrvrEntry 24 }

irusUnknownType OBJECT-TYPE
    SYNTAX     Gauge32
    MAX-ACCESS read-only
    STATUS     current
    DESCRIPTION
	    "The number of unknown type (non-RADIUS)
	    packets received."
    ::= { iasRemoteAuthenticationSrvrEntry 25 }

irusUnknownTypePerSec OBJECT-TYPE
    SYNTAX     Gauge32
    MAX-ACCESS read-only
    STATUS     current
    DESCRIPTION
	    "The average number of unknown type
	    (non-RADIUS) packets received per second. "
    ::= { iasRemoteAuthenticationSrvrEntry 26 }

icmpV4 OBJECT-IDENTITY
    STATUS     current
    DESCRIPTION
	    "The ICMP performance object consists of
	    counters that measure the rates at which
	    Internet Control Message Protocol (ICMP)
	    messages are sent and received by using the
	    ICMP protocol. It also includes counters that
	    monitor ICMP protocol errors."
    ::= { advanced 33 }

icmpV4MessagesOutboundErrors OBJECT-TYPE
    SYNTAX     Gauge32
    MAX-ACCESS read-only
    STATUS     current
    DESCRIPTION
	    "Messages Outbound Errors is the number of ICMP
	    messages that this entity did not send due to
	    problems discovered within	ICMP such as lack
	    of buffers.  This value does not include errors
	    discovered outside the ICMP layer, such as
	    those recording the failure of IP to route the
	    resultant datagram.  In some implementations,
	    none of the error types are included in the
	    value of this counter."
    ::= { icmpV4 1 }

icmpV4MessagesReceivedErrors OBJECT-TYPE
    SYNTAX     Gauge32
    MAX-ACCESS read-only
    STATUS     current
    DESCRIPTION
	    "Messages Received Errors is the number of ICMP
	    messages that the entity received but
	    determined as having errors (bad ICMP
	    checksums, bad length, etc).."
    ::= { icmpV4 2 }

icmpV4MessagesReceivedPerSec OBJECT-TYPE
    SYNTAX     Gauge32
    MAX-ACCESS read-only
    STATUS     current
    DESCRIPTION
	    "Messages Received/sec is the rate at which
	    ICMP messages are received by the entity.  The
	    rate includes those messages received in
	    error."
    ::= { icmpV4 3 }

icmpV4MessagesSentPerSec OBJECT-TYPE
    SYNTAX     Gauge32
    MAX-ACCESS read-only
    STATUS     current
    DESCRIPTION
	    "Messages Sent/sec is the rate at which ICMP
	    messages are attempted to be sent by the
	    entity.  The rate includes those messages sent
	    in error."
    ::= { icmpV4 4 }

icmpV4MessagesPerSec OBJECT-TYPE
    SYNTAX     Gauge32
    MAX-ACCESS read-only
    STATUS     current
    DESCRIPTION
	    "Messages/sec is the total rate at which ICMP
	    messages are sent and received by the entity. 
	    The rate includes those messages received or
	    sent in error."
    ::= { icmpV4 5 }

icmpV4RcvdAddressMask OBJECT-TYPE
    SYNTAX     Gauge32
    MAX-ACCESS read-only
    STATUS     current
    DESCRIPTION
	    "Received Address Mask is the number of ICMP
	    Address Mask Request messages received."
    ::= { icmpV4 6 }

icmpV4RcvdAddressMaskReply OBJECT-TYPE
    SYNTAX     Gauge32
    MAX-ACCESS read-only
    STATUS     current
    DESCRIPTION
	    "Received Address Mask Reply is the number of
	    ICMP Address Mask Reply messages received."
    ::= { icmpV4 7 }

icmpV4RcvdDestUnreachable OBJECT-TYPE
    SYNTAX     Gauge32
    MAX-ACCESS read-only
    STATUS     current
    DESCRIPTION
	    "Received Destination Unreachable is the number
	    of ICMP Destination Unreachable messages
	    received."
    ::= { icmpV4 8 }

icmpV4RcvdEchoReplyPerSec OBJECT-TYPE
    SYNTAX     Gauge32
    MAX-ACCESS read-only
    STATUS     current
    DESCRIPTION
	    "Received Echo Reply/sec is the rate of ICMP
	    Echo Reply messages received."
    ::= { icmpV4 9 }

icmpV4RcvdEchoPerSec OBJECT-TYPE
    SYNTAX     Gauge32
    MAX-ACCESS read-only
    STATUS     current
    DESCRIPTION
	    "Received Echo/sec is the rate of ICMP Echo
	    messages received."
    ::= { icmpV4 10 }

icmpV4RcvdParameterProblem OBJECT-TYPE
    SYNTAX     Gauge32
    MAX-ACCESS read-only
    STATUS     current
    DESCRIPTION
	    "Received Parameter Problem is the number of
	    ICMP Parameter Problem messages received."
    ::= { icmpV4 11 }

icmpV4RcvdRedirectPerSec OBJECT-TYPE
    SYNTAX     Gauge32
    MAX-ACCESS read-only
    STATUS     current
    DESCRIPTION
	    "Received Redirect/sec is the rate of ICMP
	    Redirect messages received."
    ::= { icmpV4 12 }

icmpV4RcvdSourceQuench OBJECT-TYPE
    SYNTAX     Gauge32
    MAX-ACCESS read-only
    STATUS     current
    DESCRIPTION
	    "Received Source Quench is the number of ICMP
	    Source Quench messages received."
    ::= { icmpV4 13 }

icmpV4RcvdTimeExceeded OBJECT-TYPE
    SYNTAX     Gauge32
    MAX-ACCESS read-only
    STATUS     current
    DESCRIPTION
	    "Received Time Exceeded is the number of ICMP
	    Time Exceeded messages received."
    ::= { icmpV4 14 }

icmpV4RcvdTimestampReplyPerSec OBJECT-TYPE
    SYNTAX     Gauge32
    MAX-ACCESS read-only
    STATUS     current
    DESCRIPTION
	    "Received Timestamp Reply/sec is the rate of
	    ICMP Timestamp Reply messages received."
    ::= { icmpV4 15 }

icmpV4RcvdTimestampPerSec OBJECT-TYPE
    SYNTAX     Gauge32
    MAX-ACCESS read-only
    STATUS     current
    DESCRIPTION
	    "Received Timestamp/sec is the rate of ICMP
	    Timestamp (request) messages received."
    ::= { icmpV4 16 }

icmpV4SentAddressMask OBJECT-TYPE
    SYNTAX     Gauge32
    MAX-ACCESS read-only
    STATUS     current
    DESCRIPTION
	    "Sent Address Mask is the number of ICMP
	    Address Mask Request messages sent."
    ::= { icmpV4 17 }

icmpV4SentAddressMaskReply OBJECT-TYPE
    SYNTAX     Gauge32
    MAX-ACCESS read-only
    STATUS     current
    DESCRIPTION
	    "Sent Address Mask Reply is the number of ICMP
	    Address Mask Reply messages sent."
    ::= { icmpV4 18 }

icmpV4SentDestinationUnreachable OBJECT-TYPE
    SYNTAX     Gauge32
    MAX-ACCESS read-only
    STATUS     current
    DESCRIPTION
	    "Sent Destination Unreachable is the number of
	    ICMP Destination Unreachable messages sent."
    ::= { icmpV4 19 }

icmpV4SentEchoReplyPerSec OBJECT-TYPE
    SYNTAX     Gauge32
    MAX-ACCESS read-only
    STATUS     current
    DESCRIPTION
	    "Sent Echo Reply/sec is the rate of ICMP Echo
	    Reply messages sent."
    ::= { icmpV4 20 }

icmpV4SentEchoPerSec OBJECT-TYPE
    SYNTAX     Gauge32
    MAX-ACCESS read-only
    STATUS     current
    DESCRIPTION
	    "Sent Echo/sec is the rate of ICMP Echo
	    messages sent."
    ::= { icmpV4 21 }

icmpV4SentParameterProblem OBJECT-TYPE
    SYNTAX     Gauge32
    MAX-ACCESS read-only
    STATUS     current
    DESCRIPTION
	    "Sent Parameter Problem is the number of ICMP
	    Parameter Problem messages sent."
    ::= { icmpV4 22 }

icmpV4SentRedirectPerSec OBJECT-TYPE
    SYNTAX     Gauge32
    MAX-ACCESS read-only
    STATUS     current
    DESCRIPTION
	    "Sent Redirect/sec is the rate of ICMP Redirect
	    messages sent."
    ::= { icmpV4 23 }

icmpV4SentSourceQuench OBJECT-TYPE
    SYNTAX     Gauge32
    MAX-ACCESS read-only
    STATUS     current
    DESCRIPTION
	    "Sent Source Quench is the number of ICMP
	    Source Quench messages sent."
    ::= { icmpV4 24 }

icmpV4SentTimeExceeded OBJECT-TYPE
    SYNTAX     Gauge32
    MAX-ACCESS read-only
    STATUS     current
    DESCRIPTION
	    "Sent Time Exceeded is the number of ICMP Time
	    Exceeded messages sent."
    ::= { icmpV4 25 }

icmpV4SentTimestampReplyPerSec OBJECT-TYPE
    SYNTAX     Gauge32
    MAX-ACCESS read-only
    STATUS     current
    DESCRIPTION
	    "Sent Timestamp Reply/sec is the rate of ICMP
	    Timestamp Reply messages sent."
    ::= { icmpV4 26 }

icmpV4SentTimestampPerSec OBJECT-TYPE
    SYNTAX     Gauge32
    MAX-ACCESS read-only
    STATUS     current
    DESCRIPTION
	    "Sent Timestamp/sec is the rate of ICMP
	    Timestamp (request) messages sent."
    ::= { icmpV4 27 }

icmpV6 OBJECT IDENTIFIER
    ::= { advanced 34 }

icmpV6MessagesOutboundErrors OBJECT-TYPE
    SYNTAX     Gauge32
    MAX-ACCESS read-only
    STATUS     current
    DESCRIPTION
	    "Messages Outbound Errors is the number of ICMP
	    messages that were not send due to problems
	    within ICMP, such as lack of buffers.  This
	    value does not include errors discovered
	    outside the ICMP layer, such as those recording
	    the failure of IP to route the resultant
	    datagram.  In some implementations, none of the
	    error types are included in the value of this
	    counter."
    ::= { icmpV6 1 }

icmpV6MessagesReceivedErrors OBJECT-TYPE
    SYNTAX     Gauge32
    MAX-ACCESS read-only
    STATUS     current
    DESCRIPTION
	    "Messages Received Errors is the number of ICMP
	    messages that the entity received but had
	    errors, such as bad ICMP checksums, bad length,
	    etc."
    ::= { icmpV6 2 }

icmpV6MessagesReceivedPerSec OBJECT-TYPE
    SYNTAX     Gauge32
    MAX-ACCESS read-only
    STATUS     current
    DESCRIPTION
	    "Messages Received/sec is the rate, in
	    incidents per second at which ICMP messages
	    were received. The rate includes messages
	    received in error."
    ::= { icmpV6 3 }

icmpV6MessagesSentPerSec OBJECT-TYPE
    SYNTAX     Gauge32
    MAX-ACCESS read-only
    STATUS     current
    DESCRIPTION
	    "Messages Sent/sec is the rate, in incidents
	    per second, at which the server attempted to
	    send. The rate includes those messages sent in
	    error."
    ::= { icmpV6 4 }

icmpV6MessagesPerSec OBJECT-TYPE
    SYNTAX     Gauge32
    MAX-ACCESS read-only
    STATUS     current
    DESCRIPTION
	    "Messages/sec is the total rate, in incidents
	    per second, at which ICMP messages were sent
	    and received by the entity. The rate includes
	    messages received or sent in error."
    ::= { icmpV6 5 }

icmpV6ReceivedDestUnreachable OBJECT-TYPE
    SYNTAX     Gauge32
    MAX-ACCESS read-only
    STATUS     current
    DESCRIPTION
	    "Received Destination Unreachable is the number
	    of ICMP Destination Unreachable messages
	    received."
    ::= { icmpV6 6 }

icmpV6ReceivedEchoReplyPerSec OBJECT-TYPE
    SYNTAX     Gauge32
    MAX-ACCESS read-only
    STATUS     current
    DESCRIPTION
	    "Received Echo Reply/sec is the rate, in
	    incidents per second, at which ICMP Echo Reply
	    messages were received."
    ::= { icmpV6 7 }

icmpV6ReceivedEchoPerSec OBJECT-TYPE
    SYNTAX     Gauge32
    MAX-ACCESS read-only
    STATUS     current
    DESCRIPTION
	    "Received Echo/sec is the rate, in incidents
	    per second, at which ICMP Echo messages were
	    received."
    ::= { icmpV6 8 }

icmpV6ReceivedMembershipQuery OBJECT-TYPE
    SYNTAX     Gauge32
    MAX-ACCESS read-only
    STATUS     current
    DESCRIPTION
	    "Received Membership Query is the number of
	    packets received thatquery their membership to
	    a group."
    ::= { icmpV6 9 }

icmpV6ReceivedMembershipReduct OBJECT-TYPE
    SYNTAX     Gauge32
    MAX-ACCESS read-only
    STATUS     current
    DESCRIPTION
	    "Received Membership Reduction is the number of
	    packets received thatcancelled their membership
	    to a group."
    ::= { icmpV6 10 }

icmpV6ReceivedMembershipReport OBJECT-TYPE
    SYNTAX     Gauge32
    MAX-ACCESS read-only
    STATUS     current
    DESCRIPTION
	    "Received Membership Report is the number of
	    packets received thatreport their membership to
	    a group."
    ::= { icmpV6 11 }

icmpV6ReceivedNeighborAdvert OBJECT-TYPE
    SYNTAX     Gauge32
    MAX-ACCESS read-only
    STATUS     current
    DESCRIPTION
	    "Received Neighbor Advert is the number of
	    packets received thatadvert a neighbor."
    ::= { icmpV6 12 }

icmpV6ReceivedNeighborSolicit OBJECT-TYPE
    SYNTAX     Gauge32
    MAX-ACCESS read-only
    STATUS     current
    DESCRIPTION
	    "Received Neighbor Solicit is the number of
	    packets received thatsolicit a neighbor."
    ::= { icmpV6 13 }

icmpV6ReceivedPacketTooBig OBJECT-TYPE
    SYNTAX     Gauge32
    MAX-ACCESS read-only
    STATUS     current
    DESCRIPTION
	    "Received Packet Too Big is the number of
	    received packets thatare larger than
	    anticipated."
    ::= { icmpV6 14 }

icmpV6ReceivedParameterProblem OBJECT-TYPE
    SYNTAX     Gauge32
    MAX-ACCESS read-only
    STATUS     current
    DESCRIPTION
	    "Received Parameter Problem is the number of
	    ICMP Parameter Problem messages received."
    ::= { icmpV6 15 }

icmpV6ReceivedRedirectPerSec OBJECT-TYPE
    SYNTAX     Gauge32
    MAX-ACCESS read-only
    STATUS     current
    DESCRIPTION
	    "Received Redirect/sec is the rate, in
	    incidents per second, at which ICMP Redirect
	    messages were received."
    ::= { icmpV6 16 }

icmpV6ReceivedRouterAdvert OBJECT-TYPE
    SYNTAX     Gauge32
    MAX-ACCESS read-only
    STATUS     current
    DESCRIPTION
	    "Received Router Advert is the number of
	    packets received thatadvert the router."
    ::= { icmpV6 17 }

icmpV6ReceivedRouterSolicit OBJECT-TYPE
    SYNTAX     Gauge32
    MAX-ACCESS read-only
    STATUS     current
    DESCRIPTION
	    "Received Router Solicit is the number of
	    packets received thatsolicit the router."
    ::= { icmpV6 18 }

icmpV6ReceivedTimeExceeded OBJECT-TYPE
    SYNTAX     Gauge32
    MAX-ACCESS read-only
    STATUS     current
    DESCRIPTION
	    "Received Time Exceeded is the number of ICMP
	    Time Exceeded messages received."
    ::= { icmpV6 19 }

icmpV6SentDestinationUnreachable OBJECT-TYPE
    SYNTAX     Gauge32
    MAX-ACCESS read-only
    STATUS     current
    DESCRIPTION
	    "Sent Destination Unreachable is the number of
	    ICMP Destination Unreachable messages sent."
    ::= { icmpV6 20 }

icmpV6SentEchoReplyPerSec OBJECT-TYPE
    SYNTAX     Gauge32
    MAX-ACCESS read-only
    STATUS     current
    DESCRIPTION
	    "Sent Echo Reply/sec is the rate, in incidents
	    per second, at which ICMP Echo Reply messages
	    were sent."
    ::= { icmpV6 21 }

icmpV6SentEchoPerSec OBJECT-TYPE
    SYNTAX     Gauge32
    MAX-ACCESS read-only
    STATUS     current
    DESCRIPTION
	    "Sent Echo/sec is the rate of ICMP Echo
	    messages sent."
    ::= { icmpV6 22 }

icmpV6SentMembershipQuery OBJECT-TYPE
    SYNTAX     Gauge32
    MAX-ACCESS read-only
    STATUS     current
    DESCRIPTION
	    "Sent Membership Query is the number of packets
	    sent thatquery their membership to a group."
    ::= { icmpV6 23 }

icmpV6SentMembershipReduction OBJECT-TYPE
    SYNTAX     Gauge32
    MAX-ACCESS read-only
    STATUS     current
    DESCRIPTION
	    "Sent Membership Reduction is the number of
	    packets sent thatcancelled their membership to
	    a group."
    ::= { icmpV6 24 }

icmpV6SentMembershipReport OBJECT-TYPE
    SYNTAX     Gauge32
    MAX-ACCESS read-only
    STATUS     current
    DESCRIPTION
	    "Sent Membership Report is the number of
	    packets sent thatreport their membership to a
	    group."
    ::= { icmpV6 25 }

icmpV6SentNeighborAdvert OBJECT-TYPE
    SYNTAX     Gauge32
    MAX-ACCESS read-only
    STATUS     current
    DESCRIPTION
	    "Sent Neighbor Advert is the number of packets
	    sent thatadvert a neighbor."
    ::= { icmpV6 26 }

icmpV6SentNeighborSolicit OBJECT-TYPE
    SYNTAX     Gauge32
    MAX-ACCESS read-only
    STATUS     current
    DESCRIPTION
	    "Sent Neighbor Solicit is the number of packets
	    sent thatsolicit a neighbor."
    ::= { icmpV6 27 }

icmpV6SentPacketTooBig OBJECT-TYPE
    SYNTAX     Gauge32
    MAX-ACCESS read-only
    STATUS     current
    DESCRIPTION
	    "Sent Packet Too Big is the number of sent
	    packets thatare larger than anticipated."
    ::= { icmpV6 28 }

icmpV6SentParameterProblem OBJECT-TYPE
    SYNTAX     Gauge32
    MAX-ACCESS read-only
    STATUS     current
    DESCRIPTION
	    "Sent Parameter Problem is the number of ICMP
	    Parameter Problem messages sent."
    ::= { icmpV6 29 }

icmpV6SentRedirectPerSec OBJECT-TYPE
    SYNTAX     Gauge32
    MAX-ACCESS read-only
    STATUS     current
    DESCRIPTION
	    "Sent Redirect/sec is the rate, in incidents
	    per second, at which ICMP Redirect messages
	    were sent."
    ::= { icmpV6 30 }

icmpV6SentRouterAdvert OBJECT-TYPE
    SYNTAX     Gauge32
    MAX-ACCESS read-only
    STATUS     current
    DESCRIPTION
	    "Sent Router Advert is the number of packets
	    sent thatadvert the router."
    ::= { icmpV6 31 }

icmpV6SentRouterSolicit OBJECT-TYPE
    SYNTAX     Gauge32
    MAX-ACCESS read-only
    STATUS     current
    DESCRIPTION
	    "Sent Router Solicit is the number of packets
	    sent thatsolicit the router."
    ::= { icmpV6 32 }

icmpV6SentTimeExceeded OBJECT-TYPE
    SYNTAX     Gauge32
    MAX-ACCESS read-only
    STATUS     current
    DESCRIPTION
	    "Sent Time Exceeded is the number of ICMP Time
	    Exceeded messages sent."
    ::= { icmpV6 33 }

indexingServiceTable OBJECT-TYPE
    SYNTAX     SEQUENCE OF IndexingServiceEntry
    MAX-ACCESS not-accessible
    STATUS     current
    DESCRIPTION
	    "The Indexing Service performance object
	    counters report statistics pertaining to the
	    creation of indexes and the merging and
	    querying of indexes by Indexing Service."
    ::= { advanced 35 }

indexingServiceEntry OBJECT-TYPE
    SYNTAX     IndexingServiceEntry
    MAX-ACCESS not-accessible
    STATUS     current
    DESCRIPTION
	    "Performance information for one particular
	    instance of 'Indexing Service' object."
    INDEX      { idxSvcInstance }
    ::= { indexingServiceTable 1 }

IndexingServiceEntry ::= SEQUENCE {
    idxSvcInstance InstanceName,
    idxSvcNumDocumentsIndexed Gauge32,
    idxSvcDeferredForIndexing Gauge32,
    idxSvcFilesToBeIndexed Gauge32,
    idxSvcIndexSizeMB Gauge32,
    idxSvcMergeProgress Gauge32,
    idxSvcRunningQueries Gauge32,
    idxSvcSavedIndexes Gauge32,
    idxSvcTotalNumDocuments Gauge32,
    idxSvcTotalNumOfQueries Gauge32,
    idxSvcUniqueKeys Gauge32,
    idxSvcWordLists Gauge32
}

idxSvcInstance OBJECT-TYPE
    SYNTAX     InstanceName
    MAX-ACCESS read-only
    STATUS     current
    DESCRIPTION
	    "Instance name."
    ::= { indexingServiceEntry 1 }

idxSvcNumDocumentsIndexed OBJECT-TYPE
    SYNTAX     Gauge32
    MAX-ACCESS read-only
    STATUS     current
    DESCRIPTION
	    "Number of documents indexed since the index
	    was mounted."
    ::= { indexingServiceEntry 2 }

idxSvcDeferredForIndexing OBJECT-TYPE
    SYNTAX     Gauge32
    MAX-ACCESS read-only
    STATUS     current
    DESCRIPTION
	    "Number of files not available and deferred for
	    indexing."
    ::= { indexingServiceEntry 3 }

idxSvcFilesToBeIndexed OBJECT-TYPE
    SYNTAX     Gauge32
    MAX-ACCESS read-only
    STATUS     current
    DESCRIPTION
	    "Number of files to be filtered and added to
	    the index."
    ::= { indexingServiceEntry 4 }

idxSvcIndexSizeMB OBJECT-TYPE
    SYNTAX     Gauge32
    MAX-ACCESS read-only
    STATUS     current
    DESCRIPTION
	    "Size of the content index (*.ci files only) in
	    megabytes."
    ::= { indexingServiceEntry 5 }

idxSvcMergeProgress OBJECT-TYPE
    SYNTAX     Gauge32
    MAX-ACCESS read-only
    STATUS     current
    DESCRIPTION
	    "Percent merge complete for the current merge."
    ::= { indexingServiceEntry 6 }

idxSvcRunningQueries OBJECT-TYPE
    SYNTAX     Gauge32
    MAX-ACCESS read-only
    STATUS     current
    DESCRIPTION
	    "Number of active query client connections."
    ::= { indexingServiceEntry 7 }

idxSvcSavedIndexes OBJECT-TYPE
    SYNTAX     Gauge32
    MAX-ACCESS read-only
    STATUS     current
    DESCRIPTION
	    "Number of saved indexes."
    ::= { indexingServiceEntry 8 }

idxSvcTotalNumDocuments OBJECT-TYPE
    SYNTAX     Gauge32
    MAX-ACCESS read-only
    STATUS     current
    DESCRIPTION
	    "Total number of documents in the index."
    ::= { indexingServiceEntry 9 }

idxSvcTotalNumOfQueries OBJECT-TYPE
    SYNTAX     Gauge32
    MAX-ACCESS read-only
    STATUS     current
    DESCRIPTION
	    "Total number of queries since the index was
	    mounted."
    ::= { indexingServiceEntry 10 }

idxSvcUniqueKeys OBJECT-TYPE
    SYNTAX     Gauge32
    MAX-ACCESS read-only
    STATUS     current
    DESCRIPTION
	    "Number of unique keys (words, etc.) in the
	    index."
    ::= { indexingServiceEntry 11 }

idxSvcWordLists OBJECT-TYPE
    SYNTAX     Gauge32
    MAX-ACCESS read-only
    STATUS     current
    DESCRIPTION
	    "Number of word lists."
    ::= { indexingServiceEntry 12 }

indexingServiceFilterTable OBJECT-TYPE
    SYNTAX     SEQUENCE OF IndexingServiceFilterEntry
    MAX-ACCESS not-accessible
    STATUS     current
    DESCRIPTION
	    "The Index Service Filter object monitors the
	    filtering activity of Indexing Service."
    ::= { advanced 36 }

indexingServiceFilterEntry OBJECT-TYPE
    SYNTAX     IndexingServiceFilterEntry
    MAX-ACCESS not-accessible
    STATUS     current
    DESCRIPTION
	    "Performance information for one particular
	    instance of 'Indexing Service Filter' object."
    INDEX      { idxSvcFilterInstance }
    ::= { indexingServiceFilterTable 1 }

IndexingServiceFilterEntry ::= SEQUENCE {
    idxSvcFilterInstance InstanceName,
    idxSvcFilterBindingTimeMsec Gauge32,
    idxSvcFilterIdxSpeedMBPerHr Gauge32,
    idxSvcFilterTotalIdxSpeedMBPerHr Gauge32
}

idxSvcFilterInstance OBJECT-TYPE
    SYNTAX     InstanceName
    MAX-ACCESS read-only
    STATUS     current
    DESCRIPTION
	    "Instance name."
    ::= { indexingServiceFilterEntry 1 }

idxSvcFilterBindingTimeMsec OBJECT-TYPE
    SYNTAX     Gauge32
    MAX-ACCESS read-only
    STATUS     current
    DESCRIPTION
	    "Average time spent binding to indexing
	    filters."
    ::= { indexingServiceFilterEntry 2 }

idxSvcFilterIdxSpeedMBPerHr OBJECT-TYPE
    SYNTAX     Gauge32
    MAX-ACCESS read-only
    STATUS     current
    DESCRIPTION
	    "Speed of indexing contents of files in
	    megabytes per hour."
    ::= { indexingServiceFilterEntry 3 }

idxSvcFilterTotalIdxSpeedMBPerHr OBJECT-TYPE
    SYNTAX     Gauge32
    MAX-ACCESS read-only
    STATUS     current
    DESCRIPTION
	    "Speed of indexing file contents and properties
	    in megabytes per hour."
    ::= { indexingServiceFilterEntry 4 }

internetInformationServicesGlobal OBJECT-IDENTITY
    STATUS     current
    DESCRIPTION
	    "The Internet Information Services Global
	    performance object consists of counters that
	    apply jointly to the Hypertext Transport
	    Protocol (HTTP) service and File Transfer
	    Protocol (FTP) service."
    ::= { advanced 37 }

iisGlobalActiveFlushedEntries OBJECT-TYPE
    SYNTAX     Gauge32
    MAX-ACCESS read-only
    STATUS     current
    DESCRIPTION
	    "Active Flushed Entries are cached file handles
	    that will be closed when all current transfers
	    complete."
    ::= { internetInformationServicesGlobal 1 }

iisGlobalBLOBCacheFlushes OBJECT-TYPE
    SYNTAX     Gauge32
    MAX-ACCESS read-only
    STATUS     current
    DESCRIPTION
	    "BLOB Cache Flushes since server startup."
    ::= { internetInformationServicesGlobal 2 }

iisGlobalBLOBCacheHits OBJECT-TYPE
    SYNTAX     Gauge32
    MAX-ACCESS read-only
    STATUS     current
    DESCRIPTION
	    "Total number of successful lookups in the BLOB
	    cache."
    ::= { internetInformationServicesGlobal 3 }

iisGlobalBLOBCacheHitsPercent OBJECT-TYPE
    SYNTAX     Gauge32
    MAX-ACCESS read-only
    STATUS     current
    DESCRIPTION
	    "The ratio of BLOB Cache Hits to total cache
	    requests."
    ::= { internetInformationServicesGlobal 4 }

iisGlobalBLOBCacheMisses OBJECT-TYPE
    SYNTAX     Gauge32
    MAX-ACCESS read-only
    STATUS     current
    DESCRIPTION
	    "Total number of unsuccessful lookups in the
	    BLOB cache."
    ::= { internetInformationServicesGlobal 5 }

iisGlobalCurBLOBsCached OBJECT-TYPE
    SYNTAX     Gauge32
    MAX-ACCESS read-only
    STATUS     current
    DESCRIPTION
	    "BLOB information blocks currently in the cache
	    for WWW and FTP services."
    ::= { internetInformationServicesGlobal 6 }

iisGlobalCurBlockAsyncIORequests OBJECT-TYPE
    SYNTAX     Gauge32
    MAX-ACCESS read-only
    STATUS     current
    DESCRIPTION
	    "Current requests temporarily blocked due to
	    bandwidth throttling settings."
    ::= { internetInformationServicesGlobal 7 }

iisGlobalCurFileCacheMemUsage OBJECT-TYPE
    SYNTAX     Gauge32
    MAX-ACCESS read-only
    STATUS     current
    DESCRIPTION
	    "Current number of bytes used for file cache."
    ::= { internetInformationServicesGlobal 8 }

iisGlobalCurFilesCached OBJECT-TYPE
    SYNTAX     Gauge32
    MAX-ACCESS read-only
    STATUS     current
    DESCRIPTION
	    "Current number of files whose content is in
	    the cache for WWW and FTP services."
    ::= { internetInformationServicesGlobal 9 }

iisGlobalCurURIsCached OBJECT-TYPE
    SYNTAX     Gauge32
    MAX-ACCESS read-only
    STATUS     current
    DESCRIPTION
	    "URI information blocks currently in the cache
	    for WWW and FTP services."
    ::= { internetInformationServicesGlobal 10 }

iisGlobalFileCacheFlushes OBJECT-TYPE
    SYNTAX     Gauge32
    MAX-ACCESS read-only
    STATUS     current
    DESCRIPTION
	    "File Cache Flushes since server startup."
    ::= { internetInformationServicesGlobal 11 }

iisGlobalFileCacheHits OBJECT-TYPE
    SYNTAX     Gauge32
    MAX-ACCESS read-only
    STATUS     current
    DESCRIPTION
	    "Total number of successful lookups in the file
	    cache."
    ::= { internetInformationServicesGlobal 12 }

iisGlobalFileCacheHitsPercent OBJECT-TYPE
    SYNTAX     Gauge32
    MAX-ACCESS read-only
    STATUS     current
    DESCRIPTION
	    "The ratio of File Cache Hits to total cache
	    requests."
    ::= { internetInformationServicesGlobal 13 }

iisGlobalFileCacheMisses OBJECT-TYPE
    SYNTAX     Gauge32
    MAX-ACCESS read-only
    STATUS     current
    DESCRIPTION
	    "Total number of unsuccessful lookups in the
	    file cache."
    ::= { internetInformationServicesGlobal 14 }

iisGlobalMaxFileCacheMemUsage OBJECT-TYPE
    SYNTAX     Gauge32
    MAX-ACCESS read-only
    STATUS     current
    DESCRIPTION
	    "Maximum number of bytes used for file cache."
    ::= { internetInformationServicesGlobal 15 }

iisGlobalMeasuredAsyncIOBwUsage OBJECT-TYPE
    SYNTAX     Gauge32
    MAX-ACCESS read-only
    STATUS     current
    DESCRIPTION
	    "Measured bandwidth of asynchronous I/O
	    averaged over a minute."
    ::= { internetInformationServicesGlobal 16 }

iisGlobalTotalAllowedAsyncIOReqs OBJECT-TYPE
    SYNTAX     Gauge32
    MAX-ACCESS read-only
    STATUS     current
    DESCRIPTION
	    "Total requests allowed by bandwidth throttling
	    settings (counted since service startup)."
    ::= { internetInformationServicesGlobal 17 }

iisGlobalTotalBLOBsCached OBJECT-TYPE
    SYNTAX     Gauge32
    MAX-ACCESS read-only
    STATUS     current
    DESCRIPTION
	    "Total number of BLOB information blocks ever
	    added to the cache for WWW and FTP services"
    ::= { internetInformationServicesGlobal 18 }

iisGlobalTotalBlockAsyncIOReqs OBJECT-TYPE
    SYNTAX     Gauge32
    MAX-ACCESS read-only
    STATUS     current
    DESCRIPTION
	    "Total requests temporarily blocked due to
	    bandwidth throttling settings (counted since
	    service startup)."
    ::= { internetInformationServicesGlobal 19 }

iisGlobalTotalFilesCached OBJECT-TYPE
    SYNTAX     Gauge32
    MAX-ACCESS read-only
    STATUS     current
    DESCRIPTION
	    "Total number of files whose content was ever
	    added to the cache for WWW and FTP services"
    ::= { internetInformationServicesGlobal 20 }

iisGlobalTotalFlushedBLOBs OBJECT-TYPE
    SYNTAX     Gauge32
    MAX-ACCESS read-only
    STATUS     current
    DESCRIPTION
	    "Total Flushed BLOBs is the number of BLOB
	    information blocks that have been removed from
	    the cache since service start up."
    ::= { internetInformationServicesGlobal 21 }

iisGlobalTotalFlushedFiles OBJECT-TYPE
    SYNTAX     Gauge32
    MAX-ACCESS read-only
    STATUS     current
    DESCRIPTION
	    "Total Flushed Files is the number of file
	    handles that have been removed from the cache
	    since service start up."
    ::= { internetInformationServicesGlobal 22 }

iisGlobalTotalFlushedURIs OBJECT-TYPE
    SYNTAX     Gauge32
    MAX-ACCESS read-only
    STATUS     current
    DESCRIPTION
	    "Total Flushed URIs is the number of URI
	    information blocks that have been removed from
	    the cache since service start up."
    ::= { internetInformationServicesGlobal 23 }

iisGlobalTotalRejectedAsyncIOReq OBJECT-TYPE
    SYNTAX     Gauge32
    MAX-ACCESS read-only
    STATUS     current
    DESCRIPTION
	    "Total requests rejected due to bandwidth
	    throttling settings (counted since service
	    startup)."
    ::= { internetInformationServicesGlobal 24 }

iisGlobalTotalURIsCached OBJECT-TYPE
    SYNTAX     Gauge32
    MAX-ACCESS read-only
    STATUS     current
    DESCRIPTION
	    "Total number of URI information blocks ever
	    added to the cache for WWW and FTP services"
    ::= { internetInformationServicesGlobal 25 }

iisGlobalURICacheFlushes OBJECT-TYPE
    SYNTAX     Gauge32
    MAX-ACCESS read-only
    STATUS     current
    DESCRIPTION
	    "URI Cache Flushes since server startup."
    ::= { internetInformationServicesGlobal 26 }

iisGlobalURICacheHits OBJECT-TYPE
    SYNTAX     Gauge32
    MAX-ACCESS read-only
    STATUS     current
    DESCRIPTION
	    "Total number of successful lookups in the URI
	    cache."
    ::= { internetInformationServicesGlobal 27 }

iisGlobalURICacheHitsPercent OBJECT-TYPE
    SYNTAX     Gauge32
    MAX-ACCESS read-only
    STATUS     current
    DESCRIPTION
	    "The ratio of URI Cache Hits to total cache
	    requests."
    ::= { internetInformationServicesGlobal 28 }

iisGlobalURICacheMisses OBJECT-TYPE
    SYNTAX     Gauge32
    MAX-ACCESS read-only
    STATUS     current
    DESCRIPTION
	    "Total number of unsuccessful lookups in the
	    URI cache."
    ::= { internetInformationServicesGlobal 29 }

ipV4 OBJECT-IDENTITY
    STATUS     current
    DESCRIPTION
	    "The Internet Protocol (IP) performance object
	    includes counters that describe the rates at
	    which IP datagrams are transmitted by a
	    computer using the IP protocol. It also
	    describes various error counts for the IP
	    protocol."
    ::= { advanced 38 }

ipV4DatagramsForwardedPerSec OBJECT-TYPE
    SYNTAX     Gauge32
    MAX-ACCESS read-only
    STATUS     current
    DESCRIPTION
	    "Datagrams Forwarded/sec is the rate, in
	    incidents per second, at which attemps were
	    made to find routes to forward input datagrams
	    their final destination, because the local
	    server was not the final IP destination. In
	    servers that do not act as IP Gateways, this
	    rate includes only packets that were
	    source-routed via this entity, where the
	    source-route option processing was successful."
    ::= { ipV4 1 }

ipV4DatagramsOutboundDiscarded OBJECT-TYPE
    SYNTAX     Gauge32
    MAX-ACCESS read-only
    STATUS     current
    DESCRIPTION
	    "Datagrams Outbound Discarded is the number of
	    output IP datagrams that were discarded even
	    though no problems were encountered to prevent
	    their transmission to their destination (for
	    example, lack of buffer space). This counter
	    includes datagrams counted in Datagrams
	    Forwarded/sec that meet this criterion."
    ::= { ipV4 2 }

ipV4DatagramsOutboundNoRoute OBJECT-TYPE
    SYNTAX     Gauge32
    MAX-ACCESS read-only
    STATUS     current
    DESCRIPTION
	    "Datagrams Outbound No Route is the number of
	    IP datagrams that were discarded because no
	    route could be found to transmit them to their
	    destination.  This counter includes any packets
	    counted in Datagrams Forwarded/sec that meet
	    this `no route' criterion."
    ::= { ipV4 3 }

ipV4DatagramsRcvdAddressErrors OBJECT-TYPE
    SYNTAX     Gauge32
    MAX-ACCESS read-only
    STATUS     current
    DESCRIPTION
	    "Datagrams Received Address Errors is the
	    number of input datagrams that were discarded
	    because the IP address in their IP header
	    destination field was not valid for the
	    computer. This count includes invalid addresses
	    (for example, 0.0.	0.0) and addresses of
	    unsupported Classes (for example, Class E). For
	    entities that are not IP gateways and do not
	    forward datagrams, this counter includes
	    datagrams that were discarded because the
	    destination address was not a local address."
    ::= { ipV4 4 }

ipV4DatagramsRcvdDeliveredPerSec OBJECT-TYPE
    SYNTAX     Gauge32
    MAX-ACCESS read-only
    STATUS     current
    DESCRIPTION
	    "Datagrams Received Delivered/sec is the rate,
	    in incidents per second, at which input
	    datagrams were successfully delivered to IP
	    user-protocols, including Internet Control
	    Message Protocol (ICMP)."
    ::= { ipV4 5 }

ipV4DatagramsRcvdDiscarded OBJECT-TYPE
    SYNTAX     Gauge32
    MAX-ACCESS read-only
    STATUS     current
    DESCRIPTION
	    "Datagrams Received Discarded is the number of
	    input IP datagrams that were discarded even
	    though problems prevented their continued
	    processing (for example, lack of buffer space).
	    This counter does not include any datagrams
	    discarded while awaiting re-assembly."
    ::= { ipV4 6 }

ipV4DatagramsRcvdHeaderErrors OBJECT-TYPE
    SYNTAX     Gauge32
    MAX-ACCESS read-only
    STATUS     current
    DESCRIPTION
	    "Datagrams Received Header Errors is the number
	    of input datagrams that were discarded due to
	    errors in the IP headers, including bad
	    checksums, version number mismatch, other
	    format errors, time-to-live exceeded, errors
	    discovered in processing their IP options,
	    etc."
    ::= { ipV4 7 }

ipV4DatagramsRcvdUnknownProtocol OBJECT-TYPE
    SYNTAX     Gauge32
    MAX-ACCESS read-only
    STATUS     current
    DESCRIPTION
	    "Datagrams Received Unknown Protocol is the
	    number of locally-addressed datagrams that were
	    successfully received but were discarded
	    because of an unknown or unsupported protocol."
    ::= { ipV4 8 }

ipV4DatagramsRcvdPerSec OBJECT-TYPE
    SYNTAX     Gauge32
    MAX-ACCESS read-only
    STATUS     current
    DESCRIPTION
	    "Datagrams Received/sec is the rate, in
	    incidents per second, at which IP datagrams are
	    received from the interfaces, including those
	    in error. Datagrams Received/sec is a subset of
	    Datagrams/sec."
    ::= { ipV4 9 }

ipV4DatagramsSentPerSec OBJECT-TYPE
    SYNTAX     Gauge32
    MAX-ACCESS read-only
    STATUS     current
    DESCRIPTION
	    "Datagrams Sent/sec is the rate, in incidents
	    per second, at which IP datagrams were supplied
	    for transmission by local IP user-protocols
	    (including ICMP). This counter does not include
	    any datagrams counted in Datagrams
	    Forwarded/sec. Datagrams Sent/sec is a subset
	    of Datagrams/sec."
    ::= { ipV4 10 }

ipV4DatagramsPerSec OBJECT-TYPE
    SYNTAX     Gauge32
    MAX-ACCESS read-only
    STATUS     current
    DESCRIPTION
	    "Datagrams/sec is the rate, in incidents per
	    second, at which IP datagrams were received
	    from or sent to the interfaces, including those
	    in error. Forwarded datagrams are not included
	    in this rate."
    ::= { ipV4 11 }

ipV4FragmentReassemblyFailures OBJECT-TYPE
    SYNTAX     Gauge32
    MAX-ACCESS read-only
    STATUS     current
    DESCRIPTION
	    "Fragment Re-assembly Failures is the number of
	    failures detected by the IP reassembly
	    algorithm, such as time outs, errors, etc. 
	    This is not necessarily a count of discarded IP
	    fragments since some algorithms (notably RFC
	    815) lose track of the number of fragments by
	    combining them as they are received."
    ::= { ipV4 12 }

ipV4FragmentationFailures OBJECT-TYPE
    SYNTAX     Gauge32
    MAX-ACCESS read-only
    STATUS     current
    DESCRIPTION
	    "Fragmentation Failures is the number of IP
	    datagrams that were discarded because they
	    needed to be fragmented at but could not be
	    (for example, because the `Don't Fragment' flag
	    was set)."
    ::= { ipV4 13 }

ipV4FragmentedDatagramsPerSec OBJECT-TYPE
    SYNTAX     Gauge32
    MAX-ACCESS read-only
    STATUS     current
    DESCRIPTION
	    "Fragmented Datagrams/sec is the rate, in
	    incidents per second, at which datagrams are
	    successfully fragmented."
    ::= { ipV4 14 }

ipV4FragmentsCreatedPerSec OBJECT-TYPE
    SYNTAX     Gauge32
    MAX-ACCESS read-only
    STATUS     current
    DESCRIPTION
	    "Fragments Created/sec is the rate, in
	    incidents per second, at which IP datagram
	    fragments were generated as a result of
	    fragmentation."
    ::= { ipV4 15 }

ipV4FragmentsReassembledPerSec OBJECT-TYPE
    SYNTAX     Gauge32
    MAX-ACCESS read-only
    STATUS     current
    DESCRIPTION
	    "Fragments Re-assembled/sec is the rate, in
	    incidents per second, at which IP fragments
	    were successfully reassembled."
    ::= { ipV4 16 }

ipV4FragmentsRcvdPerSec OBJECT-TYPE
    SYNTAX     Gauge32
    MAX-ACCESS read-only
    STATUS     current
    DESCRIPTION
	    "Fragments Received/sec is the rate, in
	    incidents per second, at which IP fragments
	    that need to be reassembled at this entity are
	    received."
    ::= { ipV4 17 }

ipV6 OBJECT IDENTIFIER
    ::= { advanced 39 }

ipV6DatagramsForwardedPerSec OBJECT-TYPE
    SYNTAX     Gauge32
    MAX-ACCESS read-only
    STATUS     current
    DESCRIPTION
	    "Datagrams Forwarded/sec is the rate, in
	    incidents per second, at which attemps were
	    made to find routes to forward input datagrams
	    their final destination, because the local
	    server was not the final IP destination. In
	    servers that do not act as IP Gateways, this
	    rate includes only packets that were
	    source-routed via this entity, where the
	    source-route option processing was successful."
    ::= { ipV6 1 }

ipV6DatagramsOutboundDiscarded OBJECT-TYPE
    SYNTAX     Gauge32
    MAX-ACCESS read-only
    STATUS     current
    DESCRIPTION
	    "Datagrams Outbound Discarded is the number of
	    output IP datagrams that were discarded even
	    though no problems were encountered to prevent
	    their transmission to their destination (for
	    example, lack of buffer space). This counter
	    includes datagrams counted in Datagrams
	    Forwarded/sec that meet this criterion."
    ::= { ipV6 2 }

ipV6DatagramsOutboundNoRoute OBJECT-TYPE
    SYNTAX     Gauge32
    MAX-ACCESS read-only
    STATUS     current
    DESCRIPTION
	    "Datagrams Outbound No Route is the number of
	    IP datagrams that were discarded because no
	    route could be found to transmit them to their
	    destination.  This counter includes any packets
	    counted in Datagrams Forwarded/sec that meet
	    this `no route' criterion."
    ::= { ipV6 3 }

ipV6DatagramsRcvdAddressErrors OBJECT-TYPE
    SYNTAX     Gauge32
    MAX-ACCESS read-only
    STATUS     current
    DESCRIPTION
	    "Datagrams Received Address Errors is the
	    number of input datagrams that were discarded
	    because the IP address in their IP header
	    destination field was not valid for the
	    computer. This count includes invalid addresses
	    (for example, 0.0.	0.0) and addresses of
	    unsupported Classes (for example, Class E). For
	    entities that are not IP gateways and do not
	    forward datagrams, this counter includes
	    datagrams that were discarded because the
	    destination address was not a local address."
    ::= { ipV6 4 }

ipV6DatagramsRcvdDeliveredPerSec OBJECT-TYPE
    SYNTAX     Gauge32
    MAX-ACCESS read-only
    STATUS     current
    DESCRIPTION
	    "Datagrams Received Delivered/sec is the rate,
	    in incidents per second, at which input
	    datagrams were successfully delivered to IP
	    user-protocols, including Internet Control
	    Message Protocol (ICMP)."
    ::= { ipV6 5 }

ipV6DatagramsRcvdDiscarded OBJECT-TYPE
    SYNTAX     Gauge32
    MAX-ACCESS read-only
    STATUS     current
    DESCRIPTION
	    "Datagrams Received Discarded is the number of
	    input IP datagrams that were discarded even
	    though problems prevented their continued
	    processing (for example, lack of buffer space).
	    This counter does not include any datagrams
	    discarded while awaiting re-assembly."
    ::= { ipV6 6 }

ipV6DatagramsRcvdHeaderErrors OBJECT-TYPE
    SYNTAX     Gauge32
    MAX-ACCESS read-only
    STATUS     current
    DESCRIPTION
	    "Datagrams Received Header Errors is the number
	    of input datagrams that were discarded due to
	    errors in the IP headers, including bad
	    checksums, version number mismatch, other
	    format errors, time-to-live exceeded, errors
	    discovered in processing their IP options,
	    etc."
    ::= { ipV6 7 }

ipV6DatagramsRcvdUnknownProtocol OBJECT-TYPE
    SYNTAX     Gauge32
    MAX-ACCESS read-only
    STATUS     current
    DESCRIPTION
	    "Datagrams Received Unknown Protocol is the
	    number of locally-addressed datagrams that were
	    successfully received but were discarded
	    because of an unknown or unsupported protocol."
    ::= { ipV6 8 }

ipV6DatagramsRcvdPerSec OBJECT-TYPE
    SYNTAX     Gauge32
    MAX-ACCESS read-only
    STATUS     current
    DESCRIPTION
	    "Datagrams Received/sec is the rate, in
	    incidents per second, at which IP datagrams are
	    received from the interfaces, including those
	    in error. Datagrams Received/sec is a subset of
	    Datagrams/sec."
    ::= { ipV6 9 }

ipV6DatagramsSentPerSec OBJECT-TYPE
    SYNTAX     Gauge32
    MAX-ACCESS read-only
    STATUS     current
    DESCRIPTION
	    "Datagrams Sent/sec is the rate, in incidents
	    per second, at which IP datagrams were supplied
	    for transmission by local IP user-protocols
	    (including ICMP). This counter does not include
	    any datagrams counted in Datagrams
	    Forwarded/sec. Datagrams Sent/sec is a subset
	    of Datagrams/sec."
    ::= { ipV6 10 }

ipV6DatagramsPerSec OBJECT-TYPE
    SYNTAX     Gauge32
    MAX-ACCESS read-only
    STATUS     current
    DESCRIPTION
	    "Datagrams/sec is the rate, in incidents per
	    second, at which IP datagrams were received
	    from or sent to the interfaces, including those
	    in error. Forwarded datagrams are not included
	    in this rate."
    ::= { ipV6 11 }

ipV6FragmentReassemblyFailures OBJECT-TYPE
    SYNTAX     Gauge32
    MAX-ACCESS read-only
    STATUS     current
    DESCRIPTION
	    "Fragment Re-assembly Failures is the number of
	    failures detected by the IP reassembly
	    algorithm, such as time outs, errors, etc. 
	    This is not necessarily a count of discarded IP
	    fragments since some algorithms (notably RFC
	    815) lose track of the number of fragments by
	    combining them as they are received."
    ::= { ipV6 12 }

ipV6FragmentationFailures OBJECT-TYPE
    SYNTAX     Gauge32
    MAX-ACCESS read-only
    STATUS     current
    DESCRIPTION
	    "Fragmentation Failures is the number of IP
	    datagrams that were discarded because they
	    needed to be fragmented at but could not be
	    (for example, because the `Don't Fragment' flag
	    was set)."
    ::= { ipV6 13 }

ipV6FragmentedDatagramsPerSec OBJECT-TYPE
    SYNTAX     Gauge32
    MAX-ACCESS read-only
    STATUS     current
    DESCRIPTION
	    "Fragmented Datagrams/sec is the rate, in
	    incidents per second, at which datagrams are
	    successfully fragmented."
    ::= { ipV6 14 }

ipV6FragmentsCreatedPerSec OBJECT-TYPE
    SYNTAX     Gauge32
    MAX-ACCESS read-only
    STATUS     current
    DESCRIPTION
	    "Fragments Created/sec is the rate, in
	    incidents per second, at which IP datagram
	    fragments were generated as a result of
	    fragmentation."
    ::= { ipV6 15 }

ipV6FragmentsReassembledPerSec OBJECT-TYPE
    SYNTAX     Gauge32
    MAX-ACCESS read-only
    STATUS     current
    DESCRIPTION
	    "Fragments Re-assembled/sec is the rate, in
	    incidents per second, at which IP fragments
	    were successfully reassembled."
    ::= { ipV6 16 }

ipV6FragmentsRcvdPerSec OBJECT-TYPE
    SYNTAX     Gauge32
    MAX-ACCESS read-only
    STATUS     current
    DESCRIPTION
	    "Fragments Received/sec is the rate, in
	    incidents per second, at which IP fragments
	    that need to be reassembled at this entity are
	    received."
    ::= { ipV6 17 }

ipSecV4Driver OBJECT IDENTIFIER
    ::= { advanced 40 }

is4dActiveSecurityAssociations OBJECT-TYPE
    SYNTAX     Gauge32
    MAX-ACCESS read-only
    STATUS     current
    DESCRIPTION
	    "The number of active IPSec quick mode security
	    associations."
    ::= { ipSecV4Driver 1 }

is4dOffloadedSecurityAssociation OBJECT-TYPE
    SYNTAX     Gauge32
    MAX-ACCESS read-only
    STATUS     current
    DESCRIPTION
	    "The number of active IPSec quick mode security
	    associations offloaded to hardware. Certain
	    network adapters can accelerate IPSec
	    processing by performing hardware offload of
	    IPSec cryptographic functions."
    ::= { ipSecV4Driver 2 }

is4dPendingKeyExchangeOperations OBJECT-TYPE
    SYNTAX     Gauge32
    MAX-ACCESS read-only
    STATUS     current
    DESCRIPTION
	    "The number of IPSec key exchange operations
	    that are in progress but are not yet
	    completed."
    ::= { ipSecV4Driver 3 }

is4dTotalBadSPIPackets OBJECT-TYPE
    SYNTAX     Gauge32
    MAX-ACCESS read-only
    STATUS     current
    DESCRIPTION
	    "The total number of packets for which the
	    Security Parameters Index (SPI) was incorrect
	    since the computer was last started. A large
	    number of packets with bad SPIs within a short
	    amount of time might indicate a packet spoofing
	    attack."
    ::= { ipSecV4Driver 4 }

is4dTotalBytesReceivedInTunnels OBJECT-TYPE
    SYNTAX     Gauge32
    MAX-ACCESS read-only
    STATUS     current
    DESCRIPTION
	    "The total number of bytes received using IPSec
	    tunnel mode since the computer was last
	    started."
    ::= { ipSecV4Driver 5 }

is4dTotalBytesSentInTunnels OBJECT-TYPE
    SYNTAX     Gauge32
    MAX-ACCESS read-only
    STATUS     current
    DESCRIPTION
	    "The total number of bytes sent using IPSec
	    tunnel mode since the computer was last
	    started."
    ::= { ipSecV4Driver 6 }

is4dTotalOffloadedBytesReceived OBJECT-TYPE
    SYNTAX     Gauge32
    MAX-ACCESS read-only
    STATUS     current
    DESCRIPTION
	    "The total number of bytes received using IPSec
	    hardware offload since the computer was last
	    started. Certain network adapters can
	    accelerate IPSec processing by performing
	    hardware offload of IPSec cryptographic
	    functions."
    ::= { ipSecV4Driver 7 }

is4dTotalOffloadedBytesSent OBJECT-TYPE
    SYNTAX     Gauge32
    MAX-ACCESS read-only
    STATUS     current
    DESCRIPTION
	    "The total number of bytes sent using IPSec
	    hardware offload since the computer was last
	    started. Certain network adapters can
	    accelerate IPSec processing by performing
	    hardware offload of IPSec cryptographic
	    functions."
    ::= { ipSecV4Driver 8 }

is4dTotalPktsFailReplayDetection OBJECT-TYPE
    SYNTAX     Gauge32
    MAX-ACCESS read-only
    STATUS     current
    DESCRIPTION
	    "The total number of packets that contained an
	    invalid sequence number since the computer was
	    last started. Increases in this counter might
	    indicate a network problem or replay attack."
    ::= { ipSecV4Driver 9 }

is4dTotalPktsNotAuthenticated OBJECT-TYPE
    SYNTAX     Gauge32
    MAX-ACCESS read-only
    STATUS     current
    DESCRIPTION
	    "The total number of packets for which data
	    could not be verified (for which the integrity
	    hash verification failed) since the computer
	    was last started. Increases in this counter
	    might indicate an IPSec packet spoofing or
	    modification attack, or packet corruption by
	    network devices."
    ::= { ipSecV4Driver 10 }

is4dTotalPktsNotDecrypted OBJECT-TYPE
    SYNTAX     Gauge32
    MAX-ACCESS read-only
    STATUS     current
    DESCRIPTION
	    "The total number of packets that could not be
	    decrypted since the computer was last started.
	    A packet might not be decrypted if it fails a
	    validation check."
    ::= { ipSecV4Driver 11 }

is4dTotalSARekeys OBJECT-TYPE
    SYNTAX     Gauge32
    MAX-ACCESS read-only
    STATUS     current
    DESCRIPTION
	    "The total number of successful rekey
	    operations for IPSec quick mode security
	    associations since the computer was last
	    started."
    ::= { ipSecV4Driver 12 }

is4dTotalTransportBytesReceived OBJECT-TYPE
    SYNTAX     Gauge32
    MAX-ACCESS read-only
    STATUS     current
    DESCRIPTION
	    "The total number of bytes received using IPSec
	    transport mode since the computer was last
	    started."
    ::= { ipSecV4Driver 13 }

is4dTotalTransportBytesSent OBJECT-TYPE
    SYNTAX     Gauge32
    MAX-ACCESS read-only
    STATUS     current
    DESCRIPTION
	    "The total number of bytes sent using IPSec
	    transport mode since the computer was last
	    started."
    ::= { ipSecV4Driver 14 }

ipSecV4IKE OBJECT IDENTIFIER
    ::= { advanced 41 }

is4iAcquireHeapSize OBJECT-TYPE
    SYNTAX     Gauge32
    MAX-ACCESS read-only
    STATUS     current
    DESCRIPTION
	    "The number of entries in the acquire heap. The
	    acquire heap stores successful acquires.
	    Acquires are outbound requests to establish
	    security associations between IPSec peers."
    ::= { ipSecV4IKE 1 }

is4iMainModeSAListEntries OBJECT-TYPE
    SYNTAX     Gauge32
    MAX-ACCESS read-only
    STATUS     current
    DESCRIPTION
	    "The number of main mode state entries. This
	    counter includes successfully negotiated main
	    modes, main mode negotiations in progress, and
	    main mode negotiations that failed or expired
	    and have not yet been deleted."
    ::= { ipSecV4IKE 2 }

is4iQuickModeSAListEntries OBJECT-TYPE
    SYNTAX     Gauge32
    MAX-ACCESS read-only
    STATUS     current
    DESCRIPTION
	    "The number of quick mode negotiations that are
	    in progress."
    ::= { ipSecV4IKE 3 }

is4iReceiveHeapSize OBJECT-TYPE
    SYNTAX     Gauge32
    MAX-ACCESS read-only
    STATUS     current
    DESCRIPTION
	    "The number of entries in the Internet Key
	    Exchange (IKE) receive buffers. The receive
	    buffers are used to store incoming IKE
	    messages."
    ::= { ipSecV4IKE 4 }

is4iTotalAuthenticationFailures OBJECT-TYPE
    SYNTAX     Gauge32
    MAX-ACCESS read-only
    STATUS     current
    DESCRIPTION
	    "The total number of identity authentication
	    (Kerberos, certificate, and preshared key)
	    failures that occurred during main mode
	    negotiation since the IPSec service was last
	    started."
    ::= { ipSecV4IKE 5 }

is4iTotalMainModeSAs OBJECT-TYPE
    SYNTAX     Gauge32
    MAX-ACCESS read-only
    STATUS     current
    DESCRIPTION
	    "The total number of successful security
	    associations created during main mode
	    negotiations since the IPSec service was last
	    started."
    ::= { ipSecV4IKE 6 }

is4iTotalNegotiationFailures OBJECT-TYPE
    SYNTAX     Gauge32
    MAX-ACCESS read-only
    STATUS     current
    DESCRIPTION
	    "The total number of negotiation failures that
	    occurred during main mode or quick mode
	    negotiation since the IPSec service was last
	    started."
    ::= { ipSecV4IKE 7 }

is4iTotalQuickModeSAs OBJECT-TYPE
    SYNTAX     Gauge32
    MAX-ACCESS read-only
    STATUS     current
    DESCRIPTION
	    "The total number of successful security
	    associations created during quick mode
	    negotiations since the IPSec service was last
	    started."
    ::= { ipSecV4IKE 8 }

is4iTotalSoftAssociations OBJECT-TYPE
    SYNTAX     Gauge32
    MAX-ACCESS read-only
    STATUS     current
    DESCRIPTION
	    "The total number of security associations
	    (SAs) formed with computers that did not
	    respond to main mode negotiation attempts
	    (though IPSec policy allowed communications)
	    since the IPSec service was last started.
	    Packets that match soft SAs are not secured by
	    IPSec."
    ::= { ipSecV4IKE 9 }

jobObjectTable OBJECT-TYPE
    SYNTAX     SEQUENCE OF JobObjectEntry
    MAX-ACCESS not-accessible
    STATUS     current
    DESCRIPTION
	    "The Job performance object reports the
	    accounting and processor usage data collected
	    by each active job object. A job object
	    provides a means of managing groups of
	    processes with respect to their processor usage
	    and other factors. For more information about
	    creating and managing job objects, see the
	    Platform SDK link on the Web Resources page at
	    http://windows.microsoft.com/windows2000/reskit
	    /webresources."
    ::= { advanced 42 }

jobObjectEntry OBJECT-TYPE
    SYNTAX     JobObjectEntry
    MAX-ACCESS not-accessible
    STATUS     current
    DESCRIPTION
	    "Performance information for one particular
	    instance of 'Job Object' object."
    INDEX      { joInstance }
    ::= { jobObjectTable 1 }

JobObjectEntry ::= SEQUENCE {
    joInstance InstanceName,
    joCurrentPercentKernelModeTime Gauge32,
    joCurrentPercentProcessorTime Gauge32,
    joCurrentPercentUserModeTime Gauge32,
    joPagesPerSec Gauge32,
    joProcessCountActive Gauge32,
    joProcessCountTerminated Gauge32,
    joProcessCountTotal Gauge32,
    joThisPeriodMSecKernelMode Gauge32,
    joThisPeriodMSecProcessor Gauge32,
    joThisPeriodMSecUserMode Gauge32,
    joTotalMSecKernelMode Gauge32,
    joTotalMSecProcessor Gauge32,
    joTotalMSecUserMode Gauge32
}

joInstance OBJECT-TYPE
    SYNTAX     InstanceName
    MAX-ACCESS read-only
    STATUS     current
    DESCRIPTION
	    "Instance name."
    ::= { jobObjectEntry 1 }

joCurrentPercentKernelModeTime OBJECT-TYPE
    SYNTAX     Gauge32
    MAX-ACCESS read-only
    STATUS     current
    DESCRIPTION
	    "Current % Kernel mode Time shows the
	    percentage of the sample interval that the
	    processes in the Job object spent executing
	    code in kernel or privileged mode."
    ::= { jobObjectEntry 2 }

joCurrentPercentProcessorTime OBJECT-TYPE
    SYNTAX     Gauge32
    MAX-ACCESS read-only
    STATUS     current
    DESCRIPTION
	    "Current % Processor Time shows the percentage
	    of the sample interval that the processes in
	    the Job object spent executing code."
    ::= { jobObjectEntry 3 }

joCurrentPercentUserModeTime OBJECT-TYPE
    SYNTAX     Gauge32
    MAX-ACCESS read-only
    STATUS     current
    DESCRIPTION
	    "Current % User mode Time shows the percentage
	    of the sample interval that the processes in
	    the Job object spent executing code in user
	    mode."
    ::= { jobObjectEntry 4 }

joPagesPerSec OBJECT-TYPE
    SYNTAX     Gauge32
    MAX-ACCESS read-only
    STATUS     current
    DESCRIPTION
	    "Pages/Sec shows the page fault rate of all the
	    processes in the Job object."
    ::= { jobObjectEntry 5 }

joProcessCountActive OBJECT-TYPE
    SYNTAX     Gauge32
    MAX-ACCESS read-only
    STATUS     current
    DESCRIPTION
	    "Process Count - Active shows the number of
	    processes that are currently associated with
	    the Job object."
    ::= { jobObjectEntry 6 }

joProcessCountTerminated OBJECT-TYPE
    SYNTAX     Gauge32
    MAX-ACCESS read-only
    STATUS     current
    DESCRIPTION
	    "Process Count - Terminated shows the number of
	    processes that have been terminated because of
	    a limit violation."
    ::= { jobObjectEntry 7 }

joProcessCountTotal OBJECT-TYPE
    SYNTAX     Gauge32
    MAX-ACCESS read-only
    STATUS     current
    DESCRIPTION
	    "Process Count - Total shows the number of
	    processes, both active and terminated, that are
	    or have been associated with the Job object."
    ::= { jobObjectEntry 8 }

joThisPeriodMSecKernelMode OBJECT-TYPE
    SYNTAX     Gauge32
    MAX-ACCESS read-only
    STATUS     current
    DESCRIPTION
	    "This Period mSec - Kernel mode shows the time,
	    in milliseconds, of kernel mode processor time
	    used by all the processes in the Job object,
	    including those that have terminated or that
	    are no longer associated with the Job object,
	    since a time limit on the Job was established."
    ::= { jobObjectEntry 9 }

joThisPeriodMSecProcessor OBJECT-TYPE
    SYNTAX     Gauge32
    MAX-ACCESS read-only
    STATUS     current
    DESCRIPTION
	    "This Period mSec - Processor shows the time,
	    in milliseconds, of processor time used by all
	    the processes in the Job object, including
	    those that have terminated or that are no
	    longer associated with the Job object, since a
	    time limit on the Job was established."
    ::= { jobObjectEntry 10 }

joThisPeriodMSecUserMode OBJECT-TYPE
    SYNTAX     Gauge32
    MAX-ACCESS read-only
    STATUS     current
    DESCRIPTION
	    "This Period mSec - User mode shows the time,
	    in milliseconds, of user mode processor time
	    used by all the processes in the Job object,
	    including those that have terminated or that
	    are no longer associated with the Job object,
	    since a time limit on the Job was established."
    ::= { jobObjectEntry 11 }

joTotalMSecKernelMode OBJECT-TYPE
    SYNTAX     Gauge32
    MAX-ACCESS read-only
    STATUS     current
    DESCRIPTION
	    "Total mSec - Kernel mode shows the time, in
	    milliseconds, of kernel mode processor time
	    used by all the processes in the Job object,
	    including those that have terminated or that
	    are no longer associated with the Job object,
	    since the Job object was created."
    ::= { jobObjectEntry 12 }

joTotalMSecProcessor OBJECT-TYPE
    SYNTAX     Gauge32
    MAX-ACCESS read-only
    STATUS     current
    DESCRIPTION
	    "Total mSec - Processor shows the time, in
	    milliseconds, of processor time used by all the
	    processes in the Job object, including those
	    that have terminated or that are no longer
	    associated with the Job object, since the Job
	    object was created."
    ::= { jobObjectEntry 13 }

joTotalMSecUserMode OBJECT-TYPE
    SYNTAX     Gauge32
    MAX-ACCESS read-only
    STATUS     current
    DESCRIPTION
	    "Total mSec - User mode shows the time, in
	    milliseconds, of user mode processor time used
	    by all the processes in the Job object,
	    including those that have terminated or that
	    are no longer associated with the Job object,
	    since the Job object was created."
    ::= { jobObjectEntry 14 }

jobObjectDetailsTable OBJECT-TYPE
    SYNTAX     SEQUENCE OF JobObjectDetailsEntry
    MAX-ACCESS not-accessible
    STATUS     current
    DESCRIPTION
	    "The Job Object Details performance object
	    counters show detailed performance information
	    about the active processes that make up a job
	    object."
    ::= { advanced 43 }

jobObjectDetailsEntry OBJECT-TYPE
    SYNTAX     JobObjectDetailsEntry
    MAX-ACCESS not-accessible
    STATUS     current
    DESCRIPTION
	    "Performance information for one particular
	    instance of 'Job Object Details' object."
    INDEX      { jodInstance }
    ::= { jobObjectDetailsTable 1 }

JobObjectDetailsEntry ::= SEQUENCE {
    jodInstance InstanceName,
    jodPercentPrivilegedTime Gauge32,
    jodPercentProcessorTime Gauge32,
    jodPercentUserTime Gauge32,
    jodCreatingProcessID Gauge32,
    jodElapsedTime Gauge32,
    jodHandleCount Gauge32,
    jodIDProcess Gauge32,
    jodIODataBytesPerSec Gauge32,
    jodIODataOperationsPerSec Gauge32,
    jodIOOtherBytesPerSec Gauge32,
    jodIOOtherOperationsPerSec Gauge32,
    jodIOReadBytesPerSec Gauge32,
    jodIOReadOperationsPerSec Gauge32,
    jodIOWriteBytesPerSec Gauge32,
    jodIOWriteOperationsPerSec Gauge32,
    jodPageFaultsPerSec Gauge32,
    jodPageFileBytes Gauge32,
    jodPageFileBytesPeak Gauge32,
    jodPoolNonpagedBytes Gauge32,
    jodPoolPagedBytes Gauge32,
    jodPriorityBase Gauge32,
    jodPrivateBytes Gauge32,
    jodThreadCount Gauge32,
    jodVirtualBytes Gauge32,
    jodVirtualBytesPeak Gauge32,
    jodWorkingSet Gauge32,
    jodWorkingSetPeak Gauge32
}

jodInstance OBJECT-TYPE
    SYNTAX     InstanceName
    MAX-ACCESS read-only
    STATUS     current
    DESCRIPTION
	    "Instance name."
    ::= { jobObjectDetailsEntry 1 }

jodPercentPrivilegedTime OBJECT-TYPE
    SYNTAX     Gauge32
    MAX-ACCESS read-only
    STATUS     current
    DESCRIPTION
	    "% Privileged Time is the percentage of elapsed
	    time that the process threads spent executing
	    code in privileged mode. When a Windows system
	    service is called, the service will often run
	    in privileged mode to gain access to
	    system-private data. Such data is protected
	    from access by threads executing in user mode.
	    Calls to the system can be explicit or
	    implicit, such as page faults or interrupts.
	    Unlike some early operating systems, Windows
	    uses process boundaries for subsystem
	    protection in addition to the traditional
	    protection of user and privileged modes. Some
	    work done by Windows on behalf of the
	    application might appear in other subsystem
	    processes in addition to the privileged time in
	    the process."
    ::= { jobObjectDetailsEntry 2 }

jodPercentProcessorTime OBJECT-TYPE
    SYNTAX     Gauge32
    MAX-ACCESS read-only
    STATUS     current
    DESCRIPTION
	    "% Processor Time is the percentage of elapsed
	    time that all of process threads used the
	    processor to execution instructions. An
	    instruction is the basic unit of execution in a
	    computer, a thread is the object that executes
	    instructions, and a process is the object
	    created when a program is run. Code executed to
	    handle some hardware interrupts and trap
	    conditions are included in this count."
    ::= { jobObjectDetailsEntry 3 }

jodPercentUserTime OBJECT-TYPE
    SYNTAX     Gauge32
    MAX-ACCESS read-only
    STATUS     current
    DESCRIPTION
	    "% User Time is the percentage of elapsed time
	    that the process threads spent executing code
	    in user mode. Applications, environment
	    subsystems, and integral subsystems execute in
	    user mode. Code executing in user mode cannot
	    damage the integrity of the Windows executive,
	    kernel, and device drivers. Unlike some early
	    operating systems, Windows uses process
	    boundaries for subsystem protection in addition
	    to the traditional protection of user and
	    privileged modes. Some work done by Windows on
	    behalf of the application might appear in other
	    subsystem processes in addition to the
	    privileged time in the process."
    ::= { jobObjectDetailsEntry 4 }

jodCreatingProcessID OBJECT-TYPE
    SYNTAX     Gauge32
    MAX-ACCESS read-only
    STATUS     current
    DESCRIPTION
	    "The Creating Process ID value is the Process
	    ID of the process that created the process. The
	    creating process may have terminated, so this
	    value may no longer identify a running
	    process."
    ::= { jobObjectDetailsEntry 5 }

jodElapsedTime OBJECT-TYPE
    SYNTAX     Gauge32
    MAX-ACCESS read-only
    STATUS     current
    DESCRIPTION
	    "The total elapsed time, in seconds, that this
	    process has been running."
    ::= { jobObjectDetailsEntry 6 }

jodHandleCount OBJECT-TYPE
    SYNTAX     Gauge32
    MAX-ACCESS read-only
    STATUS     current
    DESCRIPTION
	    "The total number of handles currently open by
	    this process. This number is equal to the sum
	    of the handles currently open by each thread in
	    this process."
    ::= { jobObjectDetailsEntry 7 }

jodIDProcess OBJECT-TYPE
    SYNTAX     Gauge32
    MAX-ACCESS read-only
    STATUS     current
    DESCRIPTION
	    "ID Process is the unique identifier of this
	    process. ID Process numbers are reused, so they
	    only identify a process for the lifetime of
	    that process."
    ::= { jobObjectDetailsEntry 8 }

jodIODataBytesPerSec OBJECT-TYPE
    SYNTAX     Gauge32
    MAX-ACCESS read-only
    STATUS     current
    DESCRIPTION
	    "The rate at which the process is reading and
	    writing bytes in I/O operations. This counter
	    counts all I/O activity generated by the
	    process to include file, network and device
	    I/Os."
    ::= { jobObjectDetailsEntry 9 }

jodIODataOperationsPerSec OBJECT-TYPE
    SYNTAX     Gauge32
    MAX-ACCESS read-only
    STATUS     current
    DESCRIPTION
	    "The rate at which the process is issuing read
	    and write I/O operations. This counter counts
	    all I/O activity generated by the process to
	    include file, network and device I/Os."
    ::= { jobObjectDetailsEntry 10 }

jodIOOtherBytesPerSec OBJECT-TYPE
    SYNTAX     Gauge32
    MAX-ACCESS read-only
    STATUS     current
    DESCRIPTION
	    "The rate at which the process is issuing bytes
	    to I/O operations that do not involve data such
	    as control operations. This counter counts all
	    I/O activity generated by the process to
	    include file, network and device I/Os."
    ::= { jobObjectDetailsEntry 11 }

jodIOOtherOperationsPerSec OBJECT-TYPE
    SYNTAX     Gauge32
    MAX-ACCESS read-only
    STATUS     current
    DESCRIPTION
	    "The rate at which the process is issuing I/O
	    operations that are neither read nor write
	    operations (for example, a control function).
	    This counter counts all I/O activity generated
	    by the process to include file, network and
	    device I/Os."
    ::= { jobObjectDetailsEntry 12 }

jodIOReadBytesPerSec OBJECT-TYPE
    SYNTAX     Gauge32
    MAX-ACCESS read-only
    STATUS     current
    DESCRIPTION
	    "The rate at which the process is reading bytes
	    from I/O operations. This counter counts all
	    I/O activity generated by the process to
	    include file, network and device I/Os."
    ::= { jobObjectDetailsEntry 13 }

jodIOReadOperationsPerSec OBJECT-TYPE
    SYNTAX     Gauge32
    MAX-ACCESS read-only
    STATUS     current
    DESCRIPTION
	    "The rate at which the process is issuing read
	    I/O operations. This counter counts all I/O
	    activity generated by the process to include
	    file, network and device I/Os."
    ::= { jobObjectDetailsEntry 14 }

jodIOWriteBytesPerSec OBJECT-TYPE
    SYNTAX     Gauge32
    MAX-ACCESS read-only
    STATUS     current
    DESCRIPTION
	    "The rate at which the process is writing bytes
	    to I/O operations. This counter counts all I/O
	    activity generated by the process to include
	    file, network and device I/Os."
    ::= { jobObjectDetailsEntry 15 }

jodIOWriteOperationsPerSec OBJECT-TYPE
    SYNTAX     Gauge32
    MAX-ACCESS read-only
    STATUS     current
    DESCRIPTION
	    "The rate at which the process is issuing write
	    I/O operations. This counter counts all I/O
	    activity generated by the process to include
	    file, network and device I/Os."
    ::= { jobObjectDetailsEntry 16 }

jodPageFaultsPerSec OBJECT-TYPE
    SYNTAX     Gauge32
    MAX-ACCESS read-only
    STATUS     current
    DESCRIPTION
	    "Page Faults/sec is the rate at which page
	    faults by the threads executing in this process
	    are occurring.  A page fault occurs when a
	    thread refers to a virtual memory page that is
	    not in its working set in main memory. This may
	    not cause the page to be fetched from disk if
	    it is on the standby list and hence already in
	    main memory, or if it is in use by another
	    process with whom the page is shared."
    ::= { jobObjectDetailsEntry 17 }

jodPageFileBytes OBJECT-TYPE
    SYNTAX     Gauge32
    MAX-ACCESS read-only
    STATUS     current
    DESCRIPTION
	    "Page File Bytes is the current number of bytes
	    that this process has used in the paging
	    file(s). Paging files are used to store pages
	    of memory used by the process that are not
	    contained in other files. Paging files are
	    shared by all processes, and the lack of space
	    in paging files can prevent other processes
	    from allocating memory."
    ::= { jobObjectDetailsEntry 18 }

jodPageFileBytesPeak OBJECT-TYPE
    SYNTAX     Gauge32
    MAX-ACCESS read-only
    STATUS     current
    DESCRIPTION
	    "Page File Bytes Peak is the maximum number of
	    bytes this process has used in the paging
	    file(s). Paging files are used to store pages
	    of memory used by the process that are not
	    contained in other files.  Paging files are
	    shared by all processes, and the lack of space
	    in paging files can prevent other processes
	    from allocating memory."
    ::= { jobObjectDetailsEntry 19 }

jodPoolNonpagedBytes OBJECT-TYPE
    SYNTAX     Gauge32
    MAX-ACCESS read-only
    STATUS     current
    DESCRIPTION
	    "Pool Nonpaged Bytes is the size, in bytes, of
	    the nonpaged pool, an area of system memory
	    (physical memory used by the operating system)
	    for objects that cannot be written to disk, but
	    must remain in physical memory as long as they
	    are allocated.  Memory\\Pool Nonpaged Bytes is
	    calculated differently than Process\\Pool
	    Nonpaged Bytes, so it might not equal
	    Process\\Pool Nonpaged Bytes\\_Total.  This
	    counter displays the last observed value only;
	    it is not an average."
    ::= { jobObjectDetailsEntry 20 }

jodPoolPagedBytes OBJECT-TYPE
    SYNTAX     Gauge32
    MAX-ACCESS read-only
    STATUS     current
    DESCRIPTION
	    "Pool Paged Bytes is the size, in bytes, of the
	    paged pool, an area of system memory (physical
	    memory used by the operating system) for
	    objects that can be written to disk when they
	    are not being used.  Memory\\Pool Paged Bytes
	    is calculated differently than Process\\Pool
	    Paged Bytes, so it might not equal
	    Process\\Pool Paged Bytes\\_Total. This counter
	    displays the last observed value only; it is
	    not an average."
    ::= { jobObjectDetailsEntry 21 }

jodPriorityBase OBJECT-TYPE
    SYNTAX     Gauge32
    MAX-ACCESS read-only
    STATUS     current
    DESCRIPTION
	    "The current base priority of this process.
	    Threads within a process can raise and lower
	    their own base priority relative to the
	    process' base priority."
    ::= { jobObjectDetailsEntry 22 }

jodPrivateBytes OBJECT-TYPE
    SYNTAX     Gauge32
    MAX-ACCESS read-only
    STATUS     current
    DESCRIPTION
	    "Private Bytes is the current size, in bytes,
	    of memory that this process has allocated that
	    cannot be shared with other processes."
    ::= { jobObjectDetailsEntry 23 }

jodThreadCount OBJECT-TYPE
    SYNTAX     Gauge32
    MAX-ACCESS read-only
    STATUS     current
    DESCRIPTION
	    "The number of threads currently active in this
	    process. An instruction is the basic unit of
	    execution in a processor, and a thread is the
	    object that executes instructions. Every
	    running process has at least one thread."
    ::= { jobObjectDetailsEntry 24 }

jodVirtualBytes OBJECT-TYPE
    SYNTAX     Gauge32
    MAX-ACCESS read-only
    STATUS     current
    DESCRIPTION
	    "Virtual Bytes is the current size, in bytes,
	    of the virtual address space the process is
	    using. Use of virtual address space does not
	    necessarily imply corresponding use of either
	    disk or main memory pages. Virtual space is
	    finite, and the process can limit its ability
	    to load libraries."
    ::= { jobObjectDetailsEntry 25 }

jodVirtualBytesPeak OBJECT-TYPE
    SYNTAX     Gauge32
    MAX-ACCESS read-only
    STATUS     current
    DESCRIPTION
	    "Virtual Bytes Peak is the maximum size, in
	    bytes, of virtual address space the process has
	    used at any one time. Use of virtual address
	    space does not necessarily imply corresponding
	    use of either disk or main memory pages.
	    However, virtual space is finite, and the
	    process might limit its ability to load
	    libraries."
    ::= { jobObjectDetailsEntry 26 }

jodWorkingSet OBJECT-TYPE
    SYNTAX     Gauge32
    MAX-ACCESS read-only
    STATUS     current
    DESCRIPTION
	    "Working Set is the current size, in bytes, of
	    the Working Set of this process. The Working
	    Set is the set of memory pages touched recently
	    by the threads in the process. If free memory
	    in the computer is above a threshold, pages are
	    left in the Working Set of a process even if
	    they are not in use.  When free memory falls
	    below a threshold, pages are trimmed from
	    Working Sets. If they are needed they will then
	    be soft-faulted back into the Working Set
	    before leaving main memory."
    ::= { jobObjectDetailsEntry 27 }

jodWorkingSetPeak OBJECT-TYPE
    SYNTAX     Gauge32
    MAX-ACCESS read-only
    STATUS     current
    DESCRIPTION
	    "Working Set Peak is the maximum size, in
	    bytes, of the Working Set of this process at
	    any point in time. The Working Set is the set
	    of memory pages touched recently by the threads
	    in the process. If free memory in the computer
	    is above a threshold, pages are left in the
	    Working Set of a process even if they are not
	    in use. When free memory falls below a
	    threshold, pages are trimmed from Working Sets.
	    If they are needed they will then be
	    soft-faulted back into the Working Set before
	    they leave main memory."
    ::= { jobObjectDetailsEntry 28 }

logicalDiskTable OBJECT-TYPE
    SYNTAX     SEQUENCE OF LogicalDiskEntry
    MAX-ACCESS not-accessible
    STATUS     current
    DESCRIPTION
	    "The Logical Disk performance object consists
	    of counters that monitor logical partitions of
	    hard or fixed disk drives. System Monitor
	    identifies logical disks by their drive letter,
	    such as 'C.' To monitor Logical Disk object
	    counters, you must activate them by typing the
	    following at the command prompt: diskperf -yv"
    ::= { advanced 44 }

logicalDiskEntry OBJECT-TYPE
    SYNTAX     LogicalDiskEntry
    MAX-ACCESS not-accessible
    STATUS     current
    DESCRIPTION
	    "Performance information for one particular
	    instance of 'LogicalDisk' object."
    INDEX      { lDiskInstance }
    ::= { logicalDiskTable 1 }

LogicalDiskEntry ::= SEQUENCE {
    lDiskInstance InstanceName,
    lDiskPercentDiskReadTime Gauge32,
    lDiskPercentDiskTime Gauge32,
    lDiskPercentDiskWriteTime Gauge32,
    lDiskPercentFreeSpace Gauge32,
    lDiskPercentIdleTime Gauge32,
    lDiskAvgDiskBytesPerRead Gauge32,
    lDiskAvgDiskBytesPerTransfer Gauge32,
    lDiskAvgDiskBytesPerWrite Gauge32,
    lDiskAvgDiskQueueLength Gauge32,
    lDiskAvgDiskReadQueueLength Gauge32,
    lDiskAvgDiskWriteQueueLength Gauge32,
    lDiskAvgDiskSecPerRead Gauge32,
    lDiskAvgDiskSecPerTransfer Gauge32,
    lDiskAvgDiskSecPerWrite Gauge32,
    lDiskCurrentDiskQueueLength Gauge32,
    lDiskDiskBytesPerSec Gauge32,
    lDiskDiskReadBytesPerSec Gauge32,
    lDiskDiskReadsPerSec Gauge32,
    lDiskDiskTransfersPerSec Gauge32,
    lDiskDiskWriteBytesPerSec Gauge32,
    lDiskDiskWritesPerSec Gauge32,
    lDiskFreeMegabytes Gauge32,
    lDiskSplitIOPerSec Gauge32
}

lDiskInstance OBJECT-TYPE
    SYNTAX     InstanceName
    MAX-ACCESS read-only
    STATUS     current
    DESCRIPTION
	    "Instance name."
    ::= { logicalDiskEntry 1 }

lDiskPercentDiskReadTime OBJECT-TYPE
    SYNTAX     Gauge32
    MAX-ACCESS read-only
    STATUS     current
    DESCRIPTION
	    "% Disk Read Time is the percentage of elapsed
	    time that the selected disk drive was busy
	    servicing read requests."
    ::= { logicalDiskEntry 2 }

lDiskPercentDiskTime OBJECT-TYPE
    SYNTAX     Gauge32
    MAX-ACCESS read-only
    STATUS     current
    DESCRIPTION
	    "% Disk Time is the percentage of elapsed time
	    that the selected disk drive was busy servicing
	    read or write requests."
    ::= { logicalDiskEntry 3 }

lDiskPercentDiskWriteTime OBJECT-TYPE
    SYNTAX     Gauge32
    MAX-ACCESS read-only
    STATUS     current
    DESCRIPTION
	    "% Disk Write Time is the percentage of elapsed
	    time that the selected disk drive was busy
	    servicing write requests."
    ::= { logicalDiskEntry 4 }

lDiskPercentFreeSpace OBJECT-TYPE
    SYNTAX     Gauge32
    MAX-ACCESS read-only
    STATUS     current
    DESCRIPTION
	    "% Free Space is the percentage of total usable
	    space on the selected logical disk drive that
	    was free."
    ::= { logicalDiskEntry 5 }

lDiskPercentIdleTime OBJECT-TYPE
    SYNTAX     Gauge32
    MAX-ACCESS read-only
    STATUS     current
    DESCRIPTION
	    "% Idle Time reports the percentage of time
	    during the sample interval that the disk was
	    idle."
    ::= { logicalDiskEntry 6 }

lDiskAvgDiskBytesPerRead OBJECT-TYPE
    SYNTAX     Gauge32
    MAX-ACCESS read-only
    STATUS     current
    DESCRIPTION
	    "Avg. Disk Bytes/Read is the average number of
	    bytes transferred from the disk during read
	    operations."
    ::= { logicalDiskEntry 7 }

lDiskAvgDiskBytesPerTransfer OBJECT-TYPE
    SYNTAX     Gauge32
    MAX-ACCESS read-only
    STATUS     current
    DESCRIPTION
	    "Avg. Disk Bytes/Transfer is the average number
	    of bytes transferred to or from the disk during
	    write or read operations."
    ::= { logicalDiskEntry 8 }

lDiskAvgDiskBytesPerWrite OBJECT-TYPE
    SYNTAX     Gauge32
    MAX-ACCESS read-only
    STATUS     current
    DESCRIPTION
	    "Avg. Disk Bytes/Write is the average number of
	    bytes transferred to the disk during write
	    operations."
    ::= { logicalDiskEntry 9 }

lDiskAvgDiskQueueLength OBJECT-TYPE
    SYNTAX     Gauge32
    MAX-ACCESS read-only
    STATUS     current
    DESCRIPTION
	    "Avg. Disk Queue Length is the average number
	    of both read and write requests that were
	    queued for the selected disk during the sample
	    interval."
    ::= { logicalDiskEntry 10 }

lDiskAvgDiskReadQueueLength OBJECT-TYPE
    SYNTAX     Gauge32
    MAX-ACCESS read-only
    STATUS     current
    DESCRIPTION
	    "Avg. Disk Read Queue Length is the average
	    number of read requests that were queued for
	    the selected disk during the sample interval."
    ::= { logicalDiskEntry 11 }

lDiskAvgDiskWriteQueueLength OBJECT-TYPE
    SYNTAX     Gauge32
    MAX-ACCESS read-only
    STATUS     current
    DESCRIPTION
	    "Avg. Disk Write Queue Length is the average
	    number of write requests that were queued for
	    the selected disk during the sample interval."
    ::= { logicalDiskEntry 12 }

lDiskAvgDiskSecPerRead OBJECT-TYPE
    SYNTAX     Gauge32
    MAX-ACCESS read-only
    STATUS     current
    DESCRIPTION
	    "Avg. Disk sec/Read is the average time, in
	    seconds, of a read of data from the disk."
    ::= { logicalDiskEntry 13 }

lDiskAvgDiskSecPerTransfer OBJECT-TYPE
    SYNTAX     Gauge32
    MAX-ACCESS read-only
    STATUS     current
    DESCRIPTION
	    "Avg. Disk sec/Transfer is the time, in
	    seconds, of the average disk transfer."
    ::= { logicalDiskEntry 14 }

lDiskAvgDiskSecPerWrite OBJECT-TYPE
    SYNTAX     Gauge32
    MAX-ACCESS read-only
    STATUS     current
    DESCRIPTION
	    "Avg. Disk sec/Write is the average time, in
	    seconds, of a write of data to the disk."
    ::= { logicalDiskEntry 15 }

lDiskCurrentDiskQueueLength OBJECT-TYPE
    SYNTAX     Gauge32
    MAX-ACCESS read-only
    STATUS     current
    DESCRIPTION
	    "Current Disk Queue Length is the number of
	    requests outstanding on the disk at the time
	    the performance data is collected. It also
	    includes requests in service at the time of the
	    collection. This is a instantaneous snapshot,
	    not an average over the time i"
    ::= { logicalDiskEntry 16 }

lDiskDiskBytesPerSec OBJECT-TYPE
    SYNTAX     Gauge32
    MAX-ACCESS read-only
    STATUS     current
    DESCRIPTION
	    "Disk Bytes/sec is the rate bytes are
	    transferred to or from the disk during write or
	    read operations."
    ::= { logicalDiskEntry 17 }

lDiskDiskReadBytesPerSec OBJECT-TYPE
    SYNTAX     Gauge32
    MAX-ACCESS read-only
    STATUS     current
    DESCRIPTION
	    "Disk Read Bytes/sec is the rate at which bytes
	    are transferred from the disk during read
	    operations."
    ::= { logicalDiskEntry 18 }

lDiskDiskReadsPerSec OBJECT-TYPE
    SYNTAX     Gauge32
    MAX-ACCESS read-only
    STATUS     current
    DESCRIPTION
	    "Disk Reads/sec is the rate of read operations
	    on the disk."
    ::= { logicalDiskEntry 19 }

lDiskDiskTransfersPerSec OBJECT-TYPE
    SYNTAX     Gauge32
    MAX-ACCESS read-only
    STATUS     current
    DESCRIPTION
	    "Disk Transfers/sec is the rate of read and
	    write operations on the disk."
    ::= { logicalDiskEntry 20 }

lDiskDiskWriteBytesPerSec OBJECT-TYPE
    SYNTAX     Gauge32
    MAX-ACCESS read-only
    STATUS     current
    DESCRIPTION
	    "Disk Write Bytes/sec is rate at which bytes
	    are transferred to the disk during write
	    operations."
    ::= { logicalDiskEntry 21 }

lDiskDiskWritesPerSec OBJECT-TYPE
    SYNTAX     Gauge32
    MAX-ACCESS read-only
    STATUS     current
    DESCRIPTION
	    "Disk Writes/sec is the rate of write
	    operations on the disk."
    ::= { logicalDiskEntry 22 }

lDiskFreeMegabytes OBJECT-TYPE
    SYNTAX     Gauge32
    MAX-ACCESS read-only
    STATUS     current
    DESCRIPTION
	    "Free Megabytes displays the unallocated space,
	    in megabytes, on the disk drive in megabytes.
	    One megabyte is equal to 1,048,576 bytes."
    ::= { logicalDiskEntry 23 }

lDiskSplitIOPerSec OBJECT-TYPE
    SYNTAX     Gauge32
    MAX-ACCESS read-only
    STATUS     current
    DESCRIPTION
	    "Split IO/Sec reports the rate at which I/Os to
	    the disk were split into multiple I/Os. A split
	    I/O may result from requesting data of a size
	    that is too large to fit into a single I/O or
	    that the disk is fragmented."
    ::= { logicalDiskEntry 24 }

macFileServer OBJECT-IDENTITY
    STATUS     current
    DESCRIPTION
	    "The MacFile Server performance object provides
	    information about a system running File Server
	    for Macintosh."
    ::= { advanced 45 }

mfsCurrentFilesOpen OBJECT-TYPE
    SYNTAX     Gauge32
    MAX-ACCESS read-only
    STATUS     current
    DESCRIPTION
	    "The number of internal files currently open in
	    the MacFile server.  This count does not
	    include files opened on behalf of Macintosh
	    clients."
    ::= { macFileServer 1 }

mfsCurrentNonPagedMemory OBJECT-TYPE
    SYNTAX     Gauge32
    MAX-ACCESS read-only
    STATUS     current
    DESCRIPTION
	    "The current amount of nonpaged memory
	    resources used by the MacFile Server."
    ::= { macFileServer 2 }

mfsCurrentPagedMemory OBJECT-TYPE
    SYNTAX     Gauge32
    MAX-ACCESS read-only
    STATUS     current
    DESCRIPTION
	    "The current amount of paged memory resources
	    used by the MacFile Server."
    ::= { macFileServer 3 }

mfsCurrentQueueLength OBJECT-TYPE
    SYNTAX     Gauge32
    MAX-ACCESS read-only
    STATUS     current
    DESCRIPTION
	    "The number of outstanding work items waiting
	    to be processed."
    ::= { macFileServer 4 }

mfsCurrentSessions OBJECT-TYPE
    SYNTAX     Gauge32
    MAX-ACCESS read-only
    STATUS     current
    DESCRIPTION
	    "The number of sessions currently connected to
	    the MacFile server.  Indicates current server
	    activity."
    ::= { macFileServer 5 }

mfsCurrentThreads OBJECT-TYPE
    SYNTAX     Gauge32
    MAX-ACCESS read-only
    STATUS     current
    DESCRIPTION
	    "The current number of threads used by MacFile
	    server.  Indicates how busy the server is."
    ::= { macFileServer 6 }

mfsDataReadPerSec OBJECT-TYPE
    SYNTAX     Gauge32
    MAX-ACCESS read-only
    STATUS     current
    DESCRIPTION
	    "The number of bytes read from disk per
	    second."
    ::= { macFileServer 7 }

mfsDataReceivedPerSec OBJECT-TYPE
    SYNTAX     Gauge32
    MAX-ACCESS read-only
    STATUS     current
    DESCRIPTION
	    "The number of bytes received from the network
	    per second.  Indicates how busy the server is."
    ::= { macFileServer 8 }

mfsDataTransmittedPerSec OBJECT-TYPE
    SYNTAX     Gauge32
    MAX-ACCESS read-only
    STATUS     current
    DESCRIPTION
	    "The number of bytes sent on the network per
	    second.  Indicates how busy the server is."
    ::= { macFileServer 9 }

mfsDataWrittenPerSec OBJECT-TYPE
    SYNTAX     Gauge32
    MAX-ACCESS read-only
    STATUS     current
    DESCRIPTION
	    "The number of bytes written to disk per
	    second."
    ::= { macFileServer 10 }

mfsFailedLogons OBJECT-TYPE
    SYNTAX     Gauge32
    MAX-ACCESS read-only
    STATUS     current
    DESCRIPTION
	    "The number of failed logon attempts to the
	    MacFile server.  Can indicate whether password
	    guessing programs are being used to crack the
	    security on the server."
    ::= { macFileServer 11 }

mfsMaxNonPagedMemory OBJECT-TYPE
    SYNTAX     Gauge32
    MAX-ACCESS read-only
    STATUS     current
    DESCRIPTION
	    "The maximum amount of nonpaged memory
	    resources use by the MacFile Server."
    ::= { macFileServer 12 }

mfsMaxPagedMemory OBJECT-TYPE
    SYNTAX     Gauge32
    MAX-ACCESS read-only
    STATUS     current
    DESCRIPTION
	    "The maximum amount of paged memory resources
	    used by the MacFile Server."
    ::= { macFileServer 13 }

mfsMaximumFilesOpen OBJECT-TYPE
    SYNTAX     Gauge32
    MAX-ACCESS read-only
    STATUS     current
    DESCRIPTION
	    "The maximum number of internal files open at
	    one time in the MacFile server.  This count
	    does not include files opened on behalf of
	    Macintosh clients."
    ::= { macFileServer 14 }

mfsMaximumQueueLength OBJECT-TYPE
    SYNTAX     Gauge32
    MAX-ACCESS read-only
    STATUS     current
    DESCRIPTION
	    "The maximum number of outstanding work items
	    waiting at one time."
    ::= { macFileServer 15 }

mfsMaximumSessions OBJECT-TYPE
    SYNTAX     Gauge32
    MAX-ACCESS read-only
    STATUS     current
    DESCRIPTION
	    "The maximum number of sessions connected at
	    one time to the MacFile server.  Indicates
	    usage level of server."
    ::= { macFileServer 16 }

mfsMaximumThreads OBJECT-TYPE
    SYNTAX     Gauge32
    MAX-ACCESS read-only
    STATUS     current
    DESCRIPTION
	    "The maximum number of threads used by MacFile
	    server.  Indicates peak usage level of server."
    ::= { macFileServer 17 }

memory OBJECT-IDENTITY
    STATUS     current
    DESCRIPTION
	    "The Memory performance object consists of
	    counters that describe the behavior of physical
	    and virtual memory on the computer. Physical
	    memory is the amount of random-access memory
	    (RAM) on the computer. Virtual memory consists
	    of space in physical memory and on disk. Many
	    of the memory counters monitor paging, which is
	    the movement of pages of code and data between
	    disk and physical memory. Excessive paging, a
	    symptom of a memory shortage, can cause delays
	    which interfere with all system processes."
    ::= { advanced 46 }

memoryPercentCommittedBytesInUse OBJECT-TYPE
    SYNTAX     Gauge32
    MAX-ACCESS read-only
    STATUS     current
    DESCRIPTION
	    "% Committed Bytes In Use is the ratio of
	    Memory\\Committed Bytes to the Memory\\Commit
	    Limit. Committed memory is the physical memory
	    in use for which space has been reserved in the
	    paging file should it need to be written to
	    disk. The commit limit is determined by the
	    size of the paging file.  If the paging file is
	    enlarged, the commit limit increases, and the
	    ratio is reduced). This counter displays the
	    current percentage value only; it is not an
	    average."
    ::= { memory 1 }

memoryAvailableBytes OBJECT-TYPE
    SYNTAX     Gauge32
    MAX-ACCESS read-only
    STATUS     current
    DESCRIPTION
	    "Available Bytes is the amount of physical
	    memory, in bytes, immediately available for
	    allocation to a process or for system use. It
	    is equal to the sum of memory assigned to the
	    standby (cached), free and zero page lists. For
	    a full explanation of the memory manager, refer
	    to MSDN and/or the System Performance and
	    Troubleshooting Guide chapter in the Windows
	    Server 2003 Resource Kit."
    ::= { memory 2 }

memoryAvailableKBytes OBJECT-TYPE
    SYNTAX     Gauge32
    MAX-ACCESS read-only
    STATUS     current
    DESCRIPTION
	    "Available KBytes is the amount of physical
	    memory, in Kilobytes, immediately available for
	    allocation to a process or for system use. It
	    is equal to the sum of memory assigned to the
	    standby (cached), free and zero page lists. For
	    a full explanation of the memory manager, refer
	    to MSDN and/or the System Performance and
	    Troubleshooting Guide chapter in the Windows
	    Server 2003 Resource Kit."
    ::= { memory 3 }

memoryAvailableMBytes OBJECT-TYPE
    SYNTAX     Gauge32
    MAX-ACCESS read-only
    STATUS     current
    DESCRIPTION
	    "Available MBytes is the amount of physical
	    memory, in Megabytes, immediately available for
	    allocation to a process or for system use. It
	    is equal to the sum of memory assigned to the
	    standby (cached), free and zero page lists. For
	    a full explanation of the memory manager, refer
	    to MSDN and/or the System Performance and
	    Troubleshooting Guide chapter in the Windows
	    Server 2003 Resource Kit."
    ::= { memory 4 }

memoryCacheBytes OBJECT-TYPE
    SYNTAX     Gauge32
    MAX-ACCESS read-only
    STATUS     current
    DESCRIPTION
	    "Cache Bytes is the sum of the Memory\\System
	    Cache Resident Bytes, Memory\\System Driver
	    Resident Bytes, Memory\\System Code Resident
	    Bytes, and Memory\\Pool Paged Resident Bytes
	    counters.  This counter displays the last
	    observed value only; it is not an average. "
    ::= { memory 5 }

memoryCacheBytesPeak OBJECT-TYPE
    SYNTAX     Gauge32
    MAX-ACCESS read-only
    STATUS     current
    DESCRIPTION
	    "Cache Bytes Peak is the maximum number of
	    bytes used by the file system cache since the
	    system was last restarted. This might be larger
	    than the current size of the cache. This
	    counter displays the last observed value only;
	    it is not an average. "
    ::= { memory 6 }

memoryCacheFaultsPerSec OBJECT-TYPE
    SYNTAX     Gauge32
    MAX-ACCESS read-only
    STATUS     current
    DESCRIPTION
	    "Cache Faults/sec is the rate at which faults
	    occur when a page sought in the file system
	    cache is not found and must be retrieved from
	    elsewhere in memory (a soft fault) or from disk
	    (a hard fault). The file system cache is an
	    area of physical memory that stores recently
	    used pages of data for applications. Cache
	    activity is a reliable indicator of most
	    application I/O operations. This counter shows
	    the number of faults, without regard for the
	    number of pages faulted in each operation."
    ::= { memory 7 }

memoryCommitLimit OBJECT-TYPE
    SYNTAX     Gauge32
    MAX-ACCESS read-only
    STATUS     current
    DESCRIPTION
	    "Commit Limit is the amount of virtual memory
	    that can be committed without having to extend
	    the paging file(s).  It is measured in bytes.
	    Committed memory is the physical memory which
	    has space reserved on the disk paging files.
	    There can be one paging file on each logical
	    drive). If the paging file(s) are be expanded,
	    this limit increases accordingly.  This counter
	    displays the last observed value only; it is
	    not an average."
    ::= { memory 8 }

memoryCommittedBytes OBJECT-TYPE
    SYNTAX     Gauge32
    MAX-ACCESS read-only
    STATUS     current
    DESCRIPTION
	    "Committed Bytes is the amount of committed
	    virtual memory, in bytes. Committed memory is
	    the physical memory which has space reserved on
	    the disk paging file(s). There can be one or
	    more paging files on each physical drive. This
	    counter displays the last observed value only;
	    it is not an average."
    ::= { memory 9 }

memoryDemandZeroFaultsPerSec OBJECT-TYPE
    SYNTAX     Gauge32
    MAX-ACCESS read-only
    STATUS     current
    DESCRIPTION
	    "Demand Zero Faults/sec is the rate at which a
	    zeroed page is required to satisfy the fault. 
	    Zeroed pages, pages emptied of previously
	    stored data and filled with zeros, are a
	    security feature of Windows that prevent
	    processes from seeing data stored by earlier
	    processes that used the memory space. Windows
	    maintains a list of zeroed pages to accelerate
	    this process. This counter shows the number of
	    faults, without regard to the number of pages
	    retrieved to satisfy the fault. This counter
	    displays the difference between the values
	    observed in the last two samples, divided by
	    the duration of the sample interval."
    ::= { memory 10 }

memoryFreeSystemPageTableEntries OBJECT-TYPE
    SYNTAX     Gauge32
    MAX-ACCESS read-only
    STATUS     current
    DESCRIPTION
	    "Free System Page Table Entries is the number
	    of page table entries not currently in used by
	    the system.  This counter displays the last
	    observed value only; it is not an average. "
    ::= { memory 11 }

memoryPageFaultsPerSec OBJECT-TYPE
    SYNTAX     Gauge32
    MAX-ACCESS read-only
    STATUS     current
    DESCRIPTION
	    "Page Faults/sec is the average number of pages
	    faulted per second. It is measured in number of
	    pages faulted per second because only one page
	    is faulted in each fault operation, hence this
	    is also equal to the number of page fault
	    operations. This counter includes both hard
	    faults (those that require disk access) and
	    soft faults (where the faulted page is found
	    elsewhere in physical memory.) Most processors
	    can handle large numbers of soft faults without
	    significant consequence. However, hard faults,
	    which require disk access, can cause
	    significant delays."
    ::= { memory 12 }

memoryPageReadsPerSec OBJECT-TYPE
    SYNTAX     Gauge32
    MAX-ACCESS read-only
    STATUS     current
    DESCRIPTION
	    "Page Reads/sec is the rate at which the disk
	    was read to resolve hard page faults. It shows
	    the number of reads operations, without regard
	    to the number of pages retrieved in each
	    operation. Hard page faults occur when a
	    process references a page in virtual memory
	    that is not in working set or elsewhere in
	    physical memory, and must be retrieved from
	    disk. This counter is a primary indicator of
	    the kinds of faults that cause system-wide
	    delays. It includes read operations to satisfy
	    faults in the file system cache (usually
	    requested by applications) and in non-cached
	    mapped memory files. Compare the value of
	    Memory\\Pages Reads/sec to the value of
	    Memory\\Pages Input/sec to determine the
	    average number of pages read during each
	    operation."
    ::= { memory 13 }

memoryPageWritesPerSec OBJECT-TYPE
    SYNTAX     Gauge32
    MAX-ACCESS read-only
    STATUS     current
    DESCRIPTION
	    "Page Writes/sec is the rate at which pages are
	    written to disk to free up space in physical
	    memory. Pages are written to disk only if they
	    are changed while in physical memory, so they
	    are likely to hold data, not code.	This
	    counter shows write operations, without regard
	    to the number of pages written in each
	    operation.	This counter displays the
	    difference between the values observed in the
	    last two samples, divided by the duration of
	    the sample interval."
    ::= { memory 14 }

memoryPagesInputPerSec OBJECT-TYPE
    SYNTAX     Gauge32
    MAX-ACCESS read-only
    STATUS     current
    DESCRIPTION
	    "Pages Input/sec is the rate at which pages are
	    read from disk to resolve hard page faults.
	    Hard page faults occur when a process refers to
	    a page in virtual memory that is not in its
	    working set or elsewhere in physical memory,
	    and must be retrieved from disk. When a page is
	    faulted, the system tries to read multiple
	    contiguous pages into memory to maximize the
	    benefit of the read operation. Compare the
	    value of Memory\\Pages Input/sec to the value
	    of	Memory\\Page Reads/sec to determine the
	    average number of pages read into memory during
	    each read operation."
    ::= { memory 15 }

memoryPagesOutputPerSec OBJECT-TYPE
    SYNTAX     Gauge32
    MAX-ACCESS read-only
    STATUS     current
    DESCRIPTION
	    "Pages Output/sec is the rate at which pages
	    are written to disk to free up space in
	    physical memory. Pages are written back to disk
	    only if they are changed in physical memory, so
	    they are likely to hold data, not code. A high
	    rate of pages output might indicate a memory
	    shortage. Windows writes more pages back to
	    disk to free up space when physical memory is
	    in short supply.  This counter shows the number
	    of pages, and can be compared to other counts
	    of pages, without conversion."
    ::= { memory 16 }

memoryPagesPerSec OBJECT-TYPE
    SYNTAX     Gauge32
    MAX-ACCESS read-only
    STATUS     current
    DESCRIPTION
	    "Pages/sec is the rate at which pages are read
	    from or written to disk to resolve hard page
	    faults. This counter is a primary indicator of
	    the kinds of faults that cause system-wide
	    delays.  It is the sum of Memory\\Pages
	    Input/sec and Memory\\Pages Output/sec.  It is
	    counted in numbers of pages, so it can be
	    compared to other counts of pages, such as
	    Memory\\Page Faults/sec, without conversion. It
	    includes pages retrieved to satisfy faults in
	    the file system cache (usually requested by
	    applications) non-cached mapped memory files."
    ::= { memory 17 }

memoryPoolNonpagedAllocs OBJECT-TYPE
    SYNTAX     Gauge32
    MAX-ACCESS read-only
    STATUS     current
    DESCRIPTION
	    "Pool Nonpaged Allocs is the number of calls to
	    allocate space in the nonpaged pool. The
	    nonpaged pool is an area of system memory area
	    for objects that cannot be written to disk, and
	    must remain in physical memory as long as they
	    are allocated.  It is measured in numbers of
	    calls to allocate space, regardless of the
	    amount of space allocated in each call.  This
	    counter displays the last observed value only;
	    it is not an average."
    ::= { memory 18 }

memoryPoolNonpagedBytes OBJECT-TYPE
    SYNTAX     Gauge32
    MAX-ACCESS read-only
    STATUS     current
    DESCRIPTION
	    "Pool Nonpaged Bytes is the size, in bytes, of
	    the nonpaged pool, an area of system memory
	    (physical memory used by the operating system)
	    for objects that cannot be written to disk, but
	    must remain in physical memory as long as they
	    are allocated.  Memory\\Pool Nonpaged Bytes is
	    calculated differently than Process\\Pool
	    Nonpaged Bytes, so it might not equal
	    Process\\Pool Nonpaged Bytes\\_Total.  This
	    counter displays the last observed value only;
	    it is not an average."
    ::= { memory 19 }

memoryPoolPagedAllocs OBJECT-TYPE
    SYNTAX     Gauge32
    MAX-ACCESS read-only
    STATUS     current
    DESCRIPTION
	    "Pool Paged Allocs is the number of calls to
	    allocate space in the paged pool. The paged
	    pool is an area of system memory (physical
	    memory used by the operating system) for
	    objects that can be written to disk when they
	    are not being used. It is measured in numbers
	    of calls to allocate space, regardless of the
	    amount of space allocated in each call.  This
	    counter displays the last observed value only;
	    it is not an average."
    ::= { memory 20 }

memoryPoolPagedBytes OBJECT-TYPE
    SYNTAX     Gauge32
    MAX-ACCESS read-only
    STATUS     current
    DESCRIPTION
	    "Pool Paged Bytes is the size, in bytes, of the
	    paged pool, an area of system memory (physical
	    memory used by the operating system) for
	    objects that can be written to disk when they
	    are not being used.  Memory\\Pool Paged Bytes
	    is calculated differently than Process\\Pool
	    Paged Bytes, so it might not equal
	    Process\\Pool Paged Bytes\\_Total. This counter
	    displays the last observed value only; it is
	    not an average."
    ::= { memory 21 }

memoryPoolPagedResidentBytes OBJECT-TYPE
    SYNTAX     Gauge32
    MAX-ACCESS read-only
    STATUS     current
    DESCRIPTION
	    "Pool Paged Resident Bytes is the current size,
	    in bytes, of the paged pool. The paged pool is
	    an area of system memory (physical memory used
	    by the operating system) for objects that can
	    be written to disk when they are not being
	    used. Space used by the paged and nonpaged
	    pools are taken from physical memory, so a pool
	    that is too large denies memory space to
	    processes. This counter displays the last
	    observed value only; it is not an average."
    ::= { memory 22 }

memorySystemCacheResidentBytes OBJECT-TYPE
    SYNTAX     Gauge32
    MAX-ACCESS read-only
    STATUS     current
    DESCRIPTION
	    "System Cache Resident Bytes is the size, in
	    bytes, of the pageable operating system code in
	    the file system cache. This value includes only
	    current physical pages and does not include any
	    virtual memory pages not currently resident. It
	    does equal the System Cache value shown in Task
	    Manager. As a result, this value may be smaller
	    than the actual amount of virtual memory in use
	    by the file system cache. This value is a
	    component of Memory\\System Code Resident Bytes
	    which represents all pageable operating system
	    code that is currently in physical memory. This
	    counter displays the last observed value only;
	    it is not an average. "
    ::= { memory 23 }

memorySystemCodeResidentBytes OBJECT-TYPE
    SYNTAX     Gauge32
    MAX-ACCESS read-only
    STATUS     current
    DESCRIPTION
	    "System Code Resident Bytes is the size, in
	    bytes of the operating system code currently in
	    physical memory that can be written to disk
	    when not in use. This value is a component of
	    Memory\\System Code Total Bytes, which also
	    includes operating system code on disk.
	    Memory\\System Code Resident Bytes (and
	    Memory\\System Code Total Bytes) does not
	    include code that must remain in physical
	    memory and cannot be written to disk. This
	    counter displays the last observed value only;
	    it is not an average."
    ::= { memory 24 }

memorySystemCodeTotalBytes OBJECT-TYPE
    SYNTAX     Gauge32
    MAX-ACCESS read-only
    STATUS     current
    DESCRIPTION
	    "System Code Total Bytes is the size, in bytes,
	    of the pageable operating system code currently
	    in virtual memory. It is a measure of the
	    amount of physical memory being used by the
	    operating system that can be written to disk
	    when not in use. This value is calculated by
	    summing the bytes in Ntoskrnl.exe, Hal.dll, the
	    boot drivers, and file systems loaded by
	    Ntldr/osloader.  This counter does not include
	    code that must remain in physical memory and
	    cannot be written to disk. This counter
	    displays the last observed value only; it is
	    not an average."
    ::= { memory 25 }

memorySystemDriverResidentBytes OBJECT-TYPE
    SYNTAX     Gauge32
    MAX-ACCESS read-only
    STATUS     current
    DESCRIPTION
	    "System Driver Resident Bytes is the size, in
	    bytes, of the pageable physical memory being
	    used by device drivers. It is the working set
	    (physical memory area) of the drivers. This
	    value is a component of Memory\\System Driver
	    Total Bytes, which also includes driver memory
	    that has been written to disk. Neither
	    Memory\\System Driver Resident Bytes nor
	    Memory\\System Driver Total Bytes includes
	    memory that cannot be written to disk."
    ::= { memory 26 }

memorySystemDriverTotalBytes OBJECT-TYPE
    SYNTAX     Gauge32
    MAX-ACCESS read-only
    STATUS     current
    DESCRIPTION
	    "System Driver Total Bytes is the size, in
	    bytes, of the pageable virtual memory currently
	    being used by device drivers. Pageable memory
	    can be written to disk when it is not being
	    used. It includes physical memory
	    (Memory\\System Driver Resident Bytes) and code
	    and data paged to disk. It is a component of
	    Memory\\System Code Total Bytes. This counter
	    displays the last observed value only; it is
	    not an average.  "
    ::= { memory 27 }

memoryTranFaultsPerSec OBJECT-TYPE
    SYNTAX     Gauge32
    MAX-ACCESS read-only
    STATUS     current
    DESCRIPTION
	    "Transition Faults/sec is the rate at which
	    page faults are resolved by recovering pages
	    that were being used by another process sharing
	    the page, or were on the modified page list or
	    the standby list, or were being written to disk
	    at the time of the page fault. The pages were
	    recovered without additional disk activity.
	    Transition faults are counted in numbers of
	    faults; because only one page is faulted in
	    each operation, it is also equal to the number
	    of pages faulted."
    ::= { memory 28 }

memoryTranPagesRePurposedPerSec OBJECT-TYPE
    SYNTAX     Gauge32
    MAX-ACCESS read-only
    STATUS     current
    DESCRIPTION
	    "Transition Pages RePurposed is the rate at
	    which the number of transition cache pages were
	    reused for a different purpose.  These pages
	    would have otherwise remained in the page cache
	    to provide a (fast) soft fault (instead of
	    retrieving it from backing store) in the event
	    the page was accessed in the future.  Note
	    these pages can contain private or sharable
	    memory."
    ::= { memory 29 }

memoryWriteCopiesPerSec OBJECT-TYPE
    SYNTAX     Gauge32
    MAX-ACCESS read-only
    STATUS     current
    DESCRIPTION
	    "Write Copies/sec is the rate at which page
	    faults are caused by attempts to write that
	    have been satisfied by coping of the page from
	    elsewhere in physical memory. This is an
	    economical way of sharing data since pages are
	    only copied when they are written to;
	    otherwise, the page is shared. This counter
	    shows the number of copies, without regard for
	    the number of pages copied in each operation."
    ::= { memory 30 }

memoryCacheKBytes OBJECT-TYPE
    SYNTAX     Gauge32
    MAX-ACCESS read-only
    STATUS     current
    DESCRIPTION
	    "Cache KiloBytes is the sum of the
	    Memory\\System Cache Resident KiloBytes,
	    Memory\\System Driver Resident KiloBytes,
	    Memory\\System Code Resident KiloBytes, and
	    Memory\\Pool Paged Resident KiloBytes counters.
	     This counter displays the last observed value
	    only; it is not an average. "
    ::= { memory 31 }

memoryCacheKBytesPeak OBJECT-TYPE
    SYNTAX     Gauge32
    MAX-ACCESS read-only
    STATUS     current
    DESCRIPTION
	    "Cache KiloBytes Peak is the maximum number of
	    kilobytes used by the file system cache since
	    the system was last restarted. This might be
	    larger than the current size of the cache. This
	    counter displays the last observed value only;
	    it is not an average. "
    ::= { memory 32 }

memoryCommittedKBytes OBJECT-TYPE
    SYNTAX     Gauge32
    MAX-ACCESS read-only
    STATUS     current
    DESCRIPTION
	    "Committed KiloBytes is the amount of committed
	    virtual memory, in kilobytes. Committed memory
	    is the physical memory which has space reserved
	    on the disk paging file(s). There can be one or
	    more paging files on each physical drive. This
	    counter displays the last observed value only;
	    it is not an average."
    ::= { memory 33 }

memoryPoolNonpagedKBytes OBJECT-TYPE
    SYNTAX     Gauge32
    MAX-ACCESS read-only
    STATUS     current
    DESCRIPTION
	    "Pool Nonpaged KiloBytes is the size, in
	    kilobytes, of the nonpaged pool, an area of
	    system memory (physical memory used by the
	    operating system) for objects that cannot be
	    written to disk, but must remain in physical
	    memory as long as they are allocated. 
	    Memory\\Pool Nonpaged KiloBytes is calculated
	    differently than Process\\Pool Nonpaged
	    KiloBytes, so it might not equal Process\\Pool
	    Nonpaged KiloBytes\\_Total.  This counter
	    displays the last observed value only; it is
	    not an average."
    ::= { memory 34 }

memoryPoolPagedKBytes OBJECT-TYPE
    SYNTAX     Gauge32
    MAX-ACCESS read-only
    STATUS     current
    DESCRIPTION
	    "Pool Paged KiloBytes is the size, in
	    kilobytes, of the paged pool, an area of system
	    memory (physical memory used by the operating
	    system) for objects that can be written to disk
	    when they are not being used.  Memory\\Pool
	    Paged KiloBytes is calculated differently than
	    Process\\Pool Paged KiloBytes, so it might not
	    equal Process\\Pool Paged KiloBytes\\_Total.
	    This counter displays the last observed value
	    only; it is not an average."
    ::= { memory 35 }

memoryPoolPagedResidentKBytes OBJECT-TYPE
    SYNTAX     Gauge32
    MAX-ACCESS read-only
    STATUS     current
    DESCRIPTION
	    "Pool Paged Resident KiloBytes is the current
	    size, in kilobytes, of the paged pool. The
	    paged pool is an area of system memory
	    (physical memory used by the operating system)
	    for objects that can be written to disk when
	    they are not being used. Space used by the
	    paged and nonpaged pools are taken from
	    physical memory, so a pool that is too large
	    denies memory space to processes. This counter
	    displays the last observed value only; it is
	    not an average."
    ::= { memory 36 }

memorySystemCacheResidentKBytes OBJECT-TYPE
    SYNTAX     Gauge32
    MAX-ACCESS read-only
    STATUS     current
    DESCRIPTION
	    "System Cache Resident KiloBytes is the size,
	    in kilobytes, of the pageable operating system
	    code in the file system cache. This value
	    includes only current physical pages and does
	    not include any virtual memory pages not
	    currently resident. It does equal the System
	    Cache value shown in Task Manager. As a result,
	    this value may be smaller than the actual
	    amount of virtual memory in use by the file
	    system cache. This value is a component of
	    Memory\\System Code Resident KiloBytes which
	    represents all pageable operating system code
	    that is currently in physical memory. This
	    counter displays the last observed value only;
	    it is not an average. "
    ::= { memory 37 }

memorySystemCodeResidentKBytes OBJECT-TYPE
    SYNTAX     Gauge32
    MAX-ACCESS read-only
    STATUS     current
    DESCRIPTION
	    "System Code Resident KiloBytes is the size, in
	    kilobytes of the operating system code
	    currently in physical memory that can be
	    written to disk when not in use. This value is
	    a component of Memory\\System Code Total
	    KiloBytes, which also includes operating system
	    code on disk. Memory\\System Code Resident
	    KiloBytes (and Memory\\System Code Total
	    KiloBytes) does not include code that must
	    remain in physical memory and cannot be written
	    to disk. This counter displays the last
	    observed value only; it is not an average."
    ::= { memory 38 }

memorySystemCodeTotalKBytes OBJECT-TYPE
    SYNTAX     Gauge32
    MAX-ACCESS read-only
    STATUS     current
    DESCRIPTION
	    "System Code Total KiloBytes is the size, in
	    kilobytes, of the pageable operating system
	    code currently in virtual memory. It is a
	    measure of the amount of physical memory being
	    used by the operating system that can be
	    written to disk when not in use. This value is
	    calculated by summing the kilobytes in
	    Ntoskrnl.exe, Hal.dll, the boot drivers, and
	    file systems loaded by Ntldr/osloader.  This
	    counter does not include code that must remain
	    in physical memory and cannot be written to
	    disk. This counter displays the last observed
	    value only; it is not an average."
    ::= { memory 39 }

memorySystemDriverResidentKBytes OBJECT-TYPE
    SYNTAX     Gauge32
    MAX-ACCESS read-only
    STATUS     current
    DESCRIPTION
	    "System Driver Resident KiloBytes is the size,
	    in kilobytes, of the pageable physical memory
	    being used by device drivers. It is the working
	    set (physical memory area) of the drivers. This
	    value is a component of Memory\\System Driver
	    Total KiloBytes, which also includes driver
	    memory that has been written to disk. Neither
	    Memory\\System Driver Resident KiloBytes nor
	    Memory\\System Driver Total KiloBytes includes
	    memory that cannot be written to disk."
    ::= { memory 40 }

memorySystemDriverTotalKBytes OBJECT-TYPE
    SYNTAX     Gauge32
    MAX-ACCESS read-only
    STATUS     current
    DESCRIPTION
	    "System Driver Total KiloBytes is the size, in
	    kilobytes, of the pageable virtual memory
	    currently being used by device drivers.
	    Pageable memory can be written to disk when it
	    is not being used. It includes physical memory
	    (Memory\\System Driver Resident KiloBytes) and
	    code and data paged to disk. It is a component
	    of Memory\\System Code Total KiloBytes. This
	    counter displays the last observed value only;
	    it is not an average.  "
    ::= { memory 41 }

memoryCacheMBytes OBJECT-TYPE
    SYNTAX     Gauge32
    MAX-ACCESS read-only
    STATUS     current
    DESCRIPTION
	    "Cache MegaBytes is the sum of the
	    Memory\\System Cache Resident MegaBytes,
	    Memory\\System Driver Resident MegaBytes,
	    Memory\\System Code Resident MegaBytes, and
	    Memory\\Pool Paged Resident MegaBytes counters.
	     This counter displays the last observed value
	    only; it is not an average. "
    ::= { memory 42 }

memoryCacheMBytesPeak OBJECT-TYPE
    SYNTAX     Gauge32
    MAX-ACCESS read-only
    STATUS     current
    DESCRIPTION
	    "Cache MegaBytes Peak is the maximum number of
	    megabytes used by the file system cache since
	    the system was last restarted. This might be
	    larger than the current size of the cache. This
	    counter displays the last observed value only;
	    it is not an average. "
    ::= { memory 43 }

memoryCommittedMBytes OBJECT-TYPE
    SYNTAX     Gauge32
    MAX-ACCESS read-only
    STATUS     current
    DESCRIPTION
	    "Committed MegaBytes is the amount of committed
	    virtual memory, in megabytes. Committed memory
	    is the physical memory which has space reserved
	    on the disk paging file(s). There can be one or
	    more paging files on each physical drive. This
	    counter displays the last observed value only;
	    it is not an average."
    ::= { memory 44 }

memoryPoolNonpagedMBytes OBJECT-TYPE
    SYNTAX     Gauge32
    MAX-ACCESS read-only
    STATUS     current
    DESCRIPTION
	    "Pool Nonpaged MegaBytes is the size, in
	    megabytes, of the nonpaged pool, an area of
	    system memory (physical memory used by the
	    operating system) for objects that cannot be
	    written to disk, but must remain in physical
	    memory as long as they are allocated. 
	    Memory\\Pool Nonpaged MegaBytes is calculated
	    differently than Process\\Pool Nonpaged
	    MegaBytes, so it might not equal Process\\Pool
	    Nonpaged MegaBytes\\_Total.  This counter
	    displays the last observed value only; it is
	    not an average."
    ::= { memory 45 }

memoryPoolPagedMBytes OBJECT-TYPE
    SYNTAX     Gauge32
    MAX-ACCESS read-only
    STATUS     current
    DESCRIPTION
	    "Pool Paged MegaBytes is the size, in
	    megabytes, of the paged pool, an area of system
	    memory (physical memory used by the operating
	    system) for objects that can be written to disk
	    when they are not being used.  Memory\\Pool
	    Paged MegaBytes is calculated differently than
	    Process\\Pool Paged MegaBytes, so it might not
	    equal Process\\Pool Paged MegaBytes\\_Total.
	    This counter displays the last observed value
	    only; it is not an average."
    ::= { memory 46 }

memoryPoolPagedResidentMBytes OBJECT-TYPE
    SYNTAX     Gauge32
    MAX-ACCESS read-only
    STATUS     current
    DESCRIPTION
	    "Pool Paged Resident MegaBytes is the current
	    size, in megabytes, of the paged pool. The
	    paged pool is an area of system memory
	    (physical memory used by the operating system)
	    for objects that can be written to disk when
	    they are not being used. Space used by the
	    paged and nonpaged pools are taken from
	    physical memory, so a pool that is too large
	    denies memory space to processes. This counter
	    displays the last observed value only; it is
	    not an average."
    ::= { memory 47 }

memorySystemCacheResidentMBytes OBJECT-TYPE
    SYNTAX     Gauge32
    MAX-ACCESS read-only
    STATUS     current
    DESCRIPTION
	    "System Cache Resident MegaBytes is the size,
	    in megabytes, of the pageable operating system
	    code in the file system cache. This value
	    includes only current physical pages and does
	    not include any virtual memory pages not
	    currently resident. It does equal the System
	    Cache value shown in Task Manager. As a result,
	    this value may be smaller than the actual
	    amount of virtual memory in use by the file
	    system cache. This value is a component of
	    Memory\\System Code Resident MegaBytes which
	    represents all pageable operating system code
	    that is currently in physical memory. This
	    counter displays the last observed value only;
	    it is not an average. "
    ::= { memory 48 }

memorySystemCodeResidentMBytes OBJECT-TYPE
    SYNTAX     Gauge32
    MAX-ACCESS read-only
    STATUS     current
    DESCRIPTION
	    "System Code Resident MegaBytes is the size, in
	    megabytes of the operating system code
	    currently in physical memory that can be
	    written to disk when not in use. This value is
	    a component of Memory\\System Code Total
	    MegaBytes, which also includes operating system
	    code on disk. Memory\\System Code Resident
	    MegaBytes (and Memory\\System Code Total
	    MegaBytes) does not include code that must
	    remain in physical memory and cannot be written
	    to disk. This counter displays the last
	    observed value only; it is not an average."
    ::= { memory 49 }

memorySystemCodeTotalMBytes OBJECT-TYPE
    SYNTAX     Gauge32
    MAX-ACCESS read-only
    STATUS     current
    DESCRIPTION
	    "System Code Total MegaBytes is the size, in
	    megabytes, of the pageable operating system
	    code currently in virtual memory. It is a
	    measure of the amount of physical memory being
	    used by the operating system that can be
	    written to disk when not in use. This value is
	    calculated by summing the megabytes in
	    Ntoskrnl.exe, Hal.dll, the boot drivers, and
	    file systems loaded by Ntldr/osloader.  This
	    counter does not include code that must remain
	    in physical memory and cannot be written to
	    disk. This counter displays the last observed
	    value only; it is not an average."
    ::= { memory 50 }

memorySystemDriverResidentMBytes OBJECT-TYPE
    SYNTAX     Gauge32
    MAX-ACCESS read-only
    STATUS     current
    DESCRIPTION
	    "System Driver Resident MegaBytes is the size,
	    in megabytes, of the pageable physical memory
	    being used by device drivers. It is the working
	    set (physical memory area) of the drivers. This
	    value is a component of Memory\\System Driver
	    Total MegaBytes, which also includes driver
	    memory that has been written to disk. Neither
	    Memory\\System Driver Resident MegaBytes nor
	    Memory\\System Driver Total MegaBytes includes
	    memory that cannot be written to disk."
    ::= { memory 51 }

memorySystemDriverTotalMBytes OBJECT-TYPE
    SYNTAX     Gauge32
    MAX-ACCESS read-only
    STATUS     current
    DESCRIPTION
	    "System Driver Total MegaBytes is the size, in
	    megabytes, of the pageable virtual memory
	    currently being used by device drivers.
	    Pageable memory can be written to disk when it
	    is not being used. It includes physical memory
	    (Memory\\System Driver Resident MegaBytes) and
	    code and data paged to disk. It is a component
	    of Memory\\System Code Total MegaBytes. This
	    counter displays the last observed value only;
	    it is not an average.  "
    ::= { memory 52 }

msmqQueueTable OBJECT-TYPE
    SYNTAX     SEQUENCE OF MSMQQueueEntry
    MAX-ACCESS not-accessible
    STATUS     current
    DESCRIPTION
	    "The MSMQ Queue performance object monitors
	    message statistics for a selected queue. There
	    are instances for each queue on the computer.
	    In addition, if an Message Queuing-based
	    application has a private queue open on another
	    computer, an instance for that queue is also
	    available. The computer queues instance
	    represents the computer's source journal and
	    dead letter queues."
    ::= { advanced 47 }

msmqQueueEntry OBJECT-TYPE
    SYNTAX     MSMQQueueEntry
    MAX-ACCESS not-accessible
    STATUS     current
    DESCRIPTION
	    "Performance information for one particular
	    instance of 'MSMQ Queue' object."
    INDEX      { msmqInstance }
    ::= { msmqQueueTable 1 }

MSMQQueueEntry ::= SEQUENCE {
    msmqInstance InstanceName,
    msmqBytesInJournalQueue Gauge32,
    msmqBytesInQueue Gauge32,
    msmqMessagesInJournalQueue Gauge32,
    msmqMessagesInQueue Gauge32
}

msmqInstance OBJECT-TYPE
    SYNTAX     InstanceName
    MAX-ACCESS read-only
    STATUS     current
    DESCRIPTION
	    "Instance name."
    ::= { msmqQueueEntry 1 }

msmqBytesInJournalQueue OBJECT-TYPE
    SYNTAX     Gauge32
    MAX-ACCESS read-only
    STATUS     current
    DESCRIPTION
	    "The total number of bytes that currently
	    reside in the journal queue. For the computer
	    queues instance, this represents the computer
	    journal queue."
    ::= { msmqQueueEntry 2 }

msmqBytesInQueue OBJECT-TYPE
    SYNTAX     Gauge32
    MAX-ACCESS read-only
    STATUS     current
    DESCRIPTION
	    "The total number of bytes that currently
	    reside in the queue. For the computer queues
	    instance, this represents the dead letter
	    queue."
    ::= { msmqQueueEntry 3 }

msmqMessagesInJournalQueue OBJECT-TYPE
    SYNTAX     Gauge32
    MAX-ACCESS read-only
    STATUS     current
    DESCRIPTION
	    "The total number of messages that currently
	    reside in the journal queue. For the computer
	    queues instance, this represents the computer
	    journal queue."
    ::= { msmqQueueEntry 4 }

msmqMessagesInQueue OBJECT-TYPE
    SYNTAX     Gauge32
    MAX-ACCESS read-only
    STATUS     current
    DESCRIPTION
	    "The total number of messages that currently
	    reside in the queue. For the computer queues
	    instance, this represents the dead letter
	    queue."
    ::= { msmqQueueEntry 5 }

msmqService OBJECT-IDENTITY
    STATUS     current
    DESCRIPTION
	    "The MSMQ Service performance object monitors
	    session and message statistics for a selected
	    computer that is running Message Queuing."
    ::= { advanced 48 }

msmqSvcIPSessions OBJECT-TYPE
    SYNTAX     Gauge32
    MAX-ACCESS read-only
    STATUS     current
    DESCRIPTION
	    "Number of open IP sessions."
    ::= { msmqService 1 }

msmqSvcIPXSessions OBJECT-TYPE
    SYNTAX     Gauge32
    MAX-ACCESS read-only
    STATUS     current
    DESCRIPTION
	    "Number of open IPX sessions."
    ::= { msmqService 2 }

msmqSvcIncomingMessagesPerSec OBJECT-TYPE
    SYNTAX     Gauge32
    MAX-ACCESS read-only
    STATUS     current
    DESCRIPTION
	    "The rate of incoming MSMQ messages handled by
	    the MSMQ service."
    ::= { msmqService 3 }

msmqSvcMSMQIncomingMessages OBJECT-TYPE
    SYNTAX     Gauge32
    MAX-ACCESS read-only
    STATUS     current
    DESCRIPTION
	    "The total number of incoming messages handled
	    by the MSMQ service."
    ::= { msmqService 4 }

msmqSvcMSMQOutgoingMessages OBJECT-TYPE
    SYNTAX     Gauge32
    MAX-ACCESS read-only
    STATUS     current
    DESCRIPTION
	    "The total number of outgoing messages handled
	    by the MSMQ service."
    ::= { msmqService 5 }

msmqSvcOutgoingMessagesPerSec OBJECT-TYPE
    SYNTAX     Gauge32
    MAX-ACCESS read-only
    STATUS     current
    DESCRIPTION
	    "The rate of outgoing MSMQ messages handled by
	    the MSMQ service."
    ::= { msmqService 6 }

msmqSvcSessions OBJECT-TYPE
    SYNTAX     Gauge32
    MAX-ACCESS read-only
    STATUS     current
    DESCRIPTION
	    "The total number of open network sessions."
    ::= { msmqService 7 }

msmqSvcTotalBytesInAllQueues OBJECT-TYPE
    SYNTAX     Gauge32
    MAX-ACCESS read-only
    STATUS     current
    DESCRIPTION
	    "The total number of bytes in all active queues
	    under the MSMQ service."
    ::= { msmqService 8 }

msmqSvcTotalMessagesInAllQueues OBJECT-TYPE
    SYNTAX     Gauge32
    MAX-ACCESS read-only
    STATUS     current
    DESCRIPTION
	    "The total number of messages in all active
	    queues under the MSMQ service."
    ::= { msmqService 9 }

nbtConnectionTable OBJECT-TYPE
    SYNTAX     SEQUENCE OF NBTConnectionEntry
    MAX-ACCESS not-accessible
    STATUS     current
    DESCRIPTION
	    "The NBT Connection performance object consists
	    of counters that measure the rates at which
	    bytes are sent and received over the NetBIOS
	    over TCP/IP (NetBT or NBT) protocol provides
	    NetBIOS support for the TCP/IP protocol. NBT
	    connection between the local computer and a
	    remote computer. The connection is identified
	    by the name of the remote computer."
    ::= { advanced 49 }

nbtConnectionEntry OBJECT-TYPE
    SYNTAX     NBTConnectionEntry
    MAX-ACCESS not-accessible
    STATUS     current
    DESCRIPTION
	    "Performance information for one particular
	    instance of 'NBT Connection' object."
    INDEX      { nbtConnectionInstance }
    ::= { nbtConnectionTable 1 }

NBTConnectionEntry ::= SEQUENCE {
    nbtConnectionInstance InstanceName,
    nbtConnectionBytesReceivedPerSec Gauge32,
    nbtConnectionBytesSentPerSec Gauge32,
    nbtConnectionBytesTotalPerSec Gauge32
}

nbtConnectionInstance OBJECT-TYPE
    SYNTAX     InstanceName
    MAX-ACCESS read-only
    STATUS     current
    DESCRIPTION
	    "Instance name."
    ::= { nbtConnectionEntry 1 }

nbtConnectionBytesReceivedPerSec OBJECT-TYPE
    SYNTAX     Gauge32
    MAX-ACCESS read-only
    STATUS     current
    DESCRIPTION
	    "Bytes Received/sec is the rate at which bytes
	    are received by the local computer over an NBT
	    connection to some remote computer.  All the
	    bytes received by the local computer over the
	    particular NBT connection are counted."
    ::= { nbtConnectionEntry 2 }

nbtConnectionBytesSentPerSec OBJECT-TYPE
    SYNTAX     Gauge32
    MAX-ACCESS read-only
    STATUS     current
    DESCRIPTION
	    "Bytes Sent/sec is the rate at which bytes are
	    sent by the local computer over an NBT
	    connection to some remote computer.  All the
	    bytes sent by the local computer over the
	    particular NBT connection are counted."
    ::= { nbtConnectionEntry 3 }

nbtConnectionBytesTotalPerSec OBJECT-TYPE
    SYNTAX     Gauge32
    MAX-ACCESS read-only
    STATUS     current
    DESCRIPTION
	    "Total Bytes/sec is the rate at which bytes are
	    sent or received by the local computer over an
	    NBT connection to some remote computer.  All
	    the bytes sent or received by the local
	    computer over the particular NBT connection are
	    counted."
    ::= { nbtConnectionEntry 4 }

netBEUITable OBJECT-TYPE
    SYNTAX     SEQUENCE OF NetBEUIEntry
    MAX-ACCESS not-accessible
    STATUS     current
    DESCRIPTION
	    "The NetBEUI performance object consists of
	    counters that measure data transmission for
	    network activity which conforms to the NetBIOS
	    End User Interface (NetBEUI) standard."
    ::= { advanced 50 }

netBEUIEntry OBJECT-TYPE
    SYNTAX     NetBEUIEntry
    MAX-ACCESS not-accessible
    STATUS     current
    DESCRIPTION
	    "Performance information for one particular
	    instance of 'NetBEUI' object."
    INDEX      { netBEUIInstance }
    ::= { netBEUITable 1 }

NetBEUIEntry ::= SEQUENCE {
    netBEUIInstance InstanceName,
    netBEUIBytesTotalPerSec Gauge32,
    netBEUIConnectionSessionTimeouts Gauge32,
    netBEUIConnectionsCanceled Gauge32,
    netBEUIConnectionsNoRetries Gauge32,
    netBEUIConnectionsOpen Gauge32,
    netBEUIConnectionsWithRetries Gauge32,
    netBEUIDatagramBytesRcvdPerSec Gauge32,
    netBEUIDatagramBytesSentPerSec Gauge32,
    netBEUIDatagramBytesPerSec Gauge32,
    netBEUIDatagramsReceivedPerSec Gauge32,
    netBEUIDatagramsSentPerSec Gauge32,
    netBEUIDatagramsPerSec Gauge32,
    netBEUIDisconnectsLocal Gauge32,
    netBEUIDisconnectsRemote Gauge32,
    netBEUIExpirationsAck Gauge32,
    netBEUIExpirationsResponse Gauge32,
    netBEUIFailuresAdapter Gauge32,
    netBEUIFailuresLink Gauge32,
    netBEUIFailuresNoListen Gauge32,
    netBEUIFailuresNotFound Gauge32,
    netBEUIFailuresResourceLocal Gauge32,
    netBEUIFailuresResourceRemote Gauge32,
    netBEUIFrameBytesReSentPerSec Gauge32,
    netBEUIFrameBytesReceivedPerSec Gauge32,
    netBEUIFrameBytesRejectedPerSec Gauge32,
    netBEUIFrameBytesSentPerSec Gauge32,
    netBEUIFrameBytesPerSec Gauge32,
    netBEUIFramesReSentPerSec Gauge32,
    netBEUIFramesReceivedPerSec Gauge32,
    netBEUIFramesRejectedPerSec Gauge32,
    netBEUIFramesSentPerSec Gauge32,
    netBEUIFramesPerSec Gauge32,
    netBEUIPacketsReceivedPerSec Gauge32,
    netBEUIPacketsSentPerSec Gauge32,
    netBEUIPacketsPerSec Gauge32,
    netBEUIPiggybackAckQueuedPerSec Gauge32,
    netBEUIPiggybackAckTimeouts Gauge32,
    netBEUIWindowSendAverage Gauge32,
    netBEUIWindowSendMaximum Gauge32
}

netBEUIInstance OBJECT-TYPE
    SYNTAX     InstanceName
    MAX-ACCESS read-only
    STATUS     current
    DESCRIPTION
	    "Instance name."
    ::= { netBEUIEntry 1 }

netBEUIBytesTotalPerSec OBJECT-TYPE
    SYNTAX     Gauge32
    MAX-ACCESS read-only
    STATUS     current
    DESCRIPTION
	    "Bytes Total/sec is the sum of Frame Bytes/sec
	    and Datagram Bytes/sec.  This is the total rate
	    of bytes sent to or received from the network
	    by the protocol, but only counts the bytes in
	    frames (i.e., packets) which carry data."
    ::= { netBEUIEntry 2 }

netBEUIConnectionSessionTimeouts OBJECT-TYPE
    SYNTAX     Gauge32
    MAX-ACCESS read-only
    STATUS     current
    DESCRIPTION
	    "Connection Session Timeouts is the number of
	    connections that were dropped due to a session
	    timeout.  This number is an accumulator and
	    shows a running total."
    ::= { netBEUIEntry 3 }

netBEUIConnectionsCanceled OBJECT-TYPE
    SYNTAX     Gauge32
    MAX-ACCESS read-only
    STATUS     current
    DESCRIPTION
	    "Connections Canceled is the number of
	    connections that were canceled.  This number is
	    an accumulator and shows a running total."
    ::= { netBEUIEntry 4 }

netBEUIConnectionsNoRetries OBJECT-TYPE
    SYNTAX     Gauge32
    MAX-ACCESS read-only
    STATUS     current
    DESCRIPTION
	    "Connections No Retries is the total count of
	    connections that were successfully made on the
	    first try.	This number is an accumulator and
	    shows a running total."
    ::= { netBEUIEntry 5 }

netBEUIConnectionsOpen OBJECT-TYPE
    SYNTAX     Gauge32
    MAX-ACCESS read-only
    STATUS     current
    DESCRIPTION
	    "Connections Open is the number of connections
	    currently open for this protocol.  This counter
	    shows the current count only and does not
	    accumulate over time."
    ::= { netBEUIEntry 6 }

netBEUIConnectionsWithRetries OBJECT-TYPE
    SYNTAX     Gauge32
    MAX-ACCESS read-only
    STATUS     current
    DESCRIPTION
	    "Connections With Retries is the total count of
	    connections that were made after retrying the
	    attempt.  A retry occurs when the first
	    connection attempt failed.	This number is an
	    accumulator and shows a running total."
    ::= { netBEUIEntry 7 }

netBEUIDatagramBytesRcvdPerSec OBJECT-TYPE
    SYNTAX     Gauge32
    MAX-ACCESS read-only
    STATUS     current
    DESCRIPTION
	    "Datagram Bytes Received/sec is the rate at
	    which datagram bytes are received by the
	    computer.  A datagram is a connectionless
	    packet whose delivery to a remote computer is
	    not guaranteed."
    ::= { netBEUIEntry 8 }

netBEUIDatagramBytesSentPerSec OBJECT-TYPE
    SYNTAX     Gauge32
    MAX-ACCESS read-only
    STATUS     current
    DESCRIPTION
	    "Datagram Bytes Sent/sec is the rate at which
	    datagram bytes are sent from the computer.	A
	    datagram is a connectionless packet whose
	    delivery to a remote computer is not
	    guaranteed."
    ::= { netBEUIEntry 9 }

netBEUIDatagramBytesPerSec OBJECT-TYPE
    SYNTAX     Gauge32
    MAX-ACCESS read-only
    STATUS     current
    DESCRIPTION
	    "Datagram Bytes/sec is the rate at which
	    datagram bytes are processed by the computer. 
	    This counter is the sum of datagram bytes that
	    are sent as well as received.  A datagram is a
	    connectionless packet whose delivery to a
	    remote is not guaranteed."
    ::= { netBEUIEntry 10 }

netBEUIDatagramsReceivedPerSec OBJECT-TYPE
    SYNTAX     Gauge32
    MAX-ACCESS read-only
    STATUS     current
    DESCRIPTION
	    "Datagrams Received/sec is the rate at which
	    datagrams are received by the computer.  A
	    datagram is a connectionless packet whose
	    delivery to a remote computer is not
	    guaranteed."
    ::= { netBEUIEntry 11 }

netBEUIDatagramsSentPerSec OBJECT-TYPE
    SYNTAX     Gauge32
    MAX-ACCESS read-only
    STATUS     current
    DESCRIPTION
	    "Datagrams Sent/sec is the rate at which
	    datagrams are sent from the computer.  A
	    datagram is a connectionless packet whose
	    delivery to a remote computer is not
	    guaranteed."
    ::= { netBEUIEntry 12 }

netBEUIDatagramsPerSec OBJECT-TYPE
    SYNTAX     Gauge32
    MAX-ACCESS read-only
    STATUS     current
    DESCRIPTION
	    "Datagrams/sec is the rate at which datagrams
	    are processed by the computer.  This counter
	    displays the sum of datagrams sent and
	    datagrams received.  A datagram is a
	    connectionless packet whose delivery to a
	    remote is not guaranteed."
    ::= { netBEUIEntry 13 }

netBEUIDisconnectsLocal OBJECT-TYPE
    SYNTAX     Gauge32
    MAX-ACCESS read-only
    STATUS     current
    DESCRIPTION
	    "Disconnects Local is the number of session
	    disconnections that were initiated by the local
	    computer.  This number is an accumulator and
	    shows a running total."
    ::= { netBEUIEntry 14 }

netBEUIDisconnectsRemote OBJECT-TYPE
    SYNTAX     Gauge32
    MAX-ACCESS read-only
    STATUS     current
    DESCRIPTION
	    "Disconnects Remote is the number of session
	    disconnections that were initiated by the
	    remote computer.  This number is an accumulator
	    and shows a running total."
    ::= { netBEUIEntry 15 }

netBEUIExpirationsAck OBJECT-TYPE
    SYNTAX     Gauge32
    MAX-ACCESS read-only
    STATUS     current
    DESCRIPTION
	    "Expirations Ack is the count of T2 timer
	    expirations."
    ::= { netBEUIEntry 16 }

netBEUIExpirationsResponse OBJECT-TYPE
    SYNTAX     Gauge32
    MAX-ACCESS read-only
    STATUS     current
    DESCRIPTION
	    "Expirations Response is the count of T1 timer
	    expirations."
    ::= { netBEUIEntry 17 }

netBEUIFailuresAdapter OBJECT-TYPE
    SYNTAX     Gauge32
    MAX-ACCESS read-only
    STATUS     current
    DESCRIPTION
	    "Failures Adapter is the number of connections
	    that were dropped due to an adapter failure. 
	    This number is an accumulator and shows a
	    running total."
    ::= { netBEUIEntry 18 }

netBEUIFailuresLink OBJECT-TYPE
    SYNTAX     Gauge32
    MAX-ACCESS read-only
    STATUS     current
    DESCRIPTION
	    "Failures Link is the number of connections
	    that were dropped due to a link failure.  This
	    number is an accumulator and shows a running
	    total."
    ::= { netBEUIEntry 19 }

netBEUIFailuresNoListen OBJECT-TYPE
    SYNTAX     Gauge32
    MAX-ACCESS read-only
    STATUS     current
    DESCRIPTION
	    "Failures No Listen is the number of
	    connections that were rejected because the
	    remote computer was not listening for
	    connection requests."
    ::= { netBEUIEntry 20 }

netBEUIFailuresNotFound OBJECT-TYPE
    SYNTAX     Gauge32
    MAX-ACCESS read-only
    STATUS     current
    DESCRIPTION
	    "Failures Not Found is the number of connection
	    attempts that failed because the remote
	    computer could not be found.  This number is an
	    accumulator and shows a running total."
    ::= { netBEUIEntry 21 }

netBEUIFailuresResourceLocal OBJECT-TYPE
    SYNTAX     Gauge32
    MAX-ACCESS read-only
    STATUS     current
    DESCRIPTION
	    "Failures Resource Local is the number of
	    connections that failed because of resource
	    problems or shortages on the local computer. 
	    This number is an accumulator and shows a
	    running total."
    ::= { netBEUIEntry 22 }

netBEUIFailuresResourceRemote OBJECT-TYPE
    SYNTAX     Gauge32
    MAX-ACCESS read-only
    STATUS     current
    DESCRIPTION
	    "Failures Resource Remote is the number of
	    connections that failed because of resource
	    problems or shortages on the remote computer. 
	    This number is an accumulator and shows a
	    running total."
    ::= { netBEUIEntry 23 }

netBEUIFrameBytesReSentPerSec OBJECT-TYPE
    SYNTAX     Gauge32
    MAX-ACCESS read-only
    STATUS     current
    DESCRIPTION
	    "Frame Bytes Re-Sent/sec is the rate at which
	    data bytes are re-sent by the computer.  This
	    counter only counts the bytes in frames that
	    carry data."
    ::= { netBEUIEntry 24 }

netBEUIFrameBytesReceivedPerSec OBJECT-TYPE
    SYNTAX     Gauge32
    MAX-ACCESS read-only
    STATUS     current
    DESCRIPTION
	    "Frame Bytes Received/sec is the rate at which
	    data bytes are received by the computer.  This
	    counter only counts the frames (packets) that
	    carry data."
    ::= { netBEUIEntry 25 }

netBEUIFrameBytesRejectedPerSec OBJECT-TYPE
    SYNTAX     Gauge32
    MAX-ACCESS read-only
    STATUS     current
    DESCRIPTION
	    "Frame Bytes Rejected/sec is the rate at which
	    data bytes are rejected.  This counter only
	    counts the bytes in data frames (packets) that
	    carry data."
    ::= { netBEUIEntry 26 }

netBEUIFrameBytesSentPerSec OBJECT-TYPE
    SYNTAX     Gauge32
    MAX-ACCESS read-only
    STATUS     current
    DESCRIPTION
	    "Frame Bytes Sent/sec is the rate at which data
	    bytes are sent by the computer.  This counter
	    only counts the bytes in frames (packets) that
	    carry data."
    ::= { netBEUIEntry 27 }

netBEUIFrameBytesPerSec OBJECT-TYPE
    SYNTAX     Gauge32
    MAX-ACCESS read-only
    STATUS     current
    DESCRIPTION
	    "Frame Bytes/sec is the rate at which data
	    bytes are processed by the computer.  This
	    counter is the sum of data frame bytes sent and
	    received.  This counter only counts the byte in
	    frames (packets) that carry data."
    ::= { netBEUIEntry 28 }

netBEUIFramesReSentPerSec OBJECT-TYPE
    SYNTAX     Gauge32
    MAX-ACCESS read-only
    STATUS     current
    DESCRIPTION
	    "Frames Re-Sent/sec is the rate at which data
	    frames (packets) are re-sent by the computer. 
	    This counter only counts the frames or packets
	    that carry data."
    ::= { netBEUIEntry 29 }

netBEUIFramesReceivedPerSec OBJECT-TYPE
    SYNTAX     Gauge32
    MAX-ACCESS read-only
    STATUS     current
    DESCRIPTION
	    "Frames Received/sec is the rate at which data
	    frames are received by the computer.  This
	    counter only counts the frames (packets) that
	    carry data."
    ::= { netBEUIEntry 30 }

netBEUIFramesRejectedPerSec OBJECT-TYPE
    SYNTAX     Gauge32
    MAX-ACCESS read-only
    STATUS     current
    DESCRIPTION
	    "Frames Rejected/sec is the rate at which data
	    frames are rejected.  This counter only counts
	    the frames (packets) that carry data."
    ::= { netBEUIEntry 31 }

netBEUIFramesSentPerSec OBJECT-TYPE
    SYNTAX     Gauge32
    MAX-ACCESS read-only
    STATUS     current
    DESCRIPTION
	    "Frames Sent/sec is the rate at which data
	    frames are sent by the computer.  This counter
	    only counts the frames (packets) that carry
	    data."
    ::= { netBEUIEntry 32 }

netBEUIFramesPerSec OBJECT-TYPE
    SYNTAX     Gauge32
    MAX-ACCESS read-only
    STATUS     current
    DESCRIPTION
	    "Frames/sec is the rate at which data frames
	    (or packets) are processed by the computer. 
	    This counter is the sum of data frames sent and
	    data frames received.  This counter only counts
	    those frames (packets) that carry data."
    ::= { netBEUIEntry 33 }

netBEUIPacketsReceivedPerSec OBJECT-TYPE
    SYNTAX     Gauge32
    MAX-ACCESS read-only
    STATUS     current
    DESCRIPTION
	    "Packets Received/sec is the rate at which
	    packets are received by the computer.  This
	    counter counts all packets processed: control
	    as well as data packets."
    ::= { netBEUIEntry 34 }

netBEUIPacketsSentPerSec OBJECT-TYPE
    SYNTAX     Gauge32
    MAX-ACCESS read-only
    STATUS     current
    DESCRIPTION
	    "Packets Sent/sec is the rate at which packets
	    are sent by the computer.  This counter counts
	    all packets sent by the computer, i.e. control
	    as well as data packets."
    ::= { netBEUIEntry 35 }

netBEUIPacketsPerSec OBJECT-TYPE
    SYNTAX     Gauge32
    MAX-ACCESS read-only
    STATUS     current
    DESCRIPTION
	    "Packets/sec is the rate at which packets are
	    processed by the computer.	This count is the
	    sum of Packets Sent and Packets Received per
	    second.  This counter includes all packets
	    processed: control as well as data packets."
    ::= { netBEUIEntry 36 }

netBEUIPiggybackAckQueuedPerSec OBJECT-TYPE
    SYNTAX     Gauge32
    MAX-ACCESS read-only
    STATUS     current
    DESCRIPTION
	    "Piggyback Ack Queued/sec is the rate at which
	    piggybacked acknowledgments are queued.
	    Piggyback acknowledgments are acknowledgments
	    to received packets that are to be included in
	    the next outgoing packet to the remote
	    computer."
    ::= { netBEUIEntry 37 }

netBEUIPiggybackAckTimeouts OBJECT-TYPE
    SYNTAX     Gauge32
    MAX-ACCESS read-only
    STATUS     current
    DESCRIPTION
	    "Piggyback Ack Timeouts is the number of times
	    that a piggyback acknowledgment could not be
	    sent because there was no outgoing packet to
	    the remote on which to piggyback.  A piggyback
	    ack is an acknowledgment to a received packet
	    that is sent along in an outgoing data packet
	    to the remote computer.  If no outgoing packet
	    is sent within the timeout period, then an ack
	    packet is sent and this counter is
	    incremented."
    ::= { netBEUIEntry 38 }

netBEUIWindowSendAverage OBJECT-TYPE
    SYNTAX     Gauge32
    MAX-ACCESS read-only
    STATUS     current
    DESCRIPTION
	    "Window Send Average is the running average
	    number of data bytes that were sent before
	    waiting for an acknowledgment from the remote
	    computer."
    ::= { netBEUIEntry 39 }

netBEUIWindowSendMaximum OBJECT-TYPE
    SYNTAX     Gauge32
    MAX-ACCESS read-only
    STATUS     current
    DESCRIPTION
	    "Window Send Maximum is the maximum number of
	    bytes of data that will be sent before waiting
	    for an acknowledgment from the remote
	    computer."
    ::= { netBEUIEntry 40 }

netBEUIResourceTable OBJECT-TYPE
    SYNTAX     SEQUENCE OF NetBEUIResourceEntry
    MAX-ACCESS not-accessible
    STATUS     current
    DESCRIPTION
	    "The NetBEUI Resource performance object
	    consists of counters that track the use of
	    buffers by the NetBEUI protocol."
    ::= { advanced 51 }

netBEUIResourceEntry OBJECT-TYPE
    SYNTAX     NetBEUIResourceEntry
    MAX-ACCESS not-accessible
    STATUS     current
    DESCRIPTION
	    "Performance information for one particular
	    instance of 'NetBEUI Resource' object."
    INDEX      { netBEUIResourceInstance }
    ::= { netBEUIResourceTable 1 }

NetBEUIResourceEntry ::= SEQUENCE {
    netBEUIResourceInstance InstanceName,
    netBEUIResourceTimesExhausted Gauge32,
    netBEUIResourceUsedAverage Gauge32,
    netBEUIResourceUsedMaximum Gauge32
}

netBEUIResourceInstance OBJECT-TYPE
    SYNTAX     InstanceName
    MAX-ACCESS read-only
    STATUS     current
    DESCRIPTION
	    "Instance name."
    ::= { netBEUIResourceEntry 1 }

netBEUIResourceTimesExhausted OBJECT-TYPE
    SYNTAX     Gauge32
    MAX-ACCESS read-only
    STATUS     current
    DESCRIPTION
	    "Times Exhausted is the number of times all the
	    resources (buffers) were in use.  The number in
	    parentheses following the resource name is used
	    to identify the resource in Event Log
	    messages."
    ::= { netBEUIResourceEntry 2 }

netBEUIResourceUsedAverage OBJECT-TYPE
    SYNTAX     Gauge32
    MAX-ACCESS read-only
    STATUS     current
    DESCRIPTION
	    "Used Average is the current number of
	    resources (buffers) in use at this time.  The
	    number in parentheses following the resource
	    name is used to identify the resource in Event
	    Log messages."
    ::= { netBEUIResourceEntry 3 }

netBEUIResourceUsedMaximum OBJECT-TYPE
    SYNTAX     Gauge32
    MAX-ACCESS read-only
    STATUS     current
    DESCRIPTION
	    "Used Maximum is the maximum number of NetBEUI
	    resources (buffers) in use at any point in
	    time.  This value is useful in sizing the
	    maximum resources provided.  The number in
	    parentheses following the resource name is used
	    to identify the resource in Event Log
	    messages."
    ::= { netBEUIResourceEntry 4 }

networkInterfaceTable OBJECT-TYPE
    SYNTAX     SEQUENCE OF NetworkInterfaceEntry
    MAX-ACCESS not-accessible
    STATUS     current
    DESCRIPTION
	    "The Network Interface performance object
	    consists of counters that measure the rates at
	    which bytes and packets are sent and received
	    over a TCP/IP connection. It includes counters
	    that monitor connection errors. The Network
	    Interface counters display data about the
	    network adapters on the server computer. The
	    first instance of the Network Interface object
	    (Instance 1) that you see in System Monitor
	    represents the loopback. The loopback is a
	    local path through the protocol driver and the
	    network adapter. All other instances represent
	    installed network adapters."
    ::= { advanced 52 }

networkInterfaceEntry OBJECT-TYPE
    SYNTAX     NetworkInterfaceEntry
    MAX-ACCESS not-accessible
    STATUS     current
    DESCRIPTION
	    "Performance information for one particular
	    instance of 'Network Interface' object."
    INDEX      { netInstance }
    ::= { networkInterfaceTable 1 }

NetworkInterfaceEntry ::= SEQUENCE {
    netInstance InstanceName,
    netBytesReceivedPerSec Gauge32,
    netBytesSentPerSec Gauge32,
    netBytesTotalPerSec Gauge32,
    netCurrentBandwidth Gauge32,
    netOutputQueueLength Gauge32,
    netPacketsOutboundDiscarded Gauge32,
    netPacketsOutboundErrors Gauge32,
    netPacketsReceivedDiscarded Gauge32,
    netPacketsReceivedErrors Gauge32,
    netPacketsRcvdNonUnicastPerSec Gauge32,
    netPacketsReceivedUnicastPerSec Gauge32,
    netPacketsReceivedUnknown Gauge32,
    netPacketsReceivedPerSec Gauge32,
    netPacketsSentNonUnicastPerSec Gauge32,
    netPacketsSentUnicastPerSec Gauge32,
    netPacketsSentPerSec Gauge32,
    netPacketsPerSec Gauge32
}

netInstance OBJECT-TYPE
    SYNTAX     InstanceName
    MAX-ACCESS read-only
    STATUS     current
    DESCRIPTION
	    "Instance name."
    ::= { networkInterfaceEntry 1 }

netBytesReceivedPerSec OBJECT-TYPE
    SYNTAX     Gauge32
    MAX-ACCESS read-only
    STATUS     current
    DESCRIPTION
	    "Bytes Received/sec is the rate at which bytes
	    are received on the interface, including
	    framing characters."
    ::= { networkInterfaceEntry 2 }

netBytesSentPerSec OBJECT-TYPE
    SYNTAX     Gauge32
    MAX-ACCESS read-only
    STATUS     current
    DESCRIPTION
	    "Bytes Sent/sec is the rate at which bytes are
	    sent on the interface, including framing
	    characters."
    ::= { networkInterfaceEntry 3 }

netBytesTotalPerSec OBJECT-TYPE
    SYNTAX     Gauge32
    MAX-ACCESS read-only
    STATUS     current
    DESCRIPTION
	    "Bytes Total/sec is the rate at which bytes are
	    sent and received on the interface, including
	    framing characters."
    ::= { networkInterfaceEntry 4 }

netCurrentBandwidth OBJECT-TYPE
    SYNTAX     Gauge32
    MAX-ACCESS read-only
    STATUS     current
    DESCRIPTION
	    "Current Bandwidth is an estimate of the
	    interface's current bandwidth in bits per
	    second (BPS).  For interfaces that do not vary
	    in bandwidth or for those where no accurate
	    estimation can be made, this value is the
	    nominal bandwidth."
    ::= { networkInterfaceEntry 5 }

netOutputQueueLength OBJECT-TYPE
    SYNTAX     Gauge32
    MAX-ACCESS read-only
    STATUS     current
    DESCRIPTION
	    "Output Queue Length is the length of the
	    output packet queue (in packets).  If this is
	    longer than 2, delays are being experienced and
	    the bottleneck should be found and eliminated
	    if possible.  Since the requests are queued by
	    NDIS in this implementation, this will always
	    be 0."
    ::= { networkInterfaceEntry 6 }

netPacketsOutboundDiscarded OBJECT-TYPE
    SYNTAX     Gauge32
    MAX-ACCESS read-only
    STATUS     current
    DESCRIPTION
	    "Packets Outbound Discarded is the number of
	    outbound packets that were chosen to be
	    discarded even though no errors had been
	    detected to prevent their being transmitted. 
	    One possible reason for discarding such a
	    packet could be to free up buffer space."
    ::= { networkInterfaceEntry 7 }

netPacketsOutboundErrors OBJECT-TYPE
    SYNTAX     Gauge32
    MAX-ACCESS read-only
    STATUS     current
    DESCRIPTION
	    "Packets Outbound Errors is the number of
	    outbound packets that could not be transmitted
	    because of errors."
    ::= { networkInterfaceEntry 8 }

netPacketsReceivedDiscarded OBJECT-TYPE
    SYNTAX     Gauge32
    MAX-ACCESS read-only
    STATUS     current
    DESCRIPTION
	    "Packets Received Discarded is the number of
	    inbound packets that were chosen to be
	    discarded even though no errors had been
	    detected to prevent their being deliverable to
	    a higher-layer protocol.  One possible reason
	    for discarding such a packet could be to free
	    up buffer space."
    ::= { networkInterfaceEntry 9 }

netPacketsReceivedErrors OBJECT-TYPE
    SYNTAX     Gauge32
    MAX-ACCESS read-only
    STATUS     current
    DESCRIPTION
	    "Packets Received Errors is the number of
	    inbound packets that contained errors
	    preventing them from being deliverable to a
	    higher-layer protocol."
    ::= { networkInterfaceEntry 10 }

netPacketsRcvdNonUnicastPerSec OBJECT-TYPE
    SYNTAX     Gauge32
    MAX-ACCESS read-only
    STATUS     current
    DESCRIPTION
	    "Packets Received Non-Unicast/sec is the rate
	    at which non-unicast (i.e., subnet broadcast or
	    subnet multicast) packets are delivered to a
	    higher-layer protocol."
    ::= { networkInterfaceEntry 11 }

netPacketsReceivedUnicastPerSec OBJECT-TYPE
    SYNTAX     Gauge32
    MAX-ACCESS read-only
    STATUS     current
    DESCRIPTION
	    "Packets Received Unicast/sec is the rate at
	    which (subnet) unicast packets are delivered to
	    a higher-layer protocol."
    ::= { networkInterfaceEntry 12 }

netPacketsReceivedUnknown OBJECT-TYPE
    SYNTAX     Gauge32
    MAX-ACCESS read-only
    STATUS     current
    DESCRIPTION
	    "Packets Received Unknown is the number of
	    packets received via the interface that were
	    discarded because of an unknown or unsupported
	    protocol."
    ::= { networkInterfaceEntry 13 }

netPacketsReceivedPerSec OBJECT-TYPE
    SYNTAX     Gauge32
    MAX-ACCESS read-only
    STATUS     current
    DESCRIPTION
	    "Packets Received/sec is the rate at which
	    packets are received on the network interface."
    ::= { networkInterfaceEntry 14 }

netPacketsSentNonUnicastPerSec OBJECT-TYPE
    SYNTAX     Gauge32
    MAX-ACCESS read-only
    STATUS     current
    DESCRIPTION
	    "Packets Sent Non-Unicast/sec is the rate at
	    which packets are requested to be transmitted
	    to non-unicast (i.e., subnet broadcast or
	    subnet multicast) addresses by higher-level
	    protocols.	The rate includes the packets that
	    were discarded or not sent."
    ::= { networkInterfaceEntry 15 }

netPacketsSentUnicastPerSec OBJECT-TYPE
    SYNTAX     Gauge32
    MAX-ACCESS read-only
    STATUS     current
    DESCRIPTION
	    "Packets Sent Unicast/sec is the rate at which
	    packets are requested to be transmitted to
	    subnet-unicast addresses by higher-level
	    protocols.	The rate includes the packets that
	    were discarded or not sent."
    ::= { networkInterfaceEntry 16 }

netPacketsSentPerSec OBJECT-TYPE
    SYNTAX     Gauge32
    MAX-ACCESS read-only
    STATUS     current
    DESCRIPTION
	    "Packets Sent/sec is the rate at which packets
	    are sent on the network interface."
    ::= { networkInterfaceEntry 17 }

netPacketsPerSec OBJECT-TYPE
    SYNTAX     Gauge32
    MAX-ACCESS read-only
    STATUS     current
    DESCRIPTION
	    "Packets/sec is the rate at which packets are
	    sent and received on the network interface."
    ::= { networkInterfaceEntry 18 }

nntpCommandsTable OBJECT-TYPE
    SYNTAX     SEQUENCE OF NNTPCommandsEntry
    MAX-ACCESS not-accessible
    STATUS     current
    DESCRIPTION
	    "The NNTP Commands performance object includes
	    counters for all NNTP commands processed by the
	    Network News Transport Protocol (NNTP) service,
	    which is installed as an optional component of
	    Internet Information Services. NNTP counters
	    are started for each virtual server instance
	    and are reset to zero when the virtual server
	    is started. A single NNTP service can have many
	    virtual servers (also called sites)."
    ::= { advanced 53 }

nntpCommandsEntry OBJECT-TYPE
    SYNTAX     NNTPCommandsEntry
    MAX-ACCESS not-accessible
    STATUS     current
    DESCRIPTION
	    "Performance information for one particular
	    instance of 'NNTP Commands' object."
    INDEX      { nntpCmdsInstance }
    ::= { nntpCommandsTable 1 }

NNTPCommandsEntry ::= SEQUENCE {
    nntpCmdsInstance InstanceName,
    nntpCmdsArticleCmds Gauge32,
    nntpCmdsArticleCmdsPerSec Gauge32,
    nntpCmdsCheckCmds Gauge32,
    nntpCmdsCheckCmdsPerSec Gauge32,
    nntpCmdsGroupCmds Gauge32,
    nntpCmdsGroupCmdsPerSec Gauge32,
    nntpCmdsHelpCmds Gauge32,
    nntpCmdsHelpCmdsPerSec Gauge32,
    nntpCmdsIHaveCmds Gauge32,
    nntpCmdsIHaveCmdsPerSec Gauge32,
    nntpCmdsLastCmds Gauge32,
    nntpCmdsLastCmdsPerSec Gauge32,
    nntpCmdsListCmds Gauge32,
    nntpCmdsListCmdsPerSec Gauge32,
    nntpCmdsLogonAttempts Gauge32,
    nntpCmdsLogonAttemptsPerSec Gauge32,
    nntpCmdsLogonFailures Gauge32,
    nntpCmdsLogonFailuresPerSec Gauge32,
    nntpCmdsModeCmds Gauge32,
    nntpCmdsModeCmdsPerSec Gauge32,
    nntpCmdsNewgroupsCmds Gauge32,
    nntpCmdsNewgroupsCmdsPerSec Gauge32,
    nntpCmdsNewnewsCmds Gauge32,
    nntpCmdsNewnewsCmdsPerSec Gauge32,
    nntpCmdsNextCmds Gauge32,
    nntpCmdsNextCmdsPerSec Gauge32,
    nntpCmdsPostCmds Gauge32,
    nntpCmdsPostCmdsPerSec Gauge32,
    nntpCmdsQuitCmds Gauge32,
    nntpCmdsQuitCmdsPerSec Gauge32,
    nntpCmdsSearchCmds Gauge32,
    nntpCmdsSearchCmdsPerSec Gauge32,
    nntpCmdsStatCmds Gauge32,
    nntpCmdsStatCmdsPerSec Gauge32,
    nntpCmdsTakethisCmds Gauge32,
    nntpCmdsTakethisCmdsPerSec Gauge32,
    nntpCmdsXHdrCmds Gauge32,
    nntpCmdsXHdrCmdsPerSec Gauge32,
    nntpCmdsXOverCmds Gauge32,
    nntpCmdsXOverCmdsPerSec Gauge32,
    nntpCmdsXPatCmds Gauge32,
    nntpCmdsXPatCmdsPerSec Gauge32,
    nntpCmdsXReplicCmds Gauge32,
    nntpCmdsXReplicCmdsPerSec Gauge32
}

nntpCmdsInstance OBJECT-TYPE
    SYNTAX     InstanceName
    MAX-ACCESS read-only
    STATUS     current
    DESCRIPTION
	    "Instance name."
    ::= { nntpCommandsEntry 1 }

nntpCmdsArticleCmds OBJECT-TYPE
    SYNTAX     Gauge32
    MAX-ACCESS read-only
    STATUS     current
    DESCRIPTION
	    "Article Commands is the number of ARTICLE
	    commands received by the NNTP Server since it
	    was started."
    ::= { nntpCommandsEntry 2 }

nntpCmdsArticleCmdsPerSec OBJECT-TYPE
    SYNTAX     Gauge32
    MAX-ACCESS read-only
    STATUS     current
    DESCRIPTION
	    "Article Commands/Sec is the number of ARTICLE
	    commands per sec received by the NNTP Server
	    since it was started."
    ::= { nntpCommandsEntry 3 }

nntpCmdsCheckCmds OBJECT-TYPE
    SYNTAX     Gauge32
    MAX-ACCESS read-only
    STATUS     current
    DESCRIPTION
	    "Check Commands is the number of CHECK commands
	    received by the NNTP Server since it was
	    started."
    ::= { nntpCommandsEntry 4 }

nntpCmdsCheckCmdsPerSec OBJECT-TYPE
    SYNTAX     Gauge32
    MAX-ACCESS read-only
    STATUS     current
    DESCRIPTION
	    "Check Commands/Sec is the number of CHECK
	    commands per sec received by the NNTP Server
	    since it was started."
    ::= { nntpCommandsEntry 5 }

nntpCmdsGroupCmds OBJECT-TYPE
    SYNTAX     Gauge32
    MAX-ACCESS read-only
    STATUS     current
    DESCRIPTION
	    "Group Commands is the number of GROUP commands
	    received by the NNTP Server since it was
	    started."
    ::= { nntpCommandsEntry 6 }

nntpCmdsGroupCmdsPerSec OBJECT-TYPE
    SYNTAX     Gauge32
    MAX-ACCESS read-only
    STATUS     current
    DESCRIPTION
	    "Group Commands/Sec is the number of GROUP
	    commands per sec received by the NNTP Server
	    since it was started."
    ::= { nntpCommandsEntry 7 }

nntpCmdsHelpCmds OBJECT-TYPE
    SYNTAX     Gauge32
    MAX-ACCESS read-only
    STATUS     current
    DESCRIPTION
	    "Help Commands is the number of HELP commands
	    received by the NNTP Server since it was
	    started."
    ::= { nntpCommandsEntry 8 }

nntpCmdsHelpCmdsPerSec OBJECT-TYPE
    SYNTAX     Gauge32
    MAX-ACCESS read-only
    STATUS     current
    DESCRIPTION
	    "Help Commands/Sec is the number of HELP
	    commands per sec received by the NNTP Server
	    since it was started."
    ::= { nntpCommandsEntry 9 }

nntpCmdsIHaveCmds OBJECT-TYPE
    SYNTAX     Gauge32
    MAX-ACCESS read-only
    STATUS     current
    DESCRIPTION
	    "IHave Commands is the number of IHAVE commands
	    received by the NNTP Server since it was
	    started."
    ::= { nntpCommandsEntry 10 }

nntpCmdsIHaveCmdsPerSec OBJECT-TYPE
    SYNTAX     Gauge32
    MAX-ACCESS read-only
    STATUS     current
    DESCRIPTION
	    "IHave Commands/Sec is the number of IHAVE
	    commands per sec received by the NNTP Server
	    since it was started."
    ::= { nntpCommandsEntry 11 }

nntpCmdsLastCmds OBJECT-TYPE
    SYNTAX     Gauge32
    MAX-ACCESS read-only
    STATUS     current
    DESCRIPTION
	    "Last Commands is the number of LAST commands
	    received by the NNTP Server since it was
	    started."
    ::= { nntpCommandsEntry 12 }

nntpCmdsLastCmdsPerSec OBJECT-TYPE
    SYNTAX     Gauge32
    MAX-ACCESS read-only
    STATUS     current
    DESCRIPTION
	    "Last Commands/Sec is the number of LAST
	    commands per sec received by the NNTP Server
	    since it was started."
    ::= { nntpCommandsEntry 13 }

nntpCmdsListCmds OBJECT-TYPE
    SYNTAX     Gauge32
    MAX-ACCESS read-only
    STATUS     current
    DESCRIPTION
	    "List Commands is the number of LIST commands
	    received by the NNTP Server since it was
	    started."
    ::= { nntpCommandsEntry 14 }

nntpCmdsListCmdsPerSec OBJECT-TYPE
    SYNTAX     Gauge32
    MAX-ACCESS read-only
    STATUS     current
    DESCRIPTION
	    "List Commands/Sec is the number of LIST
	    commands per sec received by the NNTP Server
	    since it was started."
    ::= { nntpCommandsEntry 15 }

nntpCmdsLogonAttempts OBJECT-TYPE
    SYNTAX     Gauge32
    MAX-ACCESS read-only
    STATUS     current
    DESCRIPTION
	    "Logon Attempts is the number of logon attempts
	    that have been made to the NNTP Server."
    ::= { nntpCommandsEntry 16 }

nntpCmdsLogonAttemptsPerSec OBJECT-TYPE
    SYNTAX     Gauge32
    MAX-ACCESS read-only
    STATUS     current
    DESCRIPTION
	    "Logon Attempts/Sec is the number of logon
	    attempts per sec that have been made to the
	    NNTP Server."
    ::= { nntpCommandsEntry 17 }

nntpCmdsLogonFailures OBJECT-TYPE
    SYNTAX     Gauge32
    MAX-ACCESS read-only
    STATUS     current
    DESCRIPTION
	    "Logon Failures is the number of logons that
	    had failed."
    ::= { nntpCommandsEntry 18 }

nntpCmdsLogonFailuresPerSec OBJECT-TYPE
    SYNTAX     Gauge32
    MAX-ACCESS read-only
    STATUS     current
    DESCRIPTION
	    "Logon Failures/Sec is the number of logons per
	    sec that had failed."
    ::= { nntpCommandsEntry 19 }

nntpCmdsModeCmds OBJECT-TYPE
    SYNTAX     Gauge32
    MAX-ACCESS read-only
    STATUS     current
    DESCRIPTION
	    "Mode Commands is the number of MODE commands
	    received by the NNTP Server since it was
	    started."
    ::= { nntpCommandsEntry 20 }

nntpCmdsModeCmdsPerSec OBJECT-TYPE
    SYNTAX     Gauge32
    MAX-ACCESS read-only
    STATUS     current
    DESCRIPTION
	    "Mode Commands/Sec is the number of MODE
	    commands per sec received by the NNTP Server
	    since it was started."
    ::= { nntpCommandsEntry 21 }

nntpCmdsNewgroupsCmds OBJECT-TYPE
    SYNTAX     Gauge32
    MAX-ACCESS read-only
    STATUS     current
    DESCRIPTION
	    "Newgroups Commands is the number of NEWGROUPS
	    commands received by the NNTP Server since it
	    was started."
    ::= { nntpCommandsEntry 22 }

nntpCmdsNewgroupsCmdsPerSec OBJECT-TYPE
    SYNTAX     Gauge32
    MAX-ACCESS read-only
    STATUS     current
    DESCRIPTION
	    "Newgroups Commands/Sec is the number of
	    NEWGROUPS commands per sec received by the NNTP
	    Server since it was started."
    ::= { nntpCommandsEntry 23 }

nntpCmdsNewnewsCmds OBJECT-TYPE
    SYNTAX     Gauge32
    MAX-ACCESS read-only
    STATUS     current
    DESCRIPTION
	    "Newnews Commands is the number of NEWNEWS
	    commands received by the NNTP Server since it
	    was started."
    ::= { nntpCommandsEntry 24 }

nntpCmdsNewnewsCmdsPerSec OBJECT-TYPE
    SYNTAX     Gauge32
    MAX-ACCESS read-only
    STATUS     current
    DESCRIPTION
	    "Newnews Commands/Sec is the number of NEWNEWS
	    commands per sec received by the NNTP Server
	    since it was started."
    ::= { nntpCommandsEntry 25 }

nntpCmdsNextCmds OBJECT-TYPE
    SYNTAX     Gauge32
    MAX-ACCESS read-only
    STATUS     current
    DESCRIPTION
	    "Next Commands is the number of NEXT commands
	    received by the NNTP Server since it was
	    started."
    ::= { nntpCommandsEntry 26 }

nntpCmdsNextCmdsPerSec OBJECT-TYPE
    SYNTAX     Gauge32
    MAX-ACCESS read-only
    STATUS     current
    DESCRIPTION
	    "Next Commands/Sec is the number of NEXT
	    commands per sec received by the NNTP Server
	    since it was started."
    ::= { nntpCommandsEntry 27 }

nntpCmdsPostCmds OBJECT-TYPE
    SYNTAX     Gauge32
    MAX-ACCESS read-only
    STATUS     current
    DESCRIPTION
	    "Post Commands is the number of POST commands
	    received by the NNTP Server since it was
	    started."
    ::= { nntpCommandsEntry 28 }

nntpCmdsPostCmdsPerSec OBJECT-TYPE
    SYNTAX     Gauge32
    MAX-ACCESS read-only
    STATUS     current
    DESCRIPTION
	    "Post Commands/Sec is the number of POST
	    commands per sec received by the NNTP Server
	    since it was started."
    ::= { nntpCommandsEntry 29 }

nntpCmdsQuitCmds OBJECT-TYPE
    SYNTAX     Gauge32
    MAX-ACCESS read-only
    STATUS     current
    DESCRIPTION
	    "Quit Commands is the number of QUIT commands
	    received by the NNTP Server since it was
	    started."
    ::= { nntpCommandsEntry 30 }

nntpCmdsQuitCmdsPerSec OBJECT-TYPE
    SYNTAX     Gauge32
    MAX-ACCESS read-only
    STATUS     current
    DESCRIPTION
	    "Quit Commands/Sec is the number of QUIT
	    commands per sec received by the NNTP Server
	    since it was started."
    ::= { nntpCommandsEntry 31 }

nntpCmdsSearchCmds OBJECT-TYPE
    SYNTAX     Gauge32
    MAX-ACCESS read-only
    STATUS     current
    DESCRIPTION
	    "Search Commands is the number of SEARCH
	    commands received by the NNTP Server since it
	    was started."
    ::= { nntpCommandsEntry 32 }

nntpCmdsSearchCmdsPerSec OBJECT-TYPE
    SYNTAX     Gauge32
    MAX-ACCESS read-only
    STATUS     current
    DESCRIPTION
	    "Search Commands/Sec is the number of SEARCH
	    commands per sec received by the NNTP Server
	    since it was started."
    ::= { nntpCommandsEntry 33 }

nntpCmdsStatCmds OBJECT-TYPE
    SYNTAX     Gauge32
    MAX-ACCESS read-only
    STATUS     current
    DESCRIPTION
	    "Stat Commands is the number of STAT commands
	    received by the NNTP Server since it was
	    started."
    ::= { nntpCommandsEntry 34 }

nntpCmdsStatCmdsPerSec OBJECT-TYPE
    SYNTAX     Gauge32
    MAX-ACCESS read-only
    STATUS     current
    DESCRIPTION
	    "Stat Commands/Sec is the number of STAT
	    commands per sec received by the NNTP Server
	    since it was started."
    ::= { nntpCommandsEntry 35 }

nntpCmdsTakethisCmds OBJECT-TYPE
    SYNTAX     Gauge32
    MAX-ACCESS read-only
    STATUS     current
    DESCRIPTION
	    "Takethis Commands is the number of TAKETHIS
	    commands received by the NNTP Server since it
	    was started."
    ::= { nntpCommandsEntry 36 }

nntpCmdsTakethisCmdsPerSec OBJECT-TYPE
    SYNTAX     Gauge32
    MAX-ACCESS read-only
    STATUS     current
    DESCRIPTION
	    "Takethis Commands/Sec is the number of
	    TAKETHIS commands per sec received by the NNTP
	    Server since it was started."
    ::= { nntpCommandsEntry 37 }

nntpCmdsXHdrCmds OBJECT-TYPE
    SYNTAX     Gauge32
    MAX-ACCESS read-only
    STATUS     current
    DESCRIPTION
	    "XHdr Commands is the number of XHDR commands
	    received by the NNTP Server since it was
	    started."
    ::= { nntpCommandsEntry 38 }

nntpCmdsXHdrCmdsPerSec OBJECT-TYPE
    SYNTAX     Gauge32
    MAX-ACCESS read-only
    STATUS     current
    DESCRIPTION
	    "XHdr Commands/Sec is the number of XHDR
	    commands per sec received by the NNTP Server
	    since it was started."
    ::= { nntpCommandsEntry 39 }

nntpCmdsXOverCmds OBJECT-TYPE
    SYNTAX     Gauge32
    MAX-ACCESS read-only
    STATUS     current
    DESCRIPTION
	    "XOver Commands is the number of XOVER commands
	    received by the NNTP Server since it was
	    started."
    ::= { nntpCommandsEntry 40 }

nntpCmdsXOverCmdsPerSec OBJECT-TYPE
    SYNTAX     Gauge32
    MAX-ACCESS read-only
    STATUS     current
    DESCRIPTION
	    "XOver Commands/Sec is the number of XOVER
	    commands per sec received by the NNTP Server
	    since it was started."
    ::= { nntpCommandsEntry 41 }

nntpCmdsXPatCmds OBJECT-TYPE
    SYNTAX     Gauge32
    MAX-ACCESS read-only
    STATUS     current
    DESCRIPTION
	    "XPat Commands is the number of XPAT commands
	    received by the NNTP Server since it was
	    started."
    ::= { nntpCommandsEntry 42 }

nntpCmdsXPatCmdsPerSec OBJECT-TYPE
    SYNTAX     Gauge32
    MAX-ACCESS read-only
    STATUS     current
    DESCRIPTION
	    "XPat Commands/Sec is the number of XPAT
	    commands per sec received by the NNTP Server
	    since it was started."
    ::= { nntpCommandsEntry 43 }

nntpCmdsXReplicCmds OBJECT-TYPE
    SYNTAX     Gauge32
    MAX-ACCESS read-only
    STATUS     current
    DESCRIPTION
	    "XReplic Commands is the number of XREPLIC
	    commands received by the NNTP Server since it
	    was started."
    ::= { nntpCommandsEntry 44 }

nntpCmdsXReplicCmdsPerSec OBJECT-TYPE
    SYNTAX     Gauge32
    MAX-ACCESS read-only
    STATUS     current
    DESCRIPTION
	    "XReplic Commands/Sec is the number of XREPLIC
	    commands per sec received by the NNTP Server
	    since it was started."
    ::= { nntpCommandsEntry 45 }

nntpServerTable OBJECT-TYPE
    SYNTAX     SEQUENCE OF NNTPServerEntry
    MAX-ACCESS not-accessible
    STATUS     current
    DESCRIPTION
	    "The NNTP Server performance object monitors
	    posting, authentication, and connection
	    activity on an NNTP server. The Network News
	    Transport Protocol (NNTP) service is an
	    optional component of Internet Information
	    Services. NNTP counters are started for each
	    virtual server instance and are reset to zero
	    when the virtual server is started. A single
	    NNTP service can have many virtual servers
	    (also called sites)."
    ::= { advanced 54 }

nntpServerEntry OBJECT-TYPE
    SYNTAX     NNTPServerEntry
    MAX-ACCESS not-accessible
    STATUS     current
    DESCRIPTION
	    "Performance information for one particular
	    instance of 'NNTP Server' object."
    INDEX      { nntpSrvrInstance }
    ::= { nntpServerTable 1 }

NNTPServerEntry ::= SEQUENCE {
    nntpSrvrInstance InstanceName,
    nntpSrvrArticleMapEntries Gauge32,
    nntpSrvrArticleMapEntriesPerSec Gauge32,
    nntpSrvrArticlesDeleted Gauge32,
    nntpSrvrArticlesDeletedPerSec Gauge32,
    nntpSrvrArticlesPosted Gauge32,
    nntpSrvrArticlesPostedPerSec Gauge32,
    nntpSrvrArticlesReceived Gauge32,
    nntpSrvrArticlesReceivedPerSec Gauge32,
    nntpSrvrArticlesSent Gauge32,
    nntpSrvrArticlesSentPerSec Gauge32,
    nntpSrvrArticlesTotal Gauge32,
    nntpSrvrBytesReceivedPerSec Gauge32,
    nntpSrvrBytesSentPerSec Gauge32,
    nntpSrvrBytesTotalPerSec Gauge32,
    nntpSrvrControlMessagesFailed Gauge32,
    nntpSrvrControlMessagesReceived Gauge32,
    nntpSrvrCurrentAnonymousUsers Gauge32,
    nntpSrvrCurrentConnections Gauge32,
    nntpSrvrCurrentNonAnonymousUsers Gauge32,
    nntpSrvrCurrentOutboundConns Gauge32,
    nntpSrvrFailedOutboundLogons Gauge32,
    nntpSrvrHistoryMapEntries Gauge32,
    nntpSrvrHistoryMapEntriesPerSec Gauge32,
    nntpSrvrMaximumAnonymousUsers Gauge32,
    nntpSrvrMaximumConnections Gauge32,
    nntpSrvrMaximumNonAnonymousUsers Gauge32,
    nntpSrvrModeratedPostingsFailed Gauge32,
    nntpSrvrModeratedPostingsSent Gauge32,
    nntpSrvrSessionsFlowControlled Gauge32,
    nntpSrvrTotalAnonymousUsers Gauge32,
    nntpSrvrTotalConnections Gauge32,
    nntpSrvrTotalNonAnonymousUsers Gauge32,
    nntpSrvrTotalOutboundConnections Gauge32,
    nntpSrvrTotalOutboundConnsFailed Gauge32,
    nntpSrvrTotalPassiveFeeds Gauge32,
    nntpSrvrTotalPullFeeds Gauge32,
    nntpSrvrTotalPushFeeds Gauge32,
    nntpSrvrTotalSSLConnections Gauge32,
    nntpSrvrXoverEntries Gauge32,
    nntpSrvrXoverEntriesPerSec Gauge32
}

nntpSrvrInstance OBJECT-TYPE
    SYNTAX     InstanceName
    MAX-ACCESS read-only
    STATUS     current
    DESCRIPTION
	    "Instance name."
    ::= { nntpServerEntry 1 }

nntpSrvrArticleMapEntries OBJECT-TYPE
    SYNTAX     Gauge32
    MAX-ACCESS read-only
    STATUS     current
    DESCRIPTION
	    "Article Map Entries is the entries inserted
	    into the article mapping table of the NNTP
	    Server."
    ::= { nntpServerEntry 2 }

nntpSrvrArticleMapEntriesPerSec OBJECT-TYPE
    SYNTAX     Gauge32
    MAX-ACCESS read-only
    STATUS     current
    DESCRIPTION
	    "Article Map Entries/Sec is the entries
	    inserted per sec into the article mapping table
	    of the NNTP Server."
    ::= { nntpServerEntry 3 }

nntpSrvrArticlesDeleted OBJECT-TYPE
    SYNTAX     Gauge32
    MAX-ACCESS read-only
    STATUS     current
    DESCRIPTION
	    "Articles Deleted is the number of articles
	    deleted on the NNTP Server since it was
	    started."
    ::= { nntpServerEntry 4 }

nntpSrvrArticlesDeletedPerSec OBJECT-TYPE
    SYNTAX     Gauge32
    MAX-ACCESS read-only
    STATUS     current
    DESCRIPTION
	    "Articles Deleted/Sec is the number of articles
	    deleted per sec on the NNTP Server since it was
	    started."
    ::= { nntpServerEntry 5 }

nntpSrvrArticlesPosted OBJECT-TYPE
    SYNTAX     Gauge32
    MAX-ACCESS read-only
    STATUS     current
    DESCRIPTION
	    "Articles Posted is the number of articles
	    posted to the NNTP Server."
    ::= { nntpServerEntry 6 }

nntpSrvrArticlesPostedPerSec OBJECT-TYPE
    SYNTAX     Gauge32
    MAX-ACCESS read-only
    STATUS     current
    DESCRIPTION
	    "Articles Posted/Sec is the number of articles
	    posted per sec to the NNTP Server."
    ::= { nntpServerEntry 7 }

nntpSrvrArticlesReceived OBJECT-TYPE
    SYNTAX     Gauge32
    MAX-ACCESS read-only
    STATUS     current
    DESCRIPTION
	    "Articles Received is the total number of files
	    received by the NNTP Server."
    ::= { nntpServerEntry 8 }

nntpSrvrArticlesReceivedPerSec OBJECT-TYPE
    SYNTAX     Gauge32
    MAX-ACCESS read-only
    STATUS     current
    DESCRIPTION
	    "Articles Received/Sec is the total number of
	    files per sec received by the NNTP Server."
    ::= { nntpServerEntry 9 }

nntpSrvrArticlesSent OBJECT-TYPE
    SYNTAX     Gauge32
    MAX-ACCESS read-only
    STATUS     current
    DESCRIPTION
	    "Articles Sent is the total number of files
	    sent by the NNTP Server."
    ::= { nntpServerEntry 10 }

nntpSrvrArticlesSentPerSec OBJECT-TYPE
    SYNTAX     Gauge32
    MAX-ACCESS read-only
    STATUS     current
    DESCRIPTION
	    "Articles Sent/Sec is the total number of files
	    sent per sec by the NNTP Server."
    ::= { nntpServerEntry 11 }

nntpSrvrArticlesTotal OBJECT-TYPE
    SYNTAX     Gauge32
    MAX-ACCESS read-only
    STATUS     current
    DESCRIPTION
	    "Articles Total is the sum of Articles Sent and
	    Articles Received.	This is the total number of
	    files transferred by the NNTP Server."
    ::= { nntpServerEntry 12 }

nntpSrvrBytesReceivedPerSec OBJECT-TYPE
    SYNTAX     Gauge32
    MAX-ACCESS read-only
    STATUS     current
    DESCRIPTION
	    "Bytes Received/sec is the rate that data bytes
	    are received by the NNTP Server."
    ::= { nntpServerEntry 13 }

nntpSrvrBytesSentPerSec OBJECT-TYPE
    SYNTAX     Gauge32
    MAX-ACCESS read-only
    STATUS     current
    DESCRIPTION
	    "Bytes Sent/sec is the rate that data bytes are
	    sent by the NNTP Server."
    ::= { nntpServerEntry 14 }

nntpSrvrBytesTotalPerSec OBJECT-TYPE
    SYNTAX     Gauge32
    MAX-ACCESS read-only
    STATUS     current
    DESCRIPTION
	    "Bytes Total/sec is the sum of Bytes Sent/sec
	    and Bytes Received/sec.  This is the total rate
	    of bytes transferred by the NNTP Server."
    ::= { nntpServerEntry 15 }

nntpSrvrControlMessagesFailed OBJECT-TYPE
    SYNTAX     Gauge32
    MAX-ACCESS read-only
    STATUS     current
    DESCRIPTION
	    "Control Messages Failed is the total number of
	    control messages failed or not applied by the
	    NNTP Server."
    ::= { nntpServerEntry 16 }

nntpSrvrControlMessagesReceived OBJECT-TYPE
    SYNTAX     Gauge32
    MAX-ACCESS read-only
    STATUS     current
    DESCRIPTION
	    "Control Messages Received is the total number
	    of control messages received by the NNTP
	    Server."
    ::= { nntpServerEntry 17 }

nntpSrvrCurrentAnonymousUsers OBJECT-TYPE
    SYNTAX     Gauge32
    MAX-ACCESS read-only
    STATUS     current
    DESCRIPTION
	    "Current Anonymous Users is the number of
	    anonymous users currently connected to the NNTP
	    Server."
    ::= { nntpServerEntry 18 }

nntpSrvrCurrentConnections OBJECT-TYPE
    SYNTAX     Gauge32
    MAX-ACCESS read-only
    STATUS     current
    DESCRIPTION
	    "Current Connections is the current number of
	    connections to the NNTP Server."
    ::= { nntpServerEntry 19 }

nntpSrvrCurrentNonAnonymousUsers OBJECT-TYPE
    SYNTAX     Gauge32
    MAX-ACCESS read-only
    STATUS     current
    DESCRIPTION
	    "Current NonAnonymous Users is the number of
	    nonanonymous users currently connected to the
	    NNTP Server."
    ::= { nntpServerEntry 20 }

nntpSrvrCurrentOutboundConns OBJECT-TYPE
    SYNTAX     Gauge32
    MAX-ACCESS read-only
    STATUS     current
    DESCRIPTION
	    "Current Outbound Connections is the number of
	    current outbound connections being made by the
	    NNTP Server."
    ::= { nntpServerEntry 21 }

nntpSrvrFailedOutboundLogons OBJECT-TYPE
    SYNTAX     Gauge32
    MAX-ACCESS read-only
    STATUS     current
    DESCRIPTION
	    "Failed Outbound Logons is the number of failed
	    outbound logons made by the NNTP Server."
    ::= { nntpServerEntry 22 }

nntpSrvrHistoryMapEntries OBJECT-TYPE
    SYNTAX     Gauge32
    MAX-ACCESS read-only
    STATUS     current
    DESCRIPTION
	    "History Map Entries is the entries inserted
	    into the history mapping table of the NNTP
	    Server."
    ::= { nntpServerEntry 23 }

nntpSrvrHistoryMapEntriesPerSec OBJECT-TYPE
    SYNTAX     Gauge32
    MAX-ACCESS read-only
    STATUS     current
    DESCRIPTION
	    "History Map Entries/Sec is the entries
	    inserted per sec into the history mapping table
	    of the NNTP Server."
    ::= { nntpServerEntry 24 }

nntpSrvrMaximumAnonymousUsers OBJECT-TYPE
    SYNTAX     Gauge32
    MAX-ACCESS read-only
    STATUS     current
    DESCRIPTION
	    "Maximum Anonymous Users is the maximum number
	    of anonymous users simultaneously connected to
	    the NNTP Server."
    ::= { nntpServerEntry 25 }

nntpSrvrMaximumConnections OBJECT-TYPE
    SYNTAX     Gauge32
    MAX-ACCESS read-only
    STATUS     current
    DESCRIPTION
	    "Maximum Connections is the maximum number of
	    simultaneous connections to the NNTP Server."
    ::= { nntpServerEntry 26 }

nntpSrvrMaximumNonAnonymousUsers OBJECT-TYPE
    SYNTAX     Gauge32
    MAX-ACCESS read-only
    STATUS     current
    DESCRIPTION
	    "Maximum NonAnonymous Users is the maximum
	    number of nonanonymous users simultaneously
	    connected to the NNTP Server."
    ::= { nntpServerEntry 27 }

nntpSrvrModeratedPostingsFailed OBJECT-TYPE
    SYNTAX     Gauge32
    MAX-ACCESS read-only
    STATUS     current
    DESCRIPTION
	    "Moderated Postings Failed is the total number
	    of moderated postings the NNTP Server fails to
	    send to an SMTP Server."
    ::= { nntpServerEntry 28 }

nntpSrvrModeratedPostingsSent OBJECT-TYPE
    SYNTAX     Gauge32
    MAX-ACCESS read-only
    STATUS     current
    DESCRIPTION
	    "Moderated Postings Sent is the total number of
	    moderated postings the NNTP Server attempts to
	    send to an SMTP Server."
    ::= { nntpServerEntry 29 }

nntpSrvrSessionsFlowControlled OBJECT-TYPE
    SYNTAX     Gauge32
    MAX-ACCESS read-only
    STATUS     current
    DESCRIPTION
	    "Sessions Flow Control is the number of client
	    sessions currently in a flow controlled state
	    in the NNTP Server."
    ::= { nntpServerEntry 30 }

nntpSrvrTotalAnonymousUsers OBJECT-TYPE
    SYNTAX     Gauge32
    MAX-ACCESS read-only
    STATUS     current
    DESCRIPTION
	    "Total Anonymous Users is the total number of
	    anonymous users that have ever connected to the
	    NNTP Server."
    ::= { nntpServerEntry 31 }

nntpSrvrTotalConnections OBJECT-TYPE
    SYNTAX     Gauge32
    MAX-ACCESS read-only
    STATUS     current
    DESCRIPTION
	    "Total Connections is the number of connections
	    that have been made to the NNTP Server."
    ::= { nntpServerEntry 32 }

nntpSrvrTotalNonAnonymousUsers OBJECT-TYPE
    SYNTAX     Gauge32
    MAX-ACCESS read-only
    STATUS     current
    DESCRIPTION
	    "Total NonAnonymous Users is the total number
	    of nonanonymous users that have ever connected
	    to the NNTP Server."
    ::= { nntpServerEntry 33 }

nntpSrvrTotalOutboundConnections OBJECT-TYPE
    SYNTAX     Gauge32
    MAX-ACCESS read-only
    STATUS     current
    DESCRIPTION
	    "Total Outbound Connections is the number of
	    outbound connections that have been made by the
	    NNTP Server."
    ::= { nntpServerEntry 34 }

nntpSrvrTotalOutboundConnsFailed OBJECT-TYPE
    SYNTAX     Gauge32
    MAX-ACCESS read-only
    STATUS     current
    DESCRIPTION
	    "Total Outbound Connections Failed is the
	    number of unsucessful outbound connections that
	    have been made by the NNTP Server."
    ::= { nntpServerEntry 35 }

nntpSrvrTotalPassiveFeeds OBJECT-TYPE
    SYNTAX     Gauge32
    MAX-ACCESS read-only
    STATUS     current
    DESCRIPTION
	    "Total Passive Feeds is the number of passive
	    feeds accepted by the NNTP Server."
    ::= { nntpServerEntry 36 }

nntpSrvrTotalPullFeeds OBJECT-TYPE
    SYNTAX     Gauge32
    MAX-ACCESS read-only
    STATUS     current
    DESCRIPTION
	    "Total Pull Feeds is the number of pull feeds
	    made by the NNTP Server."
    ::= { nntpServerEntry 37 }

nntpSrvrTotalPushFeeds OBJECT-TYPE
    SYNTAX     Gauge32
    MAX-ACCESS read-only
    STATUS     current
    DESCRIPTION
	    "Total Push Feeds is the number of push feeds
	    made by the NNTP Server."
    ::= { nntpServerEntry 38 }

nntpSrvrTotalSSLConnections OBJECT-TYPE
    SYNTAX     Gauge32
    MAX-ACCESS read-only
    STATUS     current
    DESCRIPTION
	    "Total SSL Connections is the number of SSL
	    connections that have been made to the NNTP
	    Server."
    ::= { nntpServerEntry 39 }

nntpSrvrXoverEntries OBJECT-TYPE
    SYNTAX     Gauge32
    MAX-ACCESS read-only
    STATUS     current
    DESCRIPTION
	    "Xover Entries is the number of xover entries
	    in the xover table table of the NNTP Server."
    ::= { nntpServerEntry 40 }

nntpSrvrXoverEntriesPerSec OBJECT-TYPE
    SYNTAX     Gauge32
    MAX-ACCESS read-only
    STATUS     current
    DESCRIPTION
	    "Xover Entries/Sec is the number of xover
	    entries inserted per sec in the xover table
	    table of the NNTP Server."
    ::= { nntpServerEntry 41 }

ntds OBJECT-IDENTITY
    STATUS     current
    DESCRIPTION
	    "The NTDS object provides statistics about the
	    activity of Active Directory."
    ::= { advanced 55 }

ntdsABANRPerSec OBJECT-TYPE
    SYNTAX     Gauge32
    MAX-ACCESS read-only
    STATUS     current
    DESCRIPTION
	    "The rate at which Address Book clients perform
	    Ambiguous Name Resolutions operations."
    ::= { ntds 1 }

ntdsABBrowsesPerSec OBJECT-TYPE
    SYNTAX     Gauge32
    MAX-ACCESS read-only
    STATUS     current
    DESCRIPTION
	    "AB Browses/sec is the rate at which Address
	    Book clients perform browse operations."
    ::= { ntds 2 }

ntdsABClientSessions OBJECT-TYPE
    SYNTAX     Gauge32
    MAX-ACCESS read-only
    STATUS     current
    DESCRIPTION
	    "AB Client Sessions is the number of connected
	    Address Book client sessions."
    ::= { ntds 3 }

ntdsABMatchesPerSec OBJECT-TYPE
    SYNTAX     Gauge32
    MAX-ACCESS read-only
    STATUS     current
    DESCRIPTION
	    "The rate at which Address Book clients perform
	    find operations."
    ::= { ntds 4 }

ntdsABPropertyReadsPerSec OBJECT-TYPE
    SYNTAX     Gauge32
    MAX-ACCESS read-only
    STATUS     current
    DESCRIPTION
	    "The rate at which Address Book clients perform
	    property read operations."
    ::= { ntds 5 }

ntdsABProxyLookupsPerSec OBJECT-TYPE
    SYNTAX     Gauge32
    MAX-ACCESS read-only
    STATUS     current
    DESCRIPTION
	    "The rate at which proxy clients perform search
	    operations."
    ::= { ntds 6 }

ntdsABSearchesPerSec OBJECT-TYPE
    SYNTAX     Gauge32
    MAX-ACCESS read-only
    STATUS     current
    DESCRIPTION
	    "The rate at which Address Book clients perform
	    key search operations."
    ::= { ntds 7 }

ntdsATQThreadsLDAP OBJECT-TYPE
    SYNTAX     Gauge32
    MAX-ACCESS read-only
    STATUS     current
    DESCRIPTION
	    "The number of threads that ATQ has currently
	    allocated to servicing LDAP requests."
    ::= { ntds 8 }

ntdsATQThreadsOther OBJECT-TYPE
    SYNTAX     Gauge32
    MAX-ACCESS read-only
    STATUS     current
    DESCRIPTION
	    "The number of threads that the ATQ has
	    currently allocated to DS services other than
	    LDAP."
    ::= { ntds 9 }

ntdsATQThreadsTotal OBJECT-TYPE
    SYNTAX     Gauge32
    MAX-ACCESS read-only
    STATUS     current
    DESCRIPTION
	    "The total number of ATQ threads that are
	    either waiting to service an incoming request,
	    or are already servicing a request."
    ::= { ntds 10 }

ntdsDRAHighestUSNCommitHighPart OBJECT-TYPE
    SYNTAX     Gauge32
    MAX-ACCESS read-only
    STATUS     current
    DESCRIPTION
	    "High-order 32 bits of the highest USN
	    Committed on the DSA."
    ::= { ntds 11 }

ntdsDRAHighestUSNCommitLowPart OBJECT-TYPE
    SYNTAX     Gauge32
    MAX-ACCESS read-only
    STATUS     current
    DESCRIPTION
	    "Low-order 32 bits of the highest USN Committed
	    on the DSA."
    ::= { ntds 12 }

ntdsDRAHighestUSNIssuedHighPart OBJECT-TYPE
    SYNTAX     Gauge32
    MAX-ACCESS read-only
    STATUS     current
    DESCRIPTION
	    "High-order 32 bits of the highest USN Issued
	    on the DSA."
    ::= { ntds 13 }

ntdsDRAHighestUSNIssuedLowPart OBJECT-TYPE
    SYNTAX     Gauge32
    MAX-ACCESS read-only
    STATUS     current
    DESCRIPTION
	    "Low-order 32 bits of the highest USN Issued on
	    the DSA."
    ::= { ntds 14 }

ntdsDRAInboundBytesCBSACSBoot OBJECT-TYPE
    SYNTAX     Gauge32
    MAX-ACCESS read-only
    STATUS     current
    DESCRIPTION
	    "Compressed size in bytes of inbound compressed
	    replication data (size after compression, from
	    DSAs in other sites)."
    ::= { ntds 15 }

ntdsDRAInboundBytesCBSACPerSec OBJECT-TYPE
    SYNTAX     Gauge32
    MAX-ACCESS read-only
    STATUS     current
    DESCRIPTION
	    "Compressed size in bytes of inbound compressed
	    replication data (size after compression, from
	    DSAs in other sites)."
    ::= { ntds 16 }

ntdsDRAInboundBytesCBSBCSBoot OBJECT-TYPE
    SYNTAX     Gauge32
    MAX-ACCESS read-only
    STATUS     current
    DESCRIPTION
	    "Original size in bytes of inbound compressed
	    replication data (size before compression, from
	    DSAs in other sites)."
    ::= { ntds 17 }

ntdsDRAInboundBytesCBSBCPerSec OBJECT-TYPE
    SYNTAX     Gauge32
    MAX-ACCESS read-only
    STATUS     current
    DESCRIPTION
	    "Original size in bytes of inbound compressed
	    replication data (size before compression, from
	    DSAs in other sites)."
    ::= { ntds 18 }

ntdsDRAInboundBytesNotCWSSBoot OBJECT-TYPE
    SYNTAX     Gauge32
    MAX-ACCESS read-only
    STATUS     current
    DESCRIPTION
	    "Number of bytes replicated in that were not
	    compressed at the source (i.e., from DSAs in
	    the same site)."
    ::= { ntds 19 }

ntdsDRAInboundBytesNotCWSPerSec OBJECT-TYPE
    SYNTAX     Gauge32
    MAX-ACCESS read-only
    STATUS     current
    DESCRIPTION
	    "Number of bytes replicated in that were not
	    compressed at the source (i.e., from DSAs in
	    the same site)."
    ::= { ntds 20 }

ntdsDRAInboundBytesTotalBoot OBJECT-TYPE
    SYNTAX     Gauge32
    MAX-ACCESS read-only
    STATUS     current
    DESCRIPTION
	    "Total number of bytes replicated in.  Sum of
	    the number of uncompressed bytes (never
	    compressed) and the number of compressed bytes
	    (after compression)."
    ::= { ntds 21 }

ntdsDRAInboundBytesTotalPerSec OBJECT-TYPE
    SYNTAX     Gauge32
    MAX-ACCESS read-only
    STATUS     current
    DESCRIPTION
	    "Total number of bytes replicated in.  Sum of
	    the number of uncompressed bytes (never
	    compressed) and the number of compressed bytes
	    (after compression)."
    ::= { ntds 22 }

ntdsDRAInboundFullSyncObjsRemain OBJECT-TYPE
    SYNTAX     Gauge32
    MAX-ACCESS read-only
    STATUS     current
    DESCRIPTION
	    "Number of objects remaining until the full
	    sync completes (when set)."
    ::= { ntds 23 }

ntdsDRAInboundObjUpdsRemainInPkt OBJECT-TYPE
    SYNTAX     Gauge32
    MAX-ACCESS read-only
    STATUS     current
    DESCRIPTION
	    "The number of object updates received in the
	    current directory replication update packet
	    that have not yet been applied to the local
	    server."
    ::= { ntds 24 }

ntdsDRAInboundObjsAppliedPerSec OBJECT-TYPE
    SYNTAX     Gauge32
    MAX-ACCESS read-only
    STATUS     current
    DESCRIPTION
	    "The rate at which replication updates received
	    from replication partners are applied by the
	    local directory service.  This count excludes
	    changes that are received but not applied
	    (e.g., when the change is already present). 
	    This indicates how much replication update
	    activity is occuring on the server as a result
	    of changes generated on other servers."
    ::= { ntds 25 }

ntdsDRAInboundObjsFilteredPerSec OBJECT-TYPE
    SYNTAX     Gauge32
    MAX-ACCESS read-only
    STATUS     current
    DESCRIPTION
	    "Number of objects received from inbound
	    replication partners that contained no updates
	    that needed to be applied."
    ::= { ntds 26 }

ntdsDRAInboundObjectsPerSec OBJECT-TYPE
    SYNTAX     Gauge32
    MAX-ACCESS read-only
    STATUS     current
    DESCRIPTION
	    "No of objects received from neighbors through
	    inbound replication."
    ::= { ntds 27 }

ntdsDRAInboundPropAppliedPerSec OBJECT-TYPE
    SYNTAX     Gauge32
    MAX-ACCESS read-only
    STATUS     current
    DESCRIPTION
	    "No of properties that are updated due to
	    incoming property winning the reconciliation
	    logic."
    ::= { ntds 28 }

ntdsDRAInboundPropFilteredPerSec OBJECT-TYPE
    SYNTAX     Gauge32
    MAX-ACCESS read-only
    STATUS     current
    DESCRIPTION
	    "No of property changes that are received
	    during the replication that we have already
	    seen."
    ::= { ntds 29 }

ntdsDRAInboundPropTotalPerSec OBJECT-TYPE
    SYNTAX     Gauge32
    MAX-ACCESS read-only
    STATUS     current
    DESCRIPTION
	    "Total number of object properties received
	    from inbound replication partners."
    ::= { ntds 30 }

ntdsDRAInboundValuesDNsPerSec OBJECT-TYPE
    SYNTAX     Gauge32
    MAX-ACCESS read-only
    STATUS     current
    DESCRIPTION
	    "Number of object property values received from
	    inbound replication partners that are
	    Distinguished Names; i.e., that reference other
	    objects.  DN-values, such as group or
	    distribution list memberships, are generally
	    more expensive to apply than other kinds of
	    values."
    ::= { ntds 31 }

ntdsDRAInboundValuesTotalPerSec OBJECT-TYPE
    SYNTAX     Gauge32
    MAX-ACCESS read-only
    STATUS     current
    DESCRIPTION
	    "Total number of object property values
	    received from inbound replication partners. 
	    Each inbound object has one or more properties,
	    and each property has zero or more values. 
	    Zero values indicates property removal."
    ::= { ntds 32 }

ntdsDRAOutboundBytesCBSACSBoot OBJECT-TYPE
    SYNTAX     Gauge32
    MAX-ACCESS read-only
    STATUS     current
    DESCRIPTION
	    "Compressed size in bytes of outbound
	    compressed replication data (size after
	    compression, from DSAs in other sites)."
    ::= { ntds 33 }

ntdsDRAOutboundBytesCBSACPerSec OBJECT-TYPE
    SYNTAX     Gauge32
    MAX-ACCESS read-only
    STATUS     current
    DESCRIPTION
	    "Compressed size in bytes of outbound
	    compressed replication data (size after
	    compression, from DSAs in other sites)."
    ::= { ntds 34 }

ntdsDRAOutboundBytesCBSBCSBoot OBJECT-TYPE
    SYNTAX     Gauge32
    MAX-ACCESS read-only
    STATUS     current
    DESCRIPTION
	    "Original size in bytes of outbound compressed
	    replication data (size before compression, from
	    DSAs in other sites)."
    ::= { ntds 35 }

ntdsDRAOutboundBytesCBSBCPerSec OBJECT-TYPE
    SYNTAX     Gauge32
    MAX-ACCESS read-only
    STATUS     current
    DESCRIPTION
	    "Original size in bytes of outbound compressed
	    replication data (size before compression, from
	    DSAs in other sites)."
    ::= { ntds 36 }

ntdsDRAOutboundBytesNotCWSSBoot OBJECT-TYPE
    SYNTAX     Gauge32
    MAX-ACCESS read-only
    STATUS     current
    DESCRIPTION
	    "Number of bytes replicated out that were not
	    compressed (i.e., from DSAs in the same site)."
    ::= { ntds 37 }

ntdsDRAOutboundBytesNotCWSPerSec OBJECT-TYPE
    SYNTAX     Gauge32
    MAX-ACCESS read-only
    STATUS     current
    DESCRIPTION
	    "Number of bytes replicated out that were not
	    compressed (i.e., from DSAs in the same site)."
    ::= { ntds 38 }

ntdsDRAOutboundBytesTotalBoot OBJECT-TYPE
    SYNTAX     Gauge32
    MAX-ACCESS read-only
    STATUS     current
    DESCRIPTION
	    "Total number of bytes replicated out.  Sum of
	    the number of uncompressed bytes (never
	    compressed) and the number of compressed bytes
	    (after compression)."
    ::= { ntds 39 }

ntdsDRAOutboundBytesTotalPerSec OBJECT-TYPE
    SYNTAX     Gauge32
    MAX-ACCESS read-only
    STATUS     current
    DESCRIPTION
	    "Total number of bytes replicated out.  Sum of
	    the number of uncompressed bytes (never
	    compressed) and the number of compressed bytes
	    (after compression)."
    ::= { ntds 40 }

ntdsDRAOutboundObjsFilterPerSec OBJECT-TYPE
    SYNTAX     Gauge32
    MAX-ACCESS read-only
    STATUS     current
    DESCRIPTION
	    "Number of objects looked at by outbound
	    replication that were determined to have no
	    updates that the outbound partner did not
	    already have."
    ::= { ntds 41 }

ntdsDRAOutboundObjectsPerSec OBJECT-TYPE
    SYNTAX     Gauge32
    MAX-ACCESS read-only
    STATUS     current
    DESCRIPTION
	    "No of objects replicated out."
    ::= { ntds 42 }

ntdsDRAOutboundPropertiesPerSec OBJECT-TYPE
    SYNTAX     Gauge32
    MAX-ACCESS read-only
    STATUS     current
    DESCRIPTION
	    "No of properties replicated out."
    ::= { ntds 43 }

ntdsDRAOutboundValuesDNsPerSec OBJECT-TYPE
    SYNTAX     Gauge32
    MAX-ACCESS read-only
    STATUS     current
    DESCRIPTION
	    "Number of object property values containing
	    Distinguished Names sent to outbound
	    replication partners.  DN-values, such as group
	    or distribution list memberships, are generally
	    more expensive to read than other kinds of
	    values."
    ::= { ntds 44 }

ntdsDRAOutboundValuesTotalPerSec OBJECT-TYPE
    SYNTAX     Gauge32
    MAX-ACCESS read-only
    STATUS     current
    DESCRIPTION
	    "Number of object property values sent to
	    outbound replication partners."
    ::= { ntds 45 }

ntdsDRAPendingReplicationSync OBJECT-TYPE
    SYNTAX     Gauge32
    MAX-ACCESS read-only
    STATUS     current
    DESCRIPTION
	    "DRA Pending Replication Synchronizations is
	    the number of directory synchronizations that
	    are queued for this server but not yet
	    processed."
    ::= { ntds 46 }

ntdsDRASyncFailOnSchemaMismatch OBJECT-TYPE
    SYNTAX     Gauge32
    MAX-ACCESS read-only
    STATUS     current
    DESCRIPTION
	    "No of sync requests made to the neighbors that
	    failed because their schema are out of sync."
    ::= { ntds 47 }

ntdsDRASyncRequestsMade OBJECT-TYPE
    SYNTAX     Gauge32
    MAX-ACCESS read-only
    STATUS     current
    DESCRIPTION
	    "No of sync requests made to the neighbors."
    ::= { ntds 48 }

ntdsDRASyncRequestsSuccessful OBJECT-TYPE
    SYNTAX     Gauge32
    MAX-ACCESS read-only
    STATUS     current
    DESCRIPTION
	    "No of sync requests made to the neighbors that
	    successfully returned."
    ::= { ntds 49 }

ntdsDSPercentReadsOther OBJECT-TYPE
    SYNTAX     Gauge32
    MAX-ACCESS read-only
    STATUS     current
    DESCRIPTION
	    "% of directory reads not coming from
	    SAM/DRA/LDAP/LSA/XDS/KCC/NSPI."
    ::= { ntds 50 }

ntdsDSPercentReadsFromDRA OBJECT-TYPE
    SYNTAX     Gauge32
    MAX-ACCESS read-only
    STATUS     current
    DESCRIPTION
	    "% of directory reads coming from DRA."
    ::= { ntds 51 }

ntdsDSPercentReadsFromKCC OBJECT-TYPE
    SYNTAX     Gauge32
    MAX-ACCESS read-only
    STATUS     current
    DESCRIPTION
	    "% of directory reads coming from KCC."
    ::= { ntds 52 }

ntdsDSPercentReadsFromLSA OBJECT-TYPE
    SYNTAX     Gauge32
    MAX-ACCESS read-only
    STATUS     current
    DESCRIPTION
	    "% of directory reads coming from LSA."
    ::= { ntds 53 }

ntdsDSPercentReadsFromNSPI OBJECT-TYPE
    SYNTAX     Gauge32
    MAX-ACCESS read-only
    STATUS     current
    DESCRIPTION
	    "% of directory reads coming from NSPI."
    ::= { ntds 54 }

ntdsDSPercentReadsFromSAM OBJECT-TYPE
    SYNTAX     Gauge32
    MAX-ACCESS read-only
    STATUS     current
    DESCRIPTION
	    "% of directory reads coming from SAM."
    ::= { ntds 55 }

ntdsDSPercentReadsFromXDS OBJECT-TYPE
    SYNTAX     Gauge32
    MAX-ACCESS read-only
    STATUS     current
    DESCRIPTION
	    "% of directory reads coming from XDS."
    ::= { ntds 56 }

ntdsDSPercentSearchesOther OBJECT-TYPE
    SYNTAX     Gauge32
    MAX-ACCESS read-only
    STATUS     current
    DESCRIPTION
	    "% of directory searches not coming from
	    SAM/DRA/LDAP/LSA/XDS/KCC/NSPI."
    ::= { ntds 57 }

ntdsDSPercentSearchesFromDRA OBJECT-TYPE
    SYNTAX     Gauge32
    MAX-ACCESS read-only
    STATUS     current
    DESCRIPTION
	    "% of directory searches coming from DRA."
    ::= { ntds 58 }

ntdsDSPercentSearchesFromKCC OBJECT-TYPE
    SYNTAX     Gauge32
    MAX-ACCESS read-only
    STATUS     current
    DESCRIPTION
	    "% of directory searches coming from KCC."
    ::= { ntds 59 }

ntdsDSPercentSearchesFromLDAP OBJECT-TYPE
    SYNTAX     Gauge32
    MAX-ACCESS read-only
    STATUS     current
    DESCRIPTION
	    "% of directory searches coming from LDAP."
    ::= { ntds 60 }

ntdsDSPercentSearchesFromLSA OBJECT-TYPE
    SYNTAX     Gauge32
    MAX-ACCESS read-only
    STATUS     current
    DESCRIPTION
	    "% of directory searches coming from LSA."
    ::= { ntds 61 }

ntdsDSPercentSearchesFromNSPI OBJECT-TYPE
    SYNTAX     Gauge32
    MAX-ACCESS read-only
    STATUS     current
    DESCRIPTION
	    "% of directory searches coming from NSPI."
    ::= { ntds 62 }

ntdsDSPercentSearchesFromSAM OBJECT-TYPE
    SYNTAX     Gauge32
    MAX-ACCESS read-only
    STATUS     current
    DESCRIPTION
	    "% of directory searches coming from SAM."
    ::= { ntds 63 }

ntdsDSPercentSearchesFromXDS OBJECT-TYPE
    SYNTAX     Gauge32
    MAX-ACCESS read-only
    STATUS     current
    DESCRIPTION
	    "% of directory searches coming from XDS."
    ::= { ntds 64 }

ntdsDSPercentWritesOther OBJECT-TYPE
    SYNTAX     Gauge32
    MAX-ACCESS read-only
    STATUS     current
    DESCRIPTION
	    "% of directory writes not coming from
	    SAM/DRA/LDAP/LSA/XDS/KCC/NSPI."
    ::= { ntds 65 }

ntdsDSPercentWritesFromDRA OBJECT-TYPE
    SYNTAX     Gauge32
    MAX-ACCESS read-only
    STATUS     current
    DESCRIPTION
	    "% of directory writes coming from DRA."
    ::= { ntds 66 }

ntdsDSPercentWritesFromKCC OBJECT-TYPE
    SYNTAX     Gauge32
    MAX-ACCESS read-only
    STATUS     current
    DESCRIPTION
	    "% of directory writes coming from KCC."
    ::= { ntds 67 }

ntdsDSPercentWritesFromLDAP OBJECT-TYPE
    SYNTAX     Gauge32
    MAX-ACCESS read-only
    STATUS     current
    DESCRIPTION
	    "% of directory writes coming from LDAP."
    ::= { ntds 68 }

ntdsDSPercentWritesFromLSA OBJECT-TYPE
    SYNTAX     Gauge32
    MAX-ACCESS read-only
    STATUS     current
    DESCRIPTION
	    "% of directory writes coming from LSA."
    ::= { ntds 69 }

ntdsDSPercentWritesFromNSPI OBJECT-TYPE
    SYNTAX     Gauge32
    MAX-ACCESS read-only
    STATUS     current
    DESCRIPTION
	    "% of directory writes coming from NSPI."
    ::= { ntds 70 }

ntdsDSPercentWritesFromSAM OBJECT-TYPE
    SYNTAX     Gauge32
    MAX-ACCESS read-only
    STATUS     current
    DESCRIPTION
	    "% of directory writes coming from SAM."
    ::= { ntds 71 }

ntdsDSPercentWritesFromXDS OBJECT-TYPE
    SYNTAX     Gauge32
    MAX-ACCESS read-only
    STATUS     current
    DESCRIPTION
	    "% of directory writes coming from XDS."
    ::= { ntds 72 }

ntdsDSClientBindsPerSec OBJECT-TYPE
    SYNTAX     Gauge32
    MAX-ACCESS read-only
    STATUS     current
    DESCRIPTION
	    "Number of ntdsapi.dll binds per second
	    serviced by this DC."
    ::= { ntds 73 }

ntdsDSClientNameTranslatePerSec OBJECT-TYPE
    SYNTAX     Gauge32
    MAX-ACCESS read-only
    STATUS     current
    DESCRIPTION
	    "Number of ntdsapi.dll name translations per
	    second serviced by this DC."
    ::= { ntds 74 }

ntdsDSDirectoryReadsPerSec OBJECT-TYPE
    SYNTAX     Gauge32
    MAX-ACCESS read-only
    STATUS     current
    DESCRIPTION
	    "Number of directory reads per second."
    ::= { ntds 75 }

ntdsDSDirectorySearchesPerSec OBJECT-TYPE
    SYNTAX     Gauge32
    MAX-ACCESS read-only
    STATUS     current
    DESCRIPTION
	    "Number of directory searches per second."
    ::= { ntds 76 }

ntdsDSDirectoryWritesPerSec OBJECT-TYPE
    SYNTAX     Gauge32
    MAX-ACCESS read-only
    STATUS     current
    DESCRIPTION
	    "Number of directory writes per second."
    ::= { ntds 77 }

ntdsDSMonitorListSize OBJECT-TYPE
    SYNTAX     Gauge32
    MAX-ACCESS read-only
    STATUS     current
    DESCRIPTION
	    "The number of requests to be notified when
	    objects are updated that are currently
	    registered with this DSA."
    ::= { ntds 78 }

ntdsDSNameCacheHitRate OBJECT-TYPE
    SYNTAX     Gauge32
    MAX-ACCESS read-only
    STATUS     current
    DESCRIPTION
	    "The percentage of directory object name
	    component look ups that are satisfied out of
	    the DSA's name cache."
    ::= { ntds 79 }

ntdsDSNotifyQueueSize OBJECT-TYPE
    SYNTAX     Gauge32
    MAX-ACCESS read-only
    STATUS     current
    DESCRIPTION
	    "The number of pending update notifications
	    that have been queued, but not yet transmitted
	    to clients."
    ::= { ntds 80 }

ntdsDSSearchSuboperationsPerSec OBJECT-TYPE
    SYNTAX     Gauge32
    MAX-ACCESS read-only
    STATUS     current
    DESCRIPTION
	    "Number of search suboperations per second. 
	    One search operation is made up of many sub
	    operations.  A sub operation roughly
	    corresponds to an object the search causes the
	    DS to consider."
    ::= { ntds 81 }

ntdsDSSecurityDescPropEvents OBJECT-TYPE
    SYNTAX     Gauge32
    MAX-ACCESS read-only
    STATUS     current
    DESCRIPTION
	    "DS Security Descriptor Propagations Events is
	    the number of Security Descriptor Propagation
	    Events that are queued but not yet processed."
    ::= { ntds 82 }

ntdsDSSecurityDescPropAvgExTime OBJECT-TYPE
    SYNTAX     Gauge32
    MAX-ACCESS read-only
    STATUS     current
    DESCRIPTION
	    "Average length of time the Security Descriptor
	    propagator spends waiting for exclusive access
	    to Data Base elements during a Security
	    Descriptor Propagation sub-operation."
    ::= { ntds 83 }

ntdsDSSecurityDescPropRunQueue OBJECT-TYPE
    SYNTAX     Gauge32
    MAX-ACCESS read-only
    STATUS     current
    DESCRIPTION
	    "Number of objects remaining to examine while
	    processing the current DS Security Descriptor
	    Propagator Event."
    ::= { ntds 84 }

ntdsDSSecurityDescSubopPerSec OBJECT-TYPE
    SYNTAX     Gauge32
    MAX-ACCESS read-only
    STATUS     current
    DESCRIPTION
	    "Number of Security Descriptor Propagation
	    suboperations per second.  One Security
	    Descriptor Propagation operation is made up of
	    many sub operations.  A sub operation roughly
	    corresponds to an object the propagation causes
	    the propagator to examine."
    ::= { ntds 85 }

ntdsDSServerBindsPerSec OBJECT-TYPE
    SYNTAX     Gauge32
    MAX-ACCESS read-only
    STATUS     current
    DESCRIPTION
	    "Number of DC-to-DC binds per second serviced
	    by this DC."
    ::= { ntds 86 }

ntdsDSServerNameTranslatePerSec OBJECT-TYPE
    SYNTAX     Gauge32
    MAX-ACCESS read-only
    STATUS     current
    DESCRIPTION
	    "Number of DC-to-DC name translations per
	    second serviced by this DC."
    ::= { ntds 87 }

ntdsDSThreadsInUse OBJECT-TYPE
    SYNTAX     Gauge32
    MAX-ACCESS read-only
    STATUS     current
    DESCRIPTION
	    "DS Threads in Use is the current number of
	    threads in use by the directory service
	    (different than the number of threads in the
	    directory service process).  Threads in Use is
	    the number of threads currently servicing
	    client API calls and can be used to indicate
	    whether additional processors could be of
	    benefit."
    ::= { ntds 88 }

ntdsKDCASRequests OBJECT-TYPE
    SYNTAX     Gauge32
    MAX-ACCESS read-only
    STATUS     current
    DESCRIPTION
	    "The number of AS requests serviced by the KDC
	    per second. AS requests are used by client to
	    obtain a ticket granting ticket."
    ::= { ntds 89 }

ntdsKDCTGSRequests OBJECT-TYPE
    SYNTAX     Gauge32
    MAX-ACCESS read-only
    STATUS     current
    DESCRIPTION
	    "The number of TGS requests serviced by the KDC
	    per second. TGS requests are used by the client
	    to obtain a ticket to a resource."
    ::= { ntds 90 }

ntdsKerberosAuthentications OBJECT-TYPE
    SYNTAX     Gauge32
    MAX-ACCESS read-only
    STATUS     current
    DESCRIPTION
	    "The number of times per second that clients
	    use a ticket to this DC to authenticate to this
	    DC."
    ::= { ntds 91 }

ntdsLDAPActiveThreads OBJECT-TYPE
    SYNTAX     Gauge32
    MAX-ACCESS read-only
    STATUS     current
    DESCRIPTION
	    "LDAP Active Threads is the current number of
	    threads in use by the LDAP subsystem of the
	    local direcotry service."
    ::= { ntds 92 }

ntdsLDAPBindTime OBJECT-TYPE
    SYNTAX     Gauge32
    MAX-ACCESS read-only
    STATUS     current
    DESCRIPTION
	    "Time (in milliseconds) taken for last
	    successful LDAP bind."
    ::= { ntds 93 }

ntdsLDAPClientSessions OBJECT-TYPE
    SYNTAX     Gauge32
    MAX-ACCESS read-only
    STATUS     current
    DESCRIPTION
	    "LDAP Client Sessions is the number of
	    connected LDAP client sessions."
    ::= { ntds 94 }

ntdsLDAPSearchesPerSec OBJECT-TYPE
    SYNTAX     Gauge32
    MAX-ACCESS read-only
    STATUS     current
    DESCRIPTION
	    "LDAP Searches/sec is the rate at which LDAP
	    clients perform search operations."
    ::= { ntds 95 }

ntdsLDAPSuccessfulBinds OBJECT-TYPE
    SYNTAX     Gauge32
    MAX-ACCESS read-only
    STATUS     current
    DESCRIPTION
	    "% of LDAP bind attempts that were successful."
    ::= { ntds 96 }

ntdsLDAPSuccessfulBindsPerSec OBJECT-TYPE
    SYNTAX     Gauge32
    MAX-ACCESS read-only
    STATUS     current
    DESCRIPTION
	    "Number of LDAP Binds per second."
    ::= { ntds 97 }

ntdsLDAPUDPOperationsPerSec OBJECT-TYPE
    SYNTAX     Gauge32
    MAX-ACCESS read-only
    STATUS     current
    DESCRIPTION
	    "The number of UDP operations the LDAP server
	    is processing per second."
    ::= { ntds 98 }

ntdsLDAPWritesPerSec OBJECT-TYPE
    SYNTAX     Gauge32
    MAX-ACCESS read-only
    STATUS     current
    DESCRIPTION
	    "LDAP Writes/sec is the rate at which LDAP
	    clients perform write operations."
    ::= { ntds 99 }

ntdsNTLMAuthentications OBJECT-TYPE
    SYNTAX     Gauge32
    MAX-ACCESS read-only
    STATUS     current
    DESCRIPTION
	    "Number of NTLM authentications per second
	    serviced by this DC."
    ::= { ntds 100 }

ntdsSAMAccountGroupMemEvalPerSec OBJECT-TYPE
    SYNTAX     Gauge32
    MAX-ACCESS read-only
    STATUS     current
    DESCRIPTION
	    "Number of SAM Account Group Membership
	    Evaluations per second."
    ::= { ntds 101 }

ntdsSAMDisplayInfoQueriesPerSec OBJECT-TYPE
    SYNTAX     Gauge32
    MAX-ACCESS read-only
    STATUS     current
    DESCRIPTION
	    "Number of queries made to obtain SAM display
	    information per second."
    ::= { ntds 102 }

ntdsSAMEnumerationsPerSec OBJECT-TYPE
    SYNTAX     Gauge32
    MAX-ACCESS read-only
    STATUS     current
    DESCRIPTION
	    "Number of SAM Enumerations per second."
    ::= { ntds 103 }

ntdsSAMGCEvaluationsPerSec OBJECT-TYPE
    SYNTAX     Gauge32
    MAX-ACCESS read-only
    STATUS     current
    DESCRIPTION
	    "Number of SAM Global Catalog Evaluations per
	    second."
    ::= { ntds 104 }

ntdsSAMMachineCreateAtpsPerSec OBJECT-TYPE
    SYNTAX     Gauge32
    MAX-ACCESS read-only
    STATUS     current
    DESCRIPTION
	    "Number of attempts made to create SAM machine
	    account per second."
    ::= { ntds 105 }

ntdsSAMMembershipChangesPerSec OBJECT-TYPE
    SYNTAX     Gauge32
    MAX-ACCESS read-only
    STATUS     current
    DESCRIPTION
	    "Number of SAM membership changes per second."
    ::= { ntds 106 }

ntdsSAMNonTransMemEvalPerSec OBJECT-TYPE
    SYNTAX     Gauge32
    MAX-ACCESS read-only
    STATUS     current
    DESCRIPTION
	    "Number of SAM Non-Transitive Membership
	    Evaluations per second."
    ::= { ntds 107 }

ntdsSAMPasswordChangesPerSec OBJECT-TYPE
    SYNTAX     Gauge32
    MAX-ACCESS read-only
    STATUS     current
    DESCRIPTION
	    "Number of SAM password changes per second."
    ::= { ntds 108 }

ntdsSAMResourceGrpMemEvalPerSec OBJECT-TYPE
    SYNTAX     Gauge32
    MAX-ACCESS read-only
    STATUS     current
    DESCRIPTION
	    "Number of SAM Resource Group Membership
	    Evaluations per second."
    ::= { ntds 109 }

ntdsSAMSuccessMachineCreatPerSec OBJECT-TYPE
    SYNTAX     Gauge32
    MAX-ACCESS read-only
    STATUS     current
    DESCRIPTION
	    "Number of successful machine creations per
	    second."
    ::= { ntds 110 }

ntdsSAMSuccessUserCreatePerSec OBJECT-TYPE
    SYNTAX     Gauge32
    MAX-ACCESS read-only
    STATUS     current
    DESCRIPTION
	    "Number of successful user creations per
	    second."
    ::= { ntds 111 }

ntdsSAMTransitiveMembEvalPerSec OBJECT-TYPE
    SYNTAX     Gauge32
    MAX-ACCESS read-only
    STATUS     current
    DESCRIPTION
	    "Number of SAM Transitive Membership
	    Evaluations per second."
    ::= { ntds 112 }

ntdsSAMUniversalGrpMemEvalPerSec OBJECT-TYPE
    SYNTAX     Gauge32
    MAX-ACCESS read-only
    STATUS     current
    DESCRIPTION
	    "Number of SAM Universal Group Membership
	    Evaluations per second."
    ::= { ntds 113 }

ntdsSAMUserCreateAttemptsPerSec OBJECT-TYPE
    SYNTAX     Gauge32
    MAX-ACCESS read-only
    STATUS     current
    DESCRIPTION
	    "Number of attempts made to create SAM user
	    account per second."
    ::= { ntds 114 }

ntdsXDSClientSessions OBJECT-TYPE
    SYNTAX     Gauge32
    MAX-ACCESS read-only
    STATUS     current
    DESCRIPTION
	    "XDS Client Sessions is the number of connected
	    Extended Directory Service client sessions. 
	    This indicates the number of connections from
	    other Windows NT services and the Windows NT
	    Administrator program."
    ::= { ntds 115 }

nwLinkIPXTable OBJECT-TYPE
    SYNTAX     SEQUENCE OF NWLinkIPXEntry
    MAX-ACCESS not-accessible
    STATUS     current
    DESCRIPTION
	    "The NWLink IPX performance object consists of
	    counters that measure datagram transmission to
	    and from computers using the IPX protocol. This
	    object only reports valid data for counters
	    that monitor datagrams and packets; for
	    frame-related counters, the object tends to
	    report zero values. In addition,
	    connection-related data is not likely to be
	    useful because IPX is a connectionless
	    protocol."
    ::= { advanced 56 }

nwLinkIPXEntry OBJECT-TYPE
    SYNTAX     NWLinkIPXEntry
    MAX-ACCESS not-accessible
    STATUS     current
    DESCRIPTION
	    "Performance information for one particular
	    instance of 'NWLink IPX' object."
    INDEX      { ipxInstance }
    ::= { nwLinkIPXTable 1 }

NWLinkIPXEntry ::= SEQUENCE {
    ipxInstance InstanceName,
    ipxBytesTotalPerSec Gauge32,
    ipxConnectionSessionTimeouts Gauge32,
    ipxConnectionsCanceled Gauge32,
    ipxConnectionsNoRetries Gauge32,
    ipxConnectionsOpen Gauge32,
    ipxConnectionsWithRetries Gauge32,
    ipxDatagramBytesReceivedPerSec Gauge32,
    ipxDatagramBytesSentPerSec Gauge32,
    ipxDatagramBytesPerSec Gauge32,
    ipxDatagramsReceivedPerSec Gauge32,
    ipxDatagramsSentPerSec Gauge32,
    ipxDatagramsPerSec Gauge32,
    ipxDisconnectsLocal Gauge32,
    ipxDisconnectsRemote Gauge32,
    ipxExpirationsAck Gauge32,
    ipxExpirationsResponse Gauge32,
    ipxFailuresAdapter Gauge32,
    ipxFailuresLink Gauge32,
    ipxFailuresNoListen Gauge32,
    ipxFailuresNotFound Gauge32,
    ipxFailuresResourceLocal Gauge32,
    ipxFailuresResourceRemote Gauge32,
    ipxFrameBytesReSentPerSec Gauge32,
    ipxFrameBytesReceivedPerSec Gauge32,
    ipxFrameBytesRejectedPerSec Gauge32,
    ipxFrameBytesSentPerSec Gauge32,
    ipxFrameBytesPerSec Gauge32,
    ipxFramesReSentPerSec Gauge32,
    ipxFramesReceivedPerSec Gauge32,
    ipxFramesRejectedPerSec Gauge32,
    ipxFramesSentPerSec Gauge32,
    ipxFramesPerSec Gauge32,
    ipxPacketsReceivedPerSec Gauge32,
    ipxPacketsSentPerSec Gauge32,
    ipxPacketsPerSec Gauge32,
    ipxPiggybackAckQueuedPerSec Gauge32,
    ipxPiggybackAckTimeouts Gauge32,
    ipxWindowSendAverage Gauge32,
    ipxWindowSendMaximum Gauge32
}

ipxInstance OBJECT-TYPE
    SYNTAX     InstanceName
    MAX-ACCESS read-only
    STATUS     current
    DESCRIPTION
	    "Instance name."
    ::= { nwLinkIPXEntry 1 }

ipxBytesTotalPerSec OBJECT-TYPE
    SYNTAX     Gauge32
    MAX-ACCESS read-only
    STATUS     current
    DESCRIPTION
	    "Bytes Total/sec is the sum of Frame Bytes/sec
	    and Datagram Bytes/sec.  This is the total rate
	    of bytes sent to or received from the network
	    by the protocol, but only counts the bytes in
	    frames (i.e., packets) which carry data."
    ::= { nwLinkIPXEntry 2 }

ipxConnectionSessionTimeouts OBJECT-TYPE
    SYNTAX     Gauge32
    MAX-ACCESS read-only
    STATUS     current
    DESCRIPTION
	    "Connection Session Timeouts is the number of
	    connections that were dropped due to a session
	    timeout.  This number is an accumulator and
	    shows a running total."
    ::= { nwLinkIPXEntry 3 }

ipxConnectionsCanceled OBJECT-TYPE
    SYNTAX     Gauge32
    MAX-ACCESS read-only
    STATUS     current
    DESCRIPTION
	    "Connections Canceled is the number of
	    connections that were canceled.  This number is
	    an accumulator and shows a running total."
    ::= { nwLinkIPXEntry 4 }

ipxConnectionsNoRetries OBJECT-TYPE
    SYNTAX     Gauge32
    MAX-ACCESS read-only
    STATUS     current
    DESCRIPTION
	    "Connections No Retries is the total count of
	    connections that were successfully made on the
	    first try.	This number is an accumulator and
	    shows a running total."
    ::= { nwLinkIPXEntry 5 }

ipxConnectionsOpen OBJECT-TYPE
    SYNTAX     Gauge32
    MAX-ACCESS read-only
    STATUS     current
    DESCRIPTION
	    "Connections Open is the number of connections
	    currently open for this protocol.  This counter
	    shows the current count only and does not
	    accumulate over time."
    ::= { nwLinkIPXEntry 6 }

ipxConnectionsWithRetries OBJECT-TYPE
    SYNTAX     Gauge32
    MAX-ACCESS read-only
    STATUS     current
    DESCRIPTION
	    "Connections With Retries is the total count of
	    connections that were made after retrying the
	    attempt.  A retry occurs when the first
	    connection attempt failed.	This number is an
	    accumulator and shows a running total."
    ::= { nwLinkIPXEntry 7 }

ipxDatagramBytesReceivedPerSec OBJECT-TYPE
    SYNTAX     Gauge32
    MAX-ACCESS read-only
    STATUS     current
    DESCRIPTION
	    "Datagram Bytes Received/sec is the rate at
	    which datagram bytes are received by the
	    computer.  A datagram is a connectionless
	    packet whose delivery to a remote computer is
	    not guaranteed."
    ::= { nwLinkIPXEntry 8 }

ipxDatagramBytesSentPerSec OBJECT-TYPE
    SYNTAX     Gauge32
    MAX-ACCESS read-only
    STATUS     current
    DESCRIPTION
	    "Datagram Bytes Sent/sec is the rate at which
	    datagram bytes are sent from the computer.	A
	    datagram is a connectionless packet whose
	    delivery to a remote computer is not
	    guaranteed."
    ::= { nwLinkIPXEntry 9 }

ipxDatagramBytesPerSec OBJECT-TYPE
    SYNTAX     Gauge32
    MAX-ACCESS read-only
    STATUS     current
    DESCRIPTION
	    "Datagram Bytes/sec is the rate at which
	    datagram bytes are processed by the computer. 
	    This counter is the sum of datagram bytes that
	    are sent as well as received.  A datagram is a
	    connectionless packet whose delivery to a
	    remote is not guaranteed."
    ::= { nwLinkIPXEntry 10 }

ipxDatagramsReceivedPerSec OBJECT-TYPE
    SYNTAX     Gauge32
    MAX-ACCESS read-only
    STATUS     current
    DESCRIPTION
	    "Datagrams Received/sec is the rate at which
	    datagrams are received by the computer.  A
	    datagram is a connectionless packet whose
	    delivery to a remote computer is not
	    guaranteed."
    ::= { nwLinkIPXEntry 11 }

ipxDatagramsSentPerSec OBJECT-TYPE
    SYNTAX     Gauge32
    MAX-ACCESS read-only
    STATUS     current
    DESCRIPTION
	    "Datagrams Sent/sec is the rate at which
	    datagrams are sent from the computer.  A
	    datagram is a connectionless packet whose
	    delivery to a remote computer is not
	    guaranteed."
    ::= { nwLinkIPXEntry 12 }

ipxDatagramsPerSec OBJECT-TYPE
    SYNTAX     Gauge32
    MAX-ACCESS read-only
    STATUS     current
    DESCRIPTION
	    "Datagrams/sec is the rate at which datagrams
	    are processed by the computer.  This counter
	    displays the sum of datagrams sent and
	    datagrams received.  A datagram is a
	    connectionless packet whose delivery to a
	    remote is not guaranteed."
    ::= { nwLinkIPXEntry 13 }

ipxDisconnectsLocal OBJECT-TYPE
    SYNTAX     Gauge32
    MAX-ACCESS read-only
    STATUS     current
    DESCRIPTION
	    "Disconnects Local is the number of session
	    disconnections that were initiated by the local
	    computer.  This number is an accumulator and
	    shows a running total."
    ::= { nwLinkIPXEntry 14 }

ipxDisconnectsRemote OBJECT-TYPE
    SYNTAX     Gauge32
    MAX-ACCESS read-only
    STATUS     current
    DESCRIPTION
	    "Disconnects Remote is the number of session
	    disconnections that were initiated by the
	    remote computer.  This number is an accumulator
	    and shows a running total."
    ::= { nwLinkIPXEntry 15 }

ipxExpirationsAck OBJECT-TYPE
    SYNTAX     Gauge32
    MAX-ACCESS read-only
    STATUS     current
    DESCRIPTION
	    "Expirations Ack is the count of T2 timer
	    expirations."
    ::= { nwLinkIPXEntry 16 }

ipxExpirationsResponse OBJECT-TYPE
    SYNTAX     Gauge32
    MAX-ACCESS read-only
    STATUS     current
    DESCRIPTION
	    "Expirations Response is the count of T1 timer
	    expirations."
    ::= { nwLinkIPXEntry 17 }

ipxFailuresAdapter OBJECT-TYPE
    SYNTAX     Gauge32
    MAX-ACCESS read-only
    STATUS     current
    DESCRIPTION
	    "Failures Adapter is the number of connections
	    that were dropped due to an adapter failure. 
	    This number is an accumulator and shows a
	    running total."
    ::= { nwLinkIPXEntry 18 }

ipxFailuresLink OBJECT-TYPE
    SYNTAX     Gauge32
    MAX-ACCESS read-only
    STATUS     current
    DESCRIPTION
	    "Failures Link is the number of connections
	    that were dropped due to a link failure.  This
	    number is an accumulator and shows a running
	    total."
    ::= { nwLinkIPXEntry 19 }

ipxFailuresNoListen OBJECT-TYPE
    SYNTAX     Gauge32
    MAX-ACCESS read-only
    STATUS     current
    DESCRIPTION
	    "Failures No Listen is the number of
	    connections that were rejected because the
	    remote computer was not listening for
	    connection requests."
    ::= { nwLinkIPXEntry 20 }

ipxFailuresNotFound OBJECT-TYPE
    SYNTAX     Gauge32
    MAX-ACCESS read-only
    STATUS     current
    DESCRIPTION
	    "Failures Not Found is the number of connection
	    attempts that failed because the remote
	    computer could not be found.  This number is an
	    accumulator and shows a running total."
    ::= { nwLinkIPXEntry 21 }

ipxFailuresResourceLocal OBJECT-TYPE
    SYNTAX     Gauge32
    MAX-ACCESS read-only
    STATUS     current
    DESCRIPTION
	    "Failures Resource Local is the number of
	    connections that failed because of resource
	    problems or shortages on the local computer. 
	    This number is an accumulator and shows a
	    running total."
    ::= { nwLinkIPXEntry 22 }

ipxFailuresResourceRemote OBJECT-TYPE
    SYNTAX     Gauge32
    MAX-ACCESS read-only
    STATUS     current
    DESCRIPTION
	    "Failures Resource Remote is the number of
	    connections that failed because of resource
	    problems or shortages on the remote computer. 
	    This number is an accumulator and shows a
	    running total."
    ::= { nwLinkIPXEntry 23 }

ipxFrameBytesReSentPerSec OBJECT-TYPE
    SYNTAX     Gauge32
    MAX-ACCESS read-only
    STATUS     current
    DESCRIPTION
	    "Frame Bytes Re-Sent/sec is the rate at which
	    data bytes are re-sent by the computer.  This
	    counter only counts the bytes in frames that
	    carry data."
    ::= { nwLinkIPXEntry 24 }

ipxFrameBytesReceivedPerSec OBJECT-TYPE
    SYNTAX     Gauge32
    MAX-ACCESS read-only
    STATUS     current
    DESCRIPTION
	    "Frame Bytes Received/sec is the rate at which
	    data bytes are received by the computer.  This
	    counter only counts the frames (packets) that
	    carry data."
    ::= { nwLinkIPXEntry 25 }

ipxFrameBytesRejectedPerSec OBJECT-TYPE
    SYNTAX     Gauge32
    MAX-ACCESS read-only
    STATUS     current
    DESCRIPTION
	    "Frame Bytes Rejected/sec is the rate at which
	    data bytes are rejected.  This counter only
	    counts the bytes in data frames (packets) that
	    carry data."
    ::= { nwLinkIPXEntry 26 }

ipxFrameBytesSentPerSec OBJECT-TYPE
    SYNTAX     Gauge32
    MAX-ACCESS read-only
    STATUS     current
    DESCRIPTION
	    "Frame Bytes Sent/sec is the rate at which data
	    bytes are sent by the computer.  This counter
	    only counts the bytes in frames (packets) that
	    carry data."
    ::= { nwLinkIPXEntry 27 }

ipxFrameBytesPerSec OBJECT-TYPE
    SYNTAX     Gauge32
    MAX-ACCESS read-only
    STATUS     current
    DESCRIPTION
	    "Frame Bytes/sec is the rate at which data
	    bytes are processed by the computer.  This
	    counter is the sum of data frame bytes sent and
	    received.  This counter only counts the byte in
	    frames (packets) that carry data."
    ::= { nwLinkIPXEntry 28 }

ipxFramesReSentPerSec OBJECT-TYPE
    SYNTAX     Gauge32
    MAX-ACCESS read-only
    STATUS     current
    DESCRIPTION
	    "Frames Re-Sent/sec is the rate at which data
	    frames (packets) are re-sent by the computer. 
	    This counter only counts the frames or packets
	    that carry data."
    ::= { nwLinkIPXEntry 29 }

ipxFramesReceivedPerSec OBJECT-TYPE
    SYNTAX     Gauge32
    MAX-ACCESS read-only
    STATUS     current
    DESCRIPTION
	    "Frames Received/sec is the rate at which data
	    frames are received by the computer.  This
	    counter only counts the frames (packets) that
	    carry data."
    ::= { nwLinkIPXEntry 30 }

ipxFramesRejectedPerSec OBJECT-TYPE
    SYNTAX     Gauge32
    MAX-ACCESS read-only
    STATUS     current
    DESCRIPTION
	    "Frames Rejected/sec is the rate at which data
	    frames are rejected.  This counter only counts
	    the frames (packets) that carry data."
    ::= { nwLinkIPXEntry 31 }

ipxFramesSentPerSec OBJECT-TYPE
    SYNTAX     Gauge32
    MAX-ACCESS read-only
    STATUS     current
    DESCRIPTION
	    "Frames Sent/sec is the rate at which data
	    frames are sent by the computer.  This counter
	    only counts the frames (packets) that carry
	    data."
    ::= { nwLinkIPXEntry 32 }

ipxFramesPerSec OBJECT-TYPE
    SYNTAX     Gauge32
    MAX-ACCESS read-only
    STATUS     current
    DESCRIPTION
	    "Frames/sec is the rate at which data frames
	    (or packets) are processed by the computer. 
	    This counter is the sum of data frames sent and
	    data frames received.  This counter only counts
	    those frames (packets) that carry data."
    ::= { nwLinkIPXEntry 33 }

ipxPacketsReceivedPerSec OBJECT-TYPE
    SYNTAX     Gauge32
    MAX-ACCESS read-only
    STATUS     current
    DESCRIPTION
	    "Packets Received/sec is the rate at which
	    packets are received by the computer.  This
	    counter counts all packets processed: control
	    as well as data packets."
    ::= { nwLinkIPXEntry 34 }

ipxPacketsSentPerSec OBJECT-TYPE
    SYNTAX     Gauge32
    MAX-ACCESS read-only
    STATUS     current
    DESCRIPTION
	    "Packets Sent/sec is the rate at which packets
	    are sent by the computer.  This counter counts
	    all packets sent by the computer, i.e. control
	    as well as data packets."
    ::= { nwLinkIPXEntry 35 }

ipxPacketsPerSec OBJECT-TYPE
    SYNTAX     Gauge32
    MAX-ACCESS read-only
    STATUS     current
    DESCRIPTION
	    "Packets/sec is the rate at which packets are
	    processed by the computer.	This count is the
	    sum of Packets Sent and Packets Received per
	    second.  This counter includes all packets
	    processed: control as well as data packets."
    ::= { nwLinkIPXEntry 36 }

ipxPiggybackAckQueuedPerSec OBJECT-TYPE
    SYNTAX     Gauge32
    MAX-ACCESS read-only
    STATUS     current
    DESCRIPTION
	    "Piggyback Ack Queued/sec is the rate at which
	    piggybacked acknowledgments are queued.
	    Piggyback acknowledgments are acknowledgments
	    to received packets that are to be included in
	    the next outgoing packet to the remote
	    computer."
    ::= { nwLinkIPXEntry 37 }

ipxPiggybackAckTimeouts OBJECT-TYPE
    SYNTAX     Gauge32
    MAX-ACCESS read-only
    STATUS     current
    DESCRIPTION
	    "Piggyback Ack Timeouts is the number of times
	    that a piggyback acknowledgment could not be
	    sent because there was no outgoing packet to
	    the remote on which to piggyback.  A piggyback
	    ack is an acknowledgment to a received packet
	    that is sent along in an outgoing data packet
	    to the remote computer.  If no outgoing packet
	    is sent within the timeout period, then an ack
	    packet is sent and this counter is
	    incremented."
    ::= { nwLinkIPXEntry 38 }

ipxWindowSendAverage OBJECT-TYPE
    SYNTAX     Gauge32
    MAX-ACCESS read-only
    STATUS     current
    DESCRIPTION
	    "Window Send Average is the running average
	    number of data bytes that were sent before
	    waiting for an acknowledgment from the remote
	    computer."
    ::= { nwLinkIPXEntry 39 }

ipxWindowSendMaximum OBJECT-TYPE
    SYNTAX     Gauge32
    MAX-ACCESS read-only
    STATUS     current
    DESCRIPTION
	    "Window Send Maximum is the maximum number of
	    bytes of data that will be sent before waiting
	    for an acknowledgment from the remote
	    computer."
    ::= { nwLinkIPXEntry 40 }

nwLinkNetBIOSTable OBJECT-TYPE
    SYNTAX     SEQUENCE OF NWLinkNetBIOSEntry
    MAX-ACCESS not-accessible
    STATUS     current
    DESCRIPTION
	    "The NWLink NetBIOS performance object consists
	    of counters that monitor IPX transport rates
	    and connections. This object only reports valid
	    data for counters that monitor datagrams and
	    packets; for frame-related counters, the object
	    tends to report zero values."
    ::= { advanced 57 }

nwLinkNetBIOSEntry OBJECT-TYPE
    SYNTAX     NWLinkNetBIOSEntry
    MAX-ACCESS not-accessible
    STATUS     current
    DESCRIPTION
	    "Performance information for one particular
	    instance of 'NWLink NetBIOS' object."
    INDEX      { netBIOSInstance }
    ::= { nwLinkNetBIOSTable 1 }

NWLinkNetBIOSEntry ::= SEQUENCE {
    netBIOSInstance InstanceName,
    netBIOSBytesTotalPerSec Gauge32,
    netBIOSConnectionSessionTimeouts Gauge32,
    netBIOSConnectionsCanceled Gauge32,
    netBIOSConnectionsNoRetries Gauge32,
    netBIOSConnectionsOpen Gauge32,
    netBIOSConnectionsWithRetries Gauge32,
    netBIOSDatagramBytesRcvdPerSec Gauge32,
    netBIOSDatagramBytesSentPerSec Gauge32,
    netBIOSDatagramBytesPerSec Gauge32,
    netBIOSDatagramsReceivedPerSec Gauge32,
    netBIOSDatagramsSentPerSec Gauge32,
    netBIOSDatagramsPerSec Gauge32,
    netBIOSDisconnectsLocal Gauge32,
    netBIOSDisconnectsRemote Gauge32,
    netBIOSExpirationsAck Gauge32,
    netBIOSExpirationsResponse Gauge32,
    netBIOSFailuresAdapter Gauge32,
    netBIOSFailuresLink Gauge32,
    netBIOSFailuresNoListen Gauge32,
    netBIOSFailuresNotFound Gauge32,
    netBIOSFailuresResourceLocal Gauge32,
    netBIOSFailuresResourceRemote Gauge32,
    netBIOSFrameBytesReSentPerSec Gauge32,
    netBIOSFrameBytesReceivedPerSec Gauge32,
    netBIOSFrameBytesRejectedPerSec Gauge32,
    netBIOSFrameBytesSentPerSec Gauge32,
    netBIOSFrameBytesPerSec Gauge32,
    netBIOSFramesReSentPerSec Gauge32,
    netBIOSFramesReceivedPerSec Gauge32,
    netBIOSFramesRejectedPerSec Gauge32,
    netBIOSFramesSentPerSec Gauge32,
    netBIOSFramesPerSec Gauge32,
    netBIOSPacketsReceivedPerSec Gauge32,
    netBIOSPacketsSentPerSec Gauge32,
    netBIOSPacketsPerSec Gauge32,
    netBIOSPiggybackAckQueuedPerSec Gauge32,
    netBIOSPiggybackAckTimeouts Gauge32,
    netBIOSWindowSendAverage Gauge32,
    netBIOSWindowSendMaximum Gauge32
}

netBIOSInstance OBJECT-TYPE
    SYNTAX     InstanceName
    MAX-ACCESS read-only
    STATUS     current
    DESCRIPTION
	    "Instance name."
    ::= { nwLinkNetBIOSEntry 1 }

netBIOSBytesTotalPerSec OBJECT-TYPE
    SYNTAX     Gauge32
    MAX-ACCESS read-only
    STATUS     current
    DESCRIPTION
	    "Bytes Total/sec is the sum of Frame Bytes/sec
	    and Datagram Bytes/sec.  This is the total rate
	    of bytes sent to or received from the network
	    by the protocol, but only counts the bytes in
	    frames (i.e., packets) which carry data."
    ::= { nwLinkNetBIOSEntry 2 }

netBIOSConnectionSessionTimeouts OBJECT-TYPE
    SYNTAX     Gauge32
    MAX-ACCESS read-only
    STATUS     current
    DESCRIPTION
	    "Connection Session Timeouts is the number of
	    connections that were dropped due to a session
	    timeout.  This number is an accumulator and
	    shows a running total."
    ::= { nwLinkNetBIOSEntry 3 }

netBIOSConnectionsCanceled OBJECT-TYPE
    SYNTAX     Gauge32
    MAX-ACCESS read-only
    STATUS     current
    DESCRIPTION
	    "Connections Canceled is the number of
	    connections that were canceled.  This number is
	    an accumulator and shows a running total."
    ::= { nwLinkNetBIOSEntry 4 }

netBIOSConnectionsNoRetries OBJECT-TYPE
    SYNTAX     Gauge32
    MAX-ACCESS read-only
    STATUS     current
    DESCRIPTION
	    "Connections No Retries is the total count of
	    connections that were successfully made on the
	    first try.	This number is an accumulator and
	    shows a running total."
    ::= { nwLinkNetBIOSEntry 5 }

netBIOSConnectionsOpen OBJECT-TYPE
    SYNTAX     Gauge32
    MAX-ACCESS read-only
    STATUS     current
    DESCRIPTION
	    "Connections Open is the number of connections
	    currently open for this protocol.  This counter
	    shows the current count only and does not
	    accumulate over time."
    ::= { nwLinkNetBIOSEntry 6 }

netBIOSConnectionsWithRetries OBJECT-TYPE
    SYNTAX     Gauge32
    MAX-ACCESS read-only
    STATUS     current
    DESCRIPTION
	    "Connections With Retries is the total count of
	    connections that were made after retrying the
	    attempt.  A retry occurs when the first
	    connection attempt failed.	This number is an
	    accumulator and shows a running total."
    ::= { nwLinkNetBIOSEntry 7 }

netBIOSDatagramBytesRcvdPerSec OBJECT-TYPE
    SYNTAX     Gauge32
    MAX-ACCESS read-only
    STATUS     current
    DESCRIPTION
	    "Datagram Bytes Received/sec is the rate at
	    which datagram bytes are received by the
	    computer.  A datagram is a connectionless
	    packet whose delivery to a remote computer is
	    not guaranteed."
    ::= { nwLinkNetBIOSEntry 8 }

netBIOSDatagramBytesSentPerSec OBJECT-TYPE
    SYNTAX     Gauge32
    MAX-ACCESS read-only
    STATUS     current
    DESCRIPTION
	    "Datagram Bytes Sent/sec is the rate at which
	    datagram bytes are sent from the computer.	A
	    datagram is a connectionless packet whose
	    delivery to a remote computer is not
	    guaranteed."
    ::= { nwLinkNetBIOSEntry 9 }

netBIOSDatagramBytesPerSec OBJECT-TYPE
    SYNTAX     Gauge32
    MAX-ACCESS read-only
    STATUS     current
    DESCRIPTION
	    "Datagram Bytes/sec is the rate at which
	    datagram bytes are processed by the computer. 
	    This counter is the sum of datagram bytes that
	    are sent as well as received.  A datagram is a
	    connectionless packet whose delivery to a
	    remote is not guaranteed."
    ::= { nwLinkNetBIOSEntry 10 }

netBIOSDatagramsReceivedPerSec OBJECT-TYPE
    SYNTAX     Gauge32
    MAX-ACCESS read-only
    STATUS     current
    DESCRIPTION
	    "Datagrams Received/sec is the rate at which
	    datagrams are received by the computer.  A
	    datagram is a connectionless packet whose
	    delivery to a remote computer is not
	    guaranteed."
    ::= { nwLinkNetBIOSEntry 11 }

netBIOSDatagramsSentPerSec OBJECT-TYPE
    SYNTAX     Gauge32
    MAX-ACCESS read-only
    STATUS     current
    DESCRIPTION
	    "Datagrams Sent/sec is the rate at which
	    datagrams are sent from the computer.  A
	    datagram is a connectionless packet whose
	    delivery to a remote computer is not
	    guaranteed."
    ::= { nwLinkNetBIOSEntry 12 }

netBIOSDatagramsPerSec OBJECT-TYPE
    SYNTAX     Gauge32
    MAX-ACCESS read-only
    STATUS     current
    DESCRIPTION
	    "Datagrams/sec is the rate at which datagrams
	    are processed by the computer.  This counter
	    displays the sum of datagrams sent and
	    datagrams received.  A datagram is a
	    connectionless packet whose delivery to a
	    remote is not guaranteed."
    ::= { nwLinkNetBIOSEntry 13 }

netBIOSDisconnectsLocal OBJECT-TYPE
    SYNTAX     Gauge32
    MAX-ACCESS read-only
    STATUS     current
    DESCRIPTION
	    "Disconnects Local is the number of session
	    disconnections that were initiated by the local
	    computer.  This number is an accumulator and
	    shows a running total."
    ::= { nwLinkNetBIOSEntry 14 }

netBIOSDisconnectsRemote OBJECT-TYPE
    SYNTAX     Gauge32
    MAX-ACCESS read-only
    STATUS     current
    DESCRIPTION
	    "Disconnects Remote is the number of session
	    disconnections that were initiated by the
	    remote computer.  This number is an accumulator
	    and shows a running total."
    ::= { nwLinkNetBIOSEntry 15 }

netBIOSExpirationsAck OBJECT-TYPE
    SYNTAX     Gauge32
    MAX-ACCESS read-only
    STATUS     current
    DESCRIPTION
	    "Expirations Ack is the count of T2 timer
	    expirations."
    ::= { nwLinkNetBIOSEntry 16 }

netBIOSExpirationsResponse OBJECT-TYPE
    SYNTAX     Gauge32
    MAX-ACCESS read-only
    STATUS     current
    DESCRIPTION
	    "Expirations Response is the count of T1 timer
	    expirations."
    ::= { nwLinkNetBIOSEntry 17 }

netBIOSFailuresAdapter OBJECT-TYPE
    SYNTAX     Gauge32
    MAX-ACCESS read-only
    STATUS     current
    DESCRIPTION
	    "Failures Adapter is the number of connections
	    that were dropped due to an adapter failure. 
	    This number is an accumulator and shows a
	    running total."
    ::= { nwLinkNetBIOSEntry 18 }

netBIOSFailuresLink OBJECT-TYPE
    SYNTAX     Gauge32
    MAX-ACCESS read-only
    STATUS     current
    DESCRIPTION
	    "Failures Link is the number of connections
	    that were dropped due to a link failure.  This
	    number is an accumulator and shows a running
	    total."
    ::= { nwLinkNetBIOSEntry 19 }

netBIOSFailuresNoListen OBJECT-TYPE
    SYNTAX     Gauge32
    MAX-ACCESS read-only
    STATUS     current
    DESCRIPTION
	    "Failures No Listen is the number of
	    connections that were rejected because the
	    remote computer was not listening for
	    connection requests."
    ::= { nwLinkNetBIOSEntry 20 }

netBIOSFailuresNotFound OBJECT-TYPE
    SYNTAX     Gauge32
    MAX-ACCESS read-only
    STATUS     current
    DESCRIPTION
	    "Failures Not Found is the number of connection
	    attempts that failed because the remote
	    computer could not be found.  This number is an
	    accumulator and shows a running total."
    ::= { nwLinkNetBIOSEntry 21 }

netBIOSFailuresResourceLocal OBJECT-TYPE
    SYNTAX     Gauge32
    MAX-ACCESS read-only
    STATUS     current
    DESCRIPTION
	    "Failures Resource Local is the number of
	    connections that failed because of resource
	    problems or shortages on the local computer. 
	    This number is an accumulator and shows a
	    running total."
    ::= { nwLinkNetBIOSEntry 22 }

netBIOSFailuresResourceRemote OBJECT-TYPE
    SYNTAX     Gauge32
    MAX-ACCESS read-only
    STATUS     current
    DESCRIPTION
	    "Failures Resource Remote is the number of
	    connections that failed because of resource
	    problems or shortages on the remote computer. 
	    This number is an accumulator and shows a
	    running total."
    ::= { nwLinkNetBIOSEntry 23 }

netBIOSFrameBytesReSentPerSec OBJECT-TYPE
    SYNTAX     Gauge32
    MAX-ACCESS read-only
    STATUS     current
    DESCRIPTION
	    "Frame Bytes Re-Sent/sec is the rate at which
	    data bytes are re-sent by the computer.  This
	    counter only counts the bytes in frames that
	    carry data."
    ::= { nwLinkNetBIOSEntry 24 }

netBIOSFrameBytesReceivedPerSec OBJECT-TYPE
    SYNTAX     Gauge32
    MAX-ACCESS read-only
    STATUS     current
    DESCRIPTION
	    "Frame Bytes Received/sec is the rate at which
	    data bytes are received by the computer.  This
	    counter only counts the frames (packets) that
	    carry data."
    ::= { nwLinkNetBIOSEntry 25 }

netBIOSFrameBytesRejectedPerSec OBJECT-TYPE
    SYNTAX     Gauge32
    MAX-ACCESS read-only
    STATUS     current
    DESCRIPTION
	    "Frame Bytes Rejected/sec is the rate at which
	    data bytes are rejected.  This counter only
	    counts the bytes in data frames (packets) that
	    carry data."
    ::= { nwLinkNetBIOSEntry 26 }

netBIOSFrameBytesSentPerSec OBJECT-TYPE
    SYNTAX     Gauge32
    MAX-ACCESS read-only
    STATUS     current
    DESCRIPTION
	    "Frame Bytes Sent/sec is the rate at which data
	    bytes are sent by the computer.  This counter
	    only counts the bytes in frames (packets) that
	    carry data."
    ::= { nwLinkNetBIOSEntry 27 }

netBIOSFrameBytesPerSec OBJECT-TYPE
    SYNTAX     Gauge32
    MAX-ACCESS read-only
    STATUS     current
    DESCRIPTION
	    "Frame Bytes/sec is the rate at which data
	    bytes are processed by the computer.  This
	    counter is the sum of data frame bytes sent and
	    received.  This counter only counts the byte in
	    frames (packets) that carry data."
    ::= { nwLinkNetBIOSEntry 28 }

netBIOSFramesReSentPerSec OBJECT-TYPE
    SYNTAX     Gauge32
    MAX-ACCESS read-only
    STATUS     current
    DESCRIPTION
	    "Frames Re-Sent/sec is the rate at which data
	    frames (packets) are re-sent by the computer. 
	    This counter only counts the frames or packets
	    that carry data."
    ::= { nwLinkNetBIOSEntry 29 }

netBIOSFramesReceivedPerSec OBJECT-TYPE
    SYNTAX     Gauge32
    MAX-ACCESS read-only
    STATUS     current
    DESCRIPTION
	    "Frames Received/sec is the rate at which data
	    frames are received by the computer.  This
	    counter only counts the frames (packets) that
	    carry data."
    ::= { nwLinkNetBIOSEntry 30 }

netBIOSFramesRejectedPerSec OBJECT-TYPE
    SYNTAX     Gauge32
    MAX-ACCESS read-only
    STATUS     current
    DESCRIPTION
	    "Frames Rejected/sec is the rate at which data
	    frames are rejected.  This counter only counts
	    the frames (packets) that carry data."
    ::= { nwLinkNetBIOSEntry 31 }

netBIOSFramesSentPerSec OBJECT-TYPE
    SYNTAX     Gauge32
    MAX-ACCESS read-only
    STATUS     current
    DESCRIPTION
	    "Frames Sent/sec is the rate at which data
	    frames are sent by the computer.  This counter
	    only counts the frames (packets) that carry
	    data."
    ::= { nwLinkNetBIOSEntry 32 }

netBIOSFramesPerSec OBJECT-TYPE
    SYNTAX     Gauge32
    MAX-ACCESS read-only
    STATUS     current
    DESCRIPTION
	    "Frames/sec is the rate at which data frames
	    (or packets) are processed by the computer. 
	    This counter is the sum of data frames sent and
	    data frames received.  This counter only counts
	    those frames (packets) that carry data."
    ::= { nwLinkNetBIOSEntry 33 }

netBIOSPacketsReceivedPerSec OBJECT-TYPE
    SYNTAX     Gauge32
    MAX-ACCESS read-only
    STATUS     current
    DESCRIPTION
	    "Packets Received/sec is the rate at which
	    packets are received by the computer.  This
	    counter counts all packets processed: control
	    as well as data packets."
    ::= { nwLinkNetBIOSEntry 34 }

netBIOSPacketsSentPerSec OBJECT-TYPE
    SYNTAX     Gauge32
    MAX-ACCESS read-only
    STATUS     current
    DESCRIPTION
	    "Packets Sent/sec is the rate at which packets
	    are sent by the computer.  This counter counts
	    all packets sent by the computer, i.e. control
	    as well as data packets."
    ::= { nwLinkNetBIOSEntry 35 }

netBIOSPacketsPerSec OBJECT-TYPE
    SYNTAX     Gauge32
    MAX-ACCESS read-only
    STATUS     current
    DESCRIPTION
	    "Packets/sec is the rate at which packets are
	    processed by the computer.	This count is the
	    sum of Packets Sent and Packets Received per
	    second.  This counter includes all packets
	    processed: control as well as data packets."
    ::= { nwLinkNetBIOSEntry 36 }

netBIOSPiggybackAckQueuedPerSec OBJECT-TYPE
    SYNTAX     Gauge32
    MAX-ACCESS read-only
    STATUS     current
    DESCRIPTION
	    "Piggyback Ack Queued/sec is the rate at which
	    piggybacked acknowledgments are queued.
	    Piggyback acknowledgments are acknowledgments
	    to received packets that are to be included in
	    the next outgoing packet to the remote
	    computer."
    ::= { nwLinkNetBIOSEntry 37 }

netBIOSPiggybackAckTimeouts OBJECT-TYPE
    SYNTAX     Gauge32
    MAX-ACCESS read-only
    STATUS     current
    DESCRIPTION
	    "Piggyback Ack Timeouts is the number of times
	    that a piggyback acknowledgment could not be
	    sent because there was no outgoing packet to
	    the remote on which to piggyback.  A piggyback
	    ack is an acknowledgment to a received packet
	    that is sent along in an outgoing data packet
	    to the remote computer.  If no outgoing packet
	    is sent within the timeout period, then an ack
	    packet is sent and this counter is
	    incremented."
    ::= { nwLinkNetBIOSEntry 38 }

netBIOSWindowSendAverage OBJECT-TYPE
    SYNTAX     Gauge32
    MAX-ACCESS read-only
    STATUS     current
    DESCRIPTION
	    "Window Send Average is the running average
	    number of data bytes that were sent before
	    waiting for an acknowledgment from the remote
	    computer."
    ::= { nwLinkNetBIOSEntry 39 }

netBIOSWindowSendMaximum OBJECT-TYPE
    SYNTAX     Gauge32
    MAX-ACCESS read-only
    STATUS     current
    DESCRIPTION
	    "Window Send Maximum is the maximum number of
	    bytes of data that will be sent before waiting
	    for an acknowledgment from the remote
	    computer."
    ::= { nwLinkNetBIOSEntry 40 }

nwLinkSPXTable OBJECT-TYPE
    SYNTAX     SEQUENCE OF NWLinkSPXEntry
    MAX-ACCESS not-accessible
    STATUS     current
    DESCRIPTION
	    "The NWLink SPX performance object consists of
	    counters that measure data transmission and
	    session connections for computers using the SPX
	    protocol. This object only reports valid data
	    for counters that monitor datagrams and
	    packets; for frame-related counters, the object
	    tends to report zero values."
    ::= { advanced 58 }

nwLinkSPXEntry OBJECT-TYPE
    SYNTAX     NWLinkSPXEntry
    MAX-ACCESS not-accessible
    STATUS     current
    DESCRIPTION
	    "Performance information for one particular
	    instance of 'NWLink SPX' object."
    INDEX      { spxInstance }
    ::= { nwLinkSPXTable 1 }

NWLinkSPXEntry ::= SEQUENCE {
    spxInstance InstanceName,
    spxBytesTotalPerSec Gauge32,
    spxConnectionSessionTimeouts Gauge32,
    spxConnectionsCanceled Gauge32,
    spxConnectionsNoRetries Gauge32,
    spxConnectionsOpen Gauge32,
    spxConnectionsWithRetries Gauge32,
    spxDatagramBytesReceivedPerSec Gauge32,
    spxDatagramBytesSentPerSec Gauge32,
    spxDatagramBytesPerSec Gauge32,
    spxDatagramsReceivedPerSec Gauge32,
    spxDatagramsSentPerSec Gauge32,
    spxDatagramsPerSec Gauge32,
    spxDisconnectsLocal Gauge32,
    spxDisconnectsRemote Gauge32,
    spxExpirationsAck Gauge32,
    spxExpirationsResponse Gauge32,
    spxFailuresAdapter Gauge32,
    spxFailuresLink Gauge32,
    spxFailuresNoListen Gauge32,
    spxFailuresNotFound Gauge32,
    spxFailuresResourceLocal Gauge32,
    spxFailuresResourceRemote Gauge32,
    spxFrameBytesReSentPerSec Gauge32,
    spxFrameBytesReceivedPerSec Gauge32,
    spxFrameBytesRejectedPerSec Gauge32,
    spxFrameBytesSentPerSec Gauge32,
    spxFrameBytesPerSec Gauge32,
    spxFramesReSentPerSec Gauge32,
    spxFramesReceivedPerSec Gauge32,
    spxFramesRejectedPerSec Gauge32,
    spxFramesSentPerSec Gauge32,
    spxFramesPerSec Gauge32,
    spxPacketsReceivedPerSec Gauge32,
    spxPacketsSentPerSec Gauge32,
    spxPacketsPerSec Gauge32,
    spxPiggybackAckQueuedPerSec Gauge32,
    spxPiggybackAckTimeouts Gauge32,
    spxWindowSendAverage Gauge32,
    spxWindowSendMaximum Gauge32
}

spxInstance OBJECT-TYPE
    SYNTAX     InstanceName
    MAX-ACCESS read-only
    STATUS     current
    DESCRIPTION
	    "Instance name."
    ::= { nwLinkSPXEntry 1 }

spxBytesTotalPerSec OBJECT-TYPE
    SYNTAX     Gauge32
    MAX-ACCESS read-only
    STATUS     current
    DESCRIPTION
	    "Bytes Total/sec is the sum of Frame Bytes/sec
	    and Datagram Bytes/sec.  This is the total rate
	    of bytes sent to or received from the network
	    by the protocol, but only counts the bytes in
	    frames (i.e., packets) which carry data."
    ::= { nwLinkSPXEntry 2 }

spxConnectionSessionTimeouts OBJECT-TYPE
    SYNTAX     Gauge32
    MAX-ACCESS read-only
    STATUS     current
    DESCRIPTION
	    "Connection Session Timeouts is the number of
	    connections that were dropped due to a session
	    timeout.  This number is an accumulator and
	    shows a running total."
    ::= { nwLinkSPXEntry 3 }

spxConnectionsCanceled OBJECT-TYPE
    SYNTAX     Gauge32
    MAX-ACCESS read-only
    STATUS     current
    DESCRIPTION
	    "Connections Canceled is the number of
	    connections that were canceled.  This number is
	    an accumulator and shows a running total."
    ::= { nwLinkSPXEntry 4 }

spxConnectionsNoRetries OBJECT-TYPE
    SYNTAX     Gauge32
    MAX-ACCESS read-only
    STATUS     current
    DESCRIPTION
	    "Connections No Retries is the total count of
	    connections that were successfully made on the
	    first try.	This number is an accumulator and
	    shows a running total."
    ::= { nwLinkSPXEntry 5 }

spxConnectionsOpen OBJECT-TYPE
    SYNTAX     Gauge32
    MAX-ACCESS read-only
    STATUS     current
    DESCRIPTION
	    "Connections Open is the number of connections
	    currently open for this protocol.  This counter
	    shows the current count only and does not
	    accumulate over time."
    ::= { nwLinkSPXEntry 6 }

spxConnectionsWithRetries OBJECT-TYPE
    SYNTAX     Gauge32
    MAX-ACCESS read-only
    STATUS     current
    DESCRIPTION
	    "Connections With Retries is the total count of
	    connections that were made after retrying the
	    attempt.  A retry occurs when the first
	    connection attempt failed.	This number is an
	    accumulator and shows a running total."
    ::= { nwLinkSPXEntry 7 }

spxDatagramBytesReceivedPerSec OBJECT-TYPE
    SYNTAX     Gauge32
    MAX-ACCESS read-only
    STATUS     current
    DESCRIPTION
	    "Datagram Bytes Received/sec is the rate at
	    which datagram bytes are received by the
	    computer.  A datagram is a connectionless
	    packet whose delivery to a remote computer is
	    not guaranteed."
    ::= { nwLinkSPXEntry 8 }

spxDatagramBytesSentPerSec OBJECT-TYPE
    SYNTAX     Gauge32
    MAX-ACCESS read-only
    STATUS     current
    DESCRIPTION
	    "Datagram Bytes Sent/sec is the rate at which
	    datagram bytes are sent from the computer.	A
	    datagram is a connectionless packet whose
	    delivery to a remote computer is not
	    guaranteed."
    ::= { nwLinkSPXEntry 9 }

spxDatagramBytesPerSec OBJECT-TYPE
    SYNTAX     Gauge32
    MAX-ACCESS read-only
    STATUS     current
    DESCRIPTION
	    "Datagram Bytes/sec is the rate at which
	    datagram bytes are processed by the computer. 
	    This counter is the sum of datagram bytes that
	    are sent as well as received.  A datagram is a
	    connectionless packet whose delivery to a
	    remote is not guaranteed."
    ::= { nwLinkSPXEntry 10 }

spxDatagramsReceivedPerSec OBJECT-TYPE
    SYNTAX     Gauge32
    MAX-ACCESS read-only
    STATUS     current
    DESCRIPTION
	    "Datagrams Received/sec is the rate at which
	    datagrams are received by the computer.  A
	    datagram is a connectionless packet whose
	    delivery to a remote computer is not
	    guaranteed."
    ::= { nwLinkSPXEntry 11 }

spxDatagramsSentPerSec OBJECT-TYPE
    SYNTAX     Gauge32
    MAX-ACCESS read-only
    STATUS     current
    DESCRIPTION
	    "Datagrams Sent/sec is the rate at which
	    datagrams are sent from the computer.  A
	    datagram is a connectionless packet whose
	    delivery to a remote computer is not
	    guaranteed."
    ::= { nwLinkSPXEntry 12 }

spxDatagramsPerSec OBJECT-TYPE
    SYNTAX     Gauge32
    MAX-ACCESS read-only
    STATUS     current
    DESCRIPTION
	    "Datagrams/sec is the rate at which datagrams
	    are processed by the computer.  This counter
	    displays the sum of datagrams sent and
	    datagrams received.  A datagram is a
	    connectionless packet whose delivery to a
	    remote is not guaranteed."
    ::= { nwLinkSPXEntry 13 }

spxDisconnectsLocal OBJECT-TYPE
    SYNTAX     Gauge32
    MAX-ACCESS read-only
    STATUS     current
    DESCRIPTION
	    "Disconnects Local is the number of session
	    disconnections that were initiated by the local
	    computer.  This number is an accumulator and
	    shows a running total."
    ::= { nwLinkSPXEntry 14 }

spxDisconnectsRemote OBJECT-TYPE
    SYNTAX     Gauge32
    MAX-ACCESS read-only
    STATUS     current
    DESCRIPTION
	    "Disconnects Remote is the number of session
	    disconnections that were initiated by the
	    remote computer.  This number is an accumulator
	    and shows a running total."
    ::= { nwLinkSPXEntry 15 }

spxExpirationsAck OBJECT-TYPE
    SYNTAX     Gauge32
    MAX-ACCESS read-only
    STATUS     current
    DESCRIPTION
	    "Expirations Ack is the count of T2 timer
	    expirations."
    ::= { nwLinkSPXEntry 16 }

spxExpirationsResponse OBJECT-TYPE
    SYNTAX     Gauge32
    MAX-ACCESS read-only
    STATUS     current
    DESCRIPTION
	    "Expirations Response is the count of T1 timer
	    expirations."
    ::= { nwLinkSPXEntry 17 }

spxFailuresAdapter OBJECT-TYPE
    SYNTAX     Gauge32
    MAX-ACCESS read-only
    STATUS     current
    DESCRIPTION
	    "Failures Adapter is the number of connections
	    that were dropped due to an adapter failure. 
	    This number is an accumulator and shows a
	    running total."
    ::= { nwLinkSPXEntry 18 }

spxFailuresLink OBJECT-TYPE
    SYNTAX     Gauge32
    MAX-ACCESS read-only
    STATUS     current
    DESCRIPTION
	    "Failures Link is the number of connections
	    that were dropped due to a link failure.  This
	    number is an accumulator and shows a running
	    total."
    ::= { nwLinkSPXEntry 19 }

spxFailuresNoListen OBJECT-TYPE
    SYNTAX     Gauge32
    MAX-ACCESS read-only
    STATUS     current
    DESCRIPTION
	    "Failures No Listen is the number of
	    connections that were rejected because the
	    remote computer was not listening for
	    connection requests."
    ::= { nwLinkSPXEntry 20 }

spxFailuresNotFound OBJECT-TYPE
    SYNTAX     Gauge32
    MAX-ACCESS read-only
    STATUS     current
    DESCRIPTION
	    "Failures Not Found is the number of connection
	    attempts that failed because the remote
	    computer could not be found.  This number is an
	    accumulator and shows a running total."
    ::= { nwLinkSPXEntry 21 }

spxFailuresResourceLocal OBJECT-TYPE
    SYNTAX     Gauge32
    MAX-ACCESS read-only
    STATUS     current
    DESCRIPTION
	    "Failures Resource Local is the number of
	    connections that failed because of resource
	    problems or shortages on the local computer. 
	    This number is an accumulator and shows a
	    running total."
    ::= { nwLinkSPXEntry 22 }

spxFailuresResourceRemote OBJECT-TYPE
    SYNTAX     Gauge32
    MAX-ACCESS read-only
    STATUS     current
    DESCRIPTION
	    "Failures Resource Remote is the number of
	    connections that failed because of resource
	    problems or shortages on the remote computer. 
	    This number is an accumulator and shows a
	    running total."
    ::= { nwLinkSPXEntry 23 }

spxFrameBytesReSentPerSec OBJECT-TYPE
    SYNTAX     Gauge32
    MAX-ACCESS read-only
    STATUS     current
    DESCRIPTION
	    "Frame Bytes Re-Sent/sec is the rate at which
	    data bytes are re-sent by the computer.  This
	    counter only counts the bytes in frames that
	    carry data."
    ::= { nwLinkSPXEntry 24 }

spxFrameBytesReceivedPerSec OBJECT-TYPE
    SYNTAX     Gauge32
    MAX-ACCESS read-only
    STATUS     current
    DESCRIPTION
	    "Frame Bytes Received/sec is the rate at which
	    data bytes are received by the computer.  This
	    counter only counts the frames (packets) that
	    carry data."
    ::= { nwLinkSPXEntry 25 }

spxFrameBytesRejectedPerSec OBJECT-TYPE
    SYNTAX     Gauge32
    MAX-ACCESS read-only
    STATUS     current
    DESCRIPTION
	    "Frame Bytes Rejected/sec is the rate at which
	    data bytes are rejected.  This counter only
	    counts the bytes in data frames (packets) that
	    carry data."
    ::= { nwLinkSPXEntry 26 }

spxFrameBytesSentPerSec OBJECT-TYPE
    SYNTAX     Gauge32
    MAX-ACCESS read-only
    STATUS     current
    DESCRIPTION
	    "Frame Bytes Sent/sec is the rate at which data
	    bytes are sent by the computer.  This counter
	    only counts the bytes in frames (packets) that
	    carry data."
    ::= { nwLinkSPXEntry 27 }

spxFrameBytesPerSec OBJECT-TYPE
    SYNTAX     Gauge32
    MAX-ACCESS read-only
    STATUS     current
    DESCRIPTION
	    "Frame Bytes/sec is the rate at which data
	    bytes are processed by the computer.  This
	    counter is the sum of data frame bytes sent and
	    received.  This counter only counts the byte in
	    frames (packets) that carry data."
    ::= { nwLinkSPXEntry 28 }

spxFramesReSentPerSec OBJECT-TYPE
    SYNTAX     Gauge32
    MAX-ACCESS read-only
    STATUS     current
    DESCRIPTION
	    "Frames Re-Sent/sec is the rate at which data
	    frames (packets) are re-sent by the computer. 
	    This counter only counts the frames or packets
	    that carry data."
    ::= { nwLinkSPXEntry 29 }

spxFramesReceivedPerSec OBJECT-TYPE
    SYNTAX     Gauge32
    MAX-ACCESS read-only
    STATUS     current
    DESCRIPTION
	    "Frames Received/sec is the rate at which data
	    frames are received by the computer.  This
	    counter only counts the frames (packets) that
	    carry data."
    ::= { nwLinkSPXEntry 30 }

spxFramesRejectedPerSec OBJECT-TYPE
    SYNTAX     Gauge32
    MAX-ACCESS read-only
    STATUS     current
    DESCRIPTION
	    "Frames Rejected/sec is the rate at which data
	    frames are rejected.  This counter only counts
	    the frames (packets) that carry data."
    ::= { nwLinkSPXEntry 31 }

spxFramesSentPerSec OBJECT-TYPE
    SYNTAX     Gauge32
    MAX-ACCESS read-only
    STATUS     current
    DESCRIPTION
	    "Frames Sent/sec is the rate at which data
	    frames are sent by the computer.  This counter
	    only counts the frames (packets) that carry
	    data."
    ::= { nwLinkSPXEntry 32 }

spxFramesPerSec OBJECT-TYPE
    SYNTAX     Gauge32
    MAX-ACCESS read-only
    STATUS     current
    DESCRIPTION
	    "Frames/sec is the rate at which data frames
	    (or packets) are processed by the computer. 
	    This counter is the sum of data frames sent and
	    data frames received.  This counter only counts
	    those frames (packets) that carry data."
    ::= { nwLinkSPXEntry 33 }

spxPacketsReceivedPerSec OBJECT-TYPE
    SYNTAX     Gauge32
    MAX-ACCESS read-only
    STATUS     current
    DESCRIPTION
	    "Packets Received/sec is the rate at which
	    packets are received by the computer.  This
	    counter counts all packets processed: control
	    as well as data packets."
    ::= { nwLinkSPXEntry 34 }

spxPacketsSentPerSec OBJECT-TYPE
    SYNTAX     Gauge32
    MAX-ACCESS read-only
    STATUS     current
    DESCRIPTION
	    "Packets Sent/sec is the rate at which packets
	    are sent by the computer.  This counter counts
	    all packets sent by the computer, i.e. control
	    as well as data packets."
    ::= { nwLinkSPXEntry 35 }

spxPacketsPerSec OBJECT-TYPE
    SYNTAX     Gauge32
    MAX-ACCESS read-only
    STATUS     current
    DESCRIPTION
	    "Packets/sec is the rate at which packets are
	    processed by the computer.	This count is the
	    sum of Packets Sent and Packets Received per
	    second.  This counter includes all packets
	    processed: control as well as data packets."
    ::= { nwLinkSPXEntry 36 }

spxPiggybackAckQueuedPerSec OBJECT-TYPE
    SYNTAX     Gauge32
    MAX-ACCESS read-only
    STATUS     current
    DESCRIPTION
	    "Piggyback Ack Queued/sec is the rate at which
	    piggybacked acknowledgments are queued.
	    Piggyback acknowledgments are acknowledgments
	    to received packets that are to be included in
	    the next outgoing packet to the remote
	    computer."
    ::= { nwLinkSPXEntry 37 }

spxPiggybackAckTimeouts OBJECT-TYPE
    SYNTAX     Gauge32
    MAX-ACCESS read-only
    STATUS     current
    DESCRIPTION
	    "Piggyback Ack Timeouts is the number of times
	    that a piggyback acknowledgment could not be
	    sent because there was no outgoing packet to
	    the remote on which to piggyback.  A piggyback
	    ack is an acknowledgment to a received packet
	    that is sent along in an outgoing data packet
	    to the remote computer.  If no outgoing packet
	    is sent within the timeout period, then an ack
	    packet is sent and this counter is
	    incremented."
    ::= { nwLinkSPXEntry 38 }

spxWindowSendAverage OBJECT-TYPE
    SYNTAX     Gauge32
    MAX-ACCESS read-only
    STATUS     current
    DESCRIPTION
	    "Window Send Average is the running average
	    number of data bytes that were sent before
	    waiting for an acknowledgment from the remote
	    computer."
    ::= { nwLinkSPXEntry 39 }

spxWindowSendMaximum OBJECT-TYPE
    SYNTAX     Gauge32
    MAX-ACCESS read-only
    STATUS     current
    DESCRIPTION
	    "Window Send Maximum is the maximum number of
	    bytes of data that will be sent before waiting
	    for an acknowledgment from the remote
	    computer."
    ::= { nwLinkSPXEntry 40 }

objects OBJECT-IDENTITY
    STATUS     current
    DESCRIPTION
	    "The Objects performance object consists of
	    counters that monitor logical objects in the
	    system, such as processes, threads, mutexes,
	    and semaphores. This information can be used to
	    detect the unnecessary consumption of computer
	    resources. Each object requires memory to store
	    basic information about the object."
    ::= { advanced 59 }

objectsEvents OBJECT-TYPE
    SYNTAX     Gauge32
    MAX-ACCESS read-only
    STATUS     current
    DESCRIPTION
	    "Events is the number of events in the computer
	    at the time of data collection.  Notice that
	    this is an instantaneous count, not an average
	    over the time interval.  An event is used when
	    two or more threads wish to synchronize
	    execution."
    ::= { objects 1 }

objectsMutexes OBJECT-TYPE
    SYNTAX     Gauge32
    MAX-ACCESS read-only
    STATUS     current
    DESCRIPTION
	    "Mutexes counts the number of mutexes in the
	    computer at the time of data collection.  This
	    is an instantaneous count, not an average over
	    the time interval.	Mutexes are used by threads
	    to assure only one thread is executing some
	    section of code."
    ::= { objects 2 }

objectsProcesses OBJECT-TYPE
    SYNTAX     Gauge32
    MAX-ACCESS read-only
    STATUS     current
    DESCRIPTION
	    "Processes is the number of processes in the
	    computer at the time of data collection. 
	    Notice that this is an instantaneous count, not
	    an average over the time interval.	Each
	    process represents the running of a program."
    ::= { objects 3 }

objectsSections OBJECT-TYPE
    SYNTAX     Gauge32
    MAX-ACCESS read-only
    STATUS     current
    DESCRIPTION
	    "Sections is the number of sections in the
	    computer at the time of data collection. 
	    Notice that this is an instantaneous count, not
	    an average over the time interval.	A section
	    is a portion of virtual memory created by a
	    process for storing data.  A process can share
	    sections with other processes."
    ::= { objects 4 }

objectsSemaphores OBJECT-TYPE
    SYNTAX     Gauge32
    MAX-ACCESS read-only
    STATUS     current
    DESCRIPTION
	    "Semaphores is the number of semaphores in the
	    computer at the time of data collection. 
	    Notice that this is an instantaneous count, not
	    an average over the time interval.	Threads use
	    semaphores to obtain exclusive access to data
	    structures that they share with other threads."
    ::= { objects 5 }

objectsThreads OBJECT-TYPE
    SYNTAX     Gauge32
    MAX-ACCESS read-only
    STATUS     current
    DESCRIPTION
	    "Threads is the number of threads in the
	    computer at the time of data collection. 
	    Notice that this is an instantaneous count, not
	    an average over the time interval.	A thread is
	    the basic executable entity that can execute
	    instructions in a processor."
    ::= { objects 6 }

pagingFileTable OBJECT-TYPE
    SYNTAX     SEQUENCE OF PagingFileEntry
    MAX-ACCESS not-accessible
    STATUS     current
    DESCRIPTION
	    "The Paging File performance object consists of
	    counters that monitor the paging file(s) on the
	    computer. The paging file is a reserved space
	    on disk that backs up committed physical memory
	    on the computer."
    ::= { advanced 60 }

pagingFileEntry OBJECT-TYPE
    SYNTAX     PagingFileEntry
    MAX-ACCESS not-accessible
    STATUS     current
    DESCRIPTION
	    "Performance information for one particular
	    instance of 'Paging File' object."
    INDEX      { pagingFileInstance }
    ::= { pagingFileTable 1 }

PagingFileEntry ::= SEQUENCE {
    pagingFileInstance InstanceName,
    pagingFilePercentUsage Gauge32,
    pagingFilePercentUsagePeak Gauge32
}

pagingFileInstance OBJECT-TYPE
    SYNTAX     InstanceName
    MAX-ACCESS read-only
    STATUS     current
    DESCRIPTION
	    "Instance name."
    ::= { pagingFileEntry 1 }

pagingFilePercentUsage OBJECT-TYPE
    SYNTAX     Gauge32
    MAX-ACCESS read-only
    STATUS     current
    DESCRIPTION
	    "The amount of the Page File instance in use in
	    percent.  See also Process: Page File Bytes."
    ::= { pagingFileEntry 2 }

pagingFilePercentUsagePeak OBJECT-TYPE
    SYNTAX     Gauge32
    MAX-ACCESS read-only
    STATUS     current
    DESCRIPTION
	    "The peak usage of the Page File instance in
	    percent.  See also Process: Page File Bytes
	    Peak."
    ::= { pagingFileEntry 3 }

physicalDiskTable OBJECT-TYPE
    SYNTAX     SEQUENCE OF PhysicalDiskEntry
    MAX-ACCESS not-accessible
    STATUS     current
    DESCRIPTION
	    "The PhysicalDisk performance object consists
	    of counters that monitor hard or fixed disk
	    drives on a computer. Disks are used to store
	    file, program, and paging data, are read to
	    retrieve these items, and are written to record
	    changes to them. The values of physical disk
	    counters are sums of the values of the logical
	    disks (or partitions) into which they are
	    divided."
    ::= { advanced 61 }

physicalDiskEntry OBJECT-TYPE
    SYNTAX     PhysicalDiskEntry
    MAX-ACCESS not-accessible
    STATUS     current
    DESCRIPTION
	    "Performance information for one particular
	    instance of 'PhysicalDisk' object."
    INDEX      { pDiskInstance }
    ::= { physicalDiskTable 1 }

PhysicalDiskEntry ::= SEQUENCE {
    pDiskInstance InstanceName,
    pDiskPercentDiskReadTime Gauge32,
    pDiskPercentDiskTime Gauge32,
    pDiskPercentDiskWriteTime Gauge32,
    pDiskPercentIdleTime Gauge32,
    pDiskAvgDiskBytesPerRead Gauge32,
    pDiskAvgDiskBytesPerTransfer Gauge32,
    pDiskAvgDiskBytesPerWrite Gauge32,
    pDiskAvgDiskQueueLength Gauge32,
    pDiskAvgDiskReadQueueLength Gauge32,
    pDiskAvgDiskWriteQueueLength Gauge32,
    pDiskAvgDiskSecPerRead Gauge32,
    pDiskAvgDiskSecPerTransfer Gauge32,
    pDiskAvgDiskSecPerWrite Gauge32,
    pDiskCurrentDiskQueueLength Gauge32,
    pDiskDiskBytesPerSec Gauge32,
    pDiskDiskReadBytesPerSec Gauge32,
    pDiskDiskReadsPerSec Gauge32,
    pDiskDiskTransfersPerSec Gauge32,
    pDiskDiskWriteBytesPerSec Gauge32,
    pDiskDiskWritesPerSec Gauge32,
    pDiskSplitIOPerSec Gauge32
}

pDiskInstance OBJECT-TYPE
    SYNTAX     InstanceName
    MAX-ACCESS read-only
    STATUS     current
    DESCRIPTION
	    "Instance name."
    ::= { physicalDiskEntry 1 }

pDiskPercentDiskReadTime OBJECT-TYPE
    SYNTAX     Gauge32
    MAX-ACCESS read-only
    STATUS     current
    DESCRIPTION
	    "% Disk Read Time is the percentage of elapsed
	    time that the selected disk drive is busy
	    servicing read requests."
    ::= { physicalDiskEntry 2 }

pDiskPercentDiskTime OBJECT-TYPE
    SYNTAX     Gauge32
    MAX-ACCESS read-only
    STATUS     current
    DESCRIPTION
	    "% Disk Time is the percentage of elapsed time
	    that the selected disk drive is busy servicing
	    read or write requests."
    ::= { physicalDiskEntry 3 }

pDiskPercentDiskWriteTime OBJECT-TYPE
    SYNTAX     Gauge32
    MAX-ACCESS read-only
    STATUS     current
    DESCRIPTION
	    "% Disk Write Time is the percentage of elapsed
	    time that the selected disk drive is busy
	    servicing write requests."
    ::= { physicalDiskEntry 4 }

pDiskPercentIdleTime OBJECT-TYPE
    SYNTAX     Gauge32
    MAX-ACCESS read-only
    STATUS     current
    DESCRIPTION
	    "% Idle Time reports the percentage of time
	    during the sample interval that the disk was
	    idle."
    ::= { physicalDiskEntry 5 }

pDiskAvgDiskBytesPerRead OBJECT-TYPE
    SYNTAX     Gauge32
    MAX-ACCESS read-only
    STATUS     current
    DESCRIPTION
	    "Avg. Disk Bytes/Read is the average number of
	    bytes transferred from the disk during read
	    operations."
    ::= { physicalDiskEntry 6 }

pDiskAvgDiskBytesPerTransfer OBJECT-TYPE
    SYNTAX     Gauge32
    MAX-ACCESS read-only
    STATUS     current
    DESCRIPTION
	    "Avg. Disk Bytes/Transfer is the average number
	    of bytes transferred to or from the disk during
	    write or read operations."
    ::= { physicalDiskEntry 7 }

pDiskAvgDiskBytesPerWrite OBJECT-TYPE
    SYNTAX     Gauge32
    MAX-ACCESS read-only
    STATUS     current
    DESCRIPTION
	    "Avg. Disk Bytes/Write is the average number of
	    bytes transferred to the disk during write
	    operations."
    ::= { physicalDiskEntry 8 }

pDiskAvgDiskQueueLength OBJECT-TYPE
    SYNTAX     Gauge32
    MAX-ACCESS read-only
    STATUS     current
    DESCRIPTION
	    "Avg. Disk Queue Length is the average number
	    of both read and write requests that were
	    queued for the selected disk during the sample
	    interval."
    ::= { physicalDiskEntry 9 }

pDiskAvgDiskReadQueueLength OBJECT-TYPE
    SYNTAX     Gauge32
    MAX-ACCESS read-only
    STATUS     current
    DESCRIPTION
	    "Avg. Disk Read Queue Length is the average
	    number of read requests that were queued for
	    the selected disk during the sample interval."
    ::= { physicalDiskEntry 10 }

pDiskAvgDiskWriteQueueLength OBJECT-TYPE
    SYNTAX     Gauge32
    MAX-ACCESS read-only
    STATUS     current
    DESCRIPTION
	    "Avg. Disk Write Queue Length is the average
	    number of write requests that were queued for
	    the selected disk during the sample interval."
    ::= { physicalDiskEntry 11 }

pDiskAvgDiskSecPerRead OBJECT-TYPE
    SYNTAX     Gauge32
    MAX-ACCESS read-only
    STATUS     current
    DESCRIPTION
	    "Avg. Disk sec/Read is the average time in
	    seconds of a read of data from the disk."
    ::= { physicalDiskEntry 12 }

pDiskAvgDiskSecPerTransfer OBJECT-TYPE
    SYNTAX     Gauge32
    MAX-ACCESS read-only
    STATUS     current
    DESCRIPTION
	    "Avg. Disk sec/Transfer is the time in seconds
	    of the average disk transfer."
    ::= { physicalDiskEntry 13 }

pDiskAvgDiskSecPerWrite OBJECT-TYPE
    SYNTAX     Gauge32
    MAX-ACCESS read-only
    STATUS     current
    DESCRIPTION
	    "Avg. Disk sec/Write is the average time in
	    seconds of a write of data to the disk."
    ::= { physicalDiskEntry 14 }

pDiskCurrentDiskQueueLength OBJECT-TYPE
    SYNTAX     Gauge32
    MAX-ACCESS read-only
    STATUS     current
    DESCRIPTION
	    "Current Disk Queue Length is the number of
	    requests outstanding on the disk at the time
	    the performance data is collected.	It includes
	    requests in service at the time of the
	    snapshot.  This is an instantaneous length, not
	    an average over the time interval. 
	    Multi-spindle disk devices can have multiple
	    requests active at one time, but other
	    concurrent requests are awaiting service.  This
	    counter might reflect a transitory high or low
	    queue length, but if there is a sustained load
	    on the disk drive, it is likely that this will
	    be consistently high.  Requests are
	    experiencing delays proportional to the length
	    of this queue minus the number of spindles on
	    the disks.	This difference should average less
	    than 2 for good performance."
    ::= { physicalDiskEntry 15 }

pDiskDiskBytesPerSec OBJECT-TYPE
    SYNTAX     Gauge32
    MAX-ACCESS read-only
    STATUS     current
    DESCRIPTION
	    "Disk Bytes/sec is the rate bytes are
	    transferred to or from the disk during write or
	    read operations."
    ::= { physicalDiskEntry 16 }

pDiskDiskReadBytesPerSec OBJECT-TYPE
    SYNTAX     Gauge32
    MAX-ACCESS read-only
    STATUS     current
    DESCRIPTION
	    "Disk Read Bytes/sec is the rate bytes are
	    transferred from the disk during read
	    operations."
    ::= { physicalDiskEntry 17 }

pDiskDiskReadsPerSec OBJECT-TYPE
    SYNTAX     Gauge32
    MAX-ACCESS read-only
    STATUS     current
    DESCRIPTION
	    "Disk Reads/sec is the rate of read operations
	    on the disk."
    ::= { physicalDiskEntry 18 }

pDiskDiskTransfersPerSec OBJECT-TYPE
    SYNTAX     Gauge32
    MAX-ACCESS read-only
    STATUS     current
    DESCRIPTION
	    "Disk Transfers/sec is the rate of read and
	    write operations on the disk."
    ::= { physicalDiskEntry 19 }

pDiskDiskWriteBytesPerSec OBJECT-TYPE
    SYNTAX     Gauge32
    MAX-ACCESS read-only
    STATUS     current
    DESCRIPTION
	    "Disk Write Bytes is rate bytes are transferred
	    to the disk during write operations."
    ::= { physicalDiskEntry 20 }

pDiskDiskWritesPerSec OBJECT-TYPE
    SYNTAX     Gauge32
    MAX-ACCESS read-only
    STATUS     current
    DESCRIPTION
	    "Disk Writes/sec is the rate of write
	    operations on the disk."
    ::= { physicalDiskEntry 21 }

pDiskSplitIOPerSec OBJECT-TYPE
    SYNTAX     Gauge32
    MAX-ACCESS read-only
    STATUS     current
    DESCRIPTION
	    "Split IO/Sec reports the rate that I/Os to the
	    disk were split into multiple I/Os.  A split
	    I/O may result from requesting data in a size
	    that is too large to fit into a single I/O or
	    that the disk is fragmented."
    ::= { physicalDiskEntry 22 }

pop3Service OBJECT IDENTIFIER
    ::= { advanced 62 }

pop3SvcBytesReceivePerSec OBJECT-TYPE
    SYNTAX     Gauge32
    MAX-ACCESS read-only
    STATUS     current
    DESCRIPTION
	    "Bytes received per second"
    ::= { pop3Service 1 }

pop3SvcBytesTransmittedPerSec OBJECT-TYPE
    SYNTAX     Gauge32
    MAX-ACCESS read-only
    STATUS     current
    DESCRIPTION
	    "Bytes transmitted per second"
    ::= { pop3Service 2 }

pop3SvcConnectionsPerSec OBJECT-TYPE
    SYNTAX     Gauge32
    MAX-ACCESS read-only
    STATUS     current
    DESCRIPTION
	    "Number of connections per second"
    ::= { pop3Service 3 }

pop3SvcFreeThreads OBJECT-TYPE
    SYNTAX     Gauge32
    MAX-ACCESS read-only
    STATUS     current
    DESCRIPTION
	    "Number of free threads"
    ::= { pop3Service 4 }

pop3SvcMailboxesInAuthState OBJECT-TYPE
    SYNTAX     Gauge32
    MAX-ACCESS read-only
    STATUS     current
    DESCRIPTION
	    "Number of connections in Authentication state"
    ::= { pop3Service 5 }

pop3SvcMailboxesInTranState OBJECT-TYPE
    SYNTAX     Gauge32
    MAX-ACCESS read-only
    STATUS     current
    DESCRIPTION
	    "Number of connections in Transaction state"
    ::= { pop3Service 6 }

pop3SvcMessagesDeliveredPerSec OBJECT-TYPE
    SYNTAX     Gauge32
    MAX-ACCESS read-only
    STATUS     current
    DESCRIPTION
	    "Number of messages delivered per second"
    ::= { pop3Service 7 }

pop3SvcSocketsInUse OBJECT-TYPE
    SYNTAX     Gauge32
    MAX-ACCESS read-only
    STATUS     current
    DESCRIPTION
	    "Number of current active POP3 connections"
    ::= { pop3Service 8 }

pop3SvcTotalConnections OBJECT-TYPE
    SYNTAX     Gauge32
    MAX-ACCESS read-only
    STATUS     current
    DESCRIPTION
	    "Total connections since the service starts."
    ::= { pop3Service 9 }

pop3SvcTotalFailedLogons OBJECT-TYPE
    SYNTAX     Gauge32
    MAX-ACCESS read-only
    STATUS     current
    DESCRIPTION
	    "Number of failed logons since service starts"
    ::= { pop3Service 10 }

pop3SvcTotalBytesReceived OBJECT-TYPE
    SYNTAX     Gauge32
    MAX-ACCESS read-only
    STATUS     current
    DESCRIPTION
	    "Total bytes of POP3 request received"
    ::= { pop3Service 11 }

pop3SvcTotalBytesTransmitted OBJECT-TYPE
    SYNTAX     Gauge32
    MAX-ACCESS read-only
    STATUS     current
    DESCRIPTION
	    "Bytes of POP3 messages transmitted"
    ::= { pop3Service 12 }

pop3SvcTotalMessagesDelivered OBJECT-TYPE
    SYNTAX     Gauge32
    MAX-ACCESS read-only
    STATUS     current
    DESCRIPTION
	    "Total number of messages delivered since
	    service starts"
    ::= { pop3Service 13 }

printQueueTable OBJECT-TYPE
    SYNTAX     SEQUENCE OF PrintQueueEntry
    MAX-ACCESS not-accessible
    STATUS     current
    DESCRIPTION
	    "Windows 2000 printing features provide the
	    Print Queue Object performance object for
	    tracking activity in the server print queue.
	    Its counters are reset when either the print
	    server or the spooler service is restarted."
    ::= { advanced 63 }

printQueueEntry OBJECT-TYPE
    SYNTAX     PrintQueueEntry
    MAX-ACCESS not-accessible
    STATUS     current
    DESCRIPTION
	    "Performance information for one particular
	    instance of 'Print Queue' object."
    INDEX      { printQueueInstance }
    ::= { printQueueTable 1 }

PrintQueueEntry ::= SEQUENCE {
    printQueueInstance InstanceName,
    printQueueAddNetworkPrinterCalls Gauge32,
    printQueueBytesPrintedPerSec Gauge32,
    printQueueEnumNetworkPrinterCall Gauge32,
    printQueueJobErrors Gauge32,
    printQueueJobs Gauge32,
    printQueueJobsSpooling Gauge32,
    printQueueMaxJobsSpooling Gauge32,
    printQueueMaxReferences Gauge32,
    printQueueNotReadyErrors Gauge32,
    printQueueOutOfPaperErrors Gauge32,
    printQueueReferences Gauge32,
    printQueueTotalJobsPrinted Gauge32,
    printQueueTotalPagesPrinted Gauge32
}

printQueueInstance OBJECT-TYPE
    SYNTAX     InstanceName
    MAX-ACCESS read-only
    STATUS     current
    DESCRIPTION
	    "Instance name."
    ::= { printQueueEntry 1 }

printQueueAddNetworkPrinterCalls OBJECT-TYPE
    SYNTAX     Gauge32
    MAX-ACCESS read-only
    STATUS     current
    DESCRIPTION
	    "Total number of calls from other print servers
	    to add shared network printers to this server
	    since last restart."
    ::= { printQueueEntry 2 }

printQueueBytesPrintedPerSec OBJECT-TYPE
    SYNTAX     Gauge32
    MAX-ACCESS read-only
    STATUS     current
    DESCRIPTION
	    "Number of bytes per second printed on a print
	    queue."
    ::= { printQueueEntry 3 }

printQueueEnumNetworkPrinterCall OBJECT-TYPE
    SYNTAX     Gauge32
    MAX-ACCESS read-only
    STATUS     current
    DESCRIPTION
	    "Total number of calls from browse clients to
	    this print server to request network browse
	    lists since last restart."
    ::= { printQueueEntry 4 }

printQueueJobErrors OBJECT-TYPE
    SYNTAX     Gauge32
    MAX-ACCESS read-only
    STATUS     current
    DESCRIPTION
	    "Total number of job errors in a print queue
	    since last restart."
    ::= { printQueueEntry 5 }

printQueueJobs OBJECT-TYPE
    SYNTAX     Gauge32
    MAX-ACCESS read-only
    STATUS     current
    DESCRIPTION
	    "Current number of jobs in a print queue."
    ::= { printQueueEntry 6 }

printQueueJobsSpooling OBJECT-TYPE
    SYNTAX     Gauge32
    MAX-ACCESS read-only
    STATUS     current
    DESCRIPTION
	    "Current number of spooling jobs in a print
	    queue."
    ::= { printQueueEntry 7 }

printQueueMaxJobsSpooling OBJECT-TYPE
    SYNTAX     Gauge32
    MAX-ACCESS read-only
    STATUS     current
    DESCRIPTION
	    "Maximum number of spooling jobs in a print
	    queue since last restart."
    ::= { printQueueEntry 8 }

printQueueMaxReferences OBJECT-TYPE
    SYNTAX     Gauge32
    MAX-ACCESS read-only
    STATUS     current
    DESCRIPTION
	    "Peak number of references (open handles) to
	    this printer."
    ::= { printQueueEntry 9 }

printQueueNotReadyErrors OBJECT-TYPE
    SYNTAX     Gauge32
    MAX-ACCESS read-only
    STATUS     current
    DESCRIPTION
	    "Total number of printer not ready errors in a
	    print queue since the last restart."
    ::= { printQueueEntry 10 }

printQueueOutOfPaperErrors OBJECT-TYPE
    SYNTAX     Gauge32
    MAX-ACCESS read-only
    STATUS     current
    DESCRIPTION
	    "Total number of out of paper errors in a print
	    queue since the last restart."
    ::= { printQueueEntry 11 }

printQueueReferences OBJECT-TYPE
    SYNTAX     Gauge32
    MAX-ACCESS read-only
    STATUS     current
    DESCRIPTION
	    "Current number of references (open handles) to
	    this printer."
    ::= { printQueueEntry 12 }

printQueueTotalJobsPrinted OBJECT-TYPE
    SYNTAX     Gauge32
    MAX-ACCESS read-only
    STATUS     current
    DESCRIPTION
	    "Total number of jobs printed on a print queue
	    since the last restart."
    ::= { printQueueEntry 13 }

printQueueTotalPagesPrinted OBJECT-TYPE
    SYNTAX     Gauge32
    MAX-ACCESS read-only
    STATUS     current
    DESCRIPTION
	    "Total number of pages printed through GDI on a
	    print queue since the last restart."
    ::= { printQueueEntry 14 }

processTable OBJECT-TYPE
    SYNTAX     SEQUENCE OF ProcessEntry
    MAX-ACCESS not-accessible
    STATUS     current
    DESCRIPTION
	    "The Process performance object consists of
	    counters that monitor running application
	    program and system processes. All the threads
	    in a process share the same address space and
	    have access to the same data."
    ::= { advanced 64 }

processEntry OBJECT-TYPE
    SYNTAX     ProcessEntry
    MAX-ACCESS not-accessible
    STATUS     current
    DESCRIPTION
	    "Performance information for one particular
	    instance of 'Process' object."
    INDEX      { processInstance }
    ::= { processTable 1 }

ProcessEntry ::= SEQUENCE {
    processInstance InstanceName,
    processPercentPrivilegedTime Gauge32,
    processPercentProcessorTime Gauge32,
    processPercentUserTime Gauge32,
    processCreatingProcessID Gauge32,
    processElapsedTime Gauge32,
    processHandleCount Gauge32,
    processIDProcess Gauge32,
    processIODataBytesPerSec Gauge32,
    processIODataOperationsPerSec Gauge32,
    processIOOtherBytesPerSec Gauge32,
    processIOOtherOperationsPerSec Gauge32,
    processIOReadBytesPerSec Gauge32,
    processIOReadOperationsPerSec Gauge32,
    processIOWriteBytesPerSec Gauge32,
    processIOWriteOperationsPerSec Gauge32,
    processPageFaultsPerSec Gauge32,
    processPageFileBytes Gauge32,
    processPageFileBytesPeak Gauge32,
    processPoolNonpagedBytes Gauge32,
    processPoolPagedBytes Gauge32,
    processPriorityBase Gauge32,
    processPrivateBytes Gauge32,
    processThreadCount Gauge32,
    processVirtualBytes Gauge32,
    processVirtualBytesPeak Gauge32,
    processWorkingSet Gauge32,
    processWorkingSetPeak Gauge32,
    processPageFileKBytes Gauge32,
    processPageFileKBytesPeak Gauge32,
    processPoolNonpagedKBytes Gauge32,
    processPoolPagedKBytes Gauge32,
    processPrivateKBytes Gauge32,
    processVirtualKBytes Gauge32,
    processVirtualKBytesPeak Gauge32,
    processWorkingSetKBytes Gauge32,
    processWorkingSetKBytesPeak Gauge32,
    processPageFileMBytes Gauge32,
    processPageFileMBytesPeak Gauge32,
    processPoolNonpagedMBytes Gauge32,
    processPoolPagedMBytes Gauge32,
    processPrivateMBytes Gauge32,
    processVirtualMBytes Gauge32,
    processVirtualMBytesPeak Gauge32,
    processWorkingSetMBytes Gauge32,
    processWorkingSetMBytesPeak Gauge32
}

processInstance OBJECT-TYPE
    SYNTAX     InstanceName
    MAX-ACCESS read-only
    STATUS     current
    DESCRIPTION
	    "Instance name."
    ::= { processEntry 1 }

processPercentPrivilegedTime OBJECT-TYPE
    SYNTAX     Gauge32
    MAX-ACCESS read-only
    STATUS     current
    DESCRIPTION
	    "% Privileged Time is the percentage of elapsed
	    time that the threads of the process have spent
	    executing code in privileged mode.	When a
	    Windows NT system service is called, the
	    service will often run in Privileged Mode to
	    gain access to system-private data.  Such data
	    is protected from access by threads executing
	    in user Mode.  Calls to the system can be
	    explicit or implicit, such as page faults or
	    interrupts.  Unlike some early operating
	    systems, Windows NT uses process boundaries for
	    subsystem protection in addition to the
	    traditional protection of user and privileged
	    modes.  These subsystem processes provide
	    additional protection.  Therefore, some work
	    done by Windows NT on behalf of your
	    application might appear in other subsystem
	    processes in addition to the privileged time in
	    your process."
    ::= { processEntry 2 }

processPercentProcessorTime OBJECT-TYPE
    SYNTAX     Gauge32
    MAX-ACCESS read-only
    STATUS     current
    DESCRIPTION
	    "% Processor Time is the percentage of elapsed
	    time that all of the threads of this process
	    used the processor to execute instructions.  An
	    instruction is the basic unit of execution in a
	    computer, a thread is the object that executes
	    instructions, and a process is the object
	    created when a program is run.  Code executed
	    to handle some hardware interrupts and trap
	    conditions are included in this count.  On
	    Multi-processor machines the maximum value of
	    the counter is 100 % times the number of
	    processors."
    ::= { processEntry 3 }

processPercentUserTime OBJECT-TYPE
    SYNTAX     Gauge32
    MAX-ACCESS read-only
    STATUS     current
    DESCRIPTION
	    "% User Time is the percentage of elapsed time
	    that this process' threads have spent executing
	    code in user mode.	Applications, environment
	    subsystems and integral subsystems execute in
	    user mode.	Code executing in user mode cannot
	    damage the integrity of the Windows NT
	    Executive, Kernel, and device drivers.  Unlike
	    some early operating systems, Windows NT uses
	    process boundaries for subsystem protection in
	    addition to the traditional protection of user
	    and privileged modes.  These subsystem
	    processes provide additional protection. 
	    Therefore, some work done by Windows NT on
	    behalf of your application might appear in
	    other subsystem processes in addition to the
	    privileged time in your process."
    ::= { processEntry 4 }

processCreatingProcessID OBJECT-TYPE
    SYNTAX     Gauge32
    MAX-ACCESS read-only
    STATUS     current
    DESCRIPTION
	    "The Creating Process ID value is the Process
	    ID of the process  that created the process. 
	    Note that the creating process may have
	    terminated since this process was created and
	    so this value may no longer identify a running
	    process."
    ::= { processEntry 5 }

processElapsedTime OBJECT-TYPE
    SYNTAX     Gauge32
    MAX-ACCESS read-only
    STATUS     current
    DESCRIPTION
	    "The total elapsed time (in seconds) this
	    process has been running."
    ::= { processEntry 6 }

processHandleCount OBJECT-TYPE
    SYNTAX     Gauge32
    MAX-ACCESS read-only
    STATUS     current
    DESCRIPTION
	    "The total number of handles currently open by
	    this process.  This number is the sum of the
	    handles currently open by each thread in this
	    process."
    ::= { processEntry 7 }

processIDProcess OBJECT-TYPE
    SYNTAX     Gauge32
    MAX-ACCESS read-only
    STATUS     current
    DESCRIPTION
	    "ID Process is the unique identifier of this
	    process.  ID Process numbers are reused, so
	    they only identify a process for the lifetime
	    of that process."
    ::= { processEntry 8 }

processIODataBytesPerSec OBJECT-TYPE
    SYNTAX     Gauge32
    MAX-ACCESS read-only
    STATUS     current
    DESCRIPTION
	    "The rate the process is reading and writing
	    bytes in I/O operations.  This counter counts
	    all I/O activity generated by the process to
	    include file, network and device I/O's."
    ::= { processEntry 9 }

processIODataOperationsPerSec OBJECT-TYPE
    SYNTAX     Gauge32
    MAX-ACCESS read-only
    STATUS     current
    DESCRIPTION
	    "The rate the process is issuing read and write
	    I/O operations.  This counter counts all I/O
	    activity generated by the process to include
	    file, network and device I/O's."
    ::= { processEntry 10 }

processIOOtherBytesPerSec OBJECT-TYPE
    SYNTAX     Gauge32
    MAX-ACCESS read-only
    STATUS     current
    DESCRIPTION
	    "The rate the process is issuing bytes to I/O
	    operations that don't involve data such as
	    control operations.  This counter counts all
	    I/O activity generated by the process to
	    include file, network and device I/O's."
    ::= { processEntry 11 }

processIOOtherOperationsPerSec OBJECT-TYPE
    SYNTAX     Gauge32
    MAX-ACCESS read-only
    STATUS     current
    DESCRIPTION
	    "The rate the process is issuing I/O operations
	    that are neither a read or a write operation. 
	    An example of this type of operation would be a
	    control function.  This counter counts all I/O
	    activity generated by the process to include
	    file, network and device I/O's."
    ::= { processEntry 12 }

processIOReadBytesPerSec OBJECT-TYPE
    SYNTAX     Gauge32
    MAX-ACCESS read-only
    STATUS     current
    DESCRIPTION
	    "The rate the process is reading bytes from I/O
	    operations.  This counter counts all I/O
	    activity generated by the process to include
	    file, network and device I/O's."
    ::= { processEntry 13 }

processIOReadOperationsPerSec OBJECT-TYPE
    SYNTAX     Gauge32
    MAX-ACCESS read-only
    STATUS     current
    DESCRIPTION
	    "The rate the process is issuing read I/O
	    operations.  This counter counts all I/O
	    activity generated by the process to include
	    file, network and device I/O's."
    ::= { processEntry 14 }

processIOWriteBytesPerSec OBJECT-TYPE
    SYNTAX     Gauge32
    MAX-ACCESS read-only
    STATUS     current
    DESCRIPTION
	    "The rate the process is writing bytes to I/O
	    operations.  This counter counts all I/O
	    activity generated by the process to include
	    file, network and device I/O's."
    ::= { processEntry 15 }

processIOWriteOperationsPerSec OBJECT-TYPE
    SYNTAX     Gauge32
    MAX-ACCESS read-only
    STATUS     current
    DESCRIPTION
	    "The rate the process is issuing write I/O
	    operations.  This counter counts all I/O
	    activity generated by the process to include
	    file, network and device I/O's."
    ::= { processEntry 16 }

processPageFaultsPerSec OBJECT-TYPE
    SYNTAX     Gauge32
    MAX-ACCESS read-only
    STATUS     current
    DESCRIPTION
	    "Page Faults/sec is the rate Page Faults occur
	    in the threads executing in this process.  A
	    page fault occurs when a thread refers to a
	    virtual memory page that is not in its working
	    set in main memory.  This will not cause the
	    page to be fetched from disk if it is on the
	    standby list and hence already in main memory,
	    or if it is in use by another process with whom
	    the page is shared."
    ::= { processEntry 17 }

processPageFileBytes OBJECT-TYPE
    SYNTAX     Gauge32
    MAX-ACCESS read-only
    STATUS     current
    DESCRIPTION
	    "Page File Bytes is the current number of bytes
	    this process has used in the paging file(s). 
	    Paging files are used to store pages of memory
	    used by the process that are not contained in
	    other files.  Paging files are shared by all
	    processes, and lack of space in paging files
	    can prevent other processes from allocating
	    memory."
    ::= { processEntry 18 }

processPageFileBytesPeak OBJECT-TYPE
    SYNTAX     Gauge32
    MAX-ACCESS read-only
    STATUS     current
    DESCRIPTION
	    "Page File Bytes Peak is the maximum number of
	    bytes this process has used in the paging
	    file(s).  Paging files are used to store pages
	    of memory used by the process that are not
	    contained in other files.  Paging files are
	    shared by all processes, and lack of space in
	    paging files can prevent other processes from
	    allocating memory."
    ::= { processEntry 19 }

processPoolNonpagedBytes OBJECT-TYPE
    SYNTAX     Gauge32
    MAX-ACCESS read-only
    STATUS     current
    DESCRIPTION
	    "Pool Nonpaged Bytes is the number of bytes in
	    the nonpaged pool, an area of system memory
	    (physical memory used by the operating system)
	    for objects that cannot be written to disk, but
	    must remain in physical memory as long as they
	    are allocated.  Memory: Pool Nonpaged Bytes is
	    calculated differently than Process: Pool
	    Nonpaged Bytes, so it might not equal Process:
	    Pool Nonpaged Bytes: _Total.  This counter
	    displays the last observed value only; it is
	    not an average.  "
    ::= { processEntry 20 }

processPoolPagedBytes OBJECT-TYPE
    SYNTAX     Gauge32
    MAX-ACCESS read-only
    STATUS     current
    DESCRIPTION
	    "Pool Paged Bytes is the number of bytes in the
	    paged pool, an area of system memory (physical
	    memory used by the operating system) for
	    objects that can be written to disk when they
	    are not being used.  Memory: Pool Paged Bytes
	    is calculated differently than Process: Pool
	    Paged Bytes, so it might not equal Process:
	    Pool Paged Bytes: _Total.  This counter
	    displays the last observed value only; it is
	    not an average.  "
    ::= { processEntry 21 }

processPriorityBase OBJECT-TYPE
    SYNTAX     Gauge32
    MAX-ACCESS read-only
    STATUS     current
    DESCRIPTION
	    "The current base priority of this process. 
	    Threads within a process can raise and lower
	    their own base priority relative to the
	    process' base priority."
    ::= { processEntry 22 }

processPrivateBytes OBJECT-TYPE
    SYNTAX     Gauge32
    MAX-ACCESS read-only
    STATUS     current
    DESCRIPTION
	    "Private Bytes is the current number of bytes
	    this process has allocated that cannot be
	    shared with other processes."
    ::= { processEntry 23 }

processThreadCount OBJECT-TYPE
    SYNTAX     Gauge32
    MAX-ACCESS read-only
    STATUS     current
    DESCRIPTION
	    "The number of threads currently active in this
	    process.  An instruction is the basic unit of
	    execution in a processor, and a thread is the
	    object that executes instructions.	Every
	    running process has at least one thread."
    ::= { processEntry 24 }

processVirtualBytes OBJECT-TYPE
    SYNTAX     Gauge32
    MAX-ACCESS read-only
    STATUS     current
    DESCRIPTION
	    "Virtual Bytes is the current size in bytes of
	    the virtual address space the process is using.
	     Use of virtual address space does not
	    necessarily imply corresponding use of either
	    disk or main memory pages.	Virtual space is
	    finite, and by using too much, the process can
	    limit its ability to load libraries."
    ::= { processEntry 25 }

processVirtualBytesPeak OBJECT-TYPE
    SYNTAX     Gauge32
    MAX-ACCESS read-only
    STATUS     current
    DESCRIPTION
	    "Virtual Bytes Peak is the maximum number of
	    bytes of virtual address space the process has
	    used at any one time.  Use of virtual address
	    space does not necessarily imply corresponding
	    use of either disk or main memory pages. 
	    Virtual space is however finite, and by using
	    too much, the process might limit its ability
	    to load libraries."
    ::= { processEntry 26 }

processWorkingSet OBJECT-TYPE
    SYNTAX     Gauge32
    MAX-ACCESS read-only
    STATUS     current
    DESCRIPTION
	    "Working Set is the current number of bytes in
	    the Working Set of this process.  The Working
	    Set is the set of memory pages touched recently
	    by the threads in the process.  If free memory
	    in the computer is above a threshold, pages are
	    left in the Working Set of a process even if
	    they are not in use.  When free memory falls
	    below a threshold, pages are trimmed from
	    Working Sets.  If they are needed they will
	    then be soft-faulted back into the Working Set
	    before they leave main memory."
    ::= { processEntry 27 }

processWorkingSetPeak OBJECT-TYPE
    SYNTAX     Gauge32
    MAX-ACCESS read-only
    STATUS     current
    DESCRIPTION
	    "Working Set Peak is the maximum number of
	    bytes in the Working Set of this process at any
	    point in time.  The Working Set is the set of
	    memory pages touched recently by the threads in
	    the process.  If free memory in the computer is
	    above a threshold, pages are left in the
	    Working Set of a process even if they are not
	    in use.  When free memory falls below a
	    threshold, pages are trimmed from Working Sets.
	     If they are needed they will then be
	    soft-faulted back into the Working Set before
	    they leave main memory."
    ::= { processEntry 28 }

processPageFileKBytes OBJECT-TYPE
    SYNTAX     Gauge32
    MAX-ACCESS read-only
    STATUS     current
    DESCRIPTION
	    "Page File KiloBytes is the current number of
	    kilobytes this process has used in the paging
	    file(s).  Paging files are used to store pages
	    of memory used by the process that are not
	    contained in other files.  Paging files are
	    shared by all processes, and lack of space in
	    paging files can prevent other processes from
	    allocating memory."
    ::= { processEntry 29 }

processPageFileKBytesPeak OBJECT-TYPE
    SYNTAX     Gauge32
    MAX-ACCESS read-only
    STATUS     current
    DESCRIPTION
	    "Page File KiloBytes Peak is the maximum number
	    of kilobytes this process has used in the
	    paging file(s).  Paging files are used to store
	    pages of memory used by the process that are
	    not contained in other files.  Paging files are
	    shared by all processes, and lack of space in
	    paging files can prevent other processes from
	    allocating memory."
    ::= { processEntry 30 }

processPoolNonpagedKBytes OBJECT-TYPE
    SYNTAX     Gauge32
    MAX-ACCESS read-only
    STATUS     current
    DESCRIPTION
	    "Pool Nonpaged KiloBytes is the number of
	    kilobytes in the nonpaged pool, an area of
	    system memory (physical memory used by the
	    operating system) for objects that cannot be
	    written to disk, but must remain in physical
	    memory as long as they are allocated.  Memory:
	    Pool Nonpaged KiloBytes is calculated
	    differently than Process: Pool Nonpaged
	    KiloBytes, so it might not equal Process: Pool
	    Nonpaged KiloBytes: _Total.  This counter
	    displays the last observed value only; it is
	    not an average.  "
    ::= { processEntry 31 }

processPoolPagedKBytes OBJECT-TYPE
    SYNTAX     Gauge32
    MAX-ACCESS read-only
    STATUS     current
    DESCRIPTION
	    "Pool Paged KiloBytes is the number of
	    kilobytes in the paged pool, an area of system
	    memory (physical memory used by the operating
	    system) for objects that can be written to disk
	    when they are not being used.  Memory: Pool
	    Paged KiloBytes is calculated differently than
	    Process: Pool Paged KiloBytes, so it might not
	    equal Process: Pool Paged KiloBytes: _Total. 
	    This counter displays the last observed value
	    only; it is not an average.  "
    ::= { processEntry 32 }

processPrivateKBytes OBJECT-TYPE
    SYNTAX     Gauge32
    MAX-ACCESS read-only
    STATUS     current
    DESCRIPTION
	    "Private KiloBytes is the current number of
	    kilobytes this process has allocated that
	    cannot be shared with other processes."
    ::= { processEntry 33 }

processVirtualKBytes OBJECT-TYPE
    SYNTAX     Gauge32
    MAX-ACCESS read-only
    STATUS     current
    DESCRIPTION
	    "Virtual KiloBytes is the current size in
	    kilobytes of the virtual address space the
	    process is using.  Use of virtual address space
	    does not necessarily imply corresponding use of
	    either disk or main memory pages.  Virtual
	    space is finite, and by using too much, the
	    process can limit its ability to load
	    libraries."
    ::= { processEntry 34 }

processVirtualKBytesPeak OBJECT-TYPE
    SYNTAX     Gauge32
    MAX-ACCESS read-only
    STATUS     current
    DESCRIPTION
	    "Virtual KiloBytes Peak is the maximum number
	    of kilobytes of virtual address space the
	    process has used at any one time.  Use of
	    virtual address space does not necessarily
	    imply corresponding use of either disk or main
	    memory pages.  Virtual space is however finite,
	    and by using too much, the process might limit
	    its ability to load libraries."
    ::= { processEntry 35 }

processWorkingSetKBytes OBJECT-TYPE
    SYNTAX     Gauge32
    MAX-ACCESS read-only
    STATUS     current
    DESCRIPTION
	    "Working Set is the current number of kilobytes
	    in the Working Set of this process.  The
	    Working Set is the set of memory pages touched
	    recently by the threads in the process.  If
	    free memory in the computer is above a
	    threshold, pages are left in the Working Set of
	    a process even if they are not in use.  When
	    free memory falls below a threshold, pages are
	    trimmed from Working Sets.	If they are needed
	    they will then be soft-faulted back into the
	    Working Set before they leave main memory."
    ::= { processEntry 36 }

processWorkingSetKBytesPeak OBJECT-TYPE
    SYNTAX     Gauge32
    MAX-ACCESS read-only
    STATUS     current
    DESCRIPTION
	    "Working Set Peak is the maximum number of
	    kilobytes in the Working Set of this process at
	    any point in time.	The Working Set is the set
	    of memory pages touched recently by the threads
	    in the process.  If free memory in the computer
	    is above a threshold, pages are left in the
	    Working Set of a process even if they are not
	    in use.  When free memory falls below a
	    threshold, pages are trimmed from Working Sets.
	     If they are needed they will then be
	    soft-faulted back into the Working Set before
	    they leave main memory."
    ::= { processEntry 37 }

processPageFileMBytes OBJECT-TYPE
    SYNTAX     Gauge32
    MAX-ACCESS read-only
    STATUS     current
    DESCRIPTION
	    "Page File MegaBytes is the current number of
	    megabytes this process has used in the paging
	    file(s).  Paging files are used to store pages
	    of memory used by the process that are not
	    contained in other files.  Paging files are
	    shared by all processes, and lack of space in
	    paging files can prevent other processes from
	    allocating memory."
    ::= { processEntry 38 }

processPageFileMBytesPeak OBJECT-TYPE
    SYNTAX     Gauge32
    MAX-ACCESS read-only
    STATUS     current
    DESCRIPTION
	    "Page File MegaBytes Peak is the maximum number
	    of megabytes this process has used in the
	    paging file(s).  Paging files are used to store
	    pages of memory used by the process that are
	    not contained in other files.  Paging files are
	    shared by all processes, and lack of space in
	    paging files can prevent other processes from
	    allocating memory."
    ::= { processEntry 39 }

processPoolNonpagedMBytes OBJECT-TYPE
    SYNTAX     Gauge32
    MAX-ACCESS read-only
    STATUS     current
    DESCRIPTION
	    "Pool Nonpaged MegaBytes is the number of
	    megabytes in the nonpaged pool, an area of
	    system memory (physical memory used by the
	    operating system) for objects that cannot be
	    written to disk, but must remain in physical
	    memory as long as they are allocated.  Memory:
	    Pool Nonpaged MegaBytes is calculated
	    differently than Process: Pool Nonpaged
	    MegaBytes, so it might not equal Process: Pool
	    Nonpaged MegaBytes: _Total.  This counter
	    displays the last observed value only; it is
	    not an average.  "
    ::= { processEntry 40 }

processPoolPagedMBytes OBJECT-TYPE
    SYNTAX     Gauge32
    MAX-ACCESS read-only
    STATUS     current
    DESCRIPTION
	    "Pool Paged MegaBytes is the number of
	    megabytes in the paged pool, an area of system
	    memory (physical memory used by the operating
	    system) for objects that can be written to disk
	    when they are not being used.  Memory: Pool
	    Paged MegaBytes is calculated differently than
	    Process: Pool Paged MegaBytes, so it might not
	    equal Process: Pool Paged MegaBytes: _Total. 
	    This counter displays the last observed value
	    only; it is not an average.  "
    ::= { processEntry 41 }

processPrivateMBytes OBJECT-TYPE
    SYNTAX     Gauge32
    MAX-ACCESS read-only
    STATUS     current
    DESCRIPTION
	    "Private MegaBytes is the current number of
	    megabytes this process has allocated that
	    cannot be shared with other processes."
    ::= { processEntry 42 }

processVirtualMBytes OBJECT-TYPE
    SYNTAX     Gauge32
    MAX-ACCESS read-only
    STATUS     current
    DESCRIPTION
	    "Virtual MegaBytes is the current size in
	    megabytes of the virtual address space the
	    process is using.  Use of virtual address space
	    does not necessarily imply corresponding use of
	    either disk or main memory pages.  Virtual
	    space is finite, and by using too much, the
	    process can limit its ability to load
	    libraries."
    ::= { processEntry 43 }

processVirtualMBytesPeak OBJECT-TYPE
    SYNTAX     Gauge32
    MAX-ACCESS read-only
    STATUS     current
    DESCRIPTION
	    "Virtual MegaBytes Peak is the maximum number
	    of megabytes of virtual address space the
	    process has used at any one time.  Use of
	    virtual address space does not necessarily
	    imply corresponding use of either disk or main
	    memory pages.  Virtual space is however finite,
	    and by using too much, the process might limit
	    its ability to load libraries."
    ::= { processEntry 44 }

processWorkingSetMBytes OBJECT-TYPE
    SYNTAX     Gauge32
    MAX-ACCESS read-only
    STATUS     current
    DESCRIPTION
	    "Working Set is the current number of megabytes
	    in the Working Set of this process.  The
	    Working Set is the set of memory pages touched
	    recently by the threads in the process.  If
	    free memory in the computer is above a
	    threshold, pages are left in the Working Set of
	    a process even if they are not in use.  When
	    free memory falls below a threshold, pages are
	    trimmed from Working Sets.	If they are needed
	    they will then be soft-faulted back into the
	    Working Set before they leave main memory."
    ::= { processEntry 45 }

processWorkingSetMBytesPeak OBJECT-TYPE
    SYNTAX     Gauge32
    MAX-ACCESS read-only
    STATUS     current
    DESCRIPTION
	    "Working Set Peak is the maximum number of
	    megabytes in the Working Set of this process at
	    any point in time.	The Working Set is the set
	    of memory pages touched recently by the threads
	    in the process.  If free memory in the computer
	    is above a threshold, pages are left in the
	    Working Set of a process even if they are not
	    in use.  When free memory falls below a
	    threshold, pages are trimmed from Working Sets.
	     If they are needed they will then be
	    soft-faulted back into the Working Set before
	    they leave main memory."
    ::= { processEntry 46 }

processorTable OBJECT-TYPE
    SYNTAX     SEQUENCE OF ProcessorEntry
    MAX-ACCESS not-accessible
    STATUS     current
    DESCRIPTION
	    "The Processor performance object consists of
	    counters that measure aspects of processor
	    activity. The processor is the part of the
	    computer that performs arithmetic and logical
	    computations, initiates operations on
	    peripherals, and runs the threads of processes.
	    A computer can have multiple processors. The
	    processor object represents each processor as
	    an instance of the object."
    ::= { advanced 65 }

processorEntry OBJECT-TYPE
    SYNTAX     ProcessorEntry
    MAX-ACCESS not-accessible
    STATUS     current
    DESCRIPTION
	    "Performance information for one particular
	    instance of 'Processor' object."
    INDEX      { cpuInstance }
    ::= { processorTable 1 }

ProcessorEntry ::= SEQUENCE {
    cpuInstance InstanceName,
    cpuPercentC1Time Gauge32,
    cpuPercentC2Time Gauge32,
    cpuPercentC3Time Gauge32,
    cpuPercentDPCTime Gauge32,
    cpuPercentIdleTime Gauge32,
    cpuPercentInterruptTime Gauge32,
    cpuPercentPrivilegedTime Gauge32,
    cpuPercentProcessorTime Gauge32,
    cpuPercentUserTime Gauge32,
    cpuC1TransitionsPerSec Gauge32,
    cpuC2TransitionsPerSec Gauge32,
    cpuC3TransitionsPerSec Gauge32,
    cpuDPCRate Gauge32,
    cpuDPCsQueuedPerSec Gauge32,
    cpuInterruptsPerSec Gauge32
}

cpuInstance OBJECT-TYPE
    SYNTAX     InstanceName
    MAX-ACCESS read-only
    STATUS     current
    DESCRIPTION
	    "Instance name."
    ::= { processorEntry 1 }

cpuPercentC1Time OBJECT-TYPE
    SYNTAX     Gauge32
    MAX-ACCESS read-only
    STATUS     current
    DESCRIPTION
	    "% C1 Time is the percentage of time the
	    processor spends in the C1 low-power idle
	    state. % C1 Time is a subset of the total
	    processor idle time. C1 low-power idle state
	    enables the processor to maintain its entire
	    context and quickly return to the running
	    state. Not all systems support the % C1 state."
    ::= { processorEntry 2 }

cpuPercentC2Time OBJECT-TYPE
    SYNTAX     Gauge32
    MAX-ACCESS read-only
    STATUS     current
    DESCRIPTION
	    "% C2 Time is the percentage of time the
	    processor spends in the C2 low-power idle
	    state. % C2 Time is a subset of the total
	    processor idle time. C2 low-power idle state
	    enables the processor to maintain the context
	    of the system caches. The C2 power state is a
	    lower power and higher exit latency state than
	    C1. Not all systems support the C2 state."
    ::= { processorEntry 3 }

cpuPercentC3Time OBJECT-TYPE
    SYNTAX     Gauge32
    MAX-ACCESS read-only
    STATUS     current
    DESCRIPTION
	    "% C3 Time is the percentage of time the
	    processor spends in the C3 low-power idle
	    state. % C3 Time is a subset of the total
	    processor idle time. When the processor is in
	    the C3 low-power idle state it is unable to
	    maintain the coherency of its caches. The C3
	    power state is a lower power and higher exit
	    latency state than C2. Not all systems support
	    the C3 state."
    ::= { processorEntry 4 }

cpuPercentDPCTime OBJECT-TYPE
    SYNTAX     Gauge32
    MAX-ACCESS read-only
    STATUS     current
    DESCRIPTION
	    "% DPC Time is the percentage of time that the
	    processor spent receiving and servicing
	    deferred procedure calls (DPCs) during the
	    sample interval. DPCs are interrupts that run
	    at a lower priority than standard interrupts. %
	    DPC Time is a component of % Privileged Time
	    because DPCs are executed in privileged mode.
	    They are counted separately and are not a
	    component of the interrupt counters. This
	    counter displays the average busy time as a
	    percentage of the sample time. "
    ::= { processorEntry 5 }

cpuPercentIdleTime OBJECT-TYPE
    SYNTAX     Gauge32
    MAX-ACCESS read-only
    STATUS     current
    DESCRIPTION
	    "% Idle Time is the percentage of time the
	    processor is idle during the sample interval"
    ::= { processorEntry 6 }

cpuPercentInterruptTime OBJECT-TYPE
    SYNTAX     Gauge32
    MAX-ACCESS read-only
    STATUS     current
    DESCRIPTION
	    "% Interrupt Time is the time the processor
	    spends receiving and servicing hardware
	    interrupts during sample intervals. This value
	    is an indirect indicator of the activity of
	    devices that generate interrupts, such as the
	    system clock, the mouse, disk drivers, data
	    communication lines, network interface cards
	    and other peripheral devices. These devices
	    normally interrupt the processor when they have
	    completed a task or require attention. Normal
	    thread execution is suspended during
	    interrupts. Most system clocks interrupt the
	    processor every 10 milliseconds, creating a
	    background of interrupt activity. suspends
	    normal thread execution during interrupts. This
	    counter displays the average busy time as a
	    percentage of the sample time."
    ::= { processorEntry 7 }

cpuPercentPrivilegedTime OBJECT-TYPE
    SYNTAX     Gauge32
    MAX-ACCESS read-only
    STATUS     current
    DESCRIPTION
	    "% Privileged Time is the percentage of elapsed
	    time that the process threads spent executing
	    code in privileged mode.  When a Windows system
	    service in called, the service will often run
	    in privileged mode to gain access to
	    system-private data. Such data is protected
	    from access by threads executing in user mode.
	    Calls to the system can be explicit or
	    implicit, such as page faults or interrupts.
	    Unlike some early operating systems, Windows
	    uses process boundaries for subsystem
	    protection in addition to the traditional
	    protection of user and privileged modes. Some
	    work done by Windows on behalf of the
	    application might appear in other subsystem
	    processes in addition to the privileged time in
	    the process. "
    ::= { processorEntry 8 }

cpuPercentProcessorTime OBJECT-TYPE
    SYNTAX     Gauge32
    MAX-ACCESS read-only
    STATUS     current
    DESCRIPTION
	    "% Processor Time is the percentage of elapsed
	    time that the processor spends to execute a
	    non-Idle thread. It is calculated by measuring
	    the duration of the idle thread is active in
	    the sample interval, and subtracting that time
	    from interval duration.  (Each processor has an
	    idle thread that consumes cycles when no other
	    threads are ready to run). This counter is the
	    primary indicator of processor activity, and
	    displays the average percentage of busy time
	    observed during the sample interval. It is
	    calculated by monitoring the time that the
	    service is inactive, and subtracting that value
	    from 100%."
    ::= { processorEntry 9 }

cpuPercentUserTime OBJECT-TYPE
    SYNTAX     Gauge32
    MAX-ACCESS read-only
    STATUS     current
    DESCRIPTION
	    "% User Time is the percentage of elapsed time
	    the processor spends in the user mode. User
	    mode is a restricted processing mode designed
	    for applications, environment subsystems, and
	    integral subsystems.  The alternative,
	    privileged mode, is designed for operating
	    system components and allows direct access to
	    hardware and all memory.  The operating system
	    switches application threads to privileged mode
	    to access operating system services. This
	    counter displays the average busy time as a
	    percentage of the sample time."
    ::= { processorEntry 10 }

cpuC1TransitionsPerSec OBJECT-TYPE
    SYNTAX     Gauge32
    MAX-ACCESS read-only
    STATUS     current
    DESCRIPTION
	    "C1 Transitions/sec is the rate that the CPU
	    enters the C1 low-power idle state. The CPU
	    enters the C1 state when it is sufficiently
	    idle and exits this state on any interrupt.
	    This counter displays the difference between
	    the values observed in the last two samples,
	    divided by the duration of the sample
	    interval."
    ::= { processorEntry 11 }

cpuC2TransitionsPerSec OBJECT-TYPE
    SYNTAX     Gauge32
    MAX-ACCESS read-only
    STATUS     current
    DESCRIPTION
	    "C2 Transitions/sec is the rate that the CPU
	    enters the C2 low-power idle state. The CPU
	    enters the C2 state when it is sufficiently
	    idle and exits this state on any interrupt.
	    This counter displays the difference between
	    the values observed in the last two samples,
	    divided by the duration of the sample
	    interval."
    ::= { processorEntry 12 }

cpuC3TransitionsPerSec OBJECT-TYPE
    SYNTAX     Gauge32
    MAX-ACCESS read-only
    STATUS     current
    DESCRIPTION
	    "C3 Transitions/sec is the rate that the CPU
	    enters the C3 low-power idle state. The CPU
	    enters the C3 state when it is sufficiently
	    idle and exits this state on any interrupt.
	    This counter displays the difference between
	    the values observed in the last two samples,
	    divided by the duration of the sample
	    interval."
    ::= { processorEntry 13 }

cpuDPCRate OBJECT-TYPE
    SYNTAX     Gauge32
    MAX-ACCESS read-only
    STATUS     current
    DESCRIPTION
	    "DPC Rate is the rate at which deferred
	    procedure calls (DPCs) were added to the
	    processors DPC queues between the timer ticks
	    of the processor clock. DPCs are interrupts
	    that run at alower priority than standard
	    interrupts.  Each processor has its own DPC
	    queue. This counter measures the rate that DPCs
	    were added to the queue, not the number of DPCs
	    in the queue. This counter displays the last
	    observed value only; it is not an average."
    ::= { processorEntry 14 }

cpuDPCsQueuedPerSec OBJECT-TYPE
    SYNTAX     Gauge32
    MAX-ACCESS read-only
    STATUS     current
    DESCRIPTION
	    "DPCs Queued/sec is the average rate, in
	    incidents per second, at which deferred
	    procedure calls (DPCs) were added to the
	    processor's DPC queue. DPCs are interrupts that
	    run at a lower priority than standard
	    interrupts.  Each processor has its own DPC
	    queue. This counter measures the rate that DPCs
	    are added to the queue, not the number of DPCs
	    in the queue.  This counter displays the
	    difference between the values observed in the
	    last two samples, divided by the duration of
	    the sample interval. "
    ::= { processorEntry 15 }

cpuInterruptsPerSec OBJECT-TYPE
    SYNTAX     Gauge32
    MAX-ACCESS read-only
    STATUS     current
    DESCRIPTION
	    "Interrupts/sec is the average rate, in
	    incidents per second, at which the processor
	    received and serviced hardware interrupts. It
	    does not include deferred procedure calls
	    (DPCs), which are counted separately. This
	    value is an indirect indicator of the activity
	    of devices that generate interrupts, such as
	    the system clock, the mouse, disk drivers, data
	    communication lines, network interface cards,
	    and other peripheral devices. These devices
	    normally interrupt the processor when they have
	    completed a task or require attention. Normal
	    thread execution is suspended. The system clock
	    typically interrupts the processor every 10
	    milliseconds, creating a background of
	    interrupt activity. This counter displays the
	    difference between the values observed in the
	    last two samples, divided by the duration of
	    the sample interval."
    ::= { processorEntry 16 }

pSchedFlowTable OBJECT-TYPE
    SYNTAX     SEQUENCE OF PSchedFlowEntry
    MAX-ACCESS not-accessible
    STATUS     current
    DESCRIPTION
	    "The PSched Flow Object shows statistics from
	    the packet scheduler, a feature of QoS
	    Admission Control."
    ::= { advanced 66 }

pSchedFlowEntry OBJECT-TYPE
    SYNTAX     PSchedFlowEntry
    MAX-ACCESS not-accessible
    STATUS     current
    DESCRIPTION
	    "Performance information for one particular
	    instance of 'PSched Flow' object."
    INDEX      { pSchedFlowInstance }
    ::= { pSchedFlowTable 1 }

PSchedFlowEntry ::= SEQUENCE {
    pSchedFlowInstance InstanceName,
    pSchedFlowAveragePktsInNetcard Gauge32,
    pSchedFlowAveragePktsInSequencer Gauge32,
    pSchedFlowAveragePktsInShaper Gauge32,
    pSchedFlowBytesScheduled Gauge32,
    pSchedFlowBytesScheduledPerSec Gauge32,
    pSchedFlowBytesTransmitted Gauge32,
    pSchedFlowBytesTransmittedPerSec Gauge32,
    pSchedFlowMaxPktsInSequencer Gauge32,
    pSchedFlowMaxPktsInShaper Gauge32,
    pSchedFlowMaximumPktsInNetcard Gauge32,
    pSchedFlowNonconfPktsSched Gauge32,
    pSchedFlowNonconfPktsSchedPerSec Gauge32,
    pSchedFlowNonconfPktsXmitd Gauge32,
    pSchedFlowNonconfPktsXmitdPerSec Gauge32,
    pSchedFlowPktsDropped Gauge32,
    pSchedFlowPktsDroppedPerSec Gauge32,
    pSchedFlowPktsScheduled Gauge32,
    pSchedFlowPktsScheduledPerSec Gauge32,
    pSchedFlowPktsTransmitted Gauge32,
    pSchedFlowPktsTransmittedPerSec Gauge32
}

pSchedFlowInstance OBJECT-TYPE
    SYNTAX     InstanceName
    MAX-ACCESS read-only
    STATUS     current
    DESCRIPTION
	    "Instance name."
    ::= { pSchedFlowEntry 1 }

pSchedFlowAveragePktsInNetcard OBJECT-TYPE
    SYNTAX     Gauge32
    MAX-ACCESS read-only
    STATUS     current
    DESCRIPTION
	    "Shows the average number of packets that have
	    been queued in the network adapter by this
	    flow."
    ::= { pSchedFlowEntry 2 }

pSchedFlowAveragePktsInSequencer OBJECT-TYPE
    SYNTAX     Gauge32
    MAX-ACCESS read-only
    STATUS     current
    DESCRIPTION
	    "Shows the average number of packets in the
	    sequencer over the last sampling period."
    ::= { pSchedFlowEntry 3 }

pSchedFlowAveragePktsInShaper OBJECT-TYPE
    SYNTAX     Gauge32
    MAX-ACCESS read-only
    STATUS     current
    DESCRIPTION
	    "Shows the average number of packets in the
	    scheduler over the last sampling period."
    ::= { pSchedFlowEntry 4 }

pSchedFlowBytesScheduled OBJECT-TYPE
    SYNTAX     Gauge32
    MAX-ACCESS read-only
    STATUS     current
    DESCRIPTION
	    "Shows the number of bytes that were scheduled
	    in some way (rather than just being directly
	    sent to the underlying miniport)."
    ::= { pSchedFlowEntry 5 }

pSchedFlowBytesScheduledPerSec OBJECT-TYPE
    SYNTAX     Gauge32
    MAX-ACCESS read-only
    STATUS     current
    DESCRIPTION
	    "Shows the number of packets per second from
	    this flow that have been scheduled."
    ::= { pSchedFlowEntry 6 }

pSchedFlowBytesTransmitted OBJECT-TYPE
    SYNTAX     Gauge32
    MAX-ACCESS read-only
    STATUS     current
    DESCRIPTION
	    "Shows the number of bytes from this flow that
	    have been sent."
    ::= { pSchedFlowEntry 7 }

pSchedFlowBytesTransmittedPerSec OBJECT-TYPE
    SYNTAX     Gauge32
    MAX-ACCESS read-only
    STATUS     current
    DESCRIPTION
	    "Shows the number of bytes per second from this
	    flow that have been sent."
    ::= { pSchedFlowEntry 8 }

pSchedFlowMaxPktsInSequencer OBJECT-TYPE
    SYNTAX     Gauge32
    MAX-ACCESS read-only
    STATUS     current
    DESCRIPTION
	    "Shows the maximum number of packets that have
	    ever simultaneously been in the sequencer."
    ::= { pSchedFlowEntry 9 }

pSchedFlowMaxPktsInShaper OBJECT-TYPE
    SYNTAX     Gauge32
    MAX-ACCESS read-only
    STATUS     current
    DESCRIPTION
	    "Shows the maximum number of packets that have
	    ever simultaneously been in the scheduler."
    ::= { pSchedFlowEntry 10 }

pSchedFlowMaximumPktsInNetcard OBJECT-TYPE
    SYNTAX     Gauge32
    MAX-ACCESS read-only
    STATUS     current
    DESCRIPTION
	    "Shows the maximum number of packets that have
	    been queued in the network adapter by this
	    flow."
    ::= { pSchedFlowEntry 11 }

pSchedFlowNonconfPktsSched OBJECT-TYPE
    SYNTAX     Gauge32
    MAX-ACCESS read-only
    STATUS     current
    DESCRIPTION
	    "Shows the number of packets that have entered
	    the packet scheduler at a rate which exceeded
	    the flow parameters."
    ::= { pSchedFlowEntry 12 }

pSchedFlowNonconfPktsSchedPerSec OBJECT-TYPE
    SYNTAX     Gauge32
    MAX-ACCESS read-only
    STATUS     current
    DESCRIPTION
	    "Shows the rate at which nonconforming packets
	    have entered the packet scheduler."
    ::= { pSchedFlowEntry 13 }

pSchedFlowNonconfPktsXmitd OBJECT-TYPE
    SYNTAX     Gauge32
    MAX-ACCESS read-only
    STATUS     current
    DESCRIPTION
	    "Shows the number of packets that have been
	    sent by the packet scheduler at a rate which
	    exceeded the flow parameters."
    ::= { pSchedFlowEntry 14 }

pSchedFlowNonconfPktsXmitdPerSec OBJECT-TYPE
    SYNTAX     Gauge32
    MAX-ACCESS read-only
    STATUS     current
    DESCRIPTION
	    "Shows the rate at which nonconforming packets
	    have been sent by the packet scheduler."
    ::= { pSchedFlowEntry 15 }

pSchedFlowPktsDropped OBJECT-TYPE
    SYNTAX     Gauge32
    MAX-ACCESS read-only
    STATUS     current
    DESCRIPTION
	    "Shows the number of packets dropped by the
	    packet scheduler."
    ::= { pSchedFlowEntry 16 }

pSchedFlowPktsDroppedPerSec OBJECT-TYPE
    SYNTAX     Gauge32
    MAX-ACCESS read-only
    STATUS     current
    DESCRIPTION
	    "Shows the number of packets that were dropped
	    by the packet scheduler from this flow per
	    second."
    ::= { pSchedFlowEntry 17 }

pSchedFlowPktsScheduled OBJECT-TYPE
    SYNTAX     Gauge32
    MAX-ACCESS read-only
    STATUS     current
    DESCRIPTION
	    "Shows the number of packets that were
	    scheduled in some way (rather than just being
	    directly sent to the underlying miniport)."
    ::= { pSchedFlowEntry 18 }

pSchedFlowPktsScheduledPerSec OBJECT-TYPE
    SYNTAX     Gauge32
    MAX-ACCESS read-only
    STATUS     current
    DESCRIPTION
	    "Shows the number of packets per second from
	    this flow that have been scheduled."
    ::= { pSchedFlowEntry 19 }

pSchedFlowPktsTransmitted OBJECT-TYPE
    SYNTAX     Gauge32
    MAX-ACCESS read-only
    STATUS     current
    DESCRIPTION
	    "Shows the number of bytes from this flow that
	    have been sent."
    ::= { pSchedFlowEntry 20 }

pSchedFlowPktsTransmittedPerSec OBJECT-TYPE
    SYNTAX     Gauge32
    MAX-ACCESS read-only
    STATUS     current
    DESCRIPTION
	    "Shows the number of packets per second from
	    this flow that have been sent."
    ::= { pSchedFlowEntry 21 }

pSchedPipeTable OBJECT-TYPE
    SYNTAX     SEQUENCE OF PSchedPipeEntry
    MAX-ACCESS not-accessible
    STATUS     current
    DESCRIPTION
	    "The PSched Pipe Object performance object
	    reports statistics from the packet scheduler, a
	    feature of QoS Admission Control."
    ::= { advanced 67 }

pSchedPipeEntry OBJECT-TYPE
    SYNTAX     PSchedPipeEntry
    MAX-ACCESS not-accessible
    STATUS     current
    DESCRIPTION
	    "Performance information for one particular
	    instance of 'PSched Pipe' object."
    INDEX      { pSchedPipeInstance }
    ::= { pSchedPipeTable 1 }

PSchedPipeEntry ::= SEQUENCE {
    pSchedPipeInstance InstanceName,
    pSchedPipeAvgPacketsInNetcard Gauge32,
    pSchedPipeAvgPacketsInSequencer Gauge32,
    pSchedPipeAvgPacketsInShaper Gauge32,
    pSchedPipeFlowModsRejected Gauge32,
    pSchedPipeFlowsClosed Gauge32,
    pSchedPipeFlowsModified Gauge32,
    pSchedPipeFlowsOpened Gauge32,
    pSchedPipeFlowsRejected Gauge32,
    pSchedPipeMaxPacketsInNetcard Gauge32,
    pSchedPipeMaxPacketsInSequencer Gauge32,
    pSchedPipeMaxPacketsInShaper Gauge32,
    pSchedPipeMaxSimultaneousFlows Gauge32,
    pSchedPipeBadPacketsSched Gauge32,
    pSchedPipeBadPacketsSchedPerSec Gauge32,
    pSchedPipeBadPacketsXmited Gauge32,
    pSchedPipeBadPacketsXmitedPerSec Gauge32,
    pSchedPipeOutOfPackets Gauge32
}

pSchedPipeInstance OBJECT-TYPE
    SYNTAX     InstanceName
    MAX-ACCESS read-only
    STATUS     current
    DESCRIPTION
	    "Instance name."
    ::= { pSchedPipeEntry 1 }

pSchedPipeAvgPacketsInNetcard OBJECT-TYPE
    SYNTAX     Gauge32
    MAX-ACCESS read-only
    STATUS     current
    DESCRIPTION
	    "The average number of packets in the network
	    card over the last sampling period"
    ::= { pSchedPipeEntry 2 }

pSchedPipeAvgPacketsInSequencer OBJECT-TYPE
    SYNTAX     Gauge32
    MAX-ACCESS read-only
    STATUS     current
    DESCRIPTION
	    "The average number of packets in the sequencer
	    over the last sampling period"
    ::= { pSchedPipeEntry 3 }

pSchedPipeAvgPacketsInShaper OBJECT-TYPE
    SYNTAX     Gauge32
    MAX-ACCESS read-only
    STATUS     current
    DESCRIPTION
	    "The average number of packets in the shaper
	    over the last sampling period"
    ::= { pSchedPipeEntry 4 }

pSchedPipeFlowModsRejected OBJECT-TYPE
    SYNTAX     Gauge32
    MAX-ACCESS read-only
    STATUS     current
    DESCRIPTION
	    "The number of times a flow modification has
	    been rejected"
    ::= { pSchedPipeEntry 5 }

pSchedPipeFlowsClosed OBJECT-TYPE
    SYNTAX     Gauge32
    MAX-ACCESS read-only
    STATUS     current
    DESCRIPTION
	    "The number of flows that have been closed"
    ::= { pSchedPipeEntry 6 }

pSchedPipeFlowsModified OBJECT-TYPE
    SYNTAX     Gauge32
    MAX-ACCESS read-only
    STATUS     current
    DESCRIPTION
	    "The of times a flow has been modified"
    ::= { pSchedPipeEntry 7 }

pSchedPipeFlowsOpened OBJECT-TYPE
    SYNTAX     Gauge32
    MAX-ACCESS read-only
    STATUS     current
    DESCRIPTION
	    "The number of flows opened on this pipe (some
	    of which may now be closed)"
    ::= { pSchedPipeEntry 8 }

pSchedPipeFlowsRejected OBJECT-TYPE
    SYNTAX     Gauge32
    MAX-ACCESS read-only
    STATUS     current
    DESCRIPTION
	    "The number of flow creations that were
	    rejected"
    ::= { pSchedPipeEntry 9 }

pSchedPipeMaxPacketsInNetcard OBJECT-TYPE
    SYNTAX     Gauge32
    MAX-ACCESS read-only
    STATUS     current
    DESCRIPTION
	    "The maximum number of packets ever
	    simultaneously in the network card"
    ::= { pSchedPipeEntry 10 }

pSchedPipeMaxPacketsInSequencer OBJECT-TYPE
    SYNTAX     Gauge32
    MAX-ACCESS read-only
    STATUS     current
    DESCRIPTION
	    "The maximum number of packets that have ever
	    simultaneously been in the sequencer"
    ::= { pSchedPipeEntry 11 }

pSchedPipeMaxPacketsInShaper OBJECT-TYPE
    SYNTAX     Gauge32
    MAX-ACCESS read-only
    STATUS     current
    DESCRIPTION
	    "The maximum number of packets that have ever
	    simultaneously been in the shaper"
    ::= { pSchedPipeEntry 12 }

pSchedPipeMaxSimultaneousFlows OBJECT-TYPE
    SYNTAX     Gauge32
    MAX-ACCESS read-only
    STATUS     current
    DESCRIPTION
	    "The maximum number of flows that have been
	    simultaneously open on this pipe"
    ::= { pSchedPipeEntry 13 }

pSchedPipeBadPacketsSched OBJECT-TYPE
    SYNTAX     Gauge32
    MAX-ACCESS read-only
    STATUS     current
    DESCRIPTION
	    "The number of packets that have entered the
	    packet scheduler at a rate which exceeded that
	    packet's flow parameters"
    ::= { pSchedPipeEntry 14 }

pSchedPipeBadPacketsSchedPerSec OBJECT-TYPE
    SYNTAX     Gauge32
    MAX-ACCESS read-only
    STATUS     current
    DESCRIPTION
	    "The rate at which nonconforming packets have
	    entered the packet scheduler"
    ::= { pSchedPipeEntry 15 }

pSchedPipeBadPacketsXmited OBJECT-TYPE
    SYNTAX     Gauge32
    MAX-ACCESS read-only
    STATUS     current
    DESCRIPTION
	    "The number of packets that have been sent by
	    the packet scheduler at a rate which exceeded
	    that packet's flow parameters"
    ::= { pSchedPipeEntry 16 }

pSchedPipeBadPacketsXmitedPerSec OBJECT-TYPE
    SYNTAX     Gauge32
    MAX-ACCESS read-only
    STATUS     current
    DESCRIPTION
	    "The rate at which nonconforming packets have
	    been sent by the packet scheduler"
    ::= { pSchedPipeEntry 17 }

pSchedPipeOutOfPackets OBJECT-TYPE
    SYNTAX     Gauge32
    MAX-ACCESS read-only
    STATUS     current
    DESCRIPTION
	    "The number of times PSched has been unable to
	    allocate a packet"
    ::= { pSchedPipeEntry 18 }

rasTotal OBJECT-IDENTITY
    STATUS     current
    DESCRIPTION
	    "The RAS Total performance object consists of
	    counters that combine values for all ports of
	    the Remote Access Service (RAS) device on the
	    computer."
    ::= { advanced 68 }

rasTotalAlignmentErrors OBJECT-TYPE
    SYNTAX     Gauge32
    MAX-ACCESS read-only
    STATUS     current
    DESCRIPTION
	    "The total number of Alignment Errors for this
	    connection.  Alignment Errors occur when a byte
	    received is different from the byte expected."
    ::= { rasTotal 1 }

rasTotalBufferOverrunErrors OBJECT-TYPE
    SYNTAX     Gauge32
    MAX-ACCESS read-only
    STATUS     current
    DESCRIPTION
	    "The total number of Buffer Overrun Errors for
	    this connection.  Buffer Overrun Errors when
	    the software cannot handle the rate at which
	    data is received."
    ::= { rasTotal 2 }

rasTotalBytesReceived OBJECT-TYPE
    SYNTAX     Gauge32
    MAX-ACCESS read-only
    STATUS     current
    DESCRIPTION
	    "The number of bytes received total for this
	    connection."
    ::= { rasTotal 3 }

rasTotalBytesReceivedPerSec OBJECT-TYPE
    SYNTAX     Gauge32
    MAX-ACCESS read-only
    STATUS     current
    DESCRIPTION
	    "The number of bytes received per second."
    ::= { rasTotal 4 }

rasTotalBytesTransmitted OBJECT-TYPE
    SYNTAX     Gauge32
    MAX-ACCESS read-only
    STATUS     current
    DESCRIPTION
	    "The number of bytes transmitted total for this
	    connection."
    ::= { rasTotal 5 }

rasTotalBytesTransmittedPerSec OBJECT-TYPE
    SYNTAX     Gauge32
    MAX-ACCESS read-only
    STATUS     current
    DESCRIPTION
	    "The number of bytes transmitted per second."
    ::= { rasTotal 6 }

rasTotalCRCErrors OBJECT-TYPE
    SYNTAX     Gauge32
    MAX-ACCESS read-only
    STATUS     current
    DESCRIPTION
	    "The total number of CRC Errors for this
	    connection.  CRC Errors occur when the frame
	    received contains erroneous data."
    ::= { rasTotal 7 }

rasTotalFramesReceived OBJECT-TYPE
    SYNTAX     Gauge32
    MAX-ACCESS read-only
    STATUS     current
    DESCRIPTION
	    "The number of data frames received total for
	    this connection."
    ::= { rasTotal 8 }

rasTotalFramesReceivedPerSec OBJECT-TYPE
    SYNTAX     Gauge32
    MAX-ACCESS read-only
    STATUS     current
    DESCRIPTION
	    "The number of frames received per second."
    ::= { rasTotal 9 }

rasTotalFramesTransmitted OBJECT-TYPE
    SYNTAX     Gauge32
    MAX-ACCESS read-only
    STATUS     current
    DESCRIPTION
	    "The number of data frames transmitted total
	    for this connection."
    ::= { rasTotal 10 }

rasTotalFramesTransmittedPerSec OBJECT-TYPE
    SYNTAX     Gauge32
    MAX-ACCESS read-only
    STATUS     current
    DESCRIPTION
	    "The number of frames transmitted per second."
    ::= { rasTotal 11 }

rasTotalPercentCompressionIn OBJECT-TYPE
    SYNTAX     Gauge32
    MAX-ACCESS read-only
    STATUS     current
    DESCRIPTION
	    "The compression ratio for bytes being
	    received."
    ::= { rasTotal 12 }

rasTotalPercentCompressionOut OBJECT-TYPE
    SYNTAX     Gauge32
    MAX-ACCESS read-only
    STATUS     current
    DESCRIPTION
	    "The compression ratio for bytes being
	    transmitted."
    ::= { rasTotal 13 }

rasTotalSerialOverrunErrors OBJECT-TYPE
    SYNTAX     Gauge32
    MAX-ACCESS read-only
    STATUS     current
    DESCRIPTION
	    "The total number of Serial Overrun Errors for
	    this connection.  Serial Overrun Errors occur
	    when the hardware cannot handle the rate at
	    which data is received."
    ::= { rasTotal 14 }

rasTotalTimeoutErrors OBJECT-TYPE
    SYNTAX     Gauge32
    MAX-ACCESS read-only
    STATUS     current
    DESCRIPTION
	    "The total number of Timeout Errors for this
	    connection.  Timeout Errors occur when an
	    expected is not received in time."
    ::= { rasTotal 15 }

rasTotalTotalConnections OBJECT-TYPE
    SYNTAX     Gauge32
    MAX-ACCESS read-only
    STATUS     current
    DESCRIPTION
	    "The total number of Remote Access
	    connections."
    ::= { rasTotal 16 }

rasTotalTotalErrors OBJECT-TYPE
    SYNTAX     Gauge32
    MAX-ACCESS read-only
    STATUS     current
    DESCRIPTION
	    "The total number of CRC, Timeout, Serial
	    Overrun, Alignment, and Buffer Overrun Errors
	    for this connection."
    ::= { rasTotal 17 }

rasTotalTotalErrorsPerSec OBJECT-TYPE
    SYNTAX     Gauge32
    MAX-ACCESS read-only
    STATUS     current
    DESCRIPTION
	    "The total number of CRC, Timeout, Serial
	    Overrun, Alignment, and Buffer Overrun Errors
	    per second."
    ::= { rasTotal 18 }

rasPortTable OBJECT-TYPE
    SYNTAX     SEQUENCE OF RASPortEntry
    MAX-ACCESS not-accessible
    STATUS     current
    DESCRIPTION
	    "The RAS Port performance object consists of
	    counters that monitor individual Remote Access
	    Service (RAS) ports of the RAS device on the
	    system."
    ::= { advanced 69 }

rasPortEntry OBJECT-TYPE
    SYNTAX     RASPortEntry
    MAX-ACCESS not-accessible
    STATUS     current
    DESCRIPTION
	    "Performance information for one particular
	    instance of 'RAS Port' object."
    INDEX      { rasPortInstance }
    ::= { rasPortTable 1 }

RASPortEntry ::= SEQUENCE {
    rasPortInstance InstanceName,
    rasPortAlignmentErrors Gauge32,
    rasPortBufferOverrunErrors Gauge32,
    rasPortBytesReceived Gauge32,
    rasPortBytesReceivedPerSec Gauge32,
    rasPortBytesTransmitted Gauge32,
    rasPortBytesTransmittedPerSec Gauge32,
    rasPortCRCErrors Gauge32,
    rasPortFramesReceived Gauge32,
    rasPortFramesReceivedPerSec Gauge32,
    rasPortFramesTransmitted Gauge32,
    rasPortFramesTransmittedPerSec Gauge32,
    rasPortPercentCompressionIn Gauge32,
    rasPortPercentCompressionOut Gauge32,
    rasPortSerialOverrunErrors Gauge32,
    rasPortTimeoutErrors Gauge32,
    rasPortTotalErrors Gauge32,
    rasPortTotalErrorsPerSec Gauge32
}

rasPortInstance OBJECT-TYPE
    SYNTAX     InstanceName
    MAX-ACCESS read-only
    STATUS     current
    DESCRIPTION
	    "Instance name."
    ::= { rasPortEntry 1 }

rasPortAlignmentErrors OBJECT-TYPE
    SYNTAX     Gauge32
    MAX-ACCESS read-only
    STATUS     current
    DESCRIPTION
	    "The total number of Alignment Errors for this
	    connection.  Alignment Errors occur when a byte
	    received is different from the byte expected."
    ::= { rasPortEntry 2 }

rasPortBufferOverrunErrors OBJECT-TYPE
    SYNTAX     Gauge32
    MAX-ACCESS read-only
    STATUS     current
    DESCRIPTION
	    "The total number of Buffer Overrun Errors for
	    this connection.  Buffer Overrun Errors when
	    the software cannot handle the rate at which
	    data is received."
    ::= { rasPortEntry 3 }

rasPortBytesReceived OBJECT-TYPE
    SYNTAX     Gauge32
    MAX-ACCESS read-only
    STATUS     current
    DESCRIPTION
	    "The number of bytes received total for this
	    connection."
    ::= { rasPortEntry 4 }

rasPortBytesReceivedPerSec OBJECT-TYPE
    SYNTAX     Gauge32
    MAX-ACCESS read-only
    STATUS     current
    DESCRIPTION
	    "The number of bytes received per second."
    ::= { rasPortEntry 5 }

rasPortBytesTransmitted OBJECT-TYPE
    SYNTAX     Gauge32
    MAX-ACCESS read-only
    STATUS     current
    DESCRIPTION
	    "The number of bytes transmitted total for this
	    connection."
    ::= { rasPortEntry 6 }

rasPortBytesTransmittedPerSec OBJECT-TYPE
    SYNTAX     Gauge32
    MAX-ACCESS read-only
    STATUS     current
    DESCRIPTION
	    "The number of bytes transmitted per second."
    ::= { rasPortEntry 7 }

rasPortCRCErrors OBJECT-TYPE
    SYNTAX     Gauge32
    MAX-ACCESS read-only
    STATUS     current
    DESCRIPTION
	    "The total number of CRC Errors for this
	    connection.  CRC Errors occur when the frame
	    received contains erroneous data."
    ::= { rasPortEntry 8 }

rasPortFramesReceived OBJECT-TYPE
    SYNTAX     Gauge32
    MAX-ACCESS read-only
    STATUS     current
    DESCRIPTION
	    "The number of data frames received total for
	    this connection."
    ::= { rasPortEntry 9 }

rasPortFramesReceivedPerSec OBJECT-TYPE
    SYNTAX     Gauge32
    MAX-ACCESS read-only
    STATUS     current
    DESCRIPTION
	    "The number of frames received per second."
    ::= { rasPortEntry 10 }

rasPortFramesTransmitted OBJECT-TYPE
    SYNTAX     Gauge32
    MAX-ACCESS read-only
    STATUS     current
    DESCRIPTION
	    "The number of data frames transmitted total
	    for this connection."
    ::= { rasPortEntry 11 }

rasPortFramesTransmittedPerSec OBJECT-TYPE
    SYNTAX     Gauge32
    MAX-ACCESS read-only
    STATUS     current
    DESCRIPTION
	    "The number of frames transmitted per second."
    ::= { rasPortEntry 12 }

rasPortPercentCompressionIn OBJECT-TYPE
    SYNTAX     Gauge32
    MAX-ACCESS read-only
    STATUS     current
    DESCRIPTION
	    "The compression ratio for bytes being
	    received."
    ::= { rasPortEntry 13 }

rasPortPercentCompressionOut OBJECT-TYPE
    SYNTAX     Gauge32
    MAX-ACCESS read-only
    STATUS     current
    DESCRIPTION
	    "The compression ratio for bytes being
	    transmitted."
    ::= { rasPortEntry 14 }

rasPortSerialOverrunErrors OBJECT-TYPE
    SYNTAX     Gauge32
    MAX-ACCESS read-only
    STATUS     current
    DESCRIPTION
	    "The total number of Serial Overrun Errors for
	    this connection.  Serial Overrun Errors occur
	    when the hardware cannot handle the rate at
	    which data is received."
    ::= { rasPortEntry 15 }

rasPortTimeoutErrors OBJECT-TYPE
    SYNTAX     Gauge32
    MAX-ACCESS read-only
    STATUS     current
    DESCRIPTION
	    "The total number of Timeout Errors for this
	    connection.  Timeout Errors occur when an
	    expected is not received in time."
    ::= { rasPortEntry 16 }

rasPortTotalErrors OBJECT-TYPE
    SYNTAX     Gauge32
    MAX-ACCESS read-only
    STATUS     current
    DESCRIPTION
	    "The total number of CRC, Timeout, Serial
	    Overrun, Alignment, and Buffer Overrun Errors
	    for this connection."
    ::= { rasPortEntry 17 }

rasPortTotalErrorsPerSec OBJECT-TYPE
    SYNTAX     Gauge32
    MAX-ACCESS read-only
    STATUS     current
    DESCRIPTION
	    "The total number of CRC, Timeout, Serial
	    Overrun, Alignment, and Buffer Overrun Errors
	    per second."
    ::= { rasPortEntry 18 }

redirector OBJECT-IDENTITY
    STATUS     current
    DESCRIPTION
	    "The Redirector performance object consists of
	    counters that monitor network connections
	    originating at the local computer."
    ::= { advanced 70 }

redirBytesReceivedPerSec OBJECT-TYPE
    SYNTAX     Gauge32
    MAX-ACCESS read-only
    STATUS     current
    DESCRIPTION
	    "Bytes Received/sec is the rate of bytes coming
	    in to the Redirector from the network.  It
	    includes all application data as well as
	    network protocol information (such as packet
	    headers)."
    ::= { redirector 1 }

redirBytesTotalPerSec OBJECT-TYPE
    SYNTAX     Gauge32
    MAX-ACCESS read-only
    STATUS     current
    DESCRIPTION
	    "Bytes Total/sec is the rate the Redirector is
	    processing data bytes.  This includes all
	    application and file data in addition to
	    protocol information such as packet headers."
    ::= { redirector 2 }

redirBytesTransmittedPerSec OBJECT-TYPE
    SYNTAX     Gauge32
    MAX-ACCESS read-only
    STATUS     current
    DESCRIPTION
	    "Bytes Transmitted/sec is the rate at which
	    bytes are leaving the Redirector to the
	    network.  It includes all application data as
	    well as network protocol information (such as
	    packet headers and the like)."
    ::= { redirector 3 }

redirConnectsCore OBJECT-TYPE
    SYNTAX     Gauge32
    MAX-ACCESS read-only
    STATUS     current
    DESCRIPTION
	    "Connects Core counts the number of connections
	    you have to servers running the original MS-Net
	    SMB protocol, including MS-Net itself and Xenix
	    and VAX's."
    ::= { redirector 4 }

redirConnectsLanManager20 OBJECT-TYPE
    SYNTAX     Gauge32
    MAX-ACCESS read-only
    STATUS     current
    DESCRIPTION
	    "Connects LAN Manager 2.0 counts connections to
	    LAN Manager 2.0 servers, including LMX
	    servers."
    ::= { redirector 5 }

redirConnectsLanManager21 OBJECT-TYPE
    SYNTAX     Gauge32
    MAX-ACCESS read-only
    STATUS     current
    DESCRIPTION
	    "Connects LAN Manager 2.1 counts connections to
	    LAN Manager 2.1 servers, including LMX
	    servers."
    ::= { redirector 6 }

redirConnectsWindowsNT OBJECT-TYPE
    SYNTAX     Gauge32
    MAX-ACCESS read-only
    STATUS     current
    DESCRIPTION
	    "Connects Windows NT counts the connections to
	    Windows NT computers.  Good choice!"
    ::= { redirector 7 }

redirCurrentCommands OBJECT-TYPE
    SYNTAX     Gauge32
    MAX-ACCESS read-only
    STATUS     current
    DESCRIPTION
	    "Current Commands counts the number of requests
	    to the Redirector that are currently queued for
	    service.  If this number is much larger than
	    the number of network adapter cards installed
	    in the computer, then the network(s) and/or the
	    server(s) being accessed are seriously
	    bottlenecked."
    ::= { redirector 8 }

redirFileDataOperationsPerSec OBJECT-TYPE
    SYNTAX     Gauge32
    MAX-ACCESS read-only
    STATUS     current
    DESCRIPTION
	    "File Data Operations/sec is the rate the
	    Redirector is processing data operations.  One
	    operation includes (hopefully) many bytes.	We
	    say hopefully here because each operation has
	    overhead.  You can determine the efficiency of
	    this path by dividing the Bytes/sec by this
	    counter to determine the average number of
	    bytes transferred/operation."
    ::= { redirector 9 }

redirFileReadOperationsPerSec OBJECT-TYPE
    SYNTAX     Gauge32
    MAX-ACCESS read-only
    STATUS     current
    DESCRIPTION
	    "File Read Operations/sec is the rate at which
	    applications are asking the Redirector for
	    data.  Each call to a file system or similar
	    Application Program Interface (API) call counts
	    as one operation."
    ::= { redirector 10 }

redirFileWriteOperationsPerSec OBJECT-TYPE
    SYNTAX     Gauge32
    MAX-ACCESS read-only
    STATUS     current
    DESCRIPTION
	    "File Write Operations/sec is the rate at which
	    applications are sending data to the
	    Redirector.  Each call to a file system or
	    similar Application Program Interface (API)
	    call counts as one operation."
    ::= { redirector 11 }

redirNetworkErrorsPerSec OBJECT-TYPE
    SYNTAX     Gauge32
    MAX-ACCESS read-only
    STATUS     current
    DESCRIPTION
	    "Network Errors/sec counts serious unexpected
	    errors that generally indicate the Redirector
	    and one or more Servers are having serious
	    communication difficulties.  For example an SMB
	    (Server Manager Block) protocol error will
	    generate a Network Error.  These result in an
	    entry in the system Event Log, so look there
	    for details."
    ::= { redirector 12 }

redirPacketsReceivedPerSec OBJECT-TYPE
    SYNTAX     Gauge32
    MAX-ACCESS read-only
    STATUS     current
    DESCRIPTION
	    "Packets Received/sec is the rate at which the
	    Redirector is receiving packets (also called
	    SMBs or Server Message Blocks).  Network
	    transmissions are divided into packets.  The
	    average number of bytes received in a packet
	    can be obtained by dividing Bytes Received/sec
	    by this counter.  Some packets received might
	    not contain incoming data, for example an
	    acknowledgment to a write made by the
	    Redirector would count as an incoming packet."
    ::= { redirector 13 }

redirPacketsTransmittedPerSec OBJECT-TYPE
    SYNTAX     Gauge32
    MAX-ACCESS read-only
    STATUS     current
    DESCRIPTION
	    "Packets Transmitted/sec is the rate at which
	    the Redirector is sending packets (also called
	    SMBs or Server Message Blocks).  Network
	    transmissions are divided into packets.  The
	    average number of bytes transmitted in a packet
	    can be obtained by dividing Bytes
	    Transmitted/sec by this counter."
    ::= { redirector 14 }

redirPacketsPerSec OBJECT-TYPE
    SYNTAX     Gauge32
    MAX-ACCESS read-only
    STATUS     current
    DESCRIPTION
	    "Packets/sec is the rate the Redirector is
	    processing data packets.  One packet includes
	    (hopefully) many bytes.  We say hopefully here
	    because each packet has protocol overhead.	You
	    can determine the efficiency of this path by
	    dividing the Bytes/sec by this counter to
	    determine the average number of bytes
	    transferred/packet.  You can also divide this
	    counter by Operations/sec to determine the
	    average number of packets per operation,
	    another measure of efficiency."
    ::= { redirector 15 }

redirReadBytesCachePerSec OBJECT-TYPE
    SYNTAX     Gauge32
    MAX-ACCESS read-only
    STATUS     current
    DESCRIPTION
	    "Read Bytes Cache/sec is the rate at which
	    applications are accessing the file system
	    cache by using the Redirector.  Some of these
	    data requests are satisfied by retrieving the
	    data from the cache.  Requests that miss the
	    Cache cause a page fault (see Read Bytes
	    Paging/sec)."
    ::= { redirector 16 }

redirReadBytesNetworkPerSec OBJECT-TYPE
    SYNTAX     Gauge32
    MAX-ACCESS read-only
    STATUS     current
    DESCRIPTION
	    "Read Bytes Network/sec is the rate at which
	    applications are reading data across the
	    network. This occurs when data sought in the
	    file system cache is not found there and must
	    be retrieved from the network.  Dividing this
	    value by Bytes Received/sec indicates the
	    proportion of application data traveling across
	    the network. (see Bytes Received/sec)."
    ::= { redirector 17 }

redirReadBytesNonPagingPerSec OBJECT-TYPE
    SYNTAX     Gauge32
    MAX-ACCESS read-only
    STATUS     current
    DESCRIPTION
	    "Read Bytes Non-Paging/sec are those bytes read
	    by the Redirector in response to normal file
	    requests by an application when they are
	    redirected to come from another computer.  In
	    addition to file requests, this counter
	    includes other methods of reading across the
	    network such as Named Pipes and Transactions. 
	    This counter does not count network protocol
	    information, just application data."
    ::= { redirector 18 }

redirReadBytesPagingPerSec OBJECT-TYPE
    SYNTAX     Gauge32
    MAX-ACCESS read-only
    STATUS     current
    DESCRIPTION
	    "Read Bytes Paging/sec is the rate at which the
	    Redirector is attempting to read bytes in
	    response to page faults.  Page faults are
	    caused by loading of modules (such as programs
	    and libraries), by a miss in the Cache (see
	    Read Bytes Cache/sec), or by files directly
	    mapped into the address space of applications
	    (a high-performance feature of Windows NT)."
    ::= { redirector 19 }

redirReadOperationsRandomPerSec OBJECT-TYPE
    SYNTAX     Gauge32
    MAX-ACCESS read-only
    STATUS     current
    DESCRIPTION
	    "Read Operations Random/sec counts the rate at
	    which, on a file-by-file basis, reads are made
	    that are not sequential.  If a read is made
	    using a particular file handle, and then is
	    followed by another read that is not
	    immediately the contiguous next byte, this
	    counter is incremented by one."
    ::= { redirector 20 }

redirReadPacketsSmallPerSec OBJECT-TYPE
    SYNTAX     Gauge32
    MAX-ACCESS read-only
    STATUS     current
    DESCRIPTION
	    "Read Packets Small/sec is the rate at which
	    reads less than one-fourth of the server's
	    negotiated buffer size are made by
	    applications.  Too many of these could indicate
	    a waste of buffers on the server.  This counter
	    is incremented once for each read. It does not
	    count packets."
    ::= { redirector 21 }

redirReadPacketsPerSec OBJECT-TYPE
    SYNTAX     Gauge32
    MAX-ACCESS read-only
    STATUS     current
    DESCRIPTION
	    "Read Packets/sec is the rate at which read
	    packets are being placed on the network.  Each
	    time a single packet is sent with a request to
	    read data remotely, this counter is incremented
	    by one."
    ::= { redirector 22 }

redirReadsDeniedPerSec OBJECT-TYPE
    SYNTAX     Gauge32
    MAX-ACCESS read-only
    STATUS     current
    DESCRIPTION
	    "Reads Denied/sec is the rate at which the
	    server is unable to accommodate requests for
	    Raw Reads.	When a read is much larger than the
	    server's negotiated buffer size, the Redirector
	    requests a Raw Read which, if granted, would
	    permit the transfer of the data without lots of
	    protocol overhead on each packet.  To
	    accomplish this the server must lock out other
	    requests, so the request is denied if the
	    server is really busy."
    ::= { redirector 23 }

redirReadsLargePerSec OBJECT-TYPE
    SYNTAX     Gauge32
    MAX-ACCESS read-only
    STATUS     current
    DESCRIPTION
	    "Reads Large/sec is the rate at which reads
	    over 2 times the server's negotiated buffer
	    size are made by applications.  Too many of
	    these could place a strain on server resources.
	     This counter is incremented once for each
	    read. It does not count packets."
    ::= { redirector 24 }

redirServerDisconnects OBJECT-TYPE
    SYNTAX     Gauge32
    MAX-ACCESS read-only
    STATUS     current
    DESCRIPTION
	    "Server Disconnects counts the number of times
	    a Server has disconnected your Redirector.	See
	    also Server Reconnects."
    ::= { redirector 25 }

redirServerReconnects OBJECT-TYPE
    SYNTAX     Gauge32
    MAX-ACCESS read-only
    STATUS     current
    DESCRIPTION
	    "Server Reconnects counts the number of times
	    your Redirector has had to reconnect to a
	    server in order to complete a new active
	    request.  You can be disconnected by the Server
	    if you remain inactive for too long.  Locally
	    even if all your remote files are closed, the
	    Redirector will keep your connections intact
	    for (nominally) ten minutes.  Such inactive
	    connections are called Dormant Connections. 
	    Reconnecting is expensive in time."
    ::= { redirector 26 }

redirServerSessions OBJECT-TYPE
    SYNTAX     Gauge32
    MAX-ACCESS read-only
    STATUS     current
    DESCRIPTION
	    "Server Sessions counts the total number of
	    security objects the Redirector has managed. 
	    For example, a logon to a server followed by a
	    network access to the same server will
	    establish one connection, but two sessions."
    ::= { redirector 27 }

redirServerSessionsHung OBJECT-TYPE
    SYNTAX     Gauge32
    MAX-ACCESS read-only
    STATUS     current
    DESCRIPTION
	    "Server Sessions Hung counts the number of
	    active sessions that are timed out and unable
	    to proceed due to a lack of response from the
	    remote server."
    ::= { redirector 28 }

redirWriteBytesCachePerSec OBJECT-TYPE
    SYNTAX     Gauge32
    MAX-ACCESS read-only
    STATUS     current
    DESCRIPTION
	    "Write Bytes Cache/sec is the rate at which
	    applications on your computer are writing to
	    the file system cache by using the Redirector. 
	    The data might not leave your computer
	    immediately; it can be retained in the cache
	    for further modification before being written
	    to the network.  This saves network traffic. 
	    Each write of a byte into the cache is counted
	    here."
    ::= { redirector 29 }

redirWriteBytesNetworkPerSec OBJECT-TYPE
    SYNTAX     Gauge32
    MAX-ACCESS read-only
    STATUS     current
    DESCRIPTION
	    "Write Bytes Network/sec is the rate at which
	    applications are writing data across the
	    network. This occurs when the file system cache
	    is bypassed, such as for Named Pipes or
	    Transactions, or when the cache writes the
	    bytes to disk to make room for other data. 
	    Dividing this counter by Bytes Transmitted/sec
	    will indicate the proportion of application
	    data being to the network (see Transmitted
	    Bytes/sec)."
    ::= { redirector 30 }

redirWriteBytesNonPagingPerSec OBJECT-TYPE
    SYNTAX     Gauge32
    MAX-ACCESS read-only
    STATUS     current
    DESCRIPTION
	    "Write Bytes Non-Paging/sec is the rate at
	    which bytes are written by the Redirector in
	    response to normal file outputs by an
	    application when they are redirected to another
	    computer.  In addition to file requests, this
	    count includes other methods of writing across
	    the network, such as Named Pipes and
	    Transactions.  This counter does not count
	    network protocol information, just application
	    data."
    ::= { redirector 31 }

redirWriteBytesPagingPerSec OBJECT-TYPE
    SYNTAX     Gauge32
    MAX-ACCESS read-only
    STATUS     current
    DESCRIPTION
	    "Write Bytes Paging/sec is the rate at which
	    the Redirector is attempting to write bytes
	    changed in the pages being used by
	    applications.  The program data changed by
	    modules (such as programs and libraries) that
	    were loaded over the network are 'paged out'
	    when no longer needed.  Other output pages come
	    from the file system cache (see Write Bytes
	    Cache/sec)."
    ::= { redirector 32 }

redirWriteOperationsRandomPerSec OBJECT-TYPE
    SYNTAX     Gauge32
    MAX-ACCESS read-only
    STATUS     current
    DESCRIPTION
	    "Write Operations Random/sec is the rate at
	    which, on a file-by-file basis, writes are made
	    that are not sequential.  If a write is made
	    using a particular file handle, and then is
	    followed by another write that is not
	    immediately the next contiguous byte, this
	    counter is incremented by one."
    ::= { redirector 33 }

redirWritePacketsSmallPerSec OBJECT-TYPE
    SYNTAX     Gauge32
    MAX-ACCESS read-only
    STATUS     current
    DESCRIPTION
	    "Write Packets Small/sec is the rate at which
	    writes are made by applications that are less
	    than one-fourth of the server's negotiated
	    buffer size.  Too many of these could indicate
	    a waste of buffers on the server.  This counter
	    is incremented once for each write: it counts
	    writes, not packets."
    ::= { redirector 34 }

redirWritePacketsPerSec OBJECT-TYPE
    SYNTAX     Gauge32
    MAX-ACCESS read-only
    STATUS     current
    DESCRIPTION
	    "Write Packets/sec is the rate at which writes
	    are being sent to the network.  Each time a
	    single packet is sent with a request to write
	    remote data, this counter is incremented by
	    one."
    ::= { redirector 35 }

redirWritesDeniedPerSec OBJECT-TYPE
    SYNTAX     Gauge32
    MAX-ACCESS read-only
    STATUS     current
    DESCRIPTION
	    "Writes Denied/sec is the rate at which the
	    server is unable to accommodate requests for
	    Raw Writes.  When a write is much larger than
	    the server's negotiated buffer size, the
	    Redirector requests a Raw Write which, if
	    granted, would permit the transfer of the data
	    without lots of protocol overhead on each
	    packet.  To accomplish this the server must
	    lock out other requests, so the request is
	    denied if the server is really busy."
    ::= { redirector 36 }

redirWritesLargePerSec OBJECT-TYPE
    SYNTAX     Gauge32
    MAX-ACCESS read-only
    STATUS     current
    DESCRIPTION
	    "Writes Large/sec is the rate at which writes
	    are made by applications that are over 2 times
	    the server's negotiated buffer size.  Too many
	    of these could place a strain on server
	    resources.	This counter is incremented once
	    for each write: it counts writes, not packets."
    ::= { redirector 37 }

rsvpInterfacesTable OBJECT-TYPE
    SYNTAX     SEQUENCE OF RSVPInterfacesEntry
    MAX-ACCESS not-accessible
    STATUS     current
    DESCRIPTION
	    "ACS/RSVP Interfaces performance object
	    counters report statistics about RSVP activity,
	    flow, bandwidth, RSVP messages sent, and so on.
	    The ACS/RSVP Interfaces object is available if
	    ACS is running and there is an object for each
	    IP address on the system."
    ::= { advanced 71 }

rsvpInterfacesEntry OBJECT-TYPE
    SYNTAX     RSVPInterfacesEntry
    MAX-ACCESS not-accessible
    STATUS     current
    DESCRIPTION
	    "Performance information for one particular
	    instance of 'RSVP Interfaces' object."
    INDEX      { rsvpIfInstance }
    ::= { rsvpInterfacesTable 1 }

RSVPInterfacesEntry ::= SEQUENCE {
    rsvpIfInstance InstanceName,
    rsvpIfBlockedRESVs Gauge32,
    rsvpIfGeneralFailures Gauge32,
    rsvpIfMaximumAdmittedBandwidth Gauge32,
    rsvpIfNumOfActiveFlows Gauge32,
    rsvpIfNumOfIncomingMsgsDropped Gauge32,
    rsvpIfNumOfOutgoingMsgsDropped Gauge32,
    rsvpIfPATHERRMsgsReceived Gauge32,
    rsvpIfPATHERRMsgsSent Gauge32,
    rsvpIfPATHTEARMsgsReceived Gauge32,
    rsvpIfPATHTEARMsgsSent Gauge32,
    rsvpIfPATHMsgsReceived Gauge32,
    rsvpIfPATHMsgsSent Gauge32,
    rsvpIfPATHStateBlockTimeouts Gauge32,
    rsvpIfPolicyControlFailures Gauge32,
    rsvpIfRESVCONFIRMMsgsReceived Gauge32,
    rsvpIfRESVCONFIRMMsgsSent Gauge32,
    rsvpIfRESVERRMsgsReceived Gauge32,
    rsvpIfRESVERRMsgsSent Gauge32,
    rsvpIfRESVTEARMsgsReceived Gauge32,
    rsvpIfRESVTEARMsgsSent Gauge32,
    rsvpIfRESVMsgsReceived Gauge32,
    rsvpIfRESVMsgsSent Gauge32,
    rsvpIfRESVStateBlockTimeouts Gauge32,
    rsvpIfReceiveMsgsErrorsBigMsgs Gauge32,
    rsvpIfReceiveMsgsErrorsNoMemory Gauge32,
    rsvpIfReservedBandwidth Gauge32,
    rsvpIfResourceControlFailures Gauge32,
    rsvpIfSendMsgsErrorsBigMsgs Gauge32,
    rsvpIfSendMsgsErrorsNoMemory Gauge32,
    rsvpIfSignalingBytesReceived Gauge32,
    rsvpIfSignalingBytesSent Gauge32
}

rsvpIfInstance OBJECT-TYPE
    SYNTAX     InstanceName
    MAX-ACCESS read-only
    STATUS     current
    DESCRIPTION
	    "Instance name."
    ::= { rsvpInterfacesEntry 1 }

rsvpIfBlockedRESVs OBJECT-TYPE
    SYNTAX     Gauge32
    MAX-ACCESS read-only
    STATUS     current
    DESCRIPTION
	    "Shows the number of blockaded reservations
	    that failed due to failed reservations that
	    have not been removed from this node. For more
	    information about blockade states, see RFC
	    2205."
    ::= { rsvpInterfacesEntry 2 }

rsvpIfGeneralFailures OBJECT-TYPE
    SYNTAX     Gauge32
    MAX-ACCESS read-only
    STATUS     current
    DESCRIPTION
	    "Shows the total number of non-admission
	    control errors that have occurred on this
	    interface. For more information about the other
	    traffic control failures, see RFC 2205."
    ::= { rsvpInterfacesEntry 3 }

rsvpIfMaximumAdmittedBandwidth OBJECT-TYPE
    SYNTAX     Gauge32
    MAX-ACCESS read-only
    STATUS     current
    DESCRIPTION
	    "Shows the highest amount of allocated
	    bandwidth admitted on the interface during the
	    period in which the ACS has been running."
    ::= { rsvpInterfacesEntry 4 }

rsvpIfNumOfActiveFlows OBJECT-TYPE
    SYNTAX     Gauge32
    MAX-ACCESS read-only
    STATUS     current
    DESCRIPTION
	    "Shows the number of reserved flows that are
	    currently installed and maintained by RSVP on
	    this interface."
    ::= { rsvpInterfacesEntry 5 }

rsvpIfNumOfIncomingMsgsDropped OBJECT-TYPE
    SYNTAX     Gauge32
    MAX-ACCESS read-only
    STATUS     current
    DESCRIPTION
	    "Number of incoming messages dropped due to
	    badly constructed RSVP objects etc."
    ::= { rsvpInterfacesEntry 6 }

rsvpIfNumOfOutgoingMsgsDropped OBJECT-TYPE
    SYNTAX     Gauge32
    MAX-ACCESS read-only
    STATUS     current
    DESCRIPTION
	    "Number of outgoing messages dropped"
    ::= { rsvpInterfacesEntry 7 }

rsvpIfPATHERRMsgsReceived OBJECT-TYPE
    SYNTAX     Gauge32
    MAX-ACCESS read-only
    STATUS     current
    DESCRIPTION
	    "Shows the total number of PATH error messages
	    received on this interface. This number
	    indicates the number of times that a PATH has
	    been rejected by a remote host."
    ::= { rsvpInterfacesEntry 8 }

rsvpIfPATHERRMsgsSent OBJECT-TYPE
    SYNTAX     Gauge32
    MAX-ACCESS read-only
    STATUS     current
    DESCRIPTION
	    "Shows the total number of PATH ERR messages
	    that were sent by the ACS/RSVP service
	    rejecting incoming PATH messages."
    ::= { rsvpInterfacesEntry 9 }

rsvpIfPATHTEARMsgsReceived OBJECT-TYPE
    SYNTAX     Gauge32
    MAX-ACCESS read-only
    STATUS     current
    DESCRIPTION
	    "Shows the total number of PATH TEAR messages
	    that have been received on the interface. A
	    PATH-TEAR message removes the PATH state along
	    the route."
    ::= { rsvpInterfacesEntry 10 }

rsvpIfPATHTEARMsgsSent OBJECT-TYPE
    SYNTAX     Gauge32
    MAX-ACCESS read-only
    STATUS     current
    DESCRIPTION
	    "Shows the total number of PATH TEAR messages
	    that were sent on the interface to tear down an
	    RSVP PATH state in the network. A PATH-ERR
	    messages indicates an error in response to the
	    PATH message."
    ::= { rsvpInterfacesEntry 11 }

rsvpIfPATHMsgsReceived OBJECT-TYPE
    SYNTAX     Gauge32
    MAX-ACCESS read-only
    STATUS     current
    DESCRIPTION
	    "Shows the total number of PATH messages that
	    have been received on this interface."
    ::= { rsvpInterfacesEntry 12 }

rsvpIfPATHMsgsSent OBJECT-TYPE
    SYNTAX     Gauge32
    MAX-ACCESS read-only
    STATUS     current
    DESCRIPTION
	    "Shows the total number of PATH messages that
	    were sent by the ACS/RSVP service on this the
	    interface."
    ::= { rsvpInterfacesEntry 13 }

rsvpIfPATHStateBlockTimeouts OBJECT-TYPE
    SYNTAX     Gauge32
    MAX-ACCESS read-only
    STATUS     current
    DESCRIPTION
	    "Shows the total number of times that the RSVP
	    PATH state timed out. This happens when no PATH
	    messages are received within the designated
	    timeout period. This error message can be
	    caused by a route change."
    ::= { rsvpInterfacesEntry 14 }

rsvpIfPolicyControlFailures OBJECT-TYPE
    SYNTAX     Gauge32
    MAX-ACCESS read-only
    STATUS     current
    DESCRIPTION
	    "Shows the total number of RSVP requests that
	    are not admitted on this interface due to a
	    conflict with policy settings."
    ::= { rsvpInterfacesEntry 15 }

rsvpIfRESVCONFIRMMsgsReceived OBJECT-TYPE
    SYNTAX     Gauge32
    MAX-ACCESS read-only
    STATUS     current
    DESCRIPTION
	    "Shows the total number of RESV CONFIRM
	    messages that have been received by the
	    interface."
    ::= { rsvpInterfacesEntry 16 }

rsvpIfRESVCONFIRMMsgsSent OBJECT-TYPE
    SYNTAX     Gauge32
    MAX-ACCESS read-only
    STATUS     current
    DESCRIPTION
	    "Shows the total number of RESV CONFIRM
	    messages that were sent on this interface in
	    response to RESV messages sent from remote
	    hosts."
    ::= { rsvpInterfacesEntry 17 }

rsvpIfRESVERRMsgsReceived OBJECT-TYPE
    SYNTAX     Gauge32
    MAX-ACCESS read-only
    STATUS     current
    DESCRIPTION
	    "Shows the total number of RESV ERR messages
	    that were sent on this interface by the
	    ACS/RSVP service. rejecting incoming RESV
	    messages. A RESV-ERR message indicates an error
	    in response to the RESV."
    ::= { rsvpInterfacesEntry 18 }

rsvpIfRESVERRMsgsSent OBJECT-TYPE
    SYNTAX     Gauge32
    MAX-ACCESS read-only
    STATUS     current
    DESCRIPTION
	    "Shows the total number of RESV errors that
	    were sent on this interface. This number
	    indicates how many reservations have been
	    rejected by the network."
    ::= { rsvpInterfacesEntry 19 }

rsvpIfRESVTEARMsgsReceived OBJECT-TYPE
    SYNTAX     Gauge32
    MAX-ACCESS read-only
    STATUS     current
    DESCRIPTION
	    "Shows the total number of RESV TEAR messages
	    that have been received on the interface. A
	    RESV-TEAR message removes the reservation along
	    the route."
    ::= { rsvpInterfacesEntry 20 }

rsvpIfRESVTEARMsgsSent OBJECT-TYPE
    SYNTAX     Gauge32
    MAX-ACCESS read-only
    STATUS     current
    DESCRIPTION
	    "Shows the total number of RESV TEAR messages
	    that were sent on the interface to tear down a
	    RESV state in the network."
    ::= { rsvpInterfacesEntry 21 }

rsvpIfRESVMsgsReceived OBJECT-TYPE
    SYNTAX     Gauge32
    MAX-ACCESS read-only
    STATUS     current
    DESCRIPTION
	    "Shows the total number of RESV messages that
	    have been received on this interface."
    ::= { rsvpInterfacesEntry 22 }

rsvpIfRESVMsgsSent OBJECT-TYPE
    SYNTAX     Gauge32
    MAX-ACCESS read-only
    STATUS     current
    DESCRIPTION
	    "Shows the total number of RESV messages that
	    were sent by the ACS/RSVP service sent on this
	    the interface"
    ::= { rsvpInterfacesEntry 23 }

rsvpIfRESVStateBlockTimeouts OBJECT-TYPE
    SYNTAX     Gauge32
    MAX-ACCESS read-only
    STATUS     current
    DESCRIPTION
	    "Shows the total number of times that the RSVP
	    RESV state timed out. This happens when no RESV
	    messages are received within the designated
	    timeout period. This error message can be
	    caused by a route change."
    ::= { rsvpInterfacesEntry 24 }

rsvpIfReceiveMsgsErrorsBigMsgs OBJECT-TYPE
    SYNTAX     Gauge32
    MAX-ACCESS read-only
    STATUS     current
    DESCRIPTION
	    "Shows the total number of outgoing RSVP
	    messages that were dropped because they were
	    bigger than the maximum configured RSVP message
	    size."
    ::= { rsvpInterfacesEntry 25 }

rsvpIfReceiveMsgsErrorsNoMemory OBJECT-TYPE
    SYNTAX     Gauge32
    MAX-ACCESS read-only
    STATUS     current
    DESCRIPTION
	    "Shows the total number of outgoing RSVP
	    messages that were dropped due to insufficient
	    memory."
    ::= { rsvpInterfacesEntry 26 }

rsvpIfReservedBandwidth OBJECT-TYPE
    SYNTAX     Gauge32
    MAX-ACCESS read-only
    STATUS     current
    DESCRIPTION
	    "Shows the reserved bandwidth for this
	    interface, in bits per second."
    ::= { rsvpInterfacesEntry 27 }

rsvpIfResourceControlFailures OBJECT-TYPE
    SYNTAX     Gauge32
    MAX-ACCESS read-only
    STATUS     current
    DESCRIPTION
	    "Shows the number of reservations that failed
	    due to the lack of resources."
    ::= { rsvpInterfacesEntry 28 }

rsvpIfSendMsgsErrorsBigMsgs OBJECT-TYPE
    SYNTAX     Gauge32
    MAX-ACCESS read-only
    STATUS     current
    DESCRIPTION
	    "Shows the total number of outgoing RSVP
	    messages that were dropped because they were
	    bigger than the maximum configured RSVP message
	    size."
    ::= { rsvpInterfacesEntry 29 }

rsvpIfSendMsgsErrorsNoMemory OBJECT-TYPE
    SYNTAX     Gauge32
    MAX-ACCESS read-only
    STATUS     current
    DESCRIPTION
	    "Shows the total number of outgoing RSVP
	    messages that were dropped due to insufficient
	    memory."
    ::= { rsvpInterfacesEntry 30 }

rsvpIfSignalingBytesReceived OBJECT-TYPE
    SYNTAX     Gauge32
    MAX-ACCESS read-only
    STATUS     current
    DESCRIPTION
	    "Shows the total RSVP signaling traffic, in
	    bytes, that have been received by the ACS/RSVP
	    service on this interface."
    ::= { rsvpInterfacesEntry 31 }

rsvpIfSignalingBytesSent OBJECT-TYPE
    SYNTAX     Gauge32
    MAX-ACCESS read-only
    STATUS     current
    DESCRIPTION
	    "Shows the total RSVP signaling traffic, in
	    bytes, that were sent by the ACS/RSVP service
	    on this interface."
    ::= { rsvpInterfacesEntry 32 }

rsvpServiceTable OBJECT-TYPE
    SYNTAX     SEQUENCE OF RSVPServiceEntry
    MAX-ACCESS not-accessible
    STATUS     current
    DESCRIPTION
	    "The ACS/RSVP Service performance object
	    counters report statistics about Resource
	    Reservation Protocol (RSVP) and Quality of
	    Service (QoS) Admission Control (ACS) activity,
	    flow, bandwidth, RSVP messages sent, and so on.
	    The ACS/RSVP Service object is available if QoS
	    Admission Control is installed, even if the
	    service is not running."
    ::= { advanced 72 }

rsvpServiceEntry OBJECT-TYPE
    SYNTAX     RSVPServiceEntry
    MAX-ACCESS not-accessible
    STATUS     current
    DESCRIPTION
	    "Performance information for one particular
	    instance of 'RSVP Service' object."
    INDEX      { rsvpSvcInstance }
    ::= { rsvpServiceTable 1 }

RSVPServiceEntry ::= SEQUENCE {
    rsvpSvcInstance InstanceName,
    rsvpSvcBytesInQoSNotifications Gauge32,
    rsvpSvcFailedQoSRequests Gauge32,
    rsvpSvcFailedQoSSends Gauge32,
    rsvpSvcNetworkInterfaces Gauge32,
    rsvpSvcNetworkSockets Gauge32,
    rsvpSvcQoSClients Gauge32,
    rsvpSvcQoSNotifications Gauge32,
    rsvpSvcQoSenabledReceivers Gauge32,
    rsvpSvcQoSenabledSenders Gauge32,
    rsvpSvcRSVPSessions Gauge32,
    rsvpSvcTimers Gauge32
}

rsvpSvcInstance OBJECT-TYPE
    SYNTAX     InstanceName
    MAX-ACCESS read-only
    STATUS     current
    DESCRIPTION
	    "Instance name."
    ::= { rsvpServiceEntry 1 }

rsvpSvcBytesInQoSNotifications OBJECT-TYPE
    SYNTAX     Gauge32
    MAX-ACCESS read-only
    STATUS     current
    DESCRIPTION
	    "A running total of the number of bytes
	    delivered in QoS Notifications to QoS-enabled
	    applications."
    ::= { rsvpServiceEntry 2 }

rsvpSvcFailedQoSRequests OBJECT-TYPE
    SYNTAX     Gauge32
    MAX-ACCESS read-only
    STATUS     current
    DESCRIPTION
	    "The number of QoS requests generated by
	    QoS-enabled applications that have been
	    rejected by the RSVP service. Failed QoS
	    requests can be caused by invalid QoS
	    requests."
    ::= { rsvpServiceEntry 3 }

rsvpSvcFailedQoSSends OBJECT-TYPE
    SYNTAX     Gauge32
    MAX-ACCESS read-only
    STATUS     current
    DESCRIPTION
	    "The number of QoS notifications the RSVP
	    service that could not be sent to the QoS
	    applications. Failed QoS sends can be caused by
	    terminated applications."
    ::= { rsvpServiceEntry 4 }

rsvpSvcNetworkInterfaces OBJECT-TYPE
    SYNTAX     Gauge32
    MAX-ACCESS read-only
    STATUS     current
    DESCRIPTION
	    "The number of local network interfaces visible
	    to, and used by the RSVP service."
    ::= { rsvpServiceEntry 5 }

rsvpSvcNetworkSockets OBJECT-TYPE
    SYNTAX     Gauge32
    MAX-ACCESS read-only
    STATUS     current
    DESCRIPTION
	    "The total number of raw sockets opened for the
	    purpose of RSVP signaling."
    ::= { rsvpServiceEntry 6 }

rsvpSvcQoSClients OBJECT-TYPE
    SYNTAX     Gauge32
    MAX-ACCESS read-only
    STATUS     current
    DESCRIPTION
	    "The number of QoS enabled applications
	    currently active."
    ::= { rsvpServiceEntry 7 }

rsvpSvcQoSNotifications OBJECT-TYPE
    SYNTAX     Gauge32
    MAX-ACCESS read-only
    STATUS     current
    DESCRIPTION
	    "The number of QoS notifications delivered to
	    QoS-enabled applications by the QoS RSVP
	    service."
    ::= { rsvpServiceEntry 8 }

rsvpSvcQoSenabledReceivers OBJECT-TYPE
    SYNTAX     Gauge32
    MAX-ACCESS read-only
    STATUS     current
    DESCRIPTION
	    "Indicates the number of RESV messages sent for
	    QoS-enabled receivers. This number increments
	    each time a RESV is refreshed."
    ::= { rsvpServiceEntry 9 }

rsvpSvcQoSenabledSenders OBJECT-TYPE
    SYNTAX     Gauge32
    MAX-ACCESS read-only
    STATUS     current
    DESCRIPTION
	    "Indicates the number of PATH messages sent for
	    QoS-enabled senders. This number increments
	    each time a PATH is refreshed."
    ::= { rsvpServiceEntry 10 }

rsvpSvcRSVPSessions OBJECT-TYPE
    SYNTAX     Gauge32
    MAX-ACCESS read-only
    STATUS     current
    DESCRIPTION
	    "The current number of active RSVP sessions on
	    the RSVP service."
    ::= { rsvpServiceEntry 11 }

rsvpSvcTimers OBJECT-TYPE
    SYNTAX     Gauge32
    MAX-ACCESS read-only
    STATUS     current
    DESCRIPTION
	    "The number of timer events scheduled to take
	    place. Shows the activity level of the RSVP
	    service."
    ::= { rsvpServiceEntry 12 }

server OBJECT-IDENTITY
    STATUS     current
    DESCRIPTION
	    "The Server performance object consists of
	    counters that measure communication between the
	    local computer and the network."
    ::= { advanced 73 }

serverBlockingRequestsRejected OBJECT-TYPE
    SYNTAX     Gauge32
    MAX-ACCESS read-only
    STATUS     current
    DESCRIPTION
	    "The number of times the server has rejected
	    blocking SMBs due to insufficient count of free
	    work items.  Indicates whether the MaxWorkItem
	    or MinFreeWorkItems server parameters might
	    need to be adjusted."
    ::= { server 1 }

serverBytesReceivedPerSec OBJECT-TYPE
    SYNTAX     Gauge32
    MAX-ACCESS read-only
    STATUS     current
    DESCRIPTION
	    "The number of bytes the server has received
	    from the network.  Indicates how busy the
	    server is."
    ::= { server 2 }

serverBytesTotalPerSec OBJECT-TYPE
    SYNTAX     Gauge32
    MAX-ACCESS read-only
    STATUS     current
    DESCRIPTION
	    "The number of bytes the server has sent to and
	    received from the network.	This value provides
	    an overall indication of how busy the server
	    is."
    ::= { server 3 }

serverBytesTransmittedPerSec OBJECT-TYPE
    SYNTAX     Gauge32
    MAX-ACCESS read-only
    STATUS     current
    DESCRIPTION
	    "The number of bytes the server has sent on the
	    network.  Indicates how busy the server is."
    ::= { server 4 }

serverContextBlocksQueuedPerSec OBJECT-TYPE
    SYNTAX     Gauge32
    MAX-ACCESS read-only
    STATUS     current
    DESCRIPTION
	    "Context Blocks Queued per second is the rate
	    at which work context blocks had to be placed
	    on the server's FSP queue to await server
	    action."
    ::= { server 5 }

serverErrorsAccessPermissions OBJECT-TYPE
    SYNTAX     Gauge32
    MAX-ACCESS read-only
    STATUS     current
    DESCRIPTION
	    "The number of times opens on behalf of clients
	    have failed with STATUS_ACCESS_DENIED.  Can
	    indicate whether somebody is randomly
	    attempting to access files in hopes of getting
	    at something that was not properly protected."
    ::= { server 6 }

serverErrorsGrantedAccess OBJECT-TYPE
    SYNTAX     Gauge32
    MAX-ACCESS read-only
    STATUS     current
    DESCRIPTION
	    "The number of times accesses to files opened
	    successfully were denied.  Can indicate
	    attempts to access files without proper access
	    authorization."
    ::= { server 7 }

serverErrorsLogon OBJECT-TYPE
    SYNTAX     Gauge32
    MAX-ACCESS read-only
    STATUS     current
    DESCRIPTION
	    "The number of failed logon attempts to the
	    server.  Can indicate whether password guessing
	    programs are being used to crack the security
	    on the server."
    ::= { server 8 }

serverErrorsSystem OBJECT-TYPE
    SYNTAX     Gauge32
    MAX-ACCESS read-only
    STATUS     current
    DESCRIPTION
	    "The number of times an internal Server Error
	    was detected.  Unexpected errors usually
	    indicate a problem with the Server."
    ::= { server 9 }

serverFileDirectorySearches OBJECT-TYPE
    SYNTAX     Gauge32
    MAX-ACCESS read-only
    STATUS     current
    DESCRIPTION
	    "The number of searches for files currently
	    active in the server.  Indicates current server
	    activity."
    ::= { server 10 }

serverFilesOpen OBJECT-TYPE
    SYNTAX     Gauge32
    MAX-ACCESS read-only
    STATUS     current
    DESCRIPTION
	    "The number of files currently opened in the
	    server.  Indicates current server activity."
    ::= { server 11 }

serverFilesOpenedTotal OBJECT-TYPE
    SYNTAX     Gauge32
    MAX-ACCESS read-only
    STATUS     current
    DESCRIPTION
	    "The number of successful open attempts
	    performed by the server of behalf of clients. 
	    Useful in determining the amount of file I/O,
	    determining overhead for path-based operations,
	    and for determining the effectiveness of open
	    locks."
    ::= { server 12 }

serverLogonTotal OBJECT-TYPE
    SYNTAX     Gauge32
    MAX-ACCESS read-only
    STATUS     current
    DESCRIPTION
	    "Logon Total includes all interactive logons,
	    network logons, service logons, successful
	    logon, and failed logons since the machine is
	    last rebooted."
    ::= { server 13 }

serverLogonPerSec OBJECT-TYPE
    SYNTAX     Gauge32
    MAX-ACCESS read-only
    STATUS     current
    DESCRIPTION
	    "Logon/sec is the rate of all server logons."
    ::= { server 14 }

serverPoolNonpagedBytes OBJECT-TYPE
    SYNTAX     Gauge32
    MAX-ACCESS read-only
    STATUS     current
    DESCRIPTION
	    "The number of bytes of non-pageable computer
	    memory the server is using.  This value is
	    useful for determining the values of the
	    MaxNonpagedMemoryUsage value entry in the
	    Windows NT Registry."
    ::= { server 15 }

serverPoolNonpagedFailures OBJECT-TYPE
    SYNTAX     Gauge32
    MAX-ACCESS read-only
    STATUS     current
    DESCRIPTION
	    "The number of times allocations from nonpaged
	    pool have failed.  Indicates that the
	    computer's physical memory is too small."
    ::= { server 16 }

serverPoolNonpagedPeak OBJECT-TYPE
    SYNTAX     Gauge32
    MAX-ACCESS read-only
    STATUS     current
    DESCRIPTION
	    "The maximum number of bytes of nonpaged pool
	    the server has had in use at any one point. 
	    Indicates how much physical memory the computer
	    should have."
    ::= { server 17 }

serverPoolPagedBytes OBJECT-TYPE
    SYNTAX     Gauge32
    MAX-ACCESS read-only
    STATUS     current
    DESCRIPTION
	    "The number of bytes of pageable computer
	    memory the server is currently using.  Can help
	    in determining good values for the
	    MaxPagedMemoryUsage parameter."
    ::= { server 18 }

serverPoolPagedFailures OBJECT-TYPE
    SYNTAX     Gauge32
    MAX-ACCESS read-only
    STATUS     current
    DESCRIPTION
	    "The number of times allocations from paged
	    pool have failed.  Indicates that the
	    computer's physical memory or paging file are
	    too small."
    ::= { server 19 }

serverPoolPagedPeak OBJECT-TYPE
    SYNTAX     Gauge32
    MAX-ACCESS read-only
    STATUS     current
    DESCRIPTION
	    "The maximum number of bytes of paged pool the
	    server has had allocated.  Indicates the proper
	    sizes of the Page File(s) and physical memory."
    ::= { server 20 }

serverServerSessions OBJECT-TYPE
    SYNTAX     Gauge32
    MAX-ACCESS read-only
    STATUS     current
    DESCRIPTION
	    "The number of sessions currently active in the
	    server.  Indicates current server activity."
    ::= { server 21 }

serverSessionsErroredOut OBJECT-TYPE
    SYNTAX     Gauge32
    MAX-ACCESS read-only
    STATUS     current
    DESCRIPTION
	    "The number of sessions that have been closed
	    due to unexpected error conditions or sessions
	    that have reached the autodisconnect timeout
	    and have been disconnected normally."
    ::= { server 22 }

serverSessionsForcedOff OBJECT-TYPE
    SYNTAX     Gauge32
    MAX-ACCESS read-only
    STATUS     current
    DESCRIPTION
	    "The number of sessions that have been forced
	    to logoff.	Can indicate how many sessions were
	    forced to logoff due to logon time
	    constraints."
    ::= { server 23 }

serverSessionsLoggedOff OBJECT-TYPE
    SYNTAX     Gauge32
    MAX-ACCESS read-only
    STATUS     current
    DESCRIPTION
	    "The number of sessions that have terminated
	    normally.  Useful in interpreting the Sessions
	    Times Out and Sessions Errored Out
	    statistics--allows percentage calculations."
    ::= { server 24 }

serverSessionsTimedOut OBJECT-TYPE
    SYNTAX     Gauge32
    MAX-ACCESS read-only
    STATUS     current
    DESCRIPTION
	    "The number of sessions that have been closed
	    due to their idle time exceeding the
	    AutoDisconnect parameter for the server.  Shows
	    whether the AutoDisconnect setting is helping
	    to conserve resources."
    ::= { server 25 }

serverWorkItemShortages OBJECT-TYPE
    SYNTAX     Gauge32
    MAX-ACCESS read-only
    STATUS     current
    DESCRIPTION
	    "The number of times STATUS_DATA_NOT_ACCEPTED
	    was returned at receive indication time.  This
	    occurs when no work item is available or can be
	    allocated to service the incoming request. 
	    Indicates whether the InitWorkItems or
	    MaxWorkItems parameters might need to be
	    adjusted."
    ::= { server 26 }

serverPoolNonpagedKBytes OBJECT-TYPE
    SYNTAX     Gauge32
    MAX-ACCESS read-only
    STATUS     current
    DESCRIPTION
	    "The number of kilobytes of non-pageable
	    computer memory the server is using.  This
	    value is useful for determining the values of
	    the MaxNonpagedMemoryUsage value entry in the
	    Windows NT Registry."
    ::= { server 27 }

serverPoolNonpagedKBytesPeak OBJECT-TYPE
    SYNTAX     Gauge32
    MAX-ACCESS read-only
    STATUS     current
    DESCRIPTION
	    "The maximum number of kilobytes of nonpaged
	    pool the server has had in use at any one
	    point.  Indicates how much physical memory the
	    computer should have."
    ::= { server 28 }

serverPoolPagedKBytes OBJECT-TYPE
    SYNTAX     Gauge32
    MAX-ACCESS read-only
    STATUS     current
    DESCRIPTION
	    "The number of kilobytes of pageable computer
	    memory the server is currently using.  Can help
	    in determining good values for the
	    MaxPagedMemoryUsage parameter."
    ::= { server 29 }

serverPoolPagedKBytesPeak OBJECT-TYPE
    SYNTAX     Gauge32
    MAX-ACCESS read-only
    STATUS     current
    DESCRIPTION
	    "The maximum number of kilobytes of paged pool
	    the server has had allocated.  Indicates the
	    proper sizes of the Page File(s) and physical
	    memory."
    ::= { server 30 }

serverPoolNonpagedMBytes OBJECT-TYPE
    SYNTAX     Gauge32
    MAX-ACCESS read-only
    STATUS     current
    DESCRIPTION
	    "The number of megabytes of non-pageable
	    computer memory the server is using.  This
	    value is useful for determining the values of
	    the MaxNonpagedMemoryUsage value entry in the
	    Windows NT Registry."
    ::= { server 31 }

serverPoolNonpagedMBytesPeak OBJECT-TYPE
    SYNTAX     Gauge32
    MAX-ACCESS read-only
    STATUS     current
    DESCRIPTION
	    "The maximum number of megabytes of nonpaged
	    pool the server has had in use at any one
	    point.  Indicates how much physical memory the
	    computer should have."
    ::= { server 32 }

serverPoolPagedMBytes OBJECT-TYPE
    SYNTAX     Gauge32
    MAX-ACCESS read-only
    STATUS     current
    DESCRIPTION
	    "The number of megabytes of pageable computer
	    memory the server is currently using.  Can help
	    in determining good values for the
	    MaxPagedMemoryUsage parameter."
    ::= { server 33 }

serverPoolPagedMBytesPeak OBJECT-TYPE
    SYNTAX     Gauge32
    MAX-ACCESS read-only
    STATUS     current
    DESCRIPTION
	    "The maximum number of megabytes of paged pool
	    the server has had allocated.  Indicates the
	    proper sizes of the Page File(s) and physical
	    memory."
    ::= { server 34 }

serverWorkQueuesTable OBJECT-TYPE
    SYNTAX     SEQUENCE OF ServerWorkQueuesEntry
    MAX-ACCESS not-accessible
    STATUS     current
    DESCRIPTION
	    "The Server Work Queues performance object
	    consists of counters that monitor the length of
	    queues and objects in the queues."
    ::= { advanced 74 }

serverWorkQueuesEntry OBJECT-TYPE
    SYNTAX     ServerWorkQueuesEntry
    MAX-ACCESS not-accessible
    STATUS     current
    DESCRIPTION
	    "Performance information for one particular
	    instance of 'Server Work Queues' object."
    INDEX      { swqInstance }
    ::= { serverWorkQueuesTable 1 }

ServerWorkQueuesEntry ::= SEQUENCE {
    swqInstance InstanceName,
    swqActiveThreads Gauge32,
    swqAvailableThreads Gauge32,
    swqAvailableWorkItems Gauge32,
    swqBorrowedWorkItems Gauge32,
    swqBytesReceivedPerSec Gauge32,
    swqBytesSentPerSec Gauge32,
    swqBytesTransferredPerSec Gauge32,
    swqContextBlocksQueuedPerSec Gauge32,
    swqCurrentClients Gauge32,
    swqQueueLength Gauge32,
    swqReadBytesPerSec Gauge32,
    swqReadOperationsPerSec Gauge32,
    swqTotalBytesPerSec Gauge32,
    swqTotalOperationsPerSec Gauge32,
    swqWorkItemShortages Gauge32,
    swqWriteBytesPerSec Gauge32,
    swqWriteOperationsPerSec Gauge32
}

swqInstance OBJECT-TYPE
    SYNTAX     InstanceName
    MAX-ACCESS read-only
    STATUS     current
    DESCRIPTION
	    "Instance name."
    ::= { serverWorkQueuesEntry 1 }

swqActiveThreads OBJECT-TYPE
    SYNTAX     Gauge32
    MAX-ACCESS read-only
    STATUS     current
    DESCRIPTION
	    "Active Threads is the number of threads
	    currently working on a request from the server
	    client for this CPU.  The system keeps this
	    number as low as possible to minimize
	    unnecessary context switching.  This is an
	    instantaneous count for the CPU, not an average
	    over time."
    ::= { serverWorkQueuesEntry 2 }

swqAvailableThreads OBJECT-TYPE
    SYNTAX     Gauge32
    MAX-ACCESS read-only
    STATUS     current
    DESCRIPTION
	    "Available Threads is the number of server
	    threads on this CPU not currently working on
	    requests from a client.  The server dynamically
	    adjusts the number of threads to maximize
	    server performance."
    ::= { serverWorkQueuesEntry 3 }

swqAvailableWorkItems OBJECT-TYPE
    SYNTAX     Gauge32
    MAX-ACCESS read-only
    STATUS     current
    DESCRIPTION
	    "Every request from a client is represented in
	    the server as a 'work item,' and the server
	    maintains a pool of available work items per
	    CPU to speed processing.  This is the
	    instantaneous number of available work items
	    for this CPU.  A sustained near-zero value
	    indicates the need to increase the
	    MinFreeWorkItems registry value for the Server
	    service.  This value will always be 0 in the
	    Blocking Queue instance."
    ::= { serverWorkQueuesEntry 4 }

swqBorrowedWorkItems OBJECT-TYPE
    SYNTAX     Gauge32
    MAX-ACCESS read-only
    STATUS     current
    DESCRIPTION
	    "Every request from a client is represented in
	    the server as a 'work item,' and the server
	    maintains a pool of available work items per
	    CPU to speed processing.  When a CPU runs out
	    of work items, it borrows a free work item from
	    another CPU.  An increasing value of this
	    running counter might indicate the need to
	    increase the 'MaxWorkItems' or
	    'MinFreeWorkItems' registry values for the
	    Server service.  This value will always be 0 in
	    the Blocking Queue instance."
    ::= { serverWorkQueuesEntry 5 }

swqBytesReceivedPerSec OBJECT-TYPE
    SYNTAX     Gauge32
    MAX-ACCESS read-only
    STATUS     current
    DESCRIPTION
	    "The rate at which the Server is receiving
	    bytes from the network clients on this CPU. 
	    This value is a measure of how busy the Server
	    is."
    ::= { serverWorkQueuesEntry 6 }

swqBytesSentPerSec OBJECT-TYPE
    SYNTAX     Gauge32
    MAX-ACCESS read-only
    STATUS     current
    DESCRIPTION
	    "The rate at which the Server is sending bytes
	    to the network clients on this CPU.  This value
	    is a measure of how busy the Server is."
    ::= { serverWorkQueuesEntry 7 }

swqBytesTransferredPerSec OBJECT-TYPE
    SYNTAX     Gauge32
    MAX-ACCESS read-only
    STATUS     current
    DESCRIPTION
	    "The rate at which the Server is sending and
	    receiving bytes with the network clients on
	    this CPU.  This value is a measure of how busy
	    the Server is."
    ::= { serverWorkQueuesEntry 8 }

swqContextBlocksQueuedPerSec OBJECT-TYPE
    SYNTAX     Gauge32
    MAX-ACCESS read-only
    STATUS     current
    DESCRIPTION
	    "Context Blocks Queued per second is the rate
	    at which work context blocks had to be placed
	    on the server's FSP queue to await server
	    action."
    ::= { serverWorkQueuesEntry 9 }

swqCurrentClients OBJECT-TYPE
    SYNTAX     Gauge32
    MAX-ACCESS read-only
    STATUS     current
    DESCRIPTION
	    "Current Clients is the instantaneous count of
	    the clients being serviced by this CPU.  The
	    server actively balances the client load across
	    all of the CPU's in the system.  This value
	    will always be 0 in the Blocking Queue
	    instance."
    ::= { serverWorkQueuesEntry 10 }

swqQueueLength OBJECT-TYPE
    SYNTAX     Gauge32
    MAX-ACCESS read-only
    STATUS     current
    DESCRIPTION
	    "Queue Length is the current length of the
	    server work queue for this CPU.  A sustained
	    queue length greater than four might indicate
	    processor congestion.  This is an instantaneous
	    count, not an average over time."
    ::= { serverWorkQueuesEntry 11 }

swqReadBytesPerSec OBJECT-TYPE
    SYNTAX     Gauge32
    MAX-ACCESS read-only
    STATUS     current
    DESCRIPTION
	    "Read Bytes/sec is the rate the server is
	    reading data from files for the clients on this
	    CPU.  This value is a measure of how busy the
	    Server is."
    ::= { serverWorkQueuesEntry 12 }

swqReadOperationsPerSec OBJECT-TYPE
    SYNTAX     Gauge32
    MAX-ACCESS read-only
    STATUS     current
    DESCRIPTION
	    "Read Operations/sec is the rate the server is
	    performing file read operations for the clients
	    on this CPU.  This value is a measure of how
	    busy the Server is.  This value will always be
	    0 in the Blocking Queue instance."
    ::= { serverWorkQueuesEntry 13 }

swqTotalBytesPerSec OBJECT-TYPE
    SYNTAX     Gauge32
    MAX-ACCESS read-only
    STATUS     current
    DESCRIPTION
	    "Total Bytes/sec is the rate the Server is
	    reading and writing data to and from the files
	    for the clients on this CPU.  This value is a
	    measure of how busy the Server is."
    ::= { serverWorkQueuesEntry 14 }

swqTotalOperationsPerSec OBJECT-TYPE
    SYNTAX     Gauge32
    MAX-ACCESS read-only
    STATUS     current
    DESCRIPTION
	    "Total Operations/sec is the rate the Server is
	    performing file read and file write operations
	    for the clients on this CPU.  This value is a
	    measure of how busy the Server is.	This value
	    will always be 0 in the Blocking Queue
	    instance."
    ::= { serverWorkQueuesEntry 15 }

swqWorkItemShortages OBJECT-TYPE
    SYNTAX     Gauge32
    MAX-ACCESS read-only
    STATUS     current
    DESCRIPTION
	    "Every request from a client is represented in
	    the server as a 'work item,' and the server
	    maintains a pool of available work items per
	    CPU to speed processing.  A sustained value
	    greater than zero indicates the need to
	    increase the 'MaxWorkItems' registry value for
	    the Server service.  This value will always be
	    0 in the Blocking Queue instance."
    ::= { serverWorkQueuesEntry 16 }

swqWriteBytesPerSec OBJECT-TYPE
    SYNTAX     Gauge32
    MAX-ACCESS read-only
    STATUS     current
    DESCRIPTION
	    "Write Bytes/sec is the rate the server is
	    writing data to files for the clients on this
	    CPU.  This value is a measure of how busy the
	    Server is."
    ::= { serverWorkQueuesEntry 17 }

swqWriteOperationsPerSec OBJECT-TYPE
    SYNTAX     Gauge32
    MAX-ACCESS read-only
    STATUS     current
    DESCRIPTION
	    "Write Operations/sec is the rate the server is
	    performing file write operations for the
	    clients on this CPU.  This value is a measure
	    of how busy the Server is.	This value will
	    always be 0 in the Blocking Queue instance."
    ::= { serverWorkQueuesEntry 18 }

smtpNTFSStoreDriverTable OBJECT-TYPE
    SYNTAX     SEQUENCE OF SMTPNTFSStoreDriverEntry
    MAX-ACCESS not-accessible
    STATUS     current
    DESCRIPTION
	    "The SMTP NTFS Store Driver performance object
	    counters describe activity of the Exchange NTFS
	    store driver, which is responsible for message
	    transport to and from the message store."
    ::= { advanced 75 }

smtpNTFSStoreDriverEntry OBJECT-TYPE
    SYNTAX     SMTPNTFSStoreDriverEntry
    MAX-ACCESS not-accessible
    STATUS     current
    DESCRIPTION
	    "Performance information for one particular
	    instance of 'SMTP NTFS Store Driver' object."
    INDEX      { snsdInstance }
    ::= { smtpNTFSStoreDriverTable 1 }

SMTPNTFSStoreDriverEntry ::= SEQUENCE {
    snsdInstance InstanceName,
    snsdMessagesAllocated Gauge32,
    snsdMessagesDeleted Gauge32,
    snsdMessagesEnumerated Gauge32,
    snsdMessagesInTheQueueDirectory Gauge32,
    snsdOpenMessageBodies Gauge32,
    snsdOpenMessageStreams Gauge32
}

snsdInstance OBJECT-TYPE
    SYNTAX     InstanceName
    MAX-ACCESS read-only
    STATUS     current
    DESCRIPTION
	    "Instance name."
    ::= { smtpNTFSStoreDriverEntry 1 }

snsdMessagesAllocated OBJECT-TYPE
    SYNTAX     Gauge32
    MAX-ACCESS read-only
    STATUS     current
    DESCRIPTION
	    "The total number of messages allocated."
    ::= { smtpNTFSStoreDriverEntry 2 }

snsdMessagesDeleted OBJECT-TYPE
    SYNTAX     Gauge32
    MAX-ACCESS read-only
    STATUS     current
    DESCRIPTION
	    "The total number of messages deleted."
    ::= { smtpNTFSStoreDriverEntry 3 }

snsdMessagesEnumerated OBJECT-TYPE
    SYNTAX     Gauge32
    MAX-ACCESS read-only
    STATUS     current
    DESCRIPTION
	    "The total number of messages enumerated during
	    startup."
    ::= { smtpNTFSStoreDriverEntry 4 }

snsdMessagesInTheQueueDirectory OBJECT-TYPE
    SYNTAX     Gauge32
    MAX-ACCESS read-only
    STATUS     current
    DESCRIPTION
	    "The current number of messages in the queue
	    directory."
    ::= { smtpNTFSStoreDriverEntry 5 }

snsdOpenMessageBodies OBJECT-TYPE
    SYNTAX     Gauge32
    MAX-ACCESS read-only
    STATUS     current
    DESCRIPTION
	    "The current number of open message bodies."
    ::= { smtpNTFSStoreDriverEntry 6 }

snsdOpenMessageStreams OBJECT-TYPE
    SYNTAX     Gauge32
    MAX-ACCESS read-only
    STATUS     current
    DESCRIPTION
	    "The current number of open message streams."
    ::= { smtpNTFSStoreDriverEntry 7 }

smtpServerTable OBJECT-TYPE
    SYNTAX     SEQUENCE OF SMTPServerEntry
    MAX-ACCESS not-accessible
    STATUS     current
    DESCRIPTION
	    "The SMTP Server performance object monitors
	    message activity generated by the Simple Mail
	    Transport Protocol (SMTP) service, that can be
	    installed as part of Windows 2000 Server."
    ::= { advanced 76 }

smtpServerEntry OBJECT-TYPE
    SYNTAX     SMTPServerEntry
    MAX-ACCESS not-accessible
    STATUS     current
    DESCRIPTION
	    "Performance information for one particular
	    instance of 'SMTP Server' object."
    INDEX      { smtpSrvrInstance }
    ::= { smtpServerTable 1 }

SMTPServerEntry ::= SEQUENCE {
    smtpSrvrInstance InstanceName,
    smtpSrvrPercentRcpntsLocal Gauge32,
    smtpSrvrPercentRcpntsRemote Gauge32,
    smtpSrvrAvgRcpntsPerMsgRcvd Gauge32,
    smtpSrvrAvgRcpntsPerMsgSent Gauge32,
    smtpSrvrAvgRetriesPerMsgDlvrd Gauge32,
    smtpSrvrAvgRetriesPerMsgSent Gauge32,
    smtpSrvrBadMailMsgsBadPickupFile Gauge32,
    smtpSrvrBadMailMsgsGeneralFail Gauge32,
    smtpSrvrBadMailMsgsHopCntExceed Gauge32,
    smtpSrvrBadMailMsgsNDROfDSN Gauge32,
    smtpSrvrBadMailMsgsNoRcpnts Gauge32,
    smtpSrvrBadMailMsgsTrigViaEvent Gauge32,
    smtpSrvrBytesRcvdTotal Gauge32,
    smtpSrvrBytesRcvdPerSec Gauge32,
    smtpSrvrBytesSentTotal Gauge32,
    smtpSrvrBytesSentPerSec Gauge32,
    smtpSrvrBytesTotal Gauge32,
    smtpSrvrBytesTotalPerSec Gauge32,
    smtpSrvrCatAddrLookupCmplt Gauge32,
    smtpSrvrCatAddrLookupCmpltPerSec Gauge32,
    smtpSrvrCatAddrLookups Gauge32,
    smtpSrvrCatAddrLookupsNotFound Gauge32,
    smtpSrvrCatAddrLookupsPerSec Gauge32,
    smtpSrvrCatCatsCmpltd Gauge32,
    smtpSrvrCatCatsCmpltdSuccess Gauge32,
    smtpSrvrCatCatsCmpltdPerSec Gauge32,
    smtpSrvrCatCatsFailDSConnFail Gauge32,
    smtpSrvrCatCatsFailDSLogonFail Gauge32,
    smtpSrvrCatCatsFailOutOfMemory Gauge32,
    smtpSrvrCatCatsFailNonRetryError Gauge32,
    smtpSrvrCatCatsFailRetryError Gauge32,
    smtpSrvrCatCatsFailSinkRetryErr Gauge32,
    smtpSrvrCatCatsInProgress Gauge32,
    smtpSrvrCatLDAPBindFail Gauge32,
    smtpSrvrCatLDAPBinds Gauge32,
    smtpSrvrCatLDAPConnFail Gauge32,
    smtpSrvrCatLDAPConns Gauge32,
    smtpSrvrCatLDAPConnsCurrOpen Gauge32,
    smtpSrvrCatLDAPGeneralCmpltFail Gauge32,
    smtpSrvrCatLDAPPageSrchCmpltFail Gauge32,
    smtpSrvrCatLDAPPagedSrchFail Gauge32,
    smtpSrvrCatLDAPPagedSrchs Gauge32,
    smtpSrvrCatLDAPPagedSrchsCmpltd Gauge32,
    smtpSrvrCatLDAPSrchCmpltFail Gauge32,
    smtpSrvrCatLDAPSrchFail Gauge32,
    smtpSrvrCatLDAPSrchs Gauge32,
    smtpSrvrCatLDAPSrchsAbandoned Gauge32,
    smtpSrvrCatLDAPSrchsCmpltd Gauge32,
    smtpSrvrCatLDAPSrchsCmpltdPerSec Gauge32,
    smtpSrvrCatLDAPSrchsPendingCmplt Gauge32,
    smtpSrvrCatLDAPSrchsPerSec Gauge32,
    smtpSrvrCatMsgsCategorized Gauge32,
    smtpSrvrCatMsgsAborted Gauge32,
    smtpSrvrCatMsgsBifurcated Gauge32,
    smtpSrvrCatMsgsSubmitted Gauge32,
    smtpSrvrCatMsgsSubmittedPerSec Gauge32,
    smtpSrvrCatRcptsNDRdAmbigsAddr Gauge32,
    smtpSrvrCatRcptsNDRdForwardLoop Gauge32,
    smtpSrvrCatRcptsNDRdIllegalAddr Gauge32,
    smtpSrvrCatRcptsNDRdSinkRecipErr Gauge32,
    smtpSrvrCatRcptsNDRdUnresolved Gauge32,
    smtpSrvrCatRcptsNDRdByCategorize Gauge32,
    smtpSrvrCatRcptsAfterCat Gauge32,
    smtpSrvrCatRcptsBeforeCat Gauge32,
    smtpSrvrCatRcptsInCat Gauge32,
    smtpSrvrCatSendersUnresolved Gauge32,
    smtpSrvrCatSendersAmbigsAddr Gauge32,
    smtpSrvrCatMailmsgDupCollisions Gauge32,
    smtpSrvrCategorizerQueueLength Gauge32,
    smtpSrvrConnErrorsPerSec Gauge32,
    smtpSrvrCurrentMsgsInLocalDlvry Gauge32,
    smtpSrvrDNSQueriesTotal Gauge32,
    smtpSrvrDNSQueriesPerSec Gauge32,
    smtpSrvrDirDropsTotal Gauge32,
    smtpSrvrDirDropsPerSec Gauge32,
    smtpSrvrETRNMsgsTotal Gauge32,
    smtpSrvrETRNMsgsPerSec Gauge32,
    smtpSrvrInboundConnsCurrent Gauge32,
    smtpSrvrInboundConnsTotal Gauge32,
    smtpSrvrLocalQueueLength Gauge32,
    smtpSrvrLocalRetryQueueLength Gauge32,
    smtpSrvrMsgBytesRcvdTotal Gauge32,
    smtpSrvrMsgBytesRcvdPerSec Gauge32,
    smtpSrvrMsgBytesSentTotal Gauge32,
    smtpSrvrMsgBytesSentPerSec Gauge32,
    smtpSrvrMsgBytesTotal Gauge32,
    smtpSrvrMsgBytesTotalPerSec Gauge32,
    smtpSrvrMsgDlvryRetries Gauge32,
    smtpSrvrMsgSendRetries Gauge32,
    smtpSrvrMsgsCurrUndeliverable Gauge32,
    smtpSrvrMsgsDlvrdTotal Gauge32,
    smtpSrvrMsgsDlvrdPerSec Gauge32,
    smtpSrvrMsgsPendingRoute Gauge32,
    smtpSrvrMsgsRcvdTotal Gauge32,
    smtpSrvrMsgsRcvdPerSec Gauge32,
    smtpSrvrMsgsRfsdForAddrObjects Gauge32,
    smtpSrvrMsgsRfsdForMailObjects Gauge32,
    smtpSrvrMsgsRfsdForSize Gauge32,
    smtpSrvrMsgsSentTotal Gauge32,
    smtpSrvrMsgsSentPerSec Gauge32,
    smtpSrvrNDRsGenerated Gauge32,
    smtpSrvrNumberOfMailFilesOpen Gauge32,
    smtpSrvrNumberOfQueueFilesOpen Gauge32,
    smtpSrvrOutboundConnsCurrent Gauge32,
    smtpSrvrOutboundConnsRfsd Gauge32,
    smtpSrvrOutboundConnsTotal Gauge32,
    smtpSrvrPickupDirMsgsRtrvdTotal Gauge32,
    smtpSrvrPickupDirMsgsRtrvdPerSec Gauge32,
    smtpSrvrRemoteQueueLength Gauge32,
    smtpSrvrRemoteRetryQueueLength Gauge32,
    smtpSrvrRouteTableLookupsTotal Gauge32,
    smtpSrvrRouteTableLookupsPerSec Gauge32,
    smtpSrvrTotalConnErrors Gauge32,
    smtpSrvrTotalDSNFail Gauge32,
    smtpSrvrTotalMsgsSubmitted Gauge32
}

smtpSrvrInstance OBJECT-TYPE
    SYNTAX     InstanceName
    MAX-ACCESS read-only
    STATUS     current
    DESCRIPTION
	    "Instance name."
    ::= { smtpServerEntry 1 }

smtpSrvrPercentRcpntsLocal OBJECT-TYPE
    SYNTAX     Gauge32
    MAX-ACCESS read-only
    STATUS     current
    DESCRIPTION
	    "The percentage of recipients that will be
	    delivered locally."
    ::= { smtpServerEntry 2 }

smtpSrvrPercentRcpntsRemote OBJECT-TYPE
    SYNTAX     Gauge32
    MAX-ACCESS read-only
    STATUS     current
    DESCRIPTION
	    "Thepercentage of recipients that will be
	    delivered remotely."
    ::= { smtpServerEntry 3 }

smtpSrvrAvgRcpntsPerMsgRcvd OBJECT-TYPE
    SYNTAX     Gauge32
    MAX-ACCESS read-only
    STATUS     current
    DESCRIPTION
	    "The average number of recipients per inbound
	    message received."
    ::= { smtpServerEntry 4 }

smtpSrvrAvgRcpntsPerMsgSent OBJECT-TYPE
    SYNTAX     Gauge32
    MAX-ACCESS read-only
    STATUS     current
    DESCRIPTION
	    "The average number of recipients per outbound
	    messages sent."
    ::= { smtpServerEntry 5 }

smtpSrvrAvgRetriesPerMsgDlvrd OBJECT-TYPE
    SYNTAX     Gauge32
    MAX-ACCESS read-only
    STATUS     current
    DESCRIPTION
	    "The average number of retries per local
	    delivery."
    ::= { smtpServerEntry 6 }

smtpSrvrAvgRetriesPerMsgSent OBJECT-TYPE
    SYNTAX     Gauge32
    MAX-ACCESS read-only
    STATUS     current
    DESCRIPTION
	    "The average number of retries per outbound
	    message sent."
    ::= { smtpServerEntry 7 }

smtpSrvrBadMailMsgsBadPickupFile OBJECT-TYPE
    SYNTAX     Gauge32
    MAX-ACCESS read-only
    STATUS     current
    DESCRIPTION
	    "The number of malformed pickup messages sent
	    to badmail."
    ::= { smtpServerEntry 8 }

smtpSrvrBadMailMsgsGeneralFail OBJECT-TYPE
    SYNTAX     Gauge32
    MAX-ACCESS read-only
    STATUS     current
    DESCRIPTION
	    "The number of messages sent to badmail for
	    reasons not associated with a specific
	    counter."
    ::= { smtpServerEntry 9 }

smtpSrvrBadMailMsgsHopCntExceed OBJECT-TYPE
    SYNTAX     Gauge32
    MAX-ACCESS read-only
    STATUS     current
    DESCRIPTION
	    "The number of messages sent to badmil becuase
	    they had exceeded the maximum hop count."
    ::= { smtpServerEntry 10 }

smtpSrvrBadMailMsgsNDROfDSN OBJECT-TYPE
    SYNTAX     Gauge32
    MAX-ACCESS read-only
    STATUS     current
    DESCRIPTION
	    "The number of Delivery Status Notifications
	    sent to badmail becuase they could not be
	    delivered."
    ::= { smtpServerEntry 11 }

smtpSrvrBadMailMsgsNoRcpnts OBJECT-TYPE
    SYNTAX     Gauge32
    MAX-ACCESS read-only
    STATUS     current
    DESCRIPTION
	    "The number of messages sent to badmail because
	    they had no recipients."
    ::= { smtpServerEntry 12 }

smtpSrvrBadMailMsgsTrigViaEvent OBJECT-TYPE
    SYNTAX     Gauge32
    MAX-ACCESS read-only
    STATUS     current
    DESCRIPTION
	    "The number of messages sent to badmail at the
	    request of a server event sink."
    ::= { smtpServerEntry 13 }

smtpSrvrBytesRcvdTotal OBJECT-TYPE
    SYNTAX     Gauge32
    MAX-ACCESS read-only
    STATUS     current
    DESCRIPTION
	    "The total number of bytes received."
    ::= { smtpServerEntry 14 }

smtpSrvrBytesRcvdPerSec OBJECT-TYPE
    SYNTAX     Gauge32
    MAX-ACCESS read-only
    STATUS     current
    DESCRIPTION
	    "The rate that bytes are received."
    ::= { smtpServerEntry 15 }

smtpSrvrBytesSentTotal OBJECT-TYPE
    SYNTAX     Gauge32
    MAX-ACCESS read-only
    STATUS     current
    DESCRIPTION
	    "The total number of bytes sent."
    ::= { smtpServerEntry 16 }

smtpSrvrBytesSentPerSec OBJECT-TYPE
    SYNTAX     Gauge32
    MAX-ACCESS read-only
    STATUS     current
    DESCRIPTION
	    "The rate that bytes are sent."
    ::= { smtpServerEntry 17 }

smtpSrvrBytesTotal OBJECT-TYPE
    SYNTAX     Gauge32
    MAX-ACCESS read-only
    STATUS     current
    DESCRIPTION
	    "The total number of bytes sent and received."
    ::= { smtpServerEntry 18 }

smtpSrvrBytesTotalPerSec OBJECT-TYPE
    SYNTAX     Gauge32
    MAX-ACCESS read-only
    STATUS     current
    DESCRIPTION
	    "The rate that bytes are sent and received."
    ::= { smtpServerEntry 19 }

smtpSrvrCatAddrLookupCmplt OBJECT-TYPE
    SYNTAX     Gauge32
    MAX-ACCESS read-only
    STATUS     current
    DESCRIPTION
	    "The number of address lookup completions
	    processed"
    ::= { smtpServerEntry 20 }

smtpSrvrCatAddrLookupCmpltPerSec OBJECT-TYPE
    SYNTAX     Gauge32
    MAX-ACCESS read-only
    STATUS     current
    DESCRIPTION
	    "The number of address lookup completions
	    processed per second"
    ::= { smtpServerEntry 21 }

smtpSrvrCatAddrLookups OBJECT-TYPE
    SYNTAX     Gauge32
    MAX-ACCESS read-only
    STATUS     current
    DESCRIPTION
	    "The number of DS lookups for individual
	    addresses"
    ::= { smtpServerEntry 22 }

smtpSrvrCatAddrLookupsNotFound OBJECT-TYPE
    SYNTAX     Gauge32
    MAX-ACCESS read-only
    STATUS     current
    DESCRIPTION
	    "The number of address lookups that did not
	    find any DS object"
    ::= { smtpServerEntry 23 }

smtpSrvrCatAddrLookupsPerSec OBJECT-TYPE
    SYNTAX     Gauge32
    MAX-ACCESS read-only
    STATUS     current
    DESCRIPTION
	    "The number of address lookups dispatched to
	    the DS per second"
    ::= { smtpServerEntry 24 }

smtpSrvrCatCatsCmpltd OBJECT-TYPE
    SYNTAX     Gauge32
    MAX-ACCESS read-only
    STATUS     current
    DESCRIPTION
	    "The total number of messages submitted to
	    categorizer that have finished categorization."
    ::= { smtpServerEntry 25 }

smtpSrvrCatCatsCmpltdSuccess OBJECT-TYPE
    SYNTAX     Gauge32
    MAX-ACCESS read-only
    STATUS     current
    DESCRIPTION
	    "The number of categorizations that completed
	    without any errors."
    ::= { smtpServerEntry 26 }

smtpSrvrCatCatsCmpltdPerSec OBJECT-TYPE
    SYNTAX     Gauge32
    MAX-ACCESS read-only
    STATUS     current
    DESCRIPTION
	    "The rate of categorizations completed."
    ::= { smtpServerEntry 27 }

smtpSrvrCatCatsFailDSConnFail OBJECT-TYPE
    SYNTAX     Gauge32
    MAX-ACCESS read-only
    STATUS     current
    DESCRIPTION
	    "The number of categorizations that failed due
	    to a DS connection failure"
    ::= { smtpServerEntry 28 }

smtpSrvrCatCatsFailDSLogonFail OBJECT-TYPE
    SYNTAX     Gauge32
    MAX-ACCESS read-only
    STATUS     current
    DESCRIPTION
	    "The number of categorizations that failed due
	    to a DS logon failure"
    ::= { smtpServerEntry 29 }

smtpSrvrCatCatsFailOutOfMemory OBJECT-TYPE
    SYNTAX     Gauge32
    MAX-ACCESS read-only
    STATUS     current
    DESCRIPTION
	    "The number of categorizations that failed due
	    to lack of available memory."
    ::= { smtpServerEntry 30 }

smtpSrvrCatCatsFailNonRetryError OBJECT-TYPE
    SYNTAX     Gauge32
    MAX-ACCESS read-only
    STATUS     current
    DESCRIPTION
	    "The number of categorizations that failed with
	    a hard error (not retryable)."
    ::= { smtpServerEntry 31 }

smtpSrvrCatCatsFailRetryError OBJECT-TYPE
    SYNTAX     Gauge32
    MAX-ACCESS read-only
    STATUS     current
    DESCRIPTION
	    "The number of categorizations that failed with
	    a retryable error."
    ::= { smtpServerEntry 32 }

smtpSrvrCatCatsFailSinkRetryErr OBJECT-TYPE
    SYNTAX     Gauge32
    MAX-ACCESS read-only
    STATUS     current
    DESCRIPTION
	    "The number of categorizations that failed with
	    a generic retryable error"
    ::= { smtpServerEntry 33 }

smtpSrvrCatCatsInProgress OBJECT-TYPE
    SYNTAX     Gauge32
    MAX-ACCESS read-only
    STATUS     current
    DESCRIPTION
	    "The number of categorizations in progress."
    ::= { smtpServerEntry 34 }

smtpSrvrCatLDAPBindFail OBJECT-TYPE
    SYNTAX     Gauge32
    MAX-ACCESS read-only
    STATUS     current
    DESCRIPTION
	    "The total number of LDAP bind failures"
    ::= { smtpServerEntry 35 }

smtpSrvrCatLDAPBinds OBJECT-TYPE
    SYNTAX     Gauge32
    MAX-ACCESS read-only
    STATUS     current
    DESCRIPTION
	    "The total number of successfull LDAP binds
	    performed"
    ::= { smtpServerEntry 36 }

smtpSrvrCatLDAPConnFail OBJECT-TYPE
    SYNTAX     Gauge32
    MAX-ACCESS read-only
    STATUS     current
    DESCRIPTION
	    "The total number of failures encountered
	    connection to LDAP servers"
    ::= { smtpServerEntry 37 }

smtpSrvrCatLDAPConns OBJECT-TYPE
    SYNTAX     Gauge32
    MAX-ACCESS read-only
    STATUS     current
    DESCRIPTION
	    "The total number of LDAP connections opened"
    ::= { smtpServerEntry 38 }

smtpSrvrCatLDAPConnsCurrOpen OBJECT-TYPE
    SYNTAX     Gauge32
    MAX-ACCESS read-only
    STATUS     current
    DESCRIPTION
	    "The number of LDAP connections currently open"
    ::= { smtpServerEntry 39 }

smtpSrvrCatLDAPGeneralCmpltFail OBJECT-TYPE
    SYNTAX     Gauge32
    MAX-ACCESS read-only
    STATUS     current
    DESCRIPTION
	    "Number of LDAP completions with a generic
	    failure"
    ::= { smtpServerEntry 40 }

smtpSrvrCatLDAPPageSrchCmpltFail OBJECT-TYPE
    SYNTAX     Gauge32
    MAX-ACCESS read-only
    STATUS     current
    DESCRIPTION
	    "Number of LDAP paged searches that completed
	    with a failure"
    ::= { smtpServerEntry 41 }

smtpSrvrCatLDAPPagedSrchFail OBJECT-TYPE
    SYNTAX     Gauge32
    MAX-ACCESS read-only
    STATUS     current
    DESCRIPTION
	    "Number of failures to dispatch an async paged
	    LDAP search"
    ::= { smtpServerEntry 42 }

smtpSrvrCatLDAPPagedSrchs OBJECT-TYPE
    SYNTAX     Gauge32
    MAX-ACCESS read-only
    STATUS     current
    DESCRIPTION
	    "LDAP paged searches successfully dispatched"
    ::= { smtpServerEntry 43 }

smtpSrvrCatLDAPPagedSrchsCmpltd OBJECT-TYPE
    SYNTAX     Gauge32
    MAX-ACCESS read-only
    STATUS     current
    DESCRIPTION
	    "Number of paged LDAP completions processed"
    ::= { smtpServerEntry 44 }

smtpSrvrCatLDAPSrchCmpltFail OBJECT-TYPE
    SYNTAX     Gauge32
    MAX-ACCESS read-only
    STATUS     current
    DESCRIPTION
	    "Number of LDAP searches that completed with a
	    failure"
    ::= { smtpServerEntry 45 }

smtpSrvrCatLDAPSrchFail OBJECT-TYPE
    SYNTAX     Gauge32
    MAX-ACCESS read-only
    STATUS     current
    DESCRIPTION
	    "Number of failures to dispatch an async LDAP
	    search"
    ::= { smtpServerEntry 46 }

smtpSrvrCatLDAPSrchs OBJECT-TYPE
    SYNTAX     Gauge32
    MAX-ACCESS read-only
    STATUS     current
    DESCRIPTION
	    "LDAP searches successfully dispatched"
    ::= { smtpServerEntry 47 }

smtpSrvrCatLDAPSrchsAbandoned OBJECT-TYPE
    SYNTAX     Gauge32
    MAX-ACCESS read-only
    STATUS     current
    DESCRIPTION
	    "Number of LDAP searches abandoned"
    ::= { smtpServerEntry 48 }

smtpSrvrCatLDAPSrchsCmpltd OBJECT-TYPE
    SYNTAX     Gauge32
    MAX-ACCESS read-only
    STATUS     current
    DESCRIPTION
	    "Number of LDAP search completions processed"
    ::= { smtpServerEntry 49 }

smtpSrvrCatLDAPSrchsCmpltdPerSec OBJECT-TYPE
    SYNTAX     Gauge32
    MAX-ACCESS read-only
    STATUS     current
    DESCRIPTION
	    "LDAP search completions processed/sec"
    ::= { smtpServerEntry 50 }

smtpSrvrCatLDAPSrchsPendingCmplt OBJECT-TYPE
    SYNTAX     Gauge32
    MAX-ACCESS read-only
    STATUS     current
    DESCRIPTION
	    "Number of LDAP searches pending async
	    completon"
    ::= { smtpServerEntry 51 }

smtpSrvrCatLDAPSrchsPerSec OBJECT-TYPE
    SYNTAX     Gauge32
    MAX-ACCESS read-only
    STATUS     current
    DESCRIPTION
	    "LDAP searches successfully dispatched/sec"
    ::= { smtpServerEntry 52 }

smtpSrvrCatMsgsCategorized OBJECT-TYPE
    SYNTAX     Gauge32
    MAX-ACCESS read-only
    STATUS     current
    DESCRIPTION
	    "The number of messages categorizer has
	    submitted to queueing."
    ::= { smtpServerEntry 53 }

smtpSrvrCatMsgsAborted OBJECT-TYPE
    SYNTAX     Gauge32
    MAX-ACCESS read-only
    STATUS     current
    DESCRIPTION
	    "The number of messages marked to be aborted by
	    the categorizer."
    ::= { smtpServerEntry 54 }

smtpSrvrCatMsgsBifurcated OBJECT-TYPE
    SYNTAX     Gauge32
    MAX-ACCESS read-only
    STATUS     current
    DESCRIPTION
	    "The number of new messages created by the
	    categorizer (bifurcation)."
    ::= { smtpServerEntry 55 }

smtpSrvrCatMsgsSubmitted OBJECT-TYPE
    SYNTAX     Gauge32
    MAX-ACCESS read-only
    STATUS     current
    DESCRIPTION
	    "The total number of messages submitted to the
	    categorizer."
    ::= { smtpServerEntry 56 }

smtpSrvrCatMsgsSubmittedPerSec OBJECT-TYPE
    SYNTAX     Gauge32
    MAX-ACCESS read-only
    STATUS     current
    DESCRIPTION
	    "The rate that messages are being submitted to
	    the categorizer."
    ::= { smtpServerEntry 57 }

smtpSrvrCatRcptsNDRdAmbigsAddr OBJECT-TYPE
    SYNTAX     Gauge32
    MAX-ACCESS read-only
    STATUS     current
    DESCRIPTION
	    "The number of recipients with addresses that
	    match multiple DS objects."
    ::= { smtpServerEntry 58 }

smtpSrvrCatRcptsNDRdForwardLoop OBJECT-TYPE
    SYNTAX     Gauge32
    MAX-ACCESS read-only
    STATUS     current
    DESCRIPTION
	    "The number of recipients NDRd by the
	    categorizer due to a forwarding loop
	    detection."
    ::= { smtpServerEntry 59 }

smtpSrvrCatRcptsNDRdIllegalAddr OBJECT-TYPE
    SYNTAX     Gauge32
    MAX-ACCESS read-only
    STATUS     current
    DESCRIPTION
	    "The number of recipients with illegal
	    addresses detected by the categorizer."
    ::= { smtpServerEntry 60 }

smtpSrvrCatRcptsNDRdSinkRecipErr OBJECT-TYPE
    SYNTAX     Gauge32
    MAX-ACCESS read-only
    STATUS     current
    DESCRIPTION
	    "The number of recipients NDRd by the
	    categorizer due to a generic recipient
	    failure."
    ::= { smtpServerEntry 61 }

smtpSrvrCatRcptsNDRdUnresolved OBJECT-TYPE
    SYNTAX     Gauge32
    MAX-ACCESS read-only
    STATUS     current
    DESCRIPTION
	    "The number of unresolved recipients (local
	    addresses not found)."
    ::= { smtpServerEntry 62 }

smtpSrvrCatRcptsNDRdByCategorize OBJECT-TYPE
    SYNTAX     Gauge32
    MAX-ACCESS read-only
    STATUS     current
    DESCRIPTION
	    "The number of recipients set to be NDRd by the
	    categorizer."
    ::= { smtpServerEntry 63 }

smtpSrvrCatRcptsAfterCat OBJECT-TYPE
    SYNTAX     Gauge32
    MAX-ACCESS read-only
    STATUS     current
    DESCRIPTION
	    "The number of mailmsg recipients submitted
	    from categorizer to queueing."
    ::= { smtpServerEntry 64 }

smtpSrvrCatRcptsBeforeCat OBJECT-TYPE
    SYNTAX     Gauge32
    MAX-ACCESS read-only
    STATUS     current
    DESCRIPTION
	    "The number of mailmsg recipients submitted to
	    categorizer."
    ::= { smtpServerEntry 65 }

smtpSrvrCatRcptsInCat OBJECT-TYPE
    SYNTAX     Gauge32
    MAX-ACCESS read-only
    STATUS     current
    DESCRIPTION
	    "The number of recipients the categorizer is
	    currently processing."
    ::= { smtpServerEntry 66 }

smtpSrvrCatSendersUnresolved OBJECT-TYPE
    SYNTAX     Gauge32
    MAX-ACCESS read-only
    STATUS     current
    DESCRIPTION
	    "The number of seners not find in the DS."
    ::= { smtpServerEntry 67 }

smtpSrvrCatSendersAmbigsAddr OBJECT-TYPE
    SYNTAX     Gauge32
    MAX-ACCESS read-only
    STATUS     current
    DESCRIPTION
	    "The number of senders with addresses that
	    match multiple DS objects."
    ::= { smtpServerEntry 68 }

smtpSrvrCatMailmsgDupCollisions OBJECT-TYPE
    SYNTAX     Gauge32
    MAX-ACCESS read-only
    STATUS     current
    DESCRIPTION
	    "The number of times a duplicate recipient
	    address was detected by mailmsg/categorizer."
    ::= { smtpServerEntry 69 }

smtpSrvrCategorizerQueueLength OBJECT-TYPE
    SYNTAX     Gauge32
    MAX-ACCESS read-only
    STATUS     current
    DESCRIPTION
	    "The number of messages in the categorizer
	    queue."
    ::= { smtpServerEntry 70 }

smtpSrvrConnErrorsPerSec OBJECT-TYPE
    SYNTAX     Gauge32
    MAX-ACCESS read-only
    STATUS     current
    DESCRIPTION
	    "The number of connection errors per second."
    ::= { smtpServerEntry 71 }

smtpSrvrCurrentMsgsInLocalDlvry OBJECT-TYPE
    SYNTAX     Gauge32
    MAX-ACCESS read-only
    STATUS     current
    DESCRIPTION
	    "The number of messages that are currently
	    being processed by a server event sink for
	    local delivery."
    ::= { smtpServerEntry 72 }

smtpSrvrDNSQueriesTotal OBJECT-TYPE
    SYNTAX     Gauge32
    MAX-ACCESS read-only
    STATUS     current
    DESCRIPTION
	    "The total number of DNS lookups."
    ::= { smtpServerEntry 73 }

smtpSrvrDNSQueriesPerSec OBJECT-TYPE
    SYNTAX     Gauge32
    MAX-ACCESS read-only
    STATUS     current
    DESCRIPTION
	    "The rate of DNS lookups."
    ::= { smtpServerEntry 74 }

smtpSrvrDirDropsTotal OBJECT-TYPE
    SYNTAX     Gauge32
    MAX-ACCESS read-only
    STATUS     current
    DESCRIPTION
	    "The total number of messages placed in a drop
	    directory."
    ::= { smtpServerEntry 75 }

smtpSrvrDirDropsPerSec OBJECT-TYPE
    SYNTAX     Gauge32
    MAX-ACCESS read-only
    STATUS     current
    DESCRIPTION
	    "The number of messages placed in a drop
	    directory per second."
    ::= { smtpServerEntry 76 }

smtpSrvrETRNMsgsTotal OBJECT-TYPE
    SYNTAX     Gauge32
    MAX-ACCESS read-only
    STATUS     current
    DESCRIPTION
	    "The total number of ETRN messages received by
	    the server."
    ::= { smtpServerEntry 77 }

smtpSrvrETRNMsgsPerSec OBJECT-TYPE
    SYNTAX     Gauge32
    MAX-ACCESS read-only
    STATUS     current
    DESCRIPTION
	    "The number of ETRN messages per second."
    ::= { smtpServerEntry 78 }

smtpSrvrInboundConnsCurrent OBJECT-TYPE
    SYNTAX     Gauge32
    MAX-ACCESS read-only
    STATUS     current
    DESCRIPTION
	    "The total number of connections currently
	    inbound."
    ::= { smtpServerEntry 79 }

smtpSrvrInboundConnsTotal OBJECT-TYPE
    SYNTAX     Gauge32
    MAX-ACCESS read-only
    STATUS     current
    DESCRIPTION
	    "The total number of inbound connections
	    received."
    ::= { smtpServerEntry 80 }

smtpSrvrLocalQueueLength OBJECT-TYPE
    SYNTAX     Gauge32
    MAX-ACCESS read-only
    STATUS     current
    DESCRIPTION
	    "The number of messages in the local queue."
    ::= { smtpServerEntry 81 }

smtpSrvrLocalRetryQueueLength OBJECT-TYPE
    SYNTAX     Gauge32
    MAX-ACCESS read-only
    STATUS     current
    DESCRIPTION
	    "The number of messages in the local retry
	    queue."
    ::= { smtpServerEntry 82 }

smtpSrvrMsgBytesRcvdTotal OBJECT-TYPE
    SYNTAX     Gauge32
    MAX-ACCESS read-only
    STATUS     current
    DESCRIPTION
	    "The total number of bytes received in
	    messages."
    ::= { smtpServerEntry 83 }

smtpSrvrMsgBytesRcvdPerSec OBJECT-TYPE
    SYNTAX     Gauge32
    MAX-ACCESS read-only
    STATUS     current
    DESCRIPTION
	    "The rate that bytes are received in messages."
    ::= { smtpServerEntry 84 }

smtpSrvrMsgBytesSentTotal OBJECT-TYPE
    SYNTAX     Gauge32
    MAX-ACCESS read-only
    STATUS     current
    DESCRIPTION
	    "The total number of bytes sent in messages."
    ::= { smtpServerEntry 85 }

smtpSrvrMsgBytesSentPerSec OBJECT-TYPE
    SYNTAX     Gauge32
    MAX-ACCESS read-only
    STATUS     current
    DESCRIPTION
	    "The rate that bytes are sent in messages."
    ::= { smtpServerEntry 86 }

smtpSrvrMsgBytesTotal OBJECT-TYPE
    SYNTAX     Gauge32
    MAX-ACCESS read-only
    STATUS     current
    DESCRIPTION
	    "The total number of bytes sent and received in
	    messages."
    ::= { smtpServerEntry 87 }

smtpSrvrMsgBytesTotalPerSec OBJECT-TYPE
    SYNTAX     Gauge32
    MAX-ACCESS read-only
    STATUS     current
    DESCRIPTION
	    "The rate that bytes are sent and received in
	    messages."
    ::= { smtpServerEntry 88 }

smtpSrvrMsgDlvryRetries OBJECT-TYPE
    SYNTAX     Gauge32
    MAX-ACCESS read-only
    STATUS     current
    DESCRIPTION
	    "The total number of local deliveries that were
	    retried."
    ::= { smtpServerEntry 89 }

smtpSrvrMsgSendRetries OBJECT-TYPE
    SYNTAX     Gauge32
    MAX-ACCESS read-only
    STATUS     current
    DESCRIPTION
	    "The total number of outbound message sends
	    that were retried."
    ::= { smtpServerEntry 90 }

smtpSrvrMsgsCurrUndeliverable OBJECT-TYPE
    SYNTAX     Gauge32
    MAX-ACCESS read-only
    STATUS     current
    DESCRIPTION
	    "The number of messages that have been reported
	    as currently undeliverable by routing."
    ::= { smtpServerEntry 91 }

smtpSrvrMsgsDlvrdTotal OBJECT-TYPE
    SYNTAX     Gauge32
    MAX-ACCESS read-only
    STATUS     current
    DESCRIPTION
	    "The total number of messages delivered to
	    local mailboxes."
    ::= { smtpServerEntry 92 }

smtpSrvrMsgsDlvrdPerSec OBJECT-TYPE
    SYNTAX     Gauge32
    MAX-ACCESS read-only
    STATUS     current
    DESCRIPTION
	    "The rate that messages are delivered to local
	    mailboxes."
    ::= { smtpServerEntry 93 }

smtpSrvrMsgsPendingRoute OBJECT-TYPE
    SYNTAX     Gauge32
    MAX-ACCESS read-only
    STATUS     current
    DESCRIPTION
	    "The number of messages that have been
	    categorized but not routed."
    ::= { smtpServerEntry 94 }

smtpSrvrMsgsRcvdTotal OBJECT-TYPE
    SYNTAX     Gauge32
    MAX-ACCESS read-only
    STATUS     current
    DESCRIPTION
	    "The total number of inbound messages
	    accepted."
    ::= { smtpServerEntry 95 }

smtpSrvrMsgsRcvdPerSec OBJECT-TYPE
    SYNTAX     Gauge32
    MAX-ACCESS read-only
    STATUS     current
    DESCRIPTION
	    "The rate that inbound messages are being
	    received."
    ::= { smtpServerEntry 96 }

smtpSrvrMsgsRfsdForAddrObjects OBJECT-TYPE
    SYNTAX     Gauge32
    MAX-ACCESS read-only
    STATUS     current
    DESCRIPTION
	    "The total number of messages refused due to no
	    address objects."
    ::= { smtpServerEntry 97 }

smtpSrvrMsgsRfsdForMailObjects OBJECT-TYPE
    SYNTAX     Gauge32
    MAX-ACCESS read-only
    STATUS     current
    DESCRIPTION
	    "The total number of messages refused due to no
	    mail objects."
    ::= { smtpServerEntry 98 }

smtpSrvrMsgsRfsdForSize OBJECT-TYPE
    SYNTAX     Gauge32
    MAX-ACCESS read-only
    STATUS     current
    DESCRIPTION
	    "The total number of messages rejected because
	    they were too big."
    ::= { smtpServerEntry 99 }

smtpSrvrMsgsSentTotal OBJECT-TYPE
    SYNTAX     Gauge32
    MAX-ACCESS read-only
    STATUS     current
    DESCRIPTION
	    "The total number of outbound messages sent."
    ::= { smtpServerEntry 100 }

smtpSrvrMsgsSentPerSec OBJECT-TYPE
    SYNTAX     Gauge32
    MAX-ACCESS read-only
    STATUS     current
    DESCRIPTION
	    "The rate that outbound messages are being
	    sent."
    ::= { smtpServerEntry 101 }

smtpSrvrNDRsGenerated OBJECT-TYPE
    SYNTAX     Gauge32
    MAX-ACCESS read-only
    STATUS     current
    DESCRIPTION
	    "The number of non-delivery reports that have
	    been generated."
    ::= { smtpServerEntry 102 }

smtpSrvrNumberOfMailFilesOpen OBJECT-TYPE
    SYNTAX     Gauge32
    MAX-ACCESS read-only
    STATUS     current
    DESCRIPTION
	    "Number of handles to open mail files."
    ::= { smtpServerEntry 103 }

smtpSrvrNumberOfQueueFilesOpen OBJECT-TYPE
    SYNTAX     Gauge32
    MAX-ACCESS read-only
    STATUS     current
    DESCRIPTION
	    "Number of handles to open queue files."
    ::= { smtpServerEntry 104 }

smtpSrvrOutboundConnsCurrent OBJECT-TYPE
    SYNTAX     Gauge32
    MAX-ACCESS read-only
    STATUS     current
    DESCRIPTION
	    "The number of connections currently outbound."
    ::= { smtpServerEntry 105 }

smtpSrvrOutboundConnsRfsd OBJECT-TYPE
    SYNTAX     Gauge32
    MAX-ACCESS read-only
    STATUS     current
    DESCRIPTION
	    "The number of outbound connection attempts
	    refused by remote sites."
    ::= { smtpServerEntry 106 }

smtpSrvrOutboundConnsTotal OBJECT-TYPE
    SYNTAX     Gauge32
    MAX-ACCESS read-only
    STATUS     current
    DESCRIPTION
	    "The total number of outbound connections
	    attempted."
    ::= { smtpServerEntry 107 }

smtpSrvrPickupDirMsgsRtrvdTotal OBJECT-TYPE
    SYNTAX     Gauge32
    MAX-ACCESS read-only
    STATUS     current
    DESCRIPTION
	    "The total number of messages retrieved from
	    the mail pick-up directory."
    ::= { smtpServerEntry 108 }

smtpSrvrPickupDirMsgsRtrvdPerSec OBJECT-TYPE
    SYNTAX     Gauge32
    MAX-ACCESS read-only
    STATUS     current
    DESCRIPTION
	    "The rate that messages are being retrieved
	    from the mail pick-up directory."
    ::= { smtpServerEntry 109 }

smtpSrvrRemoteQueueLength OBJECT-TYPE
    SYNTAX     Gauge32
    MAX-ACCESS read-only
    STATUS     current
    DESCRIPTION
	    "The number of messages in the remote queue."
    ::= { smtpServerEntry 110 }

smtpSrvrRemoteRetryQueueLength OBJECT-TYPE
    SYNTAX     Gauge32
    MAX-ACCESS read-only
    STATUS     current
    DESCRIPTION
	    "The number of messages in the retry queue for
	    remote delivery."
    ::= { smtpServerEntry 111 }

smtpSrvrRouteTableLookupsTotal OBJECT-TYPE
    SYNTAX     Gauge32
    MAX-ACCESS read-only
    STATUS     current
    DESCRIPTION
	    "The total number of routing table lookups."
    ::= { smtpServerEntry 112 }

smtpSrvrRouteTableLookupsPerSec OBJECT-TYPE
    SYNTAX     Gauge32
    MAX-ACCESS read-only
    STATUS     current
    DESCRIPTION
	    "The number of routing table lookups per
	    second."
    ::= { smtpServerEntry 113 }

smtpSrvrTotalConnErrors OBJECT-TYPE
    SYNTAX     Gauge32
    MAX-ACCESS read-only
    STATUS     current
    DESCRIPTION
	    "The total number of connection errors."
    ::= { smtpServerEntry 114 }

smtpSrvrTotalDSNFail OBJECT-TYPE
    SYNTAX     Gauge32
    MAX-ACCESS read-only
    STATUS     current
    DESCRIPTION
	    "The total number of failed DSN generation
	    attempts."
    ::= { smtpServerEntry 115 }

smtpSrvrTotalMsgsSubmitted OBJECT-TYPE
    SYNTAX     Gauge32
    MAX-ACCESS read-only
    STATUS     current
    DESCRIPTION
	    "The total messages submitted to queuing for
	    delivery."
    ::= { smtpServerEntry 116 }

system OBJECT-IDENTITY
    STATUS     current
    DESCRIPTION
	    "The System performance object consists of
	    counters that apply to more than one component
	    of the computer. Percentage counters by default
	    do not show values above 100 percent. See
	    'Overview of Performance Monitoring' in the
	    Windows 2000 Server Resource Kit Server
	    Operations Guide for instructions about
	    changing this default in the registry."
    ::= { advanced 77 }

systemPercentRegistryQuotaInUse OBJECT-TYPE
    SYNTAX     Gauge32
    MAX-ACCESS read-only
    STATUS     current
    DESCRIPTION
	    "% Registry Quota In Use is the percentage of
	    the Total Registry Quota Allowed that is
	    currently being used by the system.  This
	    counter displays the current percentage value
	    only; it is not an average. "
    ::= { system 1 }

systemAlignmentFixupsPerSec OBJECT-TYPE
    SYNTAX     Gauge32
    MAX-ACCESS read-only
    STATUS     current
    DESCRIPTION
	    "Alignment Fixups/sec is the rate of alignment
	    faults fixed by the system.  This counter
	    displays the difference between the values
	    observed in the last two samples, divided by
	    the duration of the sample interval."
    ::= { system 2 }

systemContextSwitchesPerSec OBJECT-TYPE
    SYNTAX     Gauge32
    MAX-ACCESS read-only
    STATUS     current
    DESCRIPTION
	    "Context Switches/sec is the combined rate at
	    which all processors on the computer are
	    switched from one thread to another.  Context
	    switches occur when a running thread
	    voluntarily relinquishes the processor, is
	    preempted by a higher priority ready thread, or
	    switches between user-mode and privileged
	    (kernel) mode to use an Executive or subsystem
	    service.  It is the sum of Thread: Context
	    Switches/sec for all threads running on all
	    processors in the computer and is measured in
	    numbers of switches.  There are context switch
	    counters on the System and Thread objects. This
	    counter displays the difference between the
	    values observed in the last two samples,
	    divided by the duration of the sample interval.
	    "
    ::= { system 3 }

systemExceptionDispatchesPerSec OBJECT-TYPE
    SYNTAX     Gauge32
    MAX-ACCESS read-only
    STATUS     current
    DESCRIPTION
	    "Exception Dispatches/sec is the rate of
	    exceptions dispatched by the system. This
	    counter displays the difference between the
	    values observed in the last two samples,
	    divided by the duration of the sample
	    interval."
    ::= { system 4 }

systemFileControlBytesPerSec OBJECT-TYPE
    SYNTAX     Gauge32
    MAX-ACCESS read-only
    STATUS     current
    DESCRIPTION
	    "File Control Bytes/sec is the overall rate at
	    which bytes are transferred for all file system
	    operations that are neither reads nor writes,
	    including file system control requests and
	    requests for information about device
	    characteristics or status.	It is measured in
	    numbers of bytes.  This counter displays the
	    difference between the values observed in the
	    last two samples, divided by the duration of
	    the sample interval. "
    ::= { system 5 }

systemFileControlOperationPerSec OBJECT-TYPE
    SYNTAX     Gauge32
    MAX-ACCESS read-only
    STATUS     current
    DESCRIPTION
	    "File Control Operations/sec is the combined
	    rate of file system operations that are neither
	    reads nor writes, such as file system control
	    requests and requests for information about
	    device characteristics or status.  This is the
	    inverse of System: File Data Operations/sec and
	    is measured in number of operations perf
	    second.  This counter displays the difference
	    between the values observed in the last two
	    samples, divided by the duration of the sample
	    interval. "
    ::= { system 6 }

systemFileDataOperationsPerSec OBJECT-TYPE
    SYNTAX     Gauge32
    MAX-ACCESS read-only
    STATUS     current
    DESCRIPTION
	    "File Data Operations/ sec is the combined rate
	    of read and write operations on all logical
	    disks on the computer.  This is the inverse of
	    System: File Control Operations/sec.  This
	    counter displays the difference between the
	    values observed in the last two samples,
	    divided by the duration of the sample interval.
	    "
    ::= { system 7 }

systemFileReadBytesPerSec OBJECT-TYPE
    SYNTAX     Gauge32
    MAX-ACCESS read-only
    STATUS     current
    DESCRIPTION
	    "File Read Bytes/sec is the overall rate at
	    which bytes are read to satisfy  file system
	    read requests to all devices on the computer,
	    including reads from the file system cache.  It
	    is measured in number of bytes per second. 
	    This counter displays the difference between
	    the values observed in the last two samples,
	    divided by the duration of the sample interval.
	     "
    ::= { system 8 }

systemFileReadOperationsPerSec OBJECT-TYPE
    SYNTAX     Gauge32
    MAX-ACCESS read-only
    STATUS     current
    DESCRIPTION
	    "File Read Operations/sec is the combined rate
	    of file system read requests to all devices on
	    the computer, including requests to read from
	    the file system cache.  It is measured in
	    numbers of reads.  This counter displays the
	    difference between the values observed in the
	    last two samples, divided by the duration of
	    the sample interval.  "
    ::= { system 9 }

systemFileWriteBytesPerSec OBJECT-TYPE
    SYNTAX     Gauge32
    MAX-ACCESS read-only
    STATUS     current
    DESCRIPTION
	    "File Write Bytes/sec is the overall rate at
	    which bytes are written to satisfy file system
	    write requests to all devices on the computer,
	    including writes to the file system cache.	It
	    is measured in number of bytes per second. 
	    This counter displays the difference between
	    the values observed in the last two samples,
	    divided by the duration of the sample interval.
	     "
    ::= { system 10 }

systemFileWriteOperationsPerSec OBJECT-TYPE
    SYNTAX     Gauge32
    MAX-ACCESS read-only
    STATUS     current
    DESCRIPTION
	    "File Write Operations/sec is the combined rate
	    of the file system write requests to all
	    devices on the computer, including requests to
	    write to data in the file system cache.  It is
	    measured in numbers of writes. This counter
	    displays the difference between the values
	    observed in the last two samples, divided by
	    the duration of the sample interval."
    ::= { system 11 }

systemFloatingEmulationsPerSec OBJECT-TYPE
    SYNTAX     Gauge32
    MAX-ACCESS read-only
    STATUS     current
    DESCRIPTION
	    "Floating Emulations/sec is the rate of
	    floating emulations performed by the system. 
	    This counter displays the difference between
	    the values observed in the last two samples,
	    divided by the duration of the sample
	    interval."
    ::= { system 12 }

systemProcesses OBJECT-TYPE
    SYNTAX     Gauge32
    MAX-ACCESS read-only
    STATUS     current
    DESCRIPTION
	    "Processes is the number of processes in the
	    computer at the time of data collection. 
	    Notice that this is an instantaneous count, not
	    an average over the time interval.	Each
	    process represents the running of a program."
    ::= { system 13 }

systemProcessorQueueLength OBJECT-TYPE
    SYNTAX     Gauge32
    MAX-ACCESS read-only
    STATUS     current
    DESCRIPTION
	    "Processor Queue Length is the number of
	    threads in the processor queue.  There is a
	    single queue for processor time even on
	    computers with multiple processors.  Unlike the
	    disk counters, this counter counts ready
	    threads only, not threads that are running.  A
	    sustained processor queue of  greater than two
	    threads generally indicates processor
	    congestion.  This counter displays the last
	    observed value only; it is not an average."
    ::= { system 14 }

systemSystemCallsPerSec OBJECT-TYPE
    SYNTAX     Gauge32
    MAX-ACCESS read-only
    STATUS     current
    DESCRIPTION
	    "Systems Calls/sec is the combined rate of
	    calls to Windows NT system service routines by
	    all processes running on the computer. These
	    routines perform all of the basic scheduling
	    and synchronization of activities on the
	    computer, and provide access to non-graphic
	    devices, memory management, and name space
	    management. This counter displays the
	    difference between the values observed in the
	    last two samples, divided by the duration of
	    the sample interval. "
    ::= { system 15 }

systemSystemUpTime OBJECT-TYPE
    SYNTAX     Gauge32
    MAX-ACCESS read-only
    STATUS     current
    DESCRIPTION
	    "System Up Time is the elapsed time (in
	    seconds) that the computer has been running
	    since it was last started.	This counter
	    displays the difference between the start time
	    and the current time. "
    ::= { system 16 }

systemThreads OBJECT-TYPE
    SYNTAX     Gauge32
    MAX-ACCESS read-only
    STATUS     current
    DESCRIPTION
	    "Threads is the number of threads in the
	    computer at the time of data collection. 
	    Notice that this is an instantaneous count, not
	    an average over the time interval.	A thread is
	    the basic executable entity that can execute
	    instructions in a processor."
    ::= { system 17 }

tcpV4 OBJECT-IDENTITY
    STATUS     current
    DESCRIPTION
	    "The TCP performance object consists of
	    counters that measure the rates at which TCP
	    segments are sent and received using the
	    Transmission Control Protocol (TCP). It
	    includes counters that monitor the number of
	    TCP connections in each TCP connection state."
    ::= { advanced 78 }

tcpV4ConnectionFailures OBJECT-TYPE
    SYNTAX     Gauge32
    MAX-ACCESS read-only
    STATUS     current
    DESCRIPTION
	    "Connection Failures is the number of times TCP
	    connections have made a direct transition to
	    the CLOSED state from the SYN-SENT state or the
	    SYN-RCVD state, plus the number of times TCP
	    connections have made a direct transition to
	    the LISTEN state from the SYN-RCVD state."
    ::= { tcpV4 1 }

tcpV4ConnectionsActive OBJECT-TYPE
    SYNTAX     Gauge32
    MAX-ACCESS read-only
    STATUS     current
    DESCRIPTION
	    "Connections Active is the number of times TCP
	    connections have made a direct transition to
	    the SYN-SENT state from the CLOSED state."
    ::= { tcpV4 2 }

tcpV4ConnectionsEstablished OBJECT-TYPE
    SYNTAX     Gauge32
    MAX-ACCESS read-only
    STATUS     current
    DESCRIPTION
	    "Connections Established is the number of TCP
	    connections for which the current state is
	    either ESTABLISHED or CLOSE-WAIT."
    ::= { tcpV4 3 }

tcpV4ConnectionsPassive OBJECT-TYPE
    SYNTAX     Gauge32
    MAX-ACCESS read-only
    STATUS     current
    DESCRIPTION
	    "Connections Passive is the number of times TCP
	    connections have made a direct transition to
	    the SYN-RCVD state from the LISTEN state."
    ::= { tcpV4 4 }

tcpV4ConnectionsReset OBJECT-TYPE
    SYNTAX     Gauge32
    MAX-ACCESS read-only
    STATUS     current
    DESCRIPTION
	    "Connections Reset is the number of times TCP
	    connections have made a direct transition to
	    the CLOSED state from either the ESTABLISHED
	    state or the CLOSE-WAIT state."
    ::= { tcpV4 5 }

tcpV4SegmentsReceivedPerSec OBJECT-TYPE
    SYNTAX     Gauge32
    MAX-ACCESS read-only
    STATUS     current
    DESCRIPTION
	    "Segments Received/sec is the rate at which
	    segments are received, including those received
	    in error.  This count includes segments
	    received on currently established connections."
    ::= { tcpV4 6 }

tcpV4SegmentsRetransmittedPerSec OBJECT-TYPE
    SYNTAX     Gauge32
    MAX-ACCESS read-only
    STATUS     current
    DESCRIPTION
	    "Segments Retransmitted/sec is the rate at
	    which segments are retransmitted, that is,
	    segments transmitted containing one or more
	    previously transmitted bytes."
    ::= { tcpV4 7 }

tcpV4SegmentsSentPerSec OBJECT-TYPE
    SYNTAX     Gauge32
    MAX-ACCESS read-only
    STATUS     current
    DESCRIPTION
	    "Segments Sent/sec is the rate at which
	    segments are sent, including those on current
	    connections, but excluding those containing
	    only retransmitted bytes."
    ::= { tcpV4 8 }

tcpV4SegmentsPerSec OBJECT-TYPE
    SYNTAX     Gauge32
    MAX-ACCESS read-only
    STATUS     current
    DESCRIPTION
	    "Segments/sec is the rate at which TCP segments
	    are sent or received using the TCP protocol."
    ::= { tcpV4 9 }

tcpV6 OBJECT IDENTIFIER
    ::= { advanced 79 }

tcpV6ConnectionFailures OBJECT-TYPE
    SYNTAX     Gauge32
    MAX-ACCESS read-only
    STATUS     current
    DESCRIPTION
	    "Connection Failures is the number of times TCP
	    connections have made a direct transition to
	    the CLOSED state from the SYN-SENT state or the
	    SYN-RCVD state, plus the number of times TCP
	    connections have made a direct transition to
	    the LISTEN state from the SYN-RCVD state."
    ::= { tcpV6 1 }

tcpV6ConnectionsActive OBJECT-TYPE
    SYNTAX     Gauge32
    MAX-ACCESS read-only
    STATUS     current
    DESCRIPTION
	    "Connections Active is the number of times TCP
	    connections have made a direct transition to
	    the SYN-SENT state from the CLOSED state."
    ::= { tcpV6 2 }

tcpV6ConnectionsEstablished OBJECT-TYPE
    SYNTAX     Gauge32
    MAX-ACCESS read-only
    STATUS     current
    DESCRIPTION
	    "Connections Established is the number of TCP
	    connections for which the current state is
	    either ESTABLISHED or CLOSE-WAIT."
    ::= { tcpV6 3 }

tcpV6ConnectionsPassive OBJECT-TYPE
    SYNTAX     Gauge32
    MAX-ACCESS read-only
    STATUS     current
    DESCRIPTION
	    "Connections Passive is the number of times TCP
	    connections have made a direct transition to
	    the SYN-RCVD state from the LISTEN state."
    ::= { tcpV6 4 }

tcpV6ConnectionsReset OBJECT-TYPE
    SYNTAX     Gauge32
    MAX-ACCESS read-only
    STATUS     current
    DESCRIPTION
	    "Connections Reset is the number of times TCP
	    connections have made a direct transition to
	    the CLOSED state from either the ESTABLISHED
	    state or the CLOSE-WAIT state."
    ::= { tcpV6 5 }

tcpV6SegmentsReceivedPerSec OBJECT-TYPE
    SYNTAX     Gauge32
    MAX-ACCESS read-only
    STATUS     current
    DESCRIPTION
	    "Segments Received/sec is the rate at which
	    segments are received, including those received
	    in error.  This count includes segments
	    received on currently established connections."
    ::= { tcpV6 6 }

tcpV6SegmentsRetransmittedPerSec OBJECT-TYPE
    SYNTAX     Gauge32
    MAX-ACCESS read-only
    STATUS     current
    DESCRIPTION
	    "Segments Retransmitted/sec is the rate at
	    which segments are retransmitted, that is,
	    segments transmitted containing one or more
	    previously transmitted bytes."
    ::= { tcpV6 7 }

tcpV6SegmentsSentPerSec OBJECT-TYPE
    SYNTAX     Gauge32
    MAX-ACCESS read-only
    STATUS     current
    DESCRIPTION
	    "Segments Sent/sec is the rate at which
	    segments are sent, including those on current
	    connections, but excluding those containing
	    only retransmitted bytes."
    ::= { tcpV6 8 }

tcpV6SegmentsPerSec OBJECT-TYPE
    SYNTAX     Gauge32
    MAX-ACCESS read-only
    STATUS     current
    DESCRIPTION
	    "Segments/sec is the rate at which TCP segments
	    are sent or received using the TCP protocol."
    ::= { tcpV6 9 }

telephony OBJECT-IDENTITY
    STATUS     current
    DESCRIPTION
	    "The Telephony performance object provides
	    counters for monitoring telephone-communication
	    activity on a computer running Windows 2000."
    ::= { advanced 80 }

telephonyActiveLines OBJECT-TYPE
    SYNTAX     Gauge32
    MAX-ACCESS read-only
    STATUS     current
    DESCRIPTION
	    "The number of telephone lines serviced by this
	    computer that are currently active."
    ::= { telephony 1 }

telephonyActiveTelephones OBJECT-TYPE
    SYNTAX     Gauge32
    MAX-ACCESS read-only
    STATUS     current
    DESCRIPTION
	    "The number of telephone devices that are
	    currently being monitored."
    ::= { telephony 2 }

telephonyClientApps OBJECT-TYPE
    SYNTAX     Gauge32
    MAX-ACCESS read-only
    STATUS     current
    DESCRIPTION
	    "The number of applications that are currently
	    using telephony services."
    ::= { telephony 3 }

telephonyCurrentIncomingCalls OBJECT-TYPE
    SYNTAX     Gauge32
    MAX-ACCESS read-only
    STATUS     current
    DESCRIPTION
	    "Current incoming calls being serviced by this
	    computer."
    ::= { telephony 4 }

telephonyCurrentOutgoingCalls OBJECT-TYPE
    SYNTAX     Gauge32
    MAX-ACCESS read-only
    STATUS     current
    DESCRIPTION
	    "Current outgoing calls being serviced by this
	    computer."
    ::= { telephony 5 }

telephonyIncomingCallsPerSec OBJECT-TYPE
    SYNTAX     Gauge32
    MAX-ACCESS read-only
    STATUS     current
    DESCRIPTION
	    "The rate of incoming calls answered by this
	    computer."
    ::= { telephony 6 }

telephonyLines OBJECT-TYPE
    SYNTAX     Gauge32
    MAX-ACCESS read-only
    STATUS     current
    DESCRIPTION
	    "The number of telephone lines serviced by this
	    computer."
    ::= { telephony 7 }

telephonyOutgoingCallsPerSec OBJECT-TYPE
    SYNTAX     Gauge32
    MAX-ACCESS read-only
    STATUS     current
    DESCRIPTION
	    "The rate of outgoing calls made by this
	    computer."
    ::= { telephony 8 }

telephonyTelephoneDevices OBJECT-TYPE
    SYNTAX     Gauge32
    MAX-ACCESS read-only
    STATUS     current
    DESCRIPTION
	    "The number of telephone devices serviced by
	    this computer."
    ::= { telephony 9 }

terminalServices OBJECT IDENTIFIER
    ::= { advanced 81 }

tsActiveSessions OBJECT-TYPE
    SYNTAX     Gauge32
    MAX-ACCESS read-only
    STATUS     current
    DESCRIPTION
	    "Number of active Terminal Services sessions."
    ::= { terminalServices 1 }

tsInactiveSessions OBJECT-TYPE
    SYNTAX     Gauge32
    MAX-ACCESS read-only
    STATUS     current
    DESCRIPTION
	    "Number of inactive Terminal Services
	    sessions."
    ::= { terminalServices 2 }

tsTotalSessions OBJECT-TYPE
    SYNTAX     Gauge32
    MAX-ACCESS read-only
    STATUS     current
    DESCRIPTION
	    "Total number of Terminal Services sessions."
    ::= { terminalServices 3 }

terminalServicesSessionTable OBJECT-TYPE
    SYNTAX     SEQUENCE OF TerminalServicesSessionEntry
    MAX-ACCESS not-accessible
    STATUS     current
    DESCRIPTION
	    "The Terminal Services Session object provides
	    per-session resource statistics such as packet
	    and frame transmission data, errors, and cache
	    activity for Terminal Services."
    ::= { advanced 82 }

terminalServicesSessionEntry OBJECT-TYPE
    SYNTAX     TerminalServicesSessionEntry
    MAX-ACCESS not-accessible
    STATUS     current
    DESCRIPTION
	    "Performance information for one particular
	    instance of 'Terminal Services Session'
	    object."
    INDEX      { tssInstance }
    ::= { terminalServicesSessionTable 1 }

TerminalServicesSessionEntry ::= SEQUENCE {
    tssInstance InstanceName,
    tssPercentPrivilegedTime Gauge32,
    tssPercentProcessorTime Gauge32,
    tssPercentUserTime Gauge32,
    tssHandleCount Gauge32,
    tssInputAsyncFrameError Gauge32,
    tssInputAsyncOverflow Gauge32,
    tssInputAsyncOverrun Gauge32,
    tssInputAsyncParityError Gauge32,
    tssInputBytes Gauge32,
    tssInputCompressFlushes Gauge32,
    tssInputCompressedBytes Gauge32,
    tssInputCompressionRatio Gauge32,
    tssInputErrors Gauge32,
    tssInputFrames Gauge32,
    tssInputTimeouts Gauge32,
    tssInputTransportErrors Gauge32,
    tssInputWaitForOutBuf Gauge32,
    tssInputWdBytes Gauge32,
    tssInputWdFrames Gauge32,
    tssOutputAsyncFrameError Gauge32,
    tssOutputAsyncOverflow Gauge32,
    tssOutputAsyncOverrun Gauge32,
    tssOutputAsyncParityError Gauge32,
    tssOutputBytes Gauge32,
    tssOutputCompressFlushes Gauge32,
    tssOutputCompressedBytes Gauge32,
    tssOutputCompressionRatio Gauge32,
    tssOutputErrors Gauge32,
    tssOutputFrames Gauge32,
    tssOutputTimeouts Gauge32,
    tssOutputTransportErrors Gauge32,
    tssOutputWaitForOutBuf Gauge32,
    tssOutputWdBytes Gauge32,
    tssOutputWdFrames Gauge32,
    tssPageFaultsPerSec Gauge32,
    tssPageFileBytes Gauge32,
    tssPageFileBytesPeak Gauge32,
    tssPoolNonpagedBytes Gauge32,
    tssPoolPagedBytes Gauge32,
    tssPrivateBytes Gauge32,
    tssProtocolBitmapCacheHitRatio Gauge32,
    tssProtocolBitmapCacheHits Gauge32,
    tssProtocolBitmapCacheReads Gauge32,
    tssProtocolBrushCacheHitRatio Gauge32,
    tssProtocolBrushCacheHits Gauge32,
    tssProtocolBrushCacheReads Gauge32,
    tssProtocolGlyphCacheHitRatio Gauge32,
    tssProtocolGlyphCacheHits Gauge32,
    tssProtocolGlyphCacheReads Gauge32,
    tssProtocolSvScrnBtmpCachHtRatio Gauge32,
    tssProtocolSvScrnBtmpCachHts Gauge32,
    tssProtocolSvScrnBtmpCachReads Gauge32,
    tssThreadCount Gauge32,
    tssTotalAsyncFrameError Gauge32,
    tssTotalAsyncOverflow Gauge32,
    tssTotalAsyncOverrun Gauge32,
    tssTotalAsyncParityError Gauge32,
    tssTotalBytes Gauge32,
    tssTotalCompressFlushes Gauge32,
    tssTotalCompressedBytes Gauge32,
    tssTotalCompressionRatio Gauge32,
    tssTotalErrors Gauge32,
    tssTotalFrames Gauge32,
    tssTotalProtocolCacheHitRatio Gauge32,
    tssTotalProtocolCacheHits Gauge32,
    tssTotalProtocolCacheReads Gauge32,
    tssTotalTimeouts Gauge32,
    tssTotalTransportErrors Gauge32,
    tssTotalWaitForOutBuf Gauge32,
    tssTotalWdBytes Gauge32,
    tssTotalWdFrames Gauge32,
    tssVirtualBytes Gauge32,
    tssVirtualBytesPeak Gauge32,
    tssWorkingSet Gauge32,
    tssWorkingSetPeak Gauge32
}

tssInstance OBJECT-TYPE
    SYNTAX     InstanceName
    MAX-ACCESS read-only
    STATUS     current
    DESCRIPTION
	    "Instance name."
    ::= { terminalServicesSessionEntry 1 }

tssPercentPrivilegedTime OBJECT-TYPE
    SYNTAX     Gauge32
    MAX-ACCESS read-only
    STATUS     current
    DESCRIPTION
	    "% Privileged Time is the percentage of elapsed
	    time that the threads of the process have spent
	    executing code in privileged mode.	When a
	    Windows NT system service is called, the
	    service will often run in Privileged Mode to
	    gain access to system-private data.  Such data
	    is protected from access by threads executing
	    in user Mode.  Calls to the system can be
	    explicit or implicit, such as page faults or
	    interrupts.  Unlike some early operating
	    systems, Windows NT uses process boundaries for
	    subsystem protection in addition to the
	    traditional protection of user and privileged
	    modes.  These subsystem processes provide
	    additional protection.  Therefore, some work
	    done by Windows NT on behalf of your
	    application might appear in other subsystem
	    processes in addition to the privileged time in
	    your process."
    ::= { terminalServicesSessionEntry 2 }

tssPercentProcessorTime OBJECT-TYPE
    SYNTAX     Gauge32
    MAX-ACCESS read-only
    STATUS     current
    DESCRIPTION
	    "% Processor Time is the percentage of elapsed
	    time that all of the threads of this process
	    used the processor to execute instructions.  An
	    instruction is the basic unit of execution in a
	    computer, a thread is the object that executes
	    instructions, and a process is the object
	    created when a program is run.  Code executed
	    to handle some hardware interrupts and trap
	    conditions are included in this count.  On
	    Multi-processor machines the maximum value of
	    the counter is 100 % times the number of
	    processors."
    ::= { terminalServicesSessionEntry 3 }

tssPercentUserTime OBJECT-TYPE
    SYNTAX     Gauge32
    MAX-ACCESS read-only
    STATUS     current
    DESCRIPTION
	    "% User Time is the percentage of elapsed time
	    that this process' threads have spent executing
	    code in user mode.	Applications, environment
	    subsystems and integral subsystems execute in
	    user mode.	Code executing in user mode cannot
	    damage the integrity of the Windows NT
	    Executive, Kernel, and device drivers.  Unlike
	    some early operating systems, Windows NT uses
	    process boundaries for subsystem protection in
	    addition to the traditional protection of user
	    and privileged modes.  These subsystem
	    processes provide additional protection. 
	    Therefore, some work done by Windows NT on
	    behalf of your application might appear in
	    other subsystem processes in addition to the
	    privileged time in your process."
    ::= { terminalServicesSessionEntry 4 }

tssHandleCount OBJECT-TYPE
    SYNTAX     Gauge32
    MAX-ACCESS read-only
    STATUS     current
    DESCRIPTION
	    "The total number of handles currently open by
	    this process.  This number is the sum of the
	    handles currently open by each thread in this
	    process."
    ::= { terminalServicesSessionEntry 5 }

tssInputAsyncFrameError OBJECT-TYPE
    SYNTAX     Gauge32
    MAX-ACCESS read-only
    STATUS     current
    DESCRIPTION
	    "Number of input async framing errors. These
	    can be caused by a noisy transmission line.
	    Using a smaller packet size may help in some
	    cases."
    ::= { terminalServicesSessionEntry 6 }

tssInputAsyncOverflow OBJECT-TYPE
    SYNTAX     Gauge32
    MAX-ACCESS read-only
    STATUS     current
    DESCRIPTION
	    "Number of input async overflow errors. These
	    can be caused by a lack of buffer space
	    available on the host."
    ::= { terminalServicesSessionEntry 7 }

tssInputAsyncOverrun OBJECT-TYPE
    SYNTAX     Gauge32
    MAX-ACCESS read-only
    STATUS     current
    DESCRIPTION
	    "Number of input async overrun errors. These
	    can be caused by the baud rate being faster
	    than the computer can handle, or a non-16550
	    serial line is used. Overruns can also occur if
	    too many high speed serial lines are active at
	    one time for the processor's power."
    ::= { terminalServicesSessionEntry 8 }

tssInputAsyncParityError OBJECT-TYPE
    SYNTAX     Gauge32
    MAX-ACCESS read-only
    STATUS     current
    DESCRIPTION
	    "Number of input async parity errors. These can
	    be caused by a noisy transmission line"
    ::= { terminalServicesSessionEntry 9 }

tssInputBytes OBJECT-TYPE
    SYNTAX     Gauge32
    MAX-ACCESS read-only
    STATUS     current
    DESCRIPTION
	    "Number of bytes input on this session that
	    includes all protocol overhead."
    ::= { terminalServicesSessionEntry 10 }

tssInputCompressFlushes OBJECT-TYPE
    SYNTAX     Gauge32
    MAX-ACCESS read-only
    STATUS     current
    DESCRIPTION
	    "Number of input compression dictionary
	    flushes. When the data can not be compressed,
	    the compression dictionary is flushed so that
	    newer data has a better chance of being
	    compressed. Some causes of data not compressing
	    includes transferring compressed files over
	    Client Drive Mapping."
    ::= { terminalServicesSessionEntry 11 }

tssInputCompressedBytes OBJECT-TYPE
    SYNTAX     Gauge32
    MAX-ACCESS read-only
    STATUS     current
    DESCRIPTION
	    "Number of bytes input after compression. This
	    number compared with the Total Bytes input is
	    the compression ratio."
    ::= { terminalServicesSessionEntry 12 }

tssInputCompressionRatio OBJECT-TYPE
    SYNTAX     Gauge32
    MAX-ACCESS read-only
    STATUS     current
    DESCRIPTION
	    "Compression ratio of the server input data
	    stream."
    ::= { terminalServicesSessionEntry 13 }

tssInputErrors OBJECT-TYPE
    SYNTAX     Gauge32
    MAX-ACCESS read-only
    STATUS     current
    DESCRIPTION
	    "Number of input errors of all types. Some
	    example input errors are lost ACK's, badly
	    formed packets, etc."
    ::= { terminalServicesSessionEntry 14 }

tssInputFrames OBJECT-TYPE
    SYNTAX     Gauge32
    MAX-ACCESS read-only
    STATUS     current
    DESCRIPTION
	    "Number of frames (packets) input on this
	    Session."
    ::= { terminalServicesSessionEntry 15 }

tssInputTimeouts OBJECT-TYPE
    SYNTAX     Gauge32
    MAX-ACCESS read-only
    STATUS     current
    DESCRIPTION
	    "The total number of timeouts on the
	    communication line as seen from the client side
	    of the connection. These are typically the
	    result of a noisy line. On some high latency
	    networks, this could be the result of the
	    protocol timeout being too short. Increasing
	    the protocol timeout on these types of lines
	    will improve performance by reducing needless
	    re-transmissions."
    ::= { terminalServicesSessionEntry 16 }

tssInputTransportErrors OBJECT-TYPE
    SYNTAX     Gauge32
    MAX-ACCESS read-only
    STATUS     current
    DESCRIPTION
	    "Number of Terminal Services transport-level
	    errors on input."
    ::= { terminalServicesSessionEntry 17 }

tssInputWaitForOutBuf OBJECT-TYPE
    SYNTAX     Gauge32
    MAX-ACCESS read-only
    STATUS     current
    DESCRIPTION
	    "The number of times that a wait for an
	    available send buffer was done by the protocols
	    on the client side of the connection."
    ::= { terminalServicesSessionEntry 18 }

tssInputWdBytes OBJECT-TYPE
    SYNTAX     Gauge32
    MAX-ACCESS read-only
    STATUS     current
    DESCRIPTION
	    "Number of bytes input on this session after
	    all protocol overhead has been removed."
    ::= { terminalServicesSessionEntry 19 }

tssInputWdFrames OBJECT-TYPE
    SYNTAX     Gauge32
    MAX-ACCESS read-only
    STATUS     current
    DESCRIPTION
	    "The number of frames input after any
	    additional protocol added frames have been
	    removed."
    ::= { terminalServicesSessionEntry 20 }

tssOutputAsyncFrameError OBJECT-TYPE
    SYNTAX     Gauge32
    MAX-ACCESS read-only
    STATUS     current
    DESCRIPTION
	    "Number of output async framing errors. This
	    could be caused by a hardware or line problem."
    ::= { terminalServicesSessionEntry 21 }

tssOutputAsyncOverflow OBJECT-TYPE
    SYNTAX     Gauge32
    MAX-ACCESS read-only
    STATUS     current
    DESCRIPTION
	    "Number of output async overflow errors."
    ::= { terminalServicesSessionEntry 22 }

tssOutputAsyncOverrun OBJECT-TYPE
    SYNTAX     Gauge32
    MAX-ACCESS read-only
    STATUS     current
    DESCRIPTION
	    "Number of output async overrun errors."
    ::= { terminalServicesSessionEntry 23 }

tssOutputAsyncParityError OBJECT-TYPE
    SYNTAX     Gauge32
    MAX-ACCESS read-only
    STATUS     current
    DESCRIPTION
	    "Number of output async parity errors. These
	    can be caused by a hardware or line problem."
    ::= { terminalServicesSessionEntry 24 }

tssOutputBytes OBJECT-TYPE
    SYNTAX     Gauge32
    MAX-ACCESS read-only
    STATUS     current
    DESCRIPTION
	    "Number of bytes output on this Session that
	    includes all protocol overhead."
    ::= { terminalServicesSessionEntry 25 }

tssOutputCompressFlushes OBJECT-TYPE
    SYNTAX     Gauge32
    MAX-ACCESS read-only
    STATUS     current
    DESCRIPTION
	    "Number of output compression dictionary
	    flushes. When the data can not be compressed,
	    the compression dictionary is flushed so that
	    newer data has a better chance of being
	    compressed. Some causes of data not compressing
	    includes transfering compressed files over
	    Client Drive Mapping."
    ::= { terminalServicesSessionEntry 26 }

tssOutputCompressedBytes OBJECT-TYPE
    SYNTAX     Gauge32
    MAX-ACCESS read-only
    STATUS     current
    DESCRIPTION
	    "Number of bytes output after compression. This
	    number compared with the Total Bytes output is
	    the compression ratio."
    ::= { terminalServicesSessionEntry 27 }

tssOutputCompressionRatio OBJECT-TYPE
    SYNTAX     Gauge32
    MAX-ACCESS read-only
    STATUS     current
    DESCRIPTION
	    "Compression ratio of the server output data
	    stream."
    ::= { terminalServicesSessionEntry 28 }

tssOutputErrors OBJECT-TYPE
    SYNTAX     Gauge32
    MAX-ACCESS read-only
    STATUS     current
    DESCRIPTION
	    "Number of output errors of all types. Some
	    example output errors are lost ACK's, badly
	    formed packets, etc."
    ::= { terminalServicesSessionEntry 29 }

tssOutputFrames OBJECT-TYPE
    SYNTAX     Gauge32
    MAX-ACCESS read-only
    STATUS     current
    DESCRIPTION
	    "Number of frames (packets) output on this
	    session."
    ::= { terminalServicesSessionEntry 30 }

tssOutputTimeouts OBJECT-TYPE
    SYNTAX     Gauge32
    MAX-ACCESS read-only
    STATUS     current
    DESCRIPTION
	    "The total number of timeouts on the
	    communication line from the host side of the
	    connection. These are typically the result of a
	    noisy line. On some high latency networks, this
	    could be the result of the protocol timeout
	    being too short. Increasing the protocol
	    timeout on these types of lines will improve
	    performance by reducing needless
	    re-transmissions."
    ::= { terminalServicesSessionEntry 31 }

tssOutputTransportErrors OBJECT-TYPE
    SYNTAX     Gauge32
    MAX-ACCESS read-only
    STATUS     current
    DESCRIPTION
	    "Number of Terminal Services transport-level
	    errors on output."
    ::= { terminalServicesSessionEntry 32 }

tssOutputWaitForOutBuf OBJECT-TYPE
    SYNTAX     Gauge32
    MAX-ACCESS read-only
    STATUS     current
    DESCRIPTION
	    "This is the number of times that a wait for an
	    available send buffer was done by the protocol
	    on the server side of the connection."
    ::= { terminalServicesSessionEntry 33 }

tssOutputWdBytes OBJECT-TYPE
    SYNTAX     Gauge32
    MAX-ACCESS read-only
    STATUS     current
    DESCRIPTION
	    "Number of bytes output on this session after
	    all protocol overhead has been removed."
    ::= { terminalServicesSessionEntry 34 }

tssOutputWdFrames OBJECT-TYPE
    SYNTAX     Gauge32
    MAX-ACCESS read-only
    STATUS     current
    DESCRIPTION
	    "The number of frames output before any
	    additional protocol frames have been added."
    ::= { terminalServicesSessionEntry 35 }

tssPageFaultsPerSec OBJECT-TYPE
    SYNTAX     Gauge32
    MAX-ACCESS read-only
    STATUS     current
    DESCRIPTION
	    "Page Faults/sec is the rate Page Faults occur
	    in the threads executing in this process.  A
	    page fault occurs when a thread refers to a
	    virtual memory page that is not in its working
	    set in main memory.  This will not cause the
	    page to be fetched from disk if it is on the
	    standby list and hence already in main memory,
	    or if it is in use by another process with whom
	    the page is shared."
    ::= { terminalServicesSessionEntry 36 }

tssPageFileBytes OBJECT-TYPE
    SYNTAX     Gauge32
    MAX-ACCESS read-only
    STATUS     current
    DESCRIPTION
	    "Page File Bytes is the current number of bytes
	    this process has used in the paging file(s). 
	    Paging files are used to store pages of memory
	    used by the process that are not contained in
	    other files.  Paging files are shared by all
	    processes, and lack of space in paging files
	    can prevent other processes from allocating
	    memory."
    ::= { terminalServicesSessionEntry 37 }

tssPageFileBytesPeak OBJECT-TYPE
    SYNTAX     Gauge32
    MAX-ACCESS read-only
    STATUS     current
    DESCRIPTION
	    "Page File Bytes Peak is the maximum number of
	    bytes this process has used in the paging
	    file(s).  Paging files are used to store pages
	    of memory used by the process that are not
	    contained in other files.  Paging files are
	    shared by all processes, and lack of space in
	    paging files can prevent other processes from
	    allocating memory."
    ::= { terminalServicesSessionEntry 38 }

tssPoolNonpagedBytes OBJECT-TYPE
    SYNTAX     Gauge32
    MAX-ACCESS read-only
    STATUS     current
    DESCRIPTION
	    "Pool Nonpaged Bytes is the number of bytes in
	    the nonpaged pool, an area of system memory
	    (physical memory used by the operating system)
	    for objects that cannot be written to disk, but
	    must remain in physical memory as long as they
	    are allocated.  Memory: Pool Nonpaged Bytes is
	    calculated differently than Process: Pool
	    Nonpaged Bytes, so it might not equal Process:
	    Pool Nonpaged Bytes: _Total.  This counter
	    displays the last observed value only; it is
	    not an average.  "
    ::= { terminalServicesSessionEntry 39 }

tssPoolPagedBytes OBJECT-TYPE
    SYNTAX     Gauge32
    MAX-ACCESS read-only
    STATUS     current
    DESCRIPTION
	    "Pool Paged Bytes is the number of bytes in the
	    paged pool, an area of system memory (physical
	    memory used by the operating system) for
	    objects that can be written to disk when they
	    are not being used.  Memory: Pool Paged Bytes
	    is calculated differently than Process: Pool
	    Paged Bytes, so it might not equal Process:
	    Pool Paged Bytes: _Total.  This counter
	    displays the last observed value only; it is
	    not an average.  "
    ::= { terminalServicesSessionEntry 40 }

tssPrivateBytes OBJECT-TYPE
    SYNTAX     Gauge32
    MAX-ACCESS read-only
    STATUS     current
    DESCRIPTION
	    "Private Bytes is the current number of bytes
	    this process has allocated that cannot be
	    shared with other processes."
    ::= { terminalServicesSessionEntry 41 }

tssProtocolBitmapCacheHitRatio OBJECT-TYPE
    SYNTAX     Gauge32
    MAX-ACCESS read-only
    STATUS     current
    DESCRIPTION
	    "Hit ratio in the protocol bitmap cache. A
	    higher hit ratio means better performance since
	    data transmissions are reduced. Low hit ratios
	    are due to the screen updating with new
	    information that is either not re-used, or is
	    flushed out of the client cache."
    ::= { terminalServicesSessionEntry 42 }

tssProtocolBitmapCacheHits OBJECT-TYPE
    SYNTAX     Gauge32
    MAX-ACCESS read-only
    STATUS     current
    DESCRIPTION
	    "Number of hits in the protocol bitmap cache."
    ::= { terminalServicesSessionEntry 43 }

tssProtocolBitmapCacheReads OBJECT-TYPE
    SYNTAX     Gauge32
    MAX-ACCESS read-only
    STATUS     current
    DESCRIPTION
	    "Number of references to the protocol bitmap
	    cache."
    ::= { terminalServicesSessionEntry 44 }

tssProtocolBrushCacheHitRatio OBJECT-TYPE
    SYNTAX     Gauge32
    MAX-ACCESS read-only
    STATUS     current
    DESCRIPTION
	    "Hit ratio in the protocol brush cache. A
	    higher hit ratio means better performance since
	    data transmissions are reduced. Low hit ratios
	    are due to the screen updating with new
	    information that is either not re-used, or is
	    flushed out of the client cache."
    ::= { terminalServicesSessionEntry 45 }

tssProtocolBrushCacheHits OBJECT-TYPE
    SYNTAX     Gauge32
    MAX-ACCESS read-only
    STATUS     current
    DESCRIPTION
	    "Number of hits in the protocol brush cache."
    ::= { terminalServicesSessionEntry 46 }

tssProtocolBrushCacheReads OBJECT-TYPE
    SYNTAX     Gauge32
    MAX-ACCESS read-only
    STATUS     current
    DESCRIPTION
	    "Number of references to the protocol brush
	    cache."
    ::= { terminalServicesSessionEntry 47 }

tssProtocolGlyphCacheHitRatio OBJECT-TYPE
    SYNTAX     Gauge32
    MAX-ACCESS read-only
    STATUS     current
    DESCRIPTION
	    "Hit ratio in the protocol glyph cache. A
	    higher hit ratio means better performance since
	    data transmissions are reduced. Low hit ratios
	    are due to the screen updating with new
	    information that is either not re-used, or is
	    flushed out of the client cache."
    ::= { terminalServicesSessionEntry 48 }

tssProtocolGlyphCacheHits OBJECT-TYPE
    SYNTAX     Gauge32
    MAX-ACCESS read-only
    STATUS     current
    DESCRIPTION
	    "Number of hits in the protocol glyph cache."
    ::= { terminalServicesSessionEntry 49 }

tssProtocolGlyphCacheReads OBJECT-TYPE
    SYNTAX     Gauge32
    MAX-ACCESS read-only
    STATUS     current
    DESCRIPTION
	    "Number of references to the protocol glyph
	    cache."
    ::= { terminalServicesSessionEntry 50 }

tssProtocolSvScrnBtmpCachHtRatio OBJECT-TYPE
    SYNTAX     Gauge32
    MAX-ACCESS read-only
    STATUS     current
    DESCRIPTION
	    "Hit ratio in the protocol save screen bitmap
	    cache. A higher hit ratio means better
	    performance since data transmissions are
	    reduced. Low hit ratios are due to the screen
	    updating with new information that is either
	    not re-used, or is flushed out of the client
	    cache."
    ::= { terminalServicesSessionEntry 51 }

tssProtocolSvScrnBtmpCachHts OBJECT-TYPE
    SYNTAX     Gauge32
    MAX-ACCESS read-only
    STATUS     current
    DESCRIPTION
	    "Number of hits in the protocol save screen
	    bitmap cache."
    ::= { terminalServicesSessionEntry 52 }

tssProtocolSvScrnBtmpCachReads OBJECT-TYPE
    SYNTAX     Gauge32
    MAX-ACCESS read-only
    STATUS     current
    DESCRIPTION
	    "Number of references to the protocol save
	    screen bitmap cache."
    ::= { terminalServicesSessionEntry 53 }

tssThreadCount OBJECT-TYPE
    SYNTAX     Gauge32
    MAX-ACCESS read-only
    STATUS     current
    DESCRIPTION
	    "The number of threads currently active in this
	    process.  An instruction is the basic unit of
	    execution in a processor, and a thread is the
	    object that executes instructions.	Every
	    running process has at least one thread."
    ::= { terminalServicesSessionEntry 54 }

tssTotalAsyncFrameError OBJECT-TYPE
    SYNTAX     Gauge32
    MAX-ACCESS read-only
    STATUS     current
    DESCRIPTION
	    "Total number of async framing errors. These
	    can be caused by a noisy transmission line.
	    Using a smaller packet size may help in some
	    cases."
    ::= { terminalServicesSessionEntry 55 }

tssTotalAsyncOverflow OBJECT-TYPE
    SYNTAX     Gauge32
    MAX-ACCESS read-only
    STATUS     current
    DESCRIPTION
	    "Total number of async overflow errors. These
	    can be caused by a lack of buffer space
	    available on the host."
    ::= { terminalServicesSessionEntry 56 }

tssTotalAsyncOverrun OBJECT-TYPE
    SYNTAX     Gauge32
    MAX-ACCESS read-only
    STATUS     current
    DESCRIPTION
	    "Total number of async overrun errors. These
	    can be caused by the baud rate being faster
	    than the computer can handle, or a non-16550
	    serial line is used. Overruns can also occur if
	    too many high speed serial lines are active at
	    one time for the processor's power."
    ::= { terminalServicesSessionEntry 57 }

tssTotalAsyncParityError OBJECT-TYPE
    SYNTAX     Gauge32
    MAX-ACCESS read-only
    STATUS     current
    DESCRIPTION
	    "Total number of async parity errors. These can
	    be caused by a noisy transmission line."
    ::= { terminalServicesSessionEntry 58 }

tssTotalBytes OBJECT-TYPE
    SYNTAX     Gauge32
    MAX-ACCESS read-only
    STATUS     current
    DESCRIPTION
	    "Total number of bytes on this Session that
	    includes all protocol overhead."
    ::= { terminalServicesSessionEntry 59 }

tssTotalCompressFlushes OBJECT-TYPE
    SYNTAX     Gauge32
    MAX-ACCESS read-only
    STATUS     current
    DESCRIPTION
	    "Total number of compression dictionary
	    flushes. When the data can not be compressed,
	    the compression dictionary is flushed so that
	    newer data has a better chance of being
	    compressed. Some causes of data not compressing
	    includes transfering compressed files over
	    Client Drive Mapping."
    ::= { terminalServicesSessionEntry 60 }

tssTotalCompressedBytes OBJECT-TYPE
    SYNTAX     Gauge32
    MAX-ACCESS read-only
    STATUS     current
    DESCRIPTION
	    "Total number of bytes after compression. This
	    number compared with the total bytes is the
	    compression ratio."
    ::= { terminalServicesSessionEntry 61 }

tssTotalCompressionRatio OBJECT-TYPE
    SYNTAX     Gauge32
    MAX-ACCESS read-only
    STATUS     current
    DESCRIPTION
	    "Total compression ratio of the server data
	    stream."
    ::= { terminalServicesSessionEntry 62 }

tssTotalErrors OBJECT-TYPE
    SYNTAX     Gauge32
    MAX-ACCESS read-only
    STATUS     current
    DESCRIPTION
	    "Total number of errors of all types. Some
	    example errors are lost ACK's, badly formed
	    packets, etc."
    ::= { terminalServicesSessionEntry 63 }

tssTotalFrames OBJECT-TYPE
    SYNTAX     Gauge32
    MAX-ACCESS read-only
    STATUS     current
    DESCRIPTION
	    "Total number of frames (packets) on this
	    Session."
    ::= { terminalServicesSessionEntry 64 }

tssTotalProtocolCacheHitRatio OBJECT-TYPE
    SYNTAX     Gauge32
    MAX-ACCESS read-only
    STATUS     current
    DESCRIPTION
	    "Overall hit ratio for all protocol caches."
    ::= { terminalServicesSessionEntry 65 }

tssTotalProtocolCacheHits OBJECT-TYPE
    SYNTAX     Gauge32
    MAX-ACCESS read-only
    STATUS     current
    DESCRIPTION
	    "Total hits in all protocol caches. The
	    protocol caches Windows objects that are likely
	    to be re-used to avoid having to re-send them
	    on the transmission line. Example objects are
	    Windows icons and brushes. Hits in the cache
	    represent objects that did not need to be
	    re-sent."
    ::= { terminalServicesSessionEntry 66 }

tssTotalProtocolCacheReads OBJECT-TYPE
    SYNTAX     Gauge32
    MAX-ACCESS read-only
    STATUS     current
    DESCRIPTION
	    "Total references to all protocol caches."
    ::= { terminalServicesSessionEntry 67 }

tssTotalTimeouts OBJECT-TYPE
    SYNTAX     Gauge32
    MAX-ACCESS read-only
    STATUS     current
    DESCRIPTION
	    "The total number of timeouts on the
	    communication line from both the host and
	    client sides of the connection. These are
	    typically the result of a noisy line. On some
	    high latency networks, this could be the result
	    of the protocol timeout being too short.
	    Increasing the protocol timeout on these types
	    of lines will improve performance by reducing
	    needless re-transmissions."
    ::= { terminalServicesSessionEntry 68 }

tssTotalTransportErrors OBJECT-TYPE
    SYNTAX     Gauge32
    MAX-ACCESS read-only
    STATUS     current
    DESCRIPTION
	    "Total number of Terminal Services
	    transport-level errors."
    ::= { terminalServicesSessionEntry 69 }

tssTotalWaitForOutBuf OBJECT-TYPE
    SYNTAX     Gauge32
    MAX-ACCESS read-only
    STATUS     current
    DESCRIPTION
	    "The number of times that a wait for an
	    available send buffer was done by the protocols
	    on both the server and client sides of the
	    connection."
    ::= { terminalServicesSessionEntry 70 }

tssTotalWdBytes OBJECT-TYPE
    SYNTAX     Gauge32
    MAX-ACCESS read-only
    STATUS     current
    DESCRIPTION
	    "Total number of bytes on this Session after
	    all protocol overhead has been removed."
    ::= { terminalServicesSessionEntry 71 }

tssTotalWdFrames OBJECT-TYPE
    SYNTAX     Gauge32
    MAX-ACCESS read-only
    STATUS     current
    DESCRIPTION
	    "The total number of frames input and output
	    before any additional protocol frames have been
	    added."
    ::= { terminalServicesSessionEntry 72 }

tssVirtualBytes OBJECT-TYPE
    SYNTAX     Gauge32
    MAX-ACCESS read-only
    STATUS     current
    DESCRIPTION
	    "Virtual Bytes is the current size in bytes of
	    the virtual address space the process is using.
	     Use of virtual address space does not
	    necessarily imply corresponding use of either
	    disk or main memory pages.	Virtual space is
	    finite, and by using too much, the process can
	    limit its ability to load libraries."
    ::= { terminalServicesSessionEntry 73 }

tssVirtualBytesPeak OBJECT-TYPE
    SYNTAX     Gauge32
    MAX-ACCESS read-only
    STATUS     current
    DESCRIPTION
	    "Virtual Bytes Peak is the maximum number of
	    bytes of virtual address space the process has
	    used at any one time.  Use of virtual address
	    space does not necessarily imply corresponding
	    use of either disk or main memory pages. 
	    Virtual space is however finite, and by using
	    too much, the process might limit its ability
	    to load libraries."
    ::= { terminalServicesSessionEntry 74 }

tssWorkingSet OBJECT-TYPE
    SYNTAX     Gauge32
    MAX-ACCESS read-only
    STATUS     current
    DESCRIPTION
	    "Working Set is the current number of bytes in
	    the Working Set of this process.  The Working
	    Set is the set of memory pages touched recently
	    by the threads in the process.  If free memory
	    in the computer is above a threshold, pages are
	    left in the Working Set of a process even if
	    they are not in use.  When free memory falls
	    below a threshold, pages are trimmed from
	    Working Sets.  If they are needed they will
	    then be soft-faulted back into the Working Set
	    before they leave main memory."
    ::= { terminalServicesSessionEntry 75 }

tssWorkingSetPeak OBJECT-TYPE
    SYNTAX     Gauge32
    MAX-ACCESS read-only
    STATUS     current
    DESCRIPTION
	    "Working Set Peak is the maximum number of
	    bytes in the Working Set of this process at any
	    point in time.  The Working Set is the set of
	    memory pages touched recently by the threads in
	    the process.  If free memory in the computer is
	    above a threshold, pages are left in the
	    Working Set of a process even if they are not
	    in use.  When free memory falls below a
	    threshold, pages are trimmed from Working Sets.
	     If they are needed they will then be
	    soft-faulted back into the Working Set before
	    they leave main memory."
    ::= { terminalServicesSessionEntry 76 }

threadTable OBJECT-TYPE
    SYNTAX     SEQUENCE OF ThreadEntry
    MAX-ACCESS not-accessible
    STATUS     current
    DESCRIPTION
	    "The Thread performance object consists of
	    counters that measure aspects of thread
	    behavior. A thread is the basic object that
	    executes instructions on a processor. All
	    running processes have at least one thread."
    ::= { advanced 83 }

threadEntry OBJECT-TYPE
    SYNTAX     ThreadEntry
    MAX-ACCESS not-accessible
    STATUS     current
    DESCRIPTION
	    "Performance information for one particular
	    instance of 'Thread' object."
    INDEX      { threadInstance }
    ::= { threadTable 1 }

ThreadEntry ::= SEQUENCE {
    threadInstance InstanceName,
    threadPercentPrivilegedTime Gauge32,
    threadPercentProcessorTime Gauge32,
    threadPercentUserTime Gauge32,
    threadContextSwitchesPerSec Gauge32,
    threadElapsedTime Gauge32,
    threadIDProcess Gauge32,
    threadIDThread Gauge32,
    threadPriorityBase Gauge32,
    threadPriorityCurrent Gauge32,
    threadStartAddress Gauge32,
    threadThreadState Gauge32,
    threadThreadWaitReason Gauge32
}

threadInstance OBJECT-TYPE
    SYNTAX     InstanceName
    MAX-ACCESS read-only
    STATUS     current
    DESCRIPTION
	    "Instance name."
    ::= { threadEntry 1 }

threadPercentPrivilegedTime OBJECT-TYPE
    SYNTAX     Gauge32
    MAX-ACCESS read-only
    STATUS     current
    DESCRIPTION
	    "Privileged Time is the percentage of elapsed
	    time that this thread has spent executing code
	    in privileged mode.  When a Windows NT system
	    service is called, the service will often run
	    in privileged mode in order to gain access to
	    system-private data.  Such data is protected
	    from access by threads executing in user mode. 
	    Calls to the system can be explicit or implicit
	    such as page faults and interrupts.  Unlike
	    some early operating systems, Windows NT uses
	    process boundaries for subsystem protection in
	    addition to the traditional protection of user
	    and privileged modes.  These subsystem
	    processes provide additional protection. 
	    Therefore, some work done by Windows NT on
	    behalf of your application might appear in
	    other subsystem processes in addition to the
	    privileged time in your process."
    ::= { threadEntry 2 }

threadPercentProcessorTime OBJECT-TYPE
    SYNTAX     Gauge32
    MAX-ACCESS read-only
    STATUS     current
    DESCRIPTION
	    "% Processor Time is the percentage of elapsed
	    time that this thread used the processor to
	    execute instructions.  An instruction is the
	    basic unit of execution in a processor, and a
	    thread is the object that executes
	    instructions.  Code executed to handle some
	    hardware interrupts and trap conditions are
	    included in this count."
    ::= { threadEntry 3 }

threadPercentUserTime OBJECT-TYPE
    SYNTAX     Gauge32
    MAX-ACCESS read-only
    STATUS     current
    DESCRIPTION
	    "% User Time is the percentage of elapsed time
	    that this thread has spent executing code in
	    user mode.	Applications, environment
	    subsystems, and integral subsystems execute in
	    user mode.	Code executing in user mode cannot
	    damage the integrity of the Windows NT
	    Executive, Kernel, and device drivers.  Unlike
	    some early operating systems, Windows NT uses
	    process boundaries for subsystem protection in
	    addition to the traditional protection of user
	    and privileged modes.  These subsystem
	    processes provide additional protection. 
	    Therefore, some work done by Windows NT on
	    behalf of your application might appear in
	    other subsystem processes in addition to the
	    privileged time in your process."
    ::= { threadEntry 4 }

threadContextSwitchesPerSec OBJECT-TYPE
    SYNTAX     Gauge32
    MAX-ACCESS read-only
    STATUS     current
    DESCRIPTION
	    "Context Switches/sec is the rate of switches
	    from one thread to another.  Thread switches
	    can occur either inside of a single process or
	    across processes.  A thread switch can be
	    caused either by one thread asking another for
	    information, or by a thread being preempted by
	    another, higher priority thread becoming ready
	    to run.  Unlike some early operating systems,
	    Windows NT uses process boundaries for
	    subsystem protection in addition to the
	    traditional protection of user and privileged
	    modes.  These subsystem processes provide
	    additional protection.  Therefore, some work
	    done by Windows NT on behalf of an application 
	    appear in other subsystem processes in addition
	    to the privileged time in the application. 
	    Switching to the subsystem process causes one
	    Context Switch in the application thread. 
	    Switching back causes another Context Switch in
	    the subsystem thread."
    ::= { threadEntry 5 }

threadElapsedTime OBJECT-TYPE
    SYNTAX     Gauge32
    MAX-ACCESS read-only
    STATUS     current
    DESCRIPTION
	    "The total elapsed time (in seconds) this
	    thread has been running."
    ::= { threadEntry 6 }

threadIDProcess OBJECT-TYPE
    SYNTAX     Gauge32
    MAX-ACCESS read-only
    STATUS     current
    DESCRIPTION
	    "ID Process is the unique identifier of this
	    process.  ID Process numbers are reused, so
	    they only identify a process for the lifetime
	    of that process."
    ::= { threadEntry 7 }

threadIDThread OBJECT-TYPE
    SYNTAX     Gauge32
    MAX-ACCESS read-only
    STATUS     current
    DESCRIPTION
	    "ID Thread is the unique identifier of this
	    thread.  ID Thread numbers are reused, so they
	    only identify a thread for the lifetime of that
	    thread."
    ::= { threadEntry 8 }

threadPriorityBase OBJECT-TYPE
    SYNTAX     Gauge32
    MAX-ACCESS read-only
    STATUS     current
    DESCRIPTION
	    "The current base priority of this thread.	The
	    system can raise the thread's dynamic priority
	    above the base priority if the thread is
	    handling user input, or lower it towards the
	    base priority if the thread becomes compute
	    bound."
    ::= { threadEntry 9 }

threadPriorityCurrent OBJECT-TYPE
    SYNTAX     Gauge32
    MAX-ACCESS read-only
    STATUS     current
    DESCRIPTION
	    "The current dynamic priority of this thread. 
	    The system can raise the thread's dynamic
	    priority above the base priority if the thread
	    is handling user input, or lower it towards the
	    base priority if the thread becomes compute
	    bound."
    ::= { threadEntry 10 }

threadStartAddress OBJECT-TYPE
    SYNTAX     Gauge32
    MAX-ACCESS read-only
    STATUS     current
    DESCRIPTION
	    "Starting virtual address for this thread."
    ::= { threadEntry 11 }

threadThreadState OBJECT-TYPE
    SYNTAX     Gauge32
    MAX-ACCESS read-only
    STATUS     current
    DESCRIPTION
	    "Thread State is the current state of the
	    thread.  It is 0 for Initialized, 1 for Ready,
	    2 for Running, 3 for Standby, 4 for Terminated,
	    5 for Wait, 6 for Transition, 7 for Unknown.  A
	    Running thread is using a processor; a Standby
	    thread is about to use one.  A Ready thread
	    wants to use a processor, but is waiting for a
	    processor because none are free.  A thread in
	    Transition is waiting for a resource in order
	    to execute, such as waiting for its execution
	    stack to be paged in from disk.  A Waiting
	    thread has no use for the processor because it
	    is waiting for a peripheral operation to
	    complete or a resource to become free."
    ::= { threadEntry 12 }

threadThreadWaitReason OBJECT-TYPE
    SYNTAX     Gauge32
    MAX-ACCESS read-only
    STATUS     current
    DESCRIPTION
	    "Thread Wait Reason is only applicable when the
	    thread is in the Wait state (see Thread State).
	     It is 0 or 7 when the thread is waiting for
	    the Executive, 1 or 8 for a Free Page, 2 or 9
	    for a Page In, 3 or 10 for a Pool Allocation, 4
	    or 11 for an Execution Delay, 5 or 12 for a
	    Suspended condition, 6 or 13 for a User
	    Request, 14 for an Event Pair High, 15 for an
	    Event Pair Low, 16 for an LPC Receive, 17 for
	    an LPC Reply, 18 for Virtual Memory, 19 for a
	    Page Out; 20 and higher are not assigned at the
	    time of this writing.  Event Pairs are used to
	    communicate with protected subsystems (see
	    Context Switches)."
    ::= { threadEntry 13 }

udpV4 OBJECT-IDENTITY
    STATUS     current
    DESCRIPTION
	    "The UDP performance object consists of
	    counters that measure the rates at which User
	    Data Protocol (UDP) datagrams are sent and
	    received using the UDP. It includes counters
	    that monitor UDP errors."
    ::= { advanced 84 }

udpV4DatagramsNoPortPerSec OBJECT-TYPE
    SYNTAX     Gauge32
    MAX-ACCESS read-only
    STATUS     current
    DESCRIPTION
	    "Datagrams No Port/sec is the rate of received
	    UDP datagrams for which there was no
	    application at the destination port."
    ::= { udpV4 1 }

udpV4DatagramsReceivedErrors OBJECT-TYPE
    SYNTAX     Gauge32
    MAX-ACCESS read-only
    STATUS     current
    DESCRIPTION
	    "Datagrams Received Errors is the number of
	    received UDP datagrams that could not be
	    delivered for reasons other than the lack of an
	    application at the destination port."
    ::= { udpV4 2 }

udpV4DatagramsReceivedPerSec OBJECT-TYPE
    SYNTAX     Gauge32
    MAX-ACCESS read-only
    STATUS     current
    DESCRIPTION
	    "Datagrams Received/sec is the rate at which
	    UDP datagrams are delivered to UDP users."
    ::= { udpV4 3 }

udpV4DatagramsSentPerSec OBJECT-TYPE
    SYNTAX     Gauge32
    MAX-ACCESS read-only
    STATUS     current
    DESCRIPTION
	    "Datagrams Sent/sec is the rate at which UDP
	    datagrams are sent from the entity."
    ::= { udpV4 4 }

udpV4DatagramsPerSec OBJECT-TYPE
    SYNTAX     Gauge32
    MAX-ACCESS read-only
    STATUS     current
    DESCRIPTION
	    "Datagrams/sec is the rate at which UDP
	    datagrams are sent or received by the entity."
    ::= { udpV4 5 }

udpV6 OBJECT IDENTIFIER
    ::= { advanced 85 }

udpV6DatagramsNoPortPerSec OBJECT-TYPE
    SYNTAX     Gauge32
    MAX-ACCESS read-only
    STATUS     current
    DESCRIPTION
	    "Datagrams No Port/sec is the rate of received
	    UDP datagrams for which there was no
	    application at the destination port."
    ::= { udpV6 1 }

udpV6DatagramsReceivedErrors OBJECT-TYPE
    SYNTAX     Gauge32
    MAX-ACCESS read-only
    STATUS     current
    DESCRIPTION
	    "Datagrams Received Errors is the number of
	    received UDP datagrams that could not be
	    delivered for reasons other than the lack of an
	    application at the destination port."
    ::= { udpV6 2 }

udpV6DatagramsReceivedPerSec OBJECT-TYPE
    SYNTAX     Gauge32
    MAX-ACCESS read-only
    STATUS     current
    DESCRIPTION
	    "Datagrams Received/sec is the rate at which
	    UDP datagrams are delivered to UDP users."
    ::= { udpV6 3 }

udpV6DatagramsSentPerSec OBJECT-TYPE
    SYNTAX     Gauge32
    MAX-ACCESS read-only
    STATUS     current
    DESCRIPTION
	    "Datagrams Sent/sec is the rate at which UDP
	    datagrams are sent from the entity."
    ::= { udpV6 4 }

udpV6DatagramsPerSec OBJECT-TYPE
    SYNTAX     Gauge32
    MAX-ACCESS read-only
    STATUS     current
    DESCRIPTION
	    "Datagrams/sec is the rate at which UDP
	    datagrams are sent or received by the entity."
    ::= { udpV6 5 }

webServiceTable OBJECT-TYPE
    SYNTAX     SEQUENCE OF WebServiceEntry
    MAX-ACCESS not-accessible
    STATUS     current
    DESCRIPTION
	    "The Web Service object counters installed with
	    Internet Information Service monitor file
	    transfer rates, bandwidth usage, and connection
	    rates. You can view performance data for all
	    instances of this object (using the _Total
	    instance) or for specific instances, such as
	    the Default Web Site or Administration Web Site
	    instances. In addition to these counters,
	    counters supplied by the Internet Information
	    Services Global performance object combine data
	    for the Web service with the performance data
	    they report for IIS as a whole. For more
	    information, see the Internet Information
	    Services Global object."
    ::= { advanced 86 }

webServiceEntry OBJECT-TYPE
    SYNTAX     WebServiceEntry
    MAX-ACCESS not-accessible
    STATUS     current
    DESCRIPTION
	    "Performance information for one particular
	    instance of 'Web Service' object."
    INDEX      { wsInstance }
    ::= { webServiceTable 1 }

WebServiceEntry ::= SEQUENCE {
    wsInstance InstanceName,
    wsAnonymousUsersPerSec Gauge32,
    wsBytesReceivedPerSec Gauge32,
    wsBytesSentPerSec Gauge32,
    wsBytesTotalPerSec Gauge32,
    wsCGIRqstsPerSec Gauge32,
    wsConnAtmpsPerSec Gauge32,
    wsCopyRqstsPerSec Gauge32,
    wsCurrentAnonymousUsers Gauge32,
    wsCurrentBlkdAsyncIORqsts Gauge32,
    wsCurrentCALCountForSSLConns Gauge32,
    wsCurrentCALCountForAuthdUsers Gauge32,
    wsCurrentCGIRqsts Gauge32,
    wsCurrentConns Gauge32,
    wsCurrentISAPIExtensionRqsts Gauge32,
    wsCurrentNonAnonymousUsers Gauge32,
    wsCurrentBlkdBandwidthBytes Gauge32,
    wsDeleteRqstsPerSec Gauge32,
    wsFilesReceivedPerSec Gauge32,
    wsFilesSentPerSec Gauge32,
    wsFilesPerSec Gauge32,
    wsGetRqstsPerSec Gauge32,
    wsHeadRqstsPerSec Gauge32,
    wsISAPIExtensionRqstsPerSec Gauge32,
    wsLockRqstsPerSec Gauge32,
    wsLockedErrorsPerSec Gauge32,
    wsLogonAtmpsPerSec Gauge32,
    wsMaximumAnonymousUsers Gauge32,
    wsMaximumCALCountForSSLConns Gauge32,
    wsMaximumCALCountForAuthdUsers Gauge32,
    wsMaximumCGIRqsts Gauge32,
    wsMaximumConns Gauge32,
    wsMaximumISAPIExtensionRqsts Gauge32,
    wsMaximumNonAnonymousUsers Gauge32,
    wsMeasuredAsyncIOBandwidthUsage Gauge32,
    wsMkcolRqstsPerSec Gauge32,
    wsMoveRqstsPerSec Gauge32,
    wsNonAnonymousUsersPerSec Gauge32,
    wsNotFoundErrorsPerSec Gauge32,
    wsOptionsRqstsPerSec Gauge32,
    wsOtherRqstMethodsPerSec Gauge32,
    wsPostRqstsPerSec Gauge32,
    wsPropfindRqstsPerSec Gauge32,
    wsProppatchRqstsPerSec Gauge32,
    wsPutRqstsPerSec Gauge32,
    wsSearchRqstsPerSec Gauge32,
    wsServiceUptime Gauge32,
    wsTotalAllowedAsyncIORqsts Gauge32,
    wsTotalAnonymousUsers Gauge32,
    wsTotalBlkdAsyncIORqsts Gauge32,
    wsTotalBytesReceived Gauge32,
    wsTotalBytesSent Gauge32,
    wsTotalBytesTransfered Gauge32,
    wsTotalCGIRqsts Gauge32,
    wsTotalConnAtmpsAllInstances Gauge32,
    wsTotalCopyRqsts Gauge32,
    wsTotalDeleteRqsts Gauge32,
    wsTotalFilesReceived Gauge32,
    wsTotalFilesSent Gauge32,
    wsTotalFilesTransferred Gauge32,
    wsTotalGetRqsts Gauge32,
    wsTotalHeadRqsts Gauge32,
    wsTotalISAPIExtensionRqsts Gauge32,
    wsTotalLockRqsts Gauge32,
    wsTotalLockedErrors Gauge32,
    wsTotalLogonAtmps Gauge32,
    wsTotalMethodRqsts Gauge32,
    wsTotalMethodRqstsPerSec Gauge32,
    wsTotalMkcolRqsts Gauge32,
    wsTotalMoveRqsts Gauge32,
    wsTotalNonAnonymousUsers Gauge32,
    wsTotalNotFoundErrors Gauge32,
    wsTotalOptionsRqsts Gauge32,
    wsTotalOtherRqstMethods Gauge32,
    wsTotalPostRqsts Gauge32,
    wsTotalPropfindRqsts Gauge32,
    wsTotalProppatchRqsts Gauge32,
    wsTotalPutRqsts Gauge32,
    wsTotalRejectedAsyncIORqsts Gauge32,
    wsTotalSearchRqsts Gauge32,
    wsTotalTraceRqsts Gauge32,
    wsTotalUnlockRqsts Gauge32,
    wsTotalBlkdBandwidthBytes Gauge32,
    wsTotalCountFailCALRqstsSSLConns Gauge32,
    wsTotalCountFailCALRqstsAuthdUsr Gauge32,
    wsTraceRqstsPerSec Gauge32,
    wsUnlockRqstsPerSec Gauge32
}

wsInstance OBJECT-TYPE
    SYNTAX     InstanceName
    MAX-ACCESS read-only
    STATUS     current
    DESCRIPTION
	    "Instance name."
    ::= { webServiceEntry 1 }

wsAnonymousUsersPerSec OBJECT-TYPE
    SYNTAX     Gauge32
    MAX-ACCESS read-only
    STATUS     current
    DESCRIPTION
	    "The rate users are making anonymous
	    connections to the Web service."
    ::= { webServiceEntry 2 }

wsBytesReceivedPerSec OBJECT-TYPE
    SYNTAX     Gauge32
    MAX-ACCESS read-only
    STATUS     current
    DESCRIPTION
	    "Bytes Received/sec is the rate that data bytes
	    are received by the Web service."
    ::= { webServiceEntry 3 }

wsBytesSentPerSec OBJECT-TYPE
    SYNTAX     Gauge32
    MAX-ACCESS read-only
    STATUS     current
    DESCRIPTION
	    "Bytes Sent/sec is the rate data bytes are
	    being sent by the Web service."
    ::= { webServiceEntry 4 }

wsBytesTotalPerSec OBJECT-TYPE
    SYNTAX     Gauge32
    MAX-ACCESS read-only
    STATUS     current
    DESCRIPTION
	    "Bytes Total/sec is the sum of Bytes Sent/sec
	    and Bytes Received/sec.  This is the total rate
	    of bytes transferred by the Web service."
    ::= { webServiceEntry 5 }

wsCGIRqstsPerSec OBJECT-TYPE
    SYNTAX     Gauge32
    MAX-ACCESS read-only
    STATUS     current
    DESCRIPTION
	    "The rate CGI requests are received by the Web
	    service."
    ::= { webServiceEntry 6 }

wsConnAtmpsPerSec OBJECT-TYPE
    SYNTAX     Gauge32
    MAX-ACCESS read-only
    STATUS     current
    DESCRIPTION
	    "The rate that connections to the Web service
	    are being attempted."
    ::= { webServiceEntry 7 }

wsCopyRqstsPerSec OBJECT-TYPE
    SYNTAX     Gauge32
    MAX-ACCESS read-only
    STATUS     current
    DESCRIPTION
	    "The rate HTTP requests using the COPY method
	    are made.  Copy requests are used for copying
	    files and directories."
    ::= { webServiceEntry 8 }

wsCurrentAnonymousUsers OBJECT-TYPE
    SYNTAX     Gauge32
    MAX-ACCESS read-only
    STATUS     current
    DESCRIPTION
	    "Current Anonymous Users is the number of users
	    who currently have an anonymous connection
	    using the Web service."
    ::= { webServiceEntry 9 }

wsCurrentBlkdAsyncIORqsts OBJECT-TYPE
    SYNTAX     Gauge32
    MAX-ACCESS read-only
    STATUS     current
    DESCRIPTION
	    "Current requests temporarily blocked due to
	    bandwidth throttling settings."
    ::= { webServiceEntry 10 }

wsCurrentCALCountForSSLConns OBJECT-TYPE
    SYNTAX     Gauge32
    MAX-ACCESS read-only
    STATUS     current
    DESCRIPTION
	    "This counter is no longer valid. Value will
	    always be zero."
    ::= { webServiceEntry 11 }

wsCurrentCALCountForAuthdUsers OBJECT-TYPE
    SYNTAX     Gauge32
    MAX-ACCESS read-only
    STATUS     current
    DESCRIPTION
	    "This counter is no longer valid. Value will
	    always be zero."
    ::= { webServiceEntry 12 }

wsCurrentCGIRqsts OBJECT-TYPE
    SYNTAX     Gauge32
    MAX-ACCESS read-only
    STATUS     current
    DESCRIPTION
	    "Current CGI Requests is the current number of
	    CGI requests being simultaneously processed by
	    the Web service."
    ::= { webServiceEntry 13 }

wsCurrentConns OBJECT-TYPE
    SYNTAX     Gauge32
    MAX-ACCESS read-only
    STATUS     current
    DESCRIPTION
	    "Current Connections is the current number of
	    connections established with the Web service."
    ::= { webServiceEntry 14 }

wsCurrentISAPIExtensionRqsts OBJECT-TYPE
    SYNTAX     Gauge32
    MAX-ACCESS read-only
    STATUS     current
    DESCRIPTION
	    "Current ISAPI Extension Requests is the
	    current number of ISAPI requests being
	    simultaneously processed by the Web service."
    ::= { webServiceEntry 15 }

wsCurrentNonAnonymousUsers OBJECT-TYPE
    SYNTAX     Gauge32
    MAX-ACCESS read-only
    STATUS     current
    DESCRIPTION
	    "Current NonAnonymous Users is the number of
	    users who currently have a non-anonymous
	    connection using the Web service."
    ::= { webServiceEntry 16 }

wsCurrentBlkdBandwidthBytes OBJECT-TYPE
    SYNTAX     Gauge32
    MAX-ACCESS read-only
    STATUS     current
    DESCRIPTION
	    "Current bytes temporarily blocked due to
	    bandwidth throttling settings."
    ::= { webServiceEntry 17 }

wsDeleteRqstsPerSec OBJECT-TYPE
    SYNTAX     Gauge32
    MAX-ACCESS read-only
    STATUS     current
    DESCRIPTION
	    "The rate HTTP requests using the DELETE method
	    are made.  Delete requests are generally used
	    for file removals."
    ::= { webServiceEntry 18 }

wsFilesReceivedPerSec OBJECT-TYPE
    SYNTAX     Gauge32
    MAX-ACCESS read-only
    STATUS     current
    DESCRIPTION
	    "The rate files are received by the Web
	    service."
    ::= { webServiceEntry 19 }

wsFilesSentPerSec OBJECT-TYPE
    SYNTAX     Gauge32
    MAX-ACCESS read-only
    STATUS     current
    DESCRIPTION
	    "The rate files are sent by the Web service."
    ::= { webServiceEntry 20 }

wsFilesPerSec OBJECT-TYPE
    SYNTAX     Gauge32
    MAX-ACCESS read-only
    STATUS     current
    DESCRIPTION
	    "The rate files are transferred, that is, sent
	    and received by the Web service."
    ::= { webServiceEntry 21 }

wsGetRqstsPerSec OBJECT-TYPE
    SYNTAX     Gauge32
    MAX-ACCESS read-only
    STATUS     current
    DESCRIPTION
	    "The rate HTTP requests using the GET method
	    are made.  Get requests are the most common
	    HTTP request."
    ::= { webServiceEntry 22 }

wsHeadRqstsPerSec OBJECT-TYPE
    SYNTAX     Gauge32
    MAX-ACCESS read-only
    STATUS     current
    DESCRIPTION
	    "The rate HTTP requests using the HEAD method
	    are made.  Head requests generally indicate a
	    client is querying the state of a document they
	    already have to see if it needs to be
	    refreshed."
    ::= { webServiceEntry 23 }

wsISAPIExtensionRqstsPerSec OBJECT-TYPE
    SYNTAX     Gauge32
    MAX-ACCESS read-only
    STATUS     current
    DESCRIPTION
	    "The rate that ISAPI Extension requests are
	    received by the Web service."
    ::= { webServiceEntry 24 }

wsLockRqstsPerSec OBJECT-TYPE
    SYNTAX     Gauge32
    MAX-ACCESS read-only
    STATUS     current
    DESCRIPTION
	    "The rate HTTP requests using the LOCK method
	    are made.  Lock requests are used to lock a
	    file for one user so that only that user can
	    modify the file."
    ::= { webServiceEntry 25 }

wsLockedErrorsPerSec OBJECT-TYPE
    SYNTAX     Gauge32
    MAX-ACCESS read-only
    STATUS     current
    DESCRIPTION
	    "The rate of errors due to requests that
	    couldn't be satisfied by the server because the
	    requested document was locked.  These are
	    generally reported as an HTTP 423 error code to
	    the client."
    ::= { webServiceEntry 26 }

wsLogonAtmpsPerSec OBJECT-TYPE
    SYNTAX     Gauge32
    MAX-ACCESS read-only
    STATUS     current
    DESCRIPTION
	    "The rate that logons to the Web service are
	    being attempted."
    ::= { webServiceEntry 27 }

wsMaximumAnonymousUsers OBJECT-TYPE
    SYNTAX     Gauge32
    MAX-ACCESS read-only
    STATUS     current
    DESCRIPTION
	    "Maximum Anonymous Users is the maximum number
	    of users who established concurrent anonymous
	    connections using the Web service (since
	    service startup)."
    ::= { webServiceEntry 28 }

wsMaximumCALCountForSSLConns OBJECT-TYPE
    SYNTAX     Gauge32
    MAX-ACCESS read-only
    STATUS     current
    DESCRIPTION
	    "This counter is no longer valid. Value will
	    always be zero."
    ::= { webServiceEntry 29 }

wsMaximumCALCountForAuthdUsers OBJECT-TYPE
    SYNTAX     Gauge32
    MAX-ACCESS read-only
    STATUS     current
    DESCRIPTION
	    "This counter is no longer valid. Value will
	    always be zero."
    ::= { webServiceEntry 30 }

wsMaximumCGIRqsts OBJECT-TYPE
    SYNTAX     Gauge32
    MAX-ACCESS read-only
    STATUS     current
    DESCRIPTION
	    "Maximum CGI Requests is the maximum number of
	    CGI requests simultaneously processed by the
	    Web service (since service startup)."
    ::= { webServiceEntry 31 }

wsMaximumConns OBJECT-TYPE
    SYNTAX     Gauge32
    MAX-ACCESS read-only
    STATUS     current
    DESCRIPTION
	    "Maximum Connections is the maximum number of
	    concurrent connections established with the Web
	    service (since service startup)."
    ::= { webServiceEntry 32 }

wsMaximumISAPIExtensionRqsts OBJECT-TYPE
    SYNTAX     Gauge32
    MAX-ACCESS read-only
    STATUS     current
    DESCRIPTION
	    "Maximum ISAPI Extension Requests is the
	    maximum number of ISAPI requests simultaneously
	    processed by the Web service (since service
	    startup)."
    ::= { webServiceEntry 33 }

wsMaximumNonAnonymousUsers OBJECT-TYPE
    SYNTAX     Gauge32
    MAX-ACCESS read-only
    STATUS     current
    DESCRIPTION
	    "Maximum NonAnonymous Users is the maximum
	    number of concurrent non-anonymous connections
	    to the Web service (since service startup)."
    ::= { webServiceEntry 34 }

wsMeasuredAsyncIOBandwidthUsage OBJECT-TYPE
    SYNTAX     Gauge32
    MAX-ACCESS read-only
    STATUS     current
    DESCRIPTION
	    "Measured bandwidth of asynchronous I/O
	    averaged over a minute."
    ::= { webServiceEntry 35 }

wsMkcolRqstsPerSec OBJECT-TYPE
    SYNTAX     Gauge32
    MAX-ACCESS read-only
    STATUS     current
    DESCRIPTION
	    "The rate HTTP requests using the MKCOL method
	    are made.  Mkcol requests are used to create
	    directories on the server."
    ::= { webServiceEntry 36 }

wsMoveRqstsPerSec OBJECT-TYPE
    SYNTAX     Gauge32
    MAX-ACCESS read-only
    STATUS     current
    DESCRIPTION
	    "The rate HTTP requests using the MOVE method
	    are made.  Move requests are used for moving
	    files and directories."
    ::= { webServiceEntry 37 }

wsNonAnonymousUsersPerSec OBJECT-TYPE
    SYNTAX     Gauge32
    MAX-ACCESS read-only
    STATUS     current
    DESCRIPTION
	    "The rate users are making non-anonymous
	    connections to the Web service."
    ::= { webServiceEntry 38 }

wsNotFoundErrorsPerSec OBJECT-TYPE
    SYNTAX     Gauge32
    MAX-ACCESS read-only
    STATUS     current
    DESCRIPTION
	    "The rate of errors due to requests that
	    couldn't be satisfied by the server because the
	    requested document could not be found.  These
	    are generally reported as an HTTP 404 error
	    code to the client."
    ::= { webServiceEntry 39 }

wsOptionsRqstsPerSec OBJECT-TYPE
    SYNTAX     Gauge32
    MAX-ACCESS read-only
    STATUS     current
    DESCRIPTION
	    "The rate HTTP requests using the OPTIONS
	    method are made."
    ::= { webServiceEntry 40 }

wsOtherRqstMethodsPerSec OBJECT-TYPE
    SYNTAX     Gauge32
    MAX-ACCESS read-only
    STATUS     current
    DESCRIPTION
	    "The rate HTTP requests are made that do not
	    use the OPTIONS, GET, HEAD, POST, PUT, DELETE,
	    TRACE, MOVE, COPY, MKCOL, PROPFIND, PROPPATCH,
	    SEARCH, LOCK or UNLOCK methods."
    ::= { webServiceEntry 41 }

wsPostRqstsPerSec OBJECT-TYPE
    SYNTAX     Gauge32
    MAX-ACCESS read-only
    STATUS     current
    DESCRIPTION
	    "The rate HTTP requests using the POST method
	    are made."
    ::= { webServiceEntry 42 }

wsPropfindRqstsPerSec OBJECT-TYPE
    SYNTAX     Gauge32
    MAX-ACCESS read-only
    STATUS     current
    DESCRIPTION
	    "The rate HTTP requests using the PROPFIND
	    method are made.  Propfind requests retrieve
	    property values on files and directories."
    ::= { webServiceEntry 43 }

wsProppatchRqstsPerSec OBJECT-TYPE
    SYNTAX     Gauge32
    MAX-ACCESS read-only
    STATUS     current
    DESCRIPTION
	    "The rate HTTP requests using the PROPPATCH
	    method are made.  Proppatch requests set
	    property values on files and directories."
    ::= { webServiceEntry 44 }

wsPutRqstsPerSec OBJECT-TYPE
    SYNTAX     Gauge32
    MAX-ACCESS read-only
    STATUS     current
    DESCRIPTION
	    "The rate HTTP requests using the PUT method
	    are made."
    ::= { webServiceEntry 45 }

wsSearchRqstsPerSec OBJECT-TYPE
    SYNTAX     Gauge32
    MAX-ACCESS read-only
    STATUS     current
    DESCRIPTION
	    "The rate HTTP requests using the SEARCH method
	    are made.  Search requests are used to query
	    the server to find resources that match a set
	    of conditions provided by the client."
    ::= { webServiceEntry 46 }

wsServiceUptime OBJECT-TYPE
    SYNTAX     Gauge32
    MAX-ACCESS read-only
    STATUS     current
    DESCRIPTION
	    "The length of time the Web Service has been
	    running."
    ::= { webServiceEntry 47 }

wsTotalAllowedAsyncIORqsts OBJECT-TYPE
    SYNTAX     Gauge32
    MAX-ACCESS read-only
    STATUS     current
    DESCRIPTION
	    "Total requests allowed by bandwidth throttling
	    settings (since service startup)."
    ::= { webServiceEntry 48 }

wsTotalAnonymousUsers OBJECT-TYPE
    SYNTAX     Gauge32
    MAX-ACCESS read-only
    STATUS     current
    DESCRIPTION
	    "Total Anonymous Users is the total number of
	    users who established an anonymous connection
	    with the Web service (since service startup)."
    ::= { webServiceEntry 49 }

wsTotalBlkdAsyncIORqsts OBJECT-TYPE
    SYNTAX     Gauge32
    MAX-ACCESS read-only
    STATUS     current
    DESCRIPTION
	    "Total requests temporarily blocked due to
	    bandwidth throttling settings (since service
	    startup)."
    ::= { webServiceEntry 50 }

wsTotalBytesReceived OBJECT-TYPE
    SYNTAX     Gauge32
    MAX-ACCESS read-only
    STATUS     current
    DESCRIPTION
	    "Total Bytes Received is the number of data
	    bytes that have been received by the Web
	    service (since service startup)."
    ::= { webServiceEntry 51 }

wsTotalBytesSent OBJECT-TYPE
    SYNTAX     Gauge32
    MAX-ACCESS read-only
    STATUS     current
    DESCRIPTION
	    "Total Bytes Sent is the number of data bytes
	    that have been sent by the Web service (since
	    service startup)."
    ::= { webServiceEntry 52 }

wsTotalBytesTransfered OBJECT-TYPE
    SYNTAX     Gauge32
    MAX-ACCESS read-only
    STATUS     current
    DESCRIPTION
	    "Total bytes either received or sent by the Web
	    service (since service startup)."
    ::= { webServiceEntry 53 }

wsTotalCGIRqsts OBJECT-TYPE
    SYNTAX     Gauge32
    MAX-ACCESS read-only
    STATUS     current
    DESCRIPTION
	    "Total CGI requests is the total number of CGI
	    requests (since service startup)."
    ::= { webServiceEntry 54 }

wsTotalConnAtmpsAllInstances OBJECT-TYPE
    SYNTAX     Gauge32
    MAX-ACCESS read-only
    STATUS     current
    DESCRIPTION
	    "Total Connection Attempts is the number of
	    connections that have been attempted using the
	    Web service (since service startup).  This
	    counter is for all instances listed."
    ::= { webServiceEntry 55 }

wsTotalCopyRqsts OBJECT-TYPE
    SYNTAX     Gauge32
    MAX-ACCESS read-only
    STATUS     current
    DESCRIPTION
	    "Total Copy Requests is the number of HTTP
	    requests using the COPY method (since service
	    startup).  Copy requests are used for copying
	    files and directories."
    ::= { webServiceEntry 56 }

wsTotalDeleteRqsts OBJECT-TYPE
    SYNTAX     Gauge32
    MAX-ACCESS read-only
    STATUS     current
    DESCRIPTION
	    "Total Delete Requests is the number of HTTP
	    requests using the DELETE method (since service
	    startup).  Delete requests are generally used
	    for file removals."
    ::= { webServiceEntry 57 }

wsTotalFilesReceived OBJECT-TYPE
    SYNTAX     Gauge32
    MAX-ACCESS read-only
    STATUS     current
    DESCRIPTION
	    "Total Files Received is the total number of
	    files received by the Web service (since
	    service startup)."
    ::= { webServiceEntry 58 }

wsTotalFilesSent OBJECT-TYPE
    SYNTAX     Gauge32
    MAX-ACCESS read-only
    STATUS     current
    DESCRIPTION
	    "Total Files Sent is the total number of files
	    sent by the Web service (since service
	    startup)."
    ::= { webServiceEntry 59 }

wsTotalFilesTransferred OBJECT-TYPE
    SYNTAX     Gauge32
    MAX-ACCESS read-only
    STATUS     current
    DESCRIPTION
	    "Total Files Transferred is the sum of Files
	    Sent and Files Received (since service
	    startup)."
    ::= { webServiceEntry 60 }

wsTotalGetRqsts OBJECT-TYPE
    SYNTAX     Gauge32
    MAX-ACCESS read-only
    STATUS     current
    DESCRIPTION
	    "Total Get Requests is the number of HTTP
	    requests using the GET method (since service
	    startup).  Get requests are the most common
	    HTTP request."
    ::= { webServiceEntry 61 }

wsTotalHeadRqsts OBJECT-TYPE
    SYNTAX     Gauge32
    MAX-ACCESS read-only
    STATUS     current
    DESCRIPTION
	    "Total Head Requests is the number of HTTP
	    requests using the HEAD method (since service
	    startup).  Head requests generally indicate a
	    client is querying the state of a document they
	    already have to see if it needs to be
	    refreshed."
    ::= { webServiceEntry 62 }

wsTotalISAPIExtensionRqsts OBJECT-TYPE
    SYNTAX     Gauge32
    MAX-ACCESS read-only
    STATUS     current
    DESCRIPTION
	    "Total ISAPI Extension Requests received (since
	    service startup)."
    ::= { webServiceEntry 63 }

wsTotalLockRqsts OBJECT-TYPE
    SYNTAX     Gauge32
    MAX-ACCESS read-only
    STATUS     current
    DESCRIPTION
	    "Total Lock Requests is the number of HTTP
	    requests using the LOCK method (since service
	    startup).  Lock requests are used to lock a
	    file for one user so that only that user can
	    modify the file."
    ::= { webServiceEntry 64 }

wsTotalLockedErrors OBJECT-TYPE
    SYNTAX     Gauge32
    MAX-ACCESS read-only
    STATUS     current
    DESCRIPTION
	    "Total Locked Errors is the number of requests
	    that couldn't be satisfied by the server
	    because the requested was locked (since service
	    startup).  These are generally reported as an
	    HTTP 423 error code to the client."
    ::= { webServiceEntry 65 }

wsTotalLogonAtmps OBJECT-TYPE
    SYNTAX     Gauge32
    MAX-ACCESS read-only
    STATUS     current
    DESCRIPTION
	    "Total Logon Attempts is the number of logons
	    attempts to the Web Service (since service
	    startup)."
    ::= { webServiceEntry 66 }

wsTotalMethodRqsts OBJECT-TYPE
    SYNTAX     Gauge32
    MAX-ACCESS read-only
    STATUS     current
    DESCRIPTION
	    "Total Method Requests is the number of all
	    HTTP requests (since service startup)."
    ::= { webServiceEntry 67 }

wsTotalMethodRqstsPerSec OBJECT-TYPE
    SYNTAX     Gauge32
    MAX-ACCESS read-only
    STATUS     current
    DESCRIPTION
	    "The rate HTTP requests are received."
    ::= { webServiceEntry 68 }

wsTotalMkcolRqsts OBJECT-TYPE
    SYNTAX     Gauge32
    MAX-ACCESS read-only
    STATUS     current
    DESCRIPTION
	    "Total Mkcol Requests is the number of HTTP
	    requests using the MKCOL method (since service
	    startup).  Mkcol requests are used to create
	    directories on the server."
    ::= { webServiceEntry 69 }

wsTotalMoveRqsts OBJECT-TYPE
    SYNTAX     Gauge32
    MAX-ACCESS read-only
    STATUS     current
    DESCRIPTION
	    "Total Move Requests is the number of HTTP
	    requests using the MOVE method (since service
	    startup).  Move requests are used for moving
	    files and directories."
    ::= { webServiceEntry 70 }

wsTotalNonAnonymousUsers OBJECT-TYPE
    SYNTAX     Gauge32
    MAX-ACCESS read-only
    STATUS     current
    DESCRIPTION
	    "Total NonAnonymous Users is the total number
	    of users who established a non-anonymous
	    connection with the Web service (since service
	    startup)."
    ::= { webServiceEntry 71 }

wsTotalNotFoundErrors OBJECT-TYPE
    SYNTAX     Gauge32
    MAX-ACCESS read-only
    STATUS     current
    DESCRIPTION
	    "Total Not Found Errors is the number of
	    requests that couldn't be satisfied by the
	    server because the requested document could not
	    be found (since service startup).  These are
	    generally reported as an HTTP 404 error code to
	    the client."
    ::= { webServiceEntry 72 }

wsTotalOptionsRqsts OBJECT-TYPE
    SYNTAX     Gauge32
    MAX-ACCESS read-only
    STATUS     current
    DESCRIPTION
	    "Total Options Requests is the number of HTTP
	    requests using the OPTIONS method (since
	    service startup)."
    ::= { webServiceEntry 73 }

wsTotalOtherRqstMethods OBJECT-TYPE
    SYNTAX     Gauge32
    MAX-ACCESS read-only
    STATUS     current
    DESCRIPTION
	    "Total Other Request Methods is the number of
	    HTTP requests that are not OPTIONS, GET, HEAD,
	    POST, PUT, DELETE, TRACE, MOVE, COPY, MKCOL,
	    PROPFIND, PROPPATCH, SEARCH, LOCK or UNLOCK
	    methods (since service startup)."
    ::= { webServiceEntry 74 }

wsTotalPostRqsts OBJECT-TYPE
    SYNTAX     Gauge32
    MAX-ACCESS read-only
    STATUS     current
    DESCRIPTION
	    "Total Post Requests is the number of HTTP
	    requests using the POST method (since service
	    startup)."
    ::= { webServiceEntry 75 }

wsTotalPropfindRqsts OBJECT-TYPE
    SYNTAX     Gauge32
    MAX-ACCESS read-only
    STATUS     current
    DESCRIPTION
	    "Total Propfind Requests is the number of HTTP
	    requests using the PROPFIND method (since
	    service startup).  Propfind requests retrieve
	    property values on files and directories."
    ::= { webServiceEntry 76 }

wsTotalProppatchRqsts OBJECT-TYPE
    SYNTAX     Gauge32
    MAX-ACCESS read-only
    STATUS     current
    DESCRIPTION
	    "Total Proppatch Requests is the number of HTTP
	    requests using the PROPPATCH method (since
	    service startup).  Proppatch requests set
	    property values on files and directories."
    ::= { webServiceEntry 77 }

wsTotalPutRqsts OBJECT-TYPE
    SYNTAX     Gauge32
    MAX-ACCESS read-only
    STATUS     current
    DESCRIPTION
	    "Total Put Requests is the number of HTTP
	    requests using the PUT method (since service
	    startup)."
    ::= { webServiceEntry 78 }

wsTotalRejectedAsyncIORqsts OBJECT-TYPE
    SYNTAX     Gauge32
    MAX-ACCESS read-only
    STATUS     current
    DESCRIPTION
	    "Total requests rejected due to bandwidth
	    throttling settings (since service startup)."
    ::= { webServiceEntry 79 }

wsTotalSearchRqsts OBJECT-TYPE
    SYNTAX     Gauge32
    MAX-ACCESS read-only
    STATUS     current
    DESCRIPTION
	    "Total Search Requests is the number of HTTP
	    requests using the SEARCH method (since service
	    startup).  Search requests are used to query
	    the server to find resources that match a set
	    of conditions provided by the client."
    ::= { webServiceEntry 80 }

wsTotalTraceRqsts OBJECT-TYPE
    SYNTAX     Gauge32
    MAX-ACCESS read-only
    STATUS     current
    DESCRIPTION
	    "Total Trace Requests is the number of HTTP
	    requests using the TRACE method (since service
	    startup).  Trace requests allow the client to
	    see what is being received at the end of the
	    request chain and use the information for
	    diagnostic purposes."
    ::= { webServiceEntry 81 }

wsTotalUnlockRqsts OBJECT-TYPE
    SYNTAX     Gauge32
    MAX-ACCESS read-only
    STATUS     current
    DESCRIPTION
	    "Total Unlock Requests is the number of HTTP
	    requests using the UNLOCK method (since service
	    startup).  Unlock requests are used to remove
	    locks from files."
    ::= { webServiceEntry 82 }

wsTotalBlkdBandwidthBytes OBJECT-TYPE
    SYNTAX     Gauge32
    MAX-ACCESS read-only
    STATUS     current
    DESCRIPTION
	    "Total bytes blocked due to bandwidth
	    throttling settings (since service startup)."
    ::= { webServiceEntry 83 }

wsTotalCountFailCALRqstsSSLConns OBJECT-TYPE
    SYNTAX     Gauge32
    MAX-ACCESS read-only
    STATUS     current
    DESCRIPTION
	    "This counter is no longer valid. Value will
	    always be zero."
    ::= { webServiceEntry 84 }

wsTotalCountFailCALRqstsAuthdUsr OBJECT-TYPE
    SYNTAX     Gauge32
    MAX-ACCESS read-only
    STATUS     current
    DESCRIPTION
	    "This counter is no longer valid. Value will
	    always be zero."
    ::= { webServiceEntry 85 }

wsTraceRqstsPerSec OBJECT-TYPE
    SYNTAX     Gauge32
    MAX-ACCESS read-only
    STATUS     current
    DESCRIPTION
	    "The rate HTTP requests using the TRACE method
	    are made.  Trace requests allow the client to
	    see what is being received at the end of the
	    request chain and use the information for
	    diagnostic purposes."
    ::= { webServiceEntry 86 }

wsUnlockRqstsPerSec OBJECT-TYPE
    SYNTAX     Gauge32
    MAX-ACCESS read-only
    STATUS     current
    DESCRIPTION
	    "The rate HTTP requests using the UNLOCK method
	    are made.  Unlock requests are used to remove
	    locks from files."
    ::= { webServiceEntry 87 }

webServiceCache OBJECT IDENTIFIER
    ::= { advanced 87 }

wscActiveFlushedEntries OBJECT-TYPE
    SYNTAX     Gauge32
    MAX-ACCESS read-only
    STATUS     current
    DESCRIPTION
	    "Active Flushed Entries are file handles cached
	    in user-mode that will be closed when all
	    current transfers complete."
    ::= { webServiceCache 1 }

wscCurrentFileCacheMemoryUsage OBJECT-TYPE
    SYNTAX     Gauge32
    MAX-ACCESS read-only
    STATUS     current
    DESCRIPTION
	    "Current number of bytes used for the user-mode
	    file cache."
    ::= { webServiceCache 2 }

wscCurrentFilesCached OBJECT-TYPE
    SYNTAX     Gauge32
    MAX-ACCESS read-only
    STATUS     current
    DESCRIPTION
	    "Current number of files whose content is in
	    the user-mode cache."
    ::= { webServiceCache 3 }

wscCurrentMetadataCached OBJECT-TYPE
    SYNTAX     Gauge32
    MAX-ACCESS read-only
    STATUS     current
    DESCRIPTION
	    "Current number of metadata information blocks
	    currently in the user-mode cache."
    ::= { webServiceCache 4 }

wscCurrentURIsCached OBJECT-TYPE
    SYNTAX     Gauge32
    MAX-ACCESS read-only
    STATUS     current
    DESCRIPTION
	    "URI information blocks currently in the
	    user-mode cache."
    ::= { webServiceCache 5 }

wscFileCacheFlushes OBJECT-TYPE
    SYNTAX     Gauge32
    MAX-ACCESS read-only
    STATUS     current
    DESCRIPTION
	    "The number of files removed from the user-mode
	    cache (since service startup)."
    ::= { webServiceCache 6 }

wscFileCacheHits OBJECT-TYPE
    SYNTAX     Gauge32
    MAX-ACCESS read-only
    STATUS     current
    DESCRIPTION
	    "Total number of successful lookups in the
	    user-mode file cache (since service startup)."
    ::= { webServiceCache 7 }

wscFileCacheHitsPercent OBJECT-TYPE
    SYNTAX     Gauge32
    MAX-ACCESS read-only
    STATUS     current
    DESCRIPTION
	    "The ratio of user-mode file cache hits to
	    total cache requests (since service startup)."
    ::= { webServiceCache 8 }

wscFileCacheMisses OBJECT-TYPE
    SYNTAX     Gauge32
    MAX-ACCESS read-only
    STATUS     current
    DESCRIPTION
	    "Total number of unsuccessful lookups in the
	    user-mode file cache (since service startup)."
    ::= { webServiceCache 9 }

wscKernelCurrentURIsCached OBJECT-TYPE
    SYNTAX     Gauge32
    MAX-ACCESS read-only
    STATUS     current
    DESCRIPTION
	    "URI information blocks currently cached by the
	    kernel."
    ::= { webServiceCache 10 }

wscKernelTotalFlushedURIs OBJECT-TYPE
    SYNTAX     Gauge32
    MAX-ACCESS read-only
    STATUS     current
    DESCRIPTION
	    "The number of URI information blocks that have
	    been removed from the kernel cache (since
	    service startup)."
    ::= { webServiceCache 11 }

wscKernelTotalURIsCached OBJECT-TYPE
    SYNTAX     Gauge32
    MAX-ACCESS read-only
    STATUS     current
    DESCRIPTION
	    "Total number of URI information blocks added
	    to the kernel cache (since service startup)."
    ::= { webServiceCache 12 }

wscKernelURICacheFlushes OBJECT-TYPE
    SYNTAX     Gauge32
    MAX-ACCESS read-only
    STATUS     current
    DESCRIPTION
	    "Kernel URI Cache Flushes (since server
	    startup)."
    ::= { webServiceCache 13 }

wscKernelURICacheHits OBJECT-TYPE
    SYNTAX     Gauge32
    MAX-ACCESS read-only
    STATUS     current
    DESCRIPTION
	    "Total number of successful lookups in the
	    kernel URI cache (since service startup)."
    ::= { webServiceCache 14 }

wscKernelURICacheHitsPercent OBJECT-TYPE
    SYNTAX     Gauge32
    MAX-ACCESS read-only
    STATUS     current
    DESCRIPTION
	    "The ratio of kernel URI cache hits to total
	    cache requests (since service startup)."
    ::= { webServiceCache 15 }

wscKernelURICacheMisses OBJECT-TYPE
    SYNTAX     Gauge32
    MAX-ACCESS read-only
    STATUS     current
    DESCRIPTION
	    "Total number of unsuccessful lookups in the
	    kernel URI cache (since service startup)."
    ::= { webServiceCache 16 }

wscKernelUriCacheHitsPerSec OBJECT-TYPE
    SYNTAX     Gauge32
    MAX-ACCESS read-only
    STATUS     current
    DESCRIPTION
	    "The rate of kernel URI Cache hits."
    ::= { webServiceCache 17 }

wscMaximumFileCacheMemoryUsage OBJECT-TYPE
    SYNTAX     Gauge32
    MAX-ACCESS read-only
    STATUS     current
    DESCRIPTION
	    "Maximum number of bytes used for user-mode
	    file cache (since service startup)."
    ::= { webServiceCache 18 }

wscMetadataCacheFlushes OBJECT-TYPE
    SYNTAX     Gauge32
    MAX-ACCESS read-only
    STATUS     current
    DESCRIPTION
	    "The number of user-mode metadata cache flushes
	    (since service startup)."
    ::= { webServiceCache 19 }

wscMetadataCacheHits OBJECT-TYPE
    SYNTAX     Gauge32
    MAX-ACCESS read-only
    STATUS     current
    DESCRIPTION
	    "Total number of successful lookups in the
	    user-mode metadata cache (since service
	    startup)."
    ::= { webServiceCache 20 }

wscMetadataCacheHitsPercent OBJECT-TYPE
    SYNTAX     Gauge32
    MAX-ACCESS read-only
    STATUS     current
    DESCRIPTION
	    "The ratio of user-mode metadata cache hits to
	    total cache requests (since service startup)."
    ::= { webServiceCache 21 }

wscMetadataCacheMisses OBJECT-TYPE
    SYNTAX     Gauge32
    MAX-ACCESS read-only
    STATUS     current
    DESCRIPTION
	    "Total number of unsuccessful lookups in the
	    user-mode metadata cache (since service
	    startup)."
    ::= { webServiceCache 22 }

wscTotalFilesCached OBJECT-TYPE
    SYNTAX     Gauge32
    MAX-ACCESS read-only
    STATUS     current
    DESCRIPTION
	    "Total number of files whose content was ever
	    added to the user-mode cache (since service
	    startup)."
    ::= { webServiceCache 23 }

wscTotalFlushedFiles OBJECT-TYPE
    SYNTAX     Gauge32
    MAX-ACCESS read-only
    STATUS     current
    DESCRIPTION
	    "Total Flushed Files is the number of file
	    handles that have been removed from the
	    user-mode cache (since service startup)."
    ::= { webServiceCache 24 }

wscTotalFlushedMetadata OBJECT-TYPE
    SYNTAX     Gauge32
    MAX-ACCESS read-only
    STATUS     current
    DESCRIPTION
	    "Total Flushed Metadata is the number of
	    Metadata information blocks that have been
	    removed from the user-mode cache (since service
	    startup)."
    ::= { webServiceCache 25 }

wscTotalFlushedURIs OBJECT-TYPE
    SYNTAX     Gauge32
    MAX-ACCESS read-only
    STATUS     current
    DESCRIPTION
	    "The number of URI information blocks that have
	    been removed from the user-mode cache (since
	    service startup)."
    ::= { webServiceCache 26 }

wscTotalMetadataCached OBJECT-TYPE
    SYNTAX     Gauge32
    MAX-ACCESS read-only
    STATUS     current
    DESCRIPTION
	    "Total number of metadata information blocks
	    added to the user-mode cache (since service
	    startup)."
    ::= { webServiceCache 27 }

wscTotalURIsCached OBJECT-TYPE
    SYNTAX     Gauge32
    MAX-ACCESS read-only
    STATUS     current
    DESCRIPTION
	    "Total number of URI information blocks added
	    to the user-mode cache (since service
	    startup)."
    ::= { webServiceCache 28 }

wscURICacheFlushes OBJECT-TYPE
    SYNTAX     Gauge32
    MAX-ACCESS read-only
    STATUS     current
    DESCRIPTION
	    "User-mode URI Cache flushes (since service
	    startup)."
    ::= { webServiceCache 29 }

wscURICacheHits OBJECT-TYPE
    SYNTAX     Gauge32
    MAX-ACCESS read-only
    STATUS     current
    DESCRIPTION
	    "Total number of successful lookups in the
	    user-mode URI cache (since service startup)."
    ::= { webServiceCache 30 }

wscURICacheHitsPercent OBJECT-TYPE
    SYNTAX     Gauge32
    MAX-ACCESS read-only
    STATUS     current
    DESCRIPTION
	    "The ratio of user-mode URI Cache Hits to total
	    cache requests (since service startup)."
    ::= { webServiceCache 31 }

wscURICacheMisses OBJECT-TYPE
    SYNTAX     Gauge32
    MAX-ACCESS read-only
    STATUS     current
    DESCRIPTION
	    "Total number of unsuccessful lookups in the
	    user-mode URI cache (since service startup)."
    ::= { webServiceCache 32 }

windowsMediaServices OBJECT IDENTIFIER
    ::= { advanced 88 }

wmsCurCacheDownloads OBJECT-TYPE
    SYNTAX     Gauge32
    MAX-ACCESS read-only
    STATUS     current
    DESCRIPTION
	    "Current Cache Downloads is the current number
	    of active downloads to a cache."
    ::= { windowsMediaServices 1 }

wmsCurConnectedPlayers OBJECT-TYPE
    SYNTAX     Gauge32
    MAX-ACCESS read-only
    STATUS     current
    DESCRIPTION
	    "Current Connected Players is the current
	    number of players with unicast connections to
	    the server."
    ::= { windowsMediaServices 2 }

wmsCurConnectionQueueLength OBJECT-TYPE
    SYNTAX     Gauge32
    MAX-ACCESS read-only
    STATUS     current
    DESCRIPTION
	    "Current Connection Queue Length is the current
	    number of connection requests that are pending
	    on the server."
    ::= { windowsMediaServices 3 }

wmsCurConnectionRate OBJECT-TYPE
    SYNTAX     Gauge32
    MAX-ACCESS read-only
    STATUS     current
    DESCRIPTION
	    "Current Connection Rate is the current number
	    of clients per second that are connecting to
	    the server."
    ::= { windowsMediaServices 4 }

wmsCurFileReadRateKbps OBJECT-TYPE
    SYNTAX     Gauge32
    MAX-ACCESS read-only
    STATUS     current
    DESCRIPTION
	    "Current File Read Rate is the current read
	    rate, in Kbps, for all data files."
    ::= { windowsMediaServices 5 }

wmsCurIncomingBandwidthKbps OBJECT-TYPE
    SYNTAX     Gauge32
    MAX-ACCESS read-only
    STATUS     current
    DESCRIPTION
	    "Current Incoming Bandwidth is the current
	    bandwidth, in Kbps, allocated for streams from
	    other servers."
    ::= { windowsMediaServices 6 }

wmsCurLateReadRate OBJECT-TYPE
    SYNTAX     Gauge32
    MAX-ACCESS read-only
    STATUS     current
    DESCRIPTION
	    "Current Late Read Rate is the current number
	    of late read operations per second."
    ::= { windowsMediaServices 7 }

wmsCurLateSendRate OBJECT-TYPE
    SYNTAX     Gauge32
    MAX-ACCESS read-only
    STATUS     current
    DESCRIPTION
	    "Current Late Send Rate is the current number
	    of late write operations per second."
    ::= { windowsMediaServices 8 }

wmsCurOutDistAllocBandwidthKbps OBJECT-TYPE
    SYNTAX     Gauge32
    MAX-ACCESS read-only
    STATUS     current
    DESCRIPTION
	    "Current Outgoing Distribution Allocated
	    Bandwidth is the current bandwidth, in Kbps,
	    allocated for streams to distribution servers."
    ::= { windowsMediaServices 9 }

wmsCurOutDistConnections OBJECT-TYPE
    SYNTAX     Gauge32
    MAX-ACCESS read-only
    STATUS     current
    DESCRIPTION
	    "Current Outgoing Distribution Connections is
	    the current number of connections to
	    distribution servers."
    ::= { windowsMediaServices 10 }

wmsCurOutDistSendRateKbps OBJECT-TYPE
    SYNTAX     Gauge32
    MAX-ACCESS read-only
    STATUS     current
    DESCRIPTION
	    "Current Outgoing Distribution Send Rate is the
	    current send rate, in Kbps, for connections to
	    distribution servers."
    ::= { windowsMediaServices 11 }

wmsCurPlayerAllocBandwidthKbps OBJECT-TYPE
    SYNTAX     Gauge32
    MAX-ACCESS read-only
    STATUS     current
    DESCRIPTION
	    "Current Player Allocated Bandwidth is the
	    current bandwidth, in Kbps, that is allocated
	    for streams to all players."
    ::= { windowsMediaServices 12 }

wmsCurPlayerSendRateKbps OBJECT-TYPE
    SYNTAX     Gauge32
    MAX-ACCESS read-only
    STATUS     current
    DESCRIPTION
	    "Current Player Send Rate is the current rate,
	    in Kbps, at which data is being streamed to
	    players."
    ::= { windowsMediaServices 13 }

wmsCurStreamErrorRate OBJECT-TYPE
    SYNTAX     Gauge32
    MAX-ACCESS read-only
    STATUS     current
    DESCRIPTION
	    "Current Stream Error Rate is the current
	    number of errors per second due to dropped
	    packets."
    ::= { windowsMediaServices 14 }

wmsCurStreamingHTTPPlayers OBJECT-TYPE
    SYNTAX     Gauge32
    MAX-ACCESS read-only
    STATUS     current
    DESCRIPTION
	    "Current Streaming HTTP Players is the current
	    number of players being streamed data using the
	    HTTP protocol. This does not include players
	    that are stopped or paused."
    ::= { windowsMediaServices 15 }

wmsCurStreamingMMSPlayers OBJECT-TYPE
    SYNTAX     Gauge32
    MAX-ACCESS read-only
    STATUS     current
    DESCRIPTION
	    "Current Streaming MMS Players is the current
	    number of players being streamed data using the
	    MMS protocol. This does not include players
	    that are stopped or paused."
    ::= { windowsMediaServices 16 }

wmsCurStreamingPlayers OBJECT-TYPE
    SYNTAX     Gauge32
    MAX-ACCESS read-only
    STATUS     current
    DESCRIPTION
	    "Current Streaming Players is the current
	    number of players being streamed data across
	    all protocols. This does not include players
	    that are stopped or paused."
    ::= { windowsMediaServices 17 }

wmsCurStreamingRTSPPlayers OBJECT-TYPE
    SYNTAX     Gauge32
    MAX-ACCESS read-only
    STATUS     current
    DESCRIPTION
	    "Current Streaming RTSP Players is the current
	    number of players that are being streamed data
	    using the RTSP protocol. This does not include
	    players that are stopped or paused."
    ::= { windowsMediaServices 18 }

wmsCurUDPResendRequestsRate OBJECT-TYPE
    SYNTAX     Gauge32
    MAX-ACCESS read-only
    STATUS     current
    DESCRIPTION
	    "Current UDP Resend Requests Rate is the
	    current number of requests for UDP resends per
	    second received from clients."
    ::= { windowsMediaServices 19 }

wmsCurUDPResendsSentRate OBJECT-TYPE
    SYNTAX     Gauge32
    MAX-ACCESS read-only
    STATUS     current
    DESCRIPTION
	    "Current UDP Resends Sent Rate is the current
	    number of UDP resends per second sent to
	    clients."
    ::= { windowsMediaServices 20 }

wmsPeakConnectedPlayers OBJECT-TYPE
    SYNTAX     Gauge32
    MAX-ACCESS read-only
    STATUS     current
    DESCRIPTION
	    "Peak Connected Players is the peak number of
	    players that have connected since the last time
	    the counter was reset."
    ::= { windowsMediaServices 21 }

wmsPeakOutDistAllocBandwidthKbps OBJECT-TYPE
    SYNTAX     Gauge32
    MAX-ACCESS read-only
    STATUS     current
    DESCRIPTION
	    "Peak Outgoing Distribution Allocated Bandwidth
	    is the peak bandwidth, in Kbps, allocated for
	    all streams to distribution servers that have
	    connected since the last time the counter was
	    reset."
    ::= { windowsMediaServices 22 }

wmsPeakOutDistConnections OBJECT-TYPE
    SYNTAX     Gauge32
    MAX-ACCESS read-only
    STATUS     current
    DESCRIPTION
	    "Peak Outgoing Distribution Connections is the
	    peak number of distribution servers that have
	    connected since the last time the counter was
	    reset."
    ::= { windowsMediaServices 23 }

wmsPeakOutDistSendRateKbps OBJECT-TYPE
    SYNTAX     Gauge32
    MAX-ACCESS read-only
    STATUS     current
    DESCRIPTION
	    "Peak Outgoing Distribution Send Rate is the
	    peak rate, in Kbps, at which data was streamed
	    to distribution servers since the last time the
	    counter was reset."
    ::= { windowsMediaServices 24 }

wmsPeakPlayerAllocBandwidthKbps OBJECT-TYPE
    SYNTAX     Gauge32
    MAX-ACCESS read-only
    STATUS     current
    DESCRIPTION
	    "Peak Player Allocated Bandwidth is the peak
	    bandwidth, in Kbps, that was allocated for all
	    streams to players since the last time the
	    counter was reset."
    ::= { windowsMediaServices 25 }

wmsPeakPlayerSendRateKbps OBJECT-TYPE
    SYNTAX     Gauge32
    MAX-ACCESS read-only
    STATUS     current
    DESCRIPTION
	    "Peak Player Send Rate is the peak rate, in
	    Kbps, at which data was streamed to players
	    since the last time the counter was reset."
    ::= { windowsMediaServices 26 }

wmsPeakStreamingPlayers OBJECT-TYPE
    SYNTAX     Gauge32
    MAX-ACCESS read-only
    STATUS     current
    DESCRIPTION
	    "Peak Streaming Players is the peak number of
	    players that have been streamed data since the
	    last time the counter was reset."
    ::= { windowsMediaServices 27 }

wmsTotalAdvertisements OBJECT-TYPE
    SYNTAX     Gauge32
    MAX-ACCESS read-only
    STATUS     current
    DESCRIPTION
	    "Total Advertisements is the total number of
	    advertisements that have been streamed from
	    playlists since the last time the counter was
	    reset."
    ::= { windowsMediaServices 28 }

wmsTotalConnectedPlayers OBJECT-TYPE
    SYNTAX     Gauge32
    MAX-ACCESS read-only
    STATUS     current
    DESCRIPTION
	    "Total Connected Players is the total number of
	    players that have connected since the last time
	    the counter was reset."
    ::= { windowsMediaServices 29 }

wmsTotalLateReads OBJECT-TYPE
    SYNTAX     Gauge32
    MAX-ACCESS read-only
    STATUS     current
    DESCRIPTION
	    "Total Late Reads is the total number of late
	    read operations since the last time the counter
	    was reset."
    ::= { windowsMediaServices 30 }

wmsTotalLateSends OBJECT-TYPE
    SYNTAX     Gauge32
    MAX-ACCESS read-only
    STATUS     current
    DESCRIPTION
	    "Total Late Sends is the total number of late
	    send operations since the last time the counter
	    was reset."
    ::= { windowsMediaServices 31 }

wmsTotalOutDistBytesSent OBJECT-TYPE
    SYNTAX     Gauge32
    MAX-ACCESS read-only
    STATUS     current
    DESCRIPTION
	    "Total Outgoing Distribution Bytes Sent is the
	    total number of bytes streamed to all
	    distribution servers since the last time the
	    counter was reset."
    ::= { windowsMediaServices 32 }

wmsTotalOutDistConnections OBJECT-TYPE
    SYNTAX     Gauge32
    MAX-ACCESS read-only
    STATUS     current
    DESCRIPTION
	    "Total Outgoing Distribution Connections is the
	    total number of distribution servers that have
	    connected since the last time the counter was
	    reset."
    ::= { windowsMediaServices 33 }

wmsTotalPlayerBytesSent OBJECT-TYPE
    SYNTAX     Gauge32
    MAX-ACCESS read-only
    STATUS     current
    DESCRIPTION
	    "Total Player Bytes Sent is the total number of
	    bytes streamed to all players since the last
	    time the counter was reset."
    ::= { windowsMediaServices 34 }

wmsTotalServerUptime OBJECT-TYPE
    SYNTAX     Gauge32
    MAX-ACCESS read-only
    STATUS     current
    DESCRIPTION
	    "Total Server Uptime is the elapsed time, in
	    seconds, which the Windows Media Services
	    service has been running since it was last
	    started."
    ::= { windowsMediaServices 35 }

wmsTotalStreamDenials OBJECT-TYPE
    SYNTAX     Gauge32
    MAX-ACCESS read-only
    STATUS     current
    DESCRIPTION
	    "Total Stream Denials is the total number of
	    stream denials since the last time the counter
	    was reset. This includes both denials that
	    occurred due to failure to be authorized or
	    authenticated, as well as denials that occurred
	    because limits were exceeded."
    ::= { windowsMediaServices 36 }

wmsTotalStreamErrors OBJECT-TYPE
    SYNTAX     Gauge32
    MAX-ACCESS read-only
    STATUS     current
    DESCRIPTION
	    "Total Stream Errors is the total number of
	    stream errors due to dropped packets since the
	    last time the counter was reset."
    ::= { windowsMediaServices 37 }

wmsTotalStreamTerminations OBJECT-TYPE
    SYNTAX     Gauge32
    MAX-ACCESS read-only
    STATUS     current
    DESCRIPTION
	    "Total Stream Terminations is the total number
	    of streams that were terminated due to
	    inactivity or errors since the last time the
	    counter was reset. This includes terminations
	    that occurred because player inactivity and
	    timeout limits were exceeded, as well as
	    terminations that were due to events such as
	    late reads."
    ::= { windowsMediaServices 38 }

wmsTotalStreamingPlayers OBJECT-TYPE
    SYNTAX     Gauge32
    MAX-ACCESS read-only
    STATUS     current
    DESCRIPTION
	    "Total Streaming Players is the total number of
	    players that have been streamed data since the
	    last time the counter was reset."
    ::= { windowsMediaServices 39 }

wmsTotalUDPResendRequests OBJECT-TYPE
    SYNTAX     Gauge32
    MAX-ACCESS read-only
    STATUS     current
    DESCRIPTION
	    "Total UDP Resend Requests is the total number
	    of requests for UDP resends received from
	    clients since the last time the counter was
	    reset."
    ::= { windowsMediaServices 40 }

wmsTotalUDPResendsSent OBJECT-TYPE
    SYNTAX     Gauge32
    MAX-ACCESS read-only
    STATUS     current
    DESCRIPTION
	    "Total UDP Resends Sent is the total number of
	    UDP resends sent to clients since the last time
	    the counter was reset."
    ::= { windowsMediaServices 41 }

windowsMediaPublishingPointsTable OBJECT-TYPE
    SYNTAX     SEQUENCE OF WindowsMediaPublishingPointsEntry
    MAX-ACCESS not-accessible
    STATUS     current
    DESCRIPTION
	    "A table containing performance information for
	    instances of 'Windows Media Publishing Points'
	    objects."
    ::= { advanced 89 }

windowsMediaPublishingPointsEntry OBJECT-TYPE
    SYNTAX     WindowsMediaPublishingPointsEntry
    MAX-ACCESS not-accessible
    STATUS     current
    DESCRIPTION
	    "Performance information for one particular
	    instance of 'Windows Media Publishing Points'
	    object."
    INDEX      { wmppInstance }
    ::= { windowsMediaPublishingPointsTable 1 }

WindowsMediaPublishingPointsEntry ::= SEQUENCE {
    wmppInstance InstanceName,
    wmppCurConnectedPlayers Gauge32,
    wmppCurFileReadRateKbps Gauge32,
    wmppCurLateReadRate Gauge32,
    wmppCurOutDistAllocBandwidthKbps Gauge32,
    wmppCurOutDistConnections Gauge32,
    wmppCurPlayerAllocBandwidthKbps Gauge32,
    wmppCurStreamErrorRate Gauge32,
    wmppCurStreamingHTTPPlayers Gauge32,
    wmppCurStreamingMMSPlayers Gauge32,
    wmppCurStreamingPlayers Gauge32,
    wmppCurStreamingRTSPPlayers Gauge32,
    wmppPeakConnectedPlayers Gauge32,
    wmppPeakOutDistAllocBandwdthKbps Gauge32,
    wmppPeakOutDistConnections Gauge32,
    wmppPeakPlayerAllocBandwidthKbps Gauge32,
    wmppPeakStreamingPlayers Gauge32,
    wmppTotalAdvertisements Gauge32,
    wmppTotalConnectedPlayers Gauge32,
    wmppTotalFileBytesRead Gauge32,
    wmppTotalLateReads Gauge32,
    wmppTotalOutDistBytesSent Gauge32,
    wmppTotalOutDistConnections Gauge32,
    wmppTotalPlayerBytesSent Gauge32,
    wmppTotalStreamDenials Gauge32,
    wmppTotalStreamErrors Gauge32,
    wmppTotalStreamTerminations Gauge32,
    wmppTotalStreamingPlayers Gauge32
}

wmppInstance OBJECT-TYPE
    SYNTAX     InstanceName
    MAX-ACCESS read-only
    STATUS     current
    DESCRIPTION
	    "Instance name."
    ::= { windowsMediaPublishingPointsEntry 1 }

wmppCurConnectedPlayers OBJECT-TYPE
    SYNTAX     Gauge32
    MAX-ACCESS read-only
    STATUS     current
    DESCRIPTION
	    "Current Connected Players is the current
	    number of players with unicast connections to
	    the publishing point."
    ::= { windowsMediaPublishingPointsEntry 2 }

wmppCurFileReadRateKbps OBJECT-TYPE
    SYNTAX     Gauge32
    MAX-ACCESS read-only
    STATUS     current
    DESCRIPTION
	    "Current File Read Rate is the current read
	    rate, in Kbps, for all data files."
    ::= { windowsMediaPublishingPointsEntry 3 }

wmppCurLateReadRate OBJECT-TYPE
    SYNTAX     Gauge32
    MAX-ACCESS read-only
    STATUS     current
    DESCRIPTION
	    "Current Late Read Rate is the current number
	    of late read operations per second."
    ::= { windowsMediaPublishingPointsEntry 4 }

wmppCurOutDistAllocBandwidthKbps OBJECT-TYPE
    SYNTAX     Gauge32
    MAX-ACCESS read-only
    STATUS     current
    DESCRIPTION
	    "Current Outgoing Distribution Allocated
	    Bandwidth is the current bandwidth, in Kbps,
	    allocated for streams to all distribution
	    servers."
    ::= { windowsMediaPublishingPointsEntry 5 }

wmppCurOutDistConnections OBJECT-TYPE
    SYNTAX     Gauge32
    MAX-ACCESS read-only
    STATUS     current
    DESCRIPTION
	    "Current Outgoing Distribution Connections is
	    the current number of connections to
	    distribution servers."
    ::= { windowsMediaPublishingPointsEntry 6 }

wmppCurPlayerAllocBandwidthKbps OBJECT-TYPE
    SYNTAX     Gauge32
    MAX-ACCESS read-only
    STATUS     current
    DESCRIPTION
	    "Current Player Allocated Bandwidth is the
	    current bandwidth, in Kbps, that is allocated
	    for streams to all players."
    ::= { windowsMediaPublishingPointsEntry 7 }

wmppCurStreamErrorRate OBJECT-TYPE
    SYNTAX     Gauge32
    MAX-ACCESS read-only
    STATUS     current
    DESCRIPTION
	    "Current Stream Error Rate is the current
	    number of errors per second due to dropped
	    packets."
    ::= { windowsMediaPublishingPointsEntry 8 }

wmppCurStreamingHTTPPlayers OBJECT-TYPE
    SYNTAX     Gauge32
    MAX-ACCESS read-only
    STATUS     current
    DESCRIPTION
	    "Current Streaming HTTP Players is the current
	    number of players being streamed data using the
	    HTTP protocol. This does not include players
	    that are stopped or paused."
    ::= { windowsMediaPublishingPointsEntry 9 }

wmppCurStreamingMMSPlayers OBJECT-TYPE
    SYNTAX     Gauge32
    MAX-ACCESS read-only
    STATUS     current
    DESCRIPTION
	    "Current Streaming MMS Players is the current
	    number of players being streamed data using the
	    MMS protocol. This does not include players
	    that are stopped or paused."
    ::= { windowsMediaPublishingPointsEntry 10 }

wmppCurStreamingPlayers OBJECT-TYPE
    SYNTAX     Gauge32
    MAX-ACCESS read-only
    STATUS     current
    DESCRIPTION
	    "Current Streaming Players is the current
	    number of players being streamed data across
	    all protocols. This does not include players
	    that are stopped or paused."
    ::= { windowsMediaPublishingPointsEntry 11 }

wmppCurStreamingRTSPPlayers OBJECT-TYPE
    SYNTAX     Gauge32
    MAX-ACCESS read-only
    STATUS     current
    DESCRIPTION
	    "Current Streaming RTSP Players is the current
	    number of players being streamed data using the
	    RTSP protocol. This does not include players
	    that are stopped or paused."
    ::= { windowsMediaPublishingPointsEntry 12 }

wmppPeakConnectedPlayers OBJECT-TYPE
    SYNTAX     Gauge32
    MAX-ACCESS read-only
    STATUS     current
    DESCRIPTION
	    "Peak Connected Players is the peak number of
	    players that have connected since the last time
	    the counter was reset."
    ::= { windowsMediaPublishingPointsEntry 13 }

wmppPeakOutDistAllocBandwdthKbps OBJECT-TYPE
    SYNTAX     Gauge32
    MAX-ACCESS read-only
    STATUS     current
    DESCRIPTION
	    "Peak Outgoing Distribution Allocated Bandwidth
	    is the peak bandwidth, in Kbps, allocated for
	    all streams to distribution servers that have
	    connected since the last time the server was
	    reset."
    ::= { windowsMediaPublishingPointsEntry 14 }

wmppPeakOutDistConnections OBJECT-TYPE
    SYNTAX     Gauge32
    MAX-ACCESS read-only
    STATUS     current
    DESCRIPTION
	    "Peak Outgoing Distribution Connections is the
	    peak number of distribution servers that have
	    connected since the last time the counter was
	    reset."
    ::= { windowsMediaPublishingPointsEntry 15 }

wmppPeakPlayerAllocBandwidthKbps OBJECT-TYPE
    SYNTAX     Gauge32
    MAX-ACCESS read-only
    STATUS     current
    DESCRIPTION
	    "Peak Player Allocated Bandwidth is the peak
	    bandwidth, in Kbps, that was allocated for
	    streams to players since the last time the
	    counter was reset."
    ::= { windowsMediaPublishingPointsEntry 16 }

wmppPeakStreamingPlayers OBJECT-TYPE
    SYNTAX     Gauge32
    MAX-ACCESS read-only
    STATUS     current
    DESCRIPTION
	    "Peak Streaming Players is the peak number of
	    players that have been streamed data since the
	    last time the counter was reset."
    ::= { windowsMediaPublishingPointsEntry 17 }

wmppTotalAdvertisements OBJECT-TYPE
    SYNTAX     Gauge32
    MAX-ACCESS read-only
    STATUS     current
    DESCRIPTION
	    "Total Advertisements is the total number of
	    advertisements that have been streamed from
	    playlists since the last time the counter was
	    reset."
    ::= { windowsMediaPublishingPointsEntry 18 }

wmppTotalConnectedPlayers OBJECT-TYPE
    SYNTAX     Gauge32
    MAX-ACCESS read-only
    STATUS     current
    DESCRIPTION
	    "Total Connected Players is the total number of
	    players that have connected since the last time
	    the counter was reset."
    ::= { windowsMediaPublishingPointsEntry 19 }

wmppTotalFileBytesRead OBJECT-TYPE
    SYNTAX     Gauge32
    MAX-ACCESS read-only
    STATUS     current
    DESCRIPTION
	    "Total File Bytes Read is the total number of
	    file bytes read."
    ::= { windowsMediaPublishingPointsEntry 20 }

wmppTotalLateReads OBJECT-TYPE
    SYNTAX     Gauge32
    MAX-ACCESS read-only
    STATUS     current
    DESCRIPTION
	    "Total Late Reads is the total number of late
	    read operations since the last time the counter
	    was reset."
    ::= { windowsMediaPublishingPointsEntry 21 }

wmppTotalOutDistBytesSent OBJECT-TYPE
    SYNTAX     Gauge32
    MAX-ACCESS read-only
    STATUS     current
    DESCRIPTION
	    "Total Outgoing Distribution Bytes Sent is the
	    total number of bytes streamed to all
	    distribution servers since the last time the
	    counter was reset."
    ::= { windowsMediaPublishingPointsEntry 22 }

wmppTotalOutDistConnections OBJECT-TYPE
    SYNTAX     Gauge32
    MAX-ACCESS read-only
    STATUS     current
    DESCRIPTION
	    "Total Outgoing Distribution Connections is the
	    total number of distribution servers that have
	    connected since the last time the counter was
	    reset."
    ::= { windowsMediaPublishingPointsEntry 23 }

wmppTotalPlayerBytesSent OBJECT-TYPE
    SYNTAX     Gauge32
    MAX-ACCESS read-only
    STATUS     current
    DESCRIPTION
	    "Total Player Bytes Sent is the total number of
	    bytes streamed to all players since the last
	    time the counter was reset."
    ::= { windowsMediaPublishingPointsEntry 24 }

wmppTotalStreamDenials OBJECT-TYPE
    SYNTAX     Gauge32
    MAX-ACCESS read-only
    STATUS     current
    DESCRIPTION
	    "Total Stream Denials is the total number of
	    stream denials since the last time the counter
	    was reset. This includes both denials that
	    occurred due to failure to be authorized or
	    authenticated, as well as denials that occurred
	    because limits were exceeded."
    ::= { windowsMediaPublishingPointsEntry 25 }

wmppTotalStreamErrors OBJECT-TYPE
    SYNTAX     Gauge32
    MAX-ACCESS read-only
    STATUS     current
    DESCRIPTION
	    "Total Stream Errors is the total number of
	    stream errors due to dropped packets since the
	    last time the counter was reset."
    ::= { windowsMediaPublishingPointsEntry 26 }

wmppTotalStreamTerminations OBJECT-TYPE
    SYNTAX     Gauge32
    MAX-ACCESS read-only
    STATUS     current
    DESCRIPTION
	    "Total Stream Terminations is the total number
	    of streams that were terminated due to
	    inactivity or errors since the last time the
	    counter was reset. This includes terminations
	    that occurred because player inactivity and
	    timeout limits were exceeded, as well as
	    terminations that were due to events such as
	    late reads."
    ::= { windowsMediaPublishingPointsEntry 27 }

wmppTotalStreamingPlayers OBJECT-TYPE
    SYNTAX     Gauge32
    MAX-ACCESS read-only
    STATUS     current
    DESCRIPTION
	    "Total Streaming Players is the total number of
	    players that have been streamed data since the
	    last time the counter was reset."
    ::= { windowsMediaPublishingPointsEntry 28 }

windowsMediaStationService OBJECT-IDENTITY
    STATUS     current
    DESCRIPTION
	    "The Windows Media Station Service performance
	    object provides statistics about the Windows
	    Media Station service that provides
	    multicasting, distribution and storage
	    functions for ASF streams."
    ::= { advanced 90 }

wmssControllers OBJECT-TYPE
    SYNTAX     Gauge32
    MAX-ACCESS read-only
    STATUS     current
    DESCRIPTION
	    "The number of controllers currently connected
	    to the server."
    ::= { windowsMediaStationService 1 }

wmssStations OBJECT-TYPE
    SYNTAX     Gauge32
    MAX-ACCESS read-only
    STATUS     current
    DESCRIPTION
	    "The number of station objects that currently
	    exist in the server."
    ::= { windowsMediaStationService 2 }

wmssStreams OBJECT-TYPE
    SYNTAX     Gauge32
    MAX-ACCESS read-only
    STATUS     current
    DESCRIPTION
	    "The number of stream objects that currently
	    exist in the server."
    ::= { windowsMediaStationService 3 }

windowsMediaUnicastService OBJECT-IDENTITY
    STATUS     current
    DESCRIPTION
	    "The Windows Media Unicast Service performance
	    object provides statistics about the Windows
	    Media service Unicast service that provides
	    unicasting functions for Advanced Streaming
	    Format (ASF) streams."
    ::= { advanced 91 }

wmusActiveLiveUnicastStreams OBJECT-TYPE
    SYNTAX     Gauge32
    MAX-ACCESS read-only
    STATUS     current
    DESCRIPTION
	    "The number of Live Unicast streams that are
	    being streamed."
    ::= { windowsMediaUnicastService 1 }

wmusActiveStreams OBJECT-TYPE
    SYNTAX     Gauge32
    MAX-ACCESS read-only
    STATUS     current
    DESCRIPTION
	    "The number of streams that are being
	    streamed."
    ::= { windowsMediaUnicastService 2 }

wmusActiveTCPStreams OBJECT-TYPE
    SYNTAX     Gauge32
    MAX-ACCESS read-only
    STATUS     current
    DESCRIPTION
	    "The number of TCP streams that are being
	    streamed."
    ::= { windowsMediaUnicastService 3 }

wmusActiveUDPStreams OBJECT-TYPE
    SYNTAX     Gauge32
    MAX-ACCESS read-only
    STATUS     current
    DESCRIPTION
	    "The number of UDP streams that are being
	    streamed."
    ::= { windowsMediaUnicastService 4 }

wmusAggregateReadRate OBJECT-TYPE
    SYNTAX     Gauge32
    MAX-ACCESS read-only
    STATUS     current
    DESCRIPTION
	    "The total, aggregate rate (bytes/sec) of file
	    reads."
    ::= { windowsMediaUnicastService 5 }

wmusAggregateSendRate OBJECT-TYPE
    SYNTAX     Gauge32
    MAX-ACCESS read-only
    STATUS     current
    DESCRIPTION
	    "The total, aggregate rate (bytes/sec) of
	    stream transmission."
    ::= { windowsMediaUnicastService 6 }

wmusAllocatedBandwidth OBJECT-TYPE
    SYNTAX     Gauge32
    MAX-ACCESS read-only
    STATUS     current
    DESCRIPTION
	    "The bandwidth (bytes/sec) currently allocated
	    by clients."
    ::= { windowsMediaUnicastService 7 }

wmusAuthenticationRequests OBJECT-TYPE
    SYNTAX     Gauge32
    MAX-ACCESS read-only
    STATUS     current
    DESCRIPTION
	    "The number of times an authentication plugin
	    is called to authenticate a client. Depending
	    on the protocol in use, either HTTP or
	    Microsoft Media Server (MMS), a single client
	    may be authenticated once or several times when
	    accessing each piece of unicast co"
    ::= { windowsMediaUnicastService 8 }

wmusAuthenticationsDenied OBJECT-TYPE
    SYNTAX     Gauge32
    MAX-ACCESS read-only
    STATUS     current
    DESCRIPTION
	    "The number of times clients are denied access
	    to unicast content by authentication plugins.
	    Clients are denied access by an authentication
	    plugin when their IDs cannot be verified, no
	    user accounts exist, or the authentication
	    plugin is not working."
    ::= { windowsMediaUnicastService 9 }

wmusAuthorizationRequests OBJECT-TYPE
    SYNTAX     Gauge32
    MAX-ACCESS read-only
    STATUS     current
    DESCRIPTION
	    "The number of times an authorization plugin is
	    called to authorize a client. Each client
	    action, such as opening or playing unicast
	    content, is separately authorized; therefore,
	    the total number of authorization requests is
	    greater than the number of connecte"
    ::= { windowsMediaUnicastService 10 }

wmusAuthorizationsRefused OBJECT-TYPE
    SYNTAX     Gauge32
    MAX-ACCESS read-only
    STATUS     current
    DESCRIPTION
	    "The number of times clients are denied access
	    to unicast content by authorization plugins.
	    Plugins will deny access to clients based on
	    their function; for example, a billing plugin
	    may deny client access to unicast content if
	    the user account contains insuff"
    ::= { windowsMediaUnicastService 11 }

wmusConnectedClients OBJECT-TYPE
    SYNTAX     Gauge32
    MAX-ACCESS read-only
    STATUS     current
    DESCRIPTION
	    "The number of clients connected to this
	    server."
    ::= { windowsMediaUnicastService 12 }

wmusConnectionRate OBJECT-TYPE
    SYNTAX     Gauge32
    MAX-ACCESS read-only
    STATUS     current
    DESCRIPTION
	    "The rate at which clients are connecting to
	    the server."
    ::= { windowsMediaUnicastService 13 }

wmusHTTPStreams OBJECT-TYPE
    SYNTAX     Gauge32
    MAX-ACCESS read-only
    STATUS     current
    DESCRIPTION
	    "The number of HTTP streams being streamed."
    ::= { windowsMediaUnicastService 14 }

wmusHTTPStreamsReadingHeader OBJECT-TYPE
    SYNTAX     Gauge32
    MAX-ACCESS read-only
    STATUS     current
    DESCRIPTION
	    "The number of clients connected to the server
	    via HTTP and reading a file header, but not yet
	    streaming the unicast content. HTTP Streams
	    Reading Header and HTTP Streams Reading Body
	    equal the total number of clients connected to
	    the server via HTTP, as indic"
    ::= { windowsMediaUnicastService 15 }

wmusHTTPStreamsStreamingBody OBJECT-TYPE
    SYNTAX     Gauge32
    MAX-ACCESS read-only
    STATUS     current
    DESCRIPTION
	    "The number of connected clients that have read
	    the file header and are actively streaming
	    unicast content via HTTP. HTTP Streams Reading
	    Body and HTTP Streams Reading Header equal the
	    total number of clients connected to the server
	    via HTTP, as indicated by H"
    ::= { windowsMediaUnicastService 16 }

wmusLateReads OBJECT-TYPE
    SYNTAX     Gauge32
    MAX-ACCESS read-only
    STATUS     current
    DESCRIPTION
	    "The number of late read completions per
	    second."
    ::= { windowsMediaUnicastService 17 }

wmusPendingConnections OBJECT-TYPE
    SYNTAX     Gauge32
    MAX-ACCESS read-only
    STATUS     current
    DESCRIPTION
	    "The number of clients attempting to connect to
	    the server but are not yet connected. This
	    number may be high if the server is running
	    near maximum capacity and cannot process a
	    large number of connection requests in a timely
	    manner."
    ::= { windowsMediaUnicastService 18 }

wmusPluginErrors OBJECT-TYPE
    SYNTAX     Gauge32
    MAX-ACCESS read-only
    STATUS     current
    DESCRIPTION
	    "The number of times plugins failed to perform
	    their function. For example, a plugin couldn't
	    reach its user database, the plugin crashed,
	    and so on."
    ::= { windowsMediaUnicastService 19 }

wmusPluginEvents OBJECT-TYPE
    SYNTAX     Gauge32
    MAX-ACCESS read-only
    STATUS     current
    DESCRIPTION
	    "The number of events reported to plugins. An
	    indicator of how much the server is using
	    external plugins."
    ::= { windowsMediaUnicastService 20 }

wmusSchedulingRate OBJECT-TYPE
    SYNTAX     Gauge32
    MAX-ACCESS read-only
    STATUS     current
    DESCRIPTION
	    "The rate (tasks/sec) at which tasks are being
	    scheduled."
    ::= { windowsMediaUnicastService 21 }

wmusStreamErrors OBJECT-TYPE
    SYNTAX     Gauge32
    MAX-ACCESS read-only
    STATUS     current
    DESCRIPTION
	    "The cumulative number of errors occuring per
	    second."
    ::= { windowsMediaUnicastService 22 }

wmusStreamTerminations OBJECT-TYPE
    SYNTAX     Gauge32
    MAX-ACCESS read-only
    STATUS     current
    DESCRIPTION
	    "The rate at which streams are being terminated
	    due to errors."
    ::= { windowsMediaUnicastService 23 }

wmusUDPResendRequests OBJECT-TYPE
    SYNTAX     Gauge32
    MAX-ACCESS read-only
    STATUS     current
    DESCRIPTION
	    "The number of times clients ask the server to
	    resend a data packet that was received in
	    error. This value may be high when the server
	    cannot send packets via UDP reliably. A good
	    indicator of server or network overload."
    ::= { windowsMediaUnicastService 24 }

wmusUDPResendsSent OBJECT-TYPE
    SYNTAX     Gauge32
    MAX-ACCESS read-only
    STATUS     current
    DESCRIPTION
	    "The number of UDP Resend Requests processed by
	    the server. Not all UDP Resend Requests are
	    processed if the server is under a heavy load."
    ::= { windowsMediaUnicastService 25 }

winsServer OBJECT IDENTIFIER
    ::= { advanced 92 }

winsSrvrFailedQueriesPerSec OBJECT-TYPE
    SYNTAX     Gauge32
    MAX-ACCESS read-only
    STATUS     current
    DESCRIPTION
	    "Total Number of Failed Queries/sec"
    ::= { winsServer 1 }

winsSrvrFailedReleasesPerSec OBJECT-TYPE
    SYNTAX     Gauge32
    MAX-ACCESS read-only
    STATUS     current
    DESCRIPTION
	    "Total Number of Failed Releases/sec"
    ::= { winsServer 2 }

winsSrvrGroupConflictsPerSec OBJECT-TYPE
    SYNTAX     Gauge32
    MAX-ACCESS read-only
    STATUS     current
    DESCRIPTION
	    "Group Conflicts/sec is the rate at which group
	    registration received by the WINS server
	    resulted in conflicts with records in the
	    database."
    ::= { winsServer 3 }

winsSrvrGroupRegsPerSec OBJECT-TYPE
    SYNTAX     Gauge32
    MAX-ACCESS read-only
    STATUS     current
    DESCRIPTION
	    "Group Registrations/sec is the rate at which
	    group registration are received by the WINS
	    server."
    ::= { winsServer 4 }

winsSrvrGroupRenewalsPerSec OBJECT-TYPE
    SYNTAX     Gauge32
    MAX-ACCESS read-only
    STATUS     current
    DESCRIPTION
	    "Group Renewals/sec is the rate at which group
	    renewals are received by the WINS server."
    ::= { winsServer 5 }

winsSrvrQueriesPerSec OBJECT-TYPE
    SYNTAX     Gauge32
    MAX-ACCESS read-only
    STATUS     current
    DESCRIPTION
	    "Total Number of Queries/sec is the rate at
	    which queries are received by the WINS server."
    ::= { winsServer 6 }

winsSrvrReleasesPerSec OBJECT-TYPE
    SYNTAX     Gauge32
    MAX-ACCESS read-only
    STATUS     current
    DESCRIPTION
	    "Total Number of Releases/sec is the rate at
	    which releases are received by the WINS
	    server."
    ::= { winsServer 7 }

winsSrvrSuccessfulQueriesPerSec OBJECT-TYPE
    SYNTAX     Gauge32
    MAX-ACCESS read-only
    STATUS     current
    DESCRIPTION
	    "Total Number of Successful Queries/sec"
    ::= { winsServer 8 }

winsSrvrSuccessfulReleasesPerSec OBJECT-TYPE
    SYNTAX     Gauge32
    MAX-ACCESS read-only
    STATUS     current
    DESCRIPTION
	    "Total Number of Successful Releases/sec"
    ::= { winsServer 9 }

winsSrvrTotalNumConflictsPerSec OBJECT-TYPE
    SYNTAX     Gauge32
    MAX-ACCESS read-only
    STATUS     current
    DESCRIPTION
	    "Total Number of Conflicts/sec is the sum of
	    the Unique and Group conflicts per sec.  This
	    is the total rate at which conflicts were seen
	    by the WINS server."
    ::= { winsServer 10 }

winsSrvrTotalNumRegsPerSec OBJECT-TYPE
    SYNTAX     Gauge32
    MAX-ACCESS read-only
    STATUS     current
    DESCRIPTION
	    "Total Number of Registrations/sec is the sum
	    of the Unique and Group registrations per sec. 
	    This is the total rate at which registration
	    are received by the WINS server."
    ::= { winsServer 11 }

winsSrvrTotalNumRenewalsPerSec OBJECT-TYPE
    SYNTAX     Gauge32
    MAX-ACCESS read-only
    STATUS     current
    DESCRIPTION
	    "Total Number of Renewals/sec is the sum of the
	    Unique and Group renewals per sec.	This is the
	    total rate at which renewals are received by
	    the WINS server."
    ::= { winsServer 12 }

winsSrvrUniqueConflictsPerSec OBJECT-TYPE
    SYNTAX     Gauge32
    MAX-ACCESS read-only
    STATUS     current
    DESCRIPTION
	    "Unique Conflicts/sec is the rate at which
	    unique registrations/renewals received by the
	    WINS server resulted in conflicts with records
	    in the database."
    ::= { winsServer 13 }

winsSrvrUniqueRegsPerSec OBJECT-TYPE
    SYNTAX     Gauge32
    MAX-ACCESS read-only
    STATUS     current
    DESCRIPTION
	    "Unique Registrations/sec is the rate at which
	    unique registration are received by the WINS
	    server."
    ::= { winsServer 14 }

winsSrvrUniqueRenewalsPerSec OBJECT-TYPE
    SYNTAX     Gauge32
    MAX-ACCESS read-only
    STATUS     current
    DESCRIPTION
	    "Unique Renewals/sec is the rate at which
	    unique renewals are received by the WINS
	    server."
    ::= { winsServer 15 }

wmiObjects OBJECT IDENTIFIER
    ::= { advanced 93 }

wmiObjectsHiPerfClasses OBJECT-TYPE
    SYNTAX     Gauge32
    MAX-ACCESS read-only
    STATUS     current
    DESCRIPTION
	    "Shows High Performance Classes"
    ::= { wmiObjects 1 }

wmiObjectsHiPerfValidity OBJECT-TYPE
    SYNTAX     Gauge32
    MAX-ACCESS read-only
    STATUS     current
    DESCRIPTION
	    "Shows if High Performance Classes are valid"
    ::= { wmiObjects 2 }

END
