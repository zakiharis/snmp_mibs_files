-- ****************************************************************************
--                             InnovxCore.mib
-- ****************************************************************************

-- INNOVX Access Probe - Core MIB


-- Copyright 1999 General DataComm Inc., All Rights Reserved.

-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.

-- This Specification is supplied "AS IS," and GDC makes no warranty,
-- either expressed or implied, as to the use operation, condition, or
-- performance of the Specification.

-- This mib is serves as a base or common mib for all Innovx products.
--

--
-- ****************************************************************************
--                        Revision History
-- ****************************************************************************

-- Version   Date	Name/Comments

-- 1.00A     15-Dec-98  S. Veillette
--                      1) Initial Revision
--
-- 1.00B     24-Feb-99	S. Veillette
--                      1) Added INNOVX family mib node identifiers:
--                         casGroup, ddsGroup, and dteGroup
--
--			2) Added INNOVX core mib group - coreStatus
--                         and objects: innovxLedStatus, innovxPortStatus
--                         and innovxPortFrameCounts.
--
-- 1.00C     23-Mar-99	A. Limoncelli
--                      1) removed reset of factory default object
--

-- 1.00D     21-May-99	S. Veillette
--                      1) Add ap553DS0Format & ap553NumberOfDS0s
--                         as readOnly objects for common access by Redpoint
--                         to all Innovx products.



-- ****************************************************************************

--
-- ****************************************************************************
--                       mib definitions begin
-- ****************************************************************************


INNOVX-CORE-MIB DEFINITIONS ::= BEGIN

IMPORTS	
enterprises, IpAddress			FROM RFC1155-SMI
OBJECT-TYPE				FROM RFC-1212
DisplayString, sysName			FROM RFC1213-MIB
TRAP-TYPE				FROM RFC-1215;


gdc                 	OBJECT IDENTIFIER ::= { enterprises 498 }
framerelay		OBJECT IDENTIFIER ::= { gdc 22 }
innovx			OBJECT IDENTIFIER ::= { framerelay 1 }


-- INNOVX family node identifiers & mib names

-- coreGroup    - InnovxCore.mib
-- linkProbe    - FRProbe.mib
-- liuGroup     - AP553Liu.mib
-- casGroup     - InnovxCascadeLiu.mib
-- ddsGroup     - InnovxDds.mib
-- dteGroup     - InnovxDte.mib


-- INNOVX family mib node identifiers

coreGroup	     	OBJECT IDENTIFIER ::= { innovx 1 }
linkProbe	     	OBJECT IDENTIFIER ::= { innovx 2 }
liuGroup	     	OBJECT IDENTIFIER ::= { innovx 3 }
casGroup	     	OBJECT IDENTIFIER ::= { innovx 4 }
ddsGroup		OBJECT IDENTIFIER ::= { innovx 5 }
dteGroup		OBJECT IDENTIFIER ::= { innovx 6 }


-- INNOVX core mib groups

coreAdmin        	OBJECT IDENTIFIER ::= { coreGroup  1 }
coreReset        	OBJECT IDENTIFIER ::= { coreGroup  2 }
coreDiags        	OBJECT IDENTIFIER ::= { coreGroup  3 }
coreStatus		OBJECT IDENTIFIER ::= { coreGroup  4 }
coreTrapArgs        	OBJECT IDENTIFIER ::= { coreGroup  5 }
coreAggRate        	OBJECT IDENTIFIER ::= { coreGroup  6 }
coreFeatures            OBJECT IDENTIFIER ::= { coreGroup  7 }
        

--
-- ****************************************************************************
--                            Administrative Group
-- ****************************************************************************


innovxMIBversion OBJECT-TYPE
    SYNTAX DisplayString (SIZE (5))
    ACCESS read-only
    STATUS mandatory
    DESCRIPTION
    "Identifies the version of the MIB as `X.YZT' where:

	X: Major Revision         (1-9)
	Y: Minor Revision         (0-9)
	Z: Typographical Revision (0-9)
	T: Test Revision          (A-Z)

    Upon formal release, the test revision will not be present."

    ::= { coreAdmin 1 }


innovxFirmwareVersion OBJECT-TYPE
    SYNTAX DisplayString (SIZE(8))
    ACCESS read-only
    STATUS mandatory
    DESCRIPTION
    "Identifies the version of the firmware as `MM.NN.BB' where:
	
	MM: Major Revision   (0-99)
	NN: Minor Revision   (0-99)
	BB: Bug Fix Revision (0-99) "

    ::= { coreAdmin 2 }


innovxSerialNumber OBJECT-TYPE
    SYNTAX DisplayString (SIZE (16))
    ACCESS read-only
    STATUS mandatory
    DESCRIPTION
    "Identifies the serial number of the unit."

    ::= { coreAdmin 3 }


innovxHardwareVersion OBJECT-TYPE
    SYNTAX DisplayString (SIZE (2))
    ACCESS read-only
    STATUS mandatory
    DESCRIPTION
    "Identifies the version of the base card hardware. The released
    version number is sequenced as follows: --, A-, ... AA, ... ZZ. "

    ::= { coreAdmin 4 }


innovxHardwareDescription OBJECT-TYPE
    SYNTAX DisplayString (SIZE (255))
    ACCESS read-only
    STATUS mandatory
    DESCRIPTION
    "Identifies the model number, memory size and options.
    Example=> Model: 553, Flash: 2M, RAM: 16M, Options: Cascade"

    ::= { coreAdmin 5 }


innovxBootCodeVersion OBJECT-TYPE
    SYNTAX DisplayString (SIZE(2))
    ACCESS read-only
    STATUS mandatory
    DESCRIPTION
    "Identifies the version of the bootstrap firmware. The released
    version number is sequenced as follows: --, A-, ... AA, ... ZZ. "

    ::= { coreAdmin 6 }


innovxHardwareOptions OBJECT-TYPE
    SYNTAX OCTET STRING (SIZE(2))
    ACCESS read-only
    STATUS mandatory
    DESCRIPTION
    "Identifies the hardware options installed on this innovx product.
    where 0 = not installed and 1 = installed, as follows:

                        LED       description
 
    Octet 1     bit 7 - n/u
                bit 6 - n/u
		bit 5 - n/u
		bit 4 - n/u
		bit 3 - n/u
		bit 2 - n/u
		bit 1 - n/u
		bit 0 - n/u

    Octet 2     bit 7 - n/u
		bit 6 - n/u
		bit 5 - n/u
		bit 4 - n/u
		bit 3 - n/u
		bit 2 - n/u
		bit 1 - n/u
		bit 0 - Cascade Adapter"

    ::= { coreAdmin 7 }



cmnTrapAddrTable OBJECT-TYPE
    SYNTAX  SEQUENCE OF CmnTrapAddrEntry
    ACCESS  not-accessible
    STATUS  mandatory
    DESCRIPTION
	"A table of management systems ready to accept traps
	generated by this node.

	To add an entry to the table, a set on the Community
	name for the instance (IP Address and UDP PORT) needs
	to be performed.  To delete an entry, a set on the
	Status to invalid on the instance needs to be
	performed."
    ::= { coreAdmin 8 }

cmnTrapAddrEntry OBJECT-TYPE
    SYNTAX  CmnTrapAddrEntry
    ACCESS  not-accessible
    STATUS  mandatory
    DESCRIPTION
    	"Information needed to deliver traps to a particular
    	management station. This table holds a maximum of 4
        entries."
    INDEX   { cmnTrapAddrIpDest }
    ::= { cmnTrapAddrTable 1 }

CmnTrapAddrEntry ::=
    SEQUENCE {
    	cmnTrapAddrIpDest
    		IpAddress,
    	cmnTrapAddrCommunity
                DisplayString,
        cmnTrapAddrStatus
                INTEGER
	}

cmnTrapAddrIpDest  OBJECT-TYPE
    SYNTAX  IpAddress
    ACCESS  read-only
    STATUS  mandatory
    DESCRIPTION
    	"The IP address of the management agent receiving
    	traps.

    	The IP address of 0.0.0.0 will not be allowed."
    ::= { cmnTrapAddrEntry 1 }


cmnTrapAddrCommunity  OBJECT-TYPE
    SYNTAX  DisplayString (SIZE (1..32))
    ACCESS  read-write
    STATUS  mandatory
    DESCRIPTION
	"The community name expected by the management station
	receiving traps."
    ::= { cmnTrapAddrEntry 2 }

cmnTrapAddrStatus  OBJECT-TYPE
    SYNTAX  INTEGER {
                     valid(1),
                     invalid(2)
    }
    ACCESS  read-write
    STATUS  mandatory
    DESCRIPTION
         "The status of the entry.  If read and the entry
          exists, valid(1) will always be returned.
 
          Invalid entries will be removed from the table."
    ::= { cmnTrapAddrEntry 3 }

		

--
-- ****************************************************************************
--                              Reset Group
-- ****************************************************************************


innovxSoftReset OBJECT-TYPE
    SYNTAX INTEGER
    {
	normal  (1),  -- read-only
        reset   (2)
    }
    ACCESS read-write
    STATUS mandatory
    DESCRIPTION
    "A set of `reset' on this object instructs the unit to perform a
    soft reset."

    ::= { coreReset 1 }



innovxStatsReset OBJECT-TYPE
    SYNTAX  INTEGER
    {
        normal  (1),  -- read only
        reset   (2)
    }
    ACCESS  read-write
    STATUS  mandatory
    DESCRIPTION
    "A set of `reset' on this object instructs the unit to set all statistics
    tracking objects to zero, including: current interval values, 24 hour
    total values, number of valid historical interval objects values, and all
    historical interval objects values (#1 - #96)."

    ::= { coreReset 2 }



--
-- ****************************************************************************
--                             Diagnostics Group
-- ****************************************************************************


innovxSelfTest OBJECT-TYPE
    SYNTAX INTEGER
    {
	normal      (1),  -- read-only
        start-test  (2)
    }
    ACCESS read-write
    STATUS mandatory
    DESCRIPTION
    "A set of `start-test' on this object instructs the unit to perform a
    self test."

    ::= { coreDiags 1 }


innovxSelfTestStatus OBJECT-TYPE
    SYNTAX INTEGER
    {
        normal-complete-pass  (1),
        normal-complete-fail  (2),
	test-in-progress      (3)
    }
    ACCESS read-only
    STATUS mandatory
    DESCRIPTION
    "Describes the result of a unit self test, during normal operation and
    after an innovxSoftReset or an innovxDefaultReset this object will read
    `normal-complete-pass'."

    ::= { coreDiags 2 }


--
-- ****************************************************************************
--                            Core Status Group
-- ****************************************************************************


innovxLedStatus OBJECT-TYPE	
    SYNTAX OCTET STRING (SIZE(1))
    ACCESS read-only
    STATUS mandatory
    DESCRIPTION
    "A bitwise snapshot of the front panel LED states, 
    where 0 = LED off and 1 = LED on, as follows:

                        LED       description
 
    Octet 1     bit 7 - n/u
		bit 6 - n/u
		bit 5 - n/u
		bit 4 - LAN       LAN activity
		bit 3 - ALM       Alarm Condition - any
		bit 2 - CN        Congestion (FECNS & BECNS)    
		bit 1 - TST       Test Mode
		bit 0 - ERR       Framing Errors"

    ::= { coreStatus 1 }


innovxPortStatus OBJECT-TYPE
    SYNTAX  OCTET STRING (SIZE(2))
    ACCESS  read-only
    STATUS  mandatory
    DESCRIPTION
    "A bitwise snapshot of interface port status conditions and EIA signals,
    where 0 = condition not present, and 1 = condition present, as follows:

    Octet 1 - ETHERNET Interface Port Status
 		bit 7 - n/u
               	bit 6 - n/u
                bit 5 - n/u
                bit 4 - Transmit Activity
                bit 3 - Receive Activity
                bit 2 - Runt packet (<64k bytes)
                bit 1 - CRC Error
                bit 0 - Transmit Collisions

    Octet 2 - PPP/CONSOLE Interface Port Status
 		bit 7 - interface mode: 0 = PPP, 1 = Console, 
                        (invalid if 'handshake in progress') 
               	bit 6 - handshake in progress = 1/handshake complete = 0
                bit 5 - n/u
                bit 4 - n/u
                bit 3 - n/u
                bit 2 - DTR Loss
                bit 1 - Transmit Activity
                bit 0 - Receive Activity"

    ::= { coreStatus 2 }



innovxPortFrameCounts OBJECT-TYPE	
    SYNTAX  OCTET STRING (SIZE(8))
    ACCESS  read-only
    STATUS  mandatory
    DESCRIPTION
    "The total number of frames transmitted and received on each interface
    port.  This object will be reset to zero after a read, and after power up,
    soft reset, or factory defaults reset.

    Octet 1 - ETHERNET Interface Transmit Frame Count	Octet 2
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0

    Octet 3 - ETHERNET Interface Receive Frame Count	Octet 4
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0

    Octet 5 - PPP/CONSOLE Intrf Tx Data Byte Count	Octet 6
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0

    Octet 7 - PPP/CONSOLE Intrf Rx Data Byte Count	Octet 8
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0"

    ::= { coreStatus 3 }


--
-- ****************************************************************************
--                            Trap Arguments Group
-- ****************************************************************************



innovxTrapSeverity OBJECT-TYPE
    SYNTAX INTEGER
    {
	critical  (1),
        major     (2),
        minor     (3),
        warning   (4),
        info      (5)
    }
    ACCESS not-accessible
    STATUS mandatory
    DESCRIPTION
    "Trap argument describing severity of the trap being reported."

    ::={ coreTrapArgs 1 }


innovxTrapState OBJECT-TYPE
    SYNTAX  DisplayString (SIZE (0..16))
    ACCESS not-accessible
    STATUS mandatory
    DESCRIPTION
    "Trap argument describing the state of the specific condition
    reported as: active, clear or exceeded."

    ::= { coreTrapArgs 2 }


innovxTrapDescription OBJECT-TYPE
    SYNTAX  DisplayString (SIZE (0..255))
    ACCESS  not-accessible
    STATUS  mandatory
    DESCRIPTION
    "Trap argument describing the trap being reported."

    ::= { coreTrapArgs 3 }


innovxTrapThreshold OBJECT-TYPE
    SYNTAX  DisplayString (SIZE (0..255))
    ACCESS  not-accessible
    STATUS  mandatory
    DESCRIPTION
    "Trap argument describing the threshold value which was met in reporting
    the trap condition.  This argument will be NULL (size 0) if not applicable
    to the trap condition being reported."

    ::= { coreTrapArgs 4 }


innovxTrapActualValue OBJECT-TYPE
    SYNTAX  DisplayString (SIZE (0..255))
    ACCESS  not-accessible
    STATUS  mandatory
    DESCRIPTION
    "Trap argument identifying the current event value of this trap. This
    argument will be NULL (size 0) if not applicable to the trap condition
    being reported."

    ::= { coreTrapArgs 5}


innovxTrapDlci OBJECT-TYPE
    SYNTAX INTEGER ( 16..991 )
    ACCESS not-accessible
    STATUS mandatory
    DESCRIPTION
    "Trap argument identifying the DLCI number of the specific condition
    reported.  This argument will be set to 0 if not applicable to the
    trap condition being reported."

    ::= { coreTrapArgs 6 }


innovxpvcIdentifier OBJECT-TYPE
    SYNTAX  DisplayString (SIZE (0..32))
    ACCESS  not-accessible
    STATUS  mandatory
    DESCRIPTION
    "Comment field for PVC description, backfilled from the FRProbe mib."
  
  ::= {  coreTrapArgs 7 }



--
-- ****************************************************************************
--                            Innovx Alarm Trap
-- ****************************************************************************


innovxAlarmTrap TRAP-TYPE
    ENTERPRISE  innovx
    VARIABLES  
    { 
	sysName, 
	innovxTrapSeverity,
	innovxTrapState,
	innovxTrapDescription, 
	innovxTrapThreshold,
	innovxTrapActualValue,
	innovxTrapDlci,
	innovxpvcIdentifier
    }	
    DESCRIPTION
    "Trap used to report all alarm conditions on the Innovx products.  Some
    trap arguments may not apply for specific conditions reported, see above.
    Imported arguments: sysName - from rfc1213.mib, and pvcIdentifier - from 
    FPProbe.mib, a comment field for DLCI description, pvcIdentifier will be
    NULL (size 0) if not applicable to the trap condition being reported."

    ::= 1



--
-- ****************************************************************************
--                            Core Aggregate Rate Group
-- ****************************************************************************



ap553DS0Format OBJECT-TYPE
    SYNTAX INTEGER
    {
        nx56k  (1),  -- N X 56K rate
        nx64k  (2)   -- N X 64K rate
    }
    ACCESS read-only
    STATUS mandatory
    DESCRIPTION
    "Defines the DS0 base rate as either 56K or 64K bits per second.
    This object value, in conjunction with the ap553NumDS0s object
    value determines the LIU aggregate bandwidth.
    `nx64k' defines a DS0 data format as clear channel in which all 8 bits
    of the DS0 are used for data. 
    `nx56k defines a DS0 data format as 7 bits for data, and 1 bit used for
    signalling information or unused and forced to marks.

    The DSU will enforce an 8x(N+1) minimum ones density requirement when
    ap553NetLineCoding == `ami' and ap553DS0Format == `nx64k' and
    ap553DS0AllocationScheme == `consecutive'."

    ::= { coreAggRate 1 }


ap553NumberOfDS0s OBJECT-TYPE
    SYNTAX INTEGER (1..24)
    ACCESS read-only
    STATUS mandatory
    DESCRIPTION
    "Defines the number of DS0 cells used for passing DSU data.

    When ap553DS0AllocationScheme is consecutive, valid values are 1 - N
    where N <= (25 - ap553StartingDS0).

    When ap553DS0AllocationScheme is alternate, valid values are 1 - N
    where N <= (25 - ap553StartingDS0)/2."

    ::= { coreAggRate 2 }


--
-- ****************************************************************************
--                            Core Features Group
-- ****************************************************************************


innovxFeatureTable OBJECT-TYPE
    SYNTAX  SEQUENCE OF InnovxFeatureEntry
    ACCESS  not-accessible
    STATUS  mandatory
    DESCRIPTION
	"A table of keyable software features contained in this
	this product.

	This table holds information about the software
	features that are available and can be Key enabled 
        on this product. It also holds the status (On/Off)
	of the enabled features."
    ::= { coreFeatures 1 }

innovxFeatureEntry OBJECT-TYPE
    SYNTAX  InnovxFeatureEntry
    ACCESS  not-accessible
    STATUS  mandatory
    DESCRIPTION
    	"Software Features that have been Key enabled 
        in this product. This table holds a maximum of 16
        entries."
    INDEX   { innovxFeatureIndex }
    ::= { innovxFeatureTable 1 }

InnovxFeatureEntry ::=
    SEQUENCE {
		innovxFeatureIndex
			INTEGER,
    		innovxFeatureName
                	DisplayString,
    		innovxFeatureEnable
                	INTEGER,
        	innovxFeatureStatus
                	INTEGER
	      }

innovxFeatureIndex OBJECT-TYPE
    SYNTAX INTEGER ( 1..16 )
    ACCESS read-only
    STATUS mandatory
    DESCRIPTION
        " Identifies an entry (row) in the feature table,
         1-16 features. "
    ::= { innovxFeatureEntry 1 }

innovxFeatureName  OBJECT-TYPE
    SYNTAX  DisplayString
    ACCESS  read-only
    STATUS  mandatory
    DESCRIPTION
    	"The Name of the feature that is available in 
        this software."

    ::= { innovxFeatureEntry 2 }

innovxFeatureEnable  OBJECT-TYPE
    SYNTAX INTEGER
    {
        disabled (1),
        enabled  (2)
    }
    ACCESS  read-only
    STATUS  mandatory
    DESCRIPTION
	"The state of the feature, whether it has been Key
        enabled or not.
    WEBFLAG
    Disabled
    Enabled
    WEBEND
    "
    ::= { innovxFeatureEntry 3 }

innovxFeatureStatus OBJECT-TYPE
    SYNTAX INTEGER
    {
        off (1),
        on  (2)
    }
    ACCESS read-only
    STATUS mandatory
    DESCRIPTION
	"The operational status of the feature, on -- selected,
        off -- not selected.
    WEBFLAG
    Off
    On
    WEBEND
    "
    ::= { innovxFeatureEntry 4 }


 
-- ****************************************************************************
--                       mib definitions end
-- ****************************************************************************

END
