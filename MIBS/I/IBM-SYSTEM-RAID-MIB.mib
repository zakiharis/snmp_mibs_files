IBM-SYSTEM-RAID-MIB DEFINITIONS ::= BEGIN

IMPORTS
   OBJECT-TYPE
        FROM RFC-1212

   TRAP-TYPE
        FROM RFC-1215

    DateAndTime, TruthValue
            FROM SNMPv2-TC
    SnmpAdminString
            FROM SNMP-FRAMEWORK-MIB

   ibmSystemRaid,
   Boolean, Uint8, Sint8, Uint16, Sint16, Uint32,
   Sint32, Uint64, Sint64, Real32, Real64, String, Datetime
      FROM IBM-SYSTEM-MIB;

ibmSystemRaidTrap       OBJECT IDENTIFIER ::= { ibmSystemRaid 1 }
ibmSystemRaidTrapInfo   OBJECT IDENTIFIER ::= { ibmSystemRaid 5 }

--
-- IBMPSG_RAIDController
--
ibmSystemRaidControllerTable OBJECT-TYPE
   SYNTAX         SEQUENCE OF IbmSystemRaidControllerEntry
   ACCESS         not-accessible
   STATUS         mandatory
   DESCRIPTION    "The IBMPSG_RAIDController class represents a RAID Controller"
   REFERENCE      "IBMPSG_RAIDController"
::= { ibmSystemRaid 2 }

ibmSystemRaidControllerEntry OBJECT-TYPE
   SYNTAX         IbmSystemRaidControllerEntry
   ACCESS         not-accessible
   STATUS         mandatory
   DESCRIPTION    "This class defines an entry for each IBMPSG_RAIDController
                    instance. Each instance of the IBMPSG_RAIDController class 
                    contains status and descriptive information for each disk 
                    recognized by the Director SMART provider."
   INDEX          { ibmSystemRaidControllerKeyIndex }
::= { ibmSystemRaidControllerTable 1 }

IbmSystemRaidControllerEntry ::= SEQUENCE
{
   ibmSystemRaidControllerKeyIndex String,     
   ibmSystemRaidControllerControllerID String,
   ibmSystemRaidControllerModel String,
   ibmSystemRaidControllerBIOSVersion String,
   ibmSystemRaidControllerFirmwareVersion String,
   ibmSystemRaidControllerDriverVersion String,
   ibmSystemRaidControllerManufacturer String,
   ibmSystemRaidControllerSlot Uint16,
   ibmSystemRaidControllerFRU String,
   ibmSystemRaidControllerSerialNumber String,
   ibmSystemRaidControllerInitiatorIDs String,
   ibmSystemRaidControllerStatus String
}

ibmSystemRaidControllerKeyIndex OBJECT-TYPE
   SYNTAX         String
   ACCESS         read-only
   STATUS         mandatory
   DESCRIPTION    "The RAID controller table index number (controller1, controller2, etc.)"
   REFERENCE      "IBMPSG_RAIDController.KeyIndex"
::= { ibmSystemRaidControllerEntry 1 }

ibmSystemRaidControllerControllerID OBJECT-TYPE
   SYNTAX         String
   ACCESS         read-only
   STATUS         mandatory
   DESCRIPTION    "The DeviceID that identifies the disk"
   REFERENCE      "IBMPSG_RAIDController.ControllerID"
::= { ibmSystemRaidControllerEntry 2 }

ibmSystemRaidControllerModel OBJECT-TYPE
   SYNTAX         String
   ACCESS         read-only
   STATUS         mandatory
   DESCRIPTION    "The model of the controller"
   REFERENCE      "IBMPSG_RAIDController.Model"
::= { ibmSystemRaidControllerEntry 3 }

ibmSystemRaidControllerBIOSVersion OBJECT-TYPE
   SYNTAX         String
   ACCESS         read-only
   STATUS         mandatory
   DESCRIPTION    "The version of the controllers BIOS"
   REFERENCE      "IBMPSG_RAIDController.BIOSVersion"
::= { ibmSystemRaidControllerEntry 4 }

ibmSystemRaidControllerFirmwareVersion OBJECT-TYPE
   SYNTAX         String
   ACCESS         read-only
   STATUS         mandatory
   DESCRIPTION    "The version of the controllers firmwar"
   REFERENCE      "IBMPSG_RAIDController.FirmwareVersion"
::= { ibmSystemRaidControllerEntry 5 }

ibmSystemRaidControllerDriverVersion OBJECT-TYPE
   SYNTAX         String
   ACCESS         read-only
   STATUS         mandatory
   DESCRIPTION    "The version of the controllers device driver"
   REFERENCE      "IBMPSG_RAIDController.DriverVersion"
::= { ibmSystemRaidControllerEntry 6 }

ibmSystemRaidControllerManufacturer OBJECT-TYPE
   SYNTAX         String
   ACCESS         read-only
   STATUS         mandatory
   DESCRIPTION    "the manufacturer of the controller"
   REFERENCE      "IBMPSG_RAIDController.Manufacturer"
::= { ibmSystemRaidControllerEntry 7 }

ibmSystemRaidControllerSlot OBJECT-TYPE
   SYNTAX         Uint16
   ACCESS         read-only
   STATUS         mandatory
   DESCRIPTION    "The slot number the controller resides in"
   REFERENCE      "IBMPSG_RAIDController.Slot"
::= { ibmSystemRaidControllerEntry 8 }

ibmSystemRaidControllerFRU OBJECT-TYPE
   SYNTAX         String
   ACCESS         read-only
   STATUS         mandatory
   DESCRIPTION    "The FRU number of the controller"
   REFERENCE      "IBMPSG_RAIDController.FRU"
::= { ibmSystemRaidControllerEntry 9 }

ibmSystemRaidControllerSerialNumber OBJECT-TYPE
   SYNTAX         String
   ACCESS         read-only
   STATUS         mandatory
   DESCRIPTION    "The controllers serial number"
   REFERENCE      "IBMPSG_RAIDController.SerialNumber"
::= { ibmSystemRaidControllerEntry 10 }

ibmSystemRaidControllerInitiatorIDs OBJECT-TYPE
   SYNTAX         String
   ACCESS         read-only
   STATUS         mandatory
   DESCRIPTION    "Specifies the controllers initiator IDs using a comma as the delimiter"
   REFERENCE      "IBMPSG_RAIDController.InitiatorIDs"
::= { ibmSystemRaidControllerEntry 11 }

ibmSystemRaidControllerStatus OBJECT-TYPE
   SYNTAX         String
   ACCESS         read-only
   STATUS         mandatory
   DESCRIPTION    "The current status of the controller"
   REFERENCE      "IBMPSG_RAIDController.Status"
::= { ibmSystemRaidControllerEntry 12 }

--
-- IBMPSG_RAIDDiskDrive
--
ibmSystemRaidDiskDriveTable OBJECT-TYPE
   SYNTAX         SEQUENCE OF IbmSystemRaidDiskDriveEntry
   ACCESS         not-accessible
   STATUS         mandatory
   DESCRIPTION    "The IBMPSG_RAIDDiskDrive class represents a RAID physical disk"
   REFERENCE      "IBMPSG_RAIDDiskDrive"
::= { ibmSystemRaid 3 }

ibmSystemRaidDiskDriveEntry OBJECT-TYPE
   SYNTAX         IbmSystemRaidDiskDriveEntry
   ACCESS         not-accessible
   STATUS         mandatory
   DESCRIPTION    "This class defines an entry for each IBMPSG_RAIDDiskDrive
                    instance. Each instance of the IBMPSG_RAIDDiskDrive class 
                    contains status and descriptive information for each disk 
                    attached to the RAID controller."
   INDEX          { ibmSystemRaidDiskDriveKeyIndex }
::= { ibmSystemRaidDiskDriveTable 1 }

IbmSystemRaidDiskDriveEntry ::= SEQUENCE
{
   ibmSystemRaidDiskDriveKeyIndex String,
   ibmSystemRaidDiskDriveDeviceID String,
   ibmSystemRaidDiskDriveDiskDriveID String,
   ibmSystemRaidDiskDriveControllerID String,
   ibmSystemRaidDiskDriveChannelID String,
   ibmSystemRaidDiskDriveFirmware String,
   ibmSystemRaidDiskDriveState Uint16,
   ibmSystemRaidDiskDriveStatus String
}

ibmSystemRaidDiskDriveKeyIndex OBJECT-TYPE
   SYNTAX         String
   ACCESS         read-only
   STATUS         mandatory
   DESCRIPTION    "The Physical Disk Drive table index number (Disk Drive 0, Disk Drive 1, etc.)"
   REFERENCE      "IBMPSG_RAIDDiskDrive.KeyIndex"
::= { ibmSystemRaidDiskDriveEntry 1 }

ibmSystemRaidDiskDriveDeviceID OBJECT-TYPE
   SYNTAX         String
   ACCESS         read-only
   STATUS         mandatory
   DESCRIPTION    "The device ID of the drive"
   REFERENCE      "IBMPSG_RAIDDiskDrive.DeviceID"
::= { ibmSystemRaidDiskDriveEntry 2 }

ibmSystemRaidDiskDriveDiskDriveID OBJECT-TYPE
   SYNTAX         String
   ACCESS         read-only
   STATUS         mandatory
   DESCRIPTION    "The target ID of the disk drive"
   REFERENCE      "IBMPSG_RAIDDiskDrive.DiskDriveID"
::= { ibmSystemRaidDiskDriveEntry 3 }

ibmSystemRaidDiskDriveControllerID OBJECT-TYPE
   SYNTAX         String
   ACCESS         read-only
   STATUS         mandatory
   DESCRIPTION    "The ID of the controller it is attached to"
   REFERENCE      "IBMPSG_RAIDDiskDrive.ControllerID"
::= { ibmSystemRaidDiskDriveEntry 4 }

ibmSystemRaidDiskDriveChannelID OBJECT-TYPE
   SYNTAX         String
   ACCESS         read-only
   STATUS         mandatory
   DESCRIPTION    "The channel on the controller the drive is attached to"
   REFERENCE      "IBMPSG_RAIDDiskDrive.ChannelID"
::= { ibmSystemRaidDiskDriveEntry 5 }

ibmSystemRaidDiskDriveFirmware OBJECT-TYPE
   SYNTAX         String
   ACCESS         read-only
   STATUS         mandatory
   DESCRIPTION    "The firmware revision of the drive"
   REFERENCE      "IBMPSG_RAIDDiskDrive.Firmware"
::= { ibmSystemRaidDiskDriveEntry 6 }

ibmSystemRaidDiskDriveState OBJECT-TYPE
   SYNTAX         Uint16
   ACCESS         read-only
   STATUS         mandatory
   DESCRIPTION    "The current state of the physical drive.
   					0=Empty, 1=Standby, 4=Defunct Hot Spare, 5=Standby 
   					Hot Spare, 8=Defunct Disk Drive, 129=Ready, 
   					133=Hot Spare, 137=Online, 139=Rebuild, 254=Reserved"
   REFERENCE      "IBMPSG_RAIDDiskDrive.State"
::= { ibmSystemRaidDiskDriveEntry 7 }

ibmSystemRaidDiskDriveStatus OBJECT-TYPE
   SYNTAX         String
   ACCESS         read-only
   STATUS         mandatory
   DESCRIPTION    "The status of the drive"
   REFERENCE      "IBMPSG_RAIDDiskDrive.Status"
::= { ibmSystemRaidDiskDriveEntry 8 }

--
-- IBMPSG_RAIDLogicalDrive
--
ibmSystemRaidLogicalDriveTable OBJECT-TYPE
   SYNTAX         SEQUENCE OF IbmSystemRaidLogicalDriveEntry
   ACCESS         not-accessible
   STATUS         mandatory
   DESCRIPTION    "The IBMPSG_RAIDLogicalDrive class represents a RAID Logical disk (Logical Drive 0, Logical Drive 1, etc.)"
   REFERENCE      "IBMPSG_RAIDLogicalDrive"
::= { ibmSystemRaid 4 }

ibmSystemRaidLogicalDriveEntry OBJECT-TYPE
   SYNTAX         IbmSystemRaidLogicalDriveEntry
   ACCESS         not-accessible
   STATUS         mandatory
   DESCRIPTION    "This class defines an entry for each IBMPSG_RAIDLogicalDrive
                    instance. Each instance of the IBMPSG_RAIDLogicalDrive class 
                    contains status and descriptive information for each RAID 
                    Logical disk."
   INDEX          { ibmSystemRaidLogicalDriveKeyIndex }
::= { ibmSystemRaidLogicalDriveTable 1 }

IbmSystemRaidLogicalDriveEntry ::= SEQUENCE
{
   ibmSystemRaidLogicalDriveKeyIndex String,
   ibmSystemRaidLogicalDriveLogicalDriveID String,
   ibmSystemRaidLogicalDriveControllerID String,
   ibmSystemRaidLogicalDriveArrayID String,
   ibmSystemRaidLogicalDriveRAIDLevel String,
   ibmSystemRaidLogicalDriveDataSpace Uint64,
   ibmSystemRaidLogicalDriveParitySpace Uint64,
   ibmSystemRaidLogicalDriveIsBlocked Boolean,
   ibmSystemRaidLogicalDriveState Uint16,
   ibmSystemRaidLogicalDriveStatus String
}

ibmSystemRaidLogicalDriveKeyIndex OBJECT-TYPE
   SYNTAX         String
   ACCESS         read-only
   STATUS         mandatory
   DESCRIPTION    "The Logical Disk Drive table index number (Logical Drive 0, Logical Drive 1, etc.)"
   REFERENCE      "IBMPSG_RAIDLogicalDrive.KeyIndex"
::= { ibmSystemRaidLogicalDriveEntry 1 }

ibmSystemRaidLogicalDriveLogicalDriveID OBJECT-TYPE
   SYNTAX         String
   ACCESS         read-only
   STATUS         mandatory
   DESCRIPTION    "The ID of the logical drive"
   REFERENCE      "IBMPSG_RAIDLogicalDrive.LogicalDriveID"
::= { ibmSystemRaidLogicalDriveEntry 2 }

ibmSystemRaidLogicalDriveControllerID OBJECT-TYPE
   SYNTAX         String
   ACCESS         read-only
   STATUS         mandatory
   DESCRIPTION    "The ID of the controller the logical drive belongs to"
   REFERENCE      "IBMPSG_RAIDLogicalDrive.ControllerID"
::= { ibmSystemRaidLogicalDriveEntry 3 }

ibmSystemRaidLogicalDriveArrayID OBJECT-TYPE
   SYNTAX         String
   ACCESS         read-only
   STATUS         mandatory
   DESCRIPTION    "The ID of the array that the logical drive belongs to"
   REFERENCE      "IBMPSG_RAIDLogicalDrive.ArrayID"
::= { ibmSystemRaidLogicalDriveEntry 4 }

ibmSystemRaidLogicalDriveRAIDLevel OBJECT-TYPE
   SYNTAX         String
   ACCESS         read-only
   STATUS         mandatory
   DESCRIPTION    "The RAID level of the logical drive (RAID 1, RAID 5, etc.)"
   REFERENCE      "IBMPSG_RAIDLogicalDrive.RAIDLevel"
::= { ibmSystemRaidLogicalDriveEntry 5 }

ibmSystemRaidLogicalDriveDataSpace OBJECT-TYPE
   SYNTAX         Uint64
   ACCESS         read-only
   STATUS         mandatory
   DESCRIPTION    "Size of the logical drive in megabytes"
   REFERENCE      "IBMPSG_RAIDLogicalDrive.DataSpace"
::= { ibmSystemRaidLogicalDriveEntry 6 }

ibmSystemRaidLogicalDriveParitySpace OBJECT-TYPE
   SYNTAX         Uint64
   ACCESS         read-only
   STATUS         mandatory
   DESCRIPTION    "Parity space of the logical drive in megabytes"
   REFERENCE      "IBMPSG_RAIDLogicalDrive.ParitySpace"
::= { ibmSystemRaidLogicalDriveEntry 7 }

ibmSystemRaidLogicalDriveIsBlocked OBJECT-TYPE
   SYNTAX         Boolean
   ACCESS         read-only
   STATUS         mandatory
   DESCRIPTION    "The logical drive is in a blocked state"
   REFERENCE      "IBMPSG_RAIDLogicalDrive.Blocked"
::= { ibmSystemRaidLogicalDriveEntry 8 }

ibmSystemRaidLogicalDriveState OBJECT-TYPE
   SYNTAX         Uint16
   ACCESS         read-only
   STATUS         mandatory
   DESCRIPTION    "The current state of the logical drive.
   					0=Free, 2=Offline, 3=Okay, 4=Critical, 
   					5=Logical Drive Migration, 6=System, 
   					20=Critical Logical Drive Migration, 
   					36=Critical System"
   REFERENCE      "IBMPSG_RAIDLogicalDrive.State"
::= { ibmSystemRaidLogicalDriveEntry 9 }

ibmSystemRaidLogicalDriveStatus OBJECT-TYPE
   SYNTAX         String
   ACCESS         read-only
   STATUS         mandatory
   DESCRIPTION    "The status of the logical drive"
   REFERENCE      "IBMPSG_RAIDLogicalDrive.Status"
::= { ibmSystemRaidLogicalDriveEntry 10 }

--
-- Trap variables
--
ibmSystemRaidTrapProviderName OBJECT-TYPE
    SYNTAX String
    ACCESS not-accessible
    STATUS mandatory
    DESCRIPTION
        "The CIM Provider Name"
    ::= { ibmSystemRaidTrapInfo 1 }

ibmSystemRaidTrapEventID OBJECT-TYPE
    SYNTAX String
    ACCESS not-accessible
    STATUS mandatory
    DESCRIPTION
        "Event ID"
    ::= { ibmSystemRaidTrapInfo 2 }

ibmSystemRaidTrapPerceivedSeverity OBJECT-TYPE
    SYNTAX INTEGER
    ACCESS not-accessible
    STATUS mandatory
    DESCRIPTION
        "Severity of the event
         0=Normal / OK 
         1=Warning 
         2=Critical "
    ::= { ibmSystemRaidTrapInfo 3 }

ibmSystemRaidDescription OBJECT-TYPE
    SYNTAX String
    ACCESS not-accessible
    STATUS mandatory
    DESCRIPTION
        "The event message"
    ::= { ibmSystemRaidTrapInfo 4 }

ibmSystemRaidTrapEventTime OBJECT-TYPE
    SYNTAX String
    ACCESS not-accessible
    STATUS mandatory
    DESCRIPTION
        "Time that the event occured"
    ::= { ibmSystemRaidTrapInfo 5 }

--
-- Traps
--

ibmSystemRaidNoControllers TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: No controllers were found in this system."
    ::= 201

ibmSystemRaidControllerFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Commands not responding on Controller %d."
    ::= 202

ibmSystemRaidDeadBattery TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: The battery-backup cache device on Controller %d needs a new battery."
    ::= 203

ibmSystemRaidDeadBatteryCache TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: The battery-backup cache device on Controller %d is defective %d"
    ::= 204

ibmSystemRaidPollingFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Background polling commands not responding on Controller %d %d"
    ::= 205

ibmSystemRaidConfigFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Cannot read controller configuration."
    ::= 206

ibmSystemRaidControllerAdded TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Controller %d has been added to the system."
    ::= 207

ibmSystemRaidControllerReplaced TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Controller %d has been replaced in the system."
    ::= 208

ibmSystemRaidControllerFailover TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Controller %d failover detected. Passive controller is now active."
    ::= 209

ibmSystemRaidControllerVersionMismatch TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: Controller %d version mismatch detected. The BIOS, Firmware, and Driver are not a matched set and are not compatible."
    ::= 210

ibmSystemRaidControllerBatteryOvertemp TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: Controller %d battery has exceeded normal operating temperature."
    ::= 211

ibmSystemRAIDControllerBadStripes TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: One or more logical drives contain a bad stripe: Controller %d."
    ::= 215

ibmSystemRaidControllerBatteryTempNormal TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Controller %d battery operating temperature is normal."
    ::= 216

ibmSystemRaidControllerStatusChange TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The status of the controller changed"
    ::= 217

ibmSystemRaidLogicalDriveCritical TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: Logical Drive %d is Critical on Controller %d."
    ::= 301

ibmSystemRaidLogicalDriveBlocked TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Logical Drive %d is Blocked on Controller %d."
    ::= 302

ibmSystemRaidLogicalDriveOffLine TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Logical Drive %d is Offline on Controller %d."
    ::= 303

ibmSystemRaidRebuildDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Rebuilding Logical Drive %d on Controller %d."
    ::= 304

ibmSystemRaidRebuildComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Rebuild complete on Logical Drive %d of Controller %d."
    ::= 305

ibmSystemRaidRebuildFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Rebuild failed on Logical Drive %d of Controller %d %d."
    ::= 306

ibmSystemRaidSyncDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Synchronizing Logical Drive %d on Controller %d."
    ::= 307

ibmSystemRaidSyncComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Synchronization complete on Logical Drive %d of Controller %d."
    ::= 308

ibmSystemRaidSyncFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Synchronization failed on Logical Drive %d of Controller %d %d."
    ::= 309

ibmSystemRaidMigrationDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Migrating Logical Drive %d on Controller %d."
    ::= 310

ibmSystemRaidMigrationComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Migration complete on Logical Drive %d of Controller %d."
    ::= 311

ibmSystemRaidMigrationFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Migration failed on Logical Drive %d of Controller %d %d."
    ::= 312

ibmSystemRaidCompressionDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Compressing Logical Drive %d on Controller %d."
    ::= 313

ibmSystemRaidCompressionComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Compression complete on Logical Drive %d of Controller %d."
    ::= 314

ibmSystemRaidcompressionFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Compression failed on Logical Drive %d of Controller %d %d."
    ::= 315

ibmSystemRaidDecompressionDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Decompressing Logical Drive %d on Controller %d."
    ::= 316

ibmSystemRaidDecompressionComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Decompression complete on Logical Drive %d of Controller %d."
    ::= 317

ibmSystemRaidDecompressionFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Decompression failed on Logical Drive %d of Controller %d %d."
    ::= 318

ibmSystemRaidFlashCopyDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: FlashCopying Logical Drive %d on Controller %d."
    ::= 319

ibmSystemRaidFlashCopyComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: FlashCopy complete on Logical Drive %d of Controller %d."
    ::= 320

ibmSystemRaidFlashCopyFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: FlashCopy failed on Logical Drive %d of Controller %d %d."
    ::= 321

ibmSystemRaidArrayRebuildDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Rebuilding Array %d on Controller %d."
    ::= 322

ibmSystemRaidArrayRebuildComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Rebuild complete on Array %d of Controller %d."
    ::= 323

ibmSystemRaidArrayRebuildFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Rebuild failed on Array %d of Controller %d %d."
    ::= 324

ibmSystemRaidArraySyncDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Synchronizing Array %d on Controller %d."
    ::= 325

ibmSystemRaidArraySyncComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Synchronization complete on Array %d of Controller %d."
    ::= 326

ibmSystemRaidArraySyncFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Synchronization failed on Array %d of Controller %d %d."
    ::= 327

ibmSystemRaidArrayFlashCopyDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: FlashCopying Array %d on Controller %d."
    ::= 328

ibmSystemRaidArrayFlashCopyComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: FlashCopy complete on Array %d of Controller %d."
    ::= 329

ibmSystemRaidArrayFlashCopyFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: FlashCopy failed on Array %d of Controller %d %d."
    ::= 330

ibmSystemRaidLogicalDriveUnblocked TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Logical Drive %d is unblocked on Controller %d."
    ::= 331

ibmSystemRaidCompactionDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Compacting Logical Drive %d on Controller %d."
    ::= 332

ibmSystemRaidCompactionComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Compaction complete on Logical Drive %d of Controller %d."
    ::= 333

ibmSystemRaidCompactionFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Compaction failed on Logical Drive %d of Controller %d %d."
    ::= 334

ibmSystemRaidExpansionDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Expanding Logical Drive %d on Controller %d."
    ::= 335

ibmSystemRaidExpansionComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Expansion complete on Logical Drive %d of Controller %d."
    ::= 336

ibmSystemRaidExpansionFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Expansion failed on Logical Drive %d of Controller %d %d."
    ::= 337
    
ibmSystemRaidLogicalDriveCriticalPeriodic TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: Periodic scan found 1 or more critical logical drives on Controller %d."
    ::= 338

ibmSystemRaidCopyBackDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Copy back in progress on Logical Drive %d on Controller %d."
    ::= 339

ibmSystemRaidCopyBackComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Copy back complete on Logical Drive %d of Controller %d."
    ::= 340

ibmSystemRaidCopyBackFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Copy back failed on Logical Drive %d of Controller %d %d."
    ::= 341

ibmSystemRaidInitDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Initialization in progress on Logical Drive %d on Controller %d."
    ::= 342

ibmSystemRaidInitComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Initialization complete on Logical Drive %d of Controller %d."
    ::= 343

ibmSystemRaidInitFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Initialization failed on Logical Drive %d of Controller %d %d."
    ::= 344

ibmSystemRAIDLogicalDriveOK TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Logical Drive %d of Controller %d is normal."
    ::= 345

ibmSystemRAIDLogicalDriveAdded TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Added Logical Drive %d of Controller %d."
    ::= 346

ibmSystemRAIDLogicalDriveRemoved TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Removed Logical Drive %d of Controller %d."
    ::= 347

ibmSystemRaidArrayFlashCopyStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The flashcopy operation has stopped"
    ::= 348

ibmSystemRaidArrayRebuildStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The array rebuild operation has stopped"
    ::= 349

ibmSystemRaidArrayStatusChange TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The array status has changed"
    ::= 350

ibmSystemRaidArraySyncStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The array synchronization operation has stopped"
    ::= 351

ibmSystemRaidCompactionStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The compaction operation has stopped"
    ::= 352

ibmSystemRaidCompressionStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The compression operation has stopped"
    ::= 353

ibmSystemRaidCopybackStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The copyback operation has stopped"
    ::= 354

ibmSystemRaidDecompressionStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The decompression operation has stopped"
    ::= 355

ibmSystemRaidExpansionStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The expansion operation has stopped"
    ::= 356

ibmSystemRaidFlashCopyStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The flashcopy operation has stopped"
    ::= 357

ibmSystemRaidInitStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The initialiation operation has stopped"
    ::= 358

ibmSystemRaidLogicalDriveStatusChange TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The status of the locaical drive has changed"
    ::= 359

ibmSystemRaidMigrationStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The migration operation has stopped"
    ::= 360

ibmSystemRaidRebuildStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The rebuild operation has stopped"
    ::= 361

ibmSystemRaidSyncStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The synchroniation operation has stopped"
    ::= 362

ibmSystemRaidDefunctDrive TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Defunct drive on Controller %d, Channel %d, Device ID %d."
    ::= 401

ibmSystemRaidPfaDrive TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: PFA drive on Controller %d, Channel %d, Device ID %d."
    ::= 402

ibmSystemRaidDefunctReplaced TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: A drive is set to Hot-Spare on Controller %d, Channel %d, Device ID %d."
    ::= 403
    
ibmSystemRaidDefunctDriveFru TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Defunct drive (FRU Part # %d} on controller %d, channel %d, Device ID %d."
    ::= 404

ibmSystemRaidPfaDriveFru TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: PFA drive (FRU Part # %d) on Controller %d, Channel %d, Device ID %d."
    ::= 405
    
ibmSystemRaidUnsupportedDrive TRAP-TYPE
 -- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    optional, disable by using -DshowCounterfeitDrives=false on command line
    DESCRIPTION
        "Warning: Unsupported physical drive found on Controller %d, Channel %d, Device ID %d."
    ::= 406

ibmSystemRaidDriveAdded TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Drive added on Controller %d, Channel %d, Device ID %d."
    ::= 407

ibmSystemRaidDriveRemoved TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Drive removed on Controller %d, Channel %d, Device ID %d."
    ::= 408

ibmSystemRaidDriveClearDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Clear in progress on Controller %d, Channel %d, Device ID %d."
    ::= 409

ibmSystemRaidDriveClearComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Clear complete on Controller %d, Channel %d, Device ID %d."
    ::= 410

ibmSystemRaidDriveClearFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Clear failed on Controller %d, Channel %d, Device ID %d."
    ::= 411

ibmSystemRaidDriveSyncDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Synchronization in progress on Controller %d, Channel %d, Device ID %d."
    ::= 412

ibmSystemRaidDriveSyncComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Synchronization complete on Controller %d, Channel %d, Device ID %d."
    ::= 413

ibmSystemRaidDriveSyncFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Synchronization failed on Controller %d, Channel %d, Device ID %d."
    ::= 414

ibmSystemRaidDriveVerifyDetected TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Verify in progress on Controller %d, Channel %d, Device ID %d."
    ::= 415

ibmSystemRaidDriveVerifyComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Verify complete on Controller %d, Channel %d, Device ID %d."
    ::= 416

ibmSystemRaidDriveVerifyFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Verify failed on Controller %d, Channel %d, Device ID %d."
    ::= 417

ibmSystemRaidDriveClearStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The drive clear operation has stopped"
    ::= 418

ibmSystemRaidDriveSecureEraseStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The secure erase operation has stopped"
    ::= 419

ibmSystemRaidDriveStatusChange TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The drive status has changed"
    ::= 420

ibmSystemRaidDriveSyncStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The sychronization operation has stopped"
    ::= 421

ibmSystemRaidDriveVerifyStopped TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "The verify operation has stopped"
    ::= 422

ibmSystemRaidSpareCreated TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "ibmSystemRaidSpareCreated"
    ::= 423

ibmSystemRaidSpareDeleted TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "ibmSystemRaidSpareDeleted"
    ::= 424

ibmSystemRaidEnclosureOK TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Enclosure device responding on Controller %d, Channel %d."
    ::= 501

ibmSystemRaidEnclosureFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Enclosure device not responding on Controller %d, Channel %d."
    ::= 502

ibmSystemRaidFanOk TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Enclosure fan %d on Controller %d, Channel %d is now operational."
    ::= 503

ibmSystemRaidFanFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Enclosure fan %d on Controller %d, Channel %d is malfunctioning."
    ::= 504

ibmSystemRaidFanInstalled TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Enclosure fan %d on Controller %d, Channel %d has been installed."
    ::= 505

ibmSystemRaidFanRemoved TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: Enclosure fan %d on Controller %d, Channel %d has been removed."
    ::= 506

ibmSystemRaidTempOk TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Enclosure temperature is in normal range on Controller %d, Channel %d."
    ::= 507

ibmSystemRaidTempFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Enclosure temperature is out of normal range on Controller %d, Channel %d."
    ::= 508

ibmSystemRaidPowerSupplyOk TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Enclosure power supply %d on Controller %d, Channel %d is now operational."
    ::= 509

ibmSystemRaidPowerSupplyFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Error: Enclosure power supply %d on Controller %d, Channel %d is malfunctioning."
    ::= 510

ibmSystemRaidPowerSupplyInstalled TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: Enclosure power supply %d on Controller %d, Channel %d has been installed."
    ::= 511

ibmSystemRaidPowerSupplyRemoved TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Warning: Enclosure power supply %d on Controller %d, Channel %d has been removed."
    ::= 512

ibmSystemRaidTestTrap TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "Informational: This is a test trap."
    ::= 601

-- LSI Traps

ibmSystemRaidLsiPDFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A physical drive has failed in a RAID configuration"
    ::= 1000

ibmSystemRaidLsiPDPartOfLDFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A physical drive has failed in a logical drive"
    ::= 1003

ibmSystemRaidLsiPDPartOfLDAdd TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A drive has been added to a RAID configuration"
    ::= 1004

ibmSystemRaidLsiHSPartOfLD TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "ibmSystemRaidLsiHSPartOfLD"
    ::= 1005

ibmSystemRaidLsiHSFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A hot spare drive has failed in a RAID configuration"
    ::= 1007

ibmSystemRaidLsiPDHS TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A physical drive has been made a hot spare in the RAID configuration"
    ::= 1008

ibmSystemRaidLsiLDOffline TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A logical drive is in the offline state"
    ::= 1009

ibmSystemRaidLsiLDDegraded TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A logical drive has been degraded in a RAID configuration"
    ::= 1011

ibmSystemRaidLsiLDOptimal TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A logical drive is functioning correctly"
    ::= 1012

ibmSystemRaidLsiSMARTError TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A PFA has been detected on a drive in the RAID configuration"
    ::= 1013

ibmSystemRaidLsiRbldStart TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A RAID rebuild operation is in progress on an array in the RAID configuration"
    ::= 1015

ibmSystemRaidLsiRbldComplete TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A RAID rebuild operation has completed on an array in the RAID configuration"
    ::= 1016

ibmSystemRaidLsiRbldFail TRAP-TYPE
-- Reverse mappable trap
    ENTERPRISE ibmSystemRaidTrap
    VARIABLES {
        ibmSystemRaidTrapProviderName,   
        ibmSystemRaidTrapEventID, ibmSystemRaidTrapPerceivedSeverity, 
        ibmSystemRaidDescription, ibmSystemRaidTrapEventTime          }
--  Status
--    mandatory
    DESCRIPTION
        "A RAID rebuild operation has failed on an array in the RAID configuration"
    ::= 1017


END
