IBM-SYSTEM-PROCESSOR-MIB DEFINITIONS ::= BEGIN

IMPORTS
   OBJECT-TYPE
        FROM RFC-1212

   TRAP-TYPE
        FROM RFC-1215

   ibmSystemProcessor,
   Boolean, Uint8, Sint8, Uint16, Sint16, Uint32,
   Sint32, Uint64, Sint64, Real32, Real64, String, Datetime
      FROM IBM-SYSTEM-MIB;
      
ibmSystemProcessorTable OBJECT-TYPE
   SYNTAX         SEQUENCE OF IbmSystemProcessorEntry
   ACCESS         not-accessible
   STATUS         mandatory
   DESCRIPTION    "The IBMPSG_Processor class represents an IBM managed Memory Array"
   REFERENCE      "IBMPSG_Processor"
::= { ibmSystemProcessor 1 }

ibmSystemProcessorEntry OBJECT-TYPE
   SYNTAX         IbmSystemProcessorEntry
   ACCESS         not-accessible
   STATUS         mandatory
   DESCRIPTION    "This class defines an entry for each IBMPSG_Processor
                    instance. Each instance of the IBMPSG_Processor class 
                    contains status and descriptive information for each memory 
                    bank recognized by the operating system."
   INDEX          { ibmSystemProcessorKeyIndex }
::= { ibmSystemProcessorTable 1 }

IbmSystemProcessorEntry ::= SEQUENCE
{
   ibmSystemProcessorKeyIndex String,   
   ibmSystemProcessorManufacturer String,
   ibmSystemProcessorFamily Uint16,
   ibmSystemProcessorStepping String,
   ibmSystemProcessorDescription String,
   ibmSystemProcessorCurrentClockSpeed Uint32,
   ibmSystemProcessorMaxClockSpeed Uint32,
   ibmSystemProcessorAddressWidth Uint16,
   ibmSystemProcessorDataWidth Uint16,
   ibmSystemProcessorPowerManagementSupported Boolean,
   ibmSystemProcessorUpgradeMethod Uint16,
   ibmSystemProcessorDeviceID String,
   ibmSystemProcessorUniqueID String,
   ibmSystemProcessorCPUStatus Uint16,
   ibmSystemProcessorStatus String
}

ibmSystemProcessorKeyIndex OBJECT-TYPE
   SYNTAX         String
   ACCESS         read-only
   STATUS         mandatory
   DESCRIPTION    "The processor table index number (CPU1, CPU2, etc.)"
   REFERENCE      "IBMPSG_Processor.KeyIndex"
::= { ibmSystemProcessorEntry 1 }

ibmSystemProcessorManufacturer OBJECT-TYPE
   SYNTAX         String
   ACCESS         read-only
   STATUS         mandatory
   DESCRIPTION    "The manufacturer of the processor"
   REFERENCE      "IBMPSG_Processor.Manufacturer"
::= { ibmSystemProcessorEntry 2 }

ibmSystemProcessorFamily OBJECT-TYPE
   SYNTAX         Uint16
   ACCESS         read-only
   STATUS         mandatory
   DESCRIPTION    "The processor family type.
                   1=Other,2=Unknown,3=8086,4=80286,5=80386,6=80486,7=8087,8=80287,                                                          
					9=80387,10=80487,11=Pentium(R) brand,12=Pentium(R) Pro,
					13=Pentium(R) II,14=Pentium(R) processor with MMX(TM) technology,                   
					15=Celeron(TM),16=Pentium(R) II Xeon(TM),17=Pentium(R) III,
					18=M1 Family,19=M2 Family,24=K5 Family,25=K6 Family,26=K6-2,27=K6-3,                                                           
					28=AMD Athlon(TM) Processor Family,29=AMD(R) Duron(TM) Processor,                                     
					30=AMD29000 Family,31=K6-2+,32=Power PC Family,33=Power PC 601,                                                   
					34=Power PC 603,35=Power PC 603+,36=Power PC 604,37=Power PC 620,                                                   
					38=Power PC X704,39=Power PC 750,48=Alpha Family,49=Alpha 21064,                                                    
					50=Alpha 21066,51=Alpha 21164,52=Alpha 21164PC,53=Alpha 21164a,                                                   
					54=Alpha 21264,55=Alpha 21364,64=MIPS Family,65=MIPS R4000,                                                     
					66=MIPS R4200,67=MIPS R4400,68=MIPS R4600,69=MIPS R10000,
					80=SPARC Family,81=SuperSPARC,82=microSPARC II,83=microSPARC IIep,                                                
					84=UltraSPARC,85=UltraSPARC II,86=UltraSPARC IIi,87=UltraSPARC III,                                                 
					88=UltraSPARC IIIi,96=68040,97=68xxx Family,98=68000,99=68010,                                                          
					100=68020,101=68030,112=Hobbit Family,120=Crusoe(TM) TM5000 Family,                                       
					121=Crusoe(TM) TM3000 Family,122=Efficeon(TM) TM8000 Family,
					128=Weitek,130=Itanium(TM) Processor,
					131=AMD Athlon(TM) 64 Processor Family,
					132=AMD Opteron(TM) Processor Family,144=PA-RISC Family,                                                 
					145=PA-RISC 8500,146=PA-RISC 8000,147=PA-RISC 7300LC,148=PA-RISC 7200,                                                   
					149=PA-RISC 7100LC,150=PA-RISC 7100,160=V30 Family,                                                     
					176=Pentium(R) III Xeon(TM),                                        
					177=Pentium(R) III Processor with Intel(R) SpeedStep(TM) Technology,
					178=Pentium(R) 4,179=Intel(R) Xeon(TM),180=AS400 Family,                                                   
					181=Intel(R) Xeon(TM) processor MP,182=AMD Athlon(TM) XP Family,                                       
					183=AMD Athlon(TM) MP Family,184=Intel(R) Itanium(R) 2,                                          
					185=Intel(R) Pentium(R) M processor,190=K7,= ,S/390 and zSeries Family,                                 
					200=ESA/390 G4,201=ESA/390 G5,                                                     
					202=ESA/390 G6,203=z/Architectur base,204=i860,250=i960,251=SH-3,                                                           
					260=SH-4,261=ARM,280=StrongARM,281=6x86,300=MediaGX,301=MII,
					302=WinChip,320=DSP,350=Video Processor"
   REFERENCE      "IBMPSG_Processor.Family"
::= { ibmSystemProcessorEntry 3 }

ibmSystemProcessorStepping OBJECT-TYPE
   SYNTAX         String
   ACCESS         read-only
   STATUS         mandatory
   DESCRIPTION    "Stepping is a free-form string indicating the revision level of the Processor within the Processor Family."
   REFERENCE      "IBMPSG_Processor.Stepping"
::= { ibmSystemProcessorEntry 4 }

ibmSystemProcessorDescription OBJECT-TYPE
   SYNTAX         String
   ACCESS         read-only
   STATUS         mandatory
   DESCRIPTION    "General description of the object"
   REFERENCE      "IBMPSG_Processor.Description"
::= { ibmSystemProcessorEntry 5 }

ibmSystemProcessorCurrentClockSpeed OBJECT-TYPE
   SYNTAX         Uint32
   ACCESS         read-only
   STATUS         mandatory
   DESCRIPTION    "The current speed (in MHz) of this Processor."
   REFERENCE      "IBMPSG_Processor.CurrentClockSpeed"
::= { ibmSystemProcessorEntry 6 }

ibmSystemProcessorMaxClockSpeed OBJECT-TYPE
   SYNTAX         Uint32
   ACCESS         read-only
   STATUS         mandatory
   DESCRIPTION    "The maximum speed (in MHz) of this Processor."
   REFERENCE      "IBMPSG_Processor.MaxClockSpeed"
::= { ibmSystemProcessorEntry 7 }

ibmSystemProcessorAddressWidth OBJECT-TYPE
   SYNTAX         Uint16
   ACCESS         read-only
   STATUS         mandatory
   DESCRIPTION    "Processor address width in bits."
   REFERENCE      "IBMPSG_Processor.AddressWidth"
::= { ibmSystemProcessorEntry 8 }

ibmSystemProcessorDataWidth OBJECT-TYPE
   SYNTAX         Uint16
   ACCESS         read-only
   STATUS         mandatory
   DESCRIPTION    "Processor data width in bits."
   REFERENCE      "IBMPSG_Processor.DataWidth"
::= { ibmSystemProcessorEntry 9 }

ibmSystemProcessorPowerManagementSupported OBJECT-TYPE
   SYNTAX         Boolean
   ACCESS         read-only
   STATUS         mandatory
   DESCRIPTION    "Does the processor have power management capabilities?"
   REFERENCE      "IBMPSG_Processor.PowerManagementSupported"
::= { ibmSystemProcessorEntry 10 }

ibmSystemProcessorUpgradeMethod OBJECT-TYPE
   SYNTAX         Uint16
   ACCESS         read-only
   STATUS         mandatory
   DESCRIPTION    "CPU socket information including data on how this Processor can be upgraded (if upgrades are supported).
                  1=Other,2=Unknown,3=Daughter Board,4=ZIF Socket,            
					5=Replacement/Piggy Back,6=None,7=LIF Socket,8=Slot 1,9=Slot 2,                
					10=370 Pin Socket,11=Slot A,12=Slot M,13=Socket 423,
					14=Socket A (Socket 462),15=Socket 478,16=Socket 754,            
					17=Socket 940,18=Socket 939"
   REFERENCE      "IBMPSG_Processor.UpgradeMethod"
::= { ibmSystemProcessorEntry 11 }

ibmSystemProcessorDeviceID OBJECT-TYPE
   SYNTAX         String
   ACCESS         read-only
   STATUS         mandatory
   DESCRIPTION    "General processor identifier based on the number of processors in the system (CPU1, CPU2, etc.)"
   REFERENCE      "IBMPSG_Processor.DeviceID"
::= { ibmSystemProcessorEntry 12 }

ibmSystemProcessorUniqueID OBJECT-TYPE
   SYNTAX         String
   ACCESS         read-only
   STATUS         mandatory
   DESCRIPTION    "A globally unique identifier for the Processor. This identifier may only be unique within a Processor Family."
   REFERENCE      "IBMPSG_Processor.UniqueID"
::= { ibmSystemProcessorEntry 13 }

ibmSystemProcessorCPUStatus OBJECT-TYPE
   SYNTAX         Uint16
   ACCESS         read-only
   STATUS         mandatory
   DESCRIPTION    "The CPUStatus property indicates the current status of the Processor. For example, it may be disabled by the user via BIOS (value=2), or disabled due to a POST error (value=3). Information in this property can be obtained from SMBIOS, the Type 4 structure, the Status attribute."
   REFERENCE      "IBMPSG_Processor.CPUStatus"
::= { ibmSystemProcessorEntry 14 }

ibmSystemProcessorStatus OBJECT-TYPE
   SYNTAX         String
   ACCESS         read-only
   STATUS         mandatory
   DESCRIPTION    "The current Status of the CPU."
   REFERENCE      "IBMPSG_Processor.Status"
::= { ibmSystemProcessorEntry 15 }


END
