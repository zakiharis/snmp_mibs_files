IBM-SYSTEM-HEALTH-MIB DEFINITIONS ::= BEGIN

IMPORTS
   OBJECT-TYPE
      FROM RFC-1212

   TRAP-TYPE
      FROM RFC-1215

   ibmSystemHealth,
   Boolean, Uint8, Sint8, Uint16, Sint16, Uint32,
   Sint32, Uint64, Sint64, Real32, Real64, String, Datetime
      FROM IBM-SYSTEM-MIB;


ibmSystemComponentHealthTable OBJECT-TYPE
   SYNTAX         SEQUENCE OF IbmSystemComponentHealthEntry
   ACCESS         not-accessible
   STATUS         mandatory
   DESCRIPTION    "The IBMPSG_ComponentHealth class contains instances 
                of managed components and their current states"
   REFERENCE      "IBMPSG_ComponentHealth"
::= { ibmSystemHealth 3 }

ibmSystemComponentHealthEntry OBJECT-TYPE
   SYNTAX         IbmSystemComponentHealthEntry
   ACCESS         not-accessible
   STATUS         mandatory
   DESCRIPTION    "The index used by this table"
   INDEX          { ibmSystemComponentHealthKeyIndex }
::= { ibmSystemComponentHealthTable 1 }

IbmSystemComponentHealthEntry ::= SEQUENCE
{
   ibmSystemComponentHealthKeyIndex String,
   ibmSystemComponentHealthCurrentState Uint16,
   ibmSystemComponentHealthLastState Uint16,
   ibmSystemComponentHealthDateTime Datetime,
   ibmSystemComponentHealthLastUpdate Datetime,
   ibmSystemComponentHealthDescription String,
   ibmSystemComponentHealthEventCategory String,
   ibmSystemComponentHealthResolution String,
   ibmSystemComponentHealthEventID String,
   ibmSystemComponentHealthAlertingManagedElement String,
   ibmSystemComponentHealthStatus String
}

ibmSystemComponentHealthKeyIndex OBJECT-TYPE
   SYNTAX         String
   ACCESS         read-only
   STATUS         mandatory
   DESCRIPTION    "The index used by this table"
   REFERENCE      "IBMPSG_ComponentHealth.KeyIndex"
::= { ibmSystemComponentHealthEntry 1 }

ibmSystemComponentHealthCurrentState OBJECT-TYPE
   SYNTAX         Uint16
   ACCESS         read-only
   STATUS         mandatory
   DESCRIPTION    "Current state of the component. This is an integer
                value and can have the value of 0=NORMAL, 1=WARNING, 2=CRITICAL"
   REFERENCE      "IBMPSG_ComponentHealth.CurrentState"
::= { ibmSystemComponentHealthEntry 2 }

ibmSystemComponentHealthLastState OBJECT-TYPE
   SYNTAX         Uint16
   ACCESS         read-only
   STATUS         mandatory
   DESCRIPTION    "Previous state of the component. This is an integer
                value and can have the value of 0=NORMAL, 1=WARNING, 2=CRITICAL"
   REFERENCE      "IBMPSG_ComponentHealth.LastState"
::= { ibmSystemComponentHealthEntry 3 }

ibmSystemComponentHealthDateTime OBJECT-TYPE
   SYNTAX         Datetime
   ACCESS         read-only
   STATUS         mandatory
   DESCRIPTION    "Date and time at which the entry was read."
   REFERENCE      "IBMPSG_ComponentHealth.DateTime"
::= { ibmSystemComponentHealthEntry 4 }

ibmSystemComponentHealthLastUpdate OBJECT-TYPE
   SYNTAX         Datetime
   ACCESS         read-only
   STATUS         mandatory
   DESCRIPTION    "The date and time when the status was last changed."
   REFERENCE      "IBMPSG_ComponentHealth.LastUpdate"
::= { ibmSystemComponentHealthEntry 5 }

ibmSystemComponentHealthDescription OBJECT-TYPE
   SYNTAX         String
   ACCESS         read-only
   STATUS         mandatory
   DESCRIPTION    "Descriptive name of the component"
   REFERENCE      "IBMPSG_ComponentHealth.Description"
::= { ibmSystemComponentHealthEntry 6 }

ibmSystemComponentHealthEventCategory OBJECT-TYPE
   SYNTAX         String
   ACCESS         read-only
   STATUS         mandatory
   DESCRIPTION    "Category of the last event. Possible values are Other, 
        Communications, Quality of Service, Processing Error, Device,
        Environmental, Model Change, and Security."
   REFERENCE      "IBMPSG_ComponentHealth.EventCategory"
::= { ibmSystemComponentHealthEntry 7 }

ibmSystemComponentHealthResolution OBJECT-TYPE
   SYNTAX         String
   ACCESS         read-only
   STATUS         mandatory
   DESCRIPTION    "Resolution to the error that has occurred."
   REFERENCE      "IBMPSG_ComponentHealth.Resolution"
::= { ibmSystemComponentHealthEntry 8 }

ibmSystemComponentHealthEventID OBJECT-TYPE
   SYNTAX         String
   ACCESS         read-only
   STATUS         mandatory
   DESCRIPTION    "A unique EventID that identifies the item reporting the issue"
   REFERENCE      "IBMPSG_ComponentHealth.EventID"
::= { ibmSystemComponentHealthEntry 9 }

ibmSystemComponentHealthAlertingManagedElement OBJECT-TYPE
   SYNTAX         String
   ACCESS         read-only
   STATUS         mandatory
   DESCRIPTION    "The format of the AlertingManagedElement property is
          interpretable based upon the value of this property. Values
          are defined as:
          0 - Unknown. The format is unknown or not meaningfully 
          interpretable by a CIM client application.
          1 - Other. The format is defined by the value of the
          OtherAlertingElementFormat property.
          2 - CIMObjectPath. The format is a CIMObjectPath, with
          format <NamespacePath>:<ClassName>.<Prop1>=<Value1>,
          <Prop2>=<Value2>, . . . specifying an instance in the
          CIM Schema."
   REFERENCE      "IBMPSG_ComponentHealth.AlertingManagedElement"
::= { ibmSystemComponentHealthEntry 10 }

ibmSystemComponentHealthStatus OBJECT-TYPE
   SYNTAX         String
   ACCESS         read-only
   STATUS         mandatory
   DESCRIPTION    "Current state of the component. This is a string
                value and can have the value of 0=NORMAL, 1=WARNING, 2=CRITICAL"
   REFERENCE      "IBMPSG_ComponentHealth.Status"
::= { ibmSystemComponentHealthEntry 11 }

END
