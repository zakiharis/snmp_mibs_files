IBM-SYSTEM-POWER-MIB DEFINITIONS ::= BEGIN

IMPORTS
   OBJECT-TYPE
        FROM RFC-1212

   TRAP-TYPE
        FROM RFC-1215

   ibmSystemPower,
   Boolean, Uint8, Sint8, Uint16, Sint16, Uint32,
   Sint32, Uint64, Sint64, Real32, Real64, String, Datetime
      FROM IBM-SYSTEM-MIB;
      
ibmSystemPowerSupplyTable OBJECT-TYPE
   SYNTAX         SEQUENCE OF IbmSystemPowerSupplyEntry
   ACCESS         not-accessible
   STATUS         mandatory
   DESCRIPTION    "The IBMPSG_PowerSupply class represents an IBM managed Power Supply"
   REFERENCE      "IBMPSG_PowerSupply"
::= { ibmSystemPower 1 }

ibmSystemPowerSupplyEntry OBJECT-TYPE
   SYNTAX         IbmSystemPowerSupplyEntry
   ACCESS         not-accessible
   STATUS         mandatory
   DESCRIPTION     "This class defines an entry for each IBMPSG_PowerSupply
                    instance. Each instance of the IBMPSG_PowerSupply class 
                    contains status and descriptive information for each power 
                    supply recognized by the operating system."
   INDEX          { ibmSystemPowerSupplyKeyIndex }
::= { ibmSystemPowerSupplyTable 1 }

IbmSystemPowerSupplyEntry ::= SEQUENCE
{
   ibmSystemPowerSupplyKeyIndex String,   
   ibmSystemPowerSupplyDescription String,
   ibmSystemPowerSupplyPNPDeviceID String,
   ibmSystemPowerSupplyStatusInfo Uint16,
   ibmSystemPowerSupplySystemCreationClassName String,
   ibmSystemPowerSupplyEventsEnabled Boolean,
   ibmSystemPowerSupplyPollingInterval Uint64,
   ibmSystemPowerSupplyEventAutoClearEnabled Boolean,
   ibmSystemPowerSupplyStatus String
}

ibmSystemPowerSupplyKeyIndex OBJECT-TYPE
   SYNTAX         String
   ACCESS         read-only
   STATUS         mandatory
   DESCRIPTION    "The index used by this table"
   REFERENCE      "IBMPSG_PowerSupply.KeyIndex"
::= { ibmSystemPowerSupplyEntry 1 }

ibmSystemPowerSupplyDescription OBJECT-TYPE
   SYNTAX         String
   ACCESS         read-only
   STATUS         mandatory
   DESCRIPTION    "A description of the power supply."
   REFERENCE      "IBMPSG_PowerSupply.Description"
::= { ibmSystemPowerSupplyEntry 2 }

ibmSystemPowerSupplyPNPDeviceID OBJECT-TYPE
   SYNTAX         String
   ACCESS         read-only
   STATUS         mandatory
   DESCRIPTION    "The Plug and Play Device ID for this device."
   REFERENCE      "IBMPSG_PowerSupply.PNPDeviceID"
::= { ibmSystemPowerSupplyEntry 3 }

ibmSystemPowerSupplyStatusInfo OBJECT-TYPE
   SYNTAX         Uint16
   ACCESS         read-only
   STATUS         mandatory
   DESCRIPTION    "The online status of the power supply. 
                  Other = 1
                  Unknown = 2
                  Enabled = 3
                  Disabled = 4
                  Not Applicable = 5"
   REFERENCE      "IBMPSG_PowerSupply.StatusInfo"
::= { ibmSystemPowerSupplyEntry 4 }

ibmSystemPowerSupplySystemCreationClassName OBJECT-TYPE
   SYNTAX         String
   ACCESS         read-only
   STATUS         mandatory
   DESCRIPTION    "The name of the class that was instantiated to create
                   power supply objects. [IBMPSG_PowerSupply]"
   REFERENCE      "IBMPSG_PowerSupply.SystemCreationClassName"
::= { ibmSystemPowerSupplyEntry 5 }

ibmSystemPowerSupplyEventsEnabled OBJECT-TYPE
   SYNTAX         Boolean
   ACCESS         read-only
   STATUS         mandatory
   DESCRIPTION    "Status indicating if supply eventing is currently 
                   enabled. [True or False]"
   REFERENCE      "IBMPSG_PowerSupply.EventsEnabled"
::= { ibmSystemPowerSupplyEntry 6 }

ibmSystemPowerSupplyPollingInterval OBJECT-TYPE
   SYNTAX         Uint64
   ACCESS         read-only
   STATUS         mandatory
   DESCRIPTION    "The frequency at which power supply status is checked.
                   [ex: 10000 milliseconds]"
   REFERENCE      "IBMPSG_PowerSupply.PollingInterval"
::= { ibmSystemPowerSupplyEntry 7 }

ibmSystemPowerSupplyEventAutoClearEnabled OBJECT-TYPE
   SYNTAX         Boolean
   ACCESS         read-only
   STATUS         mandatory
   DESCRIPTION    "Status stating if power supply events are configured
                   to automatically clear. [True | False]"
   REFERENCE      "IBMPSG_PowerSupply.EventAutoClearEnabled"
::= { ibmSystemPowerSupplyEntry 8 }

ibmSystemPowerSupplyStatus OBJECT-TYPE
   SYNTAX         String
   ACCESS         read-only
   STATUS         mandatory
   DESCRIPTION    "The online status of the power supply. [OK | Error]"
   REFERENCE      "IBMPSG_PowerSupply.Status"
::= { ibmSystemPowerSupplyEntry 9 }

END
