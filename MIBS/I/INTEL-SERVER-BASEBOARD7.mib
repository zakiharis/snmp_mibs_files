-- Intel copyright information 2012/2013"

INTEL-SERVER-BASEBOARD7 DEFINITIONS ::= BEGIN


IMPORTS
    MODULE-IDENTITY, OBJECT-TYPE, NOTIFICATION-TYPE, enterprises, Counter32, Integer32
        FROM SNMPv2-SMI

    DisplayString, TEXTUAL-CONVENTION     
        FROM SNMPv2-TC;

intel                           OBJECT IDENTIFIER ::= { enterprises 343 }
products                        OBJECT IDENTIFIER ::= { intel 2 }
server-management               OBJECT IDENTIFIER ::= { products 10 }
software                        OBJECT IDENTIFIER ::= { server-management 3 }
baseboardGroup7                 OBJECT IDENTIFIER ::= { software 5 }
systemManagementSoftwareGroup   OBJECT IDENTIFIER ::= { baseboardGroup7  100 }
chassisInformationGroup         OBJECT IDENTIFIER ::= { baseboardGroup7  200 }
processorGroup                  OBJECT IDENTIFIER ::= { baseboardGroup7  300 }
powerGroup                      OBJECT IDENTIFIER ::= { baseboardGroup7  400 }
memoryGroup                     OBJECT IDENTIFIER ::= { baseboardGroup7  500 }
thermalGroup                    OBJECT IDENTIFIER ::= { baseboardGroup7  600 }
driveSlotGroup                  OBJECT IDENTIFIER ::= { baseboardGroup7  700 }
miscellaneousGroup              OBJECT IDENTIFIER ::= { baseboardGroup7  800 }
baseboard7EventGroup            OBJECT IDENTIFIER ::= { baseboardGroup7  1000 }

--*****************************************************************************
--
-- MODULE IDENTITY AND REVISION GROUP
--
--*****************************************************************************

intelServerBaseboard7       MODULE-IDENTITY
    LAST-UPDATED    "201209151700Z" -- coordinated universal time UTC format is YYMMDDHHmmZ
    ORGANIZATION    "Intel, Server Management Software"
    CONTACT-INFO    " "
    DESCRIPTION     "This SNMP MIB module supports the Intel Server Baseboard SNMP subagent
                    for monitoring baseboard components, providing SNMP access to GET information
                    for baseboard components, SET sensor thresholds and support events through
                    the NOTIFICATION-TYPE construct.

                    Version:  2.0   9/15/2012 
 
                    Intel copyright information 2012/2013"
                    ::= { baseboardGroup7 1 }

--
-- 
--
IntelStatus                     ::= TEXTUAL-CONVENTION
    STATUS      current
    DESCRIPTION "The status used for the overall health of the server."
    SYNTAX      INTEGER {
					unavailable(1),
                    healthy(2),
                    warning(3),
                    critical(4)}

IntelFeatureStatus              ::= TEXTUAL-CONVENTION
    STATUS      current
    DESCRIPTION "The status of a particular feature."
    SYNTAX      INTEGER {
                    other(1), 
                    unknown(2),  
                    disabled(3),               
                    enabled(4),           
                    notImplemented(5) }      

IntelRedundancyStatus           ::= TEXTUAL-CONVENTION
    STATUS      current
    DESCRIPTION "The status of the redundancy capability if enabled on the server."
    SYNTAX      INTEGER {
                    other(1), 
                    unknown(2),  
                    full(3),               
                    degraded(4),           
                    lost(5),                
                    notRedundant(6),        
                    redundancyOffline(7),
	       			notApplicable(8) }
 
                            
OneBasedIndex                   ::= Integer32(1..2147483647)

--*****************************************************************************
--
-- SYSTEM MANAGEMENT SOFTWARE GROUP
--
--*****************************************************************************

systemManagementInfoOverallStatusHealth                 OBJECT-TYPE
    SYNTAX      IntelStatus
    MAX-ACCESS  read-only
    STATUS      current
    DESCRIPTION "This attribute defines the overall health Status of the system."
    ::= { systemManagementSoftwareGroup 1 }

systemManagementInfoPlatformDescription                 OBJECT-TYPE
    SYNTAX      DisplayString
    MAX-ACCESS  read-only
    STATUS      current
    DESCRIPTION "This attribute defines an OEM configurable string to identify the 
system.  This value is set via the configuration file read during the SNMP agent 
initialization."
    ::= { systemManagementSoftwareGroup 2 }

systemManagementInfoPlatformId                          OBJECT-TYPE
    SYNTAX      INTEGER
    MAX-ACCESS  read-only
    STATUS      current
    DESCRIPTION "This attribute defines an OEM configurable ID to identify the 
system.  This value is set via the configuration file read during the SNMP agent
initialization."
    ::= { systemManagementSoftwareGroup 3 }

systemManagementInfoTrapsEnabled                        OBJECT-TYPE
    SYNTAX      INTEGER {
                    false(0),
                    true(1)
                }
    MAX-ACCESS  read-only
    STATUS      current
    DESCRIPTION "This attribute defines whether or not TRAPs are enabled."
    ::= { systemManagementSoftwareGroup 4 }

systemManagementInfoSetsEnabled                         OBJECT-TYPE
    SYNTAX      INTEGER {
                    false(0),
                    true(1)
                }
    MAX-ACCESS  read-only
    STATUS      current
    DESCRIPTION "This attribute defines whether or not SETs are enabled."
    ::= { systemManagementSoftwareGroup 5 }

systemManagementManufacturerName                        OBJECT-TYPE
    SYNTAX      DisplayString
    MAX-ACCESS  read-only
    STATUS      current
    DESCRIPTION "The name of the product manufacturer."
    ::= { systemManagementSoftwareGroup 6 }

systemManagementProductName                             OBJECT-TYPE
    SYNTAX      DisplayString
    MAX-ACCESS  read-only
    STATUS      current
    DESCRIPTION "The display name of this software product."
    ::= { systemManagementSoftwareGroup 7 }

systemManagementProductVersion                          OBJECT-TYPE
    SYNTAX      DisplayString
    MAX-ACCESS  read-only
    STATUS      current
    DESCRIPTION "The version of this software product."
    ::= { systemManagementSoftwareGroup 8 }

systemManagementProductBuildNumber                      OBJECT-TYPE
    SYNTAX      DisplayString
    MAX-ACCESS  read-only
    STATUS      current
    DESCRIPTION "The build number of this software product."
    ::= { systemManagementSoftwareGroup 9 }

systemManagementProductDescription                      OBJECT-TYPE
    SYNTAX      DisplayString
    MAX-ACCESS  read-only
    STATUS      current
    DESCRIPTION "The description of this software product."
    ::= { systemManagementSoftwareGroup 10 }


--*****************************************************************************
--
-- CHASIS INFORMATION GROUP
--
--*****************************************************************************

chassisStatus                                           OBJECT-TYPE
    SYNTAX      IntelStatus
    MAX-ACCESS  read-only
    STATUS      current
    DESCRIPTION "This attribute maps the chassisSecurityState to the intelStatus value."
    ::= { chassisInformationGroup 1 }

chassisSecurityState                                    OBJECT-TYPE
    SYNTAX      INTEGER {
                    other(1),
                    unknown(2),
                    ok(3),
                    breachdetected(4)
                }
    MAX-ACCESS  read-only
    STATUS      current
    DESCRIPTION "This attribute defines whether the security is breached or not on the chassis."
    ::= { chassisInformationGroup 2 }

chassisBootState                                        OBJECT-TYPE
    SYNTAX      IntelStatus
    MAX-ACCESS  read-only
    STATUS      current
    DESCRIPTION "This attribute defines the boot state of the system."
    ::= { chassisInformationGroup 3 }

chassisThermalState                                     OBJECT-TYPE
    SYNTAX      IntelStatus
    MAX-ACCESS  read-only
    STATUS      current
    DESCRIPTION "This attribute defines the thermal state of the chassis."
    ::= { chassisInformationGroup 4 }

chassisPowerState                                       OBJECT-TYPE
    SYNTAX      INTEGER {
                    off(1),
                    on(2),
                    unknown(3)
                }
    MAX-ACCESS  read-only
    STATUS      current
    DESCRIPTION "This attribute defines the thermal state of the chassis."
    ::= { chassisInformationGroup 5 }

chassisLockState                                        OBJECT-TYPE
    SYNTAX      INTEGER {
                    notpresent(1),
                    present(2),
                    unknown(3)
                }
    MAX-ACCESS  read-only
    STATUS      current
    DESCRIPTION "This attribute defines whether a lock is present on the chassis."
    ::= { chassisInformationGroup 6 }

chassisKeyboardPasswordStatus                           OBJECT-TYPE
    SYNTAX      IntelFeatureStatus
    MAX-ACCESS  read-only
    STATUS      current
    DESCRIPTION "This attribute defines the keyboard password status."
    ::= { chassisInformationGroup 7 }

chassisPowerOnPasswordStatus                            OBJECT-TYPE
    SYNTAX      IntelFeatureStatus
    MAX-ACCESS  read-only
    STATUS      current
    DESCRIPTION "This attribute defines the power on password status."
    ::= { chassisInformationGroup 8 }

chassisAdministratorPasswordStatus                      OBJECT-TYPE
    SYNTAX      IntelFeatureStatus
    MAX-ACCESS  read-only
    STATUS      current
    DESCRIPTION "This attribute defines the administrator password status."
    ::= { chassisInformationGroup 9 }

chassisFrontPanelResetStatus                            OBJECT-TYPE
    SYNTAX      IntelFeatureStatus
    MAX-ACCESS  read-only
    STATUS      current
    DESCRIPTION "This attribute defines the front panel reset status."
    ::= { chassisInformationGroup 10 }

chassisContainerType                                    OBJECT-TYPE
    SYNTAX      INTEGER {
                    other(1),
                    unknown(2),
                    desktop(3),
                    lowProfileDesktop(4),
                    pizzaBox(5),
                    miniTower(6),
                    tower(7),
                    portable(8),
                    laptop(9),
                    notebook(10),
                    handHeld(11),
                    dockingStation(12),
                    allInOne(13),
                    subNoteBook(14),
                    spaceSaving(15),
                    lunchBox(16),
                    mainSystemChassis(17),
                    expansionChassis(18),
                    subChassis(19),
                    busExpansionChassis(20),
                    peripheralChassis(21),
                    raidChassis(22),
                    rackMountChassis(23),
                    sealedCasePC(24),
                    multiSystemChassis(25)
                }
    MAX-ACCESS  read-only
    STATUS      current
    DESCRIPTION "This attribute defines the container type of the chassis."
    ::= { chassisInformationGroup 11 }

chassisPartNumber                                       OBJECT-TYPE
    SYNTAX      DisplayString
    MAX-ACCESS  read-only
    STATUS      current
    DESCRIPTION "This attribute provides the part number of the system."
    ::= { chassisInformationGroup 12 }

chassisSerialNumber                                     OBJECT-TYPE
    SYNTAX      DisplayString
    MAX-ACCESS  read-only
    STATUS      current
    DESCRIPTION "This attribute provides the serial number of the system."
    ::= { chassisInformationGroup 13 }

chassisName                                             OBJECT-TYPE
    SYNTAX      DisplayString
    MAX-ACCESS  read-only
    STATUS      current
    DESCRIPTION "This attribute provides the name of the system."
    ::= { chassisInformationGroup 14 }

chassisAssetTag                                         OBJECT-TYPE
    SYNTAX      DisplayString
    MAX-ACCESS  read-only
    STATUS      current
    DESCRIPTION "This attribute of asset tag for the system."
    ::= { chassisInformationGroup 15 }



--*****************************************************************************
--
-- Processor Group
--
--*****************************************************************************

-------------------------------------------------------------------------------
-- Processor Device Table
-------------------------------------------------------------------------------

processorDeviceTable                                    OBJECT-TYPE
    SYNTAX      SEQUENCE OF ProcessorDeviceTableEntry
    MAX-ACCESS  not-accessible
    STATUS      current
    DESCRIPTION "This Group defines the Processor Device Table."
    ::= { processorGroup 10 }

processorDeviceTableEntry                               OBJECT-TYPE
    SYNTAX      ProcessorDeviceTableEntry
    MAX-ACCESS  not-accessible
    STATUS      current
    DESCRIPTION "This Group defines the Processor Device Table Entry."
    INDEX       { processorIndex }
    ::= { processorDeviceTable 1 }

ProcessorDeviceTableEntry                               ::= SEQUENCE {
    processorIndex                                      OneBasedIndex,
    processorCIMDeviceId                                INTEGER,
    processorDescription                                DisplayString,
    processorStatusString                               DisplayString,
    processorStatus                                     IntelStatus,
    processorType                                       INTEGER,
    processorPartNumber                                 DisplayString,
    processorManufacturerName                           DisplayString,
    processorFamily                                     INTEGER,
    processorVersionName                                DisplayString,
    processorMaxSpeed                                   INTEGER,
    processorCurrentSpeed                               INTEGER,
    processorExternalClockSpeed                         INTEGER,
    processorVoltage                                    INTEGER,
    processorUpgradeMethod                              INTEGER,
    processorSocketDesignation                          DisplayString,
    processorID                                         DisplayString
}

processorIndex                                          OBJECT-TYPE
    SYNTAX      OneBasedIndex
    MAX-ACCESS  read-only
    STATUS      current
    DESCRIPTION "This attribute defines the index of the Processor Device in the chassis."
    ::= { processorDeviceTableEntry 1 }

processorCIMDeviceId                                    OBJECT-TYPE
    SYNTAX      INTEGER
    MAX-ACCESS  read-only
    STATUS      current
    DESCRIPTION "This attribute defines the DeviceId used by the Intel CIM software to uniquely
identify the device.  For processors it will be the sensor #."
    ::= { processorDeviceTableEntry 2 }

processorDescription                                    OBJECT-TYPE
    SYNTAX      DisplayString
    MAX-ACCESS  read-only
    STATUS      current
    DESCRIPTION "This is the status of the processor."
    ::= { processorDeviceTableEntry 3 }

processorStatusString                                   OBJECT-TYPE
    SYNTAX      DisplayString
    MAX-ACCESS  read-only
    STATUS      current
    DESCRIPTION "This is the status of the processor."
    ::= { processorDeviceTableEntry 4 }

processorStatus                                         OBJECT-TYPE
    SYNTAX      IntelStatus
    MAX-ACCESS  read-only
    STATUS      current
    DESCRIPTION "This is the health value for the processor."
    ::= { processorDeviceTableEntry 5 }

processorType                                           OBJECT-TYPE
    SYNTAX      INTEGER {
                    other(1),
                    unknown(2),
                    centralProcessor(3),
                    mathProcessor(4),
                    dspProcessor(5),
                    videoProcessor(6)
    }                    
    MAX-ACCESS  read-only
    STATUS      current
    DESCRIPTION "This attribute defines the type of the Processor according 
to the SMBIOS definitions."
    ::= { processorDeviceTableEntry 6 }

processorPartNumber                                     OBJECT-TYPE
    SYNTAX      DisplayString
    MAX-ACCESS  read-only
    STATUS      current
    DESCRIPTION "This attribute defines the part number of the Processor Device."
    ::= { processorDeviceTableEntry 7 }

processorManufacturerName                               OBJECT-TYPE
    SYNTAX      DisplayString
    MAX-ACCESS  read-only
    STATUS      current
    DESCRIPTION "This is the name of manufacturer of the Processor Device."
    ::= { processorDeviceTableEntry 8 }

processorFamily                                         OBJECT-TYPE
    SYNTAX      INTEGER {
                    vOther                                      (1),
                    vUnknown                                    (2),
                    v8086                                       (3),
                    v80286                                      (4),
                    v80386                                      (5),
                    v80486                                      (6),
                    v8087                                       (7),
                    v80287                                      (8),
                    v80387                                      (9),
                    v80487                                      (10),
                    vPentiumProcessor                           (11),
                    vPentiumProProcessor                        (12),
                    vPentiumIIProcessor                         (13),
                    vPentiumProcessorWithMMXTechnology          (14),
                    vCeleronProcessor                           (15),
                    vPentiumIIXeonProcessor                     (16),
                    vPentiumIIIProcessor                        (17),
                    vM1Family                                   (18),
                    vM2Family                                   (19),
                    vK5Family                                   (25),
                    vK6Family                                   (26),
                    vPowerPcFamily                              (32),
                    vPowerPc601                                 (33),
                    vPowerPc603                                 (34),
                    vPowerPc603p                                (35),
                    vPowerPc604                                 (36),
                    vAlphaFamily                                (48),
                    vMipsFamily                                 (64),
                    vSparcFamily                                (80),
                    v68040                                      (96),
                    v68xxxFamily                                (97),
                    v68000                                      (98),
                    v68010                                      (99),
                    v68020                                      (100),
                    v68030                                      (101),
                    vHobbitFamily                               (112),
                    vWeitek                                     (128),
                    vItaniumProcessor                           (130),
                    vPa-riscFamily                              (144),
                    vV30Family                                  (160),
                    vPentiumIIIXeonProcessor                    (176),
                    vPentiumIIIProcessorwithSpeedStepTechnology (177),
                    vPentium4Processor                          (178),
                    vIntelXeon                                  (179),
                    vIntelXeonprocessorMP                       (181),
                    vIntelItanium2Processor                     (184)
    }
    MAX-ACCESS  read-only
    STATUS      current
    DESCRIPTION "This attribute defines the family of the Processor Device."
    ::= { processorDeviceTableEntry 9 }

processorVersionName                                    OBJECT-TYPE
    SYNTAX      DisplayString
    MAX-ACCESS  read-only
    STATUS      current
    DESCRIPTION "This is the name of the version of the Processor Device."
    ::= { processorDeviceTableEntry 10 }

processorMaxSpeed                                       OBJECT-TYPE
    SYNTAX      INTEGER
    MAX-ACCESS  read-only
    STATUS      current
    DESCRIPTION "This attribute defines the current speed of the Processor 
Device in MHz."
    ::= { processorDeviceTableEntry 11 }

processorCurrentSpeed                                   OBJECT-TYPE
    SYNTAX      INTEGER
    MAX-ACCESS  read-only
    STATUS      current
    DESCRIPTION "This attribute defines the current speed of the Processor 
Device in MHz."
    ::= { processorDeviceTableEntry 12 }

processorExternalClockSpeed                             OBJECT-TYPE
    SYNTAX      INTEGER
    MAX-ACCESS  read-only
    STATUS      current
    DESCRIPTION "This attribute defines the speed of the external clock for 
the Processor Device in MHz."
    ::= { processorDeviceTableEntry 13 }

processorVoltage                                        OBJECT-TYPE
    SYNTAX      INTEGER
    MAX-ACCESS  read-only
    STATUS      current
    DESCRIPTION "This attribute defines the voltage powering the Processor 
Device in millivolts."
    ::= { processorDeviceTableEntry 14 }

processorUpgradeMethod                                  OBJECT-TYPE
    SYNTAX      INTEGER {
                    vOther (1),
                    vUnknown (2),
                    vDaughterBoard (3),
                    vZifSocket (4),
                    vReplacementpiggyBack (5),
                    vNone (6),
                    vLIFSocket (7),
                    vSlot1 (8),
                    vSlot2 (9),
                    v370pinSocket (10),
                    vSlotA (11),
                    vSlotM (12),
                    vSocket423 (13),
                    vSocketASocket462 (14),
                    vSocket478 (15),
                    vSocket754 (16),
                    vSocket940 (17),
					vSocket939 (18),
					vSocketmPGA604 (19),
					vSocketLGA771 (20),
					vSocketLGA775 (21),
					vSocketS1 (22),
					vSocketAM2 (23),
					vSocketF (24)
                }
    MAX-ACCESS  read-only
    STATUS      current
    DESCRIPTION "This attribute defines the processor upgrade method for the 
Processor Device."
    ::= { processorDeviceTableEntry 15 }

processorSocketDesignation                              OBJECT-TYPE
    SYNTAX      DisplayString
    MAX-ACCESS  read-only
    STATUS      current
    DESCRIPTION "This is the string number for reference designation. "
    ::= { processorDeviceTableEntry 16 }

processorID                                         OBJECT-TYPE
    SYNTAX      DisplayString
    MAX-ACCESS  read-only
    STATUS      current
    DESCRIPTION "This attribute corresponds to the Processor ID field from the
SMBIOS specification.  This attribute contains processor specific information 
that describes the processor's features. "
    ::= { processorDeviceTableEntry 17 }
	
	
-------------------------------------------------------------------------------
-- Discrete Processor Sensor Table
-------------------------------------------------------------------------------

discreteProcessorTable                              OBJECT-TYPE
    SYNTAX      SEQUENCE OF DiscreteProcessorTableEntry
    MAX-ACCESS  not-accessible
    STATUS      current
    DESCRIPTION "This object defines the Discrete Processor Sensor Table."
    ::= { processorGroup 20 }

discreteProcessorTableEntry                         OBJECT-TYPE
    SYNTAX      DiscreteProcessorTableEntry
    MAX-ACCESS  not-accessible
    STATUS      current
    DESCRIPTION "This object defines the Discrete Processor Sensor Table Entry."
    INDEX       { discreteProcessorIndex }
    ::= { discreteProcessorTable 1 }


DiscreteProcessorTableEntry                         ::= SEQUENCE {
    discreteProcessorIndex                          OneBasedIndex,
    discreteProcessorCIMDeviceId                    INTEGER,
    discreteProcessorDescription                    DisplayString,
    discreteProcessorStatusString                   DisplayString,
    discreteProcessorStatus                         IntelStatus
}

discreteProcessorIndex                              OBJECT-TYPE
    SYNTAX      OneBasedIndex
    MAX-ACCESS  read-only
    STATUS      current
    DESCRIPTION "This attribute defines the index (one based) of the discrete processor sensor."
    ::= { discreteProcessorTableEntry 1 }

discreteProcessorCIMDeviceId                        OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { discreteProcessorTableEntry 2 }

discreteProcessorDescription                        OBJECT-TYPE
    SYNTAX      DisplayString
    MAX-ACCESS  read-only
    STATUS      current
    DESCRIPTION "This attribute textually describes the discrete processor sensor."
    ::= { discreteProcessorTableEntry 3 }

discreteProcessorStatusString                       OBJECT-TYPE
    SYNTAX      DisplayString
    MAX-ACCESS  read-only
    STATUS      current
    DESCRIPTION "Current status of the discrete processor sensor will be one of the 
following strings: ok, critical, or unknown."
    ::= { discreteProcessorTableEntry 4 }

discreteProcessorStatus                             OBJECT-TYPE
    SYNTAX      IntelStatus
    MAX-ACCESS  read-only
    STATUS      current
    DESCRIPTION "Current health status of the discrete processor sensor."
    ::= { discreteProcessorTableEntry 5 }	

--*****************************************************************************
--
-- POWER GROUP
--
--*****************************************************************************

-------------------------------------------------------------------------------
-- Power Unit Table
-------------------------------------------------------------------------------

powerUnitTable                                          OBJECT-TYPE
    SYNTAX      SEQUENCE OF PowerUnitTableEntry
    MAX-ACCESS  not-accessible
    STATUS      current
    DESCRIPTION "This object defines the Power Unit Table. If power redundancy 
is enabled on the server, there will be a single entry in the table coresponding
to the single sensor for redundancy implemented in the BMC.  If power redundancy 
is not implemented on the server, then there will be no entries in the powerUnitTable."
    ::= { powerGroup 10 }

powerUnitTableEntry                                     OBJECT-TYPE
    SYNTAX      PowerUnitTableEntry
    MAX-ACCESS  not-accessible
    STATUS      current
    DESCRIPTION "This object defines the Power Unit Table Entry."
    INDEX       { powerUnitIndex }
    ::= { powerUnitTable 1 }

PowerUnitTableEntry                                     ::= SEQUENCE {
    powerUnitIndex                                      OneBasedIndex,
    powerUnitCIMDeviceId                                INTEGER,
    powerUnitDescription                                DisplayString,
    powerUnitStatusString                               DisplayString,
    powerUnitStatus                                     IntelStatus,
    powerUnitRedundancyStatus                           IntelRedundancyStatus
}

powerUnitIndex                                          OBJECT-TYPE
    SYNTAX      OneBasedIndex
    MAX-ACCESS  read-only
    STATUS      current
    DESCRIPTION "This attribute defines the index (one based) of the power unit."
    ::= { powerUnitTableEntry 1 }

powerUnitCIMDeviceId                                    OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { powerUnitTableEntry 2 }

powerUnitDescription                                    OBJECT-TYPE
    SYNTAX      DisplayString
    MAX-ACCESS  read-only
    STATUS      current
    DESCRIPTION "This attribute provides the description of the power unit."
    ::= { powerUnitTableEntry 3 }

powerUnitStatusString                                   OBJECT-TYPE
    SYNTAX      DisplayString
    MAX-ACCESS  read-only
    STATUS      current
    DESCRIPTION "Current status of the sensor will be one of the
following strings: other, unknown, ok, nonCritical, critical, nonRecoverable."
    ::= { powerUnitTableEntry 4 }

powerUnitStatus                                         OBJECT-TYPE
    SYNTAX      IntelStatus
    MAX-ACCESS  read-only
    STATUS      current
    DESCRIPTION "Current health status of the sensor."
    ::= { powerUnitTableEntry 5 }

powerUnitRedundancyStatus                               OBJECT-TYPE
    SYNTAX      IntelRedundancyStatus
    MAX-ACCESS  read-only
    STATUS      current
    DESCRIPTION "This attribute defines the redundancy status of the power unit."
    ::= { powerUnitTableEntry 6 }

-------------------------------------------------------------------------------
-- Power Supply Table
-------------------------------------------------------------------------------

powerSupplyTable                                        OBJECT-TYPE
    SYNTAX      SEQUENCE OF PowerSupplyTableEntry
    MAX-ACCESS  not-accessible
    STATUS      current
    DESCRIPTION "This object defines the Power Supply Table."
    ::= { powerGroup 20 }

powerSupplyTableEntry                                   OBJECT-TYPE
    SYNTAX      PowerSupplyTableEntry
    MAX-ACCESS  not-accessible
    STATUS      current
    DESCRIPTION "This object defines the Power Supply Table Entry."
    INDEX       { powerSupplyIndex }
    ::= { powerSupplyTable 1 }


PowerSupplyTableEntry                                   ::= SEQUENCE {
    powerSupplyIndex                                    OneBasedIndex,
    powerSupplyCIMDeviceId                              INTEGER,
    powerSupplyDescription                              DisplayString,
    powerSupplyStatusString                             DisplayString,
    powerSupplyStatus                                   IntelStatus
}

powerSupplyIndex                                        OBJECT-TYPE
    SYNTAX      OneBasedIndex
    MAX-ACCESS  read-only
    STATUS      current
    DESCRIPTION "This attribute defines the index (one based) of the power supply."
    ::= { powerSupplyTableEntry 1 }

powerSupplyCIMDeviceId                                  OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { powerSupplyTableEntry 2 }

powerSupplyDescription                                  OBJECT-TYPE
    SYNTAX      DisplayString
    MAX-ACCESS  read-only
    STATUS      current
    DESCRIPTION "This attribute textually describes the power supply."
    ::= { powerSupplyTableEntry 3 }

powerSupplyStatusString                                 OBJECT-TYPE
    SYNTAX      DisplayString
    MAX-ACCESS  read-only
    STATUS      current
    DESCRIPTION "Current status of the sensor will be one of the
following strings: other, unknown, ok, nonCritical, critical, nonRecoverable."
    ::= { powerSupplyTableEntry 4 }

powerSupplyStatus                                       OBJECT-TYPE
    SYNTAX      IntelStatus
    MAX-ACCESS  read-only
    STATUS      current
    DESCRIPTION "Current health status of the sensor."
    ::= { powerSupplyTableEntry 5 }


-------------------------------------------------------------------------------
-- Voltage Probe Table
-------------------------------------------------------------------------------
voltageProbeTable                                       OBJECT-TYPE
    SYNTAX      SEQUENCE OF VoltageProbeTableEntry
    MAX-ACCESS  not-accessible
    STATUS      current
    DESCRIPTION "This object defines the Voltage Probe Table."
    ::= { powerGroup 30 }

voltageProbeTableEntry                                  OBJECT-TYPE
    SYNTAX      VoltageProbeTableEntry
    MAX-ACCESS  not-accessible
    STATUS      current
    DESCRIPTION "This object defines the Voltage Probe Table Entry."
    INDEX       { voltageIndex }
    ::= { voltageProbeTable 1 }

VoltageProbeTableEntry                                  ::= SEQUENCE {
    voltageIndex                                        OneBasedIndex,
    voltageCIMDeviceId                                  INTEGER,
    voltageDescription                                  DisplayString,
    voltageStatusString                                 DisplayString,
    voltageStatus                                       IntelStatus,
    voltageReading                                      INTEGER,
    voltageUpperNonRecoverableThreshold                 INTEGER,
    voltageUpperCriticalThreshold                       INTEGER,
    voltageUpperNonCriticalThreshold                    INTEGER,
    voltageLowerNonCriticalThreshold                    INTEGER,
    voltageLowerCriticalThreshold                       INTEGER,
    voltageLowerNonRecoverableThreshold                 INTEGER,
    voltageResolution                                   INTEGER,
    voltageTolerance                                    INTEGER,
    voltageAccuracy                                     INTEGER
}

voltageIndex                                            OBJECT-TYPE
    SYNTAX      OneBasedIndex
    MAX-ACCESS  read-only
    STATUS      current
    DESCRIPTION "This attribute defines the index (one based) of the voltage probe."
    ::= { voltageProbeTableEntry 1 }

voltageCIMDeviceId                                      OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { voltageProbeTableEntry 2 }

voltageDescription                                      OBJECT-TYPE
    SYNTAX      DisplayString
    MAX-ACCESS  read-only
    STATUS      current
    DESCRIPTION "This attribute textually describes the voltage probe."
    ::= { voltageProbeTableEntry 3}

voltageStatusString                                     OBJECT-TYPE
    SYNTAX      DisplayString
    MAX-ACCESS  read-only
    STATUS      current
    DESCRIPTION "Current status of the sensor will be one of the
following strings: other, unknown, ok, nonCritical, critical, nonRecoverable."
    ::= { voltageProbeTableEntry 4}

voltageStatus                                           OBJECT-TYPE
    SYNTAX      IntelStatus
    MAX-ACCESS  read-only
    STATUS      current
    DESCRIPTION "Current health status of the sensor."
    ::= { voltageProbeTableEntry 5 }

voltageReading                                          OBJECT-TYPE
    SYNTAX      INTEGER
    MAX-ACCESS  read-only
    STATUS      current
    DESCRIPTION "The current reading of the voltage probe in millivolts."
    ::= { voltageProbeTableEntry 6 }

voltageUpperNonRecoverableThreshold                     OBJECT-TYPE
    SYNTAX      INTEGER
    MAX-ACCESS  read-write
    STATUS      current
    DESCRIPTION "The upper non-recoverable threshold for the voltage probe,in
millivolts. 0x7fffffff (2147483647) denotes 'unknown'."
    ::= { voltageProbeTableEntry 7 }

voltageUpperCriticalThreshold                           OBJECT-TYPE
    SYNTAX      INTEGER
    MAX-ACCESS  read-write
    STATUS      current
    DESCRIPTION "The upper critical threshold for the voltage probe, in
millivolts. 0x7fffffff (2147483647) denotes 'unknown'."
    ::= { voltageProbeTableEntry 8 }

voltageUpperNonCriticalThreshold                        OBJECT-TYPE
    SYNTAX      INTEGER
    MAX-ACCESS  read-write
    STATUS      current
    DESCRIPTION "The upper non-critical threshold for the voltage probe, in
millivolts. 0x7fffffff (2147483647) denotes 'unknown'."
    ::= { voltageProbeTableEntry 9 }

voltageLowerNonCriticalThreshold                        OBJECT-TYPE
    SYNTAX      INTEGER
    MAX-ACCESS  read-write
    STATUS      current
    DESCRIPTION "The lower non-critical threshold for the voltage probe, in
millivolts. 0x7fffffff (2147483647) denotes 'unknown'."
    ::= { voltageProbeTableEntry 10 }

voltageLowerCriticalThreshold                           OBJECT-TYPE
    SYNTAX      INTEGER
    MAX-ACCESS  read-write
    STATUS      current
    DESCRIPTION "The lower non-critical threshold for the voltage probe, in
millivolts. 0x7fffffff (2147483647) denotes 'unknown'."
    ::= { voltageProbeTableEntry 11 }

voltageLowerNonRecoverableThreshold                     OBJECT-TYPE
    SYNTAX      INTEGER
    MAX-ACCESS  read-write
    STATUS      current
    DESCRIPTION "The lower non-recoverable threshold for the voltage probe, in
millivolts. 0x7fffffff (2147483647) denotes 'unknown'."
    ::= { voltageProbeTableEntry 12 }

voltageResolution                                       OBJECT-TYPE
    SYNTAX      INTEGER
    MAX-ACCESS  read-only
    STATUS      current
    DESCRIPTION "The resolution for the reading from this voltage probe, in
tenths of millivolts. '0x7fffffff (2147483647) denotes 'unknown'."
    ::= { voltageProbeTableEntry 13 }

voltageTolerance                                        OBJECT-TYPE
    SYNTAX      INTEGER
    MAX-ACCESS  read-only
    STATUS      current
    DESCRIPTION "The tolerance for the reading from this voltage probe, in
plus/minusmillivolts. 0x7fffffff (2147483647) denotes 'unknown'."
    ::= { voltageProbeTableEntry 14 }

voltageAccuracy                                         OBJECT-TYPE
    SYNTAX      INTEGER
    MAX-ACCESS  read-only
    STATUS      current
    DESCRIPTION "The accuracy for the reading from this voltage probe, in
plus/minus hundredths of a percent. 0x7fffffff (2147483647) denotes 'unknown'."
    ::= { voltageProbeTableEntry 15 }

-------------------------------------------------------------------------------
-- Discrete Voltage Probe Table
-------------------------------------------------------------------------------
discreteVoltageProbeTable                               OBJECT-TYPE
    SYNTAX      SEQUENCE OF DiscreteVoltageProbeTableEntry
    MAX-ACCESS  not-accessible
    STATUS      current
    DESCRIPTION "This object defines the Discrete Voltage Probe Table."
    ::= { powerGroup 40 }

discreteVoltageProbeTableEntry                          OBJECT-TYPE
    SYNTAX      DiscreteVoltageProbeTableEntry
    MAX-ACCESS  not-accessible
    STATUS      current
    DESCRIPTION "This object defines the Discrete Voltage Probe Table Entry."
    INDEX       { discreteVoltageIndex }
    ::= { discreteVoltageProbeTable 1 }

DiscreteVoltageProbeTableEntry                          ::= SEQUENCE {
    discreteVoltageIndex                                OneBasedIndex,
    discreteVoltageCIMDeviceId                          INTEGER,
    discreteVoltageDescription                          DisplayString,
    discreteVoltageStatusString                         DisplayString,
    discreteVoltageStatus                               IntelStatus,
    discreteVoltagePerformance                          INTEGER
}

discreteVoltageIndex                                    OBJECT-TYPE
    SYNTAX      OneBasedIndex
    MAX-ACCESS  read-only
    STATUS      current
    DESCRIPTION "This attribute defines the index (one based) of the voltage probe."
    ::= { discreteVoltageProbeTableEntry 1 }

discreteVoltageCIMDeviceId                              OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { discreteVoltageProbeTableEntry 2 }

discreteVoltageDescription                              OBJECT-TYPE
    SYNTAX      DisplayString
    MAX-ACCESS  read-only
    STATUS      current
    DESCRIPTION "This attribute textually describes the discrete voltage probe."
    ::= { discreteVoltageProbeTableEntry 3 }

discreteVoltageStatusString                             OBJECT-TYPE
    SYNTAX      DisplayString
    MAX-ACCESS  read-only
    STATUS      current
    DESCRIPTION "Current status of the sensor will be one of the
following strings: other, unknown, ok, nonCritical, critical, nonRecoverable."
    ::= { discreteVoltageProbeTableEntry 4 }

discreteVoltageStatus                                   OBJECT-TYPE
    SYNTAX      IntelStatus
    MAX-ACCESS  read-only
    STATUS      current
    DESCRIPTION "Current health status of the sensor."
    ::= { discreteVoltageProbeTableEntry 5 }

discreteVoltagePerformance                              OBJECT-TYPE
    SYNTAX      INTEGER {
                    met(1),
                    lags(2)
                }
    MAX-ACCESS  read-only
    STATUS      current
    DESCRIPTION "Describes whether or not the discrete voltage probe meets performance
standards, or is lagging."
    ::= { discreteVoltageProbeTableEntry 6 }

-------------------------------------------------------------------------------
-- Current Probe Table
-------------------------------------------------------------------------------
currentProbeTable                                       OBJECT-TYPE
    SYNTAX      SEQUENCE OF CurrentProbeTableEntry
    MAX-ACCESS  not-accessible
    STATUS      current
    DESCRIPTION "This object defines the Voltage Probe Table."
    ::= { powerGroup 50 }

currentProbeTableEntry                                  OBJECT-TYPE
    SYNTAX      CurrentProbeTableEntry
    MAX-ACCESS  not-accessible
    STATUS      current
    DESCRIPTION "This object defines the Voltage Probe Table Entry."
    INDEX       { currentIndex }
    ::= { currentProbeTable 1 }

CurrentProbeTableEntry                                  ::= SEQUENCE {
    currentIndex                                        OneBasedIndex,
    currentCIMDeviceId                                  INTEGER,
    currentDescription                                  DisplayString,
    currentStatusString                                 DisplayString,
    currentStatus                                       IntelStatus,
    currentReading                                      INTEGER,
    currentUpperNonRecoverableThreshold                 INTEGER,
    currentUpperCriticalThreshold                       INTEGER,
    currentUpperNonCriticalThreshold                    INTEGER,
    currentLowerNonCriticalThreshold                    INTEGER,
    currentLowerCriticalThreshold                       INTEGER,
    currentLowerNonRecoverableThreshold                 INTEGER,
    currentResolution                                   INTEGER,
    currentTolerance                                    INTEGER,
    currentAccuracy                                     INTEGER
}

currentIndex                                            OBJECT-TYPE
    SYNTAX      OneBasedIndex
    MAX-ACCESS  read-only
    STATUS      current
    DESCRIPTION "This attribute defines the index (one based) of the current probe."
    ::= { currentProbeTableEntry 1 }

currentCIMDeviceId                                      OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { currentProbeTableEntry 2 }

currentDescription                                      OBJECT-TYPE
    SYNTAX      DisplayString
    MAX-ACCESS  read-only
    STATUS      current
    DESCRIPTION "This attribute textually describes the current probe."
    ::= { currentProbeTableEntry 3}

currentStatusString                                     OBJECT-TYPE
    SYNTAX      DisplayString
    MAX-ACCESS  read-only
    STATUS      current
    DESCRIPTION "Current status of the sensor will be one of the
following strings: other, unknown, ok, nonCritical, critical, nonRecoverable."
    ::= { currentProbeTableEntry 4}

currentStatus                                           OBJECT-TYPE
    SYNTAX      IntelStatus
    MAX-ACCESS  read-only
    STATUS      current
    DESCRIPTION "Current health status of the sensor."
    ::= { currentProbeTableEntry 5 }

currentReading                                          OBJECT-TYPE
    SYNTAX      INTEGER
    MAX-ACCESS  read-only
    STATUS      current
    DESCRIPTION "The current reading of the current probe in millivolts."
    ::= { currentProbeTableEntry 6 }

currentUpperNonRecoverableThreshold                     OBJECT-TYPE
    SYNTAX      INTEGER
    MAX-ACCESS  read-write
    STATUS      current
    DESCRIPTION "The upper non-recoverable threshold for the current probe,in
millivolts. 0x7fffffff (2147483647) denotes 'unknown'."
    ::= { currentProbeTableEntry 7 }

currentUpperCriticalThreshold                           OBJECT-TYPE
    SYNTAX      INTEGER
    MAX-ACCESS  read-write
    STATUS      current
    DESCRIPTION "The upper critical threshold for the current probe, in
millivolts. 0x7fffffff (2147483647) denotes 'unknown'."
    ::= { currentProbeTableEntry 8 }

currentUpperNonCriticalThreshold                        OBJECT-TYPE
    SYNTAX      INTEGER
    MAX-ACCESS  read-write
    STATUS      current
    DESCRIPTION "The upper non-critical threshold for the current probe, in
millivolts. 0x7fffffff (2147483647) denotes 'unknown'."
    ::= { currentProbeTableEntry 9 }

currentLowerNonCriticalThreshold                        OBJECT-TYPE
    SYNTAX      INTEGER
    MAX-ACCESS  read-write
    STATUS      current
    DESCRIPTION "The lower non-critical threshold for the current probe, in
millivolts. 0x7fffffff (2147483647) denotes 'unknown'."
    ::= { currentProbeTableEntry 10 }

currentLowerCriticalThreshold                           OBJECT-TYPE
    SYNTAX      INTEGER
    MAX-ACCESS  read-write
    STATUS      current
    DESCRIPTION "The lower non-critical threshold for the current probe, in
millivolts. 0x7fffffff (2147483647) denotes 'unknown'."
    ::= { currentProbeTableEntry 11 }

currentLowerNonRecoverableThreshold                     OBJECT-TYPE
    SYNTAX      INTEGER
    MAX-ACCESS  read-write
    STATUS      current
    DESCRIPTION "The lower non-recoverable threshold for the current probe, in
millivolts. 0x7fffffff (2147483647) denotes 'unknown'."
    ::= { currentProbeTableEntry 12 }

currentResolution                                       OBJECT-TYPE
    SYNTAX      INTEGER
    MAX-ACCESS  read-only
    STATUS      current
    DESCRIPTION "The resolution for the reading from this current probe, in
tenths of millivolts. '0x7fffffff (2147483647) denotes 'unknown'."
    ::= { currentProbeTableEntry 13 }

currentTolerance                                        OBJECT-TYPE
    SYNTAX      INTEGER
    MAX-ACCESS  read-only
    STATUS      current
    DESCRIPTION "The tolerance for the reading from this current probe, in
plus/minusmillivolts. 0x7fffffff (2147483647) denotes 'unknown'."
    ::= { currentProbeTableEntry 14 }

currentAccuracy                                         OBJECT-TYPE
    SYNTAX      INTEGER
    MAX-ACCESS  read-only
    STATUS      current
    DESCRIPTION "The accuracy for the reading from this current probe, in
plus/minus hundredths of a percent. 0x7fffffff (2147483647) denotes 'unknown'."
    ::= { currentProbeTableEntry 15 }	
	
--*****************************************************************************
--
-- MEMORY GROUP
--  
-- CURRENTLY UNDER CONSTRUCTION. This group requires data definition by 
-- SMBIOS interface to be completed.
--
--*****************************************************************************

-------------------------------------------------------------------------------
-- Physical Memory Array Table
-------------------------------------------------------------------------------

physicalMemoryArrayTable                                OBJECT-TYPE
    SYNTAX      SEQUENCE OF PhysicalMemoryArrayTableEntry
    MAX-ACCESS  not-accessible
    STATUS      current
    DESCRIPTION "This Group defines the Physical Memory Array Table."
    ::= { memoryGroup 10 }

physicalMemoryArrayTableEntry                           OBJECT-TYPE
    SYNTAX      PhysicalMemoryArrayTableEntry
    MAX-ACCESS  not-accessible
    STATUS      current
    DESCRIPTION "This Group defines the Physical Memory Array Table Entry."
    INDEX       { physicalMemoryArrayIndex }
    ::= { physicalMemoryArrayTable 1 }

PhysicalMemoryArrayTableEntry                           ::= SEQUENCE {
    physicalMemoryArrayIndex                            OneBasedIndex,
    physicalMemoryArrayCIMDeviceId                      INTEGER,
    physicalMemoryArrayDescription                      DisplayString,
    physicalMemoryArrayStatusString                     DisplayString,
    physicalMemoryArrayStatus                           IntelStatus,
    physicalMemoryArrayLocation                         INTEGER,
    physicalMemoryArrayMaxCapacity                      INTEGER,
    physicalMemoryArrayNumberOfDevices                  INTEGER,
    physicalMemoryArrayErrorCorrection                  INTEGER,
    physicalMemoryArrayHandle                           INTEGER,
    physicalMemoryArrayUsageCode                        INTEGER,
    physicalMemoryArrayTag                              DisplayString,
    physicalMemoryArrayUsedSlot                         INTEGER
}

physicalMemoryArrayIndex                                OBJECT-TYPE
    SYNTAX      OneBasedIndex
    MAX-ACCESS  read-only
    STATUS      current
    DESCRIPTION "This attribute defines the index of the Physical Memory Array in this chassis."
    ::= { physicalMemoryArrayTableEntry 1 }

physicalMemoryArrayCIMDeviceId                          OBJECT-TYPE
    SYNTAX      INTEGER
    MAX-ACCESS  read-only
    STATUS      current
    DESCRIPTION "This attribute defines the DeviceId used by the Intel CIM software 
to uniquely identify the device."
    ::= { physicalMemoryArrayTableEntry 2 }

physicalMemoryArrayDescription                          OBJECT-TYPE
    SYNTAX      DisplayString
    MAX-ACCESS  read-only
    STATUS      current
    DESCRIPTION "This attribute defines a textual description of the Physical Memory Array."
    ::= { physicalMemoryArrayTableEntry 3 }

physicalMemoryArrayStatusString                         OBJECT-TYPE
    SYNTAX      DisplayString
    MAX-ACCESS  read-only
    STATUS      current
    DESCRIPTION "Current status of the sensor will be one of the
following strings: other, unknown, ok, nonCritical, critical, nonRecoverable."
    ::= { physicalMemoryArrayTableEntry 4 }

physicalMemoryArrayStatus                               OBJECT-TYPE
    SYNTAX      IntelStatus
    MAX-ACCESS  read-only
    STATUS      current
    DESCRIPTION "Current health status of the sensor."
    ::= { physicalMemoryArrayTableEntry 5 }

physicalMemoryArrayLocation                             OBJECT-TYPE
    SYNTAX      INTEGER
    MAX-ACCESS  read-only
    STATUS      current
    DESCRIPTION "This attribute defines the of the Physical Memory Array."
    ::= { physicalMemoryArrayTableEntry 6 }

physicalMemoryArrayMaxCapacity                          OBJECT-TYPE
    SYNTAX      INTEGER
    MAX-ACCESS  read-only
    STATUS      current
    DESCRIPTION "This attribute defines the maximum capacity of the Physical Memory Array."
    ::= { physicalMemoryArrayTableEntry 7 }

physicalMemoryArrayNumberOfDevices                      OBJECT-TYPE
    SYNTAX      INTEGER
    MAX-ACCESS  read-only
    STATUS      current
    DESCRIPTION "This attribute defines the number of slots available for memory devices
in this array."
    ::= { physicalMemoryArrayTableEntry 8 }

physicalMemoryArrayErrorCorrection                      OBJECT-TYPE
    SYNTAX      INTEGER {
                    other(1),
                    unknown(2),
					none(3),
                    singleBitErrorCorrecting(4),
                    doubleBitErrorCorrecting(5),
                    errorScrubbing(6)                    
                }
    MAX-ACCESS  read-only
    STATUS      current
    DESCRIPTION "This attribute defines the error correction of the Physical Memory Array."
    ::= { physicalMemoryArrayTableEntry 9 }

physicalMemoryArrayHandle                               OBJECT-TYPE
    SYNTAX      INTEGER
    MAX-ACCESS  read-only
    STATUS      current
    DESCRIPTION "This attribute is the handle, or instance number, associated with any error 
		         that was previously detected for the array."
    ::= { physicalMemoryArrayTableEntry 10 }
    
physicalMemoryArrayUsageCode                            OBJECT-TYPE
    SYNTAX      INTEGER {
                    other(1),
                    unknown(2),
                    systemMemory(3),
                    videoMemory(4),
                    flashMemory(5),
                    nonVolatileRAM(6),
                    cacheMemory(7)
                }
    MAX-ACCESS  read-only
    STATUS      current
    DESCRIPTION "This attribute describes the usage for the memory array."
    ::= { physicalMemoryArrayTableEntry 11 }

physicalMemoryArrayTag                                  OBJECT-TYPE
    SYNTAX      DisplayString
    MAX-ACCESS  read-only
    STATUS      current
    DESCRIPTION "This attribute provides a textual description of the array, and 
includes the handle integer in the description."
    ::= { physicalMemoryArrayTableEntry 12 }

physicalMemoryArrayUsedSlot                             OBJECT-TYPE
    SYNTAX      INTEGER
    MAX-ACCESS  read-only
    STATUS      current
    DESCRIPTION "This attribute is the count of used slots."
    ::= { physicalMemoryArrayTableEntry 13 }

-------------------------------------------------------------------------------
-- Physical Memory Device Table
-------------------------------------------------------------------------------

physicalMemoryDeviceTable                                OBJECT-TYPE
    SYNTAX      SEQUENCE OF PhysicalMemoryDeviceTableEntry
    MAX-ACCESS  not-accessible
    STATUS      current
    DESCRIPTION "This Group defines the Physical Memory Device Table."
    ::= { memoryGroup 20 }

physicalMemoryDeviceTableEntry                          OBJECT-TYPE
    SYNTAX      PhysicalMemoryDeviceTableEntry
    MAX-ACCESS  not-accessible
    STATUS      current
    DESCRIPTION "This Group defines the Physical Memory Device Table Entry."
    INDEX       { physicalMemoryDeviceIndex }
    ::= { physicalMemoryDeviceTable 1 }

PhysicalMemoryDeviceTableEntry                          ::= SEQUENCE {
    physicalMemoryDeviceIndex                           OneBasedIndex,
    physicalMemoryDeviceCIMDeviceId                     INTEGER,
    physicalMemoryDeviceDescription                     DisplayString,
    physicalMemoryDeviceStatusString                    DisplayString,
    physicalMemoryDeviceStatus                          IntelStatus,
    physicalMemoryDeviceTag                             DisplayString,
    physicalMemoryDeviceHandle                          INTEGER,
    physicalMemoryDeviceAssociatedArray                 INTEGER,
    physicalMemoryDeviceTotalWidth                      INTEGER,
    physicalMemoryDeviceDataWidth                       INTEGER,
    physicalMemoryDeviceSize                            INTEGER,
    physicalMemoryDeviceFormFactor                      INTEGER,
    physicalMemoryDeviceLocator                         DisplayString,
    physicalMemoryDeviceBankLabel                       DisplayString,
    physicalMemoryDeviceMemoryType                      INTEGER,
    physicalMemoryDeviceTypeDetail                      INTEGER,
    physicalMemoryDeviceSpeed                           INTEGER,
    physicalMemoryDeviceManufacturer                    DisplayString,
    physicalMemoryDeviceSerialNumber                    DisplayString,
    physicalMemoryDeviceAssetTag                        DisplayString,
    physicalMemoryDevicePartNumber                      DisplayString
}

physicalMemoryDeviceIndex                               OBJECT-TYPE
    SYNTAX      OneBasedIndex
    MAX-ACCESS  read-only
    STATUS      current
    DESCRIPTION "This attribute defines the index of the Physical Memory Device in this chassis."
    ::= { physicalMemoryDeviceTableEntry 1 }

physicalMemoryDeviceCIMDeviceId                         OBJECT-TYPE
    SYNTAX      INTEGER
    MAX-ACCESS  read-only
    STATUS      current
    DESCRIPTION "This attribute defines the DeviceId used by the Intel CIM software 
to uniquely identify the device."
    ::= { physicalMemoryDeviceTableEntry 2 }

physicalMemoryDeviceDescription                         OBJECT-TYPE
    SYNTAX      DisplayString
    MAX-ACCESS  read-only
    STATUS      current
    DESCRIPTION "This attribute defines a textual description of the Physical Memory Array."
    ::= { physicalMemoryDeviceTableEntry 3 }

physicalMemoryDeviceStatusString                        OBJECT-TYPE
    SYNTAX      DisplayString
    MAX-ACCESS  read-only
    STATUS      current
    DESCRIPTION "Current status of the sensor will be one of the
following strings: other, unknown, ok, nonCritical, critical, nonRecoverable."
    ::= { physicalMemoryDeviceTableEntry 4 }

physicalMemoryDeviceStatus                              OBJECT-TYPE
    SYNTAX      IntelStatus
    MAX-ACCESS  read-only
    STATUS      current
    DESCRIPTION "Current health status of the sensor."
    ::= { physicalMemoryDeviceTableEntry 5 }

physicalMemoryDeviceTag                                 OBJECT-TYPE
    SYNTAX      DisplayString
    MAX-ACCESS  read-only
    STATUS      current
    DESCRIPTION "This attribute defines a textual description of the Physical Memory Device."
    ::= { physicalMemoryDeviceTableEntry 6 }

physicalMemoryDeviceHandle                              OBJECT-TYPE
    SYNTAX      INTEGER
    MAX-ACCESS  read-only
    STATUS      current
    DESCRIPTION "This attribute defines a textual description of the Physical Memory Device."
    ::= { physicalMemoryDeviceTableEntry 7 }

physicalMemoryDeviceAssociatedArray                     OBJECT-TYPE
    SYNTAX      INTEGER
    MAX-ACCESS  read-only
    STATUS      current
    DESCRIPTION "This attribute defines the associated array of the Physical Memory Device."
    ::= { physicalMemoryDeviceTableEntry 8 }

physicalMemoryDeviceTotalWidth                          OBJECT-TYPE
    SYNTAX      INTEGER
    MAX-ACCESS  read-only
    STATUS      current
    DESCRIPTION "This attribute defines the total width in bits of the Physical Memory Device,
including any check or error correction bits.  If there are no error correction bits, this
value should be equal to data width.  If the width is unknown, the field is set to FFFFh."
    ::= { physicalMemoryDeviceTableEntry 9 }

physicalMemoryDeviceDataWidth                           OBJECT-TYPE
    SYNTAX      INTEGER
    MAX-ACCESS  read-only
    STATUS      current
    DESCRIPTION "This attribute defines the width in bits of the Physical Memory Device. 
A data width of 0 and a total width of 8 indicates that the device is being used 
solely to provide 8 error correction bits.  If the width is unknown, the field
is set to FFFFh."
    ::= { physicalMemoryDeviceTableEntry 10 }

physicalMemoryDeviceSize                                OBJECT-TYPE
    SYNTAX      INTEGER
    MAX-ACCESS  read-only
    STATUS      current
    DESCRIPTION "This attribute defines the size of the memory device in MB.  If the value 
is 0, no memory device is installed in the socket.  if the size is unknown, the field
value is FFFFh. The granularity in which the value is specified depends on the setting
of the most significant bit, bit 15.  If the bit is 0, the value is specified in megabyte
units;  if the bit is 1, the value is specified in kilobyte units.  For example, the value
8100h identifies a 256KM memory device and 0100h identifies a 256MB memory device."
    ::= { physicalMemoryDeviceTableEntry 11 }

physicalMemoryDeviceFormFactor                          OBJECT-TYPE
    SYNTAX      INTEGER {
                    vOther (1),
                    vUnknown (2),
                    vSIMM (3),
                    vSIP (4),
                    vChip (5),
                    vDIP (6),
                    vZIP (7),
                    vProprietaryCard (8),
                    vDIMM (9),
                    vTSOP (10),
                    vRowOfChips (11),
                    vRIMM (12),
                    vSODIMM (13),
                    vSRIMM (14),
                    vFBDIMM (15)
                }
    MAX-ACCESS  read-only
    STATUS      current
    DESCRIPTION "This attribute defines the form factor of the Physical Memory Device."
    ::= { physicalMemoryDeviceTableEntry 12 }

physicalMemoryDeviceLocator                             OBJECT-TYPE
    SYNTAX      DisplayString
    MAX-ACCESS  read-only
    STATUS      current
    DESCRIPTION "The string that identifies the physically labeled socket or board
position where the memory device is located."
    ::= { physicalMemoryDeviceTableEntry 13 }

physicalMemoryDeviceBankLabel                           OBJECT-TYPE
    SYNTAX      DisplayString
    MAX-ACCESS  read-only
    STATUS      current
    DESCRIPTION "The string that identifies the physically labeled bank where the 
memory device is located."
    ::= { physicalMemoryDeviceTableEntry 14 }

physicalMemoryDeviceMemoryType                          OBJECT-TYPE
    SYNTAX      INTEGER {
                    vOther (1),
                    vUnknown (2),
                    vDRAM (3),
                    vEDRAM (4),
                    vVRAM (5),
                    vSRAM (6),
                    vRAM (7),
                    vROM (8),
                    vFLASH (9),
                    vEEPROM (10),
                    vFEPROM (11),
                    vEPROM (12),
                    vCDRAM (13),
                    v3DRAM (14),
                    vSDRAM (15),
                    vSGRAM (16),
                    vRDRAM (17),
                    vDDR (18),
                    vDDR2 (19),
                    vFBDIMM (20),
					vDDR3 (21)
                }                    
    MAX-ACCESS  read-only
    STATUS      current
    DESCRIPTION "This attribute defines the type of the Physical Memory Device as per
the SMBIOS 2.3.4 specification."
    ::= { physicalMemoryDeviceTableEntry 15 }

physicalMemoryDeviceTypeDetail                          OBJECT-TYPE
    SYNTAX      INTEGER                    
    MAX-ACCESS  read-only
    STATUS      current
    DESCRIPTION "This attribute is bit encoded and specifies additional detail 
about the physical Memory Device. SMBIOS 2.3.4 specification defines that 
multiple bits can be set if more then one of the following attributes applies:
         bit 0   reserved, set to 0             bit 7  synchronous
         bit 1   other                          bit 8  CMOS
         bit 2   unknown                        bit 9  EDO
         bit 3   fast-paged                     bit 10 Window DRAM
         bit 4   static column                  bit 11 cache DRAM
         bit 5   pseudo-static                  bit 12 non-volatile
         bit 6   RAMBUS                         bits 13:15 reserves, set to 0"
    ::= { physicalMemoryDeviceTableEntry 16 }

physicalMemoryDeviceSpeed                               OBJECT-TYPE
    SYNTAX      INTEGER
    MAX-ACCESS  read-only
    STATUS      current
    DESCRIPTION "The speed of the device in MHz, or 0 if unknown."
    ::= { physicalMemoryDeviceTableEntry 17 }

physicalMemoryDeviceManufacturer                        OBJECT-TYPE
    SYNTAX      DisplayString
    MAX-ACCESS  read-only
    STATUS      current
    DESCRIPTION "The string number for the manufacturer of this device."
    ::= { physicalMemoryDeviceTableEntry 18 }

physicalMemoryDeviceSerialNumber                        OBJECT-TYPE
    SYNTAX      DisplayString
    MAX-ACCESS  read-only
    STATUS      current
    DESCRIPTION "The string number for the serial number of this memory device."
    ::= { physicalMemoryDeviceTableEntry 19 }

physicalMemoryDeviceAssetTag                            OBJECT-TYPE
    SYNTAX      DisplayString
    MAX-ACCESS  read-only
    STATUS      current
    DESCRIPTION "The string number for the asset tag of this memory device."
    ::= { physicalMemoryDeviceTableEntry 20 }

physicalMemoryDevicePartNumber                          OBJECT-TYPE
    SYNTAX      DisplayString
    MAX-ACCESS  read-only
    STATUS      current
    DESCRIPTION "The string part number if this memory device."
    ::= { physicalMemoryDeviceTableEntry 21 }


-------------------------------------------------------------------------------
-- Discrete Memory Sensor Table
-------------------------------------------------------------------------------

discreteMemoryTable                              OBJECT-TYPE
    SYNTAX      SEQUENCE OF DiscreteMemoryTableEntry
    MAX-ACCESS  not-accessible
    STATUS      current
    DESCRIPTION "This object defines the Discrete Memory Sensor Table."
    ::= { memoryGroup 30 }

discreteMemoryTableEntry                         OBJECT-TYPE
    SYNTAX      DiscreteMemoryTableEntry
    MAX-ACCESS  not-accessible
    STATUS      current
    DESCRIPTION "This object defines the Discrete Memory Sensor Table Entry."
    INDEX       { discreteMemoryIndex }
    ::= { discreteMemoryTable 1 }


DiscreteMemoryTableEntry                         ::= SEQUENCE {
    discreteMemoryIndex                          OneBasedIndex,
    discreteMemoryCIMDeviceId                    INTEGER,
    discreteMemoryDescription                    DisplayString,
    discreteMemoryStatusString                   DisplayString,
    discreteMemoryStatus                         IntelStatus
}

discreteMemoryIndex                              OBJECT-TYPE
    SYNTAX      OneBasedIndex
    MAX-ACCESS  read-only
    STATUS      current
    DESCRIPTION "This attribute defines the index (one based) of the discrete memory sensor."
    ::= { discreteMemoryTableEntry 1 }

discreteMemoryCIMDeviceId                        OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { discreteMemoryTableEntry 2 }

discreteMemoryDescription                        OBJECT-TYPE
    SYNTAX      DisplayString
    MAX-ACCESS  read-only
    STATUS      current
    DESCRIPTION "This attribute textually describes the discrete memory sensor."
    ::= { discreteMemoryTableEntry 3 }

discreteMemoryStatusString                       OBJECT-TYPE
    SYNTAX      DisplayString
    MAX-ACCESS  read-only
    STATUS      current
    DESCRIPTION "Current status of the discrete memory sensor will be one of the 
following strings: ok, critical, or unknown."
    ::= { discreteMemoryTableEntry 4 }

discreteMemoryStatus                             OBJECT-TYPE
    SYNTAX      IntelStatus
    MAX-ACCESS  read-only
    STATUS      current
    DESCRIPTION "Current health status of the discrete memory sensor."
    ::= { discreteMemoryTableEntry 5 }		
	

--*****************************************************************************
--
-- THERMAL GROUP
--
--*****************************************************************************

-------------------------------------------------------------------------------
-- Cooling Unit Table
-------------------------------------------------------------------------------

coolingUnitTable                                        OBJECT-TYPE
    SYNTAX      SEQUENCE OF CoolingUnitTableEntry
    MAX-ACCESS  not-accessible
    STATUS      current
    DESCRIPTION "This object defines the Cooling Unit Table. If cooling redundancy
is enabled on the server, there will be a single entry in the table coresponding 
to the single sensor for redundancy implemented in the BMC.  If cooling redundancy 
is not implemented on the server, then there will be no entries in the coolingUnitTable."
    ::= { thermalGroup 10 }

coolingUnitTableEntry                                   OBJECT-TYPE
    SYNTAX      CoolingUnitTableEntry
    MAX-ACCESS  not-accessible
    STATUS      current
    DESCRIPTION "This object defines the Cooling Unit Table Entry."
    INDEX       { coolingUnitIndex }
    ::= { coolingUnitTable 1 }

CoolingUnitTableEntry                                   ::= SEQUENCE {
    coolingUnitIndex                                    OneBasedIndex,
    coolingUnitCIMDeviceId                              INTEGER,
    coolingUnitDescription                              DisplayString,
    coolingUnitStatusString                             DisplayString,
    coolingUnitStatus                                   IntelStatus,
    coolingUnitRedundancyStatus                         IntelRedundancyStatus,
    coolingUnitCaption                                  DisplayString
}

coolingUnitIndex                                        OBJECT-TYPE
    SYNTAX      OneBasedIndex
    MAX-ACCESS  read-only
    STATUS      current
    DESCRIPTION "This attribute defines the index (one based) of the cooling unit."
    ::= { coolingUnitTableEntry 1}

coolingUnitCIMDeviceId                                  OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { coolingUnitTableEntry 2 }

coolingUnitDescription                                  OBJECT-TYPE
    SYNTAX      DisplayString
    MAX-ACCESS  read-only
    STATUS      current
    DESCRIPTION "This attribute textually describes the cooling unit."
    ::= { coolingUnitTableEntry 3 }

coolingUnitStatusString                                 OBJECT-TYPE
    SYNTAX      DisplayString
    MAX-ACCESS  read-only
    STATUS      current
    DESCRIPTION "Current status of the sensor will be one of the
following strings: other, unknown, ok, nonCritical, critical, nonRecoverable."
    ::= { coolingUnitTableEntry 4 }

coolingUnitStatus                                       OBJECT-TYPE
    SYNTAX      IntelStatus
    MAX-ACCESS  read-only
    STATUS      current
    DESCRIPTION "Current health status of the sensor."
    ::= { coolingUnitTableEntry 5 }

coolingUnitRedundancyStatus                             OBJECT-TYPE
    SYNTAX      IntelRedundancyStatus
    MAX-ACCESS  read-only
    STATUS      current
    DESCRIPTION "Gives the redundancy status of the Cooling Unit. 'Fully Redundan
' means that all of the configured redundancy is still available; 'Degraded
Redundancy' means that some failures have been experienced but some reduced
amount of redundancy is still available; 'Redundancy Lost' means that a sufficie
t number of failures have been experienced that no redundancy is available
and the next failure experienced within the Cooling Unit will cause overall
Cooling Unit failure. "
    ::= { coolingUnitTableEntry 6 }

coolingUnitCaption                                      OBJECT-TYPE
    SYNTAX      DisplayString
    MAX-ACCESS  read-only
    STATUS      current
    DESCRIPTION "This attribute provides the caption for the cooling unit."
    ::= { coolingUnitTableEntry 7 }
    
-------------------------------------------------------------------------------
-- Cooling Device Table
-------------------------------------------------------------------------------

coolingDeviceTable                                      OBJECT-TYPE
    SYNTAX      SEQUENCE OF CoolingDeviceTableEntry
    MAX-ACCESS  not-accessible
    STATUS      current
    DESCRIPTION "This object defines the Cooling Device Table."
    ::= { thermalGroup 20 }

coolingDeviceTableEntry                                 OBJECT-TYPE
    SYNTAX      CoolingDeviceTableEntry
    MAX-ACCESS  not-accessible
    STATUS      current
    DESCRIPTION "This object defines the Cooling Device Table Entry"
    INDEX       { coolingDeviceIndex }
    ::= { coolingDeviceTable 1 }

CoolingDeviceTableEntry                                 ::= SEQUENCE {
    coolingDeviceIndex                                  OneBasedIndex,
    coolingDeviceCIMDeviceId                            INTEGER,
    coolingDeviceDescription                            DisplayString,
    coolingDeviceStatusString                           DisplayString,
    coolingDeviceStatus                                 IntelStatus,
    coolingDeviceReading                                INTEGER,
    coolingDeviceUpperNonRecoverableThreshold           INTEGER,
    coolingDeviceUpperCriticalThreshold                 INTEGER,
    coolingDeviceUpperNonCriticalThreshold              INTEGER,
    coolingDeviceLowerNonCriticalThreshold              INTEGER,
    coolingDeviceLowerCriticalThreshold                 INTEGER,
    coolingDeviceLowerNonRecoverableThreshold           INTEGER,
    coolingDeviceResolution                             INTEGER,
    coolingDeviceTolerance                              INTEGER,
    coolingDeviceAccuracy                               INTEGER
}

coolingDeviceIndex                                      OBJECT-TYPE
    SYNTAX      OneBasedIndex
    MAX-ACCESS  read-only
    STATUS      current
    DESCRIPTION "This attribute defines the index (one based) of the cooling device."
    ::= { coolingDeviceTableEntry 1 }

coolingDeviceCIMDeviceId                                  OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { coolingDeviceTableEntry 2 }

coolingDeviceDescription                                OBJECT-TYPE
    SYNTAX      DisplayString
    MAX-ACCESS  read-only
    STATUS      current
    DESCRIPTION "This attribute textually describes the cooling device."
    ::= { coolingDeviceTableEntry 3 }

coolingDeviceStatusString                               OBJECT-TYPE
    SYNTAX      DisplayString
    MAX-ACCESS  read-only
    STATUS      current
    DESCRIPTION "Current status of the sensor will be one of the
following strings: other, unknown, ok, nonCritical, critical, nonRecoverable."
    ::= { coolingDeviceTableEntry 4}

coolingDeviceStatus                                     OBJECT-TYPE
    SYNTAX      IntelStatus
    MAX-ACCESS  read-only
    STATUS      current
    DESCRIPTION "Current health status of the sensor."
    ::= { coolingDeviceTableEntry 5 }

coolingDeviceReading                                    OBJECT-TYPE
    SYNTAX      INTEGER
    MAX-ACCESS  read-only
    STATUS      current
    DESCRIPTION "This attribute contains the current fan sensor  
reading, measured in the units specified by the Fan Units attribute. 0x7fffffff (2147483647) denotes 'unknown'."
    ::= { coolingDeviceTableEntry 6 }

coolingDeviceUpperNonRecoverableThreshold               OBJECT-TYPE
    SYNTAX      INTEGER
    MAX-ACCESS  read-write
    STATUS      current
    DESCRIPTION "This attribute contains the fatal error threshold 
level for the fan.  The threshold is given in the units specified by the Fan Units
attribute. This attribute may not apply to all fan types. 0x7fffffff (2147483647) denotes 'unknown'."
    ::= { coolingDeviceTableEntry 7 }

coolingDeviceUpperCriticalThreshold                     OBJECT-TYPE
    SYNTAX      INTEGER
    MAX-ACCESS  read-write
    STATUS      current
    DESCRIPTION "This attribute contains the major error threshold 
level for the fan.  The threshold is given in the units specified by the Fan Units
attribute. This attribute may not apply to all fan types. 0x7fffffff (2147483647) denotes 'unknown'."
    ::= { coolingDeviceTableEntry 8 }

coolingDeviceUpperNonCriticalThreshold                  OBJECT-TYPE
    SYNTAX      INTEGER 
    MAX-ACCESS  read-write
    STATUS      current
    DESCRIPTION "This attribute contains the warning threshold level 
for the fan.  The threshold is given in the units specified by the Fan Units
attribute. This attribute may not apply to all fan types. 0x7fffffff (2147483647) denotes 'unknown'."
    ::= { coolingDeviceTableEntry 9 }

coolingDeviceLowerNonCriticalThreshold                  OBJECT-TYPE
    SYNTAX      INTEGER
    MAX-ACCESS  read-write
    STATUS      current
    DESCRIPTION "This attribute contains the lower warning threshold level 
for the fan.  The threshold is given in the units specified by the Fan Units
attribute. This attribute may not apply to all fan types. 0x7fffffff (2147483647) denotes 'unknown'."
    ::= { coolingDeviceTableEntry 10 }

coolingDeviceLowerCriticalThreshold                     OBJECT-TYPE
    SYNTAX      INTEGER
    MAX-ACCESS  read-write
    STATUS      current
    DESCRIPTION "This attribute contains the lower critical threshold level
for the fan.  The threshold is given in the units specified by the Fan Units
attribute. This attribute may not apply to all fan types. 0x7fffffff (2147483647) denotes 'unknown'."   
    ::= { coolingDeviceTableEntry 11 }

coolingDeviceLowerNonRecoverableThreshold               OBJECT-TYPE
    SYNTAX      INTEGER
    MAX-ACCESS  read-write
    STATUS      current
    DESCRIPTION "This attribute contains the fatal error threshold 
level for the fan.  The threshold is given in the units specified by the Fan Units
attribute. This attribute may not apply to all fan types. 0x7fffffff (2147483647) denotes 'unknown'."  
    ::= { coolingDeviceTableEntry 12 }

coolingDeviceResolution                                 OBJECT-TYPE
    SYNTAX      INTEGER
    MAX-ACCESS  read-only
    STATUS      current
    DESCRIPTION "This attribute describes the sensor's resolution. 0x7fffffff (2147483647) denotes 'unknown'."    
    ::= { coolingDeviceTableEntry 13 }

coolingDeviceTolerance                                  OBJECT-TYPE
    SYNTAX      INTEGER
    MAX-ACCESS  read-only
    STATUS      current
    DESCRIPTION "This attribute describes the sensor's tolerance in 
the units specified by the cooling device's units attrubite. 0x7fffffff (2147483647) denotes 'unknown'."
    ::= { coolingDeviceTableEntry 14 }

coolingDeviceAccuracy                                   OBJECT-TYPE
    SYNTAX      INTEGER
    MAX-ACCESS  read-only
    STATUS      current
    DESCRIPTION "This attribute describes the sensor's accuracy in 
+/- hundredth of a percent.  0x7fffffff (2147483647) denotes 'unknown'."
    ::= { coolingDeviceTableEntry 15 }

-------------------------------------------------------------------------------
-- Discrete Cooling Device Table
-------------------------------------------------------------------------------
discreteCoolingDeviceTable                              OBJECT-TYPE
    SYNTAX      SEQUENCE OF DiscreteCoolingDeviceTableEntry
    MAX-ACCESS  not-accessible
    STATUS      current
    DESCRIPTION "This object defines the Discrete Cooling Device Table."
    ::= { thermalGroup 30 }

discreteCoolingDeviceTableEntry                         OBJECT-TYPE
    SYNTAX      DiscreteCoolingDeviceTableEntry
    MAX-ACCESS  not-accessible
    STATUS      current
    DESCRIPTION "This object defines the Discrete Cooling Device Table Entry."
    INDEX       { discreteCoolingDeviceIndex }
    ::= { discreteCoolingDeviceTable 1 }

DiscreteCoolingDeviceTableEntry                         ::= SEQUENCE {
    discreteCoolingDeviceIndex                          OneBasedIndex,
    discreteCoolingDeviceCIMDeviceId                    INTEGER,
    discreteCoolingDeviceDescription                    DisplayString,
    discreteCoolingDeviceStatusString                   DisplayString,
    discreteCoolingDeviceStatus                         IntelStatus,
    discreteCoolingDevicePerformance                    INTEGER
}

discreteCoolingDeviceIndex                              OBJECT-TYPE
    SYNTAX      OneBasedIndex
    MAX-ACCESS  read-only
    STATUS      current
    DESCRIPTION "This attribute defines the index (one based) of the discrete cooling device."
    ::= { discreteCoolingDeviceTableEntry 1 }

discreteCoolingDeviceCIMDeviceId                        OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { discreteCoolingDeviceTableEntry 2 }

discreteCoolingDeviceDescription                        OBJECT-TYPE
    SYNTAX      DisplayString
    MAX-ACCESS  read-only
    STATUS      current
    DESCRIPTION "This attribute textually describes the discrete cooling device."
    ::= { discreteCoolingDeviceTableEntry 3 }

discreteCoolingDeviceStatusString                       OBJECT-TYPE
    SYNTAX      DisplayString
    MAX-ACCESS  read-only
    STATUS      current
    DESCRIPTION "Current status of the sensor will be one of the
following strings: other, unknown, ok, nonCritical, critical, nonRecoverable."
    ::= { discreteCoolingDeviceTableEntry 4 }

discreteCoolingDeviceStatus                             OBJECT-TYPE
    SYNTAX      IntelStatus
    MAX-ACCESS  read-only
    STATUS      current
    DESCRIPTION "Current health status of the sensor."
    ::= { discreteCoolingDeviceTableEntry 5 }

discreteCoolingDevicePerformance                        OBJECT-TYPE
    SYNTAX      INTEGER {
                    met(1),
                    lags(2)
                }
    MAX-ACCESS  read-only
    STATUS      current
    DESCRIPTION "Describes whether or not the discrete cooling device meets performance
standards, or is lagging."
    ::= { discreteCoolingDeviceTableEntry 6 }


-------------------------------------------------------------------------------
-- Temperature Probe Table
-------------------------------------------------------------------------------

temperatureProbeTable                                   OBJECT-TYPE
    SYNTAX      SEQUENCE OF TemperatureProbeTableEntry
    MAX-ACCESS  not-accessible
    STATUS      current
    DESCRIPTION "This object defines the Temperature Probe Table."
    ::= { thermalGroup 40 }

temperatureProbeTableEntry                              OBJECT-TYPE
    SYNTAX      TemperatureProbeTableEntry
    MAX-ACCESS  not-accessible
    STATUS      current
    DESCRIPTION "This object defines the Temperature Probe Table Entry."
    INDEX       { temperatureIndex }
    ::= { temperatureProbeTable 1 }

TemperatureProbeTableEntry                              ::= SEQUENCE {
    temperatureIndex                                    OneBasedIndex, 
    temperatureCIMDeviceId                              INTEGER,
    temperatureDescription                              DisplayString,
    temperatureStatusString                             DisplayString,
    temperatureStatus                                   IntelStatus,
    temperatureReading                                  INTEGER,
    temperatureUpperNonRecoverableThreshold             INTEGER,
    temperatureUpperCriticalThreshold                   INTEGER,
    temperatureUpperNonCriticalThreshold                INTEGER,
    temperatureLowerNonCriticalThreshold                INTEGER,
    temperatureLowerCriticalThreshold                   INTEGER,
    temperatureLowerNonRecoverableThreshold             INTEGER,
    temperatureResolution                               INTEGER,
    temperatureTolerance                                INTEGER,
    temperatureAccuracy                                 INTEGER
}

temperatureIndex                                        OBJECT-TYPE
    SYNTAX      OneBasedIndex
    MAX-ACCESS  read-only
    STATUS      current
    DESCRIPTION "This attribute defines the index (one based) of the temperature probe."
    ::= { temperatureProbeTableEntry 1}

temperatureCIMDeviceId                                  OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { temperatureProbeTableEntry 2 }

temperatureDescription                                  OBJECT-TYPE
    SYNTAX      DisplayString
    MAX-ACCESS  read-only
    STATUS      current
    DESCRIPTION "This attribute textually describes the temperature probe."
    ::= { temperatureProbeTableEntry 3}

temperatureStatusString                                 OBJECT-TYPE
    SYNTAX      DisplayString
    MAX-ACCESS  read-only
    STATUS      current
    DESCRIPTION "Current status of the sensor will be one of the
following strings: other, unknown, ok, nonCritical, critical, nonRecoverable."
    ::= { temperatureProbeTableEntry 4}

temperatureStatus                                       OBJECT-TYPE
    SYNTAX      IntelStatus
    MAX-ACCESS  read-only
    STATUS      current
    DESCRIPTION "Current health status of the sensor."
    ::= { temperatureProbeTableEntry 5 }

temperatureReading                                      OBJECT-TYPE
    SYNTAX      INTEGER
    MAX-ACCESS  read-only
    STATUS      current
    DESCRIPTION "The present temperature reading of this temperature probe
in 1/10th degrees C. 0x7fffffff (2147483647) denotes 'unknown'."
    ::= { temperatureProbeTableEntry 6 }

temperatureUpperNonRecoverableThreshold                 OBJECT-TYPE
    SYNTAX      INTEGER
    MAX-ACCESS  read-write
    STATUS      current
    DESCRIPTION "The upper non-recoverable threshold for the temperature probe,
in 1/10th degrees C. 0x7fffffff (2147483647) denotes 'unknown'."
    ::= { temperatureProbeTableEntry 7 }

temperatureUpperCriticalThreshold                       OBJECT-TYPE
    SYNTAX      INTEGER
    MAX-ACCESS  read-write
    STATUS      current
    DESCRIPTION "The upper critical threshold for the temperature probe, in
/10th degrees C. 0x7fffffff (2147483647) denotes 'unknown'."
    ::= { temperatureProbeTableEntry 8 }

temperatureUpperNonCriticalThreshold                    OBJECT-TYPE
    SYNTAX      INTEGER
    MAX-ACCESS  read-write
    STATUS      current
    DESCRIPTION "The upper non-critical threshold for the temperature probe,
in 1/10th degrees C. 0x7fffffff (2147483647) denotes 'unknown'."
    ::= { temperatureProbeTableEntry 9 }

temperatureLowerNonCriticalThreshold                    OBJECT-TYPE
    SYNTAX      INTEGER
    MAX-ACCESS  read-write
    STATUS      current
    DESCRIPTION "The lower non-critical threshold for the temperature reading
setby the user, in 1/10th degrees C. 0x7fffffff (2147483647) denotes 'unknown'."
    ::= { temperatureProbeTableEntry 10 }

temperatureLowerCriticalThreshold                       OBJECT-TYPE
    SYNTAX      INTEGER
    MAX-ACCESS  read-write
    STATUS      current
    DESCRIPTION "The lower critical threshold for the temperature probe, in
1/10 degrees C. 0x7fffffff (2147483647) denotes 'unknown'."
    ::= { temperatureProbeTableEntry 11 }

temperatureLowerNonRecoverableThreshold                 OBJECT-TYPE
    SYNTAX      INTEGER
    MAX-ACCESS  read-write
    STATUS      current
    DESCRIPTION "The lower non-recoverable threshold for the temperature probe,
in 1/10th degrees C. 0x7fffffff (2147483647) denotes 'unknown'."
    ::= { temperatureProbeTableEntry 12 }

temperatureResolution                                   OBJECT-TYPE
    SYNTAX      INTEGER
    MAX-ACCESS  read-only
    STATUS      current
    DESCRIPTION "The resolution for the reading from this temperature probe,
in tenths of 1/10th degrees C. '0x7fffffff (2147483647) denotes 'unknown'."
    ::= { temperatureProbeTableEntry 13 }

temperatureTolerance                                    OBJECT-TYPE
    SYNTAX      INTEGER
    MAX-ACCESS  read-only
    STATUS      current
    DESCRIPTION "The tolerance for the reading from this temperature probe,
in plus/minus 1/10 degrees C. 0x7fffffff (2147483647) denotes 'unknown'."
    ::= { temperatureProbeTableEntry 14 }

temperatureAccuracy                                     OBJECT-TYPE
    SYNTAX      INTEGER
    MAX-ACCESS  read-only
    STATUS      current
    DESCRIPTION "The accuracy for the reading from this temperature probe, in
plus/minus hundredths of a percent. 0x7fffffff (2147483647) denotes 'unknown' or'unsupported'."
    ::= { temperatureProbeTableEntry 15 }

--*****************************************************************************
--
-- DRIVE SLOT GROUP
--
--*****************************************************************************

-------------------------------------------------------------------------------
-- Drive Slot Presence Sensor Table
-------------------------------------------------------------------------------

driveSlotPresenceSensorTable                              OBJECT-TYPE
    SYNTAX      SEQUENCE OF DriveSlotPresenceSensorTableEntry
    MAX-ACCESS  not-accessible
    STATUS      current
    DESCRIPTION "This object defines the Drive Slot Presence Sensor Table."
    ::= { driveSlotGroup 10 }

driveSlotPresenceSensorTableEntry                         OBJECT-TYPE
    SYNTAX      DriveSlotPresenceSensorTableEntry
    MAX-ACCESS  not-accessible
    STATUS      current
    DESCRIPTION "This object defines the Drive Slot Presence Sensor Table Entry."
    INDEX       { driveSlotPresenceSensorIndex }
    ::= { driveSlotPresenceSensorTable 1 }


DriveSlotPresenceSensorTableEntry                         ::= SEQUENCE {
    driveSlotPresenceSensorIndex                          OneBasedIndex,
    driveSlotPresenceSensorCIMDeviceId                    INTEGER,
    driveSlotPresenceSensorDescription                    DisplayString,
    driveSlotPresenceSensorStatusString                   DisplayString,
    driveSlotPresenceSensorStatus                         IntelStatus,
    driveSlotPresenceSensorPresenceStatusString           DisplayString	
}

driveSlotPresenceSensorIndex                              OBJECT-TYPE
    SYNTAX      OneBasedIndex
    MAX-ACCESS  read-only
    STATUS      current
    DESCRIPTION "This attribute defines the index (one based) of the drive slot presence sensor."
    ::= { driveSlotPresenceSensorTableEntry 1 }

driveSlotPresenceSensorCIMDeviceId                        OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { driveSlotPresenceSensorTableEntry 2 }

driveSlotPresenceSensorDescription                        OBJECT-TYPE
    SYNTAX      DisplayString
    MAX-ACCESS  read-only
    STATUS      current
    DESCRIPTION "This attribute textually describes the drive slot presence sensor."
    ::= { driveSlotPresenceSensorTableEntry 3 }

driveSlotPresenceSensorStatusString                       OBJECT-TYPE
    SYNTAX      DisplayString
    MAX-ACCESS  read-only
    STATUS      current
    DESCRIPTION "Current status of the sensor will be one of the 
following strings: ok, critical, or unknown."
    ::= { driveSlotPresenceSensorTableEntry 4 }

driveSlotPresenceSensorStatus                             OBJECT-TYPE
    SYNTAX      IntelStatus
    MAX-ACCESS  read-only
    STATUS      current
    DESCRIPTION "Current health status of the sensor."
    ::= { driveSlotPresenceSensorTableEntry 5 }
	
driveSlotPresenceSensorPresenceStatusString                       OBJECT-TYPE
    SYNTAX      DisplayString
    MAX-ACCESS  read-only
    STATUS      current
    DESCRIPTION "Current status of the sensor will be one of the 
following strings: Device Removed/Absent or Device Inserted/Present."
    ::= { driveSlotPresenceSensorTableEntry 6 }	
	
-------------------------------------------------------------------------------
-- MISCELLANEOUS Sensor Table
-------------------------------------------------------------------------------

miscellaneousSensorTable                              OBJECT-TYPE
    SYNTAX      SEQUENCE OF MiscellaneousSensorTableEntry
    MAX-ACCESS  not-accessible
    STATUS      current
    DESCRIPTION "This object defines the miscellaneous Presence Sensor Table."
    ::= { miscellaneousGroup 10 }

miscellaneousSensorTableEntry                         OBJECT-TYPE
    SYNTAX      MiscellaneousSensorTableEntry
    MAX-ACCESS  not-accessible
    STATUS      current
    DESCRIPTION "This object defines the miscellaneous Sensor Table Entry."
    INDEX       { miscellaneousSensorIndex }
    ::= { miscellaneousSensorTable 1 }


MiscellaneousSensorTableEntry                         ::= SEQUENCE {
    miscellaneousSensorIndex                          OneBasedIndex,
    miscellaneousSensorCIMDeviceId                    INTEGER,
    miscellaneousSensorDescription                    DisplayString,
    miscellaneousSensorStatusString                   DisplayString,
    miscellaneousSensorStatus                         IntelStatus
}

miscellaneousSensorIndex                              OBJECT-TYPE
    SYNTAX      OneBasedIndex
    MAX-ACCESS  read-only
    STATUS      current
    DESCRIPTION "This attribute defines the index (one based) of the miscellaneous sensor."
    ::= { miscellaneousSensorTableEntry 1 }

miscellaneousSensorCIMDeviceId                        OBJECT-TYPE
    SYNTAX      INTEGER
    MAX-ACCESS  read-only
    STATUS      current
    DESCRIPTION "This attribute defines the DeviceId used by the Intel CIM software 
to uniquely identify the device, it represents the [channel#][sensor#][IPMB OwnerID][LUN]."
    ::= { miscellaneousSensorTableEntry 2 }

miscellaneousSensorDescription                        OBJECT-TYPE
    SYNTAX      DisplayString
    MAX-ACCESS  read-only
    STATUS      current
    DESCRIPTION "This attribute textually describes the miscellaneous sensor."
    ::= { miscellaneousSensorTableEntry 3 }

miscellaneousSensorStatusString                       OBJECT-TYPE
    SYNTAX      DisplayString
    MAX-ACCESS  read-only
    STATUS      current
    DESCRIPTION "Current status of the miscellaneous sensor will be one of the 
following strings: ok, critical, or unknown."
    ::= { miscellaneousSensorTableEntry 4 }

miscellaneousSensorStatus                             OBJECT-TYPE
    SYNTAX      IntelStatus
    MAX-ACCESS  read-only
    STATUS      current
    DESCRIPTION "Current health status of the miscellaneous sensor."
    ::= { miscellaneousSensorTableEntry 5 }
	

--*****************************************************************************
--
--  EVENTS 
--
--*****************************************************************************

eventVariables                  OBJECT IDENTIFIER ::= { baseboard7EventGroup 10 }

eventDescription                OBJECT-TYPE
    SYNTAX      DisplayString
    MAX-ACCESS  read-only
    STATUS      current
    DESCRIPTION "Descriptive information about the event."
    ::= { eventVariables 1 }

eventSeverity                   OBJECT-TYPE
    SYNTAX      IntelStatus
    MAX-ACCESS  read-only
    STATUS      current
    DESCRIPTION "Severity of the event" 
    ::= { eventVariables 2 }

eventSlotDescription            OBJECT-TYPE
    SYNTAX      DisplayString
    MAX-ACCESS  read-only
    STATUS      current
    DESCRIPTION "Test string identifying the PHP slot group."
    ::= { eventVariables 3 }

eventSlotCIMDeviceId            OBJECT-TYPE
    SYNTAX      INTEGER
    MAX-ACCESS  read-only
    STATUS      current
    DESCRIPTION "The CIM Device ID of the slot reported on by the event."
    ::= { eventVariables 4 }



systemManagementSWEvents        OBJECT IDENTIFIER ::= { baseboard7EventGroup 20 }
chassisEvents                   OBJECT IDENTIFIER ::= { baseboard7EventGroup 30 }
processorEvents                 OBJECT IDENTIFIER ::= { baseboard7EventGroup 40 }
powerEvents                     OBJECT IDENTIFIER ::= { baseboard7EventGroup 50 }
memoryEvents                    OBJECT IDENTIFIER ::= { baseboard7EventGroup 60 }
thermalEvents                   OBJECT IDENTIFIER ::= { baseboard7EventGroup 70 }
slotEvents                      OBJECT IDENTIFIER ::= { baseboard7EventGroup 80 }
systemEvents                    OBJECT IDENTIFIER ::= { baseboard7EventGroup 90 }
driveSlotEvents                 OBJECT IDENTIFIER ::= { baseboard7EventGroup 100 }

-------------------------------------------------------------------------------
-- System Management SW Events
-------------------------------------------------------------------------------
systemHealthOtherEvent                      NOTIFICATION-TYPE
    OBJECTS { 
        eventDescription,
        systemManagementInfoOverallStatusHealth 
    }
    STATUS      current
    DESCRIPTION "The overall server health is now a non-standard value of other."
    --Novell NMS trap annotation
    --TYPE       "Server Health Other"
    --SEVERITY   INFORMATIONAL 
    --SUMMARY    "The overall health of the server is other."
    --CATEGORY   "Error Alarms"
    --STATE      OPERATIONAL
    --STATUS     MANDATORY 
    ::= { systemManagementSWEvents 1 }

systemHealthUnknownEvent                    NOTIFICATION-TYPE
    OBJECTS { 
        eventDescription,
        systemManagementInfoOverallStatusHealth
    }
    STATUS      current
    DESCRIPTION "The overall server health is now unknown."
    --Novell NMS trap annotation
    --TYPE       "Server Health Unknown"
    --SEVERITY   INFORMATIONAL 
    --SUMMARY    "The overall health of the server is unknown."
    --CATEGORY   "Error Alarms"
    --STATE      OPERATIONAL
    --STATUS     MANDATORY 
    ::= { systemManagementSWEvents 2 }

systemHealthOKEvent                         NOTIFICATION-TYPE
    OBJECTS { 
        eventDescription,
        systemManagementInfoOverallStatusHealth
    }
    STATUS      current
    DESCRIPTION "The overall server health is now OK."
    --Novell NMS trap annotation
    --TYPE       "Server Health OK"
    --SEVERITY   INFORMATIONAL 
    --SUMMARY    "The overall health of the server is OK."
    --CATEGORY   "Error Alarms"
    --STATE      OPERATIONAL
    --STATUS     MANDATORY         
    ::= { systemManagementSWEvents 3 }

systemHealthNonCriticalEvent                NOTIFICATION-TYPE
    OBJECTS { 
        eventDescription,
        systemManagementInfoOverallStatusHealth
    }
    STATUS      current
    DESCRIPTION "The overall server health is now Degraded."
    --Novell NMS trap annotation
    --TYPE       "Server Health Non-Critical"
    --SEVERITY   MAJOR 
    --SUMMARY    "The overall health of the server is non-critical."
    --CATEGORY   "Error Alarms"
    --STATE      DEGRADED 
    --STATUS     MANDATORY         
    ::= { systemManagementSWEvents 4 }

systemHealthCriticalEvent                   NOTIFICATION-TYPE
    OBJECTS { 
        eventDescription,
        systemManagementInfoOverallStatusHealth
    }
    STATUS      current
    DESCRIPTION "The overall server health is now Critical."
    --Novell NMS trap annotation
    --TYPE       "Server Health Critical"
    --SEVERITY   CRITICAL 
    --SUMMARY    "The overall health of the server is critical."
    --CATEGORY   "Error Alarms"
    --STATE      FAILED 
    --STATUS     MANDATORY 
    ::= { systemManagementSWEvents 5 }

systemHealthNonRecoverableEvent             NOTIFICATION-TYPE
    OBJECTS { 
        eventDescription,
        systemManagementInfoOverallStatusHealth 
    }
    STATUS      current
    DESCRIPTION "The overall server health is now non-recoverable."
    --Novell NMS trap annotation
    --TYPE       "Syerver Health Non-Recoverable"
    --SEVERITY   CRITICAL 
    --SUMMARY    "The overall health of the server is non-recoverable."
    --CATEGORY   "Error Alarms"
    --STATE      FAILED  
    --STATUS     MANDATORY 
    ::= { systemManagementSWEvents 6 }

-------------------------------------------------------------------------------
-- Chassis Events
-------------------------------------------------------------------------------
chassisIntrusionDetectedEvent               NOTIFICATION-TYPE
    OBJECTS { 
        eventDescription,
        eventSeverity
    }
    STATUS      current
    DESCRIPTION "An intrusion to the chassis has been detected."
    --Novell NMS trap annotation
    --TYPE       "Server Chassis Intrusion Detected"
    --SEVERITY   MINOR 
    --SUMMARY    "An intrusion into the chassis has been detected."
    --CATEGORY   "Error Alarms"
    --STATE      OPERATIONAL
    --STATUS     OPTIONAL 
    ::= { chassisEvents 1 }

chassisIntrusionClearedEvent                NOTIFICATION-TYPE
    OBJECTS { 
        eventDescription,
        eventSeverity
    }
    STATUS      current
    DESCRIPTION "The chassis intrusion is no longer detected."
    --Novell NMS trap annotation
    --TYPE       "Server Chassis Intrusion Cleared"
    --SEVERITY   INFORMATIONAL
    --SUMMARY    "The intrusion into the chassis has been cleared."
    --CATEGORY   "Error Alarms"
    --STATE      OPERATIONAL
    --STATUS     OPTIONAL    
    ::= { chassisEvents 2 }

-------------------------------------------------------------------------------
-- Processor Events
-------------------------------------------------------------------------------
processorIERREvent                          NOTIFICATION-TYPE
    OBJECTS { 
        eventDescription,
        processorStatus, 
        processorDescription, 
        processorCIMDeviceId 
    }
    STATUS      current
    DESCRIPTION "The processor experienced an IERR (Internal Error)."
    --Novell NMS trap annotation
    --TYPE       "Server Processor IERR"
    --SEVERITY   CRITICAL  
    --SUMMARY    "Processor %s experienced an Internal Error."
    --ARGUMENTS  {3}
    --CATEGORY   "Error Alarms"
    --STATE      FAILED 
    --STATUS     MANDATORY     
    ::= { processorEvents 1 }

processorThermalTripEvent                   NOTIFICATION-TYPE
    OBJECTS { 
        eventDescription,
        processorStatus, 
        processorDescription, 
        processorCIMDeviceId 
    }
    STATUS      current
    DESCRIPTION "The proessor experienced a thermal trip."
    --Novell NMS trap annotation
    --TYPE       "Server Processor Thermal Trip"
    --SEVERITY   CRITICAL 
    --SUMMARY    "Processor %s experienced a thermal trip."
    --ARGUMENTS  {3}
    --CATEGORY   "Error Alarms"
    --STATE      FAILED 
    --STATUS     MANDATORY     
    ::= { processorEvents 2 }

processorFRB1Event                          NOTIFICATION-TYPE
    OBJECTS { 
        eventDescription,
        processorStatus, 
        processorDescription, 
        processorCIMDeviceId 
    }
    STATUS      current
    DESCRIPTION "The processor experienced an FRB1 error, BIST failure."
    --Novell NMS trap annotation
    --TYPE       "Server Processor FRB1 Error"
    --SEVERITY   CRITICAL 
    --SUMMARY    "Processor %s experienced an FRB1 error, BIST failure."
    --ARGUMENTS  {3}
    --CATEGORY   "Error Alarms"
    --STATE      FAILED 
    --STATUS     MANDATORY     
    ::= { processorEvents 3 }

processorFRB2Event                          NOTIFICATION-TYPE
    OBJECTS { 
        eventDescription,
        processorStatus, 
        processorDescription, 
        processorCIMDeviceId 
    }
    STATUS      current
    DESCRIPTION "The processor experienced an FRB2 error, hang in POST failure."
    --Novell NMS trap annotation
    --TYPE       "Server Processor FRB2 Error"
    --SEVERITY   CRITICAL 
    --SUMMARY    "Processor %s experienced an FRB2 error, hang in POST failure."
    --ARGUMENTS  {3}
    --CATEGORY   "Error Alarms"
    --STATE      FAILED 
    --STATUS     MANDATORY     
    ::= { processorEvents 4 }

processorFRB3Event                          NOTIFICATION-TYPE
    OBJECTS { 
        eventDescription,
        processorStatus, 
        processorDescription, 
        processorCIMDeviceId 
    }
    STATUS      current
    DESCRIPTION "The processor experienced an FRB3 error, initialization failure."
    --Novell NMS trap annotation
    --TYPE       "Server Processor FRB3 Error"
    --SEVERITY   CRITICAL 
    --SUMMARY    "Processor %s experienced an FRB3 error, initialization failure."
    --ARGUMENTS  {3}
    --CATEGORY   "Error Alarms"
    --STATE      FAILED 
    --STATUS     MANDATORY     
    ::= { processorEvents 5 }

processorConfigurationErrorEvent            NOTIFICATION-TYPE
    OBJECTS { 
        eventDescription,
        processorStatus, 
        processorDescription, 
        processorCIMDeviceId 
    }
    STATUS      current
    DESCRIPTION "The processor experienced a configuration error."
    --Novell NMS trap annotation
    --TYPE       "Server Processor Configuration Error"
    --SEVERITY   CRITICAL 
    --SUMMARY    "Processor %s experienced a configuration error."
    --ARGUMENTS  {3}
    --CATEGORY   "Error Alarms"
    --STATE      FAILED 
    --STATUS     MANDATORY     
    ::= { processorEvents 6 }

processorPresenceEvent                      NOTIFICATION-TYPE
    OBJECTS { 
        eventDescription,
        processorStatus, 
        processorDescription, 
        processorCIMDeviceId 
    }
    STATUS      current
    DESCRIPTION "The processor presence has been detected."
    --Novell NMS trap annotation
    --TYPE       "Server Processor Detected"
    --SEVERITY   INFORMATIONAL  
    --SUMMARY    "Processor %s has been detected."
    --ARGUMENTS  {3}
    --CATEGORY   "Error Alarms"
    --STATE      OPERATIONAL
    --STATUS     MANDATORY     
    ::= { processorEvents 7 }

processorDisabledEvent                      NOTIFICATION-TYPE
    OBJECTS { 
        eventDescription,
        processorStatus, 
        processorDescription, 
        processorCIMDeviceId 
    }
    STATUS      current
    DESCRIPTION "The processor has been disabled."
    --Novell NMS trap annotation
    --TYPE       "Server Processor Disabled"
    --SEVERITY   CRITICAL 
    --SUMMARY    "Processor %s has been disabled."
    --ARGUMENTS  {3}
    --CATEGORY   "Error Alarms"
    --STATE      FAILED 
    --STATUS     MANDATORY     
    ::= { processorEvents 8 }

processorTerminatorEvent                    NOTIFICATION-TYPE
    OBJECTS { 
        eventDescription,
        processorStatus, 
        processorDescription, 
        processorCIMDeviceId 
    }
    STATUS      current
    DESCRIPTION "The processor terminator has been detected."
    --Novell NMS trap annotation
    --TYPE       "Server Processor Terminator Detected"
    --SEVERITY   INFORMATIONAL 
    --SUMMARY    "Processor %s terminator has been detected."
    --ARGUMENTS  {3}
    --CATEGORY   "Error Alarms"
    --STATE      OPERATIONAL
    --STATUS     MANDATORY     
    ::= { processorEvents 9 }

processorSMBIOSUncorrectableCPUEvent        NOTIFICATION-TYPE
    OBJECTS { 
        eventDescription,
        processorStatus, 
        processorDescription, 
        processorCIMDeviceId 
    }
    STATUS      current
    DESCRIPTION "The processor has encountered an SMBIOS Uncorrectable CPU-Complex error."
    --Novell NMS trap annotation
    --TYPE       "Server Processor SMBIOS Error"
    --SEVERITY   CRITICAL 
    --SUMMARY    "Processor %s has encountered an SMBIOS uncorrectable CPU-complex error."
    --ARGUMENTS  {3}
    --CATEGORY   "Error Alarms"
    --STATE      FAILED 
    --STATUS     MANDATORY         
    ::= { processorEvents 10 }

-------------------------------------------------------------------------------
-- Power Events -  Power Unit Redundancy Events
-------------------------------------------------------------------------------
powerUnitFullyRedundantEvent                NOTIFICATION-TYPE
    OBJECTS { 
        eventDescription,
        powerUnitStatus, 
        powerUnitDescription, 
        powerUnitCIMDeviceId 
    }
    STATUS      current
    DESCRIPTION "The power supply unit is fully redundant."
    --Novell NMS trap annotation
    --TYPE       "Server Power Unit Redundancy Normal"
    --SEVERITY   INFORMATIONAL 
    --SUMMARY    "The power unit is fully redundant."
    --CATEGORY   "Error Alarms"
    --STATE      OPERATIONAL
    --STATUS     OPTIONAL    
    ::= { powerEvents 1}

powerUnitRedundancyDegradedEvent            NOTIFICATION-TYPE
    OBJECTS {
        eventDescription,
        powerUnitStatus, 
        powerUnitDescription, 
        powerUnitCIMDeviceId 
    }  
    STATUS      current
    DESCRIPTION "The power supply unit redundancy has been degraded."
    --Novell NMS trap annotation
    --TYPE       "Server Power Unit Redundancy Degraded"
    --SEVERITY    MINOR 
    --SUMMARY    "The power unit redundancy has degraded."
    --CATEGORY   "Error Alarms"
    --STATE      DEGRADED 
    --STATUS     OPTIONAL    
    ::= { powerEvents 2 }

powerUnitRedundancyLostEvent                NOTIFICATION-TYPE
    OBJECTS { 
        eventDescription,
        powerUnitStatus, 
        powerUnitDescription, 
        powerUnitCIMDeviceId 
    }
    STATUS      current
    DESCRIPTION "The power supply unit redundancy has been lost."
    --Novell NMS trap annotation
    --TYPE       "Server Power Unit Redundancy Lost"
    --SEVERITY   MAJOR  
    --SUMMARY    "The power unit redundancy has been lost."
    --CATEGORY   "Error Alarms"
    --STATE      DEGRADED 
    --STATUS     OPTIONAL    
    ::= { powerEvents 3 }

-------------------------------------------------------------------------------
-- Power Events -  Power Supply Events
-------------------------------------------------------------------------------
powerSupplyPresentEvent                     NOTIFICATION-TYPE
    OBJECTS { 
        eventDescription,
        powerSupplyStatus, 
        powerSupplyDescription, 
        powerSupplyCIMDeviceId 
    }
    STATUS      current
    DESCRIPTION "The power supply presence has been detected."
    --Novell NMS trap annotation
    --TYPE       "Server Power Supply Detected"
    --SEVERITY   INFORMATIONAL 
    --SUMMARY    "The power supply %s has been detected."
    --ARGUMENTS  {3}
    --CATEGORY   "Error Alarms"
    --STATE      OPERATIONAL
    --STATUS     MANDATORY     
    ::= { powerEvents 4 }

powerSupplyRemovalEvent                     NOTIFICATION-TYPE
    OBJECTS { 
        eventDescription,
        powerSupplyStatus, 
        powerSupplyDescription, 
        powerSupplyCIMDeviceId 
    }
    STATUS      current
    DESCRIPTION "The power supply is no longer detected as present."
    --Novell NMS trap annotation
    --TYPE       "Server Power Supply Removed"
    --SEVERITY   INFORMATIONAL 
    --SUMMARY    "The power supply %s has been removed."
    --ARGUMENTS  {3}
    --CATEGORY   "Error Alarms"
    --STATE      DEGRADED 
    --STATUS     MANDATORY     
    ::= { powerEvents 5 }

powerSupplyFailureEvent                     NOTIFICATION-TYPE
    OBJECTS { 
        eventDescription,
        powerSupplyStatus, 
        powerSupplyDescription, 
        powerSupplyCIMDeviceId 
    }
    STATUS      current
    DESCRIPTION "The power supply has failed."
    --Novell NMS trap annotation
    --TYPE       "Server Power Supply Failed"
    --SEVERITY   CRITICAL 
    --SUMMARY    "The power supply %s has failed."
    --ARGUMENTS  {3}
    --CATEGORY   "Error Alarms"
    --STATE      DEGRADED 
    --STATUS     MANDATORY     
    ::= { powerEvents 6 }

powerSupplyPredictedFailureEvent            NOTIFICATION-TYPE
    OBJECTS { 
        eventDescription,
        powerSupplyStatus, 
        powerSupplyDescription, 
        powerSupplyCIMDeviceId 
    }
    STATUS      current
    DESCRIPTION "Failure of this power supply has been predicted."
    --Novell NMS trap annotation
    --TYPE       "Server Power Supply Failure Predicted"
    --SEVERITY   MINOR 
    --SUMMARY    "A failure has been predicted for power supply %d %s"
    --ARGUMENTS  {1,2}
    --CATEGORY   "Error Alarms"
    --STATE      DEGRADED 
    --STATUS     MANDATORY 
    ::= { powerEvents 7 }

powerSupplyACLostEvent                      NOTIFICATION-TYPE
    OBJECTS { 
        eventDescription,
        powerSupplyStatus, 
        powerSupplyDescription, 
        powerSupplyCIMDeviceId 
    }
    STATUS      current
    DESCRIPTION "The power supply A/C connection has been lost."
    --Novell NMS trap annotation
    --TYPE       "Server Power Supply AC Connection Lost"
    --SEVERITY   MAJOR 
    --SUMMARY    "The power supply %s has lost the AC connection."
    --ARGUMENTS  {3}
    --CATEGORY   "Error Alarms"
    --STATE      DEGRADED 
    --STATUS     MANDATORY 
    ::= { powerEvents 8 }

powerSupplyACOKEvent                        NOTIFICATION-TYPE
    OBJECTS { 
        eventDescription,
        powerSupplyStatus, 
        powerSupplyDescription, 
        powerSupplyCIMDeviceId 
    }
    STATUS      current
    DESCRIPTION "The power supply A/C connection is now OK."
    --Novell NMS trap annotation
    --TYPE       "Server Power Supply AC Connection OK"
    --SEVERITY   INFORMATIONAL 
    --SUMMARY    "The power supply %s AC connection is OK."
    --ARGUMENTS  {3}
    --CATEGORY   "Error Alarms"
    --STATE      OPERATIONAL
    --STATUS     MANDATORY 
    ::= { powerEvents 9 }

-------------------------------------------------------------------------------
-- Power Events - Voltage Events
-------------------------------------------------------------------------------
voltageLowerNonRecoverableEvent             NOTIFICATION-TYPE
    OBJECTS { 
        eventDescription,
        voltageStatus, 
        voltageDescription, 
        voltageCIMDeviceId 
    }
    STATUS      current
    DESCRIPTION "Current reading is below lower non-recoverable threshold.  Status for 
this sensor is non-recoverable."
    --Novell NMS trap annotation
    --TYPE       "Server Voltage Non-Recoverable"
    --SEVERITY   CRITICAL 
    --SUMMARY    "The voltage probe %s is below lower non-recoverable threshold."
    --ARGUMENTS  {3}
    --CATEGORY   "Threshold Alarms"
    --STATE      DEGRADED 
    --STATUS     MANDATORY     
    ::= { powerEvents 10 }

voltageLowerCriticalEvent                   NOTIFICATION-TYPE
    OBJECTS { 
        eventDescription,
        voltageStatus, 
        voltageDescription, 
        voltageCIMDeviceId 
    }
    STATUS      current
    DESCRIPTION "Current reading is below lower critical threshold. Status for this
sensor is critical."
    --Novell NMS trap annotation
    --TYPE       "Server Voltage Critical"
    --SEVERITY   CRITICAL 
    --SUMMARY    "The voltage probe %s is below lower critical threshold."
    --ARGUMENTS  {3}
    --CATEGORY   "Threshold Alarms"
    --STATE      DEGRADED 
    --STATUS     MANDATORY 
    ::= { powerEvents 11 }

voltageLowerNonCriticalEvent                NOTIFICATION-TYPE
    OBJECTS { 
        eventDescription,
        voltageStatus, 
        voltageDescription, 
        voltageCIMDeviceId
    }
    STATUS      current
    DESCRIPTION "Curret reading is below lower non-critical threshold.  Status for this
sensor is non-critical."
    --Novell NMS trap annotation
    --TYPE       "Server Voltage Non-Critical"
    --SEVERITY   MINOR 
    --SUMMARY    "The voltage probe %s is below lower non-critical threshold."
    --ARGUMENTS  {3}
    --CATEGORY   "Threshold Alarms"
    --STATE      DEGRADED 
    --STATUS     MANDATORY   
    ::= { powerEvents 12 }

voltageOKEvent                              NOTIFICATION-TYPE
    OBJECTS { 
        eventDescription,
        voltageStatus, 
        voltageDescription, 
        voltageCIMDeviceId
    }
    STATUS      current
    DESCRIPTION "Current reading is within normal thresholds, status is OK."
    --Novell NMS trap annotation
    --TYPE       "Server Voltage OK"
    --SEVERITY   INFORMATIONAL 
    --SUMMARY    "The voltage probe %s is OK."
    --ARGUMENTS  {3}
    --CATEGORY   "Threshold Alarms"
    --STATE      OPERATIONAL
    --STATUS     MANDATORY   
    ::= { powerEvents 13 }

voltageUpperNonCriticalEvent                NOTIFICATION-TYPE
    OBJECTS { 
        eventDescription,
        voltageStatus, 
        voltageDescription, 
        voltageCIMDeviceId 
    }
    STATUS      current
    DESCRIPTION "Current reading exceeds upper non-critical threshold. Status for this 
sensor is non-critical."
    --Novell NMS trap annotation
    --TYPE       "Server Voltage Upper Non-Critical"
    --SEVERITY   MINOR 
    --SUMMARY    "The voltage probe %s exceeded upper non-critical threshold."
    --ARGUMENTS  {3}
    --CATEGORY   "Threshold Alarms"
    --STATE      DEGRADED 
    --STATUS     MANDATORY     
    ::= { powerEvents 14 }

voltageUpperCriticalEvent                   NOTIFICATION-TYPE
    OBJECTS { 
        eventDescription,
        voltageStatus, 
        voltageDescription, 
        voltageCIMDeviceId
    }
    STATUS      current
    DESCRIPTION "Current reading exceeds upper critical threshold. Status for this 
sensor is critical."
    --Novell NMS trap annotation
    --TYPE       "Server Voltage Upper Critical"
    --SEVERITY   CRITICAL 
    --SUMMARY    "The voltage probe %s excees upper critical threshold."
    --ARGUMENTS  {3}
    --CATEGORY   "Threshold Alarms"
    --STATE      FAILED  
    --STATUS     MANDATORY     
    ::= { powerEvents 15 }
    
voltageUpperNonRecoverableEvent             NOTIFICATION-TYPE
    OBJECTS { 
        eventDescription,
        voltageStatus, 
        voltageDescription, 
        voltageCIMDeviceId 
    }
    STATUS      current
    DESCRIPTION "Current reading exceeds upper non-recoverable threshold.  Status for this
sensor is non-recoverable."
    --Novell NMS trap annotation
    --TYPE       "Server Voltage Upper Non-Recoverable"
    --SEVERITY   CRITICAL 
    --SUMMARY    "Voltage probe %s exceeds upper non-recoverable threshold."
    --ARGUMENTS  {3}
    --CATEGORY   "Threshold Alarms"
    --STATE      FAILED 
    --STATUS     OPTIONAL    
    ::= { powerEvents 16 }

-------------------------------------------------------------------------------
-- Power Events - Discrete Voltage Events
-------------------------------------------------------------------------------
discreteVoltagePerformanceMetEvent          NOTIFICATION-TYPE
    OBJECTS { 
        eventDescription,
        discreteVoltageStatus, 
        discreteVoltageDescription, 
        discreteVoltageCIMDeviceId
    }
    STATUS      current
    DESCRIPTION "The discrete voltage sensor meets performance standards."
    --Novell NMS trap annotation
    --TYPE       "Server Discrete Voltage OK"
    --SEVERITY   INFORMATIONAL 
    --SUMMARY    "Discrete voltage probe %s performance met."
    --ARGUMENTS  {3}
    --CATEGORY   "Threshold Alarms"
    --STATE      OPERATIONAL
    --STATUS     MANDATORY  
    ::= { powerEvents 17 }

discreteVoltagePerformanceLagsEvent         NOTIFICATION-TYPE
    OBJECTS { 
        eventDescription,
        discreteVoltageStatus, 
        discreteVoltageDescription, 
        discreteVoltageCIMDeviceId
    }
    STATUS      current
    DESCRIPTION "The discrete voltage sensor lags from performance standards."
    --Novell NMS trap annotation
    --TYPE       "Server Discrete Voltage Probe Critical"
    --SEVERITY   CRITICAL 
    --SUMMARY    "Discrete voltage probe %s performance lags."
    --ARGUMENTS  {3}
    --CATEGORY   "Threshold Alarms"
    --STATE      FAILED 
    --STATUS     MANDATORY        
    ::= { powerEvents 18 }

-------------------------------------------------------------------------------
-- Memory Events 
-------------------------------------------------------------------------------
memorySingleBitErrorEvent                   NOTIFICATION-TYPE
    OBJECTS { 
        eventDescription, 
        physicalMemoryDeviceStatus,
        physicalMemoryDeviceDescription,
        physicalMemoryDeviceCIMDeviceId
    }
    STATUS      current
    DESCRIPTION "A single bit error occured in memory."
    --Novell NMS trap annotation
    --TYPE       "Server Single Bit Memory Error"
    --SEVERITY   MINOR 
    --SUMMARY    "Memory device %s experienced a single bit memory error."
    --ARGUMENTS  {3}
    --CATEGORY   "Error Alarms"
    --STATE      DEGRADED 
    --STATUS     MANDATORY     
    ::= { memoryEvents 1 }

memoryMultiBitErrorEvent                    NOTIFICATION-TYPE
    OBJECTS { 
        eventDescription, 
        physicalMemoryDeviceStatus,
        physicalMemoryDeviceDescription,
        physicalMemoryDeviceCIMDeviceId
    }
    STATUS      current
    DESCRIPTION "A multi-bit error occured in memory."
    --Novell NMS trap annotation
    --TYPE       "Server Multi-Bit Memory Error"
    --SEVERITY   MAJOR 
    --SUMMARY    "Memory device %s experienced a multi-bit memory error."
    --ARGUMENTS  {3}
    --CATEGORY   "Error Alarms"
    --STATE      DEGRADED 
    --STATUS     MANDATORY     
    ::= { memoryEvents 2 }

memoryParityErrorEvent                      NOTIFICATION-TYPE
    OBJECTS { 
        eventDescription, 
        physicalMemoryDeviceStatus,
        physicalMemoryDeviceDescription,
        physicalMemoryDeviceCIMDeviceId
    }
    STATUS      current
    DESCRIPTION "A parity error occured in memory."
    --Novell NMS trap annotation
    --TYPE       "Server Parity Memory Error"
    --SEVERITY   MAJOR 
    --SUMMARY    "Memory device %s experienced a parity error."
    --ARGUMENTS  {3}
    --CATEGORY   "Error Alarms"
    --STATE      DEGRADED 
    --STATUS     MANDATORY     
    ::= { memoryEvents 3 }

memoryScrubFailedEvent                      NOTIFICATION-TYPE
    OBJECTS { 
        eventDescription, 
        physicalMemoryDeviceStatus,
        physicalMemoryDeviceDescription,
        physicalMemoryDeviceCIMDeviceId
    }
    STATUS      current
    DESCRIPTION "Memory scrub failed (stuck bit) error occured in memory."
    --Novell NMS trap annotation
    --TYPE       "Server Memory Scrub Failed Error"
    --SEVERITY   MAJOR 
    --SUMMARY    "Memory device %s experienced a scrub failure (stuck bit) error."
    --ARGUMENTS  {3}
    --CATEGORY   "Error Alarms"
    --STATE      DEGRADED 
    --STATUS     MANDATORY     
    ::= { memoryEvents 4 }

memoryDeviceDisabledEvent                   NOTIFICATION-TYPE
    OBJECTS { 
        eventDescription, 
        physicalMemoryDeviceStatus,
        physicalMemoryDeviceDescription,
        physicalMemoryDeviceCIMDeviceId
    }
    STATUS      current
    DESCRIPTION "Memory device was disabled."
    --Novell NMS trap annotation
    --TYPE       "Memory Device Disabled"
    --SEVERITY   MAJOR 
    --SUMMARY    "Memory device %s was disabled."
    --ARGUMENTS  {3}
    --CATEGORY   "Error Alarms"
    --STATE      DEGRADED 
    --STATUS     MANDATORY     
    ::= { memoryEvents 5 }

memoryCorrectableErrorLimitReachedEvent     NOTIFICATION-TYPE
    OBJECTS { 
        eventDescription, 
        physicalMemoryDeviceStatus,
        physicalMemoryDeviceDescription,
        physicalMemoryDeviceCIMDeviceId
    }
    STATUS      current
    DESCRIPTION "Correctable error logging limit reached for memory device."
    --Novell NMS trap annotation
    --TYPE       "Memory Correctable Error Limit Reached"
    --SEVERITY   MAJOR 
    --SUMMARY    "Memory device %s correctable error logging limit reached."
    --ARGUMENTS  {3}
    --CATEGORY   "Error Alarms"
    --STATE      DEGRADED 
    --STATUS     MANDATORY     
    ::= { memoryEvents 6 }

-------------------------------------------------------------------------------
-- Thermal Events - Cooling Unit Events
-------------------------------------------------------------------------------
coolingUnitFullyRedundantEvent              NOTIFICATION-TYPE
    OBJECTS {
        eventDescription,
        coolingUnitStatus,
        coolingUnitDescription,
        coolingUnitCIMDeviceId
    }
    STATUS      current
    DESCRIPTION "Cooling Unit is fully redundany."
    --Novell NMS trap annotation
    --TYPE       "Server Cooling Unit Redundancy Normal"
    --SEVERITY   INFORMATIONAL 
    --SUMMARY    "The cooling unit is fully redundant."
    --CATEGORY   "Threshold Alarms"
    --STATE      OPERATIONAL
    --STATUS      OPTIONAL    
    ::= { thermalEvents 1 }

coolingUnitRedundancyDegradedEvent          NOTIFICATION-TYPE
    OBJECTS {
        eventDescription,
        coolingUnitStatus,
        coolingUnitDescription,
        coolingUnitCIMDeviceId
    }  
    STATUS      current
    DESCRIPTION "Cooling Unit redundancy has been degraded."
    --Novell NMS trap annotation
    --TYPE       "Cooling Unit "
    --SEVERITY   MINOR 
    --SUMMARY    "The cooling unit redundancy has degraded."
    --CATEGORY   "Threshold Alarms"
    --STATE      DEGRADED 
    --STATUS     OPTIONAL    
    ::= { thermalEvents 2 }

coolingUnitRedundancyLostEvent              NOTIFICATION-TYPE
    OBJECTS {
        eventDescription,
        coolingUnitStatus,
        coolingUnitDescription,
        coolingUnitCIMDeviceId
    }  
    STATUS      current
    DESCRIPTION "Cooling Unit redundancy has been lost."
    --Novell NMS trap annotation
    --TYPE       "Server Cooling Unit Redundancy Lost"
    --SEVERITY   MAJOR  
    --SUMMARY    "The cooling unit redundancy has been lost."
    --CATEGORY   "Threshold Alarms"
    --STATE      DEGRADED 
    --STATUS     OPTIONAL    
    ::= { thermalEvents 3 }

-------------------------------------------------------------------------------
-- Thermal Events - Cooling Device Events
-------------------------------------------------------------------------------
coolingDeviceLowerNonRecoverableEvent       NOTIFICATION-TYPE
    OBJECTS { 
        eventDescription,
        coolingDeviceStatus,
        coolingDeviceDescription,
        coolingDeviceCIMDeviceId
    }
    STATUS      current
    DESCRIPTION "Current reading is below lower non-recoverable threshold.  Status for 
this sensor is non-recoverable."
    --Novell NMS trap annotation
    --TYPE       "Server Cooling Device Lower Non-Recoverable"
    --SEVERITY   CRITICAL 
    --SUMMARY    "Cooling device %s is below lower non-recoverable threshold."
    --ARGUMENTS  {3}
    --CATEGORY   "Threshold Alarms"
    --STATE      FAILED 
    --STATUS     OPTIONAL    
    ::= { thermalEvents 4 }

coolingDeviceLowerCriticalEvent             NOTIFICATION-TYPE
    OBJECTS { 
        eventDescription,
        coolingDeviceStatus,
        coolingDeviceDescription,
        coolingDeviceCIMDeviceId
    }
    STATUS      current
    DESCRIPTION "Current reading is below lower critical threshold. Status for this
sensor is critical."
    --Novell NMS trap annotation
    --TYPE       "Server Cooling Device Critical"
    --SEVERITY   CRITICAL 
    --SUMMARY    "Cooling device %s is below lowre critical threshold."
    --ARGUMENTS  {3}
    --CATEGORY   "Threshold Alarms"
    --STATE      FAILED 
    --STATUS     MANDATORY     
    ::= { thermalEvents 5 }

coolingDeviceLowerNonCriticalEvent          NOTIFICATION-TYPE
    OBJECTS { 
        eventDescription,
        coolingDeviceStatus,
        coolingDeviceDescription,
        coolingDeviceCIMDeviceId
    }
    STATUS      current
    DESCRIPTION "Curret reading is below lower non-critical threshold.  Status for this
sensor is non-critical."
    --Novell NMS trap annotation
    --TYPE       "Server Cooling Device Lower Non-Critical"
    --SEVERITY   MINOR  
    --SUMMARY    "Cooling device %s is below lower non-critical threshold."
    --ARGUMENTS  {3}
    --CATEGORY   "Threshold Alarms"
    --STATE      DEGRADED 
    --STATUS     MANDATORY     
    ::= { thermalEvents 6 }

coolingDeviceOKEvent                        NOTIFICATION-TYPE
    OBJECTS { 
        eventDescription,
        coolingDeviceStatus,
        coolingDeviceDescription,
        coolingDeviceCIMDeviceId
    }
    STATUS      current
    DESCRIPTION "Current reading is within normal thresholds, status is OK."
    --Novell NMS trap annotation
    --TYPE       "Server Cooling Device OK"
    --SEVERITY   INFORMATIONAL  
    --SUMMARY    "Cooling device %s is OK"
    --ARGUMENTS  {3}
    --CATEGORY   "Threshold Alarms"
    --STATE      OPERATIONAL
    --STATUS     MANDATORY     
    ::= { thermalEvents 7 }

coolingDeviceUpperNonCriticalEvent          NOTIFICATION-TYPE
    OBJECTS { 
        eventDescription,
        coolingDeviceStatus,
        coolingDeviceDescription,
        coolingDeviceCIMDeviceId
    }
    STATUS      current
    DESCRIPTION "Current reading exceeds upper non-critical threshold. Status for this 
sensor is non-critical."
    --Novell NMS trap annotation
    --TYPE       "Server Cooling Device "
    --SEVERITY   MINOR 
    --SUMMARY    "Cooling device %s exceeds upper non-critical threshold."
    --ARGUMENTS  {3}
    --CATEGORY   "Threshold Alarms"
    --STATE      DEGRADED 
    --STATUS     MANDATORY     
    ::= { thermalEvents 8 }

coolingDeviceUpperCriticalEvent             NOTIFICATION-TYPE
    OBJECTS { 
        eventDescription,
        coolingDeviceStatus,
        coolingDeviceDescription,
        coolingDeviceCIMDeviceId
    }
    STATUS      current
    DESCRIPTION "Current reading exceeds upper critical threshold. Status for this 
sensor is critical."
    --Novell NMS trap annotation
    --TYPE       "Server Cooling Device Upper Critical"
    --SEVERITY   CRITICAL 
    --SUMMARY    "Cooling device %s exceeds upper critical threshold."
    --ARGUMENTS  {3}
    --CATEGORY   "Threshold Alarms"
    --STATE      FAILED 
    --STATUS     MANDATORY    
    ::= { thermalEvents 9 }
    
coolingDeviceUpperNonRecoverableEvent       NOTIFICATION-TYPE
    OBJECTS { 
        eventDescription,
        coolingDeviceStatus,
        coolingDeviceDescription,
        coolingDeviceCIMDeviceId
    }
    STATUS      current
    DESCRIPTION "Current reading exceeds upper non-recoverable threshold.  Status for this
sensor is non-recoverable."
    --Novell NMS trap annotation
    --TYPE       "Server Cooling Upper Non-Recoverable"
    --SEVERITY   CRITICAL 
    --SUMMARY    "Cooling device %s exceeded upper non-recoverable threshold."
    --ARGUMENTS  {3}
    --CATEGORY   "Threshold Alarms"
    --STATE      FAILED  
    --STATUS     OPTIONAL    
    ::= { thermalEvents 10 }

-------------------------------------------------------------------------------
-- Thermal Events - Discrete Cooling Device Events
-------------------------------------------------------------------------------
discreteCoolingDevicePerformanceMetEvent    NOTIFICATION-TYPE
    OBJECTS { 
        eventDescription,
        discreteCoolingDeviceStatus,
        discreteCoolingDeviceDescription,
        discreteCoolingDeviceCIMDeviceId
    }
    STATUS      current
    DESCRIPTION "The discrete cooling device meets performance standards."
    --Novell NMS trap annotation
    --TYPE       "Server Discrete Cooling Device OK"
    --SEVERITY   INFORMATIONAL 
    --SUMMARY    "Discrete cooling device %s performance met."
    --ARGUMENTS  {3}
    --CATEGORY   "Threshold Alarms"
    --STATE      OPERATIONAL
    --STATUS     MANDATORY     
    ::= { thermalEvents 11 }

discreteCoolingDevicePerformanceLagsEvent   NOTIFICATION-TYPE
    OBJECTS { 
        eventDescription,
        discreteCoolingDeviceStatus,
        discreteCoolingDeviceDescription,
        discreteCoolingDeviceCIMDeviceId
    }
    STATUS      current
    DESCRIPTION "The discrete cooling device lags from performance standards."
    --Novell NMS trap annotation
    --TYPE       "Server Discrete Cooling Device Critical"
    --SEVERITY   CRITICAL 
    --SUMMARY    "Discrete cooling device %s performance lags."
    --ARGUMENTS  {3}
    --CATEGORY   "Threshold Alarms"
    --STATE      FAILED  
    --STATUS     MANDATORY     
    ::= { thermalEvents 12 }

-------------------------------------------------------------------------------
-- Thermal Events - Temperature Probe Events
-------------------------------------------------------------------------------
temperatureLowerNonRecoverableEvent         NOTIFICATION-TYPE
    OBJECTS { 
        eventDescription,
        temperatureStatus,
        temperatureDescription,
        temperatureCIMDeviceId
    }
    STATUS      current
    DESCRIPTION "Current reading is below lower non-recoverable threshold.  Status for 
this sensor is non-recoverable."
    --Novell NMS trap annotation
    --TYPE       "Server Temperature Lower Non-Recoverable"
    --SEVERITY   CRITICAL 
    --SUMMARY    "Temperature %s is below lower non-recoverable threshold."
    --ARGUMENTS  {3}
    --CATEGORY   "Threshold Alarms"
    --STATE      FAILED 
    --STATUS     OPTIONAL    
    ::= { thermalEvents 13 }

temperatureLowerCriticalEvent               NOTIFICATION-TYPE
    OBJECTS { 
        eventDescription,
        temperatureStatus,
        temperatureDescription,
        temperatureCIMDeviceId
    }
    STATUS      current
    DESCRIPTION "Current reading is below lower critical threshold. Status for this
sensor is critical."
    --Novell NMS trap annotation
    --TYPE       "Server Temperature Lower Critical"
    --SEVERITY   CRITICAL 
    --SUMMARY    "Temperature probe %s is below lower critical threshold."
    --ARGUMENTS  {3}
    --CATEGORY   "Threshold Alarms"
    --STATE      FAILED 
    --STATUS     MANDATORY     
    ::= { thermalEvents 14 }

temperatureLowerNonCriticalEvent            NOTIFICATION-TYPE
    OBJECTS { 
        eventDescription,
        temperatureStatus,
        temperatureDescription,
        temperatureCIMDeviceId
    }
    STATUS      current
    DESCRIPTION "Curret reading is below lower non-critical threshold.  Status for this
sensor is non-critical."
    --Novell NMS trap annotation
    --TYPE       "Server Temperature Lower Non-Critical"
    --SEVERITY   MINOR  
    --SUMMARY    "Temperature probe %s is below lower non-critical threshold."
    --ARGUMENTS  {3}
    --CATEGORY   "Threshold Alarms"
    --STATE      DEGRADED 
    --STATUS     MANDATORY     
    ::= { thermalEvents 15 }

temperatureOKEvent                          NOTIFICATION-TYPE
    OBJECTS { 
        eventDescription,
        temperatureStatus,
        temperatureDescription,
        temperatureCIMDeviceId
    }
    STATUS      current
    DESCRIPTION "Current reading is within normal thresholds, status is OK."
    --Novell NMS trap annotation
    --TYPE       "Server Temperature OK"
    --SEVERITY   INFORMATIONAL 
    --SUMMARY    "Temperature probe %s is OK."
    --ARGUMENTS  {3}
    --CATEGORY   "Threshold Alarms"
    --STATE      OPERATIONAL
    --STATUS     MANDATORY     
    ::= { thermalEvents 16 }

temperatureUpperNonCriticalEvent            NOTIFICATION-TYPE
    OBJECTS { 
        eventDescription,
        temperatureStatus,
        temperatureDescription,
        temperatureCIMDeviceId
    }
    STATUS      current
    DESCRIPTION "Current reading exceeds upper non-critical threshold. Status for this 
sensor is non-critical."
    --Novell NMS trap annotation
    --TYPE       "Server Temperature Upper Non-Critical"
    --SEVERITY   MINOR 
    --SUMMARY    "Temperature probe %s exceeded upper non-critical threshold."
    --ARGUMENTS  {3}
    --CATEGORY   "Threshold Alarms"
    --STATE      DEGRADED 
    --STATUS     MANDATORY     
    ::= { thermalEvents 17 }

temperatureUpperCriticalEvent               NOTIFICATION-TYPE
    OBJECTS { 
        eventDescription,
        temperatureStatus,
        temperatureDescription,
        temperatureCIMDeviceId
    }
    STATUS      current
    DESCRIPTION "Current reading exceeds upper critical threshold. Status for this 
sensor is critical."
    --Novell NMS trap annotation
    --TYPE       "Server Temperature Upper Critical"
    --SEVERITY   CRITICAL 
    --SUMMARY    "Temperature probe %s exceeded upper critical threshold."
    --ARGUMENTS  {3}
    --CATEGORY   "Threshold Alarms"
    --STATE      FAILED 
    --STATUS     MANDATORY     
    ::= { thermalEvents 18 }
    
temperatureUpperNonRecoverableEvent         NOTIFICATION-TYPE
    OBJECTS { 
        eventDescription,
        temperatureStatus,
        temperatureDescription,
        temperatureCIMDeviceId
    }
    STATUS      current
    DESCRIPTION "Current reading exceeds upper non-recoverable threshold.  Status for this
sensor is non-recoverable."
    --Novell NMS trap annotation
    --TYPE       "Server Temperature Upper Non-Recoverable"
    --SEVERITY   CRITICAL 
    --SUMMARY    "Temperature probe %s exceeds upper non-recoverable threshold."
    --ARGUMENTS  {3}
    --CATEGORY   "Threshold Alarms"
    --STATE      FAILED 
    --STATUS     OPTIONAL   
    ::= { thermalEvents 19 }

-------------------------------------------------------------------------------
-- Slot Events
-------------------------------------------------------------------------------
slotOKEvent                                 NOTIFICATION-TYPE
    OBJECTS { 
        eventDescription,
        eventSeverity, 
        eventSlotDescription,
        eventSlotCIMDeviceId
    }
    STATUS      current
    DESCRIPTION "The slot is OK."
    --Novell NMS trap annotation
    --TYPE       "Server Slot OK"
    --SEVERITY   INFORMATIONAL 
    --SUMMARY    "Slot %d is now OK."
    --ARGUMENTS  {4}
    --CATEGORY   "Error Alarms"
    --STATE      OPERATIONAL
    --STATUS     MANDATORY     
    ::= { slotEvents 1 }

slotFaultAssertedEvent                      NOTIFICATION-TYPE
    OBJECTS { 
        eventDescription,
        eventSeverity, 
        eventSlotDescription,
        eventSlotCIMDeviceId
    }
    STATUS      current
    DESCRIPTION "A fault has been detected on the slot."
    --Novell NMS trap annotation
    --TYPE       "Server Slot Faulted"
    --SEVERITY   MAJOR 
    --SUMMARY    "Slot %d has experienced a fault."
    --ARGUMENTS  {4}
    --CATEGORY   "Error Alarms"
    --STATE      FAILED 
    --STATUS     MANDATORY     
    ::= { slotEvents 2 }

slotPowerIsOffEvent                         NOTIFICATION-TYPE
    OBJECTS { 
        eventDescription,
        eventSeverity,
        eventSlotDescription, 
        eventSlotCIMDeviceId
    }
    STATUS      current
    DESCRIPTION "The slot is powered OFF."
    --Novell NMS trap annotation
    --TYPE       "Server Slot Powered OFF"
    --SEVERITY   INFORMATIONAL 
    --SUMMARY    "Slot %d is now powered OFF."
    --ARGUMENTS  {4}
    --CATEGORY   "Error Alarms"
    --STATE      OPERATIONAL
    --STATUS     MANDATORY     
    ::= { slotEvents 3 }

slotPowerIsOnEvent                          NOTIFICATION-TYPE
    OBJECTS { 
        eventDescription,
        eventSeverity,
        eventSlotDescription, 
        eventSlotCIMDeviceId
    }
    STATUS      current
    DESCRIPTION "Server slot powered ON."
    --Novell NMS trap annotation
    --TYPE       "Server Slot Powered ON"
    --SEVERITY   INFORMATIONAL 
    --SUMMARY    "Slot %d is now powered ON."
    --ARGUMENTS  {4}
    --CATEGORY   "Error Alarms"
    --STATE      OPERATIONAL
    --STATUS     MANDATORY     
    ::= { slotEvents 4 }

-------------------------------------------------------------------------------
-- System Events 
-------------------------------------------------------------------------------
systemReconfiguredEvent                     NOTIFICATION-TYPE
    OBJECTS { 
        eventDescription,
        eventSeverity
    }
    STATUS      current
    DESCRIPTION "The system BIOS has been reconfigured."
    --Novell NMS trap annotation
    --TYPE       "System BIOS reconfigured"
    --SEVERITY   INFORMATIONAL 
    --SUMMARY    "The system BIOS has been reconfigured."
    --CATEGORY   "LOGONLY"
    --STATE      OPERATIONAL
    --STATUS     MANDATORY 
    ::= { systemEvents 1 }

systemBootEvent                             NOTIFICATION-TYPE
    OBJECTS { 
        eventDescription, 
        eventSeverity
    }
    STATUS      current
    DESCRIPTION "The system has booted."
    --Novell NMS trap annotation
    --TYPE       "System boot event"
    --SEVERITY   INFORMATIONAL 
    --SUMMARY    "The system has booted."
    --CATEGORY   "LOGONLY"
    --STATE      OPERATIONAL
    --STATUS     MANDATORY 
    ::= { systemEvents 2 }

systemUndeterminedHardwareFailureEvent      NOTIFICATION-TYPE
    OBJECTS { 
        eventDescription,
        eventSeverity
    }
    STATUS      current
    DESCRIPTION "The system has experienced an undetermined hardware failure."
    --Novell NMS trap annotation
    --TYPE       "System undetermined hardware failure"
    --SEVERITY   INFORMATIONAL 
    --SUMMARY    "The system experienced an undetermined hardware failure."
    --CATEGORY   "Error Alarms"
    --STATE      OPERATIONAL
    --STATUS     MANDATORY 
    ::= { systemEvents 3 }

-------------------------------------------------------------------------------
-- Drive Slot Events -  Drive Slot Presence Sensor Events
-------------------------------------------------------------------------------
driveSlotDeviceRemovedEvent                     NOTIFICATION-TYPE
    OBJECTS { 
        eventDescription,
        driveSlotPresenceSensorStatus, 
        driveSlotPresenceSensorDescription, 
        driveSlotPresenceSensorCIMDeviceId 
    }
    STATUS      current
    DESCRIPTION "The device has been removed from the drive slot."
    --Novell NMS trap annotation
    --TYPE       "Server Drive Slot Device Removed"
    --SEVERITY   INFORMATIONAL 
    --SUMMARY    "The device has been removed from the drive slot %s."
    --ARGUMENTS  {2}
    --CATEGORY   "Error Alarms"
    --STATE      OPERATIONAL
    --STATUS     MANDATORY     
    ::= { driveSlotEvents 1 }

driveSlotDeviceInsertedEvent                     NOTIFICATION-TYPE
    OBJECTS { 
        eventDescription,
        driveSlotPresenceSensorStatus, 
        driveSlotPresenceSensorDescription, 
        driveSlotPresenceSensorCIMDeviceId 
    }
    STATUS      current
    DESCRIPTION "The device has been inserted in the drive slot."
    --Novell NMS trap annotation
    --TYPE       "Server Drive Slot Device Inserted"
    --SEVERITY   INFORMATIONAL 
    --SUMMARY    "The device has been inserted in the drive slot %s."
    --ARGUMENTS  {2}
    --CATEGORY   "Error Alarms"
    --STATE      OPERATIONAL
    --STATUS     MANDATORY     
    ::= { driveSlotEvents 2 }

END
