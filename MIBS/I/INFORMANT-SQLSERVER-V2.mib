INFORMANT-SQLSERVER-V2 DEFINITIONS ::= BEGIN

IMPORTS
    MODULE-IDENTITY, OBJECT-TYPE, Gauge32, Integer32
        FROM SNMPv2-SMI
    InstanceName, informant
        FROM WTCS;

sqlServerV2 MODULE-IDENTITY
    LAST-UPDATED "200804270606Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant SQL Server V2
             entries. This module supports SQL Server
             2005 and SQL Server 2008."
    REVISION      "200804270606Z"
    DESCRIPTION
            "The initial revision of this MIB module."
    ::= { informant 13 }

analysisServicesV2 OBJECT IDENTIFIER
    ::= { sqlServerV2 1 }

as2NameTable OBJECT-TYPE
    SYNTAX     SEQUENCE OF AnalysisServicesNameEntry
    MAX-ACCESS not-accessible
    STATUS     current
    DESCRIPTION
	    "This table contains the list of Analysis
	    Services instance names installed. The
	    as2NameIndex is used to refer to all other
	    Analysis Services SNMP entries."
    ::= { analysisServicesV2 1 }

as2NameEntry OBJECT-TYPE
    SYNTAX     AnalysisServicesNameEntry
    MAX-ACCESS not-accessible
    STATUS     current
    DESCRIPTION
	    "Performance information for one Analysis
	    Services name instance."
    INDEX      { as2NameIndex }
    ::= { as2NameTable 1 }

AnalysisServicesNameEntry ::= SEQUENCE {
    as2NameIndex Integer32,
    as2NameInstance InstanceName
}

as2NameIndex OBJECT-TYPE
    SYNTAX     Integer32 (1..2147483647)
    MAX-ACCESS read-only
    STATUS     current
    DESCRIPTION
	    "The index number associated with the instance
	    name"
    ::= { as2NameEntry 1 }

as2NameInstance OBJECT-TYPE
    SYNTAX     InstanceName
    MAX-ACCESS read-only
    STATUS     current
    DESCRIPTION
	    "The name of the Analysis Services installed
	    instance."
    ::= { as2NameEntry 2 }

as2CacheTable OBJECT-TYPE
    SYNTAX     SEQUENCE OF AnalysisServicesCacheEntry
    MAX-ACCESS not-accessible
    STATUS     current
    DESCRIPTION
	    "Statistics related to Microsoft Analysis
	    Services aggregation cache."
    ::= { analysisServicesV2 2 }

as2CacheEntry OBJECT-TYPE
    SYNTAX     AnalysisServicesCacheEntry
    MAX-ACCESS not-accessible
    STATUS     current
    DESCRIPTION
	    "Performance information for one SQL Server
	    name instance."
    INDEX      { as2NameIndex }
    ::= { as2CacheTable 1 }

AnalysisServicesCacheEntry ::= SEQUENCE {
    as2CacheCurrentKB Gauge32,
    as2CacheCurrentEntries Gauge32,
    as2CacheDirectHitRatio Gauge32,
    as2CacheDirectHitsPerSec Gauge32,
    as2CacheEvictionsPerSec Gauge32,
    as2CacheInsertsPerSec Gauge32,
    as2CacheKBAddedPerSec Gauge32,
    as2CacheLookupsPerSec Gauge32,
    as2CacheMissesPerSec Gauge32,
    as2CacheTotalDirectHits Gauge32,
    as2CacheTotalEvictions Gauge32,
    as2CacheTotalFiltIteratorCachHit Gauge32,
    as2CacheTotalFiltIteratorCachMis Gauge32,
    as2CacheTotalInserts Gauge32,
    as2CacheTotalLookups Gauge32,
    as2CacheTotalMisses Gauge32
}

as2CacheCurrentKB OBJECT-TYPE
    SYNTAX     Gauge32
    MAX-ACCESS read-only
    STATUS     current
    DESCRIPTION
	    "Current memory used by the aggregation cache,
	    in KB."
    ::= { as2CacheEntry 1 }

as2CacheCurrentEntries OBJECT-TYPE
    SYNTAX     Gauge32
    MAX-ACCESS read-only
    STATUS     current
    DESCRIPTION
	    "Current number of cache entries."
    ::= { as2CacheEntry 2 }

as2CacheDirectHitRatio OBJECT-TYPE
    SYNTAX     Gauge32
    MAX-ACCESS read-only
    STATUS     current
    DESCRIPTION
	    "Ratio of cache direct hits to cache lookups,
	    for the period between obtaining counter
	    values."
    ::= { as2CacheEntry 3 }

as2CacheDirectHitsPerSec OBJECT-TYPE
    SYNTAX     Gauge32
    MAX-ACCESS read-only
    STATUS     current
    DESCRIPTION
	    "Rate of cache direct hits.  Queries were
	    answered from an existing cache entry."
    ::= { as2CacheEntry 4 }

as2CacheEvictionsPerSec OBJECT-TYPE
    SYNTAX     Gauge32
    MAX-ACCESS read-only
    STATUS     current
    DESCRIPTION
	    "Rate of evictions from the cache.	This is per
	    partition per cube per database.  Typically due
	    to background cleaner."
    ::= { as2CacheEntry 5 }

as2CacheInsertsPerSec OBJECT-TYPE
    SYNTAX     Gauge32
    MAX-ACCESS read-only
    STATUS     current
    DESCRIPTION
	    "Rate of insertions into the cache.  This is
	    per partition per cube per database."
    ::= { as2CacheEntry 6 }

as2CacheKBAddedPerSec OBJECT-TYPE
    SYNTAX     Gauge32
    MAX-ACCESS read-only
    STATUS     current
    DESCRIPTION
	    "Rate of memory added to the cache, KB/sec."
    ::= { as2CacheEntry 7 }

as2CacheLookupsPerSec OBJECT-TYPE
    SYNTAX     Gauge32
    MAX-ACCESS read-only
    STATUS     current
    DESCRIPTION
	    "Rate of cache lookups."
    ::= { as2CacheEntry 8 }

as2CacheMissesPerSec OBJECT-TYPE
    SYNTAX     Gauge32
    MAX-ACCESS read-only
    STATUS     current
    DESCRIPTION
	    "Rate of cache misses."
    ::= { as2CacheEntry 9 }

as2CacheTotalDirectHits OBJECT-TYPE
    SYNTAX     Gauge32
    MAX-ACCESS read-only
    STATUS     current
    DESCRIPTION
	    "Total count of direct cache hits.	Queries
	    were answered from existing cache entries."
    ::= { as2CacheEntry 10 }

as2CacheTotalEvictions OBJECT-TYPE
    SYNTAX     Gauge32
    MAX-ACCESS read-only
    STATUS     current
    DESCRIPTION
	    "Evictions from the cache.	This is per
	    partition per cube per database.  Typically due
	    to background cleaner."
    ::= { as2CacheEntry 11 }

as2CacheTotalFiltIteratorCachHit OBJECT-TYPE
    SYNTAX     Gauge32
    MAX-ACCESS read-only
    STATUS     current
    DESCRIPTION
	    "Total number of cache hits that returned an
	    indexed iterator over the filtered results"
    ::= { as2CacheEntry 12 }

as2CacheTotalFiltIteratorCachMis OBJECT-TYPE
    SYNTAX     Gauge32
    MAX-ACCESS read-only
    STATUS     current
    DESCRIPTION
	    "Total number of cache hits that were unable to
	    build an indexed iterator over the filtered
	    results and had to build a new cache with the
	    filtered results"
    ::= { as2CacheEntry 13 }

as2CacheTotalInserts OBJECT-TYPE
    SYNTAX     Gauge32
    MAX-ACCESS read-only
    STATUS     current
    DESCRIPTION
	    "Insertions into the cache.  This is per
	    partition per cube per database."
    ::= { as2CacheEntry 14 }

as2CacheTotalLookups OBJECT-TYPE
    SYNTAX     Gauge32
    MAX-ACCESS read-only
    STATUS     current
    DESCRIPTION
	    "Total number of lookups into the cache."
    ::= { as2CacheEntry 15 }

as2CacheTotalMisses OBJECT-TYPE
    SYNTAX     Gauge32
    MAX-ACCESS read-only
    STATUS     current
    DESCRIPTION
	    "Total count of cache misses."
    ::= { as2CacheEntry 16 }

as2ConnectionTable OBJECT-TYPE
    SYNTAX     SEQUENCE OF AnalysisServicesConnectionEntry
    MAX-ACCESS not-accessible
    STATUS     current
    DESCRIPTION
	    "Statistics related to Microsoft Analysis
	    Services connections."
    ::= { analysisServicesV2 3 }

as2ConnectionEntry OBJECT-TYPE
    SYNTAX     AnalysisServicesConnectionEntry
    MAX-ACCESS not-accessible
    STATUS     current
    DESCRIPTION
	    "Performance information for one SQL Server
	    name instance."
    INDEX      { as2NameIndex }
    ::= { as2ConnectionTable 1 }

AnalysisServicesConnectionEntry ::= SEQUENCE {
    as2ConnectionCurrentConnections Gauge32,
    as2ConnectionCurrentUserSessions Gauge32,
    as2ConnectionFailuresPerSec Gauge32,
    as2ConnectionRequestsPerSec Gauge32,
    as2ConnectionSuccessesPerSec Gauge32,
    as2ConnectionTotalFailures Gauge32,
    as2ConnectionTotalRequests Gauge32,
    as2ConnectionTotalSuccesses Gauge32
}

as2ConnectionCurrentConnections OBJECT-TYPE
    SYNTAX     Gauge32
    MAX-ACCESS read-only
    STATUS     current
    DESCRIPTION
	    "Current number of client connections
	    established."
    ::= { as2ConnectionEntry 1 }

as2ConnectionCurrentUserSessions OBJECT-TYPE
    SYNTAX     Gauge32
    MAX-ACCESS read-only
    STATUS     current
    DESCRIPTION
	    "Current number of user sessions established."
    ::= { as2ConnectionEntry 2 }

as2ConnectionFailuresPerSec OBJECT-TYPE
    SYNTAX     Gauge32
    MAX-ACCESS read-only
    STATUS     current
    DESCRIPTION
	    "Rate of connection failures."
    ::= { as2ConnectionEntry 3 }

as2ConnectionRequestsPerSec OBJECT-TYPE
    SYNTAX     Gauge32
    MAX-ACCESS read-only
    STATUS     current
    DESCRIPTION
	    "Rate of connection requests.  These are
	    arrivals."
    ::= { as2ConnectionEntry 4 }

as2ConnectionSuccessesPerSec OBJECT-TYPE
    SYNTAX     Gauge32
    MAX-ACCESS read-only
    STATUS     current
    DESCRIPTION
	    "Rate of successful connection completions."
    ::= { as2ConnectionEntry 5 }

as2ConnectionTotalFailures OBJECT-TYPE
    SYNTAX     Gauge32
    MAX-ACCESS read-only
    STATUS     current
    DESCRIPTION
	    "Total failed connection attempts."
    ::= { as2ConnectionEntry 6 }

as2ConnectionTotalRequests OBJECT-TYPE
    SYNTAX     Gauge32
    MAX-ACCESS read-only
    STATUS     current
    DESCRIPTION
	    "Total connection requests.  These are
	    arrivals."
    ::= { as2ConnectionEntry 7 }

as2ConnectionTotalSuccesses OBJECT-TYPE
    SYNTAX     Gauge32
    MAX-ACCESS read-only
    STATUS     current
    DESCRIPTION
	    "Total successful connections."
    ::= { as2ConnectionEntry 8 }

as2DataMiningModelProcessTable OBJECT-TYPE
    SYNTAX     SEQUENCE OF DataMiningModelProcessingEntry
    MAX-ACCESS not-accessible
    STATUS     current
    DESCRIPTION
	    "Statistics related to Microsoft Analysis
	    Services Data Mining model processing."
    ::= { analysisServicesV2 4 }

as2DataMiningModelProcessEntry OBJECT-TYPE
    SYNTAX     DataMiningModelProcessingEntry
    MAX-ACCESS not-accessible
    STATUS     current
    DESCRIPTION
	    "Performance information for one SQL Server
	    name instance."
    INDEX      { as2NameIndex }
    ::= { as2DataMiningModelProcessTable 1 }

DataMiningModelProcessingEntry ::= SEQUENCE {
    as2dmmpCasesPerSec Gauge32,
    as2dmmpCurrentModelsProcessing Gauge32
}

as2dmmpCasesPerSec OBJECT-TYPE
    SYNTAX     Gauge32
    MAX-ACCESS read-only
    STATUS     current
    DESCRIPTION
	    "Rate of processing cases."
    ::= { as2DataMiningModelProcessEntry 1 }

as2dmmpCurrentModelsProcessing OBJECT-TYPE
    SYNTAX     Gauge32
    MAX-ACCESS read-only
    STATUS     current
    DESCRIPTION
	    "Current number of models being processed"
    ::= { as2DataMiningModelProcessEntry 2 }

as2DataMiningPredictionTable OBJECT-TYPE
    SYNTAX     SEQUENCE OF DataMiningPredictionEntry
    MAX-ACCESS not-accessible
    STATUS     current
    DESCRIPTION
	    "Statistics related to Microsoft Analysis
	    Services Data Mining prediction."
    ::= { analysisServicesV2 5 }

as2DataMiningPredictionEntry OBJECT-TYPE
    SYNTAX     DataMiningPredictionEntry
    MAX-ACCESS not-accessible
    STATUS     current
    DESCRIPTION
	    "Performance information for one SQL Server
	    name instance."
    INDEX      { as2NameIndex }
    ::= { as2DataMiningPredictionTable 1 }

DataMiningPredictionEntry ::= SEQUENCE {
    as2dmpConcurrentDMQueries Gauge32,
    as2dmpPredictionsPerSec Gauge32,
    as2dmpQueriesPerSec Gauge32,
    as2dmpRowsPerSec Gauge32,
    as2dmpTotalPredictions Gauge32,
    as2dmpTotalQueries Gauge32,
    as2dmpTotalRows Gauge32
}

as2dmpConcurrentDMQueries OBJECT-TYPE
    SYNTAX     Gauge32
    MAX-ACCESS read-only
    STATUS     current
    DESCRIPTION
	    "Current number of Data Mining queries being
	    actively worked on."
    ::= { as2DataMiningPredictionEntry 1 }

as2dmpPredictionsPerSec OBJECT-TYPE
    SYNTAX     Gauge32
    MAX-ACCESS read-only
    STATUS     current
    DESCRIPTION
	    "Rate of Data Mining prediction queries"
    ::= { as2DataMiningPredictionEntry 2 }

as2dmpQueriesPerSec OBJECT-TYPE
    SYNTAX     Gauge32
    MAX-ACCESS read-only
    STATUS     current
    DESCRIPTION
	    "Rate of Data Mining queries"
    ::= { as2DataMiningPredictionEntry 3 }

as2dmpRowsPerSec OBJECT-TYPE
    SYNTAX     Gauge32
    MAX-ACCESS read-only
    STATUS     current
    DESCRIPTION
	    "Rate of predicting rows"
    ::= { as2DataMiningPredictionEntry 4 }

as2dmpTotalPredictions OBJECT-TYPE
    SYNTAX     Gauge32
    MAX-ACCESS read-only
    STATUS     current
    DESCRIPTION
	    "Total Data Mining Prediction Queries received
	    by the server"
    ::= { as2DataMiningPredictionEntry 5 }

as2dmpTotalQueries OBJECT-TYPE
    SYNTAX     Gauge32
    MAX-ACCESS read-only
    STATUS     current
    DESCRIPTION
	    "Total Data Mining Queries received by the
	    server"
    ::= { as2DataMiningPredictionEntry 6 }

as2dmpTotalRows OBJECT-TYPE
    SYNTAX     Gauge32
    MAX-ACCESS read-only
    STATUS     current
    DESCRIPTION
	    "Total Rows returned by Data Mining queries"
    ::= { as2DataMiningPredictionEntry 7 }

as2LocksTable OBJECT-TYPE
    SYNTAX     SEQUENCE OF AnalysisServicesLocksEntry
    MAX-ACCESS not-accessible
    STATUS     current
    DESCRIPTION
	    "Statistics related to Microsoft Analysis
	    Services internal server locks."
    ::= { analysisServicesV2 6 }

as2LocksEntry OBJECT-TYPE
    SYNTAX     AnalysisServicesLocksEntry
    MAX-ACCESS not-accessible
    STATUS     current
    DESCRIPTION
	    "Performance information for one SQL Server
	    name instance."
    INDEX      { as2NameIndex }
    ::= { as2LocksTable 1 }

AnalysisServicesLocksEntry ::= SEQUENCE {
    as2LocksCurrentLatchWaits Gauge32,
    as2LocksCurrentLockWaits Gauge32,
    as2LocksCurrentLocks Gauge32,
    as2LocksLatchWaitsPerSec Gauge32,
    as2LocksLockDenialsPerSec Gauge32,
    as2LocksLockGrantsPerSec Gauge32,
    as2LocksLockRequestsPerSec Gauge32,
    as2LocksLockWaitsPerSec Gauge32,
    as2LocksTotalDeadlocksDetected Gauge32,
    as2LocksUnlockRequestsPerSec Gauge32
}

as2LocksCurrentLatchWaits OBJECT-TYPE
    SYNTAX     Gauge32
    MAX-ACCESS read-only
    STATUS     current
    DESCRIPTION
	    "Current number of threads waiting for a latch.
	     These are latch requests that could not be
	    given immediate grants and are in a wait
	    state."
    ::= { as2LocksEntry 1 }

as2LocksCurrentLockWaits OBJECT-TYPE
    SYNTAX     Gauge32
    MAX-ACCESS read-only
    STATUS     current
    DESCRIPTION
	    "Current number of clients waiting for a lock."
    ::= { as2LocksEntry 2 }

as2LocksCurrentLocks OBJECT-TYPE
    SYNTAX     Gauge32
    MAX-ACCESS read-only
    STATUS     current
    DESCRIPTION
	    "Current number of locked objects."
    ::= { as2LocksEntry 3 }

as2LocksLatchWaitsPerSec OBJECT-TYPE
    SYNTAX     Gauge32
    MAX-ACCESS read-only
    STATUS     current
    DESCRIPTION
	    "Rate of latch requests that could not be
	    granted immediately and had to wait before
	    being granted."
    ::= { as2LocksEntry 4 }

as2LocksLockDenialsPerSec OBJECT-TYPE
    SYNTAX     Gauge32
    MAX-ACCESS read-only
    STATUS     current
    DESCRIPTION
	    "Rate of lock denials."
    ::= { as2LocksEntry 5 }

as2LocksLockGrantsPerSec OBJECT-TYPE
    SYNTAX     Gauge32
    MAX-ACCESS read-only
    STATUS     current
    DESCRIPTION
	    "Number of lock grants per second."
    ::= { as2LocksEntry 6 }

as2LocksLockRequestsPerSec OBJECT-TYPE
    SYNTAX     Gauge32
    MAX-ACCESS read-only
    STATUS     current
    DESCRIPTION
	    "Number of lock requests per second."
    ::= { as2LocksEntry 7 }

as2LocksLockWaitsPerSec OBJECT-TYPE
    SYNTAX     Gauge32
    MAX-ACCESS read-only
    STATUS     current
    DESCRIPTION
	    "Number of lock waits per second.  These are
	    lock requests that could not be given immediate
	    lock grants and were put in a wait state."
    ::= { as2LocksEntry 8 }

as2LocksTotalDeadlocksDetected OBJECT-TYPE
    SYNTAX     Gauge32
    MAX-ACCESS read-only
    STATUS     current
    DESCRIPTION
	    "Total number of deadlocks detected."
    ::= { as2LocksEntry 9 }

as2LocksUnlockRequestsPerSec OBJECT-TYPE
    SYNTAX     Gauge32
    MAX-ACCESS read-only
    STATUS     current
    DESCRIPTION
	    "Number of unlock requests per second."
    ::= { as2LocksEntry 10 }

as2MDXTable OBJECT-TYPE
    SYNTAX     SEQUENCE OF AnalysisServicesMDXEntry
    MAX-ACCESS not-accessible
    STATUS     current
    DESCRIPTION
	    "Statistics related to Microsoft Analysis
	    Services MDX Calculations."
    ::= { analysisServicesV2 7 }

as2MDXEntry OBJECT-TYPE
    SYNTAX     AnalysisServicesMDXEntry
    MAX-ACCESS not-accessible
    STATUS     current
    DESCRIPTION
	    "Performance information for one SQL Server
	    name instance."
    INDEX      { as2NameIndex }
    ::= { as2MDXTable 1 }

AnalysisServicesMDXEntry ::= SEQUENCE {
    as2MDXCurrentNumOfCachedEvalNode Gauge32,
    as2MDXCurrentNumOfEvalNode Gauge32,
    as2MDXNumOfStorageEngineEvalNode Gauge32,
    as2MDXNumOfBulkModeEvalNode Gauge32,
    as2MDXNumOfCachedotherEvalNode Gauge32,
    as2MDXNumCacheStorEngineEvalNode Gauge32,
    as2MDXNumOfCacheBulkModeEvalNode Gauge32,
    as2MDXNumberOfCalculationCovers Gauge32,
    as2MDXNumOfCellByCellEvalNode Gauge32,
    as2MDXNumCellCellHitCacheEvalNod Gauge32,
    as2MDXNumCellCellMissCachEvalNod Gauge32,
    as2MDXNumEvalNodThatCovASglCell Gauge32,
    as2MDXNumEvalNodeCalcSameGranula Gauge32,
    as2MDXNumEvictionsEvalNode Gauge32,
    as2MDXNumHashdexHitsCacheEvalNod Gauge32,
    as2MDXNumSubcubeHitsCacheEvalNod Gauge32,
    as2MDXNumSubcubeMissCacheEvalNod Gauge32,
    as2MDXTotalAutoexist Gauge32,
    as2MDXTotalEXISTING Gauge32,
    as2MDXTotalNONEMPTY Gauge32,
    as2MDXTotalNONEMPTYCalculatMemb Gauge32,
    as2MDXTotalNONEMPTYUnoptimized Gauge32,
    as2MDXTotalSonarSubcubes Gauge32,
    as2MDXTotalCellsCalculated Gauge32,
    as2MDXTotalFlatCacheInserts Gauge32,
    as2MDXTotalRecomputes Gauge32
}

as2MDXCurrentNumOfCachedEvalNode OBJECT-TYPE
    SYNTAX     Gauge32
    MAX-ACCESS read-only
    STATUS     current
    DESCRIPTION
	    "Current (approximate) number of cached
	    evaluation nodes built by MDX execution plans"
    ::= { as2MDXEntry 1 }

as2MDXCurrentNumOfEvalNode OBJECT-TYPE
    SYNTAX     Gauge32
    MAX-ACCESS read-only
    STATUS     current
    DESCRIPTION
	    "Current (approximate) number of evaluation
	    nodes built by MDX execution plans including
	    active and cached"
    ::= { as2MDXEntry 2 }

as2MDXNumOfStorageEngineEvalNode OBJECT-TYPE
    SYNTAX     Gauge32
    MAX-ACCESS read-only
    STATUS     current
    DESCRIPTION
	    "Total number of Storage Engine evaluation
	    nodes built by MDX execution plans"
    ::= { as2MDXEntry 3 }

as2MDXNumOfBulkModeEvalNode OBJECT-TYPE
    SYNTAX     Gauge32
    MAX-ACCESS read-only
    STATUS     current
    DESCRIPTION
	    "Total number of bulk-mode evaluation nodes
	    built by MDX execution plans"
    ::= { as2MDXEntry 4 }

as2MDXNumOfCachedotherEvalNode OBJECT-TYPE
    SYNTAX     Gauge32
    MAX-ACCESS read-only
    STATUS     current
    DESCRIPTION
	    "Total number of cached evaluation nodes built
	    by MDX execution plans that are neither Storage
	    Engine nor Bulk-mode"
    ::= { as2MDXEntry 5 }

as2MDXNumCacheStorEngineEvalNode OBJECT-TYPE
    SYNTAX     Gauge32
    MAX-ACCESS read-only
    STATUS     current
    DESCRIPTION
	    "Total number of cached Storage Engine
	    evaluation nodes built by MDX execution plans"
    ::= { as2MDXEntry 6 }

as2MDXNumOfCacheBulkModeEvalNode OBJECT-TYPE
    SYNTAX     Gauge32
    MAX-ACCESS read-only
    STATUS     current
    DESCRIPTION
	    "Total number of cached bulk-mode evaluation
	    nodes built by MDX execution plans"
    ::= { as2MDXEntry 7 }

as2MDXNumberOfCalculationCovers OBJECT-TYPE
    SYNTAX     Gauge32
    MAX-ACCESS read-only
    STATUS     current
    DESCRIPTION
	    "Total number of evaluation nodes built by MDX
	    execution plans including active and cached"
    ::= { as2MDXEntry 8 }

as2MDXNumOfCellByCellEvalNode OBJECT-TYPE
    SYNTAX     Gauge32
    MAX-ACCESS read-only
    STATUS     current
    DESCRIPTION
	    "Total number of cell-by-cell evaluation nodes
	    built by MDX execution plans"
    ::= { as2MDXEntry 9 }

as2MDXNumCellCellHitCacheEvalNod OBJECT-TYPE
    SYNTAX     Gauge32
    MAX-ACCESS read-only
    STATUS     current
    DESCRIPTION
	    "Total number of cell-by-cell hits in the cache
	    of evaluation nodes"
    ::= { as2MDXEntry 10 }

as2MDXNumCellCellMissCachEvalNod OBJECT-TYPE
    SYNTAX     Gauge32
    MAX-ACCESS read-only
    STATUS     current
    DESCRIPTION
	    "Total number of cell-by-cell misses in the
	    cache of evaluation nodes"
    ::= { as2MDXEntry 11 }

as2MDXNumEvalNodThatCovASglCell OBJECT-TYPE
    SYNTAX     Gauge32
    MAX-ACCESS read-only
    STATUS     current
    DESCRIPTION
	    "Total number of evaluation nodes built by MDX
	    execution plans that covered only one cell"
    ::= { as2MDXEntry 12 }

as2MDXNumEvalNodeCalcSameGranula OBJECT-TYPE
    SYNTAX     Gauge32
    MAX-ACCESS read-only
    STATUS     current
    DESCRIPTION
	    "Total number of evaluation nodes built by MDX
	    execution plans for which the calculations were
	    at the same granularity as the evaluation node"
    ::= { as2MDXEntry 13 }

as2MDXNumEvictionsEvalNode OBJECT-TYPE
    SYNTAX     Gauge32
    MAX-ACCESS read-only
    STATUS     current
    DESCRIPTION
	    "Total number of cache evictions of evaluation
	    nodes due to collisions"
    ::= { as2MDXEntry 14 }

as2MDXNumHashdexHitsCacheEvalNod OBJECT-TYPE
    SYNTAX     Gauge32
    MAX-ACCESS read-only
    STATUS     current
    DESCRIPTION
	    "Total number of hits in the cache of
	    evaluation nodes that were satisfied by the
	    hash index"
    ::= { as2MDXEntry 15 }

as2MDXNumSubcubeHitsCacheEvalNod OBJECT-TYPE
    SYNTAX     Gauge32
    MAX-ACCESS read-only
    STATUS     current
    DESCRIPTION
	    "Total number of subcube hits in the cache of
	    evaluation nodes"
    ::= { as2MDXEntry 16 }

as2MDXNumSubcubeMissCacheEvalNod OBJECT-TYPE
    SYNTAX     Gauge32
    MAX-ACCESS read-only
    STATUS     current
    DESCRIPTION
	    "Total number of subcube misses in the cache of
	    evaluation nodes"
    ::= { as2MDXEntry 17 }

as2MDXTotalAutoexist OBJECT-TYPE
    SYNTAX     Gauge32
    MAX-ACCESS read-only
    STATUS     current
    DESCRIPTION
	    "Total number of times autoexist performed"
    ::= { as2MDXEntry 18 }

as2MDXTotalEXISTING OBJECT-TYPE
    SYNTAX     Gauge32
    MAX-ACCESS read-only
    STATUS     current
    DESCRIPTION
	    "Total number of times EXISTING set operator
	    performed"
    ::= { as2MDXEntry 19 }

as2MDXTotalNONEMPTY OBJECT-TYPE
    SYNTAX     Gauge32
    MAX-ACCESS read-only
    STATUS     current
    DESCRIPTION
	    "Total number of times NON EMPTY algorithms is
	    used"
    ::= { as2MDXEntry 20 }

as2MDXTotalNONEMPTYCalculatMemb OBJECT-TYPE
    SYNTAX     Gauge32
    MAX-ACCESS read-only
    STATUS     current
    DESCRIPTION
	    "Total number of times NON EMPTY algorithm was
	    looping over calculated members"
    ::= { as2MDXEntry 21 }

as2MDXTotalNONEMPTYUnoptimized OBJECT-TYPE
    SYNTAX     Gauge32
    MAX-ACCESS read-only
    STATUS     current
    DESCRIPTION
	    "Total number of times unoptimized NON EMPTY
	    algorithm is used"
    ::= { as2MDXEntry 22 }

as2MDXTotalSonarSubcubes OBJECT-TYPE
    SYNTAX     Gauge32
    MAX-ACCESS read-only
    STATUS     current
    DESCRIPTION
	    "Total number of subcubes that query optimizer
	    generated"
    ::= { as2MDXEntry 23 }

as2MDXTotalCellsCalculated OBJECT-TYPE
    SYNTAX     Gauge32
    MAX-ACCESS read-only
    STATUS     current
    DESCRIPTION
	    "Total number of cell properties calculated"
    ::= { as2MDXEntry 24 }

as2MDXTotalFlatCacheInserts OBJECT-TYPE
    SYNTAX     Gauge32
    MAX-ACCESS read-only
    STATUS     current
    DESCRIPTION
	    "Total number of cell values inserted into flat
	    calculation cache"
    ::= { as2MDXEntry 25 }

as2MDXTotalRecomputes OBJECT-TYPE
    SYNTAX     Gauge32
    MAX-ACCESS read-only
    STATUS     current
    DESCRIPTION
	    "Total number of cells recomputed due to error"
    ::= { as2MDXEntry 26 }

as2MemoryTable OBJECT-TYPE
    SYNTAX     SEQUENCE OF AnalysisServicesMemoryEntry
    MAX-ACCESS not-accessible
    STATUS     current
    DESCRIPTION
	    "Statistics related to Microsoft Analysis
	    Services internal server memory."
    ::= { analysisServicesV2 8 }

as2MemoryEntry OBJECT-TYPE
    SYNTAX     AnalysisServicesMemoryEntry
    MAX-ACCESS not-accessible
    STATUS     current
    DESCRIPTION
	    "Performance information for one SQL Server
	    name instance."
    INDEX      { as2NameIndex }
    ::= { as2MemoryTable 1 }

AnalysisServicesMemoryEntry ::= SEQUENCE {
    as2memAggCacheKB Gauge32,
    as2memAggregationMapFiles Gauge32,
    as2memCleanerBalancePerSec Gauge32,
    as2memCleanerCurrentPrice Gauge32,
    as2memCleanerMemoryKB Gauge32,
    as2memCleanerMemNonshrinkableKB Gauge32,
    as2memCleanerMemoryShrinkableKB Gauge32,
    as2memCleanerMemShrunkKBSec Gauge32,
    as2memDimensionIndexHashFiles Gauge32,
    as2memDimensionPropertyFiles Gauge32,
    as2memDimensionStringFiles Gauge32,
    as2memFactAggregationFiles Gauge32,
    as2memFactDataFiles Gauge32,
    as2memFactStringFiles Gauge32,
    as2memFilestoreClockPgExamineSec Gauge32,
    as2memFilestoreClockPgHaveRefSec Gauge32,
    as2memFilestoreClockPgValidSec Gauge32,
    as2memFilestoreIOErrors Gauge32,
    as2memFilestoreIOErrorsPerSec Gauge32,
    as2memFilestoreKB Gauge32,
    as2memFilestoreKBReadsPerSec Gauge32,
    as2memFilestoreKBWritePerSec Gauge32,
    as2memFilestoreMemoryPinnedKB Gauge32,
    as2memFilestorePageFaultsPerSec Gauge32,
    as2memFilestoreReadsPerSec Gauge32,
    as2memFilestoreWritesPerSec Gauge32,
    as2memInMemAggregationMapFileKB Gauge32,
    as2memInMemAggregateMapFileKBSec Gauge32,
    as2memInMemDimenIndexHashFileKB Gauge32,
    as2memInMemDimenIndHashFileKBSec Gauge32,
    as2memInMemDimenProtyFileKB Gauge32,
    as2memInMemDimenProtyFileKBSec Gauge32,
    as2memInMemDimenStringFileKB Gauge32,
    as2memInMemDimenStringFileKBSec Gauge32,
    as2memInMemFactAggregationFileKB Gauge32,
    as2memInMemFactAggregatFileKBSec Gauge32,
    as2memInMemoryFactDataFileKB Gauge32,
    as2memInMemFactDataFileKBSec Gauge32,
    as2memInMemoryFactStringFileKB Gauge32,
    as2memInMemFactStringFileKBSec Gauge32,
    as2memInMemoryMapFileKB Gauge32,
    as2memInMemoryMapFileKBPerSec Gauge32,
    as2memInMemoryOtherFileKB Gauge32,
    as2memInMemoryOtherFileKBPerSec Gauge32,
    as2memMapFiles Gauge32,
    as2memMemoryLimitHighKB Gauge32,
    as2memMemoryLimitLowKB Gauge32,
    as2memMemoryUsageKB Gauge32,
    as2memOtherFiles Gauge32,
    as2memPagePool1AllocKB Gauge32,
    as2memPagePool1LookasideKB Gauge32,
    as2memPagePool64AllocKB Gauge32,
    as2memPagePool64LookasideKB Gauge32,
    as2memPagePool8AllocKB Gauge32,
    as2memPagePool8LookasideKB Gauge32,
    as2memPotenMemAggregatMapFileKB Gauge32,
    as2memPotenMemDimenIndHashFilKB Gauge32,
    as2memPotenMemDimenProFileKB Gauge32,
    as2memPotenMemDimenStringFileKB Gauge32,
    as2memPotenMemFactAggregFileKB Gauge32,
    as2memPotenMemFactDataFileKB Gauge32,
    as2memPotenMemFactStringFileKB Gauge32,
    as2memPotentialInMemoryMapFileKB Gauge32,
    as2memPotenMemOtherFileKB Gauge32,
    as2memQuotaBlocked Gauge32,
    as2memQuotaKB Gauge32
}

as2memAggCacheKB OBJECT-TYPE
    SYNTAX     Gauge32
    MAX-ACCESS read-only
    STATUS     current
    DESCRIPTION
	    "Current memory allocated to filestore (file
	    cache), in KB."
    ::= { as2MemoryEntry 1 }

as2memAggregationMapFiles OBJECT-TYPE
    SYNTAX     Gauge32
    MAX-ACCESS read-only
    STATUS     current
    DESCRIPTION
	    "Number of aggregation map files."
    ::= { as2MemoryEntry 2 }

as2memCleanerBalancePerSec OBJECT-TYPE
    SYNTAX     Gauge32
    MAX-ACCESS read-only
    STATUS     current
    DESCRIPTION
	    "Rate of balance+shrink operations."
    ::= { as2MemoryEntry 3 }

as2memCleanerCurrentPrice OBJECT-TYPE
    SYNTAX     Gauge32
    MAX-ACCESS read-only
    STATUS     current
    DESCRIPTION
	    "Current price of memory, $/byte/time,
	    normalized to 1000."
    ::= { as2MemoryEntry 4 }

as2memCleanerMemoryKB OBJECT-TYPE
    SYNTAX     Gauge32
    MAX-ACCESS read-only
    STATUS     current
    DESCRIPTION
	    "Amount of memory, in KB, known to the
	    background cleaner.  (Cleaner memory shrinkable
	    + Cleaner memory nonshrinkable.)"
    ::= { as2MemoryEntry 5 }

as2memCleanerMemNonshrinkableKB OBJECT-TYPE
    SYNTAX     Gauge32
    MAX-ACCESS read-only
    STATUS     current
    DESCRIPTION
	    "Amount of memory, in KB, not subject to
	    purging by the background cleaner."
    ::= { as2MemoryEntry 6 }

as2memCleanerMemoryShrinkableKB OBJECT-TYPE
    SYNTAX     Gauge32
    MAX-ACCESS read-only
    STATUS     current
    DESCRIPTION
	    "Amount of memory, in KB, subject to purging by
	    the background cleaner."
    ::= { as2MemoryEntry 7 }

as2memCleanerMemShrunkKBSec OBJECT-TYPE
    SYNTAX     Gauge32
    MAX-ACCESS read-only
    STATUS     current
    DESCRIPTION
	    "Rate of shrinking, in KB/sec."
    ::= { as2MemoryEntry 8 }

as2memDimensionIndexHashFiles OBJECT-TYPE
    SYNTAX     Gauge32
    MAX-ACCESS read-only
    STATUS     current
    DESCRIPTION
	    "Number of dimension index (hash) files."
    ::= { as2MemoryEntry 9 }

as2memDimensionPropertyFiles OBJECT-TYPE
    SYNTAX     Gauge32
    MAX-ACCESS read-only
    STATUS     current
    DESCRIPTION
	    "Number of dimension property files."
    ::= { as2MemoryEntry 10 }

as2memDimensionStringFiles OBJECT-TYPE
    SYNTAX     Gauge32
    MAX-ACCESS read-only
    STATUS     current
    DESCRIPTION
	    "Number of dimension string files."
    ::= { as2MemoryEntry 11 }

as2memFactAggregationFiles OBJECT-TYPE
    SYNTAX     Gauge32
    MAX-ACCESS read-only
    STATUS     current
    DESCRIPTION
	    "Number of fact aggregation files."
    ::= { as2MemoryEntry 12 }

as2memFactDataFiles OBJECT-TYPE
    SYNTAX     Gauge32
    MAX-ACCESS read-only
    STATUS     current
    DESCRIPTION
	    "Number of fact data files."
    ::= { as2MemoryEntry 13 }

as2memFactStringFiles OBJECT-TYPE
    SYNTAX     Gauge32
    MAX-ACCESS read-only
    STATUS     current
    DESCRIPTION
	    "Number of fact string files."
    ::= { as2MemoryEntry 14 }

as2memFilestoreClockPgExamineSec OBJECT-TYPE
    SYNTAX     Gauge32
    MAX-ACCESS read-only
    STATUS     current
    DESCRIPTION
	    "Rate of background cleaner examining pages for
	    eviction consideration."
    ::= { as2MemoryEntry 15 }

as2memFilestoreClockPgHaveRefSec OBJECT-TYPE
    SYNTAX     Gauge32
    MAX-ACCESS read-only
    STATUS     current
    DESCRIPTION
	    "Rate of background cleaner examining pages
	    that have a current reference count (are
	    currently in use)."
    ::= { as2MemoryEntry 16 }

as2memFilestoreClockPgValidSec OBJECT-TYPE
    SYNTAX     Gauge32
    MAX-ACCESS read-only
    STATUS     current
    DESCRIPTION
	    "Rate of background cleaner examining pages
	    that are valid candidates for eviction."
    ::= { as2MemoryEntry 17 }

as2memFilestoreIOErrors OBJECT-TYPE
    SYNTAX     Gauge32
    MAX-ACCESS read-only
    STATUS     current
    DESCRIPTION
	    "Filestore IO Errors total."
    ::= { as2MemoryEntry 18 }

as2memFilestoreIOErrorsPerSec OBJECT-TYPE
    SYNTAX     Gauge32
    MAX-ACCESS read-only
    STATUS     current
    DESCRIPTION
	    "Filestore IO Error rate."
    ::= { as2MemoryEntry 19 }

as2memFilestoreKB OBJECT-TYPE
    SYNTAX     Gauge32
    MAX-ACCESS read-only
    STATUS     current
    DESCRIPTION
	    "Current memory allocated to filestore (file
	    cache), in KB."
    ::= { as2MemoryEntry 20 }

as2memFilestoreKBReadsPerSec OBJECT-TYPE
    SYNTAX     Gauge32
    MAX-ACCESS read-only
    STATUS     current
    DESCRIPTION
	    "Filestore KB read/sec."
    ::= { as2MemoryEntry 21 }

as2memFilestoreKBWritePerSec OBJECT-TYPE
    SYNTAX     Gauge32
    MAX-ACCESS read-only
    STATUS     current
    DESCRIPTION
	    "Filestore KB written/sec.	The writes are
	    asynchronous."
    ::= { as2MemoryEntry 22 }

as2memFilestoreMemoryPinnedKB OBJECT-TYPE
    SYNTAX     Gauge32
    MAX-ACCESS read-only
    STATUS     current
    DESCRIPTION
	    "Current filestore memory pinned KB."
    ::= { as2MemoryEntry 23 }

as2memFilestorePageFaultsPerSec OBJECT-TYPE
    SYNTAX     Gauge32
    MAX-ACCESS read-only
    STATUS     current
    DESCRIPTION
	    "Filestore page fault rate."
    ::= { as2MemoryEntry 24 }

as2memFilestoreReadsPerSec OBJECT-TYPE
    SYNTAX     Gauge32
    MAX-ACCESS read-only
    STATUS     current
    DESCRIPTION
	    "Filestore pages read/sec."
    ::= { as2MemoryEntry 25 }

as2memFilestoreWritesPerSec OBJECT-TYPE
    SYNTAX     Gauge32
    MAX-ACCESS read-only
    STATUS     current
    DESCRIPTION
	    "Filestore pages written/sec.  The writes are
	    asynchronous."
    ::= { as2MemoryEntry 26 }

as2memInMemAggregationMapFileKB OBJECT-TYPE
    SYNTAX     Gauge32
    MAX-ACCESS read-only
    STATUS     current
    DESCRIPTION
	    "Current in-memory aggregation map file KB."
    ::= { as2MemoryEntry 27 }

as2memInMemAggregateMapFileKBSec OBJECT-TYPE
    SYNTAX     Gauge32
    MAX-ACCESS read-only
    STATUS     current
    DESCRIPTION
	    "In-memory aggregation map file KB rate."
    ::= { as2MemoryEntry 28 }

as2memInMemDimenIndexHashFileKB OBJECT-TYPE
    SYNTAX     Gauge32
    MAX-ACCESS read-only
    STATUS     current
    DESCRIPTION
	    "Current in-memory dimension index (hash) file
	    KB."
    ::= { as2MemoryEntry 29 }

as2memInMemDimenIndHashFileKBSec OBJECT-TYPE
    SYNTAX     Gauge32
    MAX-ACCESS read-only
    STATUS     current
    DESCRIPTION
	    "In-memory dimension index (hash) file KB
	    rate."
    ::= { as2MemoryEntry 30 }

as2memInMemDimenProtyFileKB OBJECT-TYPE
    SYNTAX     Gauge32
    MAX-ACCESS read-only
    STATUS     current
    DESCRIPTION
	    "Current in-memory dimension proty file KB."
    ::= { as2MemoryEntry 31 }

as2memInMemDimenProtyFileKBSec OBJECT-TYPE
    SYNTAX     Gauge32
    MAX-ACCESS read-only
    STATUS     current
    DESCRIPTION
	    "In-memory dimension proty file KB rate."
    ::= { as2MemoryEntry 32 }

as2memInMemDimenStringFileKB OBJECT-TYPE
    SYNTAX     Gauge32
    MAX-ACCESS read-only
    STATUS     current
    DESCRIPTION
	    "Current in-memory dimension string file KB."
    ::= { as2MemoryEntry 33 }

as2memInMemDimenStringFileKBSec OBJECT-TYPE
    SYNTAX     Gauge32
    MAX-ACCESS read-only
    STATUS     current
    DESCRIPTION
	    "In-memory dimension string file KB rate."
    ::= { as2MemoryEntry 34 }

as2memInMemFactAggregationFileKB OBJECT-TYPE
    SYNTAX     Gauge32
    MAX-ACCESS read-only
    STATUS     current
    DESCRIPTION
	    "Current in-memory fact aggregation file KB."
    ::= { as2MemoryEntry 35 }

as2memInMemFactAggregatFileKBSec OBJECT-TYPE
    SYNTAX     Gauge32
    MAX-ACCESS read-only
    STATUS     current
    DESCRIPTION
	    "In-memory fact aggregation file KB rate."
    ::= { as2MemoryEntry 36 }

as2memInMemoryFactDataFileKB OBJECT-TYPE
    SYNTAX     Gauge32
    MAX-ACCESS read-only
    STATUS     current
    DESCRIPTION
	    "Current in-memory fact data file KB."
    ::= { as2MemoryEntry 37 }

as2memInMemFactDataFileKBSec OBJECT-TYPE
    SYNTAX     Gauge32
    MAX-ACCESS read-only
    STATUS     current
    DESCRIPTION
	    "In-memory fact data file KB rate."
    ::= { as2MemoryEntry 38 }

as2memInMemoryFactStringFileKB OBJECT-TYPE
    SYNTAX     Gauge32
    MAX-ACCESS read-only
    STATUS     current
    DESCRIPTION
	    "Current in-memory fact string file KB."
    ::= { as2MemoryEntry 39 }

as2memInMemFactStringFileKBSec OBJECT-TYPE
    SYNTAX     Gauge32
    MAX-ACCESS read-only
    STATUS     current
    DESCRIPTION
	    "In-memory fact string file KB rate."
    ::= { as2MemoryEntry 40 }

as2memInMemoryMapFileKB OBJECT-TYPE
    SYNTAX     Gauge32
    MAX-ACCESS read-only
    STATUS     current
    DESCRIPTION
	    "Current in-memory map file KB."
    ::= { as2MemoryEntry 41 }

as2memInMemoryMapFileKBPerSec OBJECT-TYPE
    SYNTAX     Gauge32
    MAX-ACCESS read-only
    STATUS     current
    DESCRIPTION
	    "In-memory map file KB rate."
    ::= { as2MemoryEntry 42 }

as2memInMemoryOtherFileKB OBJECT-TYPE
    SYNTAX     Gauge32
    MAX-ACCESS read-only
    STATUS     current
    DESCRIPTION
	    "Current in-memory other file KB."
    ::= { as2MemoryEntry 43 }

as2memInMemoryOtherFileKBPerSec OBJECT-TYPE
    SYNTAX     Gauge32
    MAX-ACCESS read-only
    STATUS     current
    DESCRIPTION
	    "In-memory other file KB rate."
    ::= { as2MemoryEntry 44 }

as2memMapFiles OBJECT-TYPE
    SYNTAX     Gauge32
    MAX-ACCESS read-only
    STATUS     current
    DESCRIPTION
	    "Number of map files."
    ::= { as2MemoryEntry 45 }

as2memMemoryLimitHighKB OBJECT-TYPE
    SYNTAX     Gauge32
    MAX-ACCESS read-only
    STATUS     current
    DESCRIPTION
	    "High memory limit, from configuration file."
    ::= { as2MemoryEntry 46 }

as2memMemoryLimitLowKB OBJECT-TYPE
    SYNTAX     Gauge32
    MAX-ACCESS read-only
    STATUS     current
    DESCRIPTION
	    "Low memory limit, from configuration file."
    ::= { as2MemoryEntry 47 }

as2memMemoryUsageKB OBJECT-TYPE
    SYNTAX     Gauge32
    MAX-ACCESS read-only
    STATUS     current
    DESCRIPTION
	    "Memory usage of the server process.  Same as
	    perfmon counter for Process\PrivateBytes."
    ::= { as2MemoryEntry 48 }

as2memOtherFiles OBJECT-TYPE
    SYNTAX     Gauge32
    MAX-ACCESS read-only
    STATUS     current
    DESCRIPTION
	    "Number of other files."
    ::= { as2MemoryEntry 49 }

as2memPagePool1AllocKB OBJECT-TYPE
    SYNTAX     Gauge32
    MAX-ACCESS read-only
    STATUS     current
    DESCRIPTION
	    "Memory borrowed from 64KB page pool, in KB. 
	    This memory is given away to other parts of the
	    server."
    ::= { as2MemoryEntry 50 }

as2memPagePool1LookasideKB OBJECT-TYPE
    SYNTAX     Gauge32
    MAX-ACCESS read-only
    STATUS     current
    DESCRIPTION
	    "Current memory in 8KB lookaside list, in KB. 
	    (Memory pages ready to be used.)"
    ::= { as2MemoryEntry 51 }

as2memPagePool64AllocKB OBJECT-TYPE
    SYNTAX     Gauge32
    MAX-ACCESS read-only
    STATUS     current
    DESCRIPTION
	    "Memory borrowed from system, in KB.  This
	    memory is given away to other parts of the
	    server."
    ::= { as2MemoryEntry 52 }

as2memPagePool64LookasideKB OBJECT-TYPE
    SYNTAX     Gauge32
    MAX-ACCESS read-only
    STATUS     current
    DESCRIPTION
	    "Current memory in 64KB lookaside list, in KB. 
	    (Memory pages ready to be used.)"
    ::= { as2MemoryEntry 53 }

as2memPagePool8AllocKB OBJECT-TYPE
    SYNTAX     Gauge32
    MAX-ACCESS read-only
    STATUS     current
    DESCRIPTION
	    "Memory borrowed from 64KB page pool, in KB. 
	    This memory is given away to other parts of the
	    server."
    ::= { as2MemoryEntry 54 }

as2memPagePool8LookasideKB OBJECT-TYPE
    SYNTAX     Gauge32
    MAX-ACCESS read-only
    STATUS     current
    DESCRIPTION
	    "Current memory in 8KB lookaside list, in KB. 
	    (Memory pages ready to be used.)"
    ::= { as2MemoryEntry 55 }

as2memPotenMemAggregatMapFileKB OBJECT-TYPE
    SYNTAX     Gauge32
    MAX-ACCESS read-only
    STATUS     current
    DESCRIPTION
	    "Potential in-memory aggregation map file KB."
    ::= { as2MemoryEntry 56 }

as2memPotenMemDimenIndHashFilKB OBJECT-TYPE
    SYNTAX     Gauge32
    MAX-ACCESS read-only
    STATUS     current
    DESCRIPTION
	    "Potential in-memory dimension index (hash)
	    file KB."
    ::= { as2MemoryEntry 57 }

as2memPotenMemDimenProFileKB OBJECT-TYPE
    SYNTAX     Gauge32
    MAX-ACCESS read-only
    STATUS     current
    DESCRIPTION
	    "Potential in-memory dimension proty file KB."
    ::= { as2MemoryEntry 58 }

as2memPotenMemDimenStringFileKB OBJECT-TYPE
    SYNTAX     Gauge32
    MAX-ACCESS read-only
    STATUS     current
    DESCRIPTION
	    "Potential in-memory dimension string file KB."
    ::= { as2MemoryEntry 59 }

as2memPotenMemFactAggregFileKB OBJECT-TYPE
    SYNTAX     Gauge32
    MAX-ACCESS read-only
    STATUS     current
    DESCRIPTION
	    "Potential in-memory fact aggregation file KB."
    ::= { as2MemoryEntry 60 }

as2memPotenMemFactDataFileKB OBJECT-TYPE
    SYNTAX     Gauge32
    MAX-ACCESS read-only
    STATUS     current
    DESCRIPTION
	    "Potential in-memory fact data file KB."
    ::= { as2MemoryEntry 61 }

as2memPotenMemFactStringFileKB OBJECT-TYPE
    SYNTAX     Gauge32
    MAX-ACCESS read-only
    STATUS     current
    DESCRIPTION
	    "Potential in-memory fact string file KB."
    ::= { as2MemoryEntry 62 }

as2memPotentialInMemoryMapFileKB OBJECT-TYPE
    SYNTAX     Gauge32
    MAX-ACCESS read-only
    STATUS     current
    DESCRIPTION
	    "Potential in-memory map file KB."
    ::= { as2MemoryEntry 63 }

as2memPotenMemOtherFileKB OBJECT-TYPE
    SYNTAX     Gauge32
    MAX-ACCESS read-only
    STATUS     current
    DESCRIPTION
	    "Potential in-memory other file KB."
    ::= { as2MemoryEntry 64 }

as2memQuotaBlocked OBJECT-TYPE
    SYNTAX     Gauge32
    MAX-ACCESS read-only
    STATUS     current
    DESCRIPTION
	    "Current number of quota requests that are
	    blocked until other memory quotas are freed."
    ::= { as2MemoryEntry 65 }

as2memQuotaKB OBJECT-TYPE
    SYNTAX     Gauge32
    MAX-ACCESS read-only
    STATUS     current
    DESCRIPTION
	    "Current memory quota, in KB.  Memory quota is
	    also known as a memory grant or memory
	    reservation."
    ::= { as2MemoryEntry 66 }

as2ProactiveCachingTable OBJECT-TYPE
    SYNTAX     SEQUENCE OF ProactiveCachingEntry
    MAX-ACCESS not-accessible
    STATUS     current
    DESCRIPTION
	    "Statistics related to Microsoft Analysis
	    Services Proactive Caching."
    ::= { analysisServicesV2 9 }

as2ProactiveCachingEntry OBJECT-TYPE
    SYNTAX     ProactiveCachingEntry
    MAX-ACCESS not-accessible
    STATUS     current
    DESCRIPTION
	    "Performance information for one SQL Server
	    name instance."
    INDEX      { as2NameIndex }
    ::= { as2ProactiveCachingTable 1 }

ProactiveCachingEntry ::= SEQUENCE {
    as2pcNotificationsPerSec Gauge32,
    as2pcProactiveCachingBeginPerSec Gauge32,
    as2pcProactiveCachCompSec Gauge32,
    as2pcProcessCancellationsSec Gauge32
}

as2pcNotificationsPerSec OBJECT-TYPE
    SYNTAX     Gauge32
    MAX-ACCESS read-only
    STATUS     current
    DESCRIPTION
	    "Rate of notifications from relational
	    database."
    ::= { as2ProactiveCachingEntry 1 }

as2pcProactiveCachingBeginPerSec OBJECT-TYPE
    SYNTAX     Gauge32
    MAX-ACCESS read-only
    STATUS     current
    DESCRIPTION
	    "Rate of proactive caching begin."
    ::= { as2ProactiveCachingEntry 2 }

as2pcProactiveCachCompSec OBJECT-TYPE
    SYNTAX     Gauge32
    MAX-ACCESS read-only
    STATUS     current
    DESCRIPTION
	    "Rate of proactive caching completion."
    ::= { as2ProactiveCachingEntry 3 }

as2pcProcessCancellationsSec OBJECT-TYPE
    SYNTAX     Gauge32
    MAX-ACCESS read-only
    STATUS     current
    DESCRIPTION
	    "Rate of processing cancellations caused by
	    notifications."
    ::= { as2ProactiveCachingEntry 4 }

as2ProcAggregationsTable OBJECT-TYPE
    SYNTAX     SEQUENCE OF ProcAggregationsEntry
    MAX-ACCESS not-accessible
    STATUS     current
    DESCRIPTION
	    "Statistics related to Microsoft Analysis
	    Services processing of aggregations in MOLAP
	    data files."
    ::= { analysisServicesV2 10 }

as2ProcAggregationsEntry OBJECT-TYPE
    SYNTAX     ProcAggregationsEntry
    MAX-ACCESS not-accessible
    STATUS     current
    DESCRIPTION
	    "Performance information for one SQL Server
	    name instance."
    INDEX      { as2NameIndex }
    ::= { as2ProcAggregationsTable 1 }

ProcAggregationsEntry ::= SEQUENCE {
    as2paCurrentPartitions Gauge32,
    as2paMemorySizeBytes Gauge32,
    as2paMemorySizeRows Gauge32,
    as2paRowsCreatedPerSec Gauge32,
    as2paRowsMergedPerSec Gauge32,
    as2paTempFileBytesWrittenPerSec Gauge32,
    as2paTempFileRowsWrittenPerSec Gauge32,
    as2paTotalPartitions Gauge32
}

as2paCurrentPartitions OBJECT-TYPE
    SYNTAX     Gauge32
    MAX-ACCESS read-only
    STATUS     current
    DESCRIPTION
	    "Current number of partitions being processed."
    ::= { as2ProcAggregationsEntry 1 }

as2paMemorySizeBytes OBJECT-TYPE
    SYNTAX     Gauge32
    MAX-ACCESS read-only
    STATUS     current
    DESCRIPTION
	    "Size of current aggregations in memory.  This
	    count is an estimate."
    ::= { as2ProcAggregationsEntry 2 }

as2paMemorySizeRows OBJECT-TYPE
    SYNTAX     Gauge32
    MAX-ACCESS read-only
    STATUS     current
    DESCRIPTION
	    "Size of current aggregations in memory.  This
	    count is an estimate."
    ::= { as2ProcAggregationsEntry 3 }

as2paRowsCreatedPerSec OBJECT-TYPE
    SYNTAX     Gauge32
    MAX-ACCESS read-only
    STATUS     current
    DESCRIPTION
	    "Rate of aggregation rows created."
    ::= { as2ProcAggregationsEntry 4 }

as2paRowsMergedPerSec OBJECT-TYPE
    SYNTAX     Gauge32
    MAX-ACCESS read-only
    STATUS     current
    DESCRIPTION
	    "Rate of rows merged or inserted into an
	    aggregation."
    ::= { as2ProcAggregationsEntry 5 }

as2paTempFileBytesWrittenPerSec OBJECT-TYPE
    SYNTAX     Gauge32
    MAX-ACCESS read-only
    STATUS     current
    DESCRIPTION
	    "Rate of writing bytes to a temporary file. 
	    Temporary files are written when aggregations
	    exceed memory limits."
    ::= { as2ProcAggregationsEntry 6 }

as2paTempFileRowsWrittenPerSec OBJECT-TYPE
    SYNTAX     Gauge32
    MAX-ACCESS read-only
    STATUS     current
    DESCRIPTION
	    "Rate of writing rows to a temporary file. 
	    Temporary files are written when aggregations
	    exceed memory limits."
    ::= { as2ProcAggregationsEntry 7 }

as2paTotalPartitions OBJECT-TYPE
    SYNTAX     Gauge32
    MAX-ACCESS read-only
    STATUS     current
    DESCRIPTION
	    "Total number of partitions processed
	    (successfully or otherwise)."
    ::= { as2ProcAggregationsEntry 8 }

as2ProcIndexesTable OBJECT-TYPE
    SYNTAX     SEQUENCE OF AnalysisServicesProcIndexesEntry
    MAX-ACCESS not-accessible
    STATUS     current
    DESCRIPTION
	    "Statistics related to Microsoft Analysis
	    Services processing of indexes for MOLAP data
	    files."
    ::= { analysisServicesV2 11 }

as2ProcIndexesEntry OBJECT-TYPE
    SYNTAX     AnalysisServicesProcIndexesEntry
    MAX-ACCESS not-accessible
    STATUS     current
    DESCRIPTION
	    "Performance information for one SQL Server
	    name instance."
    INDEX      { as2NameIndex }
    ::= { as2ProcIndexesTable 1 }

AnalysisServicesProcIndexesEntry ::= SEQUENCE {
    as2ProcIndexesCurrentPartitions Gauge32,
    as2ProcIndexesRowsPerSec Gauge32,
    as2ProcIndexesTotalPartitions Gauge32,
    as2ProcIndexesTotalRows Gauge32
}

as2ProcIndexesCurrentPartitions OBJECT-TYPE
    SYNTAX     Gauge32
    MAX-ACCESS read-only
    STATUS     current
    DESCRIPTION
	    "Current number of partitions being processed."
    ::= { as2ProcIndexesEntry 1 }

as2ProcIndexesRowsPerSec OBJECT-TYPE
    SYNTAX     Gauge32
    MAX-ACCESS read-only
    STATUS     current
    DESCRIPTION
	    "Rate of rows from MOLAP files used to create
	    indexes."
    ::= { as2ProcIndexesEntry 2 }

as2ProcIndexesTotalPartitions OBJECT-TYPE
    SYNTAX     Gauge32
    MAX-ACCESS read-only
    STATUS     current
    DESCRIPTION
	    "Total number of partitions processed
	    (successfully or otherwise)."
    ::= { as2ProcIndexesEntry 3 }

as2ProcIndexesTotalRows OBJECT-TYPE
    SYNTAX     Gauge32
    MAX-ACCESS read-only
    STATUS     current
    DESCRIPTION
	    "Total rows from MOLAP files used to create
	    indexes."
    ::= { as2ProcIndexesEntry 4 }

as2ProcessingTable OBJECT-TYPE
    SYNTAX     SEQUENCE OF AnalysisServicesProcessingEntry
    MAX-ACCESS not-accessible
    STATUS     current
    DESCRIPTION
	    "Statistics related to Microsoft Analysis
	    Services processing of data."
    ::= { analysisServicesV2 12 }

as2ProcessingEntry OBJECT-TYPE
    SYNTAX     AnalysisServicesProcessingEntry
    MAX-ACCESS not-accessible
    STATUS     current
    DESCRIPTION
	    "Performance information for one SQL Server
	    name instance."
    INDEX      { as2NameIndex }
    ::= { as2ProcessingTable 1 }

AnalysisServicesProcessingEntry ::= SEQUENCE {
    as2ProcessingRowsConvertedPerSec Gauge32,
    as2ProcessingRowsReadPerSec Gauge32,
    as2ProcessingRowsWrittenPerSec Gauge32,
    as2ProcessingTotalRowsConverted Gauge32,
    as2ProcessingTotalRowsRead Gauge32,
    as2ProcessingTotalRowsWritten Gauge32
}

as2ProcessingRowsConvertedPerSec OBJECT-TYPE
    SYNTAX     Gauge32
    MAX-ACCESS read-only
    STATUS     current
    DESCRIPTION
	    "Rate of rows converted during processing."
    ::= { as2ProcessingEntry 1 }

as2ProcessingRowsReadPerSec OBJECT-TYPE
    SYNTAX     Gauge32
    MAX-ACCESS read-only
    STATUS     current
    DESCRIPTION
	    "Rate of rows read from all relational
	    databases."
    ::= { as2ProcessingEntry 2 }

as2ProcessingRowsWrittenPerSec OBJECT-TYPE
    SYNTAX     Gauge32
    MAX-ACCESS read-only
    STATUS     current
    DESCRIPTION
	    "Rate of rows written during processing."
    ::= { as2ProcessingEntry 3 }

as2ProcessingTotalRowsConverted OBJECT-TYPE
    SYNTAX     Gauge32
    MAX-ACCESS read-only
    STATUS     current
    DESCRIPTION
	    "Count of rows converted during processing."
    ::= { as2ProcessingEntry 4 }

as2ProcessingTotalRowsRead OBJECT-TYPE
    SYNTAX     Gauge32
    MAX-ACCESS read-only
    STATUS     current
    DESCRIPTION
	    "Count of rows read from all relational
	    databases."
    ::= { as2ProcessingEntry 5 }

as2ProcessingTotalRowsWritten OBJECT-TYPE
    SYNTAX     Gauge32
    MAX-ACCESS read-only
    STATUS     current
    DESCRIPTION
	    "Count of rows written during processing."
    ::= { as2ProcessingEntry 6 }

as2StorageEngineQueryTable OBJECT-TYPE
    SYNTAX     SEQUENCE OF StorageEngineQueryEntry
    MAX-ACCESS not-accessible
    STATUS     current
    DESCRIPTION
	    "Statistics related to Microsoft Analysis
	    Services storage engine queries."
    ::= { analysisServicesV2 13 }

as2StorageEngineQueryEntry OBJECT-TYPE
    SYNTAX     StorageEngineQueryEntry
    MAX-ACCESS not-accessible
    STATUS     current
    DESCRIPTION
	    "Performance information for one SQL Server
	    name instance."
    INDEX      { as2NameIndex }
    ::= { as2StorageEngineQueryTable 1 }

StorageEngineQueryEntry ::= SEQUENCE {
    as2seqAggregationHitsPerSec Gauge32,
    as2seqAggregationLookupsPerSec Gauge32,
    as2seqAvgTimePerQuery Gauge32,
    as2seqBytesSentPerSec Gauge32,
    as2seqCalculationCacheHitsPerSec Gauge32,
    as2seqCalculationCacheLookupsSec Gauge32,
    as2seqCurrentDimensionQueries Gauge32,
    as2seqCurrentMeasureGroupQueries Gauge32,
    as2seqDataBytesPerSec Gauge32,
    as2seqDataReadsPerSec Gauge32,
    as2seqDimensionCacheHitsPerSec Gauge32,
    as2seqDimensionCacheLookupSec Gauge32,
    as2seqDimensionQueriesPerSec Gauge32,
    as2seqFlatCacheHitsPerSec Gauge32,
    as2seqFlatCacheLookupsPerSec Gauge32,
    as2seqMapBytesPerSec Gauge32,
    as2seqMapReadsPerSec Gauge32,
    as2seqMeasureGroupCacheHitsSec Gauge32,
    as2seqMeasureGroupCacheLookupSec Gauge32,
    as2seqMeasureGroupQueriesPerSec Gauge32,
    as2seqNetworkRoundTripsPerSec Gauge32,
    as2seqPersistedCacheHitsPerSec Gauge32,
    as2seqsistedCacheLookupsSec Gauge32,
    as2seqQueriesAnsweredPerSec Gauge32,
    as2seqQueryFromCacheDirectSec Gauge32,
    as2seqQueryFromCacheFilteredSec Gauge32,
    as2seqQueriesFromFilePerSec Gauge32,
    as2seqRowsSentPerSec Gauge32,
    as2seqTotalBytesSent Gauge32,
    as2seqTotalDimensionQueries Gauge32,
    as2seqTotalMeasureGroupQueries Gauge32,
    as2seqTotalNetworkRoundTrips Gauge32,
    as2seqTotalQueriesAnswered Gauge32,
    as2seqTotalQueryFromCacheDirect Gauge32,
    as2seqTotalQueryFromCachFiltered Gauge32,
    as2seqTotalQueriesFromFile Gauge32,
    as2seqTotalRowsSent Gauge32
}

as2seqAggregationHitsPerSec OBJECT-TYPE
    SYNTAX     Gauge32
    MAX-ACCESS read-only
    STATUS     current
    DESCRIPTION
	    "Rate of aggregation hits."
    ::= { as2StorageEngineQueryEntry 1 }

as2seqAggregationLookupsPerSec OBJECT-TYPE
    SYNTAX     Gauge32
    MAX-ACCESS read-only
    STATUS     current
    DESCRIPTION
	    "Rate of aggregation lookups."
    ::= { as2StorageEngineQueryEntry 2 }

as2seqAvgTimePerQuery OBJECT-TYPE
    SYNTAX     Gauge32
    MAX-ACCESS read-only
    STATUS     current
    DESCRIPTION
	    "Average time per query, in milliseconds. 
	    Response time based on queries answered since
	    the last counter measurement."
    ::= { as2StorageEngineQueryEntry 3 }

as2seqBytesSentPerSec OBJECT-TYPE
    SYNTAX     Gauge32
    MAX-ACCESS read-only
    STATUS     current
    DESCRIPTION
	    "Rate of bytes sent by server to clients, in
	    response to queries."
    ::= { as2StorageEngineQueryEntry 4 }

as2seqCalculationCacheHitsPerSec OBJECT-TYPE
    SYNTAX     Gauge32
    MAX-ACCESS read-only
    STATUS     current
    DESCRIPTION
	    "Rate of calculation cache hits.  This includes
	    global, session, and query scope calculation
	    caches."
    ::= { as2StorageEngineQueryEntry 5 }

as2seqCalculationCacheLookupsSec OBJECT-TYPE
    SYNTAX     Gauge32
    MAX-ACCESS read-only
    STATUS     current
    DESCRIPTION
	    "Rate of calculation cache lookups.  This
	    includes global, session, and query scope
	    calculation caches."
    ::= { as2StorageEngineQueryEntry 6 }

as2seqCurrentDimensionQueries OBJECT-TYPE
    SYNTAX     Gauge32
    MAX-ACCESS read-only
    STATUS     current
    DESCRIPTION
	    "Current number of dimension queries being
	    actively worked on."
    ::= { as2StorageEngineQueryEntry 7 }

as2seqCurrentMeasureGroupQueries OBJECT-TYPE
    SYNTAX     Gauge32
    MAX-ACCESS read-only
    STATUS     current
    DESCRIPTION
	    "Current number of measure group queries being
	    actively worked on."
    ::= { as2StorageEngineQueryEntry 8 }

as2seqDataBytesPerSec OBJECT-TYPE
    SYNTAX     Gauge32
    MAX-ACCESS read-only
    STATUS     current
    DESCRIPTION
	    "Bytes read from the Data file."
    ::= { as2StorageEngineQueryEntry 9 }

as2seqDataReadsPerSec OBJECT-TYPE
    SYNTAX     Gauge32
    MAX-ACCESS read-only
    STATUS     current
    DESCRIPTION
	    "Number of logical read operations using the
	    Data file."
    ::= { as2StorageEngineQueryEntry 10 }

as2seqDimensionCacheHitsPerSec OBJECT-TYPE
    SYNTAX     Gauge32
    MAX-ACCESS read-only
    STATUS     current
    DESCRIPTION
	    "Rate of dimension cache hits."
    ::= { as2StorageEngineQueryEntry 11 }

as2seqDimensionCacheLookupSec OBJECT-TYPE
    SYNTAX     Gauge32
    MAX-ACCESS read-only
    STATUS     current
    DESCRIPTION
	    "Rate of dimension cache lookups."
    ::= { as2StorageEngineQueryEntry 12 }

as2seqDimensionQueriesPerSec OBJECT-TYPE
    SYNTAX     Gauge32
    MAX-ACCESS read-only
    STATUS     current
    DESCRIPTION
	    "Rate of dimension queries"
    ::= { as2StorageEngineQueryEntry 13 }

as2seqFlatCacheHitsPerSec OBJECT-TYPE
    SYNTAX     Gauge32
    MAX-ACCESS read-only
    STATUS     current
    DESCRIPTION
	    "Rate of flat cache hits.  This includes
	    global, session, and query scope flat caches."
    ::= { as2StorageEngineQueryEntry 14 }

as2seqFlatCacheLookupsPerSec OBJECT-TYPE
    SYNTAX     Gauge32
    MAX-ACCESS read-only
    STATUS     current
    DESCRIPTION
	    "Rate of flat cache lookups.  This includes
	    global, session, and query scope flat caches."
    ::= { as2StorageEngineQueryEntry 15 }

as2seqMapBytesPerSec OBJECT-TYPE
    SYNTAX     Gauge32
    MAX-ACCESS read-only
    STATUS     current
    DESCRIPTION
	    "Bytes read from the Map file."
    ::= { as2StorageEngineQueryEntry 16 }

as2seqMapReadsPerSec OBJECT-TYPE
    SYNTAX     Gauge32
    MAX-ACCESS read-only
    STATUS     current
    DESCRIPTION
	    "Number of logical read operations using the
	    Map file."
    ::= { as2StorageEngineQueryEntry 17 }

as2seqMeasureGroupCacheHitsSec OBJECT-TYPE
    SYNTAX     Gauge32
    MAX-ACCESS read-only
    STATUS     current
    DESCRIPTION
	    "Rate of measure group cache hits."
    ::= { as2StorageEngineQueryEntry 18 }

as2seqMeasureGroupCacheLookupSec OBJECT-TYPE
    SYNTAX     Gauge32
    MAX-ACCESS read-only
    STATUS     current
    DESCRIPTION
	    "Rate of measure group cache lookups."
    ::= { as2StorageEngineQueryEntry 19 }

as2seqMeasureGroupQueriesPerSec OBJECT-TYPE
    SYNTAX     Gauge32
    MAX-ACCESS read-only
    STATUS     current
    DESCRIPTION
	    "Rate of measure group queries"
    ::= { as2StorageEngineQueryEntry 20 }

as2seqNetworkRoundTripsPerSec OBJECT-TYPE
    SYNTAX     Gauge32
    MAX-ACCESS read-only
    STATUS     current
    DESCRIPTION
	    "Rate of network round trips.  This includes
	    all client/server communication."
    ::= { as2StorageEngineQueryEntry 21 }

as2seqPersistedCacheHitsPerSec OBJECT-TYPE
    SYNTAX     Gauge32
    MAX-ACCESS read-only
    STATUS     current
    DESCRIPTION
	    "Rate of persisted cache hits.  Persisted
	    caches are created by the MDX script CACHE
	    statement."
    ::= { as2StorageEngineQueryEntry 22 }

as2seqsistedCacheLookupsSec OBJECT-TYPE
    SYNTAX     Gauge32
    MAX-ACCESS read-only
    STATUS     current
    DESCRIPTION
	    "Rate of sisted cache lookups.  sisted caches
	    are created by the MDX script CACHE statement."
    ::= { as2StorageEngineQueryEntry 23 }

as2seqQueriesAnsweredPerSec OBJECT-TYPE
    SYNTAX     Gauge32
    MAX-ACCESS read-only
    STATUS     current
    DESCRIPTION
	    "Rate of queries answered."
    ::= { as2StorageEngineQueryEntry 24 }

as2seqQueryFromCacheDirectSec OBJECT-TYPE
    SYNTAX     Gauge32
    MAX-ACCESS read-only
    STATUS     current
    DESCRIPTION
	    "Rate of queries answered from cache directly."
    ::= { as2StorageEngineQueryEntry 25 }

as2seqQueryFromCacheFilteredSec OBJECT-TYPE
    SYNTAX     Gauge32
    MAX-ACCESS read-only
    STATUS     current
    DESCRIPTION
	    "Rate of queries answered by filtering existing
	    cache entry."
    ::= { as2StorageEngineQueryEntry 26 }

as2seqQueriesFromFilePerSec OBJECT-TYPE
    SYNTAX     Gauge32
    MAX-ACCESS read-only
    STATUS     current
    DESCRIPTION
	    "Rate of queries answered from files."
    ::= { as2StorageEngineQueryEntry 27 }

as2seqRowsSentPerSec OBJECT-TYPE
    SYNTAX     Gauge32
    MAX-ACCESS read-only
    STATUS     current
    DESCRIPTION
	    "Rate of rows sent by server to clients."
    ::= { as2StorageEngineQueryEntry 28 }

as2seqTotalBytesSent OBJECT-TYPE
    SYNTAX     Gauge32
    MAX-ACCESS read-only
    STATUS     current
    DESCRIPTION
	    "Total bytes sent by server to clients, in
	    response to queries."
    ::= { as2StorageEngineQueryEntry 29 }

as2seqTotalDimensionQueries OBJECT-TYPE
    SYNTAX     Gauge32
    MAX-ACCESS read-only
    STATUS     current
    DESCRIPTION
	    "Total number of dimension queries."
    ::= { as2StorageEngineQueryEntry 30 }

as2seqTotalMeasureGroupQueries OBJECT-TYPE
    SYNTAX     Gauge32
    MAX-ACCESS read-only
    STATUS     current
    DESCRIPTION
	    "Total number of queries to measure group."
    ::= { as2StorageEngineQueryEntry 31 }

as2seqTotalNetworkRoundTrips OBJECT-TYPE
    SYNTAX     Gauge32
    MAX-ACCESS read-only
    STATUS     current
    DESCRIPTION
	    "Total network round trips.  This includes all
	    client/server communication."
    ::= { as2StorageEngineQueryEntry 32 }

as2seqTotalQueriesAnswered OBJECT-TYPE
    SYNTAX     Gauge32
    MAX-ACCESS read-only
    STATUS     current
    DESCRIPTION
	    "Total number of queries answered."
    ::= { as2StorageEngineQueryEntry 33 }

as2seqTotalQueryFromCacheDirect OBJECT-TYPE
    SYNTAX     Gauge32
    MAX-ACCESS read-only
    STATUS     current
    DESCRIPTION
	    "Total number of queries derived directly from
	    cache.  Note that this is  partition."
    ::= { as2StorageEngineQueryEntry 34 }

as2seqTotalQueryFromCachFiltered OBJECT-TYPE
    SYNTAX     Gauge32
    MAX-ACCESS read-only
    STATUS     current
    DESCRIPTION
	    "Total queries answered by filtering existing
	    cache entries."
    ::= { as2StorageEngineQueryEntry 35 }

as2seqTotalQueriesFromFile OBJECT-TYPE
    SYNTAX     Gauge32
    MAX-ACCESS read-only
    STATUS     current
    DESCRIPTION
	    "Total number of queries answered from files."
    ::= { as2StorageEngineQueryEntry 36 }

as2seqTotalRowsSent OBJECT-TYPE
    SYNTAX     Gauge32
    MAX-ACCESS read-only
    STATUS     current
    DESCRIPTION
	    "Total rows sent by server to clients."
    ::= { as2StorageEngineQueryEntry 37 }

as2ThreadsTable OBJECT-TYPE
    SYNTAX     SEQUENCE OF AnalysisServicesThreadsEntry
    MAX-ACCESS not-accessible
    STATUS     current
    DESCRIPTION
	    "Statistics related to Microsoft Analysis
	    Services threads."
    ::= { analysisServicesV2 14 }

as2ThreadsEntry OBJECT-TYPE
    SYNTAX     AnalysisServicesThreadsEntry
    MAX-ACCESS not-accessible
    STATUS     current
    DESCRIPTION
	    "Performance information for one SQL Server
	    name instance."
    INDEX      { as2NameIndex }
    ::= { as2ThreadsTable 1 }

AnalysisServicesThreadsEntry ::= SEQUENCE {
    as2ThdsLongParsingBusyThreads Gauge32,
    as2ThdsLongParsingIdleThreads Gauge32,
    as2ThdsLongParsingJobQueueLength Gauge32,
    as2ThdsLongParsingJobRate Gauge32,
    as2ThdsProcessingPoolBusyThreads Gauge32,
    as2ThdsProcessingPoolIdleThreads Gauge32,
    as2ThdsProcessPoolJobQueueLength Gauge32,
    as2ThdsProcessingPoolJobRate Gauge32,
    as2ThdsQueryPoolBusyThreads Gauge32,
    as2ThdsQueryPoolIdleThreads Gauge32,
    as2ThdsQueryPoolJobQueueLength Gauge32,
    as2ThdsQueryPoolJobRate Gauge32,
    as2ThdsShortParsingBusyThreads Gauge32,
    as2ThdsShortParsingIdleThreads Gauge32,
    as2ThdsShortParsingJobQueueLeng Gauge32,
    as2ThdsShortParsingJobRate Gauge32
}

as2ThdsLongParsingBusyThreads OBJECT-TYPE
    SYNTAX     Gauge32
    MAX-ACCESS read-only
    STATUS     current
    DESCRIPTION
	    "Number of busy threads in the long parsing
	    thread pool."
    ::= { as2ThreadsEntry 1 }

as2ThdsLongParsingIdleThreads OBJECT-TYPE
    SYNTAX     Gauge32
    MAX-ACCESS read-only
    STATUS     current
    DESCRIPTION
	    "Number of idle threads in the long parsing
	    thread pool."
    ::= { as2ThreadsEntry 2 }

as2ThdsLongParsingJobQueueLength OBJECT-TYPE
    SYNTAX     Gauge32
    MAX-ACCESS read-only
    STATUS     current
    DESCRIPTION
	    "Number of jobs in the queue of the long
	    parsing thread pool."
    ::= { as2ThreadsEntry 3 }

as2ThdsLongParsingJobRate OBJECT-TYPE
    SYNTAX     Gauge32
    MAX-ACCESS read-only
    STATUS     current
    DESCRIPTION
	    "Rate of jobs through the long parsing thread
	    pool."
    ::= { as2ThreadsEntry 4 }

as2ThdsProcessingPoolBusyThreads OBJECT-TYPE
    SYNTAX     Gauge32
    MAX-ACCESS read-only
    STATUS     current
    DESCRIPTION
	    "Number of busy threads in the processing
	    thread pool."
    ::= { as2ThreadsEntry 5 }

as2ThdsProcessingPoolIdleThreads OBJECT-TYPE
    SYNTAX     Gauge32
    MAX-ACCESS read-only
    STATUS     current
    DESCRIPTION
	    "Number of idle threads in the processing
	    thread pool."
    ::= { as2ThreadsEntry 6 }

as2ThdsProcessPoolJobQueueLength OBJECT-TYPE
    SYNTAX     Gauge32
    MAX-ACCESS read-only
    STATUS     current
    DESCRIPTION
	    "Number of jobs in the queue of the processing
	    thread pool."
    ::= { as2ThreadsEntry 7 }

as2ThdsProcessingPoolJobRate OBJECT-TYPE
    SYNTAX     Gauge32
    MAX-ACCESS read-only
    STATUS     current
    DESCRIPTION
	    "Rate of jobs through the processing thread
	    pool."
    ::= { as2ThreadsEntry 8 }

as2ThdsQueryPoolBusyThreads OBJECT-TYPE
    SYNTAX     Gauge32
    MAX-ACCESS read-only
    STATUS     current
    DESCRIPTION
	    "Number of busy threads in the query thread
	    pool."
    ::= { as2ThreadsEntry 9 }

as2ThdsQueryPoolIdleThreads OBJECT-TYPE
    SYNTAX     Gauge32
    MAX-ACCESS read-only
    STATUS     current
    DESCRIPTION
	    "Number of idle threads in the query thread
	    pool."
    ::= { as2ThreadsEntry 10 }

as2ThdsQueryPoolJobQueueLength OBJECT-TYPE
    SYNTAX     Gauge32
    MAX-ACCESS read-only
    STATUS     current
    DESCRIPTION
	    "Number of jobs in the queue of the query
	    thread pool."
    ::= { as2ThreadsEntry 11 }

as2ThdsQueryPoolJobRate OBJECT-TYPE
    SYNTAX     Gauge32
    MAX-ACCESS read-only
    STATUS     current
    DESCRIPTION
	    "Rate of jobs through the query thread pool."
    ::= { as2ThreadsEntry 12 }

as2ThdsShortParsingBusyThreads OBJECT-TYPE
    SYNTAX     Gauge32
    MAX-ACCESS read-only
    STATUS     current
    DESCRIPTION
	    "Number of busy threads in the short parsing
	    thread pool."
    ::= { as2ThreadsEntry 13 }

as2ThdsShortParsingIdleThreads OBJECT-TYPE
    SYNTAX     Gauge32
    MAX-ACCESS read-only
    STATUS     current
    DESCRIPTION
	    "Number of idle threads in the short parsing
	    thread pool."
    ::= { as2ThreadsEntry 14 }

as2ThdsShortParsingJobQueueLeng OBJECT-TYPE
    SYNTAX     Gauge32
    MAX-ACCESS read-only
    STATUS     current
    DESCRIPTION
	    "Number of jobs in the queue of the short
	    parsing thread pool."
    ::= { as2ThreadsEntry 15 }

as2ThdsShortParsingJobRate OBJECT-TYPE
    SYNTAX     Gauge32
    MAX-ACCESS read-only
    STATUS     current
    DESCRIPTION
	    "Rate of jobs through the short parsing thread
	    pool."
    ::= { as2ThreadsEntry 16 }

sqlServerEngineV2 OBJECT IDENTIFIER
    ::= { sqlServerV2 2 }

ss2NameTable OBJECT-TYPE
    SYNTAX     SEQUENCE OF SQLServerNameEntry
    MAX-ACCESS not-accessible
    STATUS     current
    DESCRIPTION
	    "This table contains the list of SQL Server
	    instance names installed. The ss2NameIndex is
	    used to refer to all other SQL Server SNMP
	    entries."
    ::= { sqlServerEngineV2 1 }

ss2NameEntry OBJECT-TYPE
    SYNTAX      SQLServerNameEntry
    MAX-ACCESS not-accessible
    STATUS     current
    DESCRIPTION
	    "Performance information for one SQL Server
	    name instance."
    INDEX      { ss2NameIndex }
    ::= { ss2NameTable 1 }

 SQLServerNameEntry ::= SEQUENCE {
    ss2NameIndex Integer32,
    ss2NameInstance InstanceName
}

ss2NameIndex OBJECT-TYPE
    SYNTAX     Integer32 (1..2147483647)
    MAX-ACCESS read-only
    STATUS     current
    DESCRIPTION
	    "The index number associated with the instance
	    name"
    ::= { ss2NameEntry 1 }

ss2NameInstance OBJECT-TYPE
    SYNTAX     InstanceName
    MAX-ACCESS read-only
    STATUS     current
    DESCRIPTION
	    "The name of the SQL Server installed
	    instance."
    ::= { ss2NameEntry 2 }

ss2AccessMethodsTable OBJECT-TYPE
    SYNTAX     SEQUENCE OF SQLServerAccessMethodsEntry
    MAX-ACCESS not-accessible
    STATUS     current
    DESCRIPTION
	    "The Access Methods object in SQL Server
	    provides counters to monitor how the logical
	    data within the database is accessed. Physical
	    access to the database pages on disk is
	    monitored using the Buffer Manager counters.
	    Monitoring the methods used to access data
	    stored in the database can help you to
	    determine whether query performance can be
	    improved by adding or modifying indexes, adding
	    or moving partitions, adding files or file
	    groups, defragmenting indexes, or by rewriting
	    queries. The Access Methods counters can also
	    be used to monitor the amount of data, indexes,
	    and free space within the database, thereby
	    indicating data volume and fragmentation for
	    each server instance. Excessive index
	    fragmentation can impair performance."
    ::= { sqlServerEngineV2 2 }

ss2AccessMethodsEntry OBJECT-TYPE
    SYNTAX      SQLServerAccessMethodsEntry
    MAX-ACCESS not-accessible
    STATUS     current
    DESCRIPTION
	    "Performance information for one SQL Server
	    AccessMethods instance."
    INDEX      { ss2NameIndex }
    ::= { ss2AccessMethodsTable 1 }

 SQLServerAccessMethodsEntry ::= SEQUENCE {
    ss2amAUCleanupBatchesPerSec Gauge32,
    ss2amAUCleanupsPerSec Gauge32,
    ss2amByReferenceLobCreateCount Gauge32,
    ss2amByReferenceLobUseCount Gauge32,
    ss2amCountLobReadahead Gauge32,
    ss2amCountPullInRow Gauge32,
    ss2amCountPushOffRow Gauge32,
    ss2amDeferredDroppedRowsets Gauge32,
    ss2amDeferredDroppedAUs Gauge32,
    ss2amDroppedRowsetCleanupsPerSec Gauge32,
    ss2amDroppedRowsetsSkippedPerSec Gauge32,
    ss2amExtentDeallocationsPerSec Gauge32,
    ss2amExtentsAllocatedPerSec Gauge32,
    ss2amFailedAUCleanupBatchesSec Gauge32,
    ss2amFailedLeafPageCookie Gauge32,
    ss2amFailedTreePageCookie Gauge32,
    ss2amForwardedRecordsPerSec Gauge32,
    ss2amFreeSpacePageFetchesPerSec Gauge32,
    ss2amFreeSpaceScansPerSec Gauge32,
    ss2amFullScansPerSec Gauge32,
    ss2amIndexSearchesPerSec Gauge32,
    ss2amLobHandleCreateCount Gauge32,
    ss2amLobHandleDestroyCount Gauge32,
    ss2amLobSSProviderCreateCount Gauge32,
    ss2amLobSSProviderDestroyCount Gauge32,
    ss2amLobSSProvideTruncationCount Gauge32,
    ss2amMixedPageAllocationsPerSec Gauge32,
    ss2amPageDeallocationsPerSec Gauge32,
    ss2amPageSplitsPerSec Gauge32,
    ss2amPageCompressionAttemptsSec Gauge32,
    ss2amPagesAllocatedPerSec Gauge32,
    ss2amPagesCompressedPerSec Gauge32,
    ss2amProbeScansPerSec Gauge32,
    ss2amRangeScansPerSec Gauge32,
    ss2amScanPointRevalidationsSec Gauge32,
    ss2amSkippedGhostedRecordsPerSec Gauge32,
    ss2amTableLockEscalationsPerSec Gauge32,
    ss2amUsedLeafPageCookie Gauge32,
    ss2amUsedTreePageCookie Gauge32,
    ss2amWorkfilesCreatedPerSec Gauge32,
    ss2amWorktablesCreatedPerSec Gauge32,
    ss2amWorktablesFromCacheRatio Gauge32
}

ss2amAUCleanupBatchesPerSec OBJECT-TYPE
    SYNTAX     Gauge32
    MAX-ACCESS read-only
    STATUS     current
    DESCRIPTION
	    "The number of batches that completed
	    successfully per second by the background task
	    that cleans up deferred dropped allocation
	    units."
    ::= { ss2AccessMethodsEntry 1 }

ss2amAUCleanupsPerSec OBJECT-TYPE
    SYNTAX     Gauge32
    MAX-ACCESS read-only
    STATUS     current
    DESCRIPTION
	    "The number of allocation units per second that
	    were successfully dropped by the background
	    task that cleans up deferred dropped allocation
	    units. Each allocation unit drop requires
	    multiple batches."
    ::= { ss2AccessMethodsEntry 2 }

ss2amByReferenceLobCreateCount OBJECT-TYPE
    SYNTAX     Gauge32
    MAX-ACCESS read-only
    STATUS     current
    DESCRIPTION
	    "Count of large object (LOB) values that were
	    passed by reference. By-reference lobs are used
	    in certain bulk operations to avoid the cost of
	    passing them by value."
    ::= { ss2AccessMethodsEntry 3 }

ss2amByReferenceLobUseCount OBJECT-TYPE
    SYNTAX     Gauge32
    MAX-ACCESS read-only
    STATUS     current
    DESCRIPTION
	    "Count of by-reference lob values that were
	    used. By-reference lobs are used in certain
	    bulk operations to avoid the cost of passing
	    them by value."
    ::= { ss2AccessMethodsEntry 4 }

ss2amCountLobReadahead OBJECT-TYPE
    SYNTAX     Gauge32
    MAX-ACCESS read-only
    STATUS     current
    DESCRIPTION
	    "Count of lob pages on which readahead was
	    issued."
    ::= { ss2AccessMethodsEntry 5 }

ss2amCountPullInRow OBJECT-TYPE
    SYNTAX     Gauge32
    MAX-ACCESS read-only
    STATUS     current
    DESCRIPTION
	    "Count of values that were pulled in-row from
	    off-row."
    ::= { ss2AccessMethodsEntry 6 }

ss2amCountPushOffRow OBJECT-TYPE
    SYNTAX     Gauge32
    MAX-ACCESS read-only
    STATUS     current
    DESCRIPTION
	    "Count of values that were pushed from in-row
	    to off-row."
    ::= { ss2AccessMethodsEntry 7 }

ss2amDeferredDroppedRowsets OBJECT-TYPE
    SYNTAX     Gauge32
    MAX-ACCESS read-only
    STATUS     current
    DESCRIPTION
	    "The number of rowsets created as a result of
	    aborted online index build operations that are
	    waiting to be dropped by the background task
	    that cleans up deferred dropped rowsets."
    ::= { ss2AccessMethodsEntry 8 }

ss2amDeferredDroppedAUs OBJECT-TYPE
    SYNTAX     Gauge32
    MAX-ACCESS read-only
    STATUS     current
    DESCRIPTION
	    "The number of allocation units waiting to be
	    dropped by the background task that cleans up
	    deferred dropped allocation units."
    ::= { ss2AccessMethodsEntry 9 }

ss2amDroppedRowsetCleanupsPerSec OBJECT-TYPE
    SYNTAX     Gauge32
    MAX-ACCESS read-only
    STATUS     current
    DESCRIPTION
	    "The number of rowsets per second created as a
	    result of aborted online index build operations
	    that were successfully dropped by the
	    background task that cleans up deferred dropped
	    rowsets."
    ::= { ss2AccessMethodsEntry 10 }

ss2amDroppedRowsetsSkippedPerSec OBJECT-TYPE
    SYNTAX     Gauge32
    MAX-ACCESS read-only
    STATUS     current
    DESCRIPTION
	    "The number of rowsets per second created as a
	    result of aborted online index build operations
	    that were skipped by the background task that
	    cleans up deferred dropped rowsets created."
    ::= { ss2AccessMethodsEntry 11 }

ss2amExtentDeallocationsPerSec OBJECT-TYPE
    SYNTAX     Gauge32
    MAX-ACCESS read-only
    STATUS     current
    DESCRIPTION
	    "Number of extents deallocated per second in
	    all databases in this SQL Server instance."
    ::= { ss2AccessMethodsEntry 12 }

ss2amExtentsAllocatedPerSec OBJECT-TYPE
    SYNTAX     Gauge32
    MAX-ACCESS read-only
    STATUS     current
    DESCRIPTION
	    "Number of extents allocated per second in all
	    databases in this SQL Server instance."
    ::= { ss2AccessMethodsEntry 13 }

ss2amFailedAUCleanupBatchesSec OBJECT-TYPE
    SYNTAX     Gauge32
    MAX-ACCESS read-only
    STATUS     current
    DESCRIPTION
	    "The number of batches  second that failed and
	    required retry, by the background task that
	    cleans up deferred dropped allocation units.
	    Failure could be due to lack of memory or disk
	    space, hardware failure and other reasons."
    ::= { ss2AccessMethodsEntry 14 }

ss2amFailedLeafPageCookie OBJECT-TYPE
    SYNTAX     Gauge32
    MAX-ACCESS read-only
    STATUS     current
    DESCRIPTION
	    "The number of times that a leaf page cookie
	    could not be used during an index search since
	    changes happened on the leaf page. The cookie
	    is used to speed up index search."
    ::= { ss2AccessMethodsEntry 15 }

ss2amFailedTreePageCookie OBJECT-TYPE
    SYNTAX     Gauge32
    MAX-ACCESS read-only
    STATUS     current
    DESCRIPTION
	    "The number of times that a tree page cookie
	    could not be used during an index search since
	    changes happened on the parent pages of those
	    tree pages. The cookie is used to speed up
	    index search."
    ::= { ss2AccessMethodsEntry 16 }

ss2amForwardedRecordsPerSec OBJECT-TYPE
    SYNTAX     Gauge32
    MAX-ACCESS read-only
    STATUS     current
    DESCRIPTION
	    "Number of records fetched through forwarded
	    record pointers."
    ::= { ss2AccessMethodsEntry 17 }

ss2amFreeSpacePageFetchesPerSec OBJECT-TYPE
    SYNTAX     Gauge32
    MAX-ACCESS read-only
    STATUS     current
    DESCRIPTION
	    "Number of pages fetched per second by free
	    space scans. These scans search for free space
	    within pages already allocated to an allocation
	    unit, to satisfy requests to insert or modify
	    record fragments."
    ::= { ss2AccessMethodsEntry 18 }

ss2amFreeSpaceScansPerSec OBJECT-TYPE
    SYNTAX     Gauge32
    MAX-ACCESS read-only
    STATUS     current
    DESCRIPTION
	    "Number of scans per second that were initiated
	    to search for free space within pages already
	    allocated to an allocation unit to insert or
	    modify record fragments. Each scan may find
	    multiple pages."
    ::= { ss2AccessMethodsEntry 19 }

ss2amFullScansPerSec OBJECT-TYPE
    SYNTAX     Gauge32
    MAX-ACCESS read-only
    STATUS     current
    DESCRIPTION
	    "Number of unrestricted full scans. These can
	    either be base table or full index scans."
    ::= { ss2AccessMethodsEntry 20 }

ss2amIndexSearchesPerSec OBJECT-TYPE
    SYNTAX     Gauge32
    MAX-ACCESS read-only
    STATUS     current
    DESCRIPTION
	    "Number of index searches. Index searches are
	    used to start range scans, single index record
	    fetches, and to reposition within an index."
    ::= { ss2AccessMethodsEntry 21 }

ss2amLobHandleCreateCount OBJECT-TYPE
    SYNTAX     Gauge32
    MAX-ACCESS read-only
    STATUS     current
    DESCRIPTION
	    "Count of temporary LOBs created."
    ::= { ss2AccessMethodsEntry 22 }

ss2amLobHandleDestroyCount OBJECT-TYPE
    SYNTAX     Gauge32
    MAX-ACCESS read-only
    STATUS     current
    DESCRIPTION
	    "Count of temporary LOBs destroyed."
    ::= { ss2AccessMethodsEntry 23 }

ss2amLobSSProviderCreateCount OBJECT-TYPE
    SYNTAX     Gauge32
    MAX-ACCESS read-only
    STATUS     current
    DESCRIPTION
	    "Count of LOB Storage Service Providers
	    created. One worktable created per LOB Storage
	    Service Provider."
    ::= { ss2AccessMethodsEntry 24 }

ss2amLobSSProviderDestroyCount OBJECT-TYPE
    SYNTAX     Gauge32
    MAX-ACCESS read-only
    STATUS     current
    DESCRIPTION
	    "Count of LOB Storage Service Providers
	    destroyed."
    ::= { ss2AccessMethodsEntry 25 }

ss2amLobSSProvideTruncationCount OBJECT-TYPE
    SYNTAX     Gauge32
    MAX-ACCESS read-only
    STATUS     current
    DESCRIPTION
	    "Count of LOB Storage Service Providers
	    truncated."
    ::= { ss2AccessMethodsEntry 26 }

ss2amMixedPageAllocationsPerSec OBJECT-TYPE
    SYNTAX     Gauge32
    MAX-ACCESS read-only
    STATUS     current
    DESCRIPTION
	    "Number of pages allocated per second from
	    mixed extents. These could be used for storing
	    the IAM pages and the first eight pages that
	    are allocated to an allocation unit."
    ::= { ss2AccessMethodsEntry 27 }

ss2amPageDeallocationsPerSec OBJECT-TYPE
    SYNTAX     Gauge32
    MAX-ACCESS read-only
    STATUS     current
    DESCRIPTION
	    "Number of pages deallocated per second in all
	    databases in this SQL Server instance. These
	    include pages from mixed extents and uniform
	    extents."
    ::= { ss2AccessMethodsEntry 28 }

ss2amPageSplitsPerSec OBJECT-TYPE
    SYNTAX     Gauge32
    MAX-ACCESS read-only
    STATUS     current
    DESCRIPTION
	    "Number of page splits per second that occur as
	    a result of overflowing index pages."
    ::= { ss2AccessMethodsEntry 29 }

ss2amPageCompressionAttemptsSec OBJECT-TYPE
    SYNTAX     Gauge32
    MAX-ACCESS read-only
    STATUS     current
    DESCRIPTION
	    "Number of attempts to compress a database page
	     second"
    ::= { ss2AccessMethodsEntry 30 }

ss2amPagesAllocatedPerSec OBJECT-TYPE
    SYNTAX     Gauge32
    MAX-ACCESS read-only
    STATUS     current
    DESCRIPTION
	    "Number of pages allocated per second in all
	    databases in this SQL Server instance. These
	    include pages allocations from both mixed
	    extents and uniform extents."
    ::= { ss2AccessMethodsEntry 31 }

ss2amPagesCompressedPerSec OBJECT-TYPE
    SYNTAX     Gauge32
    MAX-ACCESS read-only
    STATUS     current
    DESCRIPTION
	    "Number of times a database page was
	    compressed"
    ::= { ss2AccessMethodsEntry 32 }

ss2amProbeScansPerSec OBJECT-TYPE
    SYNTAX     Gauge32
    MAX-ACCESS read-only
    STATUS     current
    DESCRIPTION
	    "Number of probe scans per second that are used
	    to find at most one single qualified row in an
	    index or base table directly."
    ::= { ss2AccessMethodsEntry 33 }

ss2amRangeScansPerSec OBJECT-TYPE
    SYNTAX     Gauge32
    MAX-ACCESS read-only
    STATUS     current
    DESCRIPTION
	    "Number of qualified range scans through
	    indexes per second."
    ::= { ss2AccessMethodsEntry 34 }

ss2amScanPointRevalidationsSec OBJECT-TYPE
    SYNTAX     Gauge32
    MAX-ACCESS read-only
    STATUS     current
    DESCRIPTION
	    "Number of times the scan point had to be
	    revalidated to continue the scan."
    ::= { ss2AccessMethodsEntry 35 }

ss2amSkippedGhostedRecordsPerSec OBJECT-TYPE
    SYNTAX     Gauge32
    MAX-ACCESS read-only
    STATUS     current
    DESCRIPTION
	    "Number of ghosted records per second skipped
	    during scans."
    ::= { ss2AccessMethodsEntry 36 }

ss2amTableLockEscalationsPerSec OBJECT-TYPE
    SYNTAX     Gauge32
    MAX-ACCESS read-only
    STATUS     current
    DESCRIPTION
	    "The number of times locks on a table were
	    escalated."
    ::= { ss2AccessMethodsEntry 37 }

ss2amUsedLeafPageCookie OBJECT-TYPE
    SYNTAX     Gauge32
    MAX-ACCESS read-only
    STATUS     current
    DESCRIPTION
	    "Number of times a leaf page cookie was used
	    successfully during an index search since no
	    change happened on the leaf page. The cookie is
	    used to speed up index search."
    ::= { ss2AccessMethodsEntry 38 }

ss2amUsedTreePageCookie OBJECT-TYPE
    SYNTAX     Gauge32
    MAX-ACCESS read-only
    STATUS     current
    DESCRIPTION
	    "Number of times a tree page cookie was used
	    successfully during an index search since no
	    change happened on the parent page of the tree
	    page. The cookie is used to speed up index
	    search."
    ::= { ss2AccessMethodsEntry 39 }

ss2amWorkfilesCreatedPerSec OBJECT-TYPE
    SYNTAX     Gauge32
    MAX-ACCESS read-only
    STATUS     current
    DESCRIPTION
	    "Number of work files created per second. For
	    example, work files could be used to store
	    temporary results for hash joins and hash
	    aggregates."
    ::= { ss2AccessMethodsEntry 40 }

ss2amWorktablesCreatedPerSec OBJECT-TYPE
    SYNTAX     Gauge32
    MAX-ACCESS read-only
    STATUS     current
    DESCRIPTION
	    "Number of work tables created per second. For
	    example, work tables could be used to store
	    temporary results for query spool, LOB
	    variables, XML variables, and cursors."
    ::= { ss2AccessMethodsEntry 41 }

ss2amWorktablesFromCacheRatio OBJECT-TYPE
    SYNTAX     Gauge32
    MAX-ACCESS read-only
    STATUS     current
    DESCRIPTION
	    "Percentage of work tables created where the
	    initial two pages of the work table were not
	    allocated but were immediately available from
	    the work table cache."
    ::= { ss2AccessMethodsEntry 42 }

ss2BackupDeviceTable OBJECT-TYPE
    SYNTAX     SEQUENCE OF SQLServerBackupDeviceEntry
    MAX-ACCESS not-accessible
    STATUS     current
    DESCRIPTION
	    "The Backup Device object provides counters to
	    monitor Microsoft SQL Server backup devices
	    used for backup and restore operations. Monitor
	    backup devices when you want to determine the
	    throughput or the progress and performance of
	    your backup and restore operations on a per
	    device basis. To monitor the throughput of the
	    entire database backup or restore operation,
	    use the Backup/Restore Throughput/sec counter
	    of the SQL Server Databases object."
    ::= { sqlServerEngineV2 3 }

ss2BackupDeviceEntry OBJECT-TYPE
    SYNTAX     SQLServerBackupDeviceEntry
    MAX-ACCESS not-accessible
    STATUS     current
    DESCRIPTION
	    "Performance information for one particular
	    instance of 'Backup Device' object."
    INDEX      { ss2NameIndex, ss2BackupDeviceInstance }
    ::= { ss2BackupDeviceTable 1 }

SQLServerBackupDeviceEntry ::= SEQUENCE {
    ss2BackupDeviceInstance InstanceName,
    ss2BackupDeviceDeviceputBytesSec Gauge32
}

ss2BackupDeviceInstance OBJECT-TYPE
    SYNTAX     InstanceName
    MAX-ACCESS read-only
    STATUS     current
    DESCRIPTION
	    "Instance name."
    ::= { ss2BackupDeviceEntry 1 }

ss2BackupDeviceDeviceputBytesSec OBJECT-TYPE
    SYNTAX     Gauge32
    MAX-ACCESS read-only
    STATUS     current
    DESCRIPTION
	    "Read/write throughput for a backup device."
    ::= { ss2BackupDeviceEntry 2 }

ss2BrokerActivationTable OBJECT-TYPE
    SYNTAX     SEQUENCE OF SQLServerBrokerActivationEntry
    MAX-ACCESS not-accessible
    STATUS     current
    DESCRIPTION
	    "The BrokerActivation performance object
	    contains performance counters that report
	    information on stored procedure activation. "
    ::= { sqlServerEngineV2 4 }

ss2BrokerActivationEntry OBJECT-TYPE
    SYNTAX     SQLServerBrokerActivationEntry
    MAX-ACCESS not-accessible
    STATUS     current
    DESCRIPTION
	    "Performance information for one particular
	    instance of 'Broker Activation' object."
    INDEX      { ss2NameIndex, ss2baInstance }
    ::= { ss2BrokerActivationTable 1 }

SQLServerBrokerActivationEntry ::= SEQUENCE {
    ss2baInstance InstanceName,
    ss2baStoredProceduresInvokedSec Gauge32,
    ss2baTaskLimitReached Gauge32,
    ss2baTaskLimitReachedPerSec Gauge32,
    ss2baTasksAbortedPerSec Gauge32,
    ss2baTasksRunning Gauge32,
    ss2baTasksStartedPerSec Gauge32
}

ss2baInstance OBJECT-TYPE
    SYNTAX     InstanceName
    MAX-ACCESS read-only
    STATUS     current
    DESCRIPTION
	    "Instance name."
    ::= { ss2BrokerActivationEntry 1 }

ss2baStoredProceduresInvokedSec OBJECT-TYPE
    SYNTAX     Gauge32
    MAX-ACCESS read-only
    STATUS     current
    DESCRIPTION
	    "The number of stored procedures that are being
	    invoked  second."
    ::= { ss2BrokerActivationEntry 2 }

ss2baTaskLimitReached OBJECT-TYPE
    SYNTAX     Gauge32
    MAX-ACCESS read-only
    STATUS     current
    DESCRIPTION
	    "The total number of times the activated task
	    limit on a queue has been reached."
    ::= { ss2BrokerActivationEntry 3 }

ss2baTaskLimitReachedPerSec OBJECT-TYPE
    SYNTAX     Gauge32
    MAX-ACCESS read-only
    STATUS     current
    DESCRIPTION
	    "The number of times the activated task limit
	    on a queue has been reached per second."
    ::= { ss2BrokerActivationEntry 4 }

ss2baTasksAbortedPerSec OBJECT-TYPE
    SYNTAX     Gauge32
    MAX-ACCESS read-only
    STATUS     current
    DESCRIPTION
	    "The number of activated tasks that are being
	    aborted per second."
    ::= { ss2BrokerActivationEntry 5 }

ss2baTasksRunning OBJECT-TYPE
    SYNTAX     Gauge32
    MAX-ACCESS read-only
    STATUS     current
    DESCRIPTION
	    "The total number of activated tasks that are
	    currently running."
    ::= { ss2BrokerActivationEntry 6 }

ss2baTasksStartedPerSec OBJECT-TYPE
    SYNTAX     Gauge32
    MAX-ACCESS read-only
    STATUS     current
    DESCRIPTION
	    "The number of activated tasks that are being
	    started per second."
    ::= { ss2BrokerActivationEntry 7 }

ss2BrokerStatisticsTable OBJECT-TYPE
    SYNTAX     SEQUENCE OF SQLServerBrokerStatisticsEntry
    MAX-ACCESS not-accessible
    STATUS     current
    DESCRIPTION
	    "The Broker Statistics performance object
	    contains performance counters that report
	    general Service Broker information for an
	    instance of the Database Engine."
    ::= { sqlServerEngineV2 5 }

ss2BrokerStatisticsEntry OBJECT-TYPE
    SYNTAX      SQLServerBrokerStatisticsEntry
    MAX-ACCESS not-accessible
    STATUS     current
    DESCRIPTION
	    "Performance information for one SQL Server
	    BrokerStatistics instance."
    INDEX      { ss2NameIndex }
    ::= { ss2BrokerStatisticsTable 1 }

 SQLServerBrokerStatisticsEntry ::= SEQUENCE {
    ss2bsActivationErrorsTotal Gauge32,
    ss2bsBrokerTransactionRollbacks Gauge32,
    ss2bsCorruptedMessagesTotal Gauge32,
    ss2bsDequeuedTransmissionQMsgSec Gauge32,
    ss2bsDialogTimerEventCount Gauge32,
    ss2bsDroppedMessagesTotal Gauge32,
    ss2bsEnqueuedLocalMessagesTotal Gauge32,
    ss2bsEnqueuedLocalMessagesPerSec Gauge32,
    ss2bsEnqueuedMessagesTotal Gauge32,
    ss2bsEnqueuedMessagesPerSec Gauge32,
    ss2bsEnqueuedP1MessagesPerSec Gauge32,
    ss2bsEnqueuedP10MessagesPerSec Gauge32,
    ss2bsEnqueuedP2MessagesPerSec Gauge32,
    ss2bsEnqueuedP3MessagesPerSec Gauge32,
    ss2bsEnqueuedP4MessagesPerSec Gauge32,
    ss2bsEnqueuedP5MessagesPerSec Gauge32,
    ss2bsEnqueuedP6MessagesPerSec Gauge32,
    ss2bsEnqueuedP7MessagesPerSec Gauge32,
    ss2bsEnqueuedP8MessagesPerSec Gauge32,
    ss2bsEnqueuedP9MessagesPerSec Gauge32,
    ss2bsEnqueuedTransmissionQMsgSec Gauge32,
    ss2bsEnqueuedTransportMsgFragTot Gauge32,
    ss2bsEnqueuedTransportMsgFragSec Gauge32,
    ss2bsEnqueuedTransportMsgsTotal Gauge32,
    ss2bsEnqueuedTransportMsgsPerSec Gauge32,
    ss2bsForwardedMessagesTotal Gauge32,
    ss2bsForwardedMessagesPerSec Gauge32,
    ss2bsForwardedMsgByteTotal Gauge32,
    ss2bsForwardedMsgBytesPerSec Gauge32,
    ss2bsForwardedMsgDiscardedTotal Gauge32,
    ss2bsForwardedMsgsDiscardedSec Gauge32,
    ss2bsForwardedPendingMsgBytes Gauge32,
    ss2bsForwardedPendingMsgCount Gauge32,
    ss2bsSQLReceiveTotal Gauge32,
    ss2bsSQLReceivesPerSec Gauge32,
    ss2bsSQLSendTotal Gauge32,
    ss2bsSQLSendsPerSec Gauge32
}

ss2bsActivationErrorsTotal OBJECT-TYPE
    SYNTAX     Gauge32
    MAX-ACCESS read-only
    STATUS     current
    DESCRIPTION
	    "The number of times an activation stored
	    procedure exited with an error."
    ::= { ss2BrokerStatisticsEntry 1 }

ss2bsBrokerTransactionRollbacks OBJECT-TYPE
    SYNTAX     Gauge32
    MAX-ACCESS read-only
    STATUS     current
    DESCRIPTION
	    "The number of Service Broker related
	    transactions that have rolled back."
    ::= { ss2BrokerStatisticsEntry 2 }

ss2bsCorruptedMessagesTotal OBJECT-TYPE
    SYNTAX     Gauge32
    MAX-ACCESS read-only
    STATUS     current
    DESCRIPTION
	    "The number of corrupted messages that were
	    received in the instance."
    ::= { ss2BrokerStatisticsEntry 3 }

ss2bsDequeuedTransmissionQMsgSec OBJECT-TYPE
    SYNTAX     Gauge32
    MAX-ACCESS read-only
    STATUS     current
    DESCRIPTION
	    "The number of messages that have been removed
	    from the broker transmission queue	second."
    ::= { ss2BrokerStatisticsEntry 4 }

ss2bsDialogTimerEventCount OBJECT-TYPE
    SYNTAX     Gauge32
    MAX-ACCESS read-only
    STATUS     current
    DESCRIPTION
	    "The number of dialog endpoint related timer
	    events in the Broker."
    ::= { ss2BrokerStatisticsEntry 5 }

ss2bsDroppedMessagesTotal OBJECT-TYPE
    SYNTAX     Gauge32
    MAX-ACCESS read-only
    STATUS     current
    DESCRIPTION
	    "The number of messages that were received in
	    the instance but could not be delivered."
    ::= { ss2BrokerStatisticsEntry 6 }

ss2bsEnqueuedLocalMessagesTotal OBJECT-TYPE
    SYNTAX     Gauge32
    MAX-ACCESS read-only
    STATUS     current
    DESCRIPTION
	    "Total number of messages from local endpoints
	    that are successfully delivered directly into
	    local target queues."
    ::= { ss2BrokerStatisticsEntry 7 }

ss2bsEnqueuedLocalMessagesPerSec OBJECT-TYPE
    SYNTAX     Gauge32
    MAX-ACCESS read-only
    STATUS     current
    DESCRIPTION
	    "The number of messages from local endpoints
	    that are successfully delivered directly into
	    local target queues per second."
    ::= { ss2BrokerStatisticsEntry 8 }

ss2bsEnqueuedMessagesTotal OBJECT-TYPE
    SYNTAX     Gauge32
    MAX-ACCESS read-only
    STATUS     current
    DESCRIPTION
	    "Total number of messages from local endpoints
	    and the transport that are successfully
	    delivered into local target queues."
    ::= { ss2BrokerStatisticsEntry 9 }

ss2bsEnqueuedMessagesPerSec OBJECT-TYPE
    SYNTAX     Gauge32
    MAX-ACCESS read-only
    STATUS     current
    DESCRIPTION
	    "The number of messages from local endpoints
	    and the transport that are successfully
	    delivered into local target queues per second."
    ::= { ss2BrokerStatisticsEntry 10 }

ss2bsEnqueuedP1MessagesPerSec OBJECT-TYPE
    SYNTAX     Gauge32
    MAX-ACCESS read-only
    STATUS     current
    DESCRIPTION
	    "The number of priority 1 messages from local
	    endpoints and the transport that are
	    successfully delivered into local target queues
	    per second."
    ::= { ss2BrokerStatisticsEntry 11 }

ss2bsEnqueuedP10MessagesPerSec OBJECT-TYPE
    SYNTAX     Gauge32
    MAX-ACCESS read-only
    STATUS     current
    DESCRIPTION
	    "The number of priority 10 messages from local
	    endpoints and the transport that are
	    successfully delivered into local target queues
	    per second."
    ::= { ss2BrokerStatisticsEntry 12 }

ss2bsEnqueuedP2MessagesPerSec OBJECT-TYPE
    SYNTAX     Gauge32
    MAX-ACCESS read-only
    STATUS     current
    DESCRIPTION
	    "The number of priority 2 messages from local
	    endpoints and the transport that are
	    successfully delivered into local target queues
	    per second."
    ::= { ss2BrokerStatisticsEntry 13 }

ss2bsEnqueuedP3MessagesPerSec OBJECT-TYPE
    SYNTAX     Gauge32
    MAX-ACCESS read-only
    STATUS     current
    DESCRIPTION
	    "The number of priority 3 messages from local
	    endpoints and the transport that are
	    successfully delivered into local target queues
	    per second."
    ::= { ss2BrokerStatisticsEntry 14 }

ss2bsEnqueuedP4MessagesPerSec OBJECT-TYPE
    SYNTAX     Gauge32
    MAX-ACCESS read-only
    STATUS     current
    DESCRIPTION
	    "The number of priority 4 messages from local
	    endpoints and the transport that are
	    successfully delivered into local target queues
	    per second."
    ::= { ss2BrokerStatisticsEntry 15 }

ss2bsEnqueuedP5MessagesPerSec OBJECT-TYPE
    SYNTAX     Gauge32
    MAX-ACCESS read-only
    STATUS     current
    DESCRIPTION
	    "The number of priority 5 messages from local
	    endpoints and the transport that are
	    successfully delivered into local target queues
	    per second."
    ::= { ss2BrokerStatisticsEntry 16 }

ss2bsEnqueuedP6MessagesPerSec OBJECT-TYPE
    SYNTAX     Gauge32
    MAX-ACCESS read-only
    STATUS     current
    DESCRIPTION
	    "The number of priority 6 messages from local
	    endpoints and the transport that are
	    successfully delivered into local target queues
	    per second."
    ::= { ss2BrokerStatisticsEntry 17 }

ss2bsEnqueuedP7MessagesPerSec OBJECT-TYPE
    SYNTAX     Gauge32
    MAX-ACCESS read-only
    STATUS     current
    DESCRIPTION
	    "The number of priority 7 messages from local
	    endpoints and the transport that are
	    successfully delivered into local target queues
	    per second."
    ::= { ss2BrokerStatisticsEntry 18 }

ss2bsEnqueuedP8MessagesPerSec OBJECT-TYPE
    SYNTAX     Gauge32
    MAX-ACCESS read-only
    STATUS     current
    DESCRIPTION
	    "The number of priority 8 messages from local
	    endpoints and the transport that are
	    successfully delivered into local target queues
	    per second."
    ::= { ss2BrokerStatisticsEntry 19 }

ss2bsEnqueuedP9MessagesPerSec OBJECT-TYPE
    SYNTAX     Gauge32
    MAX-ACCESS read-only
    STATUS     current
    DESCRIPTION
	    "The number of priority 9 messages from local
	    endpoints and the transport that are
	    successfully delivered into local target queues
	    per second."
    ::= { ss2BrokerStatisticsEntry 20 }

ss2bsEnqueuedTransmissionQMsgSec OBJECT-TYPE
    SYNTAX     Gauge32
    MAX-ACCESS read-only
    STATUS     current
    DESCRIPTION
	    "The number of messages that have been placed
	    into the broker transmission queue	second."
    ::= { ss2BrokerStatisticsEntry 21 }

ss2bsEnqueuedTransportMsgFragTot OBJECT-TYPE
    SYNTAX     Gauge32
    MAX-ACCESS read-only
    STATUS     current
    DESCRIPTION
	    "Total number of message fragments from the
	    transport that are successfully delivered into
	    local target queues. Note that the message can
	    be marked as disabled if it is incomplete
	    and/or out of order."
    ::= { ss2BrokerStatisticsEntry 22 }

ss2bsEnqueuedTransportMsgFragSec OBJECT-TYPE
    SYNTAX     Gauge32
    MAX-ACCESS read-only
    STATUS     current
    DESCRIPTION
	    "The number of message fragments from the
	    transport that are successfully delivered into
	    local target queues  second. Note that the
	    message can be marked as disabled if it is
	    incomplete and/or out of order."
    ::= { ss2BrokerStatisticsEntry 23 }

ss2bsEnqueuedTransportMsgsTotal OBJECT-TYPE
    SYNTAX     Gauge32
    MAX-ACCESS read-only
    STATUS     current
    DESCRIPTION
	    "Total number of messages from the transport
	    that are successfully delivered into local
	    target queues. This includes all messages from
	    remote endpoints and messages from local
	    endpoints which go through the transport."
    ::= { ss2BrokerStatisticsEntry 24 }

ss2bsEnqueuedTransportMsgsPerSec OBJECT-TYPE
    SYNTAX     Gauge32
    MAX-ACCESS read-only
    STATUS     current
    DESCRIPTION
	    "The number of messages from the transport that
	    are successfully delivered into local target
	    queues per second. This includes all messages
	    from remote endpoints and messages from local
	    endpoints which go through the transport."
    ::= { ss2BrokerStatisticsEntry 25 }

ss2bsForwardedMessagesTotal OBJECT-TYPE
    SYNTAX     Gauge32
    MAX-ACCESS read-only
    STATUS     current
    DESCRIPTION
	    "Total number of forwarded messages
	    successfully sent."
    ::= { ss2BrokerStatisticsEntry 26 }

ss2bsForwardedMessagesPerSec OBJECT-TYPE
    SYNTAX     Gauge32
    MAX-ACCESS read-only
    STATUS     current
    DESCRIPTION
	    "The number of forwarded messages successfully
	    sent per second."
    ::= { ss2BrokerStatisticsEntry 27 }

ss2bsForwardedMsgByteTotal OBJECT-TYPE
    SYNTAX     Gauge32
    MAX-ACCESS read-only
    STATUS     current
    DESCRIPTION
	    "Total number of forwarded message bytes
	    successfully sent."
    ::= { ss2BrokerStatisticsEntry 28 }

ss2bsForwardedMsgBytesPerSec OBJECT-TYPE
    SYNTAX     Gauge32
    MAX-ACCESS read-only
    STATUS     current
    DESCRIPTION
	    "The number of forwarded message bytes
	    successfully sent per second."
    ::= { ss2BrokerStatisticsEntry 29 }

ss2bsForwardedMsgDiscardedTotal OBJECT-TYPE
    SYNTAX     Gauge32
    MAX-ACCESS read-only
    STATUS     current
    DESCRIPTION
	    "Total number of forwarded messages discarded
	    due to forwarded message memory limits, age
	    limits, etc."
    ::= { ss2BrokerStatisticsEntry 30 }

ss2bsForwardedMsgsDiscardedSec OBJECT-TYPE
    SYNTAX     Gauge32
    MAX-ACCESS read-only
    STATUS     current
    DESCRIPTION
	    "The number of forwarded messages that were
	    discarded  second due to forwarded message
	    memory limits, age limits, etc."
    ::= { ss2BrokerStatisticsEntry 31 }

ss2bsForwardedPendingMsgBytes OBJECT-TYPE
    SYNTAX     Gauge32
    MAX-ACCESS read-only
    STATUS     current
    DESCRIPTION
	    "The number of forwarded message bytes that
	    have not been successfully sent yet."
    ::= { ss2BrokerStatisticsEntry 32 }

ss2bsForwardedPendingMsgCount OBJECT-TYPE
    SYNTAX     Gauge32
    MAX-ACCESS read-only
    STATUS     current
    DESCRIPTION
	    "The number of forwarded messages that have not
	    been successfully sent yet."
    ::= { ss2BrokerStatisticsEntry 33 }

ss2bsSQLReceiveTotal OBJECT-TYPE
    SYNTAX     Gauge32
    MAX-ACCESS read-only
    STATUS     current
    DESCRIPTION
	    "Total number of SQL RECEIVE commands processed
	    by the Broker."
    ::= { ss2BrokerStatisticsEntry 34 }

ss2bsSQLReceivesPerSec OBJECT-TYPE
    SYNTAX     Gauge32
    MAX-ACCESS read-only
    STATUS     current
    DESCRIPTION
	    "The number of SQL RECEIVE commands processed
	    by the Broker per second."
    ::= { ss2BrokerStatisticsEntry 35 }

ss2bsSQLSendTotal OBJECT-TYPE
    SYNTAX     Gauge32
    MAX-ACCESS read-only
    STATUS     current
    DESCRIPTION
	    "Total number of SQL SEND commands processed by
	    the Broker."
    ::= { ss2BrokerStatisticsEntry 36 }

ss2bsSQLSendsPerSec OBJECT-TYPE
    SYNTAX     Gauge32
    MAX-ACCESS read-only
    STATUS     current
    DESCRIPTION
	    "The number of SQL SEND commands processed by
	    the Broker per second."
    ::= { ss2BrokerStatisticsEntry 37 }

ss2BrokerTOStatisticsTable OBJECT-TYPE
    SYNTAX     SEQUENCE OF BrokerTOStatisticsEntry
    MAX-ACCESS not-accessible
    STATUS     current
    DESCRIPTION
	    "The Broker TO Statistics performance object
	    reports information about how many times
	    Service Broker dialogs request transmission
	    objects, and how often transmission objects are
	    written to tempdb.
	    
	    Transmission objects record the state of
	    message transmissions for a Service Broker
	    dialog. They are stored in memory. To free
	    memory, Service Broker periodically writes
	    batches of inactive transmission objects to
	    work tables in tempdb."
    ::= { sqlServerEngineV2 6 }

ss2BrokerTOStatisticsEntry OBJECT-TYPE
    SYNTAX     BrokerTOStatisticsEntry
    MAX-ACCESS not-accessible
    STATUS     current
    DESCRIPTION
	    "Performance information for one SQL Server
	    BrokerTOStatistics instance."
    INDEX      { ss2NameIndex }
    ::= { ss2BrokerTOStatisticsTable 1 }

BrokerTOStatisticsEntry ::= SEQUENCE {
    ss2btosAvgLengthOfBatchedWrites Gauge32,
    ss2btosAvgTimeBetweenBatchesMs Gauge32,
    ss2btosAvgTimeToWriteBatchMs Gauge32,
    ss2btosTransmissionObjGetsPerSec Gauge32,
    ss2btosTransmissionObjSetDirtSec Gauge32,
    ss2btosTransmissionObjWritesSec Gauge32
}

ss2btosAvgLengthOfBatchedWrites OBJECT-TYPE
    SYNTAX     Gauge32
    MAX-ACCESS read-only
    STATUS     current
    DESCRIPTION
	    "Average Number of Transmission Objects saved
	    in a batch."
    ::= { ss2BrokerTOStatisticsEntry 1 }

ss2btosAvgTimeBetweenBatchesMs OBJECT-TYPE
    SYNTAX     Gauge32
    MAX-ACCESS read-only
    STATUS     current
    DESCRIPTION
	    "Average time between Transmission Object batch
	    flushes."
    ::= { ss2BrokerTOStatisticsEntry 2 }

ss2btosAvgTimeToWriteBatchMs OBJECT-TYPE
    SYNTAX     Gauge32
    MAX-ACCESS read-only
    STATUS     current
    DESCRIPTION
	    "Average time to save a Transmission Object
	    batch."
    ::= { ss2BrokerTOStatisticsEntry 3 }

ss2btosTransmissionObjGetsPerSec OBJECT-TYPE
    SYNTAX     Gauge32
    MAX-ACCESS read-only
    STATUS     current
    DESCRIPTION
	    "The number of Transmission Objects requested
	    per second."
    ::= { ss2BrokerTOStatisticsEntry 4 }

ss2btosTransmissionObjSetDirtSec OBJECT-TYPE
    SYNTAX     Gauge32
    MAX-ACCESS read-only
    STATUS     current
    DESCRIPTION
	    "The number of Transmission Objects marked
	    dirty  second."
    ::= { ss2BrokerTOStatisticsEntry 5 }

ss2btosTransmissionObjWritesSec OBJECT-TYPE
    SYNTAX     Gauge32
    MAX-ACCESS read-only
    STATUS     current
    DESCRIPTION
	    "The number of Transmission Objects saved 
	    second."
    ::= { ss2BrokerTOStatisticsEntry 6 }

ss2BrokerPerDBMTransportTable OBJECT-TYPE
    SYNTAX     SEQUENCE OF BrokerPerDBMTransportEntry
    MAX-ACCESS not-accessible
    STATUS     current
    DESCRIPTION
	    "The Broker / DBM Transport performance object
	    contains performance counters that report
	    networking information for Service Broker and
	    database mirroring."
    ::= { sqlServerEngineV2 7 }

ss2BrokerPerDBMTransportEntry OBJECT-TYPE
    SYNTAX     BrokerPerDBMTransportEntry
    MAX-ACCESS not-accessible
    STATUS     current
    DESCRIPTION
	    "Performance information for one SQL Server
	    BrokerPerDBMTransport instance."
    INDEX      { ss2NameIndex }
    ::= { ss2BrokerPerDBMTransportTable 1 }

BrokerPerDBMTransportEntry ::= SEQUENCE {
    ss2bdtCurrentBytesForRecvIPerO Gauge32,
    ss2bdtCurrentBytesForSendIPerO Gauge32,
    ss2bdtCurrentMsgFragForSendIO Gauge32,
    ss2bdtMessageFragmentP1SenSec Gauge32,
    ss2bdtMsgFragmentP10SendsSec Gauge32,
    ss2bdtMsgFragmentP2SendsSec Gauge32,
    ss2bdtMsgFragmentP3SendsSec Gauge32,
    ss2bdtMsgFragmentP4SendsSec Gauge32,
    ss2bdtMsgFragmentP5SendsSec Gauge32,
    ss2bdtMsgFragmentP6SendsSec Gauge32,
    ss2bdtMsgFragmentP7SendsSec Gauge32,
    ss2bdtMsgFragmentP8SendsSec Gauge32,
    ss2bdtMsgFragmentP9SendsSec Gauge32,
    ss2bdtMsgFragmentReceivesSec Gauge32,
    ss2bdtMessageFragmentSendsPerSec Gauge32,
    ss2bdtMsgFragmentRecvSizeAvg Gauge32,
    ss2bdtMsgFragmentSendSizeAvg Gauge32,
    ss2bdtOpenConnectionCount Gauge32,
    ss2bdtPendingBytesForRecvIPerO Gauge32,
    ss2bdtPendingBytesForSendIPerO Gauge32,
    ss2bdtPendingMsgFragForRecvIO Gauge32,
    ss2bdtPendingMsgFragForSendIO Gauge32,
    ss2bdtReceiveIPerOLenAvg Gauge32,
    ss2bdtReceiveIPerOBytesPerSec Gauge32,
    ss2bdtReceiveIPerOsPerSec Gauge32,
    ss2bdtRecvIPerOBufferCopiesCount Gauge32,
    ss2bdtRecvIOBufferCopiesBytesSec Gauge32,
    ss2bdtSendIPerOLenAvg Gauge32,
    ss2bdtSendIPerOBytesPerSec Gauge32,
    ss2bdtSendIPerOsPerSec Gauge32
}

ss2bdtCurrentBytesForRecvIPerO OBJECT-TYPE
    SYNTAX     Gauge32
    MAX-ACCESS read-only
    STATUS     current
    DESCRIPTION
	    "The number of bytes associated with current
	    transport receive I/O operations that haven't
	    completed."
    ::= { ss2BrokerPerDBMTransportEntry 1 }

ss2bdtCurrentBytesForSendIPerO OBJECT-TYPE
    SYNTAX     Gauge32
    MAX-ACCESS read-only
    STATUS     current
    DESCRIPTION
	    "The number of buffer bytes associated with
	    current transport send I/O operations that
	    haven't completed."
    ::= { ss2BrokerPerDBMTransportEntry 2 }

ss2bdtCurrentMsgFragForSendIO OBJECT-TYPE
    SYNTAX     Gauge32
    MAX-ACCESS read-only
    STATUS     current
    DESCRIPTION
	    "The current number of message fragments
	    associated with current transport send I/O
	    oations that haven't completed."
    ::= { ss2BrokerPerDBMTransportEntry 3 }

ss2bdtMessageFragmentP1SenSec OBJECT-TYPE
    SYNTAX     Gauge32
    MAX-ACCESS read-only
    STATUS     current
    DESCRIPTION
	    "The number of priority 1 message fragments
	    sent  second in transport send I/O oations."
    ::= { ss2BrokerPerDBMTransportEntry 4 }

ss2bdtMsgFragmentP10SendsSec OBJECT-TYPE
    SYNTAX     Gauge32
    MAX-ACCESS read-only
    STATUS     current
    DESCRIPTION
	    "The number of priority 10 message fragments
	    sent  second in transport send I/O oations."
    ::= { ss2BrokerPerDBMTransportEntry 5 }

ss2bdtMsgFragmentP2SendsSec OBJECT-TYPE
    SYNTAX     Gauge32
    MAX-ACCESS read-only
    STATUS     current
    DESCRIPTION
	    "The number of priority 2 message fragments
	    sent  second in transport send I/O oations."
    ::= { ss2BrokerPerDBMTransportEntry 6 }

ss2bdtMsgFragmentP3SendsSec OBJECT-TYPE
    SYNTAX     Gauge32
    MAX-ACCESS read-only
    STATUS     current
    DESCRIPTION
	    "The number of priority 3 message fragments
	    sent  second in transport send I/O oations."
    ::= { ss2BrokerPerDBMTransportEntry 7 }

ss2bdtMsgFragmentP4SendsSec OBJECT-TYPE
    SYNTAX     Gauge32
    MAX-ACCESS read-only
    STATUS     current
    DESCRIPTION
	    "The number of priority 4 message fragments
	    sent  second in transport send I/O oations."
    ::= { ss2BrokerPerDBMTransportEntry 8 }

ss2bdtMsgFragmentP5SendsSec OBJECT-TYPE
    SYNTAX     Gauge32
    MAX-ACCESS read-only
    STATUS     current
    DESCRIPTION
	    "The number of priority 5 message fragments
	    sent  second in transport send I/O oations."
    ::= { ss2BrokerPerDBMTransportEntry 9 }

ss2bdtMsgFragmentP6SendsSec OBJECT-TYPE
    SYNTAX     Gauge32
    MAX-ACCESS read-only
    STATUS     current
    DESCRIPTION
	    "The number of priority 6 message fragments
	    sent  second in transport send I/O oations."
    ::= { ss2BrokerPerDBMTransportEntry 10 }

ss2bdtMsgFragmentP7SendsSec OBJECT-TYPE
    SYNTAX     Gauge32
    MAX-ACCESS read-only
    STATUS     current
    DESCRIPTION
	    "The number of priority 7 message fragments
	    sent  second in transport send I/O oations."
    ::= { ss2BrokerPerDBMTransportEntry 11 }

ss2bdtMsgFragmentP8SendsSec OBJECT-TYPE
    SYNTAX     Gauge32
    MAX-ACCESS read-only
    STATUS     current
    DESCRIPTION
	    "The number of priority 8 message fragments
	    sent  second in transport send I/O oations."
    ::= { ss2BrokerPerDBMTransportEntry 12 }

ss2bdtMsgFragmentP9SendsSec OBJECT-TYPE
    SYNTAX     Gauge32
    MAX-ACCESS read-only
    STATUS     current
    DESCRIPTION
	    "The number of priority 9 message fragments
	    sent  second in transport send I/O oations."
    ::= { ss2BrokerPerDBMTransportEntry 13 }

ss2bdtMsgFragmentReceivesSec OBJECT-TYPE
    SYNTAX     Gauge32
    MAX-ACCESS read-only
    STATUS     current
    DESCRIPTION
	    "The number of message fragments received 
	    second in transport receive I/O oations."
    ::= { ss2BrokerPerDBMTransportEntry 14 }

ss2bdtMessageFragmentSendsPerSec OBJECT-TYPE
    SYNTAX     Gauge32
    MAX-ACCESS read-only
    STATUS     current
    DESCRIPTION
	    "The number of message fragments sent per
	    second in transport send I/O operations."
    ::= { ss2BrokerPerDBMTransportEntry 15 }

ss2bdtMsgFragmentRecvSizeAvg OBJECT-TYPE
    SYNTAX     Gauge32
    MAX-ACCESS read-only
    STATUS     current
    DESCRIPTION
	    "The average byte size of message fragments
	    received in transport receive I/O operations."
    ::= { ss2BrokerPerDBMTransportEntry 16 }

ss2bdtMsgFragmentSendSizeAvg OBJECT-TYPE
    SYNTAX     Gauge32
    MAX-ACCESS read-only
    STATUS     current
    DESCRIPTION
	    "The average byte size of message fragments
	    sent in transport send I/O operations."
    ::= { ss2BrokerPerDBMTransportEntry 17 }

ss2bdtOpenConnectionCount OBJECT-TYPE
    SYNTAX     Gauge32
    MAX-ACCESS read-only
    STATUS     current
    DESCRIPTION
	    "The total number of transport connections
	    currently open."
    ::= { ss2BrokerPerDBMTransportEntry 18 }

ss2bdtPendingBytesForRecvIPerO OBJECT-TYPE
    SYNTAX     Gauge32
    MAX-ACCESS read-only
    STATUS     current
    DESCRIPTION
	    "The number of bytes associated with in
	    completed transport receive I/O operations
	    whose message fragments haven't been enqueued
	    (or rejected) yet."
    ::= { ss2BrokerPerDBMTransportEntry 19 }

ss2bdtPendingBytesForSendIPerO OBJECT-TYPE
    SYNTAX     Gauge32
    MAX-ACCESS read-only
    STATUS     current
    DESCRIPTION
	    "The number of buffer bytes associated with
	    message fragments being marshalled, or
	    marshalled and ready to be sent with send I/O
	    operations."
    ::= { ss2BrokerPerDBMTransportEntry 20 }

ss2bdtPendingMsgFragForRecvIO OBJECT-TYPE
    SYNTAX     Gauge32
    MAX-ACCESS read-only
    STATUS     current
    DESCRIPTION
	    "The current number of message fragments
	    received in transport receive I/O oations that
	    have not been enqueued (or rejected) yet."
    ::= { ss2BrokerPerDBMTransportEntry 21 }

ss2bdtPendingMsgFragForSendIO OBJECT-TYPE
    SYNTAX     Gauge32
    MAX-ACCESS read-only
    STATUS     current
    DESCRIPTION
	    "The current number of message fragments that
	    are being marshalled, or marshalled and ready
	    to be sent via the transport layer."
    ::= { ss2BrokerPerDBMTransportEntry 22 }

ss2bdtReceiveIPerOLenAvg OBJECT-TYPE
    SYNTAX     Gauge32
    MAX-ACCESS read-only
    STATUS     current
    DESCRIPTION
	    "The average byte length of transport receive
	    I/O operations."
    ::= { ss2BrokerPerDBMTransportEntry 23 }

ss2bdtReceiveIPerOBytesPerSec OBJECT-TYPE
    SYNTAX     Gauge32
    MAX-ACCESS read-only
    STATUS     current
    DESCRIPTION
	    "The number of transport receive I/O bytes per
	    second."
    ::= { ss2BrokerPerDBMTransportEntry 24 }

ss2bdtReceiveIPerOsPerSec OBJECT-TYPE
    SYNTAX     Gauge32
    MAX-ACCESS read-only
    STATUS     current
    DESCRIPTION
	    "The number of transport receives I/O per
	    second. Note that a transport receive I/O may
	    contain more than one message fragment."
    ::= { ss2BrokerPerDBMTransportEntry 25 }

ss2bdtRecvIPerOBufferCopiesCount OBJECT-TYPE
    SYNTAX     Gauge32
    MAX-ACCESS read-only
    STATUS     current
    DESCRIPTION
	    "The number of times when transport receive I/O
	    operations had to move buffer fragments in
	    memory."
    ::= { ss2BrokerPerDBMTransportEntry 26 }

ss2bdtRecvIOBufferCopiesBytesSec OBJECT-TYPE
    SYNTAX     Gauge32
    MAX-ACCESS read-only
    STATUS     current
    DESCRIPTION
	    "The rate at which transport receive I/O
	    oations had to move buffer fragments in
	    memory."
    ::= { ss2BrokerPerDBMTransportEntry 27 }

ss2bdtSendIPerOLenAvg OBJECT-TYPE
    SYNTAX     Gauge32
    MAX-ACCESS read-only
    STATUS     current
    DESCRIPTION
	    "The average byte length of transport send I/O
	    operations."
    ::= { ss2BrokerPerDBMTransportEntry 28 }

ss2bdtSendIPerOBytesPerSec OBJECT-TYPE
    SYNTAX     Gauge32
    MAX-ACCESS read-only
    STATUS     current
    DESCRIPTION
	    "The number of transport send I/O bytes per
	    second."
    ::= { ss2BrokerPerDBMTransportEntry 29 }

ss2bdtSendIPerOsPerSec OBJECT-TYPE
    SYNTAX     Gauge32
    MAX-ACCESS read-only
    STATUS     current
    DESCRIPTION
	    "The number of transport send I/Os per second.
	    Note that a transport send I/O may contain more
	    than one message fragment."
    ::= { ss2BrokerPerDBMTransportEntry 30 }

ss2BufferManagerTable OBJECT-TYPE
    SYNTAX     SEQUENCE OF SQLServerBufferManagerEntry
    MAX-ACCESS not-accessible
    STATUS     current
    DESCRIPTION
	    "The Buffer Manager object provides counters to
	    monitor how SQL Server uses:
	    
		* Memory to store data pages, internal data
	    structures, and the procedure cache.
		* Counters to monitor the physical I/O as
	    SQL Server reads and writes database pages.
	    
	    Monitoring the memory and the counters used by
	    SQL Server helps you determine:
	    
		* If bottlenecks exist from inadequate
	    physical memory. If it cannot store frequently
	    accessed data in cache, SQL Server must
	    retrieve the data from disk.
		* If query performance can be improved by
	    adding more memory, or by making more memory
	    available to the data cache or SQL Server
	    internal structures.
		* How often SQL Server needs to read data
	    from disk. Compared with other operations, such
	    as memory access, physical I/O consumes a lot
	    of time. Minimizing physical I/O can improve
	    query performance.
	    
	    You can also monitor Address Windowing
	    Extensions (AWE) activity in SQL Server with
	    the AWE counters. For example, you can make
	    sure that SQL Server has enough memory
	    allocated for AWE to run properly."
    ::= { sqlServerEngineV2 8 }

ss2BufferManagerEntry OBJECT-TYPE
    SYNTAX      SQLServerBufferManagerEntry
    MAX-ACCESS not-accessible
    STATUS     current
    DESCRIPTION
	    "Performance information for one SQL Server
	    BufferManager instance."
    INDEX      { ss2NameIndex }
    ::= { ss2BufferManagerTable 1 }

 SQLServerBufferManagerEntry ::= SEQUENCE {
    ss2bmAWELookupMapsPerSec Gauge32,
    ss2bmAWEStolenMapsPerSec Gauge32,
    ss2bmAWEUnmapCallsPerSec Gauge32,
    ss2bmAWEUnmapPagesPerSec Gauge32,
    ss2bmAWEWriteMapsPerSec Gauge32,
    ss2bmBufferCacheHitRatio Gauge32,
    ss2bmCheckpointPagesPerSec Gauge32,
    ss2bmDatabasePages Gauge32,
    ss2bmFreeListStallsPerSec Gauge32,
    ss2bmFreePages Gauge32,
    ss2bmLazyWritesPerSec Gauge32,
    ss2bmPageLifeExpectancy Gauge32,
    ss2bmPageLookupsPerSec Gauge32,
    ss2bmPageReadsPerSec Gauge32,
    ss2bmPageWritesPerSec Gauge32,
    ss2bmReadaheadPagesPerSec Gauge32,
    ss2bmReservedPages Gauge32,
    ss2bmStolenPages Gauge32,
    ss2bmTargetPages Gauge32,
    ss2bmTotalPages Gauge32
}

ss2bmAWELookupMapsPerSec OBJECT-TYPE
    SYNTAX     Gauge32
    MAX-ACCESS read-only
    STATUS     current
    DESCRIPTION
	    "Number of AWE map calls made for pages found
	    in the buffer pool."
    ::= { ss2BufferManagerEntry 1 }

ss2bmAWEStolenMapsPerSec OBJECT-TYPE
    SYNTAX     Gauge32
    MAX-ACCESS read-only
    STATUS     current
    DESCRIPTION
	    "Number of AWE map calls made for pages stolen
	    from the buffer pool."
    ::= { ss2BufferManagerEntry 2 }

ss2bmAWEUnmapCallsPerSec OBJECT-TYPE
    SYNTAX     Gauge32
    MAX-ACCESS read-only
    STATUS     current
    DESCRIPTION
	    "Number of AWE unmap calls."
    ::= { ss2BufferManagerEntry 3 }

ss2bmAWEUnmapPagesPerSec OBJECT-TYPE
    SYNTAX     Gauge32
    MAX-ACCESS read-only
    STATUS     current
    DESCRIPTION
	    "Number of AWE pages unmapped."
    ::= { ss2BufferManagerEntry 4 }

ss2bmAWEWriteMapsPerSec OBJECT-TYPE
    SYNTAX     Gauge32
    MAX-ACCESS read-only
    STATUS     current
    DESCRIPTION
	    "Number of AWE map calls made for pages to be
	    written to disk."
    ::= { ss2BufferManagerEntry 5 }

ss2bmBufferCacheHitRatio OBJECT-TYPE
    SYNTAX     Gauge32
    MAX-ACCESS read-only
    STATUS     current
    DESCRIPTION
	    "Percentage of pages that were found in the
	    buffer pool without having to incur a read from
	    disk."
    ::= { ss2BufferManagerEntry 6 }

ss2bmCheckpointPagesPerSec OBJECT-TYPE
    SYNTAX     Gauge32
    MAX-ACCESS read-only
    STATUS     current
    DESCRIPTION
	    "Number of pages flushed by checkpoint or other
	    operations that require all dirty pages to be
	    flushed."
    ::= { ss2BufferManagerEntry 7 }

ss2bmDatabasePages OBJECT-TYPE
    SYNTAX     Gauge32
    MAX-ACCESS read-only
    STATUS     current
    DESCRIPTION
	    "Number of pages in the buffer pool with
	    database content."
    ::= { ss2BufferManagerEntry 8 }

ss2bmFreeListStallsPerSec OBJECT-TYPE
    SYNTAX     Gauge32
    MAX-ACCESS read-only
    STATUS     current
    DESCRIPTION
	    "Number of requests that had to wait for a free
	    page."
    ::= { ss2BufferManagerEntry 9 }

ss2bmFreePages OBJECT-TYPE
    SYNTAX     Gauge32
    MAX-ACCESS read-only
    STATUS     current
    DESCRIPTION
	    "Total number of pages on all free lists."
    ::= { ss2BufferManagerEntry 10 }

ss2bmLazyWritesPerSec OBJECT-TYPE
    SYNTAX     Gauge32
    MAX-ACCESS read-only
    STATUS     current
    DESCRIPTION
	    "Number of buffers written by buffer manager's
	    lazy writer."
    ::= { ss2BufferManagerEntry 11 }

ss2bmPageLifeExpectancy OBJECT-TYPE
    SYNTAX     Gauge32
    MAX-ACCESS read-only
    STATUS     current
    DESCRIPTION
	    "Number of seconds a page will stay in the
	    buffer pool without references."
    ::= { ss2BufferManagerEntry 12 }

ss2bmPageLookupsPerSec OBJECT-TYPE
    SYNTAX     Gauge32
    MAX-ACCESS read-only
    STATUS     current
    DESCRIPTION
	    "Number of requests to find a page in the
	    buffer pool."
    ::= { ss2BufferManagerEntry 13 }

ss2bmPageReadsPerSec OBJECT-TYPE
    SYNTAX     Gauge32
    MAX-ACCESS read-only
    STATUS     current
    DESCRIPTION
	    "Number of physical database page reads
	    issued."
    ::= { ss2BufferManagerEntry 14 }

ss2bmPageWritesPerSec OBJECT-TYPE
    SYNTAX     Gauge32
    MAX-ACCESS read-only
    STATUS     current
    DESCRIPTION
	    "Number of physical database page writes
	    issued."
    ::= { ss2BufferManagerEntry 15 }

ss2bmReadaheadPagesPerSec OBJECT-TYPE
    SYNTAX     Gauge32
    MAX-ACCESS read-only
    STATUS     current
    DESCRIPTION
	    "Number of pages read in anticipation of use."
    ::= { ss2BufferManagerEntry 16 }

ss2bmReservedPages OBJECT-TYPE
    SYNTAX     Gauge32
    MAX-ACCESS read-only
    STATUS     current
    DESCRIPTION
	    "Number of buffer pool reserved pages."
    ::= { ss2BufferManagerEntry 17 }

ss2bmStolenPages OBJECT-TYPE
    SYNTAX     Gauge32
    MAX-ACCESS read-only
    STATUS     current
    DESCRIPTION
	    "Number of pages used for miscellaneous server
	    purposes (including procedure cache)."
    ::= { ss2BufferManagerEntry 18 }

ss2bmTargetPages OBJECT-TYPE
    SYNTAX     Gauge32
    MAX-ACCESS read-only
    STATUS     current
    DESCRIPTION
	    "Ideal number of pages in the buffer pool."
    ::= { ss2BufferManagerEntry 19 }

ss2bmTotalPages OBJECT-TYPE
    SYNTAX     Gauge32
    MAX-ACCESS read-only
    STATUS     current
    DESCRIPTION
	    "Number of pages in the buffer pool (includes
	    database, free, and stolen)."
    ::= { ss2BufferManagerEntry 20 }

ss2BufferNodeTable OBJECT-TYPE
    SYNTAX     SEQUENCE OF SQLServerBufferNodeEntry
    MAX-ACCESS not-accessible
    STATUS     current
    DESCRIPTION
	    "The Buffer Node object provides counters that
	    complement counters provided by the Buffer
	    Manager object. It allows you to monitor the
	    SQL Server buffer pool page distribution for
	    each non-uniform memory access (NUMA) node.
	    There is an instance of the Buffer Node object
	    for each NUMA node in use. On non-NUMA
	    architecture there will be a single instance of
	    the Buffer Node object."
    ::= { sqlServerEngineV2 9 }

ss2BufferNodeEntry OBJECT-TYPE
    SYNTAX     SQLServerBufferNodeEntry
    MAX-ACCESS not-accessible
    STATUS     current
    DESCRIPTION
	    "Performance information for one particular
	    instance of 'Buffer Node' object."
    INDEX      { ss2NameIndex, ss2bnInstance }
    ::= { ss2BufferNodeTable 1 }

SQLServerBufferNodeEntry ::= SEQUENCE {
    ss2bnInstance InstanceName,
    ss2bnDatabasePages Gauge32,
    ss2bnForeignPages Gauge32,
    ss2bnFreePages Gauge32,
    ss2bnLocalNodePageLookupsPerSec Gauge32,
    ss2bnPageLifeExpectancy Gauge32,
    ss2bnRemoteNodePageLookupsPerSec Gauge32,
    ss2bnStolenPages Gauge32,
    ss2bnTargetPages Gauge32,
    ss2bnTotalPages Gauge32
}

ss2bnInstance OBJECT-TYPE
    SYNTAX     InstanceName
    MAX-ACCESS read-only
    STATUS     current
    DESCRIPTION
	    "Instance name."
    ::= { ss2BufferNodeEntry 1 }

ss2bnDatabasePages OBJECT-TYPE
    SYNTAX     Gauge32
    MAX-ACCESS read-only
    STATUS     current
    DESCRIPTION
	    "Number of pages in the buffer pool with
	    database content."
    ::= { ss2BufferNodeEntry 2 }

ss2bnForeignPages OBJECT-TYPE
    SYNTAX     Gauge32
    MAX-ACCESS read-only
    STATUS     current
    DESCRIPTION
	    "Number of pages which are not from NUMA-local
	    memory."
    ::= { ss2BufferNodeEntry 3 }

ss2bnFreePages OBJECT-TYPE
    SYNTAX     Gauge32
    MAX-ACCESS read-only
    STATUS     current
    DESCRIPTION
	    "Total number of pages on all free lists."
    ::= { ss2BufferNodeEntry 4 }

ss2bnLocalNodePageLookupsPerSec OBJECT-TYPE
    SYNTAX     Gauge32
    MAX-ACCESS read-only
    STATUS     current
    DESCRIPTION
	    "Number of lookup requests from this node which
	    were satisfied from this node."
    ::= { ss2BufferNodeEntry 5 }

ss2bnPageLifeExpectancy OBJECT-TYPE
    SYNTAX     Gauge32
    MAX-ACCESS read-only
    STATUS     current
    DESCRIPTION
	    "Number of seconds a page will stay in the
	    buffer pool without references."
    ::= { ss2BufferNodeEntry 6 }

ss2bnRemoteNodePageLookupsPerSec OBJECT-TYPE
    SYNTAX     Gauge32
    MAX-ACCESS read-only
    STATUS     current
    DESCRIPTION
	    "Number of lookup requests from this node which
	    were satisfied from other nodes."
    ::= { ss2BufferNodeEntry 7 }

ss2bnStolenPages OBJECT-TYPE
    SYNTAX     Gauge32
    MAX-ACCESS read-only
    STATUS     current
    DESCRIPTION
	    "Number of pages used for miscellaneous server
	    purposes (including procedure cache)."
    ::= { ss2BufferNodeEntry 8 }

ss2bnTargetPages OBJECT-TYPE
    SYNTAX     Gauge32
    MAX-ACCESS read-only
    STATUS     current
    DESCRIPTION
	    "Ideal number of pages in the buffer pool."
    ::= { ss2BufferNodeEntry 9 }

ss2bnTotalPages OBJECT-TYPE
    SYNTAX     Gauge32
    MAX-ACCESS read-only
    STATUS     current
    DESCRIPTION
	    "Number of pages in the buffer pool (includes
	    database, free, and stolen)."
    ::= { ss2BufferNodeEntry 10 }

ss2BufferPartitionTable OBJECT-TYPE
    SYNTAX     SEQUENCE OF SQLServerBufferPartitionEntry
    MAX-ACCESS not-accessible
    STATUS     current
    DESCRIPTION
	    "The Buffer Partition object provides counters
	    to monitor how SQL Server uses free pages."
    ::= { sqlServerEngineV2 10 }

ss2BufferPartitionEntry OBJECT-TYPE
    SYNTAX     SQLServerBufferPartitionEntry
    MAX-ACCESS not-accessible
    STATUS     current
    DESCRIPTION
	    "Performance information for one particular
	    instance of 'Buffer Partition' object."
    INDEX      { ss2NameIndex, ss2bpInstance }
    ::= { ss2BufferPartitionTable 1 }

SQLServerBufferPartitionEntry ::= SEQUENCE {
    ss2bpInstance InstanceName,
    ss2bpFreeListEmptyPerSec Gauge32,
    ss2bpFreeListRequestsPerSec Gauge32,
    ss2bpFreePages Gauge32
}

ss2bpInstance OBJECT-TYPE
    SYNTAX     InstanceName
    MAX-ACCESS read-only
    STATUS     current
    DESCRIPTION
	    "Instance name."
    ::= { ss2BufferPartitionEntry 1 }

ss2bpFreeListEmptyPerSec OBJECT-TYPE
    SYNTAX     Gauge32
    MAX-ACCESS read-only
    STATUS     current
    DESCRIPTION
	    "Number of times a free page was requested and
	    none were available."
    ::= { ss2BufferPartitionEntry 2 }

ss2bpFreeListRequestsPerSec OBJECT-TYPE
    SYNTAX     Gauge32
    MAX-ACCESS read-only
    STATUS     current
    DESCRIPTION
	    "Number of times a free page was requested."
    ::= { ss2BufferPartitionEntry 3 }

ss2bpFreePages OBJECT-TYPE
    SYNTAX     Gauge32
    MAX-ACCESS read-only
    STATUS     current
    DESCRIPTION
	    "Total number of pages on all free lists."
    ::= { ss2BufferPartitionEntry 4 }

ss2CLRTable OBJECT-TYPE
    SYNTAX     SEQUENCE OF SQLServerCLREntry
    MAX-ACCESS not-accessible
    STATUS     current
    DESCRIPTION
	    "The CLR object provides counters to monitor
	    common language runtime (CLR) execution in
	    Microsoft SQL Server."
    ::= { sqlServerEngineV2 11 }

ss2CLREntry OBJECT-TYPE
    SYNTAX      SQLServerCLREntry
    MAX-ACCESS not-accessible
    STATUS     current
    DESCRIPTION
	    "Performance information for one SQL Server CLR
	    instance."
    INDEX      { ss2NameIndex }
    ::= { ss2CLRTable 1 }

 SQLServerCLREntry ::= SEQUENCE {
    ss2CLRCLRExecution Gauge32
}

ss2CLRCLRExecution OBJECT-TYPE
    SYNTAX     Gauge32
    MAX-ACCESS read-only
    STATUS     current
    DESCRIPTION
	    "Total Execution time in CLR ( microseconds )."
    ::= { ss2CLREntry 1 }

ss2CatalogMetadataTable OBJECT-TYPE
    SYNTAX     SEQUENCE OF SQLServerCatalogMetadataEntry
    MAX-ACCESS not-accessible
    STATUS     current
    DESCRIPTION
	    "A table containing performance information for
	    instances of 'Catalog Metadata' objects."
    ::= { sqlServerEngineV2 12 }

ss2CatalogMetadataEntry OBJECT-TYPE
    SYNTAX     SQLServerCatalogMetadataEntry
    MAX-ACCESS not-accessible
    STATUS     current
    DESCRIPTION
	    "Performance information for one particular
	    instance of 'Catalog Metadata' object."
    INDEX      { ss2NameIndex, ss2cmdInstance }
    ::= { ss2CatalogMetadataTable 1 }

SQLServerCatalogMetadataEntry ::= SEQUENCE {
    ss2cmdInstance InstanceName,
    ss2cmdCacheEntriesCount Gauge32,
    ss2cmdCacheEntriesPinnedCount Gauge32,
    ss2cmdCacheHitRatio Gauge32
}

ss2cmdInstance OBJECT-TYPE
    SYNTAX     InstanceName
    MAX-ACCESS read-only
    STATUS     current
    DESCRIPTION
	    "Instance name."
    ::= { ss2CatalogMetadataEntry 1 }

ss2cmdCacheEntriesCount OBJECT-TYPE
    SYNTAX     Gauge32
    MAX-ACCESS read-only
    STATUS     current
    DESCRIPTION
	    "Number of entries in the catalog metadata
	    cache"
    ::= { ss2CatalogMetadataEntry 2 }

ss2cmdCacheEntriesPinnedCount OBJECT-TYPE
    SYNTAX     Gauge32
    MAX-ACCESS read-only
    STATUS     current
    DESCRIPTION
	    "Number of catalog metadata cache entries that
	    are pinned"
    ::= { ss2CatalogMetadataEntry 3 }

ss2cmdCacheHitRatio OBJECT-TYPE
    SYNTAX     Gauge32
    MAX-ACCESS read-only
    STATUS     current
    DESCRIPTION
	    "Ratio between cache hits and lookups"
    ::= { ss2CatalogMetadataEntry 4 }

ss2CursorManagerTotalTable OBJECT-TYPE
    SYNTAX     SEQUENCE OF SQLServerCursorManagerTotalEntry
    MAX-ACCESS not-accessible
    STATUS     current
    DESCRIPTION
	    "The Cursor Manager Total object provides
	    counters to monitor cursors."
    ::= { sqlServerEngineV2 13 }

ss2CursorManagerTotalEntry OBJECT-TYPE
    SYNTAX     SQLServerCursorManagerTotalEntry
    MAX-ACCESS not-accessible
    STATUS     current
    DESCRIPTION
	    "Performance information for one particular
	    instance of 'Cursor Manager by Type' object."
    INDEX      { ss2NameIndex }
    ::= { ss2CursorManagerTotalTable 1 }

SQLServerCursorManagerTotalEntry ::= SEQUENCE {
    ss2cmtAsyncPopulationCount Gauge32,
    ss2cmtCursorConversionRate Gauge32,
    ss2cmtCursorFlushes Gauge32
}

ss2cmtAsyncPopulationCount OBJECT-TYPE
    SYNTAX     Gauge32
    MAX-ACCESS read-only
    STATUS     current
    DESCRIPTION
	    "Number of cursors being populated
	    asynchronously."
    ::= { ss2CursorManagerTotalEntry 1 }

ss2cmtCursorConversionRate OBJECT-TYPE
    SYNTAX     Gauge32
    MAX-ACCESS read-only
    STATUS     current
    DESCRIPTION
	    "Number of cursor conversions/sec."
    ::= { ss2CursorManagerTotalEntry 2 }

ss2cmtCursorFlushes OBJECT-TYPE
    SYNTAX     Gauge32
    MAX-ACCESS read-only
    STATUS     current
    DESCRIPTION
	    "Total number of times a flush for a cursor
	    xstmt occured."
    ::= { ss2CursorManagerTotalEntry 3 }

ss2CursorManagerByTypeTable OBJECT-TYPE
    SYNTAX     SEQUENCE OF CursorManagerByTypeEntry
    MAX-ACCESS not-accessible
    STATUS     current
    DESCRIPTION
	    "The Cursor Manager by Type object provides
	    counters to monitor cursors, grouped by type."
    ::= { sqlServerEngineV2 14 }

ss2CursorManagerByTypeEntry OBJECT-TYPE
    SYNTAX     CursorManagerByTypeEntry
    MAX-ACCESS not-accessible
    STATUS     current
    DESCRIPTION
	    "Performance information for one particular
	    instance of 'Cursor Manager by Type' object."
    INDEX      { ss2NameIndex, ss2cmbtInstance }
    ::= { ss2CursorManagerByTypeTable 1 }

CursorManagerByTypeEntry ::= SEQUENCE {
    ss2cmbtInstance InstanceName,
    ss2cmbtActiveCursors Gauge32,
    ss2cmbtCacheHitRatio Gauge32,
    ss2cmbtCachedCursorCounts Gauge32,
    ss2cmbtCursorCacheUseCountsSec Gauge32,
    ss2cmbtCursorRequestsPerSec Gauge32,
    ss2cmbtCursorMemoryUsage Gauge32,
    ss2cmbtCursorWorktableUsage Gauge32,
    ss2cmbtNumberOfActiveCursorPlans Gauge32
}

ss2cmbtInstance OBJECT-TYPE
    SYNTAX     InstanceName
    MAX-ACCESS read-only
    STATUS     current
    DESCRIPTION
	    "Instance name."
    ::= { ss2CursorManagerByTypeEntry 1 }

ss2cmbtActiveCursors OBJECT-TYPE
    SYNTAX     Gauge32
    MAX-ACCESS read-only
    STATUS     current
    DESCRIPTION
	    "Number of active cursors."
    ::= { ss2CursorManagerByTypeEntry 2 }

ss2cmbtCacheHitRatio OBJECT-TYPE
    SYNTAX     Gauge32
    MAX-ACCESS read-only
    STATUS     current
    DESCRIPTION
	    "Ratio between cache hits and lookups"
    ::= { ss2CursorManagerByTypeEntry 3 }

ss2cmbtCachedCursorCounts OBJECT-TYPE
    SYNTAX     Gauge32
    MAX-ACCESS read-only
    STATUS     current
    DESCRIPTION
	    "Number of cursors of a given type in the
	    cache"
    ::= { ss2CursorManagerByTypeEntry 4 }

ss2cmbtCursorCacheUseCountsSec OBJECT-TYPE
    SYNTAX     Gauge32
    MAX-ACCESS read-only
    STATUS     current
    DESCRIPTION
	    "Times each type of cached cursor has been
	    used"
    ::= { ss2CursorManagerByTypeEntry 5 }

ss2cmbtCursorRequestsPerSec OBJECT-TYPE
    SYNTAX     Gauge32
    MAX-ACCESS read-only
    STATUS     current
    DESCRIPTION
	    "Number of SQL cursor requests received by
	    server."
    ::= { ss2CursorManagerByTypeEntry 6 }

ss2cmbtCursorMemoryUsage OBJECT-TYPE
    SYNTAX     Gauge32
    MAX-ACCESS read-only
    STATUS     current
    DESCRIPTION
	    "Amount of memory consumed by cursors (KB)."
    ::= { ss2CursorManagerByTypeEntry 7 }

ss2cmbtCursorWorktableUsage OBJECT-TYPE
    SYNTAX     Gauge32
    MAX-ACCESS read-only
    STATUS     current
    DESCRIPTION
	    "Number of worktables used by cursors."
    ::= { ss2CursorManagerByTypeEntry 8 }

ss2cmbtNumberOfActiveCursorPlans OBJECT-TYPE
    SYNTAX     Gauge32
    MAX-ACCESS read-only
    STATUS     current
    DESCRIPTION
	    "Number of cursor plans."
    ::= { ss2CursorManagerByTypeEntry 9 }

ss2DatabaseMirroringTable OBJECT-TYPE
    SYNTAX     SEQUENCE OF SQLServerDatabaseMirroringEntry
    MAX-ACCESS not-accessible
    STATUS     current
    DESCRIPTION
	    "The Database Mirroring performance object
	    contains performance counters that report
	    information about SQL Server database
	    mirroring."
    ::= { sqlServerEngineV2 15 }

ss2DatabaseMirroringEntry OBJECT-TYPE
    SYNTAX     SQLServerDatabaseMirroringEntry
    MAX-ACCESS not-accessible
    STATUS     current
    DESCRIPTION
	    "Performance information for one particular
	    instance of 'Database Mirroring' object."
    INDEX      { ss2NameIndex, ss2dmInstance }
    ::= { ss2DatabaseMirroringTable 1 }

SQLServerDatabaseMirroringEntry ::= SEQUENCE {
    ss2dmInstance InstanceName,
    ss2dmBytesReceivedPerSec Gauge32,
    ss2dmBytesSentPerSec Gauge32,
    ss2dmLogBytesReceivedPerSec Gauge32,
    ss2dmLogBytesRedoneFromCacheSec Gauge32,
    ss2dmLogBytesSentFromCachePerSec Gauge32,
    ss2dmLogBytesSentPerSec Gauge32,
    ss2dmLogCompressedBytesRcvdSec Gauge32,
    ss2dmLogCompressedBytesSentSec Gauge32,
    ss2dmLogHardenTimeMs Gauge32,
    ss2dmLogRemainingForUndoKB Gauge32,
    ss2dmLogScannedForUndoKB Gauge32,
    ss2dmLogSendFlowControlTimeMs Gauge32,
    ss2dmLogSendQueueKB Gauge32,
    ss2dmMirroredWritTransactionsSec Gauge32,
    ss2dmPagesSentPerSec Gauge32,
    ss2dmReceivesPerSec Gauge32,
    ss2dmRedoBytesPerSec Gauge32,
    ss2dmRedoQueueKB Gauge32,
    ss2dmSendPerReceiveAckTime Gauge32,
    ss2dmSendsPerSec Gauge32,
    ss2dmTransactionDelay Gauge32
}

ss2dmInstance OBJECT-TYPE
    SYNTAX     InstanceName
    MAX-ACCESS read-only
    STATUS     current
    DESCRIPTION
	    "Instance name."
    ::= { ss2DatabaseMirroringEntry 1 }

ss2dmBytesReceivedPerSec OBJECT-TYPE
    SYNTAX     Gauge32
    MAX-ACCESS read-only
    STATUS     current
    DESCRIPTION
	    "Number of bytes received per second"
    ::= { ss2DatabaseMirroringEntry 2 }

ss2dmBytesSentPerSec OBJECT-TYPE
    SYNTAX     Gauge32
    MAX-ACCESS read-only
    STATUS     current
    DESCRIPTION
	    "Number of bytes sent per second"
    ::= { ss2DatabaseMirroringEntry 3 }

ss2dmLogBytesReceivedPerSec OBJECT-TYPE
    SYNTAX     Gauge32
    MAX-ACCESS read-only
    STATUS     current
    DESCRIPTION
	    "Number of bytes of log received per second"
    ::= { ss2DatabaseMirroringEntry 4 }

ss2dmLogBytesRedoneFromCacheSec OBJECT-TYPE
    SYNTAX     Gauge32
    MAX-ACCESS read-only
    STATUS     current
    DESCRIPTION
	    "Number of log bytes which were redone from the
	    Database Mirroring log cache  second."
    ::= { ss2DatabaseMirroringEntry 5 }

ss2dmLogBytesSentFromCachePerSec OBJECT-TYPE
    SYNTAX     Gauge32
    MAX-ACCESS read-only
    STATUS     current
    DESCRIPTION
	    "Number of sent log bytes which were sent from
	    the Database Mirroring log cache in the last
	    second."
    ::= { ss2DatabaseMirroringEntry 6 }

ss2dmLogBytesSentPerSec OBJECT-TYPE
    SYNTAX     Gauge32
    MAX-ACCESS read-only
    STATUS     current
    DESCRIPTION
	    "Number of bytes of log sent per second"
    ::= { ss2DatabaseMirroringEntry 7 }

ss2dmLogCompressedBytesRcvdSec OBJECT-TYPE
    SYNTAX     Gauge32
    MAX-ACCESS read-only
    STATUS     current
    DESCRIPTION
	    "Number of compressed bytes of log received in
	    the last second."
    ::= { ss2DatabaseMirroringEntry 8 }

ss2dmLogCompressedBytesSentSec OBJECT-TYPE
    SYNTAX     Gauge32
    MAX-ACCESS read-only
    STATUS     current
    DESCRIPTION
	    "Number of compressed bytes of log sent in the
	    last second."
    ::= { ss2DatabaseMirroringEntry 9 }

ss2dmLogHardenTimeMs OBJECT-TYPE
    SYNTAX     Gauge32
    MAX-ACCESS read-only
    STATUS     current
    DESCRIPTION
	    "Milliseconds log blocks waited to be hardened
	    to disk in the last second."
    ::= { ss2DatabaseMirroringEntry 10 }

ss2dmLogRemainingForUndoKB OBJECT-TYPE
    SYNTAX     Gauge32
    MAX-ACCESS read-only
    STATUS     current
    DESCRIPTION
	    "Total number of kilobytes of log that remain
	    to be scanned by the new mirror server after
	    failover."
    ::= { ss2DatabaseMirroringEntry 11 }

ss2dmLogScannedForUndoKB OBJECT-TYPE
    SYNTAX     Gauge32
    MAX-ACCESS read-only
    STATUS     current
    DESCRIPTION
	    "Total number of kilobytes of log that have
	    been scanned by the new mirror server after
	    failover."
    ::= { ss2DatabaseMirroringEntry 12 }

ss2dmLogSendFlowControlTimeMs OBJECT-TYPE
    SYNTAX     Gauge32
    MAX-ACCESS read-only
    STATUS     current
    DESCRIPTION
	    "Milliseconds log stream messages waited for
	    send flow control in the last second."
    ::= { ss2DatabaseMirroringEntry 13 }

ss2dmLogSendQueueKB OBJECT-TYPE
    SYNTAX     Gauge32
    MAX-ACCESS read-only
    STATUS     current
    DESCRIPTION
	    "Total number of kilobytes of log that have not
	    been sent to the mirror server"
    ::= { ss2DatabaseMirroringEntry 14 }

ss2dmMirroredWritTransactionsSec OBJECT-TYPE
    SYNTAX     Gauge32
    MAX-ACCESS read-only
    STATUS     current
    DESCRIPTION
	    "Number of transactions which wrote to the
	    mirrored database in the last second, that
	    waited for log to be sent to the mirror."
    ::= { ss2DatabaseMirroringEntry 15 }

ss2dmPagesSentPerSec OBJECT-TYPE
    SYNTAX     Gauge32
    MAX-ACCESS read-only
    STATUS     current
    DESCRIPTION
	    "Number of pages sent per second"
    ::= { ss2DatabaseMirroringEntry 16 }

ss2dmReceivesPerSec OBJECT-TYPE
    SYNTAX     Gauge32
    MAX-ACCESS read-only
    STATUS     current
    DESCRIPTION
	    "Number of mirroring message receives per
	    second"
    ::= { ss2DatabaseMirroringEntry 17 }

ss2dmRedoBytesPerSec OBJECT-TYPE
    SYNTAX     Gauge32
    MAX-ACCESS read-only
    STATUS     current
    DESCRIPTION
	    "Number of bytes of log redone by the mirror
	    database per second"
    ::= { ss2DatabaseMirroringEntry 18 }

ss2dmRedoQueueKB OBJECT-TYPE
    SYNTAX     Gauge32
    MAX-ACCESS read-only
    STATUS     current
    DESCRIPTION
	    "Total number of kilobytes that redo on the
	    mirror database is behind the hardened log"
    ::= { ss2DatabaseMirroringEntry 19 }

ss2dmSendPerReceiveAckTime OBJECT-TYPE
    SYNTAX     Gauge32
    MAX-ACCESS read-only
    STATUS     current
    DESCRIPTION
	    "Milliseconds messages waited for
	    acknowledgement from the partner per second."
    ::= { ss2DatabaseMirroringEntry 20 }

ss2dmSendsPerSec OBJECT-TYPE
    SYNTAX     Gauge32
    MAX-ACCESS read-only
    STATUS     current
    DESCRIPTION
	    "Number of sends initiated per second"
    ::= { ss2DatabaseMirroringEntry 21 }

ss2dmTransactionDelay OBJECT-TYPE
    SYNTAX     Gauge32
    MAX-ACCESS read-only
    STATUS     current
    DESCRIPTION
	    "Number of milliseconds transaction termination
	    waited for acknowledgement per second."
    ::= { ss2DatabaseMirroringEntry 22 }

ss2DatabasesTable OBJECT-TYPE
    SYNTAX     SEQUENCE OF SQLServerDatabasesEntry
    MAX-ACCESS not-accessible
    STATUS     current
    DESCRIPTION
	    "The Databases object in SQL Server provides
	    counters to monitor bulk copy operations,
	    backup and restore throughput, and transaction
	    log activities. Monitor transactions and the
	    transaction log to determine how much user
	    activity is occurring in the database and how
	    full the transaction log is becoming. The
	    amount of user activity can determine the
	    performance of the database and affect log
	    size, locking, and replication. Monitoring
	    low-level log activity to gauge user activity
	    and resource usage can help you to identify
	    performance bottlenecks.
	    
	    Multiple instances of the Databases object,
	    each representing a single database, can be
	    monitored at the same time."
    ::= { sqlServerEngineV2 16 }

ss2DatabasesEntry OBJECT-TYPE
    SYNTAX     SQLServerDatabasesEntry
    MAX-ACCESS not-accessible
    STATUS     current
    DESCRIPTION
	    "Performance information for one particular
	    instance of 'Databases' object."
    INDEX      { ss2NameIndex, ss2dbInstance }
    ::= { ss2DatabasesTable 1 }

SQLServerDatabasesEntry ::= SEQUENCE {
    ss2dbInstance InstanceName,
    ss2dbActiveTransactions Gauge32,
    ss2dbBackupRestoreThroughputSec Gauge32,
    ss2dbBulkCopyRowsPerSec Gauge32,
    ss2dbBulkCopyThroughputPerSec Gauge32,
    ss2dbCommitTableEntries Gauge32,
    ss2dbDBCCLogicalScanBytesPerSec Gauge32,
    ss2dbDataFileSSizeKB Gauge32,
    ss2dbLogBytesFlushedPerSec Gauge32,
    ss2dbLogCacheHitRatio Gauge32,
    ss2dbLogCacheReadsPerSec Gauge32,
    ss2dbLogFileSSizeKB Gauge32,
    ss2dbLogFileSUsedSizeKB Gauge32,
    ss2dbLogFlushWaitTime Gauge32,
    ss2dbLogFlushWaitsPerSec Gauge32,
    ss2dbLogFlushesPerSec Gauge32,
    ss2dbLogGrowths Gauge32,
    ss2dbLogShrinks Gauge32,
    ss2dbLogTruncations Gauge32,
    ss2dbPercentLogUsed Gauge32,
    ss2dbReplPendingXacts Gauge32,
    ss2dbReplTransRate Gauge32,
    ss2dbShrinkDataMovementBytesSec Gauge32,
    ss2dbTrackedTransactionsPerSec Gauge32,
    ss2dbTransactionsPerSec Gauge32,
    ss2dbWriteTransactionsPerSec Gauge32
}

ss2dbInstance OBJECT-TYPE
    SYNTAX     InstanceName
    MAX-ACCESS read-only
    STATUS     current
    DESCRIPTION
	    "Instance name."
    ::= { ss2DatabasesEntry 1 }

ss2dbActiveTransactions OBJECT-TYPE
    SYNTAX     Gauge32
    MAX-ACCESS read-only
    STATUS     current
    DESCRIPTION
	    "Number of active update transactions for the
	    database."
    ::= { ss2DatabasesEntry 2 }

ss2dbBackupRestoreThroughputSec OBJECT-TYPE
    SYNTAX     Gauge32
    MAX-ACCESS read-only
    STATUS     current
    DESCRIPTION
	    "Read/write throughput for backup/restore of a
	    database."
    ::= { ss2DatabasesEntry 3 }

ss2dbBulkCopyRowsPerSec OBJECT-TYPE
    SYNTAX     Gauge32
    MAX-ACCESS read-only
    STATUS     current
    DESCRIPTION
	    "Number of rows bulk copied."
    ::= { ss2DatabasesEntry 4 }

ss2dbBulkCopyThroughputPerSec OBJECT-TYPE
    SYNTAX     Gauge32
    MAX-ACCESS read-only
    STATUS     current
    DESCRIPTION
	    "KiloBytes bulk copied."
    ::= { ss2DatabasesEntry 5 }

ss2dbCommitTableEntries OBJECT-TYPE
    SYNTAX     Gauge32
    MAX-ACCESS read-only
    STATUS     current
    DESCRIPTION
	    "The size of the in-memory part of the commit
	    table for the database."
    ::= { ss2DatabasesEntry 6 }

ss2dbDBCCLogicalScanBytesPerSec OBJECT-TYPE
    SYNTAX     Gauge32
    MAX-ACCESS read-only
    STATUS     current
    DESCRIPTION
	    "Logical read scan rate for DBCC commands"
    ::= { ss2DatabasesEntry 7 }

ss2dbDataFileSSizeKB OBJECT-TYPE
    SYNTAX     Gauge32
    MAX-ACCESS read-only
    STATUS     current
    DESCRIPTION
	    "The cumulative size of all the data files in
	    the database."
    ::= { ss2DatabasesEntry 8 }

ss2dbLogBytesFlushedPerSec OBJECT-TYPE
    SYNTAX     Gauge32
    MAX-ACCESS read-only
    STATUS     current
    DESCRIPTION
	    "Total number of log bytes flushed."
    ::= { ss2DatabasesEntry 9 }

ss2dbLogCacheHitRatio OBJECT-TYPE
    SYNTAX     Gauge32
    MAX-ACCESS read-only
    STATUS     current
    DESCRIPTION
	    "Percentage of log cache reads that were
	    satisfied from the log cache."
    ::= { ss2DatabasesEntry 10 }

ss2dbLogCacheReadsPerSec OBJECT-TYPE
    SYNTAX     Gauge32
    MAX-ACCESS read-only
    STATUS     current
    DESCRIPTION
	    "Reads performed through the log manager
	    cache."
    ::= { ss2DatabasesEntry 11 }

ss2dbLogFileSSizeKB OBJECT-TYPE
    SYNTAX     Gauge32
    MAX-ACCESS read-only
    STATUS     current
    DESCRIPTION
	    "The cumulative size of all the log files in
	    the database."
    ::= { ss2DatabasesEntry 12 }

ss2dbLogFileSUsedSizeKB OBJECT-TYPE
    SYNTAX     Gauge32
    MAX-ACCESS read-only
    STATUS     current
    DESCRIPTION
	    "The cumulative used size of all the log files
	    in the database."
    ::= { ss2DatabasesEntry 13 }

ss2dbLogFlushWaitTime OBJECT-TYPE
    SYNTAX     Gauge32
    MAX-ACCESS read-only
    STATUS     current
    DESCRIPTION
	    "Total wait time (milliseconds)."
    ::= { ss2DatabasesEntry 14 }

ss2dbLogFlushWaitsPerSec OBJECT-TYPE
    SYNTAX     Gauge32
    MAX-ACCESS read-only
    STATUS     current
    DESCRIPTION
	    "Number of commits waiting on log flush."
    ::= { ss2DatabasesEntry 15 }

ss2dbLogFlushesPerSec OBJECT-TYPE
    SYNTAX     Gauge32
    MAX-ACCESS read-only
    STATUS     current
    DESCRIPTION
	    "Number of log flushes."
    ::= { ss2DatabasesEntry 16 }

ss2dbLogGrowths OBJECT-TYPE
    SYNTAX     Gauge32
    MAX-ACCESS read-only
    STATUS     current
    DESCRIPTION
	    "Total number of log growths for this
	    database."
    ::= { ss2DatabasesEntry 17 }

ss2dbLogShrinks OBJECT-TYPE
    SYNTAX     Gauge32
    MAX-ACCESS read-only
    STATUS     current
    DESCRIPTION
	    "Total number of log shrinks for this
	    database."
    ::= { ss2DatabasesEntry 18 }

ss2dbLogTruncations OBJECT-TYPE
    SYNTAX     Gauge32
    MAX-ACCESS read-only
    STATUS     current
    DESCRIPTION
	    "Total number of log truncations for this
	    database."
    ::= { ss2DatabasesEntry 19 }

ss2dbPercentLogUsed OBJECT-TYPE
    SYNTAX     Gauge32
    MAX-ACCESS read-only
    STATUS     current
    DESCRIPTION
	    "The percent of space in the log that is in
	    use."
    ::= { ss2DatabasesEntry 20 }

ss2dbReplPendingXacts OBJECT-TYPE
    SYNTAX     Gauge32
    MAX-ACCESS read-only
    STATUS     current
    DESCRIPTION
	    "Number of pending replication transactions in
	    the database."
    ::= { ss2DatabasesEntry 21 }

ss2dbReplTransRate OBJECT-TYPE
    SYNTAX     Gauge32
    MAX-ACCESS read-only
    STATUS     current
    DESCRIPTION
	    "Replication transaction rate (replicated
	    transactions/sec.)."
    ::= { ss2DatabasesEntry 22 }

ss2dbShrinkDataMovementBytesSec OBJECT-TYPE
    SYNTAX     Gauge32
    MAX-ACCESS read-only
    STATUS     current
    DESCRIPTION
	    "The rate data is being moved by Autoshrink,
	    DBCC SHRINKDATABASE or SHRINKFILE."
    ::= { ss2DatabasesEntry 23 }

ss2dbTrackedTransactionsPerSec OBJECT-TYPE
    SYNTAX     Gauge32
    MAX-ACCESS read-only
    STATUS     current
    DESCRIPTION
	    "Number of committed transactions recorded in
	    the commit table for the database."
    ::= { ss2DatabasesEntry 24 }

ss2dbTransactionsPerSec OBJECT-TYPE
    SYNTAX     Gauge32
    MAX-ACCESS read-only
    STATUS     current
    DESCRIPTION
	    "Number of transactions started for the
	    database."
    ::= { ss2DatabasesEntry 25 }

ss2dbWriteTransactionsPerSec OBJECT-TYPE
    SYNTAX     Gauge32
    MAX-ACCESS read-only
    STATUS     current
    DESCRIPTION
	    "Number of transactions which wrote to the
	    database in the last second."
    ::= { ss2DatabasesEntry 26 }

ss2DeprecatedFeaturesTable OBJECT-TYPE
    SYNTAX     SEQUENCE OF SQLServerDeprecatedFeaturesEntry
    MAX-ACCESS not-accessible
    STATUS     current
    DESCRIPTION
	    "The Deprecated Features object in SQL Server
	    provides a counter to monitor the features
	    designated as deprecated. In each case the
	    counter provides a usage count that lists the
	    number of times the deprecated feature was
	    encountered since SQL Server last started."
    ::= { sqlServerEngineV2 17 }

ss2DeprecatedFeaturesEntry OBJECT-TYPE
    SYNTAX     SQLServerDeprecatedFeaturesEntry
    MAX-ACCESS not-accessible
    STATUS     current
    DESCRIPTION
	    "Performance information for one particular
	    instance of 'Deprecated Features' object."
    INDEX      { ss2NameIndex, ss2DeprecatedFeaturesInstance }
    ::= { ss2DeprecatedFeaturesTable 1 }

SQLServerDeprecatedFeaturesEntry ::= SEQUENCE {
    ss2DeprecatedFeaturesInstance InstanceName,
    ss2DeprecatedFeaturesUsage Gauge32
}

ss2DeprecatedFeaturesInstance OBJECT-TYPE
    SYNTAX     InstanceName
    MAX-ACCESS read-only
    STATUS     current
    DESCRIPTION
	    "Instance name."
    ::= { ss2DeprecatedFeaturesEntry 1 }

ss2DeprecatedFeaturesUsage OBJECT-TYPE
    SYNTAX     Gauge32
    MAX-ACCESS read-only
    STATUS     current
    DESCRIPTION
	    "Feature usage since last SQL Server startup"
    ::= { ss2DeprecatedFeaturesEntry 2 }

ss2ExecStatisticsTable OBJECT-TYPE
    SYNTAX     SEQUENCE OF SQLServerExecStatisticsEntry
    MAX-ACCESS not-accessible
    STATUS     current
    DESCRIPTION
	    "The ExecStatistics object in Microsoft SQL
	    Server provides counters to monitor various
	    executions."
    ::= { sqlServerEngineV2 18 }

ss2ExecStatisticsEntry OBJECT-TYPE
    SYNTAX     SQLServerExecStatisticsEntry
    MAX-ACCESS not-accessible
    STATUS     current
    DESCRIPTION
	    "Performance information for one particular
	    instance of 'Exec Statistics' object."
    INDEX      { ss2NameIndex, ss2ExecStatisticsInstance }
    ::= { ss2ExecStatisticsTable 1 }

SQLServerExecStatisticsEntry ::= SEQUENCE {
    ss2ExecStatisticsInstance InstanceName,
    ss2ExecStatisticsDTCCalls Gauge32,
    ss2ExecStatisticDistributedQuery Gauge32,
    ss2ExecStatistExtendedProcedures Gauge32,
    ss2ExecStatisticsOLEDBCalls Gauge32
}

ss2ExecStatisticsInstance OBJECT-TYPE
    SYNTAX     InstanceName
    MAX-ACCESS read-only
    STATUS     current
    DESCRIPTION
	    "Instance name."
    ::= { ss2ExecStatisticsEntry 1 }

ss2ExecStatisticsDTCCalls OBJECT-TYPE
    SYNTAX     Gauge32
    MAX-ACCESS read-only
    STATUS     current
    DESCRIPTION
	    "Statistics relevant to execution of DTC
	    calls."
    ::= { ss2ExecStatisticsEntry 2 }

ss2ExecStatisticDistributedQuery OBJECT-TYPE
    SYNTAX     Gauge32
    MAX-ACCESS read-only
    STATUS     current
    DESCRIPTION
	    "Statistics relevant to execution of
	    distributed queries."
    ::= { ss2ExecStatisticsEntry 3 }

ss2ExecStatistExtendedProcedures OBJECT-TYPE
    SYNTAX     Gauge32
    MAX-ACCESS read-only
    STATUS     current
    DESCRIPTION
	    "Statistics relevant to execution of XP calls."
    ::= { ss2ExecStatisticsEntry 4 }

ss2ExecStatisticsOLEDBCalls OBJECT-TYPE
    SYNTAX     Gauge32
    MAX-ACCESS read-only
    STATUS     current
    DESCRIPTION
	    "Statistics relevant to execution of OLEDB
	    calls."
    ::= { ss2ExecStatisticsEntry 5 }

ss2GeneralStatisticsTable OBJECT-TYPE
    SYNTAX     SEQUENCE OF SQLServerGeneralStatisticsEntry
    MAX-ACCESS not-accessible
    STATUS     current
    DESCRIPTION
	    "The General Statistics object in Microsoft SQL
	    Server provides counters to monitor general
	    server-wide activity, such as the number of
	    current connections and the number of users
	    connecting and disconnecting per second from
	    computers running an instance of SQL Server.
	    This can be useful when you are working on
	    large online transaction processing (OLTP) type
	    systems where there are many clients connecting
	    and disconnecting from an instance of SQL
	    Server."
    ::= { sqlServerEngineV2 19 }

ss2GeneralStatisticsEntry OBJECT-TYPE
    SYNTAX      SQLServerGeneralStatisticsEntry
    MAX-ACCESS not-accessible
    STATUS     current
    DESCRIPTION
	    "Performance information for one SQL Server
	    GeneralStatistics instance."
    INDEX      { ss2NameIndex }
    ::= { ss2GeneralStatisticsTable 1 }

 SQLServerGeneralStatisticsEntry ::= SEQUENCE {
    ss2gsActiveTempTables Gauge32,
    ss2gsConnectionResetPerSec Gauge32,
    ss2gsEventNotificationsDelayDrop Gauge32,
    ss2gsHTTPAuthenticatedRequests Gauge32,
    ss2gsLogicalConnections Gauge32,
    ss2gsLoginsPerSec Gauge32,
    ss2gsLogoutsPerSec Gauge32,
    ss2gsMarsDeadlocks Gauge32,
    ss2gsNonAtomicYieldRate Gauge32,
    ss2gsProcessesBlocked Gauge32,
    ss2gsSOAPEmptyRequests Gauge32,
    ss2gsSOAPMethodInvocations Gauge32,
    ss2gsSOAPSQLRequests Gauge32,
    ss2gsSOAPSessionInitiateRequests Gauge32,
    ss2gsSOAPSessionTerminateRequest Gauge32,
    ss2gsSOAPWSDLRequests Gauge32,
    ss2gsSQLTraceIOProviderLockWaits Gauge32,
    ss2gsTempTablesCreationRate Gauge32,
    ss2gsTempTablesForDestruction Gauge32,
    ss2gsTempdbRecoveryUnitId Gauge32,
    ss2gsTempdbRowsetId Gauge32,
    ss2gsTraceEventNotificationQueue Gauge32,
    ss2gsTransactions Gauge32,
    ss2gsUserConnections Gauge32
}

ss2gsActiveTempTables OBJECT-TYPE
    SYNTAX     Gauge32
    MAX-ACCESS read-only
    STATUS     current
    DESCRIPTION
	    "Number of temporary tables/table variables in
	    use"
    ::= { ss2GeneralStatisticsEntry 1 }

ss2gsConnectionResetPerSec OBJECT-TYPE
    SYNTAX     Gauge32
    MAX-ACCESS read-only
    STATUS     current
    DESCRIPTION
	    "Total number of connection resets per second."
    ::= { ss2GeneralStatisticsEntry 2 }

ss2gsEventNotificationsDelayDrop OBJECT-TYPE
    SYNTAX     Gauge32
    MAX-ACCESS read-only
    STATUS     current
    DESCRIPTION
	    "Number of event notifications waiting to be
	    dropped by a system thread"
    ::= { ss2GeneralStatisticsEntry 3 }

ss2gsHTTPAuthenticatedRequests OBJECT-TYPE
    SYNTAX     Gauge32
    MAX-ACCESS read-only
    STATUS     current
    DESCRIPTION
	    "Number of authenticated HTTP requests started
	    per second."
    ::= { ss2GeneralStatisticsEntry 4 }

ss2gsLogicalConnections OBJECT-TYPE
    SYNTAX     Gauge32
    MAX-ACCESS read-only
    STATUS     current
    DESCRIPTION
	    "Number of logical connections to the system."
    ::= { ss2GeneralStatisticsEntry 5 }

ss2gsLoginsPerSec OBJECT-TYPE
    SYNTAX     Gauge32
    MAX-ACCESS read-only
    STATUS     current
    DESCRIPTION
	    "Total number of logins started per second."
    ::= { ss2GeneralStatisticsEntry 6 }

ss2gsLogoutsPerSec OBJECT-TYPE
    SYNTAX     Gauge32
    MAX-ACCESS read-only
    STATUS     current
    DESCRIPTION
	    "Total number of logouts started per second."
    ::= { ss2GeneralStatisticsEntry 7 }

ss2gsMarsDeadlocks OBJECT-TYPE
    SYNTAX     Gauge32
    MAX-ACCESS read-only
    STATUS     current
    DESCRIPTION
	    "Number of Mars Deadlocks detected."
    ::= { ss2GeneralStatisticsEntry 8 }

ss2gsNonAtomicYieldRate OBJECT-TYPE
    SYNTAX     Gauge32
    MAX-ACCESS read-only
    STATUS     current
    DESCRIPTION
	    "Number of non-atomic yields per second."
    ::= { ss2GeneralStatisticsEntry 9 }

ss2gsProcessesBlocked OBJECT-TYPE
    SYNTAX     Gauge32
    MAX-ACCESS read-only
    STATUS     current
    DESCRIPTION
	    "Number of currently blocked processes."
    ::= { ss2GeneralStatisticsEntry 10 }

ss2gsSOAPEmptyRequests OBJECT-TYPE
    SYNTAX     Gauge32
    MAX-ACCESS read-only
    STATUS     current
    DESCRIPTION
	    "Number of empty SOAP requests started per
	    second."
    ::= { ss2GeneralStatisticsEntry 11 }

ss2gsSOAPMethodInvocations OBJECT-TYPE
    SYNTAX     Gauge32
    MAX-ACCESS read-only
    STATUS     current
    DESCRIPTION
	    "Number of SOAP method invocations started per
	    second."
    ::= { ss2GeneralStatisticsEntry 12 }

ss2gsSOAPSQLRequests OBJECT-TYPE
    SYNTAX     Gauge32
    MAX-ACCESS read-only
    STATUS     current
    DESCRIPTION
	    "Number of SOAP SQL requests started per
	    second."
    ::= { ss2GeneralStatisticsEntry 13 }

ss2gsSOAPSessionInitiateRequests OBJECT-TYPE
    SYNTAX     Gauge32
    MAX-ACCESS read-only
    STATUS     current
    DESCRIPTION
	    "Number of SOAP Session initiate requests
	    started per second."
    ::= { ss2GeneralStatisticsEntry 14 }

ss2gsSOAPSessionTerminateRequest OBJECT-TYPE
    SYNTAX     Gauge32
    MAX-ACCESS read-only
    STATUS     current
    DESCRIPTION
	    "Number of SOAP Session terminate requests
	    started  second."
    ::= { ss2GeneralStatisticsEntry 15 }

ss2gsSOAPWSDLRequests OBJECT-TYPE
    SYNTAX     Gauge32
    MAX-ACCESS read-only
    STATUS     current
    DESCRIPTION
	    "Number of SOAP Web Service Description
	    Language requests started per second."
    ::= { ss2GeneralStatisticsEntry 16 }

ss2gsSQLTraceIOProviderLockWaits OBJECT-TYPE
    SYNTAX     Gauge32
    MAX-ACCESS read-only
    STATUS     current
    DESCRIPTION
	    "Number of waits for the File IO Provider lock
	    per second"
    ::= { ss2GeneralStatisticsEntry 17 }

ss2gsTempTablesCreationRate OBJECT-TYPE
    SYNTAX     Gauge32
    MAX-ACCESS read-only
    STATUS     current
    DESCRIPTION
	    "Number of temporary tables/table variables
	    created/sec"
    ::= { ss2GeneralStatisticsEntry 18 }

ss2gsTempTablesForDestruction OBJECT-TYPE
    SYNTAX     Gauge32
    MAX-ACCESS read-only
    STATUS     current
    DESCRIPTION
	    "Number of temporary tables/table variables
	    waiting to be destroyed by the cleanup system
	    thread"
    ::= { ss2GeneralStatisticsEntry 19 }

ss2gsTempdbRecoveryUnitId OBJECT-TYPE
    SYNTAX     Gauge32
    MAX-ACCESS read-only
    STATUS     current
    DESCRIPTION
	    "Number of duplicate tempdb recovery unit id
	    generated"
    ::= { ss2GeneralStatisticsEntry 20 }

ss2gsTempdbRowsetId OBJECT-TYPE
    SYNTAX     Gauge32
    MAX-ACCESS read-only
    STATUS     current
    DESCRIPTION
	    "Number of duplicate tempdb rowset id
	    generated"
    ::= { ss2GeneralStatisticsEntry 21 }

ss2gsTraceEventNotificationQueue OBJECT-TYPE
    SYNTAX     Gauge32
    MAX-ACCESS read-only
    STATUS     current
    DESCRIPTION
	    "Number of trace event notification instances
	    waiting in the internal queue to be sent thru
	    Service Broker"
    ::= { ss2GeneralStatisticsEntry 22 }

ss2gsTransactions OBJECT-TYPE
    SYNTAX     Gauge32
    MAX-ACCESS read-only
    STATUS     current
    DESCRIPTION
	    "Number of transaction enlistments (local, dtc,
	    and bound)."
    ::= { ss2GeneralStatisticsEntry 23 }

ss2gsUserConnections OBJECT-TYPE
    SYNTAX     Gauge32
    MAX-ACCESS read-only
    STATUS     current
    DESCRIPTION
	    "Number of users connected to the system."
    ::= { ss2GeneralStatisticsEntry 24 }

ss2LatchesTable OBJECT-TYPE
    SYNTAX     SEQUENCE OF SQLServerLatchesEntry
    MAX-ACCESS not-accessible
    STATUS     current
    DESCRIPTION
	    "The Latches object in Microsoft SQL Server
	    provides counters to monitor internal SQL
	    Server resource locks called latches.
	    Monitoring the latches to determine user
	    activity and resource usage can help you to
	    identify performance bottlenecks."
    ::= { sqlServerEngineV2 20 }

ss2LatchesEntry OBJECT-TYPE
    SYNTAX      SQLServerLatchesEntry
    MAX-ACCESS not-accessible
    STATUS     current
    DESCRIPTION
	    "Performance information for one SQL Server
	    Latches instance."
    INDEX      { ss2NameIndex }
    ::= { ss2LatchesTable 1 }

 SQLServerLatchesEntry ::= SEQUENCE {
    ss2LatchesAverageLatchWaitTimeMs Gauge32,
    ss2LatchesLatchWaitsPerSec Gauge32,
    ss2LatchesNumberOfSuperLatches Gauge32,
    ss2LatchesSuLatchDemotionsSec Gauge32,
    ss2LatchesSuLatchPromotionsSec Gauge32,
    ss2LatchesTotalLatchWaitTimeMs Gauge32
}

ss2LatchesAverageLatchWaitTimeMs OBJECT-TYPE
    SYNTAX     Gauge32
    MAX-ACCESS read-only
    STATUS     current
    DESCRIPTION
	    "Average latch wait time (milliseconds) for
	    latch requests that had to wait."
    ::= { ss2LatchesEntry 1 }

ss2LatchesLatchWaitsPerSec OBJECT-TYPE
    SYNTAX     Gauge32
    MAX-ACCESS read-only
    STATUS     current
    DESCRIPTION
	    "Number of latch requests that could not be
	    granted immediately and had to wait before
	    being granted."
    ::= { ss2LatchesEntry 2 }

ss2LatchesNumberOfSuperLatches OBJECT-TYPE
    SYNTAX     Gauge32
    MAX-ACCESS read-only
    STATUS     current
    DESCRIPTION
	    "Number of latches that are currently
	    SuperLatches."
    ::= { ss2LatchesEntry 3 }

ss2LatchesSuLatchDemotionsSec OBJECT-TYPE
    SYNTAX     Gauge32
    MAX-ACCESS read-only
    STATUS     current
    DESCRIPTION
	    "Number of SuLatches that have been demoted to
	    regular latches"
    ::= { ss2LatchesEntry 4 }

ss2LatchesSuLatchPromotionsSec OBJECT-TYPE
    SYNTAX     Gauge32
    MAX-ACCESS read-only
    STATUS     current
    DESCRIPTION
	    "Number of latches that have been promoted to
	    SuLatches"
    ::= { ss2LatchesEntry 5 }

ss2LatchesTotalLatchWaitTimeMs OBJECT-TYPE
    SYNTAX     Gauge32
    MAX-ACCESS read-only
    STATUS     current
    DESCRIPTION
	    "Total latch wait time (milliseconds) for latch
	    requests that had to wait in the last second."
    ::= { ss2LatchesEntry 6 }

ss2LocksTable OBJECT-TYPE
    SYNTAX     SEQUENCE OF SQLServerLocksEntry
    MAX-ACCESS not-accessible
    STATUS     current
    DESCRIPTION
	    "The Locks object in Microsoft SQL Server
	    provides information about SQL Server locks on
	    individual resource types. Locks are held on
	    SQL Server resources, such as rows read or
	    modified during a transaction, to prevent
	    concurrent use of resources by different
	    transactions. For example, if an exclusive (X)
	    lock is held on a row within a table by a
	    transaction, no other transaction can modify
	    that row until the lock is released. Minimizing
	    locks increases concurrency, which can improve
	    performance. Multiple instances of the Locks
	    object can be monitored at the same time, with
	    each instance representing a lock on a resource
	    type."
    ::= { sqlServerEngineV2 21 }

ss2LocksEntry OBJECT-TYPE
    SYNTAX     SQLServerLocksEntry
    MAX-ACCESS not-accessible
    STATUS     current
    DESCRIPTION
	    "Performance information for one particular
	    instance of 'Locks' object."
    INDEX      { ss2NameIndex, ss2LocksInstance }
    ::= { ss2LocksTable 1 }

SQLServerLocksEntry ::= SEQUENCE {
    ss2LocksInstance InstanceName,
    ss2LocksAverageWaitTimeMs Gauge32,
    ss2LocksLockRequestsPerSec Gauge32,
    ss2LocksTimeoutsGreaterThan0Sec Gauge32,
    ss2LocksLockTimeoutsPerSec Gauge32,
    ss2LocksLockWaitTimeMs Gauge32,
    ss2LocksLockWaitsPerSec Gauge32,
    ss2LocksNumberOfDeadlocksPerSec Gauge32
}

ss2LocksInstance OBJECT-TYPE
    SYNTAX     InstanceName
    MAX-ACCESS read-only
    STATUS     current
    DESCRIPTION
	    "Instance name."
    ::= { ss2LocksEntry 1 }

ss2LocksAverageWaitTimeMs OBJECT-TYPE
    SYNTAX     Gauge32
    MAX-ACCESS read-only
    STATUS     current
    DESCRIPTION
	    "The average amount of wait time (milliseconds)
	    for each lock request that resulted in a wait."
    ::= { ss2LocksEntry 2 }

ss2LocksLockRequestsPerSec OBJECT-TYPE
    SYNTAX     Gauge32
    MAX-ACCESS read-only
    STATUS     current
    DESCRIPTION
	    "Number of new locks and lock conversions
	    requested from the lock manager."
    ::= { ss2LocksEntry 3 }

ss2LocksTimeoutsGreaterThan0Sec OBJECT-TYPE
    SYNTAX     Gauge32
    MAX-ACCESS read-only
    STATUS     current
    DESCRIPTION
	    "Number of lock requests that timed out. This
	    does not include requests for NOWAIT locks."
    ::= { ss2LocksEntry 4 }

ss2LocksLockTimeoutsPerSec OBJECT-TYPE
    SYNTAX     Gauge32
    MAX-ACCESS read-only
    STATUS     current
    DESCRIPTION
	    "Number of lock requests that timed out. This
	    includes requests for NOWAIT locks."
    ::= { ss2LocksEntry 5 }

ss2LocksLockWaitTimeMs OBJECT-TYPE
    SYNTAX     Gauge32
    MAX-ACCESS read-only
    STATUS     current
    DESCRIPTION
	    "Total wait time (milliseconds) for locks in
	    the last second."
    ::= { ss2LocksEntry 6 }

ss2LocksLockWaitsPerSec OBJECT-TYPE
    SYNTAX     Gauge32
    MAX-ACCESS read-only
    STATUS     current
    DESCRIPTION
	    "Number of lock requests that could not be
	    satisfied immediately and required the caller
	    to wait before being granted the lock."
    ::= { ss2LocksEntry 7 }

ss2LocksNumberOfDeadlocksPerSec OBJECT-TYPE
    SYNTAX     Gauge32
    MAX-ACCESS read-only
    STATUS     current
    DESCRIPTION
	    "Number of lock requests that resulted in a
	    deadlock."
    ::= { ss2LocksEntry 8 }

ss2MemoryManagerTable OBJECT-TYPE
    SYNTAX     SEQUENCE OF SQLServerMemoryManagerEntry
    MAX-ACCESS not-accessible
    STATUS     current
    DESCRIPTION
	    "The Memory Manager object in Microsoft SQL
	    Server provides counters to monitor overall
	    server memory usage. Monitoring overall server
	    memory usage to gauge user activity and
	    resource usage can help you to identify
	    performance bottlenecks. Monitoring the memory
	    used by an instance of SQL Server can help
	    determine:
	    
		* If bottlenecks exist from inadequate
	    physical memory for storing frequently accessed
	    data in cache. If memory is inadequate, SQL
	    Server must retrieve the data from disk.
		* If query performance can be improved by
	    adding more memory or by making more memory
	    available to the data cache or SQL Server
	    internal structures."
    ::= { sqlServerEngineV2 22 }

ss2MemoryManagerEntry OBJECT-TYPE
    SYNTAX      SQLServerMemoryManagerEntry
    MAX-ACCESS not-accessible
    STATUS     current
    DESCRIPTION
	    "Performance information for one SQL Server
	    MemoryManager instance."
    INDEX      { ss2NameIndex }
    ::= { ss2MemoryManagerTable 1 }

 SQLServerMemoryManagerEntry ::= SEQUENCE {
    ss2mmConnectionMemoryKB Gauge32,
    ss2mmGrantedWorkspaceMemoryKB Gauge32,
    ss2mmLockBlocks Gauge32,
    ss2mmLockBlocksAllocated Gauge32,
    ss2mmLockMemoryKB Gauge32,
    ss2mmLockOwnerBlocks Gauge32,
    ss2mmLockOwnerBlocksAllocated Gauge32,
    ss2mmMaximumWorkspaceMemoryKB Gauge32,
    ss2mmMemoryGrantsOutstanding Gauge32,
    ss2mmMemoryGrantsPending Gauge32,
    ss2mmOptimizerMemoryKB Gauge32,
    ss2mmSQLCacheMemoryKB Gauge32,
    ss2mmTargetServerMemoryKB Gauge32,
    ss2mmTotalServerMemoryKB Gauge32
}

ss2mmConnectionMemoryKB OBJECT-TYPE
    SYNTAX     Gauge32
    MAX-ACCESS read-only
    STATUS     current
    DESCRIPTION
	    "Total amount of dynamic memory the server is
	    using for maintaining connections"
    ::= { ss2MemoryManagerEntry 1 }

ss2mmGrantedWorkspaceMemoryKB OBJECT-TYPE
    SYNTAX     Gauge32
    MAX-ACCESS read-only
    STATUS     current
    DESCRIPTION
	    "Total amount of memory granted to executing
	    processes. This memory is used for hash, sort
	    and create index operations."
    ::= { ss2MemoryManagerEntry 2 }

ss2mmLockBlocks OBJECT-TYPE
    SYNTAX     Gauge32
    MAX-ACCESS read-only
    STATUS     current
    DESCRIPTION
	    "The current number of lock blocks that are in
	    use on the server. Refreshed periodically."
    ::= { ss2MemoryManagerEntry 3 }

ss2mmLockBlocksAllocated OBJECT-TYPE
    SYNTAX     Gauge32
    MAX-ACCESS read-only
    STATUS     current
    DESCRIPTION
	    "The current number of allocated lock blocks."
    ::= { ss2MemoryManagerEntry 4 }

ss2mmLockMemoryKB OBJECT-TYPE
    SYNTAX     Gauge32
    MAX-ACCESS read-only
    STATUS     current
    DESCRIPTION
	    "Total amount of dynamic memory the server is
	    using for locks"
    ::= { ss2MemoryManagerEntry 5 }

ss2mmLockOwnerBlocks OBJECT-TYPE
    SYNTAX     Gauge32
    MAX-ACCESS read-only
    STATUS     current
    DESCRIPTION
	    "The number of lock owner blocks that are
	    currently in use on the server. Refreshed
	    periodically."
    ::= { ss2MemoryManagerEntry 6 }

ss2mmLockOwnerBlocksAllocated OBJECT-TYPE
    SYNTAX     Gauge32
    MAX-ACCESS read-only
    STATUS     current
    DESCRIPTION
	    "The current number of allocated lock owner
	    blocks."
    ::= { ss2MemoryManagerEntry 7 }

ss2mmMaximumWorkspaceMemoryKB OBJECT-TYPE
    SYNTAX     Gauge32
    MAX-ACCESS read-only
    STATUS     current
    DESCRIPTION
	    "Total amount of memory granted to executing
	    processes. This memory is used primarily for
	    hash, sort and create index operations."
    ::= { ss2MemoryManagerEntry 8 }

ss2mmMemoryGrantsOutstanding OBJECT-TYPE
    SYNTAX     Gauge32
    MAX-ACCESS read-only
    STATUS     current
    DESCRIPTION
	    "Current number of processes that have
	    successfully acquired a workspace memory grant"
    ::= { ss2MemoryManagerEntry 9 }

ss2mmMemoryGrantsPending OBJECT-TYPE
    SYNTAX     Gauge32
    MAX-ACCESS read-only
    STATUS     current
    DESCRIPTION
	    "Current number of processes waiting for a
	    workspace memory grant"
    ::= { ss2MemoryManagerEntry 10 }

ss2mmOptimizerMemoryKB OBJECT-TYPE
    SYNTAX     Gauge32
    MAX-ACCESS read-only
    STATUS     current
    DESCRIPTION
	    "Total amount of dynamic memory the server is
	    using for query optimization"
    ::= { ss2MemoryManagerEntry 11 }

ss2mmSQLCacheMemoryKB OBJECT-TYPE
    SYNTAX     Gauge32
    MAX-ACCESS read-only
    STATUS     current
    DESCRIPTION
	    "Total amount of dynamic memory the server is
	    using for the dynamic SQL cache"
    ::= { ss2MemoryManagerEntry 12 }

ss2mmTargetServerMemoryKB OBJECT-TYPE
    SYNTAX     Gauge32
    MAX-ACCESS read-only
    STATUS     current
    DESCRIPTION
	    "Total amount of dynamic memory the server is
	    willing to consume"
    ::= { ss2MemoryManagerEntry 13 }

ss2mmTotalServerMemoryKB OBJECT-TYPE
    SYNTAX     Gauge32
    MAX-ACCESS read-only
    STATUS     current
    DESCRIPTION
	    "Total amount of dynamic memory the server is
	    currently consuming"
    ::= { ss2MemoryManagerEntry 14 }

ss2PlanCacheTable OBJECT-TYPE
    SYNTAX     SEQUENCE OF SQLServerPlanCacheEntry
    MAX-ACCESS not-accessible
    STATUS     current
    DESCRIPTION
	    "The Plan Cache object provides counters to
	    monitor how SQL Server uses memory to store
	    objects such as stored procedures, ad hoc and
	    prepared Transact-SQL statements, and triggers.
	    Multiple instances of the Plan Cache object can
	    be monitored at the same time, with each
	    instance representing a different type of plan
	    to monitor."
    ::= { sqlServerEngineV2 23 }

ss2PlanCacheEntry OBJECT-TYPE
    SYNTAX     SQLServerPlanCacheEntry
    MAX-ACCESS not-accessible
    STATUS     current
    DESCRIPTION
	    "Performance information for one particular
	    instance of 'Plan Cache' object."
    INDEX      { ss2NameIndex, ss2PlanCacheInstance }
    ::= { ss2PlanCacheTable 1 }

SQLServerPlanCacheEntry ::= SEQUENCE {
    ss2PlanCacheInstance InstanceName,
    ss2PlanCacheCacheHitRatio Gauge32,
    ss2PlanCacheCacheObjectCounts Gauge32,
    ss2PlanCacheCacheObjectsInUse Gauge32,
    ss2PlanCacheCachePages Gauge32
}

ss2PlanCacheInstance OBJECT-TYPE
    SYNTAX     InstanceName
    MAX-ACCESS read-only
    STATUS     current
    DESCRIPTION
	    "Instance name."
    ::= { ss2PlanCacheEntry 1 }

ss2PlanCacheCacheHitRatio OBJECT-TYPE
    SYNTAX     Gauge32
    MAX-ACCESS read-only
    STATUS     current
    DESCRIPTION
	    "Ratio between cache hits and lookups"
    ::= { ss2PlanCacheEntry 2 }

ss2PlanCacheCacheObjectCounts OBJECT-TYPE
    SYNTAX     Gauge32
    MAX-ACCESS read-only
    STATUS     current
    DESCRIPTION
	    "Number of cache objects in the cache"
    ::= { ss2PlanCacheEntry 3 }

ss2PlanCacheCacheObjectsInUse OBJECT-TYPE
    SYNTAX     Gauge32
    MAX-ACCESS read-only
    STATUS     current
    DESCRIPTION
	    "Number of cache objects in use"
    ::= { ss2PlanCacheEntry 4 }

ss2PlanCacheCachePages OBJECT-TYPE
    SYNTAX     Gauge32
    MAX-ACCESS read-only
    STATUS     current
    DESCRIPTION
	    "Number of 8k pages used by cache objects"
    ::= { ss2PlanCacheEntry 5 }

ss2ReplicationAgentsTable OBJECT-TYPE
    SYNTAX     SEQUENCE OF SQLServerReplicationAgentsEntry
    MAX-ACCESS not-accessible
    STATUS     current
    DESCRIPTION
	    "A table containing performance information for
	    instances of 'Replication Agents' objects."
    ::= { sqlServerEngineV2 24 }

ss2ReplicationAgentsEntry OBJECT-TYPE
    SYNTAX     SQLServerReplicationAgentsEntry
    MAX-ACCESS not-accessible
    STATUS     current
    DESCRIPTION
	    "Performance information for one particular
	    instance of 'Replication Agents' object."
    INDEX      { ss2NameIndex, ss2ReplicationAgentsInstance }
    ::= { ss2ReplicationAgentsTable 1 }

SQLServerReplicationAgentsEntry ::= SEQUENCE {
    ss2ReplicationAgentsInstance InstanceName,
    ss2ReplicationAgentsRunning Gauge32
}

ss2ReplicationAgentsInstance OBJECT-TYPE
    SYNTAX     InstanceName
    MAX-ACCESS read-only
    STATUS     current
    DESCRIPTION
	    "Instance name."
    ::= { ss2ReplicationAgentsEntry 1 }

ss2ReplicationAgentsRunning OBJECT-TYPE
    SYNTAX     Gauge32
    MAX-ACCESS read-only
    STATUS     current
    DESCRIPTION
	    "The number of replication agents currently
	    running."
    ::= { ss2ReplicationAgentsEntry 2 }

ss2ReplicationDistTable OBJECT-TYPE
    SYNTAX     SEQUENCE OF SQLServerReplicationDistEntry
    MAX-ACCESS not-accessible
    STATUS     current
    DESCRIPTION
	    "A table containing performance information for
	    instances of 'Replication Dist.' objects."
    ::= { sqlServerEngineV2 25 }

ss2ReplicationDistEntry OBJECT-TYPE
    SYNTAX     SQLServerReplicationDistEntry
    MAX-ACCESS not-accessible
    STATUS     current
    DESCRIPTION
	    "Performance information for one particular
	    instance of 'Replication Dist.' object."
    INDEX      { ss2NameIndex, ss2rdInstance }
    ::= { ss2ReplicationDistTable 1 }

SQLServerReplicationDistEntry ::= SEQUENCE {
    ss2rdInstance InstanceName,
    ss2rdDistDeliveredCmdsPerSec Gauge32,
    ss2rdDistDeliveredTransPerSec Gauge32,
    ss2rdDistDeliveryLatency Gauge32
}

ss2rdInstance OBJECT-TYPE
    SYNTAX     InstanceName
    MAX-ACCESS read-only
    STATUS     current
    DESCRIPTION
	    "Instance name."
    ::= { ss2ReplicationDistEntry 1 }

ss2rdDistDeliveredCmdsPerSec OBJECT-TYPE
    SYNTAX     Gauge32
    MAX-ACCESS read-only
    STATUS     current
    DESCRIPTION
	    "The number of commands per second delivered to
	    the Subscriber."
    ::= { ss2ReplicationDistEntry 2 }

ss2rdDistDeliveredTransPerSec OBJECT-TYPE
    SYNTAX     Gauge32
    MAX-ACCESS read-only
    STATUS     current
    DESCRIPTION
	    "The number of transactions per second
	    delivered to the Subscriber."
    ::= { ss2ReplicationDistEntry 3 }

ss2rdDistDeliveryLatency OBJECT-TYPE
    SYNTAX     Gauge32
    MAX-ACCESS read-only
    STATUS     current
    DESCRIPTION
	    "The current amount of time, in milliseconds,
	    elapsed from when transactions are delivered to
	    the Distributor to when they are applied at the
	    Subscriber."
    ::= { ss2ReplicationDistEntry 4 }

ss2ReplicationLogreaderTable OBJECT-TYPE
    SYNTAX     SEQUENCE OF ReplicationLogreaderEntry
    MAX-ACCESS not-accessible
    STATUS     current
    DESCRIPTION
	    "A table containing performance information for
	    instances of 'Replication Logreader' objects."
    ::= { sqlServerEngineV2 26 }

ss2ReplicationLogreaderEntry OBJECT-TYPE
    SYNTAX     ReplicationLogreaderEntry
    MAX-ACCESS not-accessible
    STATUS     current
    DESCRIPTION
	    "Performance information for one particular
	    instance of 'Replication Logreader' object."
    INDEX      { ss2NameIndex, ss2rlInstance }
    ::= { ss2ReplicationLogreaderTable 1 }

ReplicationLogreaderEntry ::= SEQUENCE {
    ss2rlInstance InstanceName,
    ss2rlLogreaderDeliveredCmdsSec Gauge32,
    ss2rlLogreaderDeliveredTransSec Gauge32,
    ss2rlLogreaderDeliveryLatency Gauge32
}

ss2rlInstance OBJECT-TYPE
    SYNTAX     InstanceName
    MAX-ACCESS read-only
    STATUS     current
    DESCRIPTION
	    "Instance name."
    ::= { ss2ReplicationLogreaderEntry 1 }

ss2rlLogreaderDeliveredCmdsSec OBJECT-TYPE
    SYNTAX     Gauge32
    MAX-ACCESS read-only
    STATUS     current
    DESCRIPTION
	    "The number of commands  second delivered to
	    the Distributor."
    ::= { ss2ReplicationLogreaderEntry 2 }

ss2rlLogreaderDeliveredTransSec OBJECT-TYPE
    SYNTAX     Gauge32
    MAX-ACCESS read-only
    STATUS     current
    DESCRIPTION
	    "The number of transactions  second delivered
	    to the Distributor."
    ::= { ss2ReplicationLogreaderEntry 3 }

ss2rlLogreaderDeliveryLatency OBJECT-TYPE
    SYNTAX     Gauge32
    MAX-ACCESS read-only
    STATUS     current
    DESCRIPTION
	    "The current amount of time, in milliseconds,
	    elapsed from when transactions are applied at
	    the Publisher to when they are delivered to the
	    Distributor."
    ::= { ss2ReplicationLogreaderEntry 4 }

ss2ReplicationMergeTable OBJECT-TYPE
    SYNTAX     SEQUENCE OF SQLServerReplicationMergeEntry
    MAX-ACCESS not-accessible
    STATUS     current
    DESCRIPTION
	    "A table containing performance information for
	    instances of 'Replication Merge' objects."
    ::= { sqlServerEngineV2 27 }

ss2ReplicationMergeEntry OBJECT-TYPE
    SYNTAX     SQLServerReplicationMergeEntry
    MAX-ACCESS not-accessible
    STATUS     current
    DESCRIPTION
	    "Performance information for one particular
	    instance of 'Replication Merge' object."
    INDEX      { ss2NameIndex, ss2rmInstance }
    ::= { ss2ReplicationMergeTable 1 }

SQLServerReplicationMergeEntry ::= SEQUENCE {
    ss2rmInstance InstanceName,
    ss2rmConflictsPerSec Gauge32,
    ss2rmDownloadedChangesPerSec Gauge32,
    ss2rmUploadedChangesPerSec Gauge32
}

ss2rmInstance OBJECT-TYPE
    SYNTAX     InstanceName
    MAX-ACCESS read-only
    STATUS     current
    DESCRIPTION
	    "Instance name."
    ::= { ss2ReplicationMergeEntry 1 }

ss2rmConflictsPerSec OBJECT-TYPE
    SYNTAX     Gauge32
    MAX-ACCESS read-only
    STATUS     current
    DESCRIPTION
	    "The number of conflicts per second occurring
	    during the merge process."
    ::= { ss2ReplicationMergeEntry 2 }

ss2rmDownloadedChangesPerSec OBJECT-TYPE
    SYNTAX     Gauge32
    MAX-ACCESS read-only
    STATUS     current
    DESCRIPTION
	    "The number of rows per second merged from the
	    Publisher to the Subscriber."
    ::= { ss2ReplicationMergeEntry 3 }

ss2rmUploadedChangesPerSec OBJECT-TYPE
    SYNTAX     Gauge32
    MAX-ACCESS read-only
    STATUS     current
    DESCRIPTION
	    "The number of rows per second merged from the
	    Subscriber to the Publisher."
    ::= { ss2ReplicationMergeEntry 4 }

ss2ReplicationSnapshotTable OBJECT-TYPE
    SYNTAX     SEQUENCE OF ReplicationSnapshotEntry
    MAX-ACCESS not-accessible
    STATUS     current
    DESCRIPTION
	    "A table containing performance information for
	    instances of 'Replication Snapshot' objects."
    ::= { sqlServerEngineV2 28 }

ss2ReplicationSnapshotEntry OBJECT-TYPE
    SYNTAX     ReplicationSnapshotEntry
    MAX-ACCESS not-accessible
    STATUS     current
    DESCRIPTION
	    "Performance information for one particular
	    instance of 'Replication Snapshot' object."
    INDEX      { ss2NameIndex, ss2rsInstance }
    ::= { ss2ReplicationSnapshotTable 1 }

ReplicationSnapshotEntry ::= SEQUENCE {
    ss2rsInstance InstanceName,
    ss2rsSnapshotDeliveredCmdsPerSec Gauge32,
    ss2rsSnapshotDeliveredTransSec Gauge32
}

ss2rsInstance OBJECT-TYPE
    SYNTAX     InstanceName
    MAX-ACCESS read-only
    STATUS     current
    DESCRIPTION
	    "Instance name."
    ::= { ss2ReplicationSnapshotEntry 1 }

ss2rsSnapshotDeliveredCmdsPerSec OBJECT-TYPE
    SYNTAX     Gauge32
    MAX-ACCESS read-only
    STATUS     current
    DESCRIPTION
	    "The number of commands per second delivered to
	    the Distributor."
    ::= { ss2ReplicationSnapshotEntry 2 }

ss2rsSnapshotDeliveredTransSec OBJECT-TYPE
    SYNTAX     Gauge32
    MAX-ACCESS read-only
    STATUS     current
    DESCRIPTION
	    "The number of transactions  second delivered
	    to the Distributor."
    ::= { ss2ReplicationSnapshotEntry 3 }

ss2ResourcePoolStatsTable OBJECT-TYPE
    SYNTAX     SEQUENCE OF SQLServerResourcePoolStatsEntry
    MAX-ACCESS not-accessible
    STATUS     current
    DESCRIPTION
	    "A table containing performance information for
	    instances of 'Resource Pool Stats' objects."
    ::= { sqlServerEngineV2 29 }

ss2ResourcePoolStatsEntry OBJECT-TYPE
    SYNTAX     SQLServerResourcePoolStatsEntry
    MAX-ACCESS not-accessible
    STATUS     current
    DESCRIPTION
	    "Performance information for one particular
	    instance of 'Resource Pool Stats' object."
    INDEX      { ss2NameIndex, ss2rpsInstance }
    ::= { ss2ResourcePoolStatsTable 1 }

SQLServerResourcePoolStatsEntry ::= SEQUENCE {
    ss2rpsInstance InstanceName,
    ss2rpsActiveMemoryGrantAmountKB Gauge32,
    ss2rpsActiveMemoryGrantsCount Gauge32,
    ss2rpsCPUControlEffectPercent Gauge32,
    ss2rpsCPUUsagePercent Gauge32,
    ss2rpsCPUUsageTargetPercent Gauge32,
    ss2rpsCacheMemoryTargetKB Gauge32,
    ss2rpsCompileMemoryTargetKB Gauge32,
    ss2rpsMaxMemoryKB Gauge32,
    ss2rpsMemoryGrantTimeoutsPerSec Gauge32,
    ss2rpsMemoryGrantsPerSec Gauge32,
    ss2rpsPendingMemoryGrantsCount Gauge32,
    ss2rpsQueryExecMemoryTargetKB Gauge32,
    ss2rpsTargetMemoryKB Gauge32,
    ss2rpsUsedMemoryKB Gauge32
}

ss2rpsInstance OBJECT-TYPE
    SYNTAX     InstanceName
    MAX-ACCESS read-only
    STATUS     current
    DESCRIPTION
	    "Instance name."
    ::= { ss2ResourcePoolStatsEntry 1 }

ss2rpsActiveMemoryGrantAmountKB OBJECT-TYPE
    SYNTAX     Gauge32
    MAX-ACCESS read-only
    STATUS     current
    DESCRIPTION
	    "Total amount of granted memory in kilobytes in
	    the resource pool."
    ::= { ss2ResourcePoolStatsEntry 2 }

ss2rpsActiveMemoryGrantsCount OBJECT-TYPE
    SYNTAX     Gauge32
    MAX-ACCESS read-only
    STATUS     current
    DESCRIPTION
	    "Number of query memory grants in the resource
	    pool."
    ::= { ss2ResourcePoolStatsEntry 3 }

ss2rpsCPUControlEffectPercent OBJECT-TYPE
    SYNTAX     Gauge32
    MAX-ACCESS read-only
    STATUS     current
    DESCRIPTION
	    "Effect of the resource governor on the
	    resource pool calculated as (CPU usage %) /
	    (CPU usage % without RG)."
    ::= { ss2ResourcePoolStatsEntry 4 }

ss2rpsCPUUsagePercent OBJECT-TYPE
    SYNTAX     Gauge32
    MAX-ACCESS read-only
    STATUS     current
    DESCRIPTION
	    "System CPU usage by all requests in the
	    specified instance of the performance object."
    ::= { ss2ResourcePoolStatsEntry 5 }

ss2rpsCPUUsageTargetPercent OBJECT-TYPE
    SYNTAX     Gauge32
    MAX-ACCESS read-only
    STATUS     current
    DESCRIPTION
	    "Target value of 'CPU usage %' for the resource
	    pool based on the configuration settings and
	    the system load."
    ::= { ss2ResourcePoolStatsEntry 6 }

ss2rpsCacheMemoryTargetKB OBJECT-TYPE
    SYNTAX     Gauge32
    MAX-ACCESS read-only
    STATUS     current
    DESCRIPTION
	    "Current memory target for cache memory in
	    kilobytes."
    ::= { ss2ResourcePoolStatsEntry 7 }

ss2rpsCompileMemoryTargetKB OBJECT-TYPE
    SYNTAX     Gauge32
    MAX-ACCESS read-only
    STATUS     current
    DESCRIPTION
	    "Current memory target for query compile in
	    kilobytes."
    ::= { ss2ResourcePoolStatsEntry 8 }

ss2rpsMaxMemoryKB OBJECT-TYPE
    SYNTAX     Gauge32
    MAX-ACCESS read-only
    STATUS     current
    DESCRIPTION
	    "Maximum amount of memory in kilobytes the
	    resource pool can have based on the settings
	    and server state."
    ::= { ss2ResourcePoolStatsEntry 9 }

ss2rpsMemoryGrantTimeoutsPerSec OBJECT-TYPE
    SYNTAX     Gauge32
    MAX-ACCESS read-only
    STATUS     current
    DESCRIPTION
	    "Number of query memory grant timeouts per
	    second occurring in the resource pool."
    ::= { ss2ResourcePoolStatsEntry 10 }

ss2rpsMemoryGrantsPerSec OBJECT-TYPE
    SYNTAX     Gauge32
    MAX-ACCESS read-only
    STATUS     current
    DESCRIPTION
	    "Number of query memory grants per second
	    occurring in the resource pool."
    ::= { ss2ResourcePoolStatsEntry 11 }

ss2rpsPendingMemoryGrantsCount OBJECT-TYPE
    SYNTAX     Gauge32
    MAX-ACCESS read-only
    STATUS     current
    DESCRIPTION
	    "Number of queries waiting for memory grants in
	    the resource pool."
    ::= { ss2ResourcePoolStatsEntry 12 }

ss2rpsQueryExecMemoryTargetKB OBJECT-TYPE
    SYNTAX     Gauge32
    MAX-ACCESS read-only
    STATUS     current
    DESCRIPTION
	    "Current memory target for query execution
	    memory grant in kilobytes."
    ::= { ss2ResourcePoolStatsEntry 13 }

ss2rpsTargetMemoryKB OBJECT-TYPE
    SYNTAX     Gauge32
    MAX-ACCESS read-only
    STATUS     current
    DESCRIPTION
	    "Target amount of memory in kilobytes the
	    resource pool is trying to attain based on the
	    settings and server state."
    ::= { ss2ResourcePoolStatsEntry 14 }

ss2rpsUsedMemoryKB OBJECT-TYPE
    SYNTAX     Gauge32
    MAX-ACCESS read-only
    STATUS     current
    DESCRIPTION
	    "Used amount of memory in kilobytes in the
	    resource pool."
    ::= { ss2ResourcePoolStatsEntry 15 }

ss2SQLErrorsTable OBJECT-TYPE
    SYNTAX     SEQUENCE OF SQLServerSQLErrorsEntry
    MAX-ACCESS not-accessible
    STATUS     current
    DESCRIPTION
	    "The SQL Errors object in Microsoft SQL Server
	    provides counters to monitor SQL Errors."
    ::= { sqlServerEngineV2 30 }

ss2SQLErrorsEntry OBJECT-TYPE
    SYNTAX     SQLServerSQLErrorsEntry
    MAX-ACCESS not-accessible
    STATUS     current
    DESCRIPTION
	    "Performance information for one particular
	    instance of 'SQL Errors' object."
    INDEX      { ss2NameIndex, ss2SQLErrorsInstance }
    ::= { ss2SQLErrorsTable 1 }

SQLServerSQLErrorsEntry ::= SEQUENCE {
    ss2SQLErrorsInstance InstanceName,
    ss2SQLErrorsErrorsPerSec Gauge32
}

ss2SQLErrorsInstance OBJECT-TYPE
    SYNTAX     InstanceName
    MAX-ACCESS read-only
    STATUS     current
    DESCRIPTION
	    "Instance name."
    ::= { ss2SQLErrorsEntry 1 }

ss2SQLErrorsErrorsPerSec OBJECT-TYPE
    SYNTAX     Gauge32
    MAX-ACCESS read-only
    STATUS     current
    DESCRIPTION
	    "Number of errors/sec"
    ::= { ss2SQLErrorsEntry 2 }

ss2SQLStatisticsTable OBJECT-TYPE
    SYNTAX     SEQUENCE OF SQLServerSQLStatisticsEntry
    MAX-ACCESS not-accessible
    STATUS     current
    DESCRIPTION
	    "The SQL Statistics object in SQL Server
	    provides counters to monitor compilation and
	    the type of requests sent to an instance of SQL
	    Server. Monitoring the number of query
	    compilations and recompilations and the number
	    of batches received by an instance of SQL
	    Server gives you an indication of how quickly
	    SQL Server is processing user queries and how
	    effectively the query optimizer is processing
	    the queries.
	    
	    Compilation is a significant part of a query's
	    turnaround time. In order to save the
	    compilation cost, the Database Engine saves the
	    compiled query plan in a query cache. The
	    objective of the cache is to reduce compilation
	    by storing compiled queries for later reuse,
	    therefore ending the requirement to recompile
	    queries when later executed. However, each
	    unique query must be compiled at least one
	    time. Query recompilations can be caused by the
	    following factors:
	    
	    * Schema changes, including base schema changes
	    such as adding columns or indexes to a table,
	    or statistics schema changes such as inserting
	    or deleting a significant number of rows from a
	    table.
	    * Environment (SET statement) changes. Changes
	    in session settings such as ANSI_PADDING or
	    ANSI_NULLS can cause a query to be recompiled."
    ::= { sqlServerEngineV2 31 }

ss2SQLStatisticsEntry OBJECT-TYPE
    SYNTAX      SQLServerSQLStatisticsEntry
    MAX-ACCESS not-accessible
    STATUS     current
    DESCRIPTION
	    "Performance information for one SQL Server
	    SQLStatistics instance."
    INDEX      { ss2NameIndex }
    ::= { ss2SQLStatisticsTable 1 }

 SQLServerSQLStatisticsEntry ::= SEQUENCE {
    ss2sqsAutoParamAttemptsPerSec Gauge32,
    ss2sqsBatchRequestsPerSec Gauge32,
    ss2sqsFailedAutoParamsPerSec Gauge32,
    ss2sqsForcedParameterizationsSec Gauge32,
    ss2sqsGuidedPlanExecutionsPerSec Gauge32,
    ss2sqsMisguidedPlanExecutionsSec Gauge32,
    ss2sqsSQLAttentionRate Gauge32,
    ss2sqsSQLCompilationsPerSec Gauge32,
    ss2sqsSQLReCompilationsPerSec Gauge32,
    ss2sqsSafeAutoParamsPerSec Gauge32,
    ss2sqsUnsafeAutoParamsPerSec Gauge32
}

ss2sqsAutoParamAttemptsPerSec OBJECT-TYPE
    SYNTAX     Gauge32
    MAX-ACCESS read-only
    STATUS     current
    DESCRIPTION
	    "Number of auto-parameterization attempts."
    ::= { ss2SQLStatisticsEntry 1 }

ss2sqsBatchRequestsPerSec OBJECT-TYPE
    SYNTAX     Gauge32
    MAX-ACCESS read-only
    STATUS     current
    DESCRIPTION
	    "Number of SQL batch requests received by
	    server."
    ::= { ss2SQLStatisticsEntry 2 }

ss2sqsFailedAutoParamsPerSec OBJECT-TYPE
    SYNTAX     Gauge32
    MAX-ACCESS read-only
    STATUS     current
    DESCRIPTION
	    "Number of failed auto-parameterizations."
    ::= { ss2SQLStatisticsEntry 3 }

ss2sqsForcedParameterizationsSec OBJECT-TYPE
    SYNTAX     Gauge32
    MAX-ACCESS read-only
    STATUS     current
    DESCRIPTION
	    "Number of statements parameterized by forced
	    parameterization  second."
    ::= { ss2SQLStatisticsEntry 4 }

ss2sqsGuidedPlanExecutionsPerSec OBJECT-TYPE
    SYNTAX     Gauge32
    MAX-ACCESS read-only
    STATUS     current
    DESCRIPTION
	    "Number of plan executions per second in which
	    the query plan has been generated by using a
	    plan guide."
    ::= { ss2SQLStatisticsEntry 5 }

ss2sqsMisguidedPlanExecutionsSec OBJECT-TYPE
    SYNTAX     Gauge32
    MAX-ACCESS read-only
    STATUS     current
    DESCRIPTION
	    "Number of plan executions	second in which a
	    plan guide could not be honored during plan
	    generation. The plan guide was disregarded and
	    normal compilation was used to generate the
	    executed plan."
    ::= { ss2SQLStatisticsEntry 6 }

ss2sqsSQLAttentionRate OBJECT-TYPE
    SYNTAX     Gauge32
    MAX-ACCESS read-only
    STATUS     current
    DESCRIPTION
	    "Number of attentions per second."
    ::= { ss2SQLStatisticsEntry 7 }

ss2sqsSQLCompilationsPerSec OBJECT-TYPE
    SYNTAX     Gauge32
    MAX-ACCESS read-only
    STATUS     current
    DESCRIPTION
	    "Number of SQL compilations."
    ::= { ss2SQLStatisticsEntry 8 }

ss2sqsSQLReCompilationsPerSec OBJECT-TYPE
    SYNTAX     Gauge32
    MAX-ACCESS read-only
    STATUS     current
    DESCRIPTION
	    "Number of SQL re-compiles."
    ::= { ss2SQLStatisticsEntry 9 }

ss2sqsSafeAutoParamsPerSec OBJECT-TYPE
    SYNTAX     Gauge32
    MAX-ACCESS read-only
    STATUS     current
    DESCRIPTION
	    "Number of safe auto-parameterizations."
    ::= { ss2SQLStatisticsEntry 10 }

ss2sqsUnsafeAutoParamsPerSec OBJECT-TYPE
    SYNTAX     Gauge32
    MAX-ACCESS read-only
    STATUS     current
    DESCRIPTION
	    "Number of unsafe auto-parameterizations."
    ::= { ss2SQLStatisticsEntry 11 }

ss2SSISPipelineTable OBJECT-TYPE
    SYNTAX     SEQUENCE OF SQLServerSSISPipelineEntry
    MAX-ACCESS not-accessible
    STATUS     current
    DESCRIPTION
	    "A table containing performance information for
	    instances of 'SSIS Pipeline' objects."
    ::= { sqlServerEngineV2 32 }

ss2SSISPipelineEntry OBJECT-TYPE
    SYNTAX      SQLServerSSISPipelineEntry
    MAX-ACCESS not-accessible
    STATUS     current
    DESCRIPTION
	    "Performance information for one particular
	    instance of 'SSIS Pipeline' object."
    INDEX      { ss2NameIndex }
    ::= { ss2SSISPipelineTable 1 }

 SQLServerSSISPipelineEntry ::= SEQUENCE {
    ss2SSISPipelineBLOBBytesRead Gauge32,
    ss2SSISPipelineBLOBBytesWritten Gauge32,
    ss2SSISPipelineBLOBFilesInUse Gauge32,
    ss2SSISPipelineBufferMemory Gauge32,
    ss2SSISPipelineBuffersInUse Gauge32,
    ss2SSISPipelineBuffersSpooled Gauge32,
    ss2SSISPipelineFlatBufferMemory Gauge32,
    ss2SSISPipelineFlatBuffersInUse Gauge32,
    ss2SSISPipelinePrivateBuffMemory Gauge32,
    ss2SSISPipelinePrivateBuffersUse Gauge32,
    ss2SSISPipelineRowsRead Gauge32,
    ss2SSISPipelineRowsWritten Gauge32
}

ss2SSISPipelineBLOBBytesRead OBJECT-TYPE
    SYNTAX     Gauge32
    MAX-ACCESS read-only
    STATUS     current
    DESCRIPTION
	    "The number of BLOB bytes read from all data
	    sources in total."
    ::= { ss2SSISPipelineEntry 1 }

ss2SSISPipelineBLOBBytesWritten OBJECT-TYPE
    SYNTAX     Gauge32
    MAX-ACCESS read-only
    STATUS     current
    DESCRIPTION
	    "The number of BLOB bytes written to all data
	    sources in total."
    ::= { ss2SSISPipelineEntry 2 }

ss2SSISPipelineBLOBFilesInUse OBJECT-TYPE
    SYNTAX     Gauge32
    MAX-ACCESS read-only
    STATUS     current
    DESCRIPTION
	    "The number of BLOB spooling files in use
	    throughout the pipeline."
    ::= { ss2SSISPipelineEntry 3 }

ss2SSISPipelineBufferMemory OBJECT-TYPE
    SYNTAX     Gauge32
    MAX-ACCESS read-only
    STATUS     current
    DESCRIPTION
	    "The amount of memory allocated to buffers in
	    the pipeline."
    ::= { ss2SSISPipelineEntry 4 }

ss2SSISPipelineBuffersInUse OBJECT-TYPE
    SYNTAX     Gauge32
    MAX-ACCESS read-only
    STATUS     current
    DESCRIPTION
	    "The number of pipeline buffers in use
	    throughout the pipeline."
    ::= { ss2SSISPipelineEntry 5 }

ss2SSISPipelineBuffersSpooled OBJECT-TYPE
    SYNTAX     Gauge32
    MAX-ACCESS read-only
    STATUS     current
    DESCRIPTION
	    "The number of buffers spooled to disk."
    ::= { ss2SSISPipelineEntry 6 }

ss2SSISPipelineFlatBufferMemory OBJECT-TYPE
    SYNTAX     Gauge32
    MAX-ACCESS read-only
    STATUS     current
    DESCRIPTION
	    "The amount of memory allocated to flat memory
	    buffers."
    ::= { ss2SSISPipelineEntry 7 }

ss2SSISPipelineFlatBuffersInUse OBJECT-TYPE
    SYNTAX     Gauge32
    MAX-ACCESS read-only
    STATUS     current
    DESCRIPTION
	    "The number of flat memory buffers in use
	    throughout the pipeline."
    ::= { ss2SSISPipelineEntry 8 }

ss2SSISPipelinePrivateBuffMemory OBJECT-TYPE
    SYNTAX     Gauge32
    MAX-ACCESS read-only
    STATUS     current
    DESCRIPTION
	    "The amount of memory allocated to private
	    transformation buffers."
    ::= { ss2SSISPipelineEntry 9 }

ss2SSISPipelinePrivateBuffersUse OBJECT-TYPE
    SYNTAX     Gauge32
    MAX-ACCESS read-only
    STATUS     current
    DESCRIPTION
	    "The number of private transformation buffers
	    in use throughout the pipeline."
    ::= { ss2SSISPipelineEntry 10 }

ss2SSISPipelineRowsRead OBJECT-TYPE
    SYNTAX     Gauge32
    MAX-ACCESS read-only
    STATUS     current
    DESCRIPTION
	    "The number of rows read from all data sources
	    in total."
    ::= { ss2SSISPipelineEntry 11 }

ss2SSISPipelineRowsWritten OBJECT-TYPE
    SYNTAX     Gauge32
    MAX-ACCESS read-only
    STATUS     current
    DESCRIPTION
	    "The number of rows written to all data
	    destinations in total."
    ::= { ss2SSISPipelineEntry 12 }

ss2SSISServiceTable OBJECT-TYPE
    SYNTAX     SEQUENCE OF SQLServerSSISServiceEntry
    MAX-ACCESS not-accessible
    STATUS     current
    DESCRIPTION
	    "A table containing performance information for
	    instances of 'SSIS Service' objects."
    ::= { sqlServerEngineV2 33 }

ss2SSISServiceEntry OBJECT-TYPE
    SYNTAX      SQLServerSSISServiceEntry
    MAX-ACCESS not-accessible
    STATUS     current
    DESCRIPTION
	    "Performance information for one particular
	    instance of 'SSIS Service' object."
    INDEX      { ss2NameIndex }
    ::= { ss2SSISServiceTable 1 }

 SQLServerSSISServiceEntry ::= SEQUENCE {
    ss2SSISServiceSSISPackageInstanc Gauge32
}

ss2SSISServiceSSISPackageInstanc OBJECT-TYPE
    SYNTAX     Gauge32
    MAX-ACCESS read-only
    STATUS     current
    DESCRIPTION
	    "The number of package instances currently
	    running."
    ::= { ss2SSISServiceEntry 1 }

ss2TraceEventStatisticsTable OBJECT-TYPE
    SYNTAX     SEQUENCE OF TraceEventStatisticsEntry
    MAX-ACCESS not-accessible
    STATUS     current
    DESCRIPTION
	    "A table containing performance information for
	    instances of 'Trace Event Statistics' objects."
    ::= { sqlServerEngineV2 34 }

ss2TraceEventStatisticsEntry OBJECT-TYPE
    SYNTAX     TraceEventStatisticsEntry
    MAX-ACCESS not-accessible
    STATUS     current
    DESCRIPTION
	    "Performance information for one particular
	    instance of 'Trace Event Statistics' object."
    INDEX      { ss2NameIndex, ss2tesInstance }
    ::= { ss2TraceEventStatisticsTable 1 }

TraceEventStatisticsEntry ::= SEQUENCE {
    ss2tesInstance InstanceName,
    ss2tesBytesPerSec Gauge32,
    ss2tesCPUTicksPerSec Gauge32,
    ss2tesEventsFilteredPerSec Gauge32,
    ss2tesEventsFiredPerSec Gauge32,
    ss2tesEventsPrefilteredPerSec Gauge32
}

ss2tesInstance OBJECT-TYPE
    SYNTAX     InstanceName
    MAX-ACCESS read-only
    STATUS     current
    DESCRIPTION
	    "Instance name."
    ::= { ss2TraceEventStatisticsEntry 1 }

ss2tesBytesPerSec OBJECT-TYPE
    SYNTAX     Gauge32
    MAX-ACCESS read-only
    STATUS     current
    DESCRIPTION
	    "Bytes transferred by this trace per second"
    ::= { ss2TraceEventStatisticsEntry 2 }

ss2tesCPUTicksPerSec OBJECT-TYPE
    SYNTAX     Gauge32
    MAX-ACCESS read-only
    STATUS     current
    DESCRIPTION
	    "CPU usage per second (Requires -T1904)"
    ::= { ss2TraceEventStatisticsEntry 3 }

ss2tesEventsFilteredPerSec OBJECT-TYPE
    SYNTAX     Gauge32
    MAX-ACCESS read-only
    STATUS     current
    DESCRIPTION
	    "Events filtered per second"
    ::= { ss2TraceEventStatisticsEntry 4 }

ss2tesEventsFiredPerSec OBJECT-TYPE
    SYNTAX     Gauge32
    MAX-ACCESS read-only
    STATUS     current
    DESCRIPTION
	    "Events fired by this trace per second"
    ::= { ss2TraceEventStatisticsEntry 5 }

ss2tesEventsPrefilteredPerSec OBJECT-TYPE
    SYNTAX     Gauge32
    MAX-ACCESS read-only
    STATUS     current
    DESCRIPTION
	    "Prefiltered events per second"
    ::= { ss2TraceEventStatisticsEntry 6 }

ss2TraceStatisticsTable OBJECT-TYPE
    SYNTAX     SEQUENCE OF SQLServerTraceStatisticsEntry
    MAX-ACCESS not-accessible
    STATUS     current
    DESCRIPTION
	    "A table containing performance information for
	    instances of 'Trace Statistics' objects."
    ::= { sqlServerEngineV2 35 }

ss2TraceStatisticsEntry OBJECT-TYPE
    SYNTAX     SQLServerTraceStatisticsEntry
    MAX-ACCESS not-accessible
    STATUS     current
    DESCRIPTION
	    "Performance information for one particular
	    instance of 'Trace Statistics' object."
    INDEX      { ss2NameIndex, ss2tstInstance }
    ::= { ss2TraceStatisticsTable 1 }

SQLServerTraceStatisticsEntry ::= SEQUENCE {
    ss2tstInstance InstanceName,
    ss2tstBytesPerSec Gauge32,
    ss2tstDroppedEventsPerSec Gauge32,
    ss2tstEventsFilteredPerSec Gauge32,
    ss2tstEventsFiredPerSec Gauge32
}

ss2tstInstance OBJECT-TYPE
    SYNTAX     InstanceName
    MAX-ACCESS read-only
    STATUS     current
    DESCRIPTION
	    "Instance name."
    ::= { ss2TraceStatisticsEntry 1 }

ss2tstBytesPerSec OBJECT-TYPE
    SYNTAX     Gauge32
    MAX-ACCESS read-only
    STATUS     current
    DESCRIPTION
	    "Bytes transferred by this trace per second"
    ::= { ss2TraceStatisticsEntry 2 }

ss2tstDroppedEventsPerSec OBJECT-TYPE
    SYNTAX     Gauge32
    MAX-ACCESS read-only
    STATUS     current
    DESCRIPTION
	    "Events dropped by this trace per second"
    ::= { ss2TraceStatisticsEntry 3 }

ss2tstEventsFilteredPerSec OBJECT-TYPE
    SYNTAX     Gauge32
    MAX-ACCESS read-only
    STATUS     current
    DESCRIPTION
	    "Events filtered per second"
    ::= { ss2TraceStatisticsEntry 4 }

ss2tstEventsFiredPerSec OBJECT-TYPE
    SYNTAX     Gauge32
    MAX-ACCESS read-only
    STATUS     current
    DESCRIPTION
	    "Events fired by this trace per second"
    ::= { ss2TraceStatisticsEntry 5 }

ss2TransactionsTable OBJECT-TYPE
    SYNTAX     SEQUENCE OF SQLServerTransactionsEntry
    MAX-ACCESS not-accessible
    STATUS     current
    DESCRIPTION
	    "The Transactions object in Microsoft SQL
	    Server provides counters to monitor the number
	    of transactions active in an instance of the
	    Database Engine, and the effects of those
	    transactions on resources such as the snapshot
	    isolation row version store in tempdb.
	    Transactions are logical units of work; a set
	    of operations that must either all succeed or
	    all be erased from a database in order to
	    maintain the logical integrity of the data. All
	    modifications of data in SQL Server databases
	    are made in transactions.
	    
	    When a database is set to allow snapshot
	    isolation level, SQL Server must maintain a
	    record of the modifications made to each row in
	    a database. Each time a row is modified, a copy
	    of the row as it existed before the
	    modification is recorded in a row version store
	    in tempdb. Many of the counters in the
	    Transaction object can be used to monitor the
	    size and rate of growth of the row version
	    store in tempdb.
	    
	    The Transactions object counters report all
	    transactions in one instance of the Database
	    Engine."
    ::= { sqlServerEngineV2 36 }

ss2TransactionsEntry OBJECT-TYPE
    SYNTAX      SQLServerTransactionsEntry
    MAX-ACCESS not-accessible
    STATUS     current
    DESCRIPTION
	    "Performance information for one SQL Server
	    Transactions instance."
    INDEX      { ss2NameIndex }
    ::= { ss2TransactionsTable 1 }

 SQLServerTransactionsEntry ::= SEQUENCE {
    ss2trnFreeSpaceInTempdbKB Gauge32,
    ss2trnLongestTransactRunningTime Gauge32,
    ss2trnNonSnapshotVersionTransact Gauge32,
    ss2trnSnapshotTransactions Gauge32,
    ss2trnTransactions Gauge32,
    ss2trnUpdateSnapshotTransactions Gauge32,
    ss2trnUpdateConflictRatio Gauge32,
    ss2trnVersionCleanupRateKBPerS Gauge32,
    ss2trnVersionGenerationRateKBS Gauge32,
    ss2trnVersionStoreSizeKB Gauge32,
    ss2trnVersionStoreUnitCount Gauge32,
    ss2trnVersionStoreUnitCreation Gauge32,
    ss2trnVersionStoreUnitTruncation Gauge32
}

ss2trnFreeSpaceInTempdbKB OBJECT-TYPE
    SYNTAX     Gauge32
    MAX-ACCESS read-only
    STATUS     current
    DESCRIPTION
	    "The free space in tempdb in KB."
    ::= { ss2TransactionsEntry 1 }

ss2trnLongestTransactRunningTime OBJECT-TYPE
    SYNTAX     Gauge32
    MAX-ACCESS read-only
    STATUS     current
    DESCRIPTION
	    "The longest running time of any transcation in
	    seconds."
    ::= { ss2TransactionsEntry 2 }

ss2trnNonSnapshotVersionTransact OBJECT-TYPE
    SYNTAX     Gauge32
    MAX-ACCESS read-only
    STATUS     current
    DESCRIPTION
	    "The total number of active non-snapshot
	    transactions that generate version records."
    ::= { ss2TransactionsEntry 3 }

ss2trnSnapshotTransactions OBJECT-TYPE
    SYNTAX     Gauge32
    MAX-ACCESS read-only
    STATUS     current
    DESCRIPTION
	    "The total number of active snapshot
	    transactions."
    ::= { ss2TransactionsEntry 4 }

ss2trnTransactions OBJECT-TYPE
    SYNTAX     Gauge32
    MAX-ACCESS read-only
    STATUS     current
    DESCRIPTION
	    "Number of transaction enlistments (local, dtc,
	    and bound)."
    ::= { ss2TransactionsEntry 5 }

ss2trnUpdateSnapshotTransactions OBJECT-TYPE
    SYNTAX     Gauge32
    MAX-ACCESS read-only
    STATUS     current
    DESCRIPTION
	    "The total number of active snapshot
	    transactions that do updates."
    ::= { ss2TransactionsEntry 6 }

ss2trnUpdateConflictRatio OBJECT-TYPE
    SYNTAX     Gauge32
    MAX-ACCESS read-only
    STATUS     current
    DESCRIPTION
	    "The fraction of update snapshot transactions
	    that have update conflicts to the total number
	    of update snapshot transactions."
    ::= { ss2TransactionsEntry 7 }

ss2trnVersionCleanupRateKBPerS OBJECT-TYPE
    SYNTAX     Gauge32
    MAX-ACCESS read-only
    STATUS     current
    DESCRIPTION
	    "The version cleanup rate in KB per seconds."
    ::= { ss2TransactionsEntry 8 }

ss2trnVersionGenerationRateKBS OBJECT-TYPE
    SYNTAX     Gauge32
    MAX-ACCESS read-only
    STATUS     current
    DESCRIPTION
	    "The version generation rate in KB	seconds."
    ::= { ss2TransactionsEntry 9 }

ss2trnVersionStoreSizeKB OBJECT-TYPE
    SYNTAX     Gauge32
    MAX-ACCESS read-only
    STATUS     current
    DESCRIPTION
	    "The size of the version store in KB."
    ::= { ss2TransactionsEntry 10 }

ss2trnVersionStoreUnitCount OBJECT-TYPE
    SYNTAX     Gauge32
    MAX-ACCESS read-only
    STATUS     current
    DESCRIPTION
	    "Number of unit in Version Store."
    ::= { ss2TransactionsEntry 11 }

ss2trnVersionStoreUnitCreation OBJECT-TYPE
    SYNTAX     Gauge32
    MAX-ACCESS read-only
    STATUS     current
    DESCRIPTION
	    "Creation of new unit in Version Store."
    ::= { ss2TransactionsEntry 12 }

ss2trnVersionStoreUnitTruncation OBJECT-TYPE
    SYNTAX     Gauge32
    MAX-ACCESS read-only
    STATUS     current
    DESCRIPTION
	    "Truncation of unit in Version Store."
    ::= { ss2TransactionsEntry 13 }

ss2UserSettableTable OBJECT-TYPE
    SYNTAX     SEQUENCE OF SQLServerUserSettableEntry
    MAX-ACCESS not-accessible
    STATUS     current
    DESCRIPTION
	    "The User Settable object in Microsoft SQL
	    Server allows you to create custom counter
	    instances. Use custom counter instances to
	    monitor aspects of the server not monitored by
	    existing counters, such as components unique to
	    your SQL Server database (for example, the
	    number of customer orders logged or the product
	    inventory).
	    
	    The User Settable object contains 10 instances
	    of the query counter: User counter 1 through
	    User counter 10. These counters map to the SQL
	    Server stored procedures sp_user_counter1
	    through sp_user_counter10. As these stored
	    procedures are executed by user applications,
	    the values set by the stored procedures are
	    displayed in System Monitor. A counter can
	    monitor any single integer value (for example,
	    a stored procedure that counts how many orders
	    for a particular product have occurred in one
	    day)."
    ::= { sqlServerEngineV2 37 }

ss2UserSettableEntry OBJECT-TYPE
    SYNTAX     SQLServerUserSettableEntry
    MAX-ACCESS not-accessible
    STATUS     current
    DESCRIPTION
	    "Performance information for one particular
	    instance of 'User Settable' object."
    INDEX      { ss2NameIndex, ss2UserSettableInstance }
    ::= { ss2UserSettableTable 1 }

SQLServerUserSettableEntry ::= SEQUENCE {
    ss2UserSettableInstance InstanceName,
    ss2UserSettableQuery Gauge32
}

ss2UserSettableInstance OBJECT-TYPE
    SYNTAX     InstanceName
    MAX-ACCESS read-only
    STATUS     current
    DESCRIPTION
	    "Instance name."
    ::= { ss2UserSettableEntry 1 }

ss2UserSettableQuery OBJECT-TYPE
    SYNTAX     Gauge32
    MAX-ACCESS read-only
    STATUS     current
    DESCRIPTION
	    "As defined by the user."
    ::= { ss2UserSettableEntry 2 }

ss2WaitStatisticsTable OBJECT-TYPE
    SYNTAX     SEQUENCE OF SQLServerWaitStatisticsEntry
    MAX-ACCESS not-accessible
    STATUS     current
    DESCRIPTION
	    "The Wait Statistics performance object
	    contains performance counters that report
	    information about wait status."
    ::= { sqlServerEngineV2 38 }

ss2WaitStatisticsEntry OBJECT-TYPE
    SYNTAX     SQLServerWaitStatisticsEntry
    MAX-ACCESS not-accessible
    STATUS     current
    DESCRIPTION
	    "Performance information for one particular
	    instance of 'Wait Statistics' object."
    INDEX      { ss2NameIndex, ss2wsInstance }
    ::= { ss2WaitStatisticsTable 1 }

SQLServerWaitStatisticsEntry ::= SEQUENCE {
    ss2wsInstance InstanceName,
    ss2wsLockWaits Gauge32,
    ss2wsLogBufferWaits Gauge32,
    ss2wsLogWriteWaits Gauge32,
    ss2wsMemoryGrantQueueWaits Gauge32,
    ss2wsNetworkIOWaits Gauge32,
    ss2wsNonPageLatchWaits Gauge32,
    ss2wsPageIOLatchWaits Gauge32,
    ss2wsPageLatchWaits Gauge32,
    ss2wsThreadSafeMemoryObjectsWait Gauge32,
    ss2wsTransactionOwnershipWaits Gauge32,
    ss2wsWaitForTheWorker Gauge32,
    ss2wsWorkspaceSynchronizatWaits Gauge32
}

ss2wsInstance OBJECT-TYPE
    SYNTAX     InstanceName
    MAX-ACCESS read-only
    STATUS     current
    DESCRIPTION
	    "Instance name."
    ::= { ss2WaitStatisticsEntry 1 }

ss2wsLockWaits OBJECT-TYPE
    SYNTAX     Gauge32
    MAX-ACCESS read-only
    STATUS     current
    DESCRIPTION
	    "Statistics for processes waiting on a lock."
    ::= { ss2WaitStatisticsEntry 2 }

ss2wsLogBufferWaits OBJECT-TYPE
    SYNTAX     Gauge32
    MAX-ACCESS read-only
    STATUS     current
    DESCRIPTION
	    "Statistics for processes waiting for log
	    buffer to be available."
    ::= { ss2WaitStatisticsEntry 3 }

ss2wsLogWriteWaits OBJECT-TYPE
    SYNTAX     Gauge32
    MAX-ACCESS read-only
    STATUS     current
    DESCRIPTION
	    "Statistics for processes waiting for log
	    buffer to be written."
    ::= { ss2WaitStatisticsEntry 4 }

ss2wsMemoryGrantQueueWaits OBJECT-TYPE
    SYNTAX     Gauge32
    MAX-ACCESS read-only
    STATUS     current
    DESCRIPTION
	    "Statistics for processes waiting for memory
	    grant to become available."
    ::= { ss2WaitStatisticsEntry 5 }

ss2wsNetworkIOWaits OBJECT-TYPE
    SYNTAX     Gauge32
    MAX-ACCESS read-only
    STATUS     current
    DESCRIPTION
	    "Statistics relevant to wait on network IO."
    ::= { ss2WaitStatisticsEntry 6 }

ss2wsNonPageLatchWaits OBJECT-TYPE
    SYNTAX     Gauge32
    MAX-ACCESS read-only
    STATUS     current
    DESCRIPTION
	    "Statistics relevant to non-page latches."
    ::= { ss2WaitStatisticsEntry 7 }

ss2wsPageIOLatchWaits OBJECT-TYPE
    SYNTAX     Gauge32
    MAX-ACCESS read-only
    STATUS     current
    DESCRIPTION
	    "Statistics relevant to page IO latches."
    ::= { ss2WaitStatisticsEntry 8 }

ss2wsPageLatchWaits OBJECT-TYPE
    SYNTAX     Gauge32
    MAX-ACCESS read-only
    STATUS     current
    DESCRIPTION
	    "Statistics relevant to page latches, not
	    including IO latches"
    ::= { ss2WaitStatisticsEntry 9 }

ss2wsThreadSafeMemoryObjectsWait OBJECT-TYPE
    SYNTAX     Gauge32
    MAX-ACCESS read-only
    STATUS     current
    DESCRIPTION
	    "Statistics for processes waiting on
	    thread-safe memory allocators."
    ::= { ss2WaitStatisticsEntry 10 }

ss2wsTransactionOwnershipWaits OBJECT-TYPE
    SYNTAX     Gauge32
    MAX-ACCESS read-only
    STATUS     current
    DESCRIPTION
	    "Statistics relevant to processes synchronizing
	    access to transaction."
    ::= { ss2WaitStatisticsEntry 11 }

ss2wsWaitForTheWorker OBJECT-TYPE
    SYNTAX     Gauge32
    MAX-ACCESS read-only
    STATUS     current
    DESCRIPTION
	    "Statistics relevant to processes waiting for
	    worker to become available."
    ::= { ss2WaitStatisticsEntry 12 }

ss2wsWorkspaceSynchronizatWaits OBJECT-TYPE
    SYNTAX     Gauge32
    MAX-ACCESS read-only
    STATUS     current
    DESCRIPTION
	    "Statistics relevant to processes synchronizing
	    access to workspace."
    ::= { ss2WaitStatisticsEntry 13 }

ss2WorkloadGroupStatsTable OBJECT-TYPE
    SYNTAX     SEQUENCE OF SQLServerWorkloadGroupStatsEntry
    MAX-ACCESS not-accessible
    STATUS     current
    DESCRIPTION
	    "A table containing performance information for
	    instances of 'Workload Group Stats' objects."
    ::= { sqlServerEngineV2 39 }

ss2WorkloadGroupStatsEntry OBJECT-TYPE
    SYNTAX     SQLServerWorkloadGroupStatsEntry
    MAX-ACCESS not-accessible
    STATUS     current
    DESCRIPTION
	    "Performance information for one particular
	    instance of 'Workload Group Stats' object."
    INDEX      { ss2NameIndex, ss2wgsInstance }
    ::= { ss2WorkloadGroupStatsTable 1 }

SQLServerWorkloadGroupStatsEntry ::= SEQUENCE {
    ss2wgsInstance InstanceName,
    ss2wgsActiveParallelThreads Gauge32,
    ss2wgsActiveRequests Gauge32,
    ss2wgsBlockedTasks Gauge32,
    ss2wgsCPUUsagePercent Gauge32,
    ss2wgsMaxRequestCpuTimeMs Gauge32,
    ss2wgsMaxRequestMemoryGrantKB Gauge32,
    ss2wgsQueryOptimizationsPerSec Gauge32,
    ss2wgsQueuedRequests Gauge32,
    ss2wgsReducedMemoryGrantsPerSec Gauge32,
    ss2wgsRequestsCompletedPerSec Gauge32,
    ss2wgsSuboptimalPlansPerSec Gauge32
}

ss2wgsInstance OBJECT-TYPE
    SYNTAX     InstanceName
    MAX-ACCESS read-only
    STATUS     current
    DESCRIPTION
	    "Instance name."
    ::= { ss2WorkloadGroupStatsEntry 1 }

ss2wgsActiveParallelThreads OBJECT-TYPE
    SYNTAX     Gauge32
    MAX-ACCESS read-only
    STATUS     current
    DESCRIPTION
	    "Number of threads used by parallel queries in
	    the workload group. Serial queries and the main
	    thread of parallel queries are not included in
	    this number."
    ::= { ss2WorkloadGroupStatsEntry 2 }

ss2wgsActiveRequests OBJECT-TYPE
    SYNTAX     Gauge32
    MAX-ACCESS read-only
    STATUS     current
    DESCRIPTION
	    "Number of currently running requests in the
	    workload group."
    ::= { ss2WorkloadGroupStatsEntry 3 }

ss2wgsBlockedTasks OBJECT-TYPE
    SYNTAX     Gauge32
    MAX-ACCESS read-only
    STATUS     current
    DESCRIPTION
	    "Number of blocked tasks in the workload
	    group."
    ::= { ss2WorkloadGroupStatsEntry 4 }

ss2wgsCPUUsagePercent OBJECT-TYPE
    SYNTAX     Gauge32
    MAX-ACCESS read-only
    STATUS     current
    DESCRIPTION
	    "System CPU usage by all requests in the
	    specified instance of the performance object."
    ::= { ss2WorkloadGroupStatsEntry 5 }

ss2wgsMaxRequestCpuTimeMs OBJECT-TYPE
    SYNTAX     Gauge32
    MAX-ACCESS read-only
    STATUS     current
    DESCRIPTION
	    "Maximum CPU time in milliseconds used by a
	    request in the workload group."
    ::= { ss2WorkloadGroupStatsEntry 6 }

ss2wgsMaxRequestMemoryGrantKB OBJECT-TYPE
    SYNTAX     Gauge32
    MAX-ACCESS read-only
    STATUS     current
    DESCRIPTION
	    "Maximum value of memory grant in kilobytes
	    used by a query in the workload group."
    ::= { ss2WorkloadGroupStatsEntry 7 }

ss2wgsQueryOptimizationsPerSec OBJECT-TYPE
    SYNTAX     Gauge32
    MAX-ACCESS read-only
    STATUS     current
    DESCRIPTION
	    "Number of query optimizations per second
	    occurring in the workload group."
    ::= { ss2WorkloadGroupStatsEntry 8 }

ss2wgsQueuedRequests OBJECT-TYPE
    SYNTAX     Gauge32
    MAX-ACCESS read-only
    STATUS     current
    DESCRIPTION
	    "Number of requests waiting in the queue due to
	    resource governor limits in the workload
	    group."
    ::= { ss2WorkloadGroupStatsEntry 9 }

ss2wgsReducedMemoryGrantsPerSec OBJECT-TYPE
    SYNTAX     Gauge32
    MAX-ACCESS read-only
    STATUS     current
    DESCRIPTION
	    "Number of queries per second getting less than
	    ideal amount of memory in the workload group."
    ::= { ss2WorkloadGroupStatsEntry 10 }

ss2wgsRequestsCompletedPerSec OBJECT-TYPE
    SYNTAX     Gauge32
    MAX-ACCESS read-only
    STATUS     current
    DESCRIPTION
	    "Number of completed requests per second in the
	    workload group."
    ::= { ss2WorkloadGroupStatsEntry 11 }

ss2wgsSuboptimalPlansPerSec OBJECT-TYPE
    SYNTAX     Gauge32
    MAX-ACCESS read-only
    STATUS     current
    DESCRIPTION
	    "Number of suboptimal query plans generated per
	    second in the workload group."
    ::= { ss2WorkloadGroupStatsEntry 12 }

sqlServerAgentV2 OBJECT IDENTIFIER
    ::= { sqlServerV2 3 }

sa2NameTable OBJECT-TYPE
    SYNTAX     SEQUENCE OF SQLAgentNameEntry
    MAX-ACCESS not-accessible
    STATUS     current
    DESCRIPTION
	    "This table contains the list of SQL Server
	    Agent instance names installed. The
	    ss2NameIndex is used to refer to all other SQL
	    Server Agent SNMP entries."
    ::= { sqlServerAgentV2 1 }

sa2NameEntry OBJECT-TYPE
    SYNTAX     SQLAgentNameEntry
    MAX-ACCESS not-accessible
    STATUS     current
    DESCRIPTION
	    "Performance information for one SQL Server
	    Agent name instance."
    INDEX      { sa2NameIndex }
    ::= { sa2NameTable 1 }

SQLAgentNameEntry ::= SEQUENCE {
    sa2NameIndex Integer32,
    sa2NameInstance InstanceName
}

sa2NameIndex OBJECT-TYPE
    SYNTAX     Integer32 (1..2147483647)
    MAX-ACCESS read-only
    STATUS     current
    DESCRIPTION
	    "The index number associated with the instance
	    name"
    ::= { sa2NameEntry 1 }

sa2NameInstance OBJECT-TYPE
    SYNTAX     InstanceName
    MAX-ACCESS read-only
    STATUS     current
    DESCRIPTION
	    "The name of the SQL Server Agent installed
	    instance."
    ::= { sa2NameEntry 2 }

sa2AlertsTable OBJECT-TYPE
    SYNTAX     SEQUENCE OF SQLAgentAlertsEntry
    MAX-ACCESS not-accessible
    STATUS     current
    DESCRIPTION
	    "The SQL Server Agent Alerts performance object
	    contains performance counters that report
	    information about SQL Server Agent alerts."
    ::= { sqlServerAgentV2 2 }

sa2AlertsEntry OBJECT-TYPE
    SYNTAX     SQLAgentAlertsEntry
    MAX-ACCESS not-accessible
    STATUS     current
    DESCRIPTION
	    "Performance information for one particular
	    instance of 'Alerts' object."
    INDEX      { sa2NameIndex }
    ::= { sa2AlertsTable 1 }

SQLAgentAlertsEntry ::= SEQUENCE {
    sa2AlertsActivatedAlerts Gauge32,
    sa2AlertsAlertsActivatedMinute Gauge32
}

sa2AlertsActivatedAlerts OBJECT-TYPE
    SYNTAX     Gauge32
    MAX-ACCESS read-only
    STATUS     current
    DESCRIPTION
	    "The number of Alerts that have activated since
	    the last SQL Server restart."
    ::= { sa2AlertsEntry 1 }

sa2AlertsAlertsActivatedMinute OBJECT-TYPE
    SYNTAX     Gauge32
    MAX-ACCESS read-only
    STATUS     current
    DESCRIPTION
	    "The number of Alerts that have activated
	    within the last minute."
    ::= { sa2AlertsEntry 2 }

sa2JobsTable OBJECT-TYPE
    SYNTAX     SEQUENCE OF SQLAgentJobsEntry
    MAX-ACCESS not-accessible
    STATUS     current
    DESCRIPTION
	    "The SQL Server Agent Jobs performance object
	    contains performance counters that report
	    information about SQL Server Agent jobs."
    ::= { sqlServerAgentV2 3 }

sa2JobsEntry OBJECT-TYPE
    SYNTAX     SQLAgentJobsEntry
    MAX-ACCESS not-accessible
    STATUS     current
    DESCRIPTION
	    "Performance information for one particular
	    instance of 'Jobs' object."
    INDEX      { sa2NameIndex, sa2JobsInstance }
    ::= { sa2JobsTable 1 }

SQLAgentJobsEntry ::= SEQUENCE {
    sa2JobsInstance InstanceName,
    sa2JobsActiveJobs Gauge32,
    sa2JobsFailedJobs Gauge32,
    sa2JobsJobSuccessRate Gauge32,
    sa2JobsJobsActivatedPerMinute Gauge32,
    sa2JobsQueuedJobs Gauge32,
    sa2JobsSuccessfulJobs Gauge32
}

sa2JobsInstance OBJECT-TYPE
    SYNTAX     InstanceName
    MAX-ACCESS read-only
    STATUS     current
    DESCRIPTION
	    "Instance name."
    ::= { sa2JobsEntry 1 }

sa2JobsActiveJobs OBJECT-TYPE
    SYNTAX     Gauge32
    MAX-ACCESS read-only
    STATUS     current
    DESCRIPTION
	    "Number of running jobs."
    ::= { sa2JobsEntry 2 }

sa2JobsFailedJobs OBJECT-TYPE
    SYNTAX     Gauge32
    MAX-ACCESS read-only
    STATUS     current
    DESCRIPTION
	    "Number of failed jobs."
    ::= { sa2JobsEntry 3 }

sa2JobsJobSuccessRate OBJECT-TYPE
    SYNTAX     Gauge32
    MAX-ACCESS read-only
    STATUS     current
    DESCRIPTION
	    "Percentage of successful jobs from the total
	    number of executed jobs."
    ::= { sa2JobsEntry 4 }

sa2JobsJobsActivatedPerMinute OBJECT-TYPE
    SYNTAX     Gauge32
    MAX-ACCESS read-only
    STATUS     current
    DESCRIPTION
	    "Number of jobs activated within the last
	    minute."
    ::= { sa2JobsEntry 5 }

sa2JobsQueuedJobs OBJECT-TYPE
    SYNTAX     Gauge32
    MAX-ACCESS read-only
    STATUS     current
    DESCRIPTION
	    "Number of jobs queued."
    ::= { sa2JobsEntry 6 }

sa2JobsSuccessfulJobs OBJECT-TYPE
    SYNTAX     Gauge32
    MAX-ACCESS read-only
    STATUS     current
    DESCRIPTION
	    "Number of successful jobs."
    ::= { sa2JobsEntry 7 }

sa2JobStepsTable OBJECT-TYPE
    SYNTAX     SEQUENCE OF SQLAgentJobStepsEntry
    MAX-ACCESS not-accessible
    STATUS     current
    DESCRIPTION
	    "The SQL Server Agent JobSteps performance
	    object contains performance counters that
	    report information about SQL Server Agent job
	    steps."
    ::= { sqlServerAgentV2 4 }

sa2JobStepsEntry OBJECT-TYPE
    SYNTAX     SQLAgentJobStepsEntry
    MAX-ACCESS not-accessible
    STATUS     current
    DESCRIPTION
	    "Performance information for one particular
	    instance of 'JobSteps' object."
    INDEX      { sa2NameIndex, sa2JobStepsInstance }
    ::= { sa2JobStepsTable 1 }

SQLAgentJobStepsEntry ::= SEQUENCE {
    sa2JobStepsInstance InstanceName,
    sa2JobStepsActiveSteps Gauge32,
    sa2JobStepsQueuedSteps Gauge32,
    sa2JobStepsTotalStepRetries Gauge32
}

sa2JobStepsInstance OBJECT-TYPE
    SYNTAX     InstanceName
    MAX-ACCESS read-only
    STATUS     current
    DESCRIPTION
	    "Instance name."
    ::= { sa2JobStepsEntry 1 }

sa2JobStepsActiveSteps OBJECT-TYPE
    SYNTAX     Gauge32
    MAX-ACCESS read-only
    STATUS     current
    DESCRIPTION
	    "Number of active steps."
    ::= { sa2JobStepsEntry 2 }

sa2JobStepsQueuedSteps OBJECT-TYPE
    SYNTAX     Gauge32
    MAX-ACCESS read-only
    STATUS     current
    DESCRIPTION
	    "Number of queued steps."
    ::= { sa2JobStepsEntry 3 }

sa2JobStepsTotalStepRetries OBJECT-TYPE
    SYNTAX     Gauge32
    MAX-ACCESS read-only
    STATUS     current
    DESCRIPTION
	    "The total number of times any Job Step
	    execution is retried since the last SQL Server
	    restart."
    ::= { sa2JobStepsEntry 4 }

sa2StatisticsTable OBJECT-TYPE
    SYNTAX     SEQUENCE OF SQLAgentStatisticsEntry
    MAX-ACCESS not-accessible
    STATUS     current
    DESCRIPTION
	    "The SQL Server Agent Statistics performance
	    object contains performance counters that
	    report information about SQL Server Agent."
    ::= { sqlServerAgentV2 5 }

sa2StatisticsEntry OBJECT-TYPE
    SYNTAX     SQLAgentStatisticsEntry
    MAX-ACCESS not-accessible
    STATUS     current
    DESCRIPTION
	    "Performance information for one particular
	    instance of 'Statistics' object."
    INDEX      { sa2NameIndex }
    ::= { sa2StatisticsTable 1 }

SQLAgentStatisticsEntry ::= SEQUENCE {
    sa2StatisticsSQLServerRestarted Gauge32
}

sa2StatisticsSQLServerRestarted OBJECT-TYPE
    SYNTAX     Gauge32
    MAX-ACCESS read-only
    STATUS     current
    DESCRIPTION
	    "The number of times the SQL Server has been
	    successfully restarted by SQL Server Agent,
	    since the last SQL Server Agent restart."
    ::= { sa2StatisticsEntry 1 }

reportingServicesV2 OBJECT IDENTIFIER
    ::= { sqlServerV2 4 }

rs2WebService OBJECT IDENTIFIER
    ::= { reportingServicesV2 1 }

rs2wbsActiveSessions OBJECT-TYPE
    SYNTAX     Gauge32
    MAX-ACCESS read-only
    STATUS     current
    DESCRIPTION
	    "Number of active sessions."
    ::= { rs2WebService 1 }

rs2wbsCacheHitsPerSec OBJECT-TYPE
    SYNTAX     Gauge32
    MAX-ACCESS read-only
    STATUS     current
    DESCRIPTION
	    "Number of report server cache hits per
	    second."
    ::= { rs2WebService 2 }

rs2wbsCacheHitsSecSemanticModels OBJECT-TYPE
    SYNTAX     Gauge32
    MAX-ACCESS read-only
    STATUS     current
    DESCRIPTION
	    "Number of times  second that models can be
	    retrieved from the cache."
    ::= { rs2WebService 3 }

rs2wbsCacheMissesPerSec OBJECT-TYPE
    SYNTAX     Gauge32
    MAX-ACCESS read-only
    STATUS     current
    DESCRIPTION
	    "Number of times per second that reports cannot
	    be retrieved from cache."
    ::= { rs2WebService 4 }

rs2wbsCacheMissesSecSemantModels OBJECT-TYPE
    SYNTAX     Gauge32
    MAX-ACCESS read-only
    STATUS     current
    DESCRIPTION
	    "Number of times  second that models cannot be
	    retrieved from the cache."
    ::= { rs2WebService 5 }

rs2wbsFirstSessionRequestsPerSec OBJECT-TYPE
    SYNTAX     Gauge32
    MAX-ACCESS read-only
    STATUS     current
    DESCRIPTION
	    "Number of new user sessions that are started
	    per second."
    ::= { rs2WebService 6 }

rs2wbsMemoryCacheHitsPerSec OBJECT-TYPE
    SYNTAX     Gauge32
    MAX-ACCESS read-only
    STATUS     current
    DESCRIPTION
	    "Number of times per second that reports can be
	    retrieved from the in memory cache."
    ::= { rs2WebService 7 }

rs2wbsMemoryCacheMissPerSec OBJECT-TYPE
    SYNTAX     Gauge32
    MAX-ACCESS read-only
    STATUS     current
    DESCRIPTION
	    "Number of times per second that reports cannot
	    be retrieved from the in memory cache."
    ::= { rs2WebService 8 }

rs2wbsNextSessionRequestsPerSec OBJECT-TYPE
    SYNTAX     Gauge32
    MAX-ACCESS read-only
    STATUS     current
    DESCRIPTION
	    "Number of requests per second for reports that
	    are open in an existing session."
    ::= { rs2WebService 9 }

rs2wbsReportRequests OBJECT-TYPE
    SYNTAX     Gauge32
    MAX-ACCESS read-only
    STATUS     current
    DESCRIPTION
	    "Number of active report requests."
    ::= { rs2WebService 10 }

rs2wbsReportsExecutedPerSec OBJECT-TYPE
    SYNTAX     Gauge32
    MAX-ACCESS read-only
    STATUS     current
    DESCRIPTION
	    "Number of reports executed per second."
    ::= { rs2WebService 11 }

rs2wbsRequestsPerSec OBJECT-TYPE
    SYNTAX     Gauge32
    MAX-ACCESS read-only
    STATUS     current
    DESCRIPTION
	    "Number of requests per second."
    ::= { rs2WebService 12 }

rs2wbsTotalCacheHits OBJECT-TYPE
    SYNTAX     Gauge32
    MAX-ACCESS read-only
    STATUS     current
    DESCRIPTION
	    "Total number of report server cache hits."
    ::= { rs2WebService 13 }

rs2wbsTotalCacheHitSemanticModel OBJECT-TYPE
    SYNTAX     Gauge32
    MAX-ACCESS read-only
    STATUS     current
    DESCRIPTION
	    "Total number of cache hits made in the model
	    cache."
    ::= { rs2WebService 14 }

rs2wbsTotalCacheMisses OBJECT-TYPE
    SYNTAX     Gauge32
    MAX-ACCESS read-only
    STATUS     current
    DESCRIPTION
	    "Total number of cache misses."
    ::= { rs2WebService 15 }

rs2wbsTotalCachMissSemanticModel OBJECT-TYPE
    SYNTAX     Gauge32
    MAX-ACCESS read-only
    STATUS     current
    DESCRIPTION
	    "Total number of cache misses made in the model
	    cache."
    ::= { rs2WebService 16 }

rs2wbsTotalMemoryCacheHits OBJECT-TYPE
    SYNTAX     Gauge32
    MAX-ACCESS read-only
    STATUS     current
    DESCRIPTION
	    "Total number of cache hits made in the in
	    memory cache."
    ::= { rs2WebService 17 }

rs2wbsTotalMemoryCacheMisses OBJECT-TYPE
    SYNTAX     Gauge32
    MAX-ACCESS read-only
    STATUS     current
    DESCRIPTION
	    "Total number of cache misses made in the in
	    memory cache."
    ::= { rs2WebService 18 }

rs2wbsTotalProcessingFailures OBJECT-TYPE
    SYNTAX     Gauge32
    MAX-ACCESS read-only
    STATUS     current
    DESCRIPTION
	    "Total number of processing failures."
    ::= { rs2WebService 19 }

rs2wbsTotalRejectedThreads OBJECT-TYPE
    SYNTAX     Gauge32
    MAX-ACCESS read-only
    STATUS     current
    DESCRIPTION
	    "Total number of rejected threads as a result
	    of thread pressure."
    ::= { rs2WebService 20 }

rs2wbsTotalReportsExecute OBJECT-TYPE
    SYNTAX     Gauge32
    MAX-ACCESS read-only
    STATUS     current
    DESCRIPTION
	    "Total number of reports executed."
    ::= { rs2WebService 21 }

rs2wbsTotalRequests OBJECT-TYPE
    SYNTAX     Gauge32
    MAX-ACCESS read-only
    STATUS     current
    DESCRIPTION
	    "Total number of requests being processed."
    ::= { rs2WebService 22 }

rs2WindowsServiceTable OBJECT-TYPE
    SYNTAX     SEQUENCE OF MSRS2008WindowsServiceEntry
    MAX-ACCESS not-accessible
    STATUS     current
    DESCRIPTION
	    "A table containing performance information for
	    instances of 'MSRS Windows Service' objects."
    ::= { reportingServicesV2 2 }

rs2WindowsServiceEntry OBJECT-TYPE
    SYNTAX     MSRS2008WindowsServiceEntry
    MAX-ACCESS not-accessible
    STATUS     current
    DESCRIPTION
	    "Performance information for one particular
	    instance of 'MSRS Windows Service' object."
    INDEX      { rs2wnsInstance }
    ::= { rs2WindowsServiceTable 1 }

MSRS2008WindowsServiceEntry ::= SEQUENCE {
    rs2wnsInstance InstanceName,
    rs2wnsActiveSessions Gauge32,
    rs2wnsCacheFlushesPerSec Gauge32,
    rs2wnsCacheHitsPerSec Gauge32,
    rs2wnsCacheHitsSecSemanticModels Gauge32,
    rs2wnsCacheMissesPerSec Gauge32,
    rs2wnsCacheMissSecSemanticModels Gauge32,
    rs2wnsDeliversPerSec Gauge32,
    rs2wnsEventsPerSec Gauge32,
    rs2wnsFirstSessionRequestsPerSec Gauge32,
    rs2wnsMemoryCacheHitsPerSec Gauge32,
    rs2wnsMemoryCacheMissPerSec Gauge32,
    rs2wnsNextSessionRequestsPerSec Gauge32,
    rs2wnsReportRequests Gauge32,
    rs2wnsReportsExecutedPerSec Gauge32,
    rs2wnsRequestsPerSec Gauge32,
    rs2wnsSnapshotUpdatesPerSec Gauge32,
    rs2wnsTotalAppDomainRecycles Gauge32,
    rs2wnsTotalCacheFlushes Gauge32,
    rs2wnsTotalCacheHits Gauge32,
    rs2wnsTotalCacheHitSemanticModel Gauge32,
    rs2wnsTotalCacheMisses Gauge32,
    rs2wnsTotalCachMissSemanticModel Gauge32,
    rs2wnsTotalDeliveries Gauge32,
    rs2wnsTotalEvents Gauge32,
    rs2wnsTotalMemoryCacheHits Gauge32,
    rs2wnsTotalMemoryCacheMisses Gauge32,
    rs2wnsTotalProcessingFailures Gauge32,
    rs2wnsTotalRejectedThreads Gauge32,
    rs2wnsTotalReportsExecuted Gauge32,
    rs2wnsTotalRequests Gauge32,
    rs2wnsTotalSnapshotUpdates Gauge32
}

rs2wnsInstance OBJECT-TYPE
    SYNTAX     InstanceName
    MAX-ACCESS read-only
    STATUS     current
    DESCRIPTION
	    "Instance name."
    ::= { rs2WindowsServiceEntry 1 }

rs2wnsActiveSessions OBJECT-TYPE
    SYNTAX     Gauge32
    MAX-ACCESS read-only
    STATUS     current
    DESCRIPTION
	    "Number of active sessions."
    ::= { rs2WindowsServiceEntry 2 }

rs2wnsCacheFlushesPerSec OBJECT-TYPE
    SYNTAX     Gauge32
    MAX-ACCESS read-only
    STATUS     current
    DESCRIPTION
	    "Number of cache flushes per second."
    ::= { rs2WindowsServiceEntry 3 }

rs2wnsCacheHitsPerSec OBJECT-TYPE
    SYNTAX     Gauge32
    MAX-ACCESS read-only
    STATUS     current
    DESCRIPTION
	    "Number of report server cache hits per
	    second."
    ::= { rs2WindowsServiceEntry 4 }

rs2wnsCacheHitsSecSemanticModels OBJECT-TYPE
    SYNTAX     Gauge32
    MAX-ACCESS read-only
    STATUS     current
    DESCRIPTION
	    "Number of times  second that models can be
	    retrieved from the cache."
    ::= { rs2WindowsServiceEntry 5 }

rs2wnsCacheMissesPerSec OBJECT-TYPE
    SYNTAX     Gauge32
    MAX-ACCESS read-only
    STATUS     current
    DESCRIPTION
	    "Number of times per second that reports cannot
	    be retrieved from cache."
    ::= { rs2WindowsServiceEntry 6 }

rs2wnsCacheMissSecSemanticModels OBJECT-TYPE
    SYNTAX     Gauge32
    MAX-ACCESS read-only
    STATUS     current
    DESCRIPTION
	    "Number of times  second that models cannot be
	    retrieved from the cache."
    ::= { rs2WindowsServiceEntry 7 }

rs2wnsDeliversPerSec OBJECT-TYPE
    SYNTAX     Gauge32
    MAX-ACCESS read-only
    STATUS     current
    DESCRIPTION
	    "Number of delivers deliveries per second."
    ::= { rs2WindowsServiceEntry 8 }

rs2wnsEventsPerSec OBJECT-TYPE
    SYNTAX     Gauge32
    MAX-ACCESS read-only
    STATUS     current
    DESCRIPTION
	    "Number of events per second."
    ::= { rs2WindowsServiceEntry 9 }

rs2wnsFirstSessionRequestsPerSec OBJECT-TYPE
    SYNTAX     Gauge32
    MAX-ACCESS read-only
    STATUS     current
    DESCRIPTION
	    "Number of new user sessions that are started
	    per second."
    ::= { rs2WindowsServiceEntry 10 }

rs2wnsMemoryCacheHitsPerSec OBJECT-TYPE
    SYNTAX     Gauge32
    MAX-ACCESS read-only
    STATUS     current
    DESCRIPTION
	    "Number of times per second that reports can be
	    retrieved from the in memory cache."
    ::= { rs2WindowsServiceEntry 11 }

rs2wnsMemoryCacheMissPerSec OBJECT-TYPE
    SYNTAX     Gauge32
    MAX-ACCESS read-only
    STATUS     current
    DESCRIPTION
	    "Number of times per second that reports cannot
	    be retrieved from the in memory cache."
    ::= { rs2WindowsServiceEntry 12 }

rs2wnsNextSessionRequestsPerSec OBJECT-TYPE
    SYNTAX     Gauge32
    MAX-ACCESS read-only
    STATUS     current
    DESCRIPTION
	    "Number of requests per second for reports that
	    are open in an existing session."
    ::= { rs2WindowsServiceEntry 13 }

rs2wnsReportRequests OBJECT-TYPE
    SYNTAX     Gauge32
    MAX-ACCESS read-only
    STATUS     current
    DESCRIPTION
	    "Number of active report requests."
    ::= { rs2WindowsServiceEntry 14 }

rs2wnsReportsExecutedPerSec OBJECT-TYPE
    SYNTAX     Gauge32
    MAX-ACCESS read-only
    STATUS     current
    DESCRIPTION
	    "Number of reports executed per second."
    ::= { rs2WindowsServiceEntry 15 }

rs2wnsRequestsPerSec OBJECT-TYPE
    SYNTAX     Gauge32
    MAX-ACCESS read-only
    STATUS     current
    DESCRIPTION
	    "Number of requests per second."
    ::= { rs2WindowsServiceEntry 16 }

rs2wnsSnapshotUpdatesPerSec OBJECT-TYPE
    SYNTAX     Gauge32
    MAX-ACCESS read-only
    STATUS     current
    DESCRIPTION
	    "Number of snapshot updates per second."
    ::= { rs2WindowsServiceEntry 17 }

rs2wnsTotalAppDomainRecycles OBJECT-TYPE
    SYNTAX     Gauge32
    MAX-ACCESS read-only
    STATUS     current
    DESCRIPTION
	    "Total number of application domain recycles."
    ::= { rs2WindowsServiceEntry 18 }

rs2wnsTotalCacheFlushes OBJECT-TYPE
    SYNTAX     Gauge32
    MAX-ACCESS read-only
    STATUS     current
    DESCRIPTION
	    "Total number of report execution server cache
	    updates."
    ::= { rs2WindowsServiceEntry 19 }

rs2wnsTotalCacheHits OBJECT-TYPE
    SYNTAX     Gauge32
    MAX-ACCESS read-only
    STATUS     current
    DESCRIPTION
	    "Total number of report server cache hits."
    ::= { rs2WindowsServiceEntry 20 }

rs2wnsTotalCacheHitSemanticModel OBJECT-TYPE
    SYNTAX     Gauge32
    MAX-ACCESS read-only
    STATUS     current
    DESCRIPTION
	    "Total number of cache hits made in the model
	    cache."
    ::= { rs2WindowsServiceEntry 21 }

rs2wnsTotalCacheMisses OBJECT-TYPE
    SYNTAX     Gauge32
    MAX-ACCESS read-only
    STATUS     current
    DESCRIPTION
	    "Total number of cache misses."
    ::= { rs2WindowsServiceEntry 22 }

rs2wnsTotalCachMissSemanticModel OBJECT-TYPE
    SYNTAX     Gauge32
    MAX-ACCESS read-only
    STATUS     current
    DESCRIPTION
	    "Total number of cache misses made in the model
	    cache."
    ::= { rs2WindowsServiceEntry 23 }

rs2wnsTotalDeliveries OBJECT-TYPE
    SYNTAX     Gauge32
    MAX-ACCESS read-only
    STATUS     current
    DESCRIPTION
	    "Total number of deliveries."
    ::= { rs2WindowsServiceEntry 24 }

rs2wnsTotalEvents OBJECT-TYPE
    SYNTAX     Gauge32
    MAX-ACCESS read-only
    STATUS     current
    DESCRIPTION
	    "Total number of events."
    ::= { rs2WindowsServiceEntry 25 }

rs2wnsTotalMemoryCacheHits OBJECT-TYPE
    SYNTAX     Gauge32
    MAX-ACCESS read-only
    STATUS     current
    DESCRIPTION
	    "Total number of cache hits made in the in
	    memory cache."
    ::= { rs2WindowsServiceEntry 26 }

rs2wnsTotalMemoryCacheMisses OBJECT-TYPE
    SYNTAX     Gauge32
    MAX-ACCESS read-only
    STATUS     current
    DESCRIPTION
	    "Total number of cache misses made in the in
	    memory cache."
    ::= { rs2WindowsServiceEntry 27 }

rs2wnsTotalProcessingFailures OBJECT-TYPE
    SYNTAX     Gauge32
    MAX-ACCESS read-only
    STATUS     current
    DESCRIPTION
	    "Total number of processing failures."
    ::= { rs2WindowsServiceEntry 28 }

rs2wnsTotalRejectedThreads OBJECT-TYPE
    SYNTAX     Gauge32
    MAX-ACCESS read-only
    STATUS     current
    DESCRIPTION
	    "Total number of rejected threads as a result
	    of thread pressure."
    ::= { rs2WindowsServiceEntry 29 }

rs2wnsTotalReportsExecuted OBJECT-TYPE
    SYNTAX     Gauge32
    MAX-ACCESS read-only
    STATUS     current
    DESCRIPTION
	    "Total number of reports executed."
    ::= { rs2WindowsServiceEntry 30 }

rs2wnsTotalRequests OBJECT-TYPE
    SYNTAX     Gauge32
    MAX-ACCESS read-only
    STATUS     current
    DESCRIPTION
	    "Total number of requests being processed."
    ::= { rs2WindowsServiceEntry 31 }

rs2wnsTotalSnapshotUpdates OBJECT-TYPE
    SYNTAX     Gauge32
    MAX-ACCESS read-only
    STATUS     current
    DESCRIPTION
	    "Total number of report execution snapshot
	    updates."
    ::= { rs2WindowsServiceEntry 32 }

rs2ReportServerHTTPTable OBJECT-TYPE
    SYNTAX     SEQUENCE OF ReportingServicesNameEntry
    MAX-ACCESS not-accessible
    STATUS     current
    DESCRIPTION
	    "Statistics related to Report Server HTTP
	    Service"
    ::= { reportingServicesV2 3 }

rs2ReportServerHTTPEntry OBJECT-TYPE
    SYNTAX     ReportingServicesNameEntry
    MAX-ACCESS not-accessible
    STATUS     current
    DESCRIPTION
	    "Performance information for one SQL Server
	    name instance."
    INDEX      { rs2HTTPNameIndex }
    ::= { rs2ReportServerHTTPTable 1 }

ReportingServicesNameEntry ::= SEQUENCE {
    rs2HTTPNameIndex Integer32,
    rs2HTTPNameInstance InstanceName,
    rs2HTTPRequestsPerSec Gauge32,
    rs2HTTPTotalRequests Gauge32
}

rs2HTTPNameIndex OBJECT-TYPE
    SYNTAX     Integer32 (1..2147483647)
    MAX-ACCESS read-only
    STATUS     current
    DESCRIPTION
	    "The index number associated with the instance
	    name"
    ::= { rs2ReportServerHTTPEntry 1 }

rs2HTTPNameInstance OBJECT-TYPE
    SYNTAX     InstanceName
    MAX-ACCESS read-only
    STATUS     current
    DESCRIPTION
	    "The name of the Report Server installed
	    instance."
    ::= { rs2ReportServerHTTPEntry 2 }

rs2HTTPRequestsPerSec OBJECT-TYPE
    SYNTAX     Gauge32
    MAX-ACCESS read-only
    STATUS     current
    DESCRIPTION
	    "Number of HTTP requests received."
    ::= { rs2ReportServerHTTPEntry 3 }

rs2HTTPTotalRequests OBJECT-TYPE
    SYNTAX     Gauge32
    MAX-ACCESS read-only
    STATUS     current
    DESCRIPTION
	    "Total number of HTTP requests received."
    ::= { rs2ReportServerHTTPEntry 4 }

END
