-- ****************************************************************************
--                             InnovxDte.mib
-- ****************************************************************************

-- INNOVX Access Probe - DTE Interface MIB


-- Copyright 1999 General DataComm Inc., All Rights Reserved.

-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.

-- This Specification is supplied "AS IS," and GDC makes no warranty,
-- either expressed or implied, as to the use operation, condition, or
-- performance of the Specification.


-- Objects in this mib may be controlled or influenced by objects
-- in the Innovx Access Probe Core mib: InnovxCore.mib



-- ****************************************************************************
--                        Revision History
-- ****************************************************************************

-- Version   Date	Name/Comments

-- 1.00A     19-Feb-99  L. Olah
--                      1) Initial Revision
--
-- 1.00B     24-Feb-99  S. Veillette
--                      1) rename mib to InnovxDte.mib
--                      2) pack bits from bit 0 up for dteLedStatus object

-- 1.00C     24-Feb-99  S. Veillette
--                      1) change mib definition name tag
--                         DDS-MIB => INNOVX-DDS-MIB

-- 1.00D     25-Feb-99  S. Veillette
--                      1) change mib definition name tag
--                         INNOVX-DDS-MIB => INNOVX-DTE-MIB
--                      2) Remove Gauge IMPORT, not used warning
--			3) Change object name ddsMIBversion => dtesMIBversion
--
-- 1.00E     26-Feb-99  A. Limoncelli
-- 			1) combined dteInvertTiming and dteTxTiming objects 
--			   into one object
--			2) deleted  dteTmControl object

-- 1.00F      3-Mar-99  S. Veillette
--                      1) Add WEBFLAG/WEBEND tokens to description text of
--                         enumerated objects for web page support.
--                      2) re-ordered enums for dteInterfaceType object

-- 1.00G      4-Mar-99  S. Veillette
--                      1) Add WEBFLAG/WEBEND tokens to 
--                         dteDtrLossTrapSeverity object

-- 1.00H     18-Mar-99  S. Shankar
--                      1) Added dteDiagTestDuration
--                      2) Added dteDiagTestStatus   

-- 1.00I      7-Apr-99  S. Veillette
--                      1) Remove V.36 options from dteInterfaceType

-- 1.00J      8-Sep-99  L. Olah
--			1) bump rev to J, since I should not be used.


-- ****************************************************************************



--
-- ****************************************************************************
--                       mib definitions begin
-- ****************************************************************************


INNOVX-DTE-MIB DEFINITIONS ::= BEGIN

IMPORTS	
OBJECT-TYPE		FROM RFC-1212
DisplayString		FROM RFC1213-MIB
dteGroup		FROM INNOVX-CORE-MIB;


dteAdmin        	OBJECT IDENTIFIER ::= { dteGroup  1 }
dteCfg     		OBJECT IDENTIFIER ::= { dteGroup  2 }
dteAlarmCfg	 	OBJECT IDENTIFIER ::= { dteGroup  3 }
dteDiagnostics		OBJECT IDENTIFIER ::= { dteGroup  4 }
dteStatus		OBJECT IDENTIFIER ::= { dteGroup  5 }




--
-- ****************************************************************************
--                            Administrative Group
-- ****************************************************************************


dtesMIBversion OBJECT-TYPE
    SYNTAX DisplayString (SIZE (5))
    ACCESS read-only
    STATUS mandatory
    DESCRIPTION
    "Identifies the version of the MIB as `X.YZT' where:

	X: Major Revision         (1-9)
	Y: Minor Revision         (0-9)
	Z: Typographical Revision (0-9)
	T: Test Revision          (A-Z)

    Upon formal release, the test revision will not be present."

    ::= { dteAdmin 1 }



--
-- ****************************************************************************
--                DTE Configuration
-- ****************************************************************************


dteInterfaceType OBJECT-TYPE
    SYNTAX INTEGER 
    {
	v28      (1),
    	v35      (2),	
	rs449    (3),
	eia530   (4),
	eia530a  (5),
	x21      (6)
    }
    ACCESS read-write
    STATUS mandatory
    DESCRIPTION
    "Defines the DTE Interface Type.
    WEBFLAG
    V.28
    V.35
    RS-449
    EIA-530
    EIA-530A
    X.21
    WEBEND"

    ::= { dteCfg 1 }


dteTxInvertingTiming OBJECT-TYPE
    SYNTAX INTEGER 
    {
    	slaveNormal  (1),			
    	slaveInvert  (2),
    	external     (3)			
    }
    ACCESS read-write
    STATUS mandatory
    DESCRIPTION
    "normal(1) tx timing clocks the transmit data from the DTE using
    an internal generated clock. invert (2) Invert Internally generated 
    transmit clock used to sample the transmit data from the DTE.
    external(3) uses the DTE clock, EXTCLK, to clock the transmit data
    from the DTE.
    WEBFLAG
    Slave Normal
    Slave Inverted
    External
    WEBEND"

    ::= { dteCfg 2 }


dteRxCarrier OBJECT-TYPE
    SYNTAX INTEGER 
    {
    	forcedOn  (1),
        normal    (2)
    }
    ACCESS read-write
    STATUS mandatory
    DESCRIPTION
    "The Receive Carrier option. This option controls the operation of DCD.
    WEBFLAG
    Forced On
    Normal Operation
    WEBEND"

    ::= { dteCfg 3 }


dteDsrControl OBJECT-TYPE
    SYNTAX INTEGER 
    {
    	forcedOn    (1),
        followsDTR  (2)
    }
    ACCESS read-write
    STATUS mandatory
    DESCRIPTION
    "The DSR option.  This option controls the operation of DSR.
    When forcedOn(1) is selected, DSR is normally on, 
    if set for followsDTR(2) then DSR is on only when DTR is on.
    WEBFLAG
    Forced On
    Follows DTR
    WEBEND"

    ::= { dteCfg 4 }
 


--
-- ****************************************************************************
--                DTE Mask Configuration Group
-- ****************************************************************************


dteDtrLossTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Channel Data
    Terminal Ready Loss Alarm when this event occurs.
    WEBFLAG
    Inhibit
    Critical
    Major
    Minor
    Warning
    Info
    WEBEND"

    ::= { dteAlarmCfg 1 }

--
-- ****************************************************************************
--                        Diagnostics Group
-- ****************************************************************************


dteLoopback OBJECT-TYPE
    SYNTAX INTEGER 
    {
	noTest  (1),
    	toChan  (2)
    }
    ACCESS read-write
    STATUS mandatory
    DESCRIPTION
    "Control the DTE loopback to the channel. noTest(1) stops 
    the test. toChan(2) starts a loopback toward the DTE."

    ::= { dteDiagnostics 1 }


dteDiagTestDuration OBJECT-TYPE
    SYNTAX INTEGER
    {
        testTime1Min    (1),
        testTime5Mins   (2),
        testTime10Mins  (3),
        testTime20Mins  (4)
    }   
    ACCESS read-write
    STATUS mandatory
    DESCRIPTION
    "Defines the length of the  diagnostic test."
 
    ::= { dteDiagnostics 2 }
 

dteDiagTestStatus OBJECT-TYPE
    SYNTAX INTEGER
    {
  	statDteLoop    			  (1),
	statNoTestinProgress      (2)
    }
    ACCESS read-only
    STATUS mandatory
    DESCRIPTION
    "Displays the test in progress, if any."

    ::= { dteDiagnostics 3 }




-- ****************************************************************************
--                             Status Group
-- ****************************************************************************


dteLedStatus OBJECT-TYPE	
    SYNTAX OCTET STRING (SIZE(1))
    ACCESS read-only
    STATUS mandatory
    DESCRIPTION
    "A bitwise snapshot of the front panel LED states, 
    where 0 = LED off and 1 = LED on, as follows:

                        LED       description
 
    Octet 1     bit 7 - n/u
                bit 6 - n/u               
		bit 5 - n/u
		bit 4 - n/u
		bit 3 - n/u
		bit 2 - DTE LMI   LMI traffic on DTE
		bit 1 - SD EQP    send data - equipment traffic
		bit 0 - RD EQP    receive data - equipment traffic"

    ::= { dteStatus 1 }


dtePortStatus OBJECT-TYPE
    SYNTAX  OCTET STRING (SIZE(1))
    ACCESS  read-only
    STATUS  mandatory
    DESCRIPTION
    "A bitwise snapshot of interface port status conditions and EIA signals,
    where 0 = condition not present, and 1 = condition present, as follows:

    Octet 1 - DTE Interface Port Status
 		bit 7 - n/u
               	bit 6 - n/u
                bit 5 - n/u
                bit 4 - n/u
                bit 3 - n/u
                bit 2 - Transmit Activity
                bit 1 - Receive Activity
                bit 0 - DTR Loss"

    ::= { dteStatus 2 }


dtePortFrameCounts OBJECT-TYPE
    SYNTAX  OCTET STRING (SIZE(4))
    ACCESS  read-only
    STATUS  mandatory
    DESCRIPTION
    "The total number of frames transmitted and received on each interface
    port.  This object will be reset to zero after a read, and after power up,
    soft reset, or factory defaults reset.

    Octet 1 - DTE Interface Transmit Frame Count	Octet 2
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0

    Octet 3 - DTE Interface Receive Frame Count       	Octet 4
 		bit 7 - 2^15 				bit 7 - 2^7
               	bit 6 - 2^14				bit 6 - 2^6	
                bit 5 - 2^13				bit 5 - 2^5
                bit 4 - 2^12				bit 4 - 2^4	
                bit 3 - 2^11				bit 3 - 2^3
                bit 2 - 2^10				bit 2 - 2^2
                bit 1 - 2^9				bit 1 - 2^1
                bit 0 - 2^8				bit 0 - 2^0"

::= { dteStatus 3 }
    

 
-- ****************************************************************************
--                       mib definitions end
-- ****************************************************************************

END
