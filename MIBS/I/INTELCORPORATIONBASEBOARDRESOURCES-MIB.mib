-- MIB generated by miftomib version 1.0a

INTELCORPORATIONBASEBOARDRESOURCES-MIB DEFINITIONS ::= BEGIN

-- This component provides information on the system resources in the N440BX 
-- DP Product the Groups in this component are a subset of the Standard 
-- System MIF Groups.

IMPORTS
    OBJECT-TYPE
    FROM RFC-1212
    enterprises
    FROM RFC1155-SMI
    DisplayString
    FROM RFC1213-MIB;

DmiInteger			::= INTEGER
DmiInteger64X		::= INTEGER (-18446744073709551615..18446744073709551615)
DmiDisplaystring	::= DisplayString
DmiDateX			::= OCTET STRING (SIZE (28))
DmiComponentIndex	::= INTEGER

intel                   OBJECT IDENTIFIER ::= {enterprises 343}
products                OBJECT IDENTIFIER ::= {intel 2}
server-products         OBJECT IDENTIFIER ::= {products 6}
platforms               OBJECT IDENTIFIER ::= {server-products 2}
resources               OBJECT IDENTIFIER ::= {platforms 3}
dmtfGroups              OBJECT IDENTIFIER ::= {resources 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
This groupis required."
	::= {dmtfGroups 1}

eComponentid OBJECT-TYPE
	SYNTAX		SComponentid
	ACCESS		not-accessible
	STATUS		mandatory
	DESCRIPTION	""
	--INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is stillinstalled and working."
	::= {eComponentid 6}

SSystemResources2 ::= SEQUENCE {
	a41SystemResourcesIndex                 	DmiInteger,
	a41ResourceUser                         	DmiInteger,
	a41ResourceSet                          	DmiInteger,
	a41ResourceAssignment                   	DmiInteger,
	a41ResourceType                         	DmiInteger,
	a41ResourceNumber                       	DmiInteger,
	a41ResourceInfoId                       	DmiInteger,
	a41StartAddress                         	DmiInteger64X,
	a41EndAddress                           	DmiInteger64X,
	a41ResourceSize                         	DmiInteger,
	a41BaseAlignment                        	DmiInteger,
	a41Shareable                            	DmiInteger,
	a41Shared                               	DmiInteger
}

tSystemResources2 OBJECT-TYPE
	SYNTAX		SEQUENCE OF SSystemResources2
	ACCESS		not-accessible
	STATUS		mandatory
	DESCRIPTION	"This group describes the base level of Memory, I/O, DMA,
and INT(interrupt) resources that are used by a device in the system."
	::= {dmtfGroups 41}

eSystemResources2 OBJECT-TYPE
	SYNTAX		SSystemResources2
	ACCESS		not-accessible
	STATUS		mandatory
	DESCRIPTION	""
	--INDEX		{DmiComponentIndex, a41SystemResourcesIndex}
	::= {tSystemResources2 1}

a41SystemResourcesIndex OBJECT-TYPE
	SYNTAX		DmiInteger
	ACCESS		read-only
	STATUS		mandatory
	DESCRIPTION	"A number that uniquely identifies the rows in this table."
	::= {eSystemResources2 1}

a41ResourceUser OBJECT-TYPE
	SYNTAX		DmiInteger
	ACCESS		read-only
	STATUS		mandatory
	DESCRIPTION	"A unique number for each different 'resource user' that has
resourcesspecified in this table."
	::= {eSystemResources2 2}

a41ResourceSet OBJECT-TYPE
	SYNTAX		DmiInteger
	ACCESS		read-only
	STATUS		mandatory
	DESCRIPTION	"A number used as the ID of a set of Memory, I/O, DMA and/or
INTresources for the resource user."
	::= {eSystemResources2 3}

a41ResourceAssignment OBJECT-TYPE
	SYNTAX		INTEGER {
		vOther                                  	(1),
		vUnknown                                	(2),
		vAllocated                              	(3),
		vAssignable                             	(4),
		vTemporaryAssignment                    	(5)
	}
	ACCESS		read-only
	STATUS		mandatory
	DESCRIPTION	"Describes the state of the assignment of this set of resources.
(Note: Thisvalue must be the same for all resources within a given set.)"
	::= {eSystemResources2 4}

a41ResourceType OBJECT-TYPE
	SYNTAX		INTEGER {
		vOther                                  	(1),
		vUnknown                                	(2),
		vMemory                                 	(3),
		vIo                                     	(4),
		vIrq                                    	(5),
		vDma                                    	(6)
	}
	ACCESS		read-only
	STATUS		mandatory
	DESCRIPTION	"The type of resource described by this row."
	::= {eSystemResources2 5}

a41ResourceNumber OBJECT-TYPE
	SYNTAX		DmiInteger
	ACCESS		read-only
	STATUS		mandatory
	DESCRIPTION	"DMA or IRQ number - 0 for Memory and I/O ranges. This is
theinterrupt or DMA number relative to the bus that the interrupt is sourced
from."
	::= {eSystemResources2 6}

a41ResourceInfoId OBJECT-TYPE
	SYNTAX		DmiInteger
	ACCESS		read-only
	STATUS		mandatory
	DESCRIPTION	"ID of the row in the 'Info' table for this type of system
resource. E.g. ifthis Resource Type is 'I/O' then this would be an index
into the 'System Resource I/OInfo' table."
	::= {eSystemResources2 7}

a41StartAddress OBJECT-TYPE
	SYNTAX		DmiInteger64X
	ACCESS		read-only
	STATUS		mandatory
	DESCRIPTION	"Starting physical address for this memory range, or the minimum
baseaddress if this attribute is being used to describe a programmable range.
0 for IRQ andDMA resources."
	::= {eSystemResources2 8}

a41EndAddress OBJECT-TYPE
	SYNTAX		DmiInteger64X
	ACCESS		read-only
	STATUS		mandatory
	DESCRIPTION	"Ending physical address (address of last byte) for this memory
range, orthe maximum configurable base address if this attribute is being
used to describe aprogrammable range. 0 for IRQ and DMA resources."
	::= {eSystemResources2 9}

a41ResourceSize OBJECT-TYPE
	SYNTAX		DmiInteger
	ACCESS		read-only
	STATUS		mandatory
	DESCRIPTION	"Number of consecutive bytes that a memory or I/O resource
consumes. 0for IRQ and DMA resources."
	::= {eSystemResources2 10}

a41BaseAlignment OBJECT-TYPE
	SYNTAX		DmiInteger
	ACCESS		read-only
	STATUS		mandatory
	DESCRIPTION	"Alignment of Start Address, in bytes. Indicates the granularity
of theincrements in which a programmable range can be set."
	::= {eSystemResources2 11}

a41Shareable OBJECT-TYPE
	SYNTAX		INTEGER {
		vFalse                                  	(0),
		vTrue                                   	(1),
		vUnknown                                	(2)
	}
	ACCESS		read-only
	STATUS		mandatory
	DESCRIPTION	"Indicates whether the resource is shareable."
	::= {eSystemResources2 12}

a41Shared OBJECT-TYPE
	SYNTAX		INTEGER {
		vFalse                                  	(0),
		vTrue                                   	(1),
		vUnknown                                	(2)
	}
	ACCESS		read-only
	STATUS		mandatory
	DESCRIPTION	"Indicates whether this resource, or a portion of this resource,
is sharedwith another device."
	::= {eSystemResources2 13}

SSystemResourceDeviceInfo ::= SEQUENCE {
	a42ResourceUser                         	DmiInteger,
	a42DeviceId                             	DmiInteger,
	a42DeviceSerialNumber                   	DmiInteger,
	a42LogicalDeviceId-ClassCode            	DmiInteger,
	a42DeviceFlags                          	DmiInteger,
	a42DeviceNumber                         	DmiInteger,
	a42FunctionNumber                       	DmiInteger,
	a42BusType                              	DmiInteger,
	a42CmReserved                           	DmiInteger
}

tSystemResourceDeviceInfo OBJECT-TYPE
	SYNTAX		SEQUENCE OF SSystemResourceDeviceInfo
	ACCESS		not-accessible
	STATUS		mandatory
	DESCRIPTION	"This group describes the base level of Memory, I/O, DMA,
and INT(interrupt) resources that are used by a device in the system."
	::= {dmtfGroups 42}

eSystemResourceDeviceInfo OBJECT-TYPE
	SYNTAX		SSystemResourceDeviceInfo
	ACCESS		not-accessible
	STATUS		mandatory
	DESCRIPTION	""
	--INDEX		{DmiComponentIndex, a42ResourceUser}
	::= {tSystemResourceDeviceInfo 1}

a42ResourceUser OBJECT-TYPE
	SYNTAX		DmiInteger
	ACCESS		read-only
	STATUS		mandatory
	DESCRIPTION	"A number that uniquely identifies this device. This number
may bederived from the 'device number' that is assigned by 'Plug N Play',
or may be uniquelyassigned by the component instrumentation."
	::= {eSystemResourceDeviceInfo 1}

a42DeviceId OBJECT-TYPE
	SYNTAX		DmiInteger
	ACCESS		read-only
	STATUS		mandatory
	DESCRIPTION	"Physical Device ID from Config manager info. Equal to theCISTPL_
ANFID field for PCMCIA devices. 0xFFFFFFFF = Unknown"
	::= {eSystemResourceDeviceInfo 2}

a42DeviceSerialNumber OBJECT-TYPE
	SYNTAX		DmiInteger
	ACCESS		read-only
	STATUS		mandatory
	DESCRIPTION	"Device Serial Number from Config manager info. 0 = Undefined"
	::= {eSystemResourceDeviceInfo 3}

a42LogicalDeviceId-ClassCode OBJECT-TYPE
	SYNTAX		DmiInteger
	ACCESS		read-only
	STATUS		mandatory
	DESCRIPTION	"Logical device ID for PnP ISA devices, Class code for PCI
devices, CISTPL_FUNCID for PCMCIA devices. 0xFFFFFFFF = Undefined, 0 = reserved"
	::= {eSystemResourceDeviceInfo 4}

a42DeviceFlags OBJECT-TYPE
	SYNTAX		DmiInteger
	ACCESS		read-only
	STATUS		mandatory
	DESCRIPTION	"Device flags from config manager info.Bit 0: 1 = device has
been initializedBit 1: 1 = device is enabledBit 2: 1 = device config has
been lockedBit 3: 1 = device has temporary config resources assignedBit 4:
1 = device is reconfigurable"
	::= {eSystemResourceDeviceInfo 5}

a42DeviceNumber OBJECT-TYPE
	SYNTAX		DmiInteger
	ACCESS		read-only
	STATUS		mandatory
	DESCRIPTION	"Device Number for PCI Devices, Logical Device number for
PnPDevices. 0 otherwise."
	::= {eSystemResourceDeviceInfo 6}

a42FunctionNumber OBJECT-TYPE
	SYNTAX		DmiInteger
	ACCESS		read-only
	STATUS		mandatory
	DESCRIPTION	"Function Number for PCI & EISA Devices. 0 otherwise."
	::= {eSystemResourceDeviceInfo 7}

a42BusType OBJECT-TYPE
	SYNTAX		DmiInteger
	ACCESS		read-only
	STATUS		mandatory
	DESCRIPTION	"Bus number (0-255) for PCI Devices, Slot number for EISA
and PnPDevices, Card logical socket number for PCMCIA devices. Zero otherwise."
	::= {eSystemResourceDeviceInfo 8}

a42CmReserved OBJECT-TYPE
	SYNTAX		DmiInteger
	ACCESS		read-only
	STATUS		mandatory
	DESCRIPTION	"Data from the Reserved field of the Configuration Manager
bus accessstructure, or 0."
	::= {eSystemResourceDeviceInfo 9}

SSystemResourceMemoryInfo ::= SEQUENCE {
	a43SystemResourceMemoryInfoIndex        	DmiInteger,
	a43IsapcmciaRangeDescriptor             	DmiInteger,
	a43EisaRangeDescriptor                  	DmiInteger,
	a43DecodeSupport                        	DmiInteger,
	a43Cacheable                            	DmiInteger,
	a43CacheType                            	DmiInteger,
	a43Read-write                           	DmiInteger
}

tSystemResourceMemoryInfo OBJECT-TYPE
	SYNTAX		SEQUENCE OF SSystemResourceMemoryInfo
	ACCESS		not-accessible
	STATUS		mandatory
	DESCRIPTION	"This group presents additional information about memory resource
 thathave been defined in the System Resources table."
	::= {dmtfGroups 43}

eSystemResourceMemoryInfo OBJECT-TYPE
	SYNTAX		SSystemResourceMemoryInfo
	ACCESS		not-accessible
	STATUS		mandatory
	DESCRIPTION	""
	--INDEX		{DmiComponentIndex, a43SystemResourceMemoryInfoIndex}
	::= {tSystemResourceMemoryInfo 1}

a43SystemResourceMemoryInfoIndex OBJECT-TYPE
	SYNTAX		DmiInteger
	ACCESS		read-only
	STATUS		mandatory
	DESCRIPTION	"A number the uniquely identifies rows in this table."
	::= {eSystemResourceMemoryInfo 1}

a43IsapcmciaRangeDescriptor OBJECT-TYPE
	SYNTAX		INTEGER {
		vOther                                  	(1),
		vUnknown                                	(2),
		v8-bitMemoryOnly                        	(3),
		v16-bitMemoryOnly                       	(4),
		v8-And16-bitMemorySupported             	(5),
		v32-bitMemoryOnly                       	(6)
	}
	ACCESS		read-only
	STATUS		mandatory
	DESCRIPTION	"For PnP ISA/PCMCIA memory range descriptor compatibility."
	::= {eSystemResourceMemoryInfo 2}

a43EisaRangeDescriptor OBJECT-TYPE
	SYNTAX		INTEGER {
		vOther                                  	(1),
		vUnknown                                	(2),
		v8-bitMemoryOnly                        	(3),
		v16-bitMemoryOnly                       	(4),
		v8-And16-bitMemorySupported             	(5),
		v32-bitMemoryOnly                       	(6)
	}
	ACCESS		read-only
	STATUS		mandatory
	DESCRIPTION	"For PnP EISA memory range descriptor compatibility."
	::= {eSystemResourceMemoryInfo 3}

a43DecodeSupport OBJECT-TYPE
	SYNTAX		INTEGER {
		vOther                                  	(1),
		vUnknown                                	(2),
		vDecodeSupportsHighAddress              	(3),
		vDecodeSupportsRangeLength              	(4)
	}
	ACCESS		read-only
	STATUS		mandatory
	DESCRIPTION	"For PnP memory range descriptor compatibility."
	::= {eSystemResourceMemoryInfo 4}

a43Cacheable OBJECT-TYPE
	SYNTAX		INTEGER {
		vFalse                                  	(0),
		vTrue                                   	(1),
		vUnknown                                	(2)
	}
	ACCESS		read-only
	STATUS		mandatory
	DESCRIPTION	"Indicates whether it is allowable for this memory range to
be cached ornot."
	::= {eSystemResourceMemoryInfo 5}

a43CacheType OBJECT-TYPE
	SYNTAX		INTEGER {
		vOther                                  	(1),
		vUnknown                                	(2),
		vWrite-back                             	(3),
		vWrite-through                          	(4)
	}
	ACCESS		read-only
	STATUS		mandatory
	DESCRIPTION	"Indicates Cache Type that is compatible with this resource."
	::= {eSystemResourceMemoryInfo 6}

a43Read-write OBJECT-TYPE
	SYNTAX		INTEGER {
		vOther                                  	(1),
		vUnknown                                	(2),
		vRomReadOnly                            	(3),
		vRamReadwrite                           	(4)
	}
	ACCESS		read-only
	STATUS		mandatory
	DESCRIPTION	"Indicates the read-write accessibility of this memory resource."
	::= {eSystemResourceMemoryInfo 7}

SSystemResourceIoInfo ::= SEQUENCE {
	a44SystemResourceIoInfoIndex            	DmiInteger,
	a44IoDecode                             	DmiInteger
}

tSystemResourceIoInfo OBJECT-TYPE
	SYNTAX		SEQUENCE OF SSystemResourceIoInfo
	ACCESS		not-accessible
	STATUS		mandatory
	DESCRIPTION	"This group presents additional information about I/O resources
that havebeen defined in the System Resources table."
	::= {dmtfGroups 44}

eSystemResourceIoInfo OBJECT-TYPE
	SYNTAX		SSystemResourceIoInfo
	ACCESS		not-accessible
	STATUS		mandatory
	DESCRIPTION	""
	--INDEX		{DmiComponentIndex, a44SystemResourceIoInfoIndex}
	::= {tSystemResourceIoInfo 1}

a44SystemResourceIoInfoIndex OBJECT-TYPE
	SYNTAX		DmiInteger
	ACCESS		read-only
	STATUS		mandatory
	DESCRIPTION	"A number the uniquely identifies rows in this table."
	::= {eSystemResourceIoInfo 1}

a44IoDecode OBJECT-TYPE
	SYNTAX		INTEGER {
		vOther                                  	(1),
		vUnknown                                	(2),
		v10Bits                                 	(3),
		v16Bits                                 	(4)
	}
	ACCESS		read-only
	STATUS		mandatory
	DESCRIPTION	"Number of bits used for I/O decode"
	::= {eSystemResourceIoInfo 2}

SSystemResourceIrqInfo ::= SEQUENCE {
	a45SystemResourceIrqInfoIndex           	DmiInteger,
	a45TriggerType                          	DmiInteger,
	a45TriggerLevel                         	DmiInteger
}

tSystemResourceIrqInfo OBJECT-TYPE
	SYNTAX		SEQUENCE OF SSystemResourceIrqInfo
	ACCESS		not-accessible
	STATUS		mandatory
	DESCRIPTION	"This group presents additional information about I/O resources
that havebeen defined in the System Resources table."
	::= {dmtfGroups 45}

eSystemResourceIrqInfo OBJECT-TYPE
	SYNTAX		SSystemResourceIrqInfo
	ACCESS		not-accessible
	STATUS		mandatory
	DESCRIPTION	""
	--INDEX		{DmiComponentIndex, a45SystemResourceIrqInfoIndex}
	::= {tSystemResourceIrqInfo 1}

a45SystemResourceIrqInfoIndex OBJECT-TYPE
	SYNTAX		DmiInteger
	ACCESS		read-only
	STATUS		mandatory
	DESCRIPTION	"A number the uniquely identifies rows in this table."
	::= {eSystemResourceIrqInfo 1}

a45TriggerType OBJECT-TYPE
	SYNTAX		INTEGER {
		vOther                                  	(1),
		vUnknown                                	(2),
		vLevel                                  	(3),
		vEdge                                   	(4)
	}
	ACCESS		read-only
	STATUS		mandatory
	DESCRIPTION	"The trigger type for this interrupt."
	::= {eSystemResourceIrqInfo 2}

a45TriggerLevel OBJECT-TYPE
	SYNTAX		INTEGER {
		vOther                                  	(1),
		vUnknown                                	(2),
		vActiveLow                              	(3),
		vActiveHigh                             	(4)
	}
	ACCESS		read-only
	STATUS		mandatory
	DESCRIPTION	"The trigger level for this interrupt."
	::= {eSystemResourceIrqInfo 3}

SSystemResourceDmaInfo ::= SEQUENCE {
	a46SystemResourceDmaInfoIndex           	DmiInteger,
	a46DmaTransferWidth                     	DmiInteger,
	a46DmaAddressSize                       	DmiInteger,
	a46DmaMaximumTransferSize               	DmiInteger,
	a46DmaTransferPreference                	DmiInteger,
	a46BusMaster                            	DmiInteger,
	a46ByteMode                             	DmiInteger,
	a46WordMode                             	DmiInteger,
	a46ChannelTiming                        	DmiInteger,
	a46Type-cTiming                         	DmiInteger
}

tSystemResourceDmaInfo OBJECT-TYPE
	SYNTAX		SEQUENCE OF SSystemResourceDmaInfo
	ACCESS		not-accessible
	STATUS		mandatory
	DESCRIPTION	"This group presents additional information about DMA resources
thathave been defined in the System Resources table."
	::= {dmtfGroups 46}

eSystemResourceDmaInfo OBJECT-TYPE
	SYNTAX		SSystemResourceDmaInfo
	ACCESS		not-accessible
	STATUS		mandatory
	DESCRIPTION	""
	--INDEX		{DmiComponentIndex, a46SystemResourceDmaInfoIndex}
	::= {tSystemResourceDmaInfo 1}

a46SystemResourceDmaInfoIndex OBJECT-TYPE
	SYNTAX		DmiInteger
	ACCESS		read-only
	STATUS		mandatory
	DESCRIPTION	"A number the uniquely identifies rows in this table."
	::= {eSystemResourceDmaInfo 1}

a46DmaTransferWidth OBJECT-TYPE
	SYNTAX		INTEGER {
		vOther                                  	(1),
		vUnknown                                	(2),
		v8-bit                                  	(3),
		v8-And16-bit                            	(4),
		v16-bit                                 	(5),
		v32-bit                                 	(6),
		v64-bit                                 	(7),
		v128-bit                                	(8)
	}
	ACCESS		read-only
	STATUS		mandatory
	DESCRIPTION	"Width of DMA transfers supported"
	::= {eSystemResourceDmaInfo 2}

a46DmaAddressSize OBJECT-TYPE
	SYNTAX		INTEGER {
		vOther                                  	(1),
		vUnknown                                	(2),
		v8-bit                                  	(3),
		v16-bit                                 	(5),
		v32-bit                                 	(6),
		v64-bit                                 	(7)
	}
	ACCESS		read-only
	STATUS		mandatory
	DESCRIPTION	"The width of the DMA address."
	::= {eSystemResourceDmaInfo 3}

a46DmaMaximumTransferSize OBJECT-TYPE
	SYNTAX		DmiInteger
	ACCESS		read-only
	STATUS		mandatory
	DESCRIPTION	"The maximum number of bytes that can be transferred by thisDMA
Channel."
	::= {eSystemResourceDmaInfo 4}

a46DmaTransferPreference OBJECT-TYPE
	SYNTAX		INTEGER {
		vOther                                  	(1),
		vUnknown                                	(2),
		v8-bit                                  	(3),
		v8-And16-bit                            	(4),
		v16-bit                                 	(5),
		v32-bit                                 	(6),
		v64-bit                                 	(7)
	}
	ACCESS		read-only
	STATUS		mandatory
	DESCRIPTION	"DMA transfer type preference."
	::= {eSystemResourceDmaInfo 5}

a46BusMaster OBJECT-TYPE
	SYNTAX		INTEGER {
		vOther                                  	(1),
		vUnknown                                	(2),
		vLogicalDeviceIsNotABusMaster           	(3),
		vLogicalDeviceIsABusMaster              	(4)
	}
	ACCESS		read-only
	STATUS		mandatory
	DESCRIPTION	"Indicates whether the device is using DMA is a bus master."
	::= {eSystemResourceDmaInfo 6}

a46ByteMode OBJECT-TYPE
	SYNTAX		INTEGER {
		vOther                                  	(1),
		vUnknown                                	(2),
		vDmaMayNotExecuteInCountByByteMode      	(3),
		vDmaMayExecuteInCountByByteMode         	(4)
	}
	ACCESS		read-only
	STATUS		mandatory
	DESCRIPTION	"Indicates whether DMA may execute in 'count by byte' mode."
	::= {eSystemResourceDmaInfo 7}

a46WordMode OBJECT-TYPE
	SYNTAX		INTEGER {
		vOther                                  	(1),
		vUnknown                                	(2),
		vDmaMayNotExecuteInCountByWordMode 		   	(3),
		vDmaMayExecuteInCountByWordMode     	  	(4)
	}
	ACCESS		read-only
	STATUS		mandatory
	DESCRIPTION	"Indicates whether DMA may execute in 'count by word' mode."
	::= {eSystemResourceDmaInfo 8}

a46ChannelTiming OBJECT-TYPE
	SYNTAX		INTEGER {
		vOther                                  	(1),
		vUnknown                                	(2),
		vIsaCompatible                          	(3),
		vTypeA                                  	(4),
		vTypeB                                  	(5),
		vTypeF                                  	(6)
	}
	ACCESS		read-only
	STATUS		mandatory
	DESCRIPTION	"DMA channel speed support."
	::= {eSystemResourceDmaInfo 9}

a46Type-cTiming OBJECT-TYPE
	SYNTAX		INTEGER {
		vOther                                  	(1),
		vUnknown                                	(2),
		vIsaCompatible                          	(3),
		vCTypeTimingIsNotSupported              	(4),
		vCTypeTimingIsSupported                 	(5)
	}
	ACCESS		read-only
	STATUS		mandatory
	DESCRIPTION	"Indicates whether C type (burst) timing is supported."
	::= {eSystemResourceDmaInfo 10}

SMiftomib ::= SEQUENCE {
	a1001MibName                            	DmiDisplaystring,
	a1001MibOid                             	DmiDisplaystring,
	a1001DisableTrap                        	DmiInteger
}

tMiftomib OBJECT-TYPE
	SYNTAX		SEQUENCE OF SMiftomib
	ACCESS		not-accessible
	STATUS		mandatory
	DESCRIPTION	"This group defines attributes required for DMI to
SNMP translati
n."
	::= {dmtfGroups 1001}

eMiftomib OBJECT-TYPE
	SYNTAX		SMiftomib
	ACCESS		not-accessible
	STATUS		mandatory
	DESCRIPTION	""
	--INDEX		{DmiComponentIndex}
	::= {tMiftomib 1}

a1001MibName OBJECT-TYPE
	SYNTAX		DmiDisplaystring
	ACCESS		read-only
	STATUS		mandatory
	DESCRIPTION	"The MIB name that defines this MIF"
	::= {eMiftomib 1}

a1001MibOid OBJECT-TYPE
	SYNTAX		DmiDisplaystring
	ACCESS		read-only
	STATUS		mandatory
	DESCRIPTION	"The MIB Object Identifier that corresponds to this MIF"
	::= {eMiftomib 2}

a1001DisableTrap OBJECT-TYPE
	SYNTAX		DmiInteger
	ACCESS		read-write
	STATUS		mandatory
	DESCRIPTION	"This attribute can be changed to disable sending oftraps
from this component"
	::= {eMiftomib 3}

END
