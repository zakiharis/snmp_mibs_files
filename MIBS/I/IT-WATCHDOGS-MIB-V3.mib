IT-WATCHDOGS-MIB-V3 DEFINITIONS ::= BEGIN

IMPORTS 


DisplayString                                                   FROM SNMPv2-TC
MODULE-IDENTITY, OBJECT-TYPE, enterprises, Gauge32,
Integer32, NOTIFICATION-TYPE FROM                               SNMPv2-SMI;

itwatchdogs MODULE-IDENTITY
	LAST-UPDATED "201306190000Z"
	ORGANIZATION "I.T. Watchdogs"
	CONTACT-INFO "support@itwatchdogs.com"
	DESCRIPTION "The MIB for I.T. Watchdogs Products"
	::= { enterprises 17373 }

itwatchdogs OBJECT IDENTIFIER
	::= { enterprises 17373 }
	
owl OBJECT IDENTIFIER
	::= { itwatchdogs 3 }
deviceInfo OBJECT IDENTIFIER
	::= { owl 1 }

productTitle OBJECT-TYPE
	SYNTAX DisplayString
	MAX-ACCESS read-only
	STATUS current
	DESCRIPTION "Product name"
	::= { deviceInfo 1 }

productVersion OBJECT-TYPE
	SYNTAX DisplayString
	MAX-ACCESS read-only
	STATUS current
	DESCRIPTION "Product version"
	::= { deviceInfo 2 }

productFriendlyName OBJECT-TYPE
	SYNTAX DisplayString
	MAX-ACCESS read-only
	STATUS current
	DESCRIPTION "User-assigned name"
	::= { deviceInfo 3 }

productMacAddress OBJECT-TYPE
	SYNTAX DisplayString
	MAX-ACCESS read-only
	STATUS current
	DESCRIPTION "Product's unique MAC address"
	::= { deviceInfo 4 }

productUrl OBJECT-TYPE
	SYNTAX DisplayString
	MAX-ACCESS read-only
	STATUS current
	DESCRIPTION "Product's main URL access point"
	::= { deviceInfo 5 }

alarmTripType OBJECT-TYPE
        SYNTAX INTEGER { none(0), low(1), high(2), unplugged(3) }
        MAX-ACCESS read-only
        STATUS current
        DESCRIPTION "Type of alarm trip. 0 = None, 1 = Low, 2 = High, 3 = Unplugged"
        ::= { deviceInfo 6 }

productHardware OBJECT-TYPE
        SYNTAX DisplayString
        MAX-ACCESS read-only
        STATUS current
        DESCRIPTION "Product's hardware type"
        ::= { deviceInfo 7 }
       
temperaturePrecision OBJECT-TYPE
        SYNTAX INTEGER { degree(0), deciDegree(1) }
        MAX-ACCESS read-write
        STATUS current
        DESCRIPTION 
		"Temperature Precision:
		    0 = degree: whole degree (value X 1) 
		    1 = deci-degree: tenths of a degree (value X 10)
		        ex. 550 = 55.0 degrees
		"
        ::= { deviceInfo 9 }

alarmTrigger OBJECT-TYPE
        SYNTAX DisplayString
        MAX-ACCESS accessible-for-notify
        STATUS current
        DESCRIPTION 
        	"Used in a trap var-bind to indicate what triggered 
        	the alarm. The alarmTrigger will remain consistent 
        	for both trip and clear traps. Possible values include:
        	
        	    'Low' = Low-trip trigger
        	    'High' = High-trip trigger
        	    'Unplugged' = Unplugged device trigger
        	"
        ::= { deviceInfo 11 }

alarmInstance OBJECT-TYPE
        SYNTAX INTEGER(1..200)
        MAX-ACCESS accessible-for-notify
        STATUS current
        DESCRIPTION 
        	"Provides the row index (instance number) for the alarm
        	that generated a trap. This value is only available when
        	included in the var-binds of an associated trap. "
        ::= { deviceInfo 12 }
        
        
sensorCountsBase OBJECT IDENTIFIER
	::= { deviceInfo 8 }
	
sensorCounts OBJECT IDENTIFIER
	::= { sensorCountsBase 1 }

	
climateCount OBJECT-TYPE
        SYNTAX INTEGER(0..16)
        MAX-ACCESS read-only
        STATUS current
        DESCRIPTION "Number of climate monitors currently plugged in"
        ::= { sensorCounts 2 }
		
powerMonitorCount OBJECT-TYPE
        SYNTAX INTEGER(0..16)
        MAX-ACCESS read-only
        STATUS current
        DESCRIPTION "Number of power monitors currently plugged in"
        ::= { sensorCounts 3 }
		
tempSensorCount OBJECT-TYPE
        SYNTAX INTEGER(0..16)
        MAX-ACCESS read-only
        STATUS current
        DESCRIPTION "Number of temperature sensors currently plugged in"
        ::= { sensorCounts 4 }
		
airflowSensorCount OBJECT-TYPE
        SYNTAX INTEGER(0..16)
        MAX-ACCESS read-only
        STATUS current
        DESCRIPTION "Number of airflow sensors currently plugged in"
        ::= { sensorCounts 5 }
		
ctrl3ChDELTACount OBJECT-TYPE
        SYNTAX INTEGER(0..16)
        MAX-ACCESS read-only
        STATUS current
        DESCRIPTION "Number of DELTA 3 channel controllers currently plugged in"
        ::= { sensorCounts 6 }
		
doorSensorCount OBJECT-TYPE
        SYNTAX INTEGER(0..16)
        MAX-ACCESS read-only
        STATUS current
        DESCRIPTION "Number of door sensors currently plugged in"
        ::= { sensorCounts 7 }
		
waterSensorCount OBJECT-TYPE
        SYNTAX INTEGER(0..16)
        MAX-ACCESS read-only
        STATUS current
        DESCRIPTION "Number of water sensors currently plugged in"
        ::= { sensorCounts 8 }
		
currentSensorCount OBJECT-TYPE
        SYNTAX INTEGER(0..16)
        MAX-ACCESS read-only
        STATUS current
        DESCRIPTION "Number of current sensors currently plugged in"
        ::= { sensorCounts 9 }
		
millivoltSensorCount OBJECT-TYPE
        SYNTAX INTEGER(0..16)
        MAX-ACCESS read-only
        STATUS current
        DESCRIPTION "Number of millivolt sensors currently plugged in"
        ::= { sensorCounts 10 }
		
power3ChSensorCount OBJECT-TYPE
        SYNTAX INTEGER(0..16)
        MAX-ACCESS read-only
        STATUS current
        DESCRIPTION "Number of 3 channel power monitors currently plugged in"
        ::= { sensorCounts 11 }
		
outletCount OBJECT-TYPE
        SYNTAX INTEGER(0..16)
        MAX-ACCESS read-only
        STATUS current
        DESCRIPTION "Number of outlets currently plugged in"
        ::= { sensorCounts 12 }
		
vsfcCount OBJECT-TYPE
        SYNTAX INTEGER(0..16)
        MAX-ACCESS read-only
        STATUS current
        DESCRIPTION "Number of fan controller monitors currently plugged in"
        ::= { sensorCounts 13 }
		
ctrl3ChCount OBJECT-TYPE
        SYNTAX INTEGER(0..16)
        MAX-ACCESS read-only
        STATUS current
        DESCRIPTION "Number of 3 channel controllers currently plugged in"
        ::= { sensorCounts 14 }
		
ctrlGrpAmpsCount OBJECT-TYPE
        SYNTAX INTEGER(0..16)
        MAX-ACCESS read-only
        STATUS current
        DESCRIPTION "Number of amperage controllers currently plugged in"
        ::= { sensorCounts 15 }
		
ctrlOutletCount OBJECT-TYPE
        SYNTAX INTEGER(0..16)
        MAX-ACCESS read-only
        STATUS current
        DESCRIPTION "Number of monitored or switched outlets"
        ::= { sensorCounts 16 }
		
dewpointSensorCount OBJECT-TYPE
        SYNTAX INTEGER(0..16)
        MAX-ACCESS read-only
        STATUS current
        DESCRIPTION "Number of dewpoint sensors currently plugged in"
        ::= { sensorCounts 17 }
		
digitalSensorCount OBJECT-TYPE
        SYNTAX INTEGER(0..16)
        MAX-ACCESS read-only
        STATUS current
        DESCRIPTION "Number of digital sensors currently plugged in"
        ::= { sensorCounts 18 }
		
dstsSensorCount OBJECT-TYPE
        SYNTAX INTEGER(0..16)
        MAX-ACCESS read-only
        STATUS current
        DESCRIPTION "Number of DSTS controllers currently plugged in"
        ::= { sensorCounts 19 }
		
cpmSensorCount OBJECT-TYPE
        SYNTAX INTEGER(0..16)
        MAX-ACCESS read-only
        STATUS current
        DESCRIPTION "Number of city power sensors currently plugged in"
        ::= { sensorCounts 20 }
		
smokeAlarmSensorCount OBJECT-TYPE
        SYNTAX INTEGER(0..16)
        MAX-ACCESS read-only
        STATUS current
        DESCRIPTION "Number of smoke alarm sensors currently plugged in"
        ::= { sensorCounts 21 }
		
neg48VdcSensorCount OBJECT-TYPE
        SYNTAX INTEGER(0..16)
        MAX-ACCESS read-only
        STATUS current
        DESCRIPTION "Number of -48Vdc sensors currently plugged in"
        ::= { sensorCounts 22 }
		
pos30VdcSensorCount OBJECT-TYPE
        SYNTAX INTEGER(0..16)
        MAX-ACCESS read-only
        STATUS current
        DESCRIPTION "Number of 30Vdc sensors currently plugged in"
        ::= { sensorCounts 23 }
		
analogSensorCount OBJECT-TYPE
        SYNTAX INTEGER(0..16)
        MAX-ACCESS read-only
        STATUS current
        DESCRIPTION "Number of remote analog inputs currently plugged in"
        ::= { sensorCounts 24 }
		
ctrl3ChIECCount OBJECT-TYPE
        SYNTAX INTEGER(0..16)
        MAX-ACCESS read-only
        STATUS current
        DESCRIPTION "Number of IEC 3 channel controllers currently plugged in"
        ::= { sensorCounts 25 }
		
climateRelayCount OBJECT-TYPE
        SYNTAX INTEGER(0..16)
        MAX-ACCESS read-only
        STATUS current
        DESCRIPTION "Number of climate relay monitors currently plugged in"
        ::= { sensorCounts 26 }
		
ctrlRelayCount OBJECT-TYPE
        SYNTAX INTEGER(0..16)
        MAX-ACCESS read-only
        STATUS current
        DESCRIPTION "Number of relay controllers currently plugged in"
        ::= { sensorCounts 27 }
		
airSpeedSwitchSensorCount OBJECT-TYPE
        SYNTAX INTEGER(0..16)
        MAX-ACCESS read-only
        STATUS current
        DESCRIPTION "Number of air speed switch sensors currently plugged in"
        ::= { sensorCounts 28 }
		
powerDMCount OBJECT-TYPE
        SYNTAX INTEGER(0..16)
        MAX-ACCESS read-only
        STATUS current
        DESCRIPTION "Number of DM48 current sensors currently plugged in"
        ::= { sensorCounts 29 }
		
ioExpanderCount OBJECT-TYPE
        SYNTAX INTEGER(0..16)
        MAX-ACCESS read-only
        STATUS current
        DESCRIPTION "Number of IO expander devices currently plugged in"
        ::= { sensorCounts 30 }
		
t3hdSensorCount OBJECT-TYPE
        SYNTAX INTEGER(0..16)
        MAX-ACCESS read-only
        STATUS current
        DESCRIPTION "Number of T3HD sensors currently plugged in"
        ::= { sensorCounts 31 }
		
thdSensorCount OBJECT-TYPE
        SYNTAX INTEGER(0..16)
        MAX-ACCESS read-only
        STATUS current
        DESCRIPTION "Number of THD sensors currently plugged in"
        ::= { sensorCounts 32 }
		
pos60VdcSensorCount OBJECT-TYPE
        SYNTAX INTEGER(0..16)
        MAX-ACCESS read-only
        STATUS current
        DESCRIPTION "Number of 60Vdc sensors currently plugged in"
        ::= { sensorCounts 33 }
		
ctrl2CirTotCount OBJECT-TYPE
        SYNTAX INTEGER(0..16)
        MAX-ACCESS read-only
        STATUS current
        DESCRIPTION "Number of IEC 3 channel controllers currently plugged in"
        ::= { sensorCounts 34 }
		
sc10Count OBJECT-TYPE
        SYNTAX INTEGER(0..16)
        MAX-ACCESS read-only
        STATUS current
        DESCRIPTION "Number of fan controller monitors currently plugged in"
        ::= { sensorCounts 35 }
		
climateTable OBJECT-TYPE
	SYNTAX SEQUENCE OF ClimateEntry
	MAX-ACCESS  not-accessible
	STATUS current
	DESCRIPTION "Climate sensors (internal sensors for climate units)"
	::= { owl 2 }

powMonTable OBJECT-TYPE
	SYNTAX SEQUENCE OF PowMonEntry
	MAX-ACCESS  not-accessible
	STATUS current
	DESCRIPTION "A table of Power Monitors"
	::= { owl 3 }

tempSensorTable OBJECT-TYPE
	SYNTAX SEQUENCE OF TempSensorEntry
	MAX-ACCESS  not-accessible
	STATUS current
	DESCRIPTION "A table of temperature sensors"
	::= { owl 4 }

airFlowSensorTable OBJECT-TYPE
	SYNTAX SEQUENCE OF AirFlowSensorEntry
	MAX-ACCESS  not-accessible
	STATUS current
	DESCRIPTION "A table of airflow sensors"
	::= { owl 5 }

ctrl3ChDELTATable OBJECT-TYPE
	SYNTAX SEQUENCE OF Ctrl3ChDELTAEntry
	MAX-ACCESS  not-accessible
	STATUS current
	DESCRIPTION "A table of a 3 phase outlet control (DELTA)"
	::= { owl 6 }

doorSensorTable OBJECT-TYPE
	SYNTAX SEQUENCE OF DoorSensorEntry
	MAX-ACCESS  not-accessible
	STATUS current
	DESCRIPTION "A table of door sensors"
	::= { owl 7 }

waterSensorTable OBJECT-TYPE
	SYNTAX SEQUENCE OF WaterSensorEntry
	MAX-ACCESS  not-accessible
	STATUS current
	DESCRIPTION "A table of water sensors"
	::= { owl 8 }

currentMonitorTable OBJECT-TYPE
	SYNTAX SEQUENCE OF CurrentMonitorEntry
	MAX-ACCESS  not-accessible
	STATUS current
	DESCRIPTION "A table of current monitors"
	::= { owl 9 }

millivoltMonitorTable OBJECT-TYPE
	SYNTAX SEQUENCE OF MillivoltMonitorEntry
	MAX-ACCESS  not-accessible
	STATUS current
	DESCRIPTION "A table of millivolt monitors"
	::= { owl 10 }

pow3ChTable OBJECT-TYPE
	SYNTAX SEQUENCE OF Pow3ChEntry
	MAX-ACCESS  not-accessible
	STATUS current
	DESCRIPTION "A table of Power Monitor 3 Channel"
	::= { owl 11 }

outletTable OBJECT-TYPE
	SYNTAX SEQUENCE OF OutletEntry
	MAX-ACCESS  not-accessible
	STATUS current
	DESCRIPTION "A table of outlets"
	::= { owl 12 }

vsfcTable OBJECT-TYPE
	SYNTAX SEQUENCE OF VsfcEntry
	MAX-ACCESS  not-accessible
	STATUS current
	DESCRIPTION "VSFC sensors (internal sensors for VSFC units)"
	::= { owl 13 }

ctrl3ChTable OBJECT-TYPE
	SYNTAX SEQUENCE OF Ctrl3ChEntry
	MAX-ACCESS  not-accessible
	STATUS current
	DESCRIPTION "A table of a 3 phase outlet control"
	::= { owl 14 }

ctrlGrpAmpsTable OBJECT-TYPE
	SYNTAX SEQUENCE OF CtrlGrpAmpsEntry
	MAX-ACCESS  not-accessible
	STATUS current
	DESCRIPTION "A table of Control Group Amp readings"
	::= { owl 15 }

ctrlOutletTable OBJECT-TYPE
	SYNTAX SEQUENCE OF CtrlOutletEntry
	MAX-ACCESS  not-accessible
	STATUS current
	DESCRIPTION "A table of outlet information"
	::= { owl 16 }

dewPointSensorTable OBJECT-TYPE
	SYNTAX SEQUENCE OF DewPointSensorEntry
	MAX-ACCESS  not-accessible
	STATUS current
	DESCRIPTION "A table of dew point sensors"
	::= { owl 17 }

digitalSensorTable OBJECT-TYPE
	SYNTAX SEQUENCE OF DigitalSensorEntry
	MAX-ACCESS  not-accessible
	STATUS current
	DESCRIPTION "A table of digital sensors"
	::= { owl 18 }

dstsTable OBJECT-TYPE
	SYNTAX SEQUENCE OF DstsEntry
	MAX-ACCESS  not-accessible
	STATUS current
	DESCRIPTION "Digital Static Transfer Switch status"
	::= { owl 19 }

cpmSensorTable OBJECT-TYPE
	SYNTAX SEQUENCE OF CpmSensorEntry
	MAX-ACCESS  not-accessible
	STATUS current
	DESCRIPTION "A table of city power sensors"
	::= { owl 20 }

smokeAlarmTable OBJECT-TYPE
	SYNTAX SEQUENCE OF SmokeAlarmEntry
	MAX-ACCESS  not-accessible
	STATUS current
	DESCRIPTION "A table of smoke alarm sensors"
	::= { owl 21 }

neg48VdcSensorTable OBJECT-TYPE
	SYNTAX SEQUENCE OF Neg48VdcSensorEntry
	MAX-ACCESS  not-accessible
	STATUS current
	DESCRIPTION "A table of -48Vdc sensors"
	::= { owl 22 }

pos30VdcSensorTable OBJECT-TYPE
	SYNTAX SEQUENCE OF Pos30VdcSensorEntry
	MAX-ACCESS  not-accessible
	STATUS current
	DESCRIPTION "A table of 30Vdc sensors"
	::= { owl 23 }

analogSensorTable OBJECT-TYPE
	SYNTAX SEQUENCE OF AnalogSensorEntry
	MAX-ACCESS  not-accessible
	STATUS current
	DESCRIPTION "A table of analog sensors"
	::= { owl 24 }

ctrl3ChIECTable OBJECT-TYPE
	SYNTAX SEQUENCE OF Ctrl3ChIECEntry
	MAX-ACCESS  not-accessible
	STATUS current
	DESCRIPTION "A table of a 3 phase outlet control (IEC)"
	::= { owl 25 }

climateRelayTable OBJECT-TYPE
	SYNTAX SEQUENCE OF ClimateRelayEntry
	MAX-ACCESS  not-accessible
	STATUS current
	DESCRIPTION "Climate Relay sensors (internal sensors for climate relay units)"
	::= { owl 26 }

ctrlRelayTable OBJECT-TYPE
	SYNTAX SEQUENCE OF CtrlRelayEntry
	MAX-ACCESS  not-accessible
	STATUS current
	DESCRIPTION "A table of relay information"
	::= { owl 27 }

airSpeedSwitchSensorTable OBJECT-TYPE
	SYNTAX SEQUENCE OF AirSpeedSwitchSensorEntry
	MAX-ACCESS  not-accessible
	STATUS current
	DESCRIPTION "A table of air speed switch sensors"
	::= { owl 28 }

powerDMTable OBJECT-TYPE
	SYNTAX SEQUENCE OF PowerDMEntry
	MAX-ACCESS  not-accessible
	STATUS current
	DESCRIPTION "A table of DM48 current monitors"
	::= { owl 29 }

ioExpanderTable OBJECT-TYPE
	SYNTAX SEQUENCE OF IoExpanderEntry
	MAX-ACCESS  not-accessible
	STATUS current
	DESCRIPTION "IO Expander device with relay capability"
	::= { owl 30 }

t3hdSensorTable OBJECT-TYPE
	SYNTAX SEQUENCE OF T3hdSensorEntry
	MAX-ACCESS  not-accessible
	STATUS current
	DESCRIPTION "A table of T3HD sensors"
	::= { owl 31 }

thdSensorTable OBJECT-TYPE
	SYNTAX SEQUENCE OF ThdSensorEntry
	MAX-ACCESS  not-accessible
	STATUS current
	DESCRIPTION "A table of THD sensors"
	::= { owl 32 }

pos60VdcSensorTable OBJECT-TYPE
	SYNTAX SEQUENCE OF Pos60VdcSensorEntry
	MAX-ACCESS  not-accessible
	STATUS current
	DESCRIPTION "A table of 60Vdc sensors"
	::= { owl 33 }

ctrl2CirTotTable OBJECT-TYPE
	SYNTAX SEQUENCE OF Ctrl2CirTotEntry
	MAX-ACCESS  not-accessible
	STATUS current
	DESCRIPTION "A table of a 3 phase outlet control (IEC)"
	::= { owl 34 }

sc10Table OBJECT-TYPE
	SYNTAX SEQUENCE OF Sc10Entry
	MAX-ACCESS  not-accessible
	STATUS current
	DESCRIPTION "SC10 sensors (internal measurements for SC10 units)"
	::= { owl 35 }

climateEntry OBJECT-TYPE
	SYNTAX  ClimateEntry
	MAX-ACCESS  not-accessible
	STATUS current
	DESCRIPTION 
		"Entry in the climate table: each entry contains
an index (climateIndex) and other details"
	INDEX { climateIndex }
	::= { climateTable 1 }

ClimateEntry ::= SEQUENCE {
	climateIndex		INTEGER,
	climateSerial		DisplayString,
	climateName		DisplayString,
	climateAvail		Gauge32,
	climateTempC		INTEGER,
	climateTempF		INTEGER,
	climateHumidity		INTEGER,
	climateLight		INTEGER,
	climateAirflow		INTEGER,
	climateSound		INTEGER,
	climateIO1		INTEGER,
	climateIO2		INTEGER,
	climateIO3		INTEGER,
	climateDewPointC		INTEGER,
	climateDewPointF		INTEGER
}

climateIndex OBJECT-TYPE
	SYNTAX  INTEGER(1..1)
	MAX-ACCESS  not-accessible
	STATUS current
	DESCRIPTION "Table entry index value"
	::= { climateEntry  1 }
	
climateSerial OBJECT-TYPE
	SYNTAX  DisplayString
	MAX-ACCESS  read-only
	STATUS current
	DESCRIPTION "Serial Number"
	::= { climateEntry  2 }
	
climateName OBJECT-TYPE
	SYNTAX  DisplayString
	MAX-ACCESS  read-only
	STATUS current
	DESCRIPTION "Friendly Name"
	::= { climateEntry  3 }
	
climateAvail OBJECT-TYPE
	SYNTAX  Gauge32
	MAX-ACCESS  read-only
	STATUS current
	DESCRIPTION "Is device currently plugged in?"
	::= { climateEntry  4 }
	
climateTempC OBJECT-TYPE
	SYNTAX  INTEGER(-50..100)
	UNITS "Degrees Celsius"
	MAX-ACCESS  read-only
	STATUS current
	DESCRIPTION "Current reading for Temperature (C)"
	::= { climateEntry  5 }
	
climateTempF OBJECT-TYPE
	SYNTAX  INTEGER(-58..212)
	UNITS "Degress Fahrenheit"
	MAX-ACCESS  read-only
	STATUS current
	DESCRIPTION "Current reading for Temperature (F)"
	::= { climateEntry  6 }
	
climateHumidity OBJECT-TYPE
	SYNTAX  INTEGER(0..100)
	UNITS "%"
	MAX-ACCESS  read-only
	STATUS current
	DESCRIPTION "Current reading for Humidity"
	::= { climateEntry  7 }
	
climateLight OBJECT-TYPE
	SYNTAX  INTEGER(0..100)
	MAX-ACCESS  read-only
	STATUS current
	DESCRIPTION "Current reading for Ambient Light"
	::= { climateEntry  8 }
	
climateAirflow OBJECT-TYPE
	SYNTAX  INTEGER(0..100)
	MAX-ACCESS  read-only
	STATUS current
	DESCRIPTION "Current reading for Airflow"
	::= { climateEntry  9 }
	
climateSound OBJECT-TYPE
	SYNTAX  INTEGER(0..100)
	MAX-ACCESS  read-only
	STATUS current
	DESCRIPTION "Current reading for Sound"
	::= { climateEntry  10 }
	
climateIO1 OBJECT-TYPE
	SYNTAX  INTEGER(0..100)
	MAX-ACCESS  read-only
	STATUS current
	DESCRIPTION "Current reading for Analog Input 1"
	::= { climateEntry  11 }
	
climateIO2 OBJECT-TYPE
	SYNTAX  INTEGER(0..100)
	MAX-ACCESS  read-only
	STATUS current
	DESCRIPTION "Current reading for Analog Input 2"
	::= { climateEntry  12 }
	
climateIO3 OBJECT-TYPE
	SYNTAX  INTEGER(0..100)
	MAX-ACCESS  read-only
	STATUS current
	DESCRIPTION "Current reading for Analog Input 3"
	::= { climateEntry  13 }
	
climateDewPointC OBJECT-TYPE
	SYNTAX  INTEGER(-50..100)
	UNITS "Degrees Celsius"
	MAX-ACCESS  read-only
	STATUS current
	DESCRIPTION "Current reading for Dew Point (C)"
	::= { climateEntry  14 }
	
climateDewPointF OBJECT-TYPE
	SYNTAX  INTEGER(-58..212)
	UNITS "Degress Fahrenheit"
	MAX-ACCESS  read-only
	STATUS current
	DESCRIPTION "Current reading for Dew Point (F)"
	::= { climateEntry  15 }
	
powMonEntry OBJECT-TYPE
	SYNTAX  PowMonEntry
	MAX-ACCESS  not-accessible
	STATUS current
	DESCRIPTION 
		"Entry in the power monitor table: each entry contains
an index (powMonIndex) and other power monitoring details"
	INDEX { powMonIndex }
	::= { powMonTable 1 }

PowMonEntry ::= SEQUENCE {
	powMonIndex		INTEGER,
	powMonSerial		DisplayString,
	powMonName		DisplayString,
	powMonAvail		Gauge32,
	powMonkWattHrs		Gauge32,
	powMonVolts		Gauge32,
	powMonVoltMax		Gauge32,
	powMonVoltMin		Gauge32,
	powMonVoltPeak		Gauge32,
	powMonDeciAmps		Gauge32,
	powMonRealPower		Gauge32,
	powMonApparentPower		Gauge32,
	powMonPowerFactor		INTEGER,
	powMonOutlet1		INTEGER,
	powMonOutlet2		INTEGER,
	powMonOutlet1StatusTime		Gauge32,
	powMonOutlet2StatusTime		Gauge32
}

powMonIndex OBJECT-TYPE
	SYNTAX  INTEGER(1..100)
	MAX-ACCESS  not-accessible
	STATUS current
	DESCRIPTION "Table entry index value"
	::= { powMonEntry  1 }
	
powMonSerial OBJECT-TYPE
	SYNTAX  DisplayString
	MAX-ACCESS  read-only
	STATUS current
	DESCRIPTION "Serial Number"
	::= { powMonEntry  2 }
	
powMonName OBJECT-TYPE
	SYNTAX  DisplayString
	MAX-ACCESS  read-only
	STATUS current
	DESCRIPTION "Friendly Name"
	::= { powMonEntry  3 }
	
powMonAvail OBJECT-TYPE
	SYNTAX  Gauge32
	MAX-ACCESS  read-only
	STATUS current
	DESCRIPTION "Is device currently plugged in?"
	::= { powMonEntry  4 }
	
powMonkWattHrs OBJECT-TYPE
	SYNTAX  Gauge32
	UNITS "kWh"
	MAX-ACCESS  read-only
	STATUS current
	DESCRIPTION "Current reading for kWatt-Hours"
	::= { powMonEntry  5 }
	
powMonVolts OBJECT-TYPE
	SYNTAX  Gauge32
	UNITS "Volts (rms)"
	MAX-ACCESS  read-only
	STATUS current
	DESCRIPTION "Current reading for Volts"
	::= { powMonEntry  6 }
	
powMonVoltMax OBJECT-TYPE
	SYNTAX  Gauge32
	UNITS "Volts (rms)"
	MAX-ACCESS  read-only
	STATUS current
	DESCRIPTION "Current reading for Volts (Max)"
	::= { powMonEntry  7 }
	
powMonVoltMin OBJECT-TYPE
	SYNTAX  Gauge32
	UNITS "Volts (rms)"
	MAX-ACCESS  read-only
	STATUS current
	DESCRIPTION "Current reading for Volts (Min)"
	::= { powMonEntry  8 }
	
powMonVoltPeak OBJECT-TYPE
	SYNTAX  Gauge32
	UNITS "Volts (rms)"
	MAX-ACCESS  read-only
	STATUS current
	DESCRIPTION "Current reading for Volts (Peak)"
	::= { powMonEntry  9 }
	
powMonDeciAmps OBJECT-TYPE
	SYNTAX  Gauge32
	UNITS "0.1 Amps (rms)"
	MAX-ACCESS  read-only
	STATUS current
	DESCRIPTION "Current reading for DeciAmps"
	::= { powMonEntry  10 }
	
powMonRealPower OBJECT-TYPE
	SYNTAX  Gauge32
	UNITS "Watts"
	MAX-ACCESS  read-only
	STATUS current
	DESCRIPTION "Current reading for Real Power"
	::= { powMonEntry  11 }
	
powMonApparentPower OBJECT-TYPE
	SYNTAX  Gauge32
	UNITS "Volt-Amps"
	MAX-ACCESS  read-only
	STATUS current
	DESCRIPTION "Current reading for Apparent Power"
	::= { powMonEntry  12 }
	
powMonPowerFactor OBJECT-TYPE
	SYNTAX  INTEGER(0..100)
	UNITS "%"
	MAX-ACCESS  read-only
	STATUS current
	DESCRIPTION "Current reading for Power Factor"
	::= { powMonEntry  13 }
	
powMonOutlet1 OBJECT-TYPE
	SYNTAX  INTEGER(0..100)
	UNITS "Outlet 1"
	MAX-ACCESS  read-only
	STATUS current
	DESCRIPTION "Outlet 1 Trap"
	::= { powMonEntry  14 }
	
powMonOutlet2 OBJECT-TYPE
	SYNTAX  INTEGER(0..100)
	UNITS "Outlet 2"
	MAX-ACCESS  read-only
	STATUS current
	DESCRIPTION "Outlet 2 Trap"
	::= { powMonEntry  15 }
	
powMonOutlet1StatusTime OBJECT-TYPE
	SYNTAX  Gauge32
	UNITS "seconds"
	MAX-ACCESS  read-only
	STATUS current
	DESCRIPTION "Seconds Since Outlet 1 Last Changed Its Status"
	::= { powMonEntry  16 }
	
powMonOutlet2StatusTime OBJECT-TYPE
	SYNTAX  Gauge32
	UNITS "seconds"
	MAX-ACCESS  read-only
	STATUS current
	DESCRIPTION "Seconds Since Outlet 2 Last Changed Its Status"
	::= { powMonEntry  17 }
	
tempSensorEntry OBJECT-TYPE
	SYNTAX  TempSensorEntry
	MAX-ACCESS  not-accessible
	STATUS current
	DESCRIPTION 
		"Entry in the temperature sensor table: each entry contains
an index (tempIndex) and other sensor details"
	INDEX { tempSensorIndex }
	::= { tempSensorTable 1 }

TempSensorEntry ::= SEQUENCE {
	tempSensorIndex		INTEGER,
	tempSensorSerial		DisplayString,
	tempSensorName		DisplayString,
	tempSensorAvail		Gauge32,
	tempSensorTempC		INTEGER,
	tempSensorTempF		INTEGER
}

tempSensorIndex OBJECT-TYPE
	SYNTAX  INTEGER(1..100)
	MAX-ACCESS  not-accessible
	STATUS current
	DESCRIPTION "Table entry index value"
	::= { tempSensorEntry  1 }
	
tempSensorSerial OBJECT-TYPE
	SYNTAX  DisplayString
	MAX-ACCESS  read-only
	STATUS current
	DESCRIPTION "Serial Number"
	::= { tempSensorEntry  2 }
	
tempSensorName OBJECT-TYPE
	SYNTAX  DisplayString
	MAX-ACCESS  read-only
	STATUS current
	DESCRIPTION "Friendly Name"
	::= { tempSensorEntry  3 }
	
tempSensorAvail OBJECT-TYPE
	SYNTAX  Gauge32
	MAX-ACCESS  read-only
	STATUS current
	DESCRIPTION "Is device currently plugged in?"
	::= { tempSensorEntry  4 }
	
tempSensorTempC OBJECT-TYPE
	SYNTAX  INTEGER(-50..100)
	UNITS "Degrees Celsius"
	MAX-ACCESS  read-only
	STATUS current
	DESCRIPTION "Temperature in Celsius"
	::= { tempSensorEntry  5 }
	
tempSensorTempF OBJECT-TYPE
	SYNTAX  INTEGER(-58..212)
	UNITS "Degrees Fahrenheit"
	MAX-ACCESS  read-only
	STATUS current
	DESCRIPTION "Temperature in Fahrenheit"
	::= { tempSensorEntry  6 }
	
airFlowSensorEntry OBJECT-TYPE
	SYNTAX  AirFlowSensorEntry
	MAX-ACCESS  not-accessible
	STATUS current
	DESCRIPTION 
		"Entry in the air flow sensor table: each entry contains
an index (airFlowSensorIndex) and other sensor details"
	INDEX { airFlowSensorIndex }
	::= { airFlowSensorTable 1 }

AirFlowSensorEntry ::= SEQUENCE {
	airFlowSensorIndex		INTEGER,
	airFlowSensorSerial		DisplayString,
	airFlowSensorName		DisplayString,
	airFlowSensorAvail		Gauge32,
	airFlowSensorTempC		INTEGER,
	airFlowSensorTempF		INTEGER,
	airFlowSensorFlow		INTEGER,
	airFlowSensorHumidity		INTEGER,
	airFlowSensorDewPointC		INTEGER,
	airFlowSensorDewPointF		INTEGER
}

airFlowSensorIndex OBJECT-TYPE
	SYNTAX  INTEGER(1..100)
	MAX-ACCESS  not-accessible
	STATUS current
	DESCRIPTION "Table entry index value"
	::= { airFlowSensorEntry  1 }
	
airFlowSensorSerial OBJECT-TYPE
	SYNTAX  DisplayString
	MAX-ACCESS  read-only
	STATUS current
	DESCRIPTION "Serial Number"
	::= { airFlowSensorEntry  2 }
	
airFlowSensorName OBJECT-TYPE
	SYNTAX  DisplayString
	MAX-ACCESS  read-only
	STATUS current
	DESCRIPTION "Friendly Name"
	::= { airFlowSensorEntry  3 }
	
airFlowSensorAvail OBJECT-TYPE
	SYNTAX  Gauge32
	MAX-ACCESS  read-only
	STATUS current
	DESCRIPTION "Is device currently plugged in?"
	::= { airFlowSensorEntry  4 }
	
airFlowSensorTempC OBJECT-TYPE
	SYNTAX  INTEGER(-50..100)
	UNITS "Degrees Celsius"
	MAX-ACCESS  read-only
	STATUS current
	DESCRIPTION "Temperature reading in C"
	::= { airFlowSensorEntry  5 }
	
airFlowSensorTempF OBJECT-TYPE
	SYNTAX  INTEGER(-58..212)
	UNITS "Degrees Fahrenheit"
	MAX-ACCESS  read-only
	STATUS current
	DESCRIPTION "Temperature reading in F"
	::= { airFlowSensorEntry  6 }
	
airFlowSensorFlow OBJECT-TYPE
	SYNTAX  INTEGER(0..100)
	MAX-ACCESS  read-only
	STATUS current
	DESCRIPTION "Air flow reading"
	::= { airFlowSensorEntry  7 }
	
airFlowSensorHumidity OBJECT-TYPE
	SYNTAX  INTEGER(0..100)
	UNITS "%"
	MAX-ACCESS  read-only
	STATUS current
	DESCRIPTION "Humidity reading"
	::= { airFlowSensorEntry  8 }
	
airFlowSensorDewPointC OBJECT-TYPE
	SYNTAX  INTEGER(-50..100)
	UNITS "Degrees Celsius"
	MAX-ACCESS  read-only
	STATUS current
	DESCRIPTION "Current reading for Dew Point (C)"
	::= { airFlowSensorEntry  9 }
	
airFlowSensorDewPointF OBJECT-TYPE
	SYNTAX  INTEGER(-58..212)
	UNITS "Degress Fahrenheit"
	MAX-ACCESS  read-only
	STATUS current
	DESCRIPTION "Current reading for Dew Point (F)"
	::= { airFlowSensorEntry  10 }
	
ctrl3ChDELTAEntry OBJECT-TYPE
	SYNTAX  Ctrl3ChDELTAEntry
	MAX-ACCESS  not-accessible
	STATUS current
	DESCRIPTION 
		"Entry in the 3 phase delta outlet control table: each entry contains
an index (ctrl3ChDELTAIndex) and other outlet control monitoring details"
	INDEX { ctrl3ChDELTAIndex }
	::= { ctrl3ChDELTATable 1 }

Ctrl3ChDELTAEntry ::= SEQUENCE {
	ctrl3ChDELTAIndex		INTEGER,
	ctrl3ChDELTASerial		DisplayString,
	ctrl3ChDELTAName		DisplayString,
	ctrl3ChDELTAAvail		Gauge32,
	ctrl3ChDELTAPowerChCount		INTEGER,
	ctrl3ChDELTADeciAmpsA		Gauge32,
	ctrl3ChDELTADeciAmpsB		Gauge32,
	ctrl3ChDELTADeciAmpsC		Gauge32,
	ctrl3ChDELTAkWattHrsTotal		Gauge32,
	ctrl3ChDELTARealPowerTotal		Gauge32,
	ctrl3ChDELTAkWattHrsAB		Gauge32,
	ctrl3ChDELTAVoltsAB		Gauge32,
	ctrl3ChDELTAVoltPeakAB		Gauge32,
	ctrl3ChDELTARealPowerAB		Gauge32,
	ctrl3ChDELTAApparentPowerAB		Gauge32,
	ctrl3ChDELTAPowerFactorAB		INTEGER,
	ctrl3ChDELTAkWattHrsBC		Gauge32,
	ctrl3ChDELTAVoltsBC		Gauge32,
	ctrl3ChDELTAVoltPeakBC		Gauge32,
	ctrl3ChDELTARealPowerBC		Gauge32,
	ctrl3ChDELTAApparentPowerBC		Gauge32,
	ctrl3ChDELTAPowerFactorBC		INTEGER,
	ctrl3ChDELTAkWattHrsCA		Gauge32,
	ctrl3ChDELTAVoltsCA		Gauge32,
	ctrl3ChDELTAVoltPeakCA		Gauge32,
	ctrl3ChDELTARealPowerCA		Gauge32,
	ctrl3ChDELTAApparentPowerCA		Gauge32,
	ctrl3ChDELTAPowerFactorCA		INTEGER
}

ctrl3ChDELTAIndex OBJECT-TYPE
	SYNTAX  INTEGER(1..100)
	MAX-ACCESS  not-accessible
	STATUS current
	DESCRIPTION "Table entry index value"
	::= { ctrl3ChDELTAEntry  1 }
	
ctrl3ChDELTASerial OBJECT-TYPE
	SYNTAX  DisplayString
	MAX-ACCESS  read-only
	STATUS current
	DESCRIPTION "Serial Number"
	::= { ctrl3ChDELTAEntry  2 }
	
ctrl3ChDELTAName OBJECT-TYPE
	SYNTAX  DisplayString
	MAX-ACCESS  read-only
	STATUS current
	DESCRIPTION "Friendly Name"
	::= { ctrl3ChDELTAEntry  3 }
	
ctrl3ChDELTAAvail OBJECT-TYPE
	SYNTAX  Gauge32
	MAX-ACCESS  read-only
	STATUS current
	DESCRIPTION "Is device currently plugged in?"
	::= { ctrl3ChDELTAEntry  4 }
	
ctrl3ChDELTAPowerChCount OBJECT-TYPE
	SYNTAX  INTEGER(0..3)
	MAX-ACCESS  read-only
	STATUS current
	DESCRIPTION "Number of active power channels"
	::= { ctrl3ChDELTAEntry  5 }
	
ctrl3ChDELTADeciAmpsA OBJECT-TYPE
	SYNTAX  Gauge32
	UNITS "0.1 Amps (rms)"
	MAX-ACCESS  read-only
	STATUS current
	DESCRIPTION "Current reading for DeciAmps (Line A)"
	::= { ctrl3ChDELTAEntry  6 }
	
ctrl3ChDELTADeciAmpsB OBJECT-TYPE
	SYNTAX  Gauge32
	UNITS "0.1 Amps (rms)"
	MAX-ACCESS  read-only
	STATUS current
	DESCRIPTION "Current reading for DeciAmps (Line B)"
	::= { ctrl3ChDELTAEntry  7 }
	
ctrl3ChDELTADeciAmpsC OBJECT-TYPE
	SYNTAX  Gauge32
	UNITS "0.1 Amps (rms)"
	MAX-ACCESS  read-only
	STATUS current
	DESCRIPTION "Current reading for DeciAmps (Line C)"
	::= { ctrl3ChDELTAEntry  8 }
	
ctrl3ChDELTAkWattHrsTotal OBJECT-TYPE
	SYNTAX  Gauge32
	UNITS "kWh"
	MAX-ACCESS  read-only
	STATUS current
	DESCRIPTION "Current Reading for kWatt-Hours (Total)"
	::= { ctrl3ChDELTAEntry  9 }
	
ctrl3ChDELTARealPowerTotal OBJECT-TYPE
	SYNTAX  Gauge32
	UNITS "Watts"
	MAX-ACCESS  read-only
	STATUS current
	DESCRIPTION "Current reading for Watts (Total)"
	::= { ctrl3ChDELTAEntry  10 }
	
ctrl3ChDELTAkWattHrsAB OBJECT-TYPE
	SYNTAX  Gauge32
	UNITS "kWh"
	MAX-ACCESS  read-only
	STATUS current
	DESCRIPTION "Current Reading for kWatt-Hours (Phase AB)"
	::= { ctrl3ChDELTAEntry  11 }
	
ctrl3ChDELTAVoltsAB OBJECT-TYPE
	SYNTAX  Gauge32
	UNITS "Volts (rms)"
	MAX-ACCESS  read-only
	STATUS current
	DESCRIPTION "Current reading for Volts (Phase AB)"
	::= { ctrl3ChDELTAEntry  12 }
	
ctrl3ChDELTAVoltPeakAB OBJECT-TYPE
	SYNTAX  Gauge32
	UNITS "Volts (rms)"
	MAX-ACCESS  read-only
	STATUS current
	DESCRIPTION "Current reading for Peak-Volts (Phase AB)"
	::= { ctrl3ChDELTAEntry  13 }
	
ctrl3ChDELTARealPowerAB OBJECT-TYPE
	SYNTAX  Gauge32
	UNITS "Watts"
	MAX-ACCESS  read-only
	STATUS current
	DESCRIPTION "Current reading for Real Power (Phase AB)"
	::= { ctrl3ChDELTAEntry  14 }
	
ctrl3ChDELTAApparentPowerAB OBJECT-TYPE
	SYNTAX  Gauge32
	UNITS "Volt-Amps"
	MAX-ACCESS  read-only
	STATUS current
	DESCRIPTION "Current reading for VoltAmps (Phase AB)"
	::= { ctrl3ChDELTAEntry  15 }
	
ctrl3ChDELTAPowerFactorAB OBJECT-TYPE
	SYNTAX  INTEGER(0..100)
	UNITS "%"
	MAX-ACCESS  read-only
	STATUS current
	DESCRIPTION "Current reading for Power Factor (Phase AB)"
	::= { ctrl3ChDELTAEntry  16 }
	
ctrl3ChDELTAkWattHrsBC OBJECT-TYPE
	SYNTAX  Gauge32
	UNITS "kWh"
	MAX-ACCESS  read-only
	STATUS current
	DESCRIPTION "Current Reading for kWatt-Hours (Phase BC)"
	::= { ctrl3ChDELTAEntry  17 }
	
ctrl3ChDELTAVoltsBC OBJECT-TYPE
	SYNTAX  Gauge32
	UNITS "Volts (rms)"
	MAX-ACCESS  read-only
	STATUS current
	DESCRIPTION "Current reading for Volts (Phase BC)"
	::= { ctrl3ChDELTAEntry  18 }
	
ctrl3ChDELTAVoltPeakBC OBJECT-TYPE
	SYNTAX  Gauge32
	UNITS "Volts (rms)"
	MAX-ACCESS  read-only
	STATUS current
	DESCRIPTION "Current reading for Peak-Volts (Phase BC)"
	::= { ctrl3ChDELTAEntry  19 }
	
ctrl3ChDELTARealPowerBC OBJECT-TYPE
	SYNTAX  Gauge32
	UNITS "Watts"
	MAX-ACCESS  read-only
	STATUS current
	DESCRIPTION "Current reading for Real Power (Phase BC)"
	::= { ctrl3ChDELTAEntry  20 }
	
ctrl3ChDELTAApparentPowerBC OBJECT-TYPE
	SYNTAX  Gauge32
	UNITS "Volt-Amps"
	MAX-ACCESS  read-only
	STATUS current
	DESCRIPTION "Current reading for VoltAmps (Phase BC)"
	::= { ctrl3ChDELTAEntry  21 }
	
ctrl3ChDELTAPowerFactorBC OBJECT-TYPE
	SYNTAX  INTEGER(0..100)
	UNITS "%"
	MAX-ACCESS  read-only
	STATUS current
	DESCRIPTION "Current reading for Power Factor (Phase BC)"
	::= { ctrl3ChDELTAEntry  22 }
	
ctrl3ChDELTAkWattHrsCA OBJECT-TYPE
	SYNTAX  Gauge32
	UNITS "kWh"
	MAX-ACCESS  read-only
	STATUS current
	DESCRIPTION "Current Reading for kWatt-Hours (Phase CA)"
	::= { ctrl3ChDELTAEntry  23 }
	
ctrl3ChDELTAVoltsCA OBJECT-TYPE
	SYNTAX  Gauge32
	UNITS "Volts (rms)"
	MAX-ACCESS  read-only
	STATUS current
	DESCRIPTION "Current reading for Volts (Phase CA)"
	::= { ctrl3ChDELTAEntry  24 }
	
ctrl3ChDELTAVoltPeakCA OBJECT-TYPE
	SYNTAX  Gauge32
	UNITS "Volts (rms)"
	MAX-ACCESS  read-only
	STATUS current
	DESCRIPTION "Current reading for Peak-Volts (Phase CA)"
	::= { ctrl3ChDELTAEntry  25 }
	
ctrl3ChDELTARealPowerCA OBJECT-TYPE
	SYNTAX  Gauge32
	UNITS "Watts"
	MAX-ACCESS  read-only
	STATUS current
	DESCRIPTION "Current reading for Real Power (Phase CA)"
	::= { ctrl3ChDELTAEntry  26 }
	
ctrl3ChDELTAApparentPowerCA OBJECT-TYPE
	SYNTAX  Gauge32
	UNITS "Volt-Amps"
	MAX-ACCESS  read-only
	STATUS current
	DESCRIPTION "Current reading for VoltAmps (Phase CA)"
	::= { ctrl3ChDELTAEntry  27 }
	
ctrl3ChDELTAPowerFactorCA OBJECT-TYPE
	SYNTAX  INTEGER(0..100)
	UNITS "%"
	MAX-ACCESS  read-only
	STATUS current
	DESCRIPTION "Current reading for Power Factor (Phase CA)"
	::= { ctrl3ChDELTAEntry  28 }
	
doorSensorEntry OBJECT-TYPE
	SYNTAX  DoorSensorEntry
	MAX-ACCESS  not-accessible
	STATUS current
	DESCRIPTION 
		"Entry in the door sensor table: each entry contains
an index (doorSensorIndex) and other sensor details"
	INDEX { doorSensorIndex }
	::= { doorSensorTable 1 }

DoorSensorEntry ::= SEQUENCE {
	doorSensorIndex		INTEGER,
	doorSensorSerial		DisplayString,
	doorSensorName		DisplayString,
	doorSensorAvail		Gauge32,
	doorSensorStatus		INTEGER
}

doorSensorIndex OBJECT-TYPE
	SYNTAX  INTEGER(1..100)
	MAX-ACCESS  not-accessible
	STATUS current
	DESCRIPTION "Table entry index value"
	::= { doorSensorEntry  1 }
	
doorSensorSerial OBJECT-TYPE
	SYNTAX  DisplayString
	MAX-ACCESS  read-only
	STATUS current
	DESCRIPTION "Serial Number"
	::= { doorSensorEntry  2 }
	
doorSensorName OBJECT-TYPE
	SYNTAX  DisplayString
	MAX-ACCESS  read-only
	STATUS current
	DESCRIPTION "Friendly Name"
	::= { doorSensorEntry  3 }
	
doorSensorAvail OBJECT-TYPE
	SYNTAX  Gauge32
	MAX-ACCESS  read-only
	STATUS current
	DESCRIPTION "Is device currently plugged in?"
	::= { doorSensorEntry  4 }
	
doorSensorStatus OBJECT-TYPE
	SYNTAX  INTEGER(0..100)
	MAX-ACCESS  read-only
	STATUS current
	DESCRIPTION "Door sensor status"
	::= { doorSensorEntry  5 }
	
waterSensorEntry OBJECT-TYPE
	SYNTAX  WaterSensorEntry
	MAX-ACCESS  not-accessible
	STATUS current
	DESCRIPTION 
		"Entry in the water sensor table: each entry contains
an index (waterSensorIndex) and other sensor details"
	INDEX { waterSensorIndex }
	::= { waterSensorTable 1 }

WaterSensorEntry ::= SEQUENCE {
	waterSensorIndex		INTEGER,
	waterSensorSerial		DisplayString,
	waterSensorName		DisplayString,
	waterSensorAvail		Gauge32,
	waterSensorDampness		INTEGER
}

waterSensorIndex OBJECT-TYPE
	SYNTAX  INTEGER(1..100)
	MAX-ACCESS  not-accessible
	STATUS current
	DESCRIPTION "Table entry index value"
	::= { waterSensorEntry  1 }
	
waterSensorSerial OBJECT-TYPE
	SYNTAX  DisplayString
	MAX-ACCESS  read-only
	STATUS current
	DESCRIPTION "Serial Number"
	::= { waterSensorEntry  2 }
	
waterSensorName OBJECT-TYPE
	SYNTAX  DisplayString
	MAX-ACCESS  read-only
	STATUS current
	DESCRIPTION "Friendly Name"
	::= { waterSensorEntry  3 }
	
waterSensorAvail OBJECT-TYPE
	SYNTAX  Gauge32
	MAX-ACCESS  read-only
	STATUS current
	DESCRIPTION "Is device currently plugged in?"
	::= { waterSensorEntry  4 }
	
waterSensorDampness OBJECT-TYPE
	SYNTAX  INTEGER(0..100)
	MAX-ACCESS  read-only
	STATUS current
	DESCRIPTION "Dampness of the water sensor"
	::= { waterSensorEntry  5 }
	
currentMonitorEntry OBJECT-TYPE
	SYNTAX  CurrentMonitorEntry
	MAX-ACCESS  not-accessible
	STATUS current
	DESCRIPTION 
		"Entry in the current monitor table: each entry contains
an index (currentMonitorIndex) and other sensor details"
	INDEX { currentMonitorIndex }
	::= { currentMonitorTable 1 }

CurrentMonitorEntry ::= SEQUENCE {
	currentMonitorIndex		INTEGER,
	currentMonitorSerial		DisplayString,
	currentMonitorName		DisplayString,
	currentMonitorAvail		Gauge32,
	currentMonitorDeciAmps		INTEGER
}

currentMonitorIndex OBJECT-TYPE
	SYNTAX  INTEGER(1..100)
	MAX-ACCESS  not-accessible
	STATUS current
	DESCRIPTION "Table entry index value"
	::= { currentMonitorEntry  1 }
	
currentMonitorSerial OBJECT-TYPE
	SYNTAX  DisplayString
	MAX-ACCESS  read-only
	STATUS current
	DESCRIPTION "Serial Number"
	::= { currentMonitorEntry  2 }
	
currentMonitorName OBJECT-TYPE
	SYNTAX  DisplayString
	MAX-ACCESS  read-only
	STATUS current
	DESCRIPTION "Friendly Name"
	::= { currentMonitorEntry  3 }
	
currentMonitorAvail OBJECT-TYPE
	SYNTAX  Gauge32
	MAX-ACCESS  read-only
	STATUS current
	DESCRIPTION "Is device currently plugged in?"
	::= { currentMonitorEntry  4 }
	
currentMonitorDeciAmps OBJECT-TYPE
	SYNTAX  INTEGER(0..30)
	UNITS "0.1 Amps"
	MAX-ACCESS  read-only
	STATUS current
	DESCRIPTION "Current in deciamps"
	::= { currentMonitorEntry  5 }
	
millivoltMonitorEntry OBJECT-TYPE
	SYNTAX  MillivoltMonitorEntry
	MAX-ACCESS  not-accessible
	STATUS current
	DESCRIPTION 
		"Entry in the millivolt monitor table: each entry contains
an index (millivoltMonitorIndex) and other sensor details"
	INDEX { millivoltMonitorIndex }
	::= { millivoltMonitorTable 1 }

MillivoltMonitorEntry ::= SEQUENCE {
	millivoltMonitorIndex		INTEGER,
	millivoltMonitorSerial		DisplayString,
	millivoltMonitorName		DisplayString,
	millivoltMonitorAvail		Gauge32,
	millivoltMonitorMV		INTEGER
}

millivoltMonitorIndex OBJECT-TYPE
	SYNTAX  INTEGER(1..100)
	MAX-ACCESS  not-accessible
	STATUS current
	DESCRIPTION "Table entry index value"
	::= { millivoltMonitorEntry  1 }
	
millivoltMonitorSerial OBJECT-TYPE
	SYNTAX  DisplayString
	MAX-ACCESS  read-only
	STATUS current
	DESCRIPTION "Serial Number"
	::= { millivoltMonitorEntry  2 }
	
millivoltMonitorName OBJECT-TYPE
	SYNTAX  DisplayString
	MAX-ACCESS  read-only
	STATUS current
	DESCRIPTION "Friendly Name"
	::= { millivoltMonitorEntry  3 }
	
millivoltMonitorAvail OBJECT-TYPE
	SYNTAX  Gauge32
	MAX-ACCESS  read-only
	STATUS current
	DESCRIPTION "Is device currently plugged in?"
	::= { millivoltMonitorEntry  4 }
	
millivoltMonitorMV OBJECT-TYPE
	SYNTAX  INTEGER(0..5000)
	UNITS "millivolts"
	MAX-ACCESS  read-only
	STATUS current
	DESCRIPTION "millivolts"
	::= { millivoltMonitorEntry  5 }
	
pow3ChEntry OBJECT-TYPE
	SYNTAX  Pow3ChEntry
	MAX-ACCESS  not-accessible
	STATUS current
	DESCRIPTION 
		"Entry in the power monitor 3 channel table: each entry contains
an index (pow3ChIndex) and other power monitoring details"
	INDEX { pow3ChIndex }
	::= { pow3ChTable 1 }

Pow3ChEntry ::= SEQUENCE {
	pow3ChIndex		INTEGER,
	pow3ChSerial		DisplayString,
	pow3ChName		DisplayString,
	pow3ChAvail		Gauge32,
	pow3ChkWattHrsA		Gauge32,
	pow3ChVoltsA		Gauge32,
	pow3ChVoltMaxA		Gauge32,
	pow3ChVoltMinA		Gauge32,
	pow3ChVoltPeakA		Gauge32,
	pow3ChDeciAmpsA		Gauge32,
	pow3ChRealPowerA		Gauge32,
	pow3ChApparentPowerA		Gauge32,
	pow3ChPowerFactorA		INTEGER,
	pow3ChkWattHrsB		Gauge32,
	pow3ChVoltsB		Gauge32,
	pow3ChVoltMaxB		Gauge32,
	pow3ChVoltMinB		Gauge32,
	pow3ChVoltPeakB		Gauge32,
	pow3ChDeciAmpsB		Gauge32,
	pow3ChRealPowerB		Gauge32,
	pow3ChApparentPowerB		Gauge32,
	pow3ChPowerFactorB		INTEGER,
	pow3ChkWattHrsC		Gauge32,
	pow3ChVoltsC		Gauge32,
	pow3ChVoltMaxC		Gauge32,
	pow3ChVoltMinC		Gauge32,
	pow3ChVoltPeakC		Gauge32,
	pow3ChDeciAmpsC		Gauge32,
	pow3ChRealPowerC		Gauge32,
	pow3ChApparentPowerC		Gauge32,
	pow3ChPowerFactorC		INTEGER,
	pow3ChkWattHrsTotal		Gauge32,
	pow3ChRealPowerTotal		Gauge32
}

pow3ChIndex OBJECT-TYPE
	SYNTAX  INTEGER(1..100)
	MAX-ACCESS  not-accessible
	STATUS current
	DESCRIPTION "Table entry index value"
	::= { pow3ChEntry  1 }
	
pow3ChSerial OBJECT-TYPE
	SYNTAX  DisplayString
	MAX-ACCESS  read-only
	STATUS current
	DESCRIPTION "Serial Number"
	::= { pow3ChEntry  2 }
	
pow3ChName OBJECT-TYPE
	SYNTAX  DisplayString
	MAX-ACCESS  read-only
	STATUS current
	DESCRIPTION "Friendly Name"
	::= { pow3ChEntry  3 }
	
pow3ChAvail OBJECT-TYPE
	SYNTAX  Gauge32
	MAX-ACCESS  read-only
	STATUS current
	DESCRIPTION "Is device currently plugged in?"
	::= { pow3ChEntry  4 }
	
pow3ChkWattHrsA OBJECT-TYPE
	SYNTAX  Gauge32
	UNITS "kWh"
	MAX-ACCESS  read-only
	STATUS current
	DESCRIPTION "Current reading for kWatt-Hours (Phase A)"
	::= { pow3ChEntry  5 }
	
pow3ChVoltsA OBJECT-TYPE
	SYNTAX  Gauge32
	UNITS "Volts (rms)"
	MAX-ACCESS  read-only
	STATUS current
	DESCRIPTION "Current reading for Volts (Phase A)"
	::= { pow3ChEntry  6 }
	
pow3ChVoltMaxA OBJECT-TYPE
	SYNTAX  Gauge32
	UNITS "Volts (rms)"
	MAX-ACCESS  read-only
	STATUS current
	DESCRIPTION "Current reading for Max-Volts (Phase A)"
	::= { pow3ChEntry  7 }
	
pow3ChVoltMinA OBJECT-TYPE
	SYNTAX  Gauge32
	UNITS "Volts (rms)"
	MAX-ACCESS  read-only
	STATUS current
	DESCRIPTION "Current reading for Min-Volts (Phase A)"
	::= { pow3ChEntry  8 }
	
pow3ChVoltPeakA OBJECT-TYPE
	SYNTAX  Gauge32
	UNITS "Volts"
	MAX-ACCESS  read-only
	STATUS current
	DESCRIPTION "Current reading for Peak-Volts (Phase A)"
	::= { pow3ChEntry  9 }
	
pow3ChDeciAmpsA OBJECT-TYPE
	SYNTAX  Gauge32
	UNITS "0.1 Amps (rms)"
	MAX-ACCESS  read-only
	STATUS current
	DESCRIPTION "Current reading for DeciAmps (Phase A)"
	::= { pow3ChEntry  10 }
	
pow3ChRealPowerA OBJECT-TYPE
	SYNTAX  Gauge32
	UNITS "Watts"
	MAX-ACCESS  read-only
	STATUS current
	DESCRIPTION "Current reading for Real Power (Phase A)"
	::= { pow3ChEntry  11 }
	
pow3ChApparentPowerA OBJECT-TYPE
	SYNTAX  Gauge32
	UNITS "Volt-Amps"
	MAX-ACCESS  read-only
	STATUS current
	DESCRIPTION "Current reading for Apparent Power (Phase A)"
	::= { pow3ChEntry  12 }
	
pow3ChPowerFactorA OBJECT-TYPE
	SYNTAX  INTEGER(0..100)
	UNITS "%"
	MAX-ACCESS  read-only
	STATUS current
	DESCRIPTION "Current reading for Power Factor (Phase A)"
	::= { pow3ChEntry  13 }
	
pow3ChkWattHrsB OBJECT-TYPE
	SYNTAX  Gauge32
	UNITS "kWh"
	MAX-ACCESS  read-only
	STATUS current
	DESCRIPTION "Current reading for kWatt-Hours (Phase B)"
	::= { pow3ChEntry  14 }
	
pow3ChVoltsB OBJECT-TYPE
	SYNTAX  Gauge32
	UNITS "Volts (rms)"
	MAX-ACCESS  read-only
	STATUS current
	DESCRIPTION "Current reading for Volts (Phase B)"
	::= { pow3ChEntry  15 }
	
pow3ChVoltMaxB OBJECT-TYPE
	SYNTAX  Gauge32
	UNITS "Volts (rms)"
	MAX-ACCESS  read-only
	STATUS current
	DESCRIPTION "Current reading for Max-Volts (Phase B)"
	::= { pow3ChEntry  16 }
	
pow3ChVoltMinB OBJECT-TYPE
	SYNTAX  Gauge32
	UNITS "Volts (rms)"
	MAX-ACCESS  read-only
	STATUS current
	DESCRIPTION "Current reading for Min-Volts (Phase B)"
	::= { pow3ChEntry  17 }
	
pow3ChVoltPeakB OBJECT-TYPE
	SYNTAX  Gauge32
	UNITS "Volts"
	MAX-ACCESS  read-only
	STATUS current
	DESCRIPTION "Current reading for Peak-Volts (Phase B)"
	::= { pow3ChEntry  18 }
	
pow3ChDeciAmpsB OBJECT-TYPE
	SYNTAX  Gauge32
	UNITS "0.1 Amps (rms)"
	MAX-ACCESS  read-only
	STATUS current
	DESCRIPTION "Current reading for DeciAmps (Phase B)"
	::= { pow3ChEntry  19 }
	
pow3ChRealPowerB OBJECT-TYPE
	SYNTAX  Gauge32
	UNITS "Watts"
	MAX-ACCESS  read-only
	STATUS current
	DESCRIPTION "Current reading for Real Power (Phase B)"
	::= { pow3ChEntry  20 }
	
pow3ChApparentPowerB OBJECT-TYPE
	SYNTAX  Gauge32
	UNITS "Volt-Amps"
	MAX-ACCESS  read-only
	STATUS current
	DESCRIPTION "Current reading for Apparent Power (Phase B)"
	::= { pow3ChEntry  21 }
	
pow3ChPowerFactorB OBJECT-TYPE
	SYNTAX  INTEGER(0..100)
	UNITS "%"
	MAX-ACCESS  read-only
	STATUS current
	DESCRIPTION "Current reading for Power Factor (Phase B)"
	::= { pow3ChEntry  22 }
	
pow3ChkWattHrsC OBJECT-TYPE
	SYNTAX  Gauge32
	UNITS "kWh"
	MAX-ACCESS  read-only
	STATUS current
	DESCRIPTION "Current reading for kWatt-Hours (Phase C)"
	::= { pow3ChEntry  23 }
	
pow3ChVoltsC OBJECT-TYPE
	SYNTAX  Gauge32
	UNITS "Volts (rms)"
	MAX-ACCESS  read-only
	STATUS current
	DESCRIPTION "Current reading for Volts (Phase C)"
	::= { pow3ChEntry  24 }
	
pow3ChVoltMaxC OBJECT-TYPE
	SYNTAX  Gauge32
	UNITS "Volts (rms)"
	MAX-ACCESS  read-only
	STATUS current
	DESCRIPTION "Current reading for Max-Volts (Phase C)"
	::= { pow3ChEntry  25 }
	
pow3ChVoltMinC OBJECT-TYPE
	SYNTAX  Gauge32
	UNITS "Volts (rms)"
	MAX-ACCESS  read-only
	STATUS current
	DESCRIPTION "Current reading for Min-Volts (Phase C)"
	::= { pow3ChEntry  26 }
	
pow3ChVoltPeakC OBJECT-TYPE
	SYNTAX  Gauge32
	UNITS "Volts"
	MAX-ACCESS  read-only
	STATUS current
	DESCRIPTION "Current reading for Peak-Volts (Phase C)"
	::= { pow3ChEntry  27 }
	
pow3ChDeciAmpsC OBJECT-TYPE
	SYNTAX  Gauge32
	UNITS "0.1 Amps (rms)"
	MAX-ACCESS  read-only
	STATUS current
	DESCRIPTION "Current reading for DeciAmps (Phase C)"
	::= { pow3ChEntry  28 }
	
pow3ChRealPowerC OBJECT-TYPE
	SYNTAX  Gauge32
	UNITS "Watts"
	MAX-ACCESS  read-only
	STATUS current
	DESCRIPTION "Current reading for Real Power (Phase C)"
	::= { pow3ChEntry  29 }
	
pow3ChApparentPowerC OBJECT-TYPE
	SYNTAX  Gauge32
	UNITS "Volt-Amps"
	MAX-ACCESS  read-only
	STATUS current
	DESCRIPTION "Current reading for Apparent Power (Phase C)"
	::= { pow3ChEntry  30 }
	
pow3ChPowerFactorC OBJECT-TYPE
	SYNTAX  INTEGER(0..100)
	UNITS "%"
	MAX-ACCESS  read-only
	STATUS current
	DESCRIPTION "Current reading for Power Factor (Phase C)"
	::= { pow3ChEntry  31 }
	
pow3ChkWattHrsTotal OBJECT-TYPE
	SYNTAX  Gauge32
	UNITS "kWh"
	MAX-ACCESS  read-only
	STATUS current
	DESCRIPTION "Current reading for kWatt-Hours (Total)"
	::= { pow3ChEntry  32 }
	
pow3ChRealPowerTotal OBJECT-TYPE
	SYNTAX  Gauge32
	UNITS "Watts"
	MAX-ACCESS  read-only
	STATUS current
	DESCRIPTION "Current reading for Real Power (Total)"
	::= { pow3ChEntry  33 }
	
outletEntry OBJECT-TYPE
	SYNTAX  OutletEntry
	MAX-ACCESS  not-accessible
	STATUS current
	DESCRIPTION 
		"Entry in the outlet table: each entry contains
an index (outletIndex) and other sensor details"
	INDEX { outletIndex }
	::= { outletTable 1 }

OutletEntry ::= SEQUENCE {
	outletIndex		INTEGER,
	outletSerial		DisplayString,
	outletName		DisplayString,
	outletAvail		Gauge32,
	outlet1Status		INTEGER,
	outlet2Status		INTEGER
}

outletIndex OBJECT-TYPE
	SYNTAX  INTEGER(1..100)
	MAX-ACCESS  not-accessible
	STATUS current
	DESCRIPTION "Table entry index value"
	::= { outletEntry  1 }
	
outletSerial OBJECT-TYPE
	SYNTAX  DisplayString
	MAX-ACCESS  read-only
	STATUS current
	DESCRIPTION "Serial Number"
	::= { outletEntry  2 }
	
outletName OBJECT-TYPE
	SYNTAX  DisplayString
	MAX-ACCESS  read-only
	STATUS current
	DESCRIPTION "Friendly Name"
	::= { outletEntry  3 }
	
outletAvail OBJECT-TYPE
	SYNTAX  Gauge32
	MAX-ACCESS  read-only
	STATUS current
	DESCRIPTION "Is device currently plugged in?"
	::= { outletEntry  4 }
	
outlet1Status OBJECT-TYPE
	SYNTAX  INTEGER(0..100)
	MAX-ACCESS  read-only
	STATUS current
	DESCRIPTION "Outlet 1 status"
	::= { outletEntry  5 }
	
outlet2Status OBJECT-TYPE
	SYNTAX  INTEGER(0..100)
	MAX-ACCESS  read-only
	STATUS current
	DESCRIPTION "Outlet 2 status"
	::= { outletEntry  6 }
	
vsfcEntry OBJECT-TYPE
	SYNTAX  VsfcEntry
	MAX-ACCESS  not-accessible
	STATUS current
	DESCRIPTION 
		"Entry in the vsfc table: each entry contains
an index (vsfcIndex) and other details"
	INDEX { vsfcIndex }
	::= { vsfcTable 1 }

VsfcEntry ::= SEQUENCE {
	vsfcIndex		INTEGER,
	vsfcSerial		DisplayString,
	vsfcName		DisplayString,
	vsfcAvail		Gauge32,
	vsfcSetPointC		INTEGER,
	vsfcSetPointF		INTEGER,
	vsfcFanSpeed		INTEGER,
	vsfcIntTempC		INTEGER,
	vsfcIntTempF		INTEGER,
	vsfcExt1TempC		INTEGER,
	vsfcExt1TempF		INTEGER,
	vsfcExt2TempC		INTEGER,
	vsfcExt2TempF		INTEGER,
	vsfcExt3TempC		INTEGER,
	vsfcExt3TempF		INTEGER,
	vsfcExt4TempC		INTEGER,
	vsfcExt4TempF		INTEGER
}

vsfcIndex OBJECT-TYPE
	SYNTAX  INTEGER(1..1)
	MAX-ACCESS  not-accessible
	STATUS current
	DESCRIPTION "Table entry index value"
	::= { vsfcEntry  1 }
	
vsfcSerial OBJECT-TYPE
	SYNTAX  DisplayString
	MAX-ACCESS  read-only
	STATUS current
	DESCRIPTION "Serial Number"
	::= { vsfcEntry  2 }
	
vsfcName OBJECT-TYPE
	SYNTAX  DisplayString
	MAX-ACCESS  read-only
	STATUS current
	DESCRIPTION "Friendly Name"
	::= { vsfcEntry  3 }
	
vsfcAvail OBJECT-TYPE
	SYNTAX  Gauge32
	MAX-ACCESS  read-only
	STATUS current
	DESCRIPTION "Is device currently plugged in?"
	::= { vsfcEntry  4 }
	
vsfcSetPointC OBJECT-TYPE
	SYNTAX  INTEGER(18..38)
	UNITS "Degrees Celsius"
	MAX-ACCESS  read-only
	STATUS current
	DESCRIPTION "Current temperature set point in C"
	::= { vsfcEntry  5 }
	
vsfcSetPointF OBJECT-TYPE
	SYNTAX  INTEGER(65..100)
	UNITS "Degrees Fahrenheit"
	MAX-ACCESS  read-only
	STATUS current
	DESCRIPTION "Current temperature set point in F"
	::= { vsfcEntry  6 }
	
vsfcFanSpeed OBJECT-TYPE
	SYNTAX  INTEGER(0..100)
	UNITS "%"
	MAX-ACCESS  read-only
	STATUS current
	DESCRIPTION "Current reading for Fan Speed"
	::= { vsfcEntry  7 }
	
vsfcIntTempC OBJECT-TYPE
	SYNTAX  INTEGER(-20..50)
	UNITS "Degrees Celsius"
	MAX-ACCESS  read-only
	STATUS current
	DESCRIPTION "Current internal temperature reading in C"
	::= { vsfcEntry  8 }
	
vsfcIntTempF OBJECT-TYPE
	SYNTAX  INTEGER(-4..122)
	UNITS "Degrees Fahrenheit"
	MAX-ACCESS  read-only
	STATUS current
	DESCRIPTION "Current internal temperature reading in F"
	::= { vsfcEntry  9 }
	
vsfcExt1TempC OBJECT-TYPE
	SYNTAX  INTEGER(-20..50)
	UNITS "Degrees Celsius"
	MAX-ACCESS  read-only
	STATUS current
	DESCRIPTION "Current reading for external temp 1 in C"
	::= { vsfcEntry  10 }
	
vsfcExt1TempF OBJECT-TYPE
	SYNTAX  INTEGER(-20..122)
	UNITS "Degrees Fahrenheit"
	MAX-ACCESS  read-only
	STATUS current
	DESCRIPTION "Current reading for external temp 1 in F"
	::= { vsfcEntry  11 }
	
vsfcExt2TempC OBJECT-TYPE
	SYNTAX  INTEGER(-20..50)
	UNITS "Degrees Celsius"
	MAX-ACCESS  read-only
	STATUS current
	DESCRIPTION "Current reading for external temp 2 in C"
	::= { vsfcEntry  12 }
	
vsfcExt2TempF OBJECT-TYPE
	SYNTAX  INTEGER(-20..122)
	UNITS "Degrees Fahrenheit"
	MAX-ACCESS  read-only
	STATUS current
	DESCRIPTION "Current reading for external temp 1 in F"
	::= { vsfcEntry  13 }
	
vsfcExt3TempC OBJECT-TYPE
	SYNTAX  INTEGER(-20..50)
	UNITS "Degrees Celsius"
	MAX-ACCESS  read-only
	STATUS current
	DESCRIPTION "Current reading for external temp 3 in C"
	::= { vsfcEntry  14 }
	
vsfcExt3TempF OBJECT-TYPE
	SYNTAX  INTEGER(-20..122)
	UNITS "Degrees Fahrenheit"
	MAX-ACCESS  read-only
	STATUS current
	DESCRIPTION "Current reading for external temp 1 in F"
	::= { vsfcEntry  15 }
	
vsfcExt4TempC OBJECT-TYPE
	SYNTAX  INTEGER(-20..50)
	UNITS "Degrees Celsius"
	MAX-ACCESS  read-only
	STATUS current
	DESCRIPTION "Current reading for external temp 4 in C"
	::= { vsfcEntry  16 }
	
vsfcExt4TempF OBJECT-TYPE
	SYNTAX  INTEGER(-20..122)
	UNITS "Degrees Fahrenheit"
	MAX-ACCESS  read-only
	STATUS current
	DESCRIPTION "Current reading for external temp 1 in F"
	::= { vsfcEntry  17 }
	
ctrl3ChEntry OBJECT-TYPE
	SYNTAX  Ctrl3ChEntry
	MAX-ACCESS  not-accessible
	STATUS current
	DESCRIPTION 
		"Entry in the 3 phase outlet control table: each entry contains
an index (ctrl3ChIndex) and other outlet control monitoring details"
	INDEX { ctrl3ChIndex }
	::= { ctrl3ChTable 1 }

Ctrl3ChEntry ::= SEQUENCE {
	ctrl3ChIndex		INTEGER,
	ctrl3ChSerial		DisplayString,
	ctrl3ChName		DisplayString,
	ctrl3ChAvail		Gauge32,
	ctrl3ChVoltsA		Gauge32,
	ctrl3ChVoltPeakA		Gauge32,
	ctrl3ChDeciAmpsA		Gauge32,
	ctrl3ChDeciAmpsPeakA		Gauge32,
	ctrl3ChRealPowerA		Gauge32,
	ctrl3ChApparentPowerA		Gauge32,
	ctrl3ChPowerFactorA		INTEGER,
	ctrl3ChVoltsB		Gauge32,
	ctrl3ChVoltPeakB		Gauge32,
	ctrl3ChDeciAmpsB		Gauge32,
	ctrl3ChDeciAmpsPeakB		Gauge32,
	ctrl3ChRealPowerB		Gauge32,
	ctrl3ChApparentPowerB		Gauge32,
	ctrl3ChPowerFactorB		INTEGER,
	ctrl3ChVoltsC		Gauge32,
	ctrl3ChVoltPeakC		Gauge32,
	ctrl3ChDeciAmpsC		Gauge32,
	ctrl3ChDeciAmpsPeakC		Gauge32,
	ctrl3ChRealPowerC		Gauge32,
	ctrl3ChApparentPowerC		Gauge32,
	ctrl3ChPowerFactorC		INTEGER
}

ctrl3ChIndex OBJECT-TYPE
	SYNTAX  INTEGER(1..1)
	MAX-ACCESS  not-accessible
	STATUS current
	DESCRIPTION "Table entry index value"
	::= { ctrl3ChEntry  1 }
	
ctrl3ChSerial OBJECT-TYPE
	SYNTAX  DisplayString
	MAX-ACCESS  read-only
	STATUS current
	DESCRIPTION "Serial Number"
	::= { ctrl3ChEntry  2 }
	
ctrl3ChName OBJECT-TYPE
	SYNTAX  DisplayString
	MAX-ACCESS  read-only
	STATUS current
	DESCRIPTION "Friendly Name"
	::= { ctrl3ChEntry  3 }
	
ctrl3ChAvail OBJECT-TYPE
	SYNTAX  Gauge32
	MAX-ACCESS  read-only
	STATUS current
	DESCRIPTION "Is device currently plugged in?"
	::= { ctrl3ChEntry  4 }
	
ctrl3ChVoltsA OBJECT-TYPE
	SYNTAX  Gauge32
	UNITS "Volts (rms)"
	MAX-ACCESS  read-only
	STATUS current
	DESCRIPTION "Current reading for Volts (Phase A)"
	::= { ctrl3ChEntry  5 }
	
ctrl3ChVoltPeakA OBJECT-TYPE
	SYNTAX  Gauge32
	UNITS "Volts (rms)"
	MAX-ACCESS  read-only
	STATUS current
	DESCRIPTION "Current reading for Peak-Volts (Phase A)"
	::= { ctrl3ChEntry  6 }
	
ctrl3ChDeciAmpsA OBJECT-TYPE
	SYNTAX  Gauge32
	UNITS "0.1 Amps (rms)"
	MAX-ACCESS  read-only
	STATUS current
	DESCRIPTION "Current reading for DeciAmps (Phase A)"
	::= { ctrl3ChEntry  7 }
	
ctrl3ChDeciAmpsPeakA OBJECT-TYPE
	SYNTAX  Gauge32
	UNITS "0.1 Amps (rms)"
	MAX-ACCESS  read-only
	STATUS current
	DESCRIPTION "Current reading for Peak-DeciAmps (Phase A)"
	::= { ctrl3ChEntry  8 }
	
ctrl3ChRealPowerA OBJECT-TYPE
	SYNTAX  Gauge32
	UNITS "Watts"
	MAX-ACCESS  read-only
	STATUS current
	DESCRIPTION "Current reading for Real Power (Phase A)"
	::= { ctrl3ChEntry  9 }
	
ctrl3ChApparentPowerA OBJECT-TYPE
	SYNTAX  Gauge32
	UNITS "Volt-Amps"
	MAX-ACCESS  read-only
	STATUS current
	DESCRIPTION "Current reading for Apparent Power (Phase A)"
	::= { ctrl3ChEntry  10 }
	
ctrl3ChPowerFactorA OBJECT-TYPE
	SYNTAX  INTEGER(0..100)
	UNITS "%"
	MAX-ACCESS  read-only
	STATUS current
	DESCRIPTION "Current reading for Power Factor (Phase A)"
	::= { ctrl3ChEntry  11 }
	
ctrl3ChVoltsB OBJECT-TYPE
	SYNTAX  Gauge32
	UNITS "Volts (rms)"
	MAX-ACCESS  read-only
	STATUS current
	DESCRIPTION "Current reading for Volts (Phase B)"
	::= { ctrl3ChEntry  12 }
	
ctrl3ChVoltPeakB OBJECT-TYPE
	SYNTAX  Gauge32
	UNITS "Volts (rms)"
	MAX-ACCESS  read-only
	STATUS current
	DESCRIPTION "Current reading for Peak-Volts (Phase B)"
	::= { ctrl3ChEntry  13 }
	
ctrl3ChDeciAmpsB OBJECT-TYPE
	SYNTAX  Gauge32
	UNITS "0.1 Amps (rms)"
	MAX-ACCESS  read-only
	STATUS current
	DESCRIPTION "Current reading for DeciAmps (Phase B)"
	::= { ctrl3ChEntry  14 }
	
ctrl3ChDeciAmpsPeakB OBJECT-TYPE
	SYNTAX  Gauge32
	UNITS "0.1 Amps (rms)"
	MAX-ACCESS  read-only
	STATUS current
	DESCRIPTION "Current reading for Peak-DeciAmps (Phase B)"
	::= { ctrl3ChEntry  15 }
	
ctrl3ChRealPowerB OBJECT-TYPE
	SYNTAX  Gauge32
	UNITS "Watts"
	MAX-ACCESS  read-only
	STATUS current
	DESCRIPTION "Current reading for Real Power (Phase B)"
	::= { ctrl3ChEntry  16 }
	
ctrl3ChApparentPowerB OBJECT-TYPE
	SYNTAX  Gauge32
	UNITS "Volt-Amps"
	MAX-ACCESS  read-only
	STATUS current
	DESCRIPTION "Current reading for Apparent Power (Phase B)"
	::= { ctrl3ChEntry  17 }
	
ctrl3ChPowerFactorB OBJECT-TYPE
	SYNTAX  INTEGER(0..100)
	UNITS "%"
	MAX-ACCESS  read-only
	STATUS current
	DESCRIPTION "Current reading for Power Factor (Phase B)"
	::= { ctrl3ChEntry  18 }
	
ctrl3ChVoltsC OBJECT-TYPE
	SYNTAX  Gauge32
	UNITS "Volts (rms)"
	MAX-ACCESS  read-only
	STATUS current
	DESCRIPTION "Current reading for Volts (Phase C)"
	::= { ctrl3ChEntry  19 }
	
ctrl3ChVoltPeakC OBJECT-TYPE
	SYNTAX  Gauge32
	UNITS "Volts (rms)"
	MAX-ACCESS  read-only
	STATUS current
	DESCRIPTION "Current reading for Peak-Volts (Phase C)"
	::= { ctrl3ChEntry  20 }
	
ctrl3ChDeciAmpsC OBJECT-TYPE
	SYNTAX  Gauge32
	UNITS "0.1 Amps (rms)"
	MAX-ACCESS  read-only
	STATUS current
	DESCRIPTION "Current reading for DeciAmps (Phase C)"
	::= { ctrl3ChEntry  21 }
	
ctrl3ChDeciAmpsPeakC OBJECT-TYPE
	SYNTAX  Gauge32
	UNITS "0.1 Amps (rms)"
	MAX-ACCESS  read-only
	STATUS current
	DESCRIPTION "Current reading for Peak-DeciAmps (Phase C)"
	::= { ctrl3ChEntry  22 }
	
ctrl3ChRealPowerC OBJECT-TYPE
	SYNTAX  Gauge32
	UNITS "Watts"
	MAX-ACCESS  read-only
	STATUS current
	DESCRIPTION "Current reading for Real Power (Phase C)"
	::= { ctrl3ChEntry  23 }
	
ctrl3ChApparentPowerC OBJECT-TYPE
	SYNTAX  Gauge32
	UNITS "Volt-Amps"
	MAX-ACCESS  read-only
	STATUS current
	DESCRIPTION "Current reading for Apparent Power (Phase C)"
	::= { ctrl3ChEntry  24 }
	
ctrl3ChPowerFactorC OBJECT-TYPE
	SYNTAX  INTEGER(0..100)
	UNITS "%"
	MAX-ACCESS  read-only
	STATUS current
	DESCRIPTION "Current reading for Power Factor (Phase C)"
	::= { ctrl3ChEntry  25 }
	
ctrlGrpAmpsEntry OBJECT-TYPE
	SYNTAX  CtrlGrpAmpsEntry
	MAX-ACCESS  not-accessible
	STATUS current
	DESCRIPTION 
		"Entry in the Control Group Amps table: each entry contains
an index (ctrlGrpAmpsIndex) and other sensor details"
	INDEX { ctrlGrpAmpsIndex }
	::= { ctrlGrpAmpsTable 1 }

CtrlGrpAmpsEntry ::= SEQUENCE {
	ctrlGrpAmpsIndex		INTEGER,
	ctrlGrpAmpsSerial		DisplayString,
	ctrlGrpAmpsName		DisplayString,
	ctrlGrpAmpsAvail		Gauge32,
	ctrlGrpAmpsA		Gauge32,
	ctrlGrpAmpsB		Gauge32,
	ctrlGrpAmpsC		Gauge32,
	ctrlGrpAmpsD		Gauge32,
	ctrlGrpAmpsE		Gauge32,
	ctrlGrpAmpsF		Gauge32,
	ctrlGrpAmpsG		Gauge32,
	ctrlGrpAmpsH		Gauge32,
	ctrlGrpAmpsAVolts		Gauge32,
	ctrlGrpAmpsBVolts		Gauge32,
	ctrlGrpAmpsCVolts		Gauge32,
	ctrlGrpAmpsDVolts		Gauge32,
	ctrlGrpAmpsEVolts		Gauge32,
	ctrlGrpAmpsFVolts		Gauge32,
	ctrlGrpAmpsGVolts		Gauge32,
	ctrlGrpAmpsHVolts		Gauge32,
	ctrlGrpAmpsI		Gauge32,
	ctrlGrpAmpsJ		Gauge32,
	ctrlGrpAmpsK		Gauge32,
	ctrlGrpAmpsL		Gauge32,
	ctrlGrpAmpsM		Gauge32,
	ctrlGrpAmpsN		Gauge32,
	ctrlGrpAmpsO		Gauge32,
	ctrlGrpAmpsP		Gauge32,
	ctrlGrpAmpsIVolts		Gauge32,
	ctrlGrpAmpsJVolts		Gauge32,
	ctrlGrpAmpsKVolts		Gauge32,
	ctrlGrpAmpsLVolts		Gauge32,
	ctrlGrpAmpsMVolts		Gauge32,
	ctrlGrpAmpsNVolts		Gauge32,
	ctrlGrpAmpsOVolts		Gauge32,
	ctrlGrpAmpsPVolts		Gauge32
}

ctrlGrpAmpsIndex OBJECT-TYPE
	SYNTAX  INTEGER(1..1)
	MAX-ACCESS  not-accessible
	STATUS current
	DESCRIPTION "Table entry index value"
	::= { ctrlGrpAmpsEntry  1 }
	
ctrlGrpAmpsSerial OBJECT-TYPE
	SYNTAX  DisplayString
	MAX-ACCESS  read-only
	STATUS current
	DESCRIPTION "Serial Number"
	::= { ctrlGrpAmpsEntry  2 }
	
ctrlGrpAmpsName OBJECT-TYPE
	SYNTAX  DisplayString
	MAX-ACCESS  read-only
	STATUS current
	DESCRIPTION "Friendly Name"
	::= { ctrlGrpAmpsEntry  3 }
	
ctrlGrpAmpsAvail OBJECT-TYPE
	SYNTAX  Gauge32
	MAX-ACCESS  read-only
	STATUS current
	DESCRIPTION "Is device currently plugged in?"
	::= { ctrlGrpAmpsEntry  4 }
	
ctrlGrpAmpsA OBJECT-TYPE
	SYNTAX  Gauge32
	UNITS "0.1 Amps (rms)"
	MAX-ACCESS  read-only
	STATUS current
	DESCRIPTION "DeciAmps Group A"
	::= { ctrlGrpAmpsEntry  5 }
	
ctrlGrpAmpsB OBJECT-TYPE
	SYNTAX  Gauge32
	UNITS "0.1 Amps (rms)"
	MAX-ACCESS  read-only
	STATUS current
	DESCRIPTION "DeciAmps Group B"
	::= { ctrlGrpAmpsEntry  6 }
	
ctrlGrpAmpsC OBJECT-TYPE
	SYNTAX  Gauge32
	UNITS "0.1 Amps (rms)"
	MAX-ACCESS  read-only
	STATUS current
	DESCRIPTION "DeciAmps Group C"
	::= { ctrlGrpAmpsEntry  7 }
	
ctrlGrpAmpsD OBJECT-TYPE
	SYNTAX  Gauge32
	UNITS "0.1 Amps (rms)"
	MAX-ACCESS  read-only
	STATUS current
	DESCRIPTION "DeciAmps Group D"
	::= { ctrlGrpAmpsEntry  8 }
	
ctrlGrpAmpsE OBJECT-TYPE
	SYNTAX  Gauge32
	UNITS "0.1 Amps (rms)"
	MAX-ACCESS  read-only
	STATUS current
	DESCRIPTION "DeciAmps Group E"
	::= { ctrlGrpAmpsEntry  9 }
	
ctrlGrpAmpsF OBJECT-TYPE
	SYNTAX  Gauge32
	UNITS "0.1 Amps (rms)"
	MAX-ACCESS  read-only
	STATUS current
	DESCRIPTION "DeciAmps Group F"
	::= { ctrlGrpAmpsEntry  10 }
	
ctrlGrpAmpsG OBJECT-TYPE
	SYNTAX  Gauge32
	UNITS "0.1 Amps (rms)"
	MAX-ACCESS  read-only
	STATUS current
	DESCRIPTION "DeciAmps Group G"
	::= { ctrlGrpAmpsEntry  11 }
	
ctrlGrpAmpsH OBJECT-TYPE
	SYNTAX  Gauge32
	UNITS "0.1 Amps (rms)"
	MAX-ACCESS  read-only
	STATUS current
	DESCRIPTION "DeciAmps Group H"
	::= { ctrlGrpAmpsEntry  12 }
	
ctrlGrpAmpsAVolts OBJECT-TYPE
	SYNTAX  Gauge32
	UNITS "Volts (rms)"
	MAX-ACCESS  read-only
	STATUS current
	DESCRIPTION "Volts Group A"
	::= { ctrlGrpAmpsEntry  13 }
	
ctrlGrpAmpsBVolts OBJECT-TYPE
	SYNTAX  Gauge32
	UNITS "Volts (rms)"
	MAX-ACCESS  read-only
	STATUS current
	DESCRIPTION "Volts Group B"
	::= { ctrlGrpAmpsEntry  14 }
	
ctrlGrpAmpsCVolts OBJECT-TYPE
	SYNTAX  Gauge32
	UNITS "Volts (rms)"
	MAX-ACCESS  read-only
	STATUS current
	DESCRIPTION "Volts Group C"
	::= { ctrlGrpAmpsEntry  15 }
	
ctrlGrpAmpsDVolts OBJECT-TYPE
	SYNTAX  Gauge32
	UNITS "Volts (rms)"
	MAX-ACCESS  read-only
	STATUS current
	DESCRIPTION "Volts Group D"
	::= { ctrlGrpAmpsEntry  16 }
	
ctrlGrpAmpsEVolts OBJECT-TYPE
	SYNTAX  Gauge32
	UNITS "Volts (rms)"
	MAX-ACCESS  read-only
	STATUS current
	DESCRIPTION "Volts Group E"
	::= { ctrlGrpAmpsEntry  17 }
	
ctrlGrpAmpsFVolts OBJECT-TYPE
	SYNTAX  Gauge32
	UNITS "Volts (rms)"
	MAX-ACCESS  read-only
	STATUS current
	DESCRIPTION "Volts Group F"
	::= { ctrlGrpAmpsEntry  18 }
	
ctrlGrpAmpsGVolts OBJECT-TYPE
	SYNTAX  Gauge32
	UNITS "Volts (rms)"
	MAX-ACCESS  read-only
	STATUS current
	DESCRIPTION "Volts Group G"
	::= { ctrlGrpAmpsEntry  19 }
	
ctrlGrpAmpsHVolts OBJECT-TYPE
	SYNTAX  Gauge32
	UNITS "Volts (rms)"
	MAX-ACCESS  read-only
	STATUS current
	DESCRIPTION "Volts Group H"
	::= { ctrlGrpAmpsEntry  20 }
	
ctrlGrpAmpsI OBJECT-TYPE
	SYNTAX  Gauge32
	UNITS "0.1 Amps (rms)"
	MAX-ACCESS  read-only
	STATUS current
	DESCRIPTION "DeciAmps Group I"
	::= { ctrlGrpAmpsEntry  21 }
	
ctrlGrpAmpsJ OBJECT-TYPE
	SYNTAX  Gauge32
	UNITS "0.1 Amps (rms)"
	MAX-ACCESS  read-only
	STATUS current
	DESCRIPTION "DeciAmps Group J"
	::= { ctrlGrpAmpsEntry  22 }
	
ctrlGrpAmpsK OBJECT-TYPE
	SYNTAX  Gauge32
	UNITS "0.1 Amps (rms)"
	MAX-ACCESS  read-only
	STATUS current
	DESCRIPTION "DeciAmps Group K"
	::= { ctrlGrpAmpsEntry  23 }
	
ctrlGrpAmpsL OBJECT-TYPE
	SYNTAX  Gauge32
	UNITS "0.1 Amps (rms)"
	MAX-ACCESS  read-only
	STATUS current
	DESCRIPTION "DeciAmps Group L"
	::= { ctrlGrpAmpsEntry  24 }
	
ctrlGrpAmpsM OBJECT-TYPE
	SYNTAX  Gauge32
	UNITS "0.1 Amps (rms)"
	MAX-ACCESS  read-only
	STATUS current
	DESCRIPTION "DeciAmps Group M"
	::= { ctrlGrpAmpsEntry  25 }
	
ctrlGrpAmpsN OBJECT-TYPE
	SYNTAX  Gauge32
	UNITS "0.1 Amps (rms)"
	MAX-ACCESS  read-only
	STATUS current
	DESCRIPTION "DeciAmps Group N"
	::= { ctrlGrpAmpsEntry  26 }
	
ctrlGrpAmpsO OBJECT-TYPE
	SYNTAX  Gauge32
	UNITS "0.1 Amps (rms)"
	MAX-ACCESS  read-only
	STATUS current
	DESCRIPTION "DeciAmps Group O"
	::= { ctrlGrpAmpsEntry  27 }
	
ctrlGrpAmpsP OBJECT-TYPE
	SYNTAX  Gauge32
	UNITS "0.1 Amps (rms)"
	MAX-ACCESS  read-only
	STATUS current
	DESCRIPTION "DeciAmps Group P"
	::= { ctrlGrpAmpsEntry  28 }
	
ctrlGrpAmpsIVolts OBJECT-TYPE
	SYNTAX  Gauge32
	UNITS "Volts (rms)"
	MAX-ACCESS  read-only
	STATUS current
	DESCRIPTION "Volts Group I"
	::= { ctrlGrpAmpsEntry  29 }
	
ctrlGrpAmpsJVolts OBJECT-TYPE
	SYNTAX  Gauge32
	UNITS "Volts (rms)"
	MAX-ACCESS  read-only
	STATUS current
	DESCRIPTION "Volts Group J"
	::= { ctrlGrpAmpsEntry  30 }
	
ctrlGrpAmpsKVolts OBJECT-TYPE
	SYNTAX  Gauge32
	UNITS "Volts (rms)"
	MAX-ACCESS  read-only
	STATUS current
	DESCRIPTION "Volts Group K"
	::= { ctrlGrpAmpsEntry  31 }
	
ctrlGrpAmpsLVolts OBJECT-TYPE
	SYNTAX  Gauge32
	UNITS "Volts (rms)"
	MAX-ACCESS  read-only
	STATUS current
	DESCRIPTION "Volts Group L"
	::= { ctrlGrpAmpsEntry  32 }
	
ctrlGrpAmpsMVolts OBJECT-TYPE
	SYNTAX  Gauge32
	UNITS "Volts (rms)"
	MAX-ACCESS  read-only
	STATUS current
	DESCRIPTION "Volts Group M"
	::= { ctrlGrpAmpsEntry  33 }
	
ctrlGrpAmpsNVolts OBJECT-TYPE
	SYNTAX  Gauge32
	UNITS "Volts (rms)"
	MAX-ACCESS  read-only
	STATUS current
	DESCRIPTION "Volts Group N"
	::= { ctrlGrpAmpsEntry  34 }
	
ctrlGrpAmpsOVolts OBJECT-TYPE
	SYNTAX  Gauge32
	UNITS "Volts (rms)"
	MAX-ACCESS  read-only
	STATUS current
	DESCRIPTION "Volts Group O"
	::= { ctrlGrpAmpsEntry  35 }
	
ctrlGrpAmpsPVolts OBJECT-TYPE
	SYNTAX  Gauge32
	UNITS "Volts (rms)"
	MAX-ACCESS  read-only
	STATUS current
	DESCRIPTION "Volts Group P"
	::= { ctrlGrpAmpsEntry  36 }
	
ctrlOutletEntry OBJECT-TYPE
	SYNTAX  CtrlOutletEntry
	MAX-ACCESS  not-accessible
	STATUS current
	DESCRIPTION 
		"Entry in the control outlet table: each entry contains
an index (ctrlOutletIndex) and other sensor details"
	INDEX { ctrlOutletIndex }
	::= { ctrlOutletTable 1 }

CtrlOutletEntry ::= SEQUENCE {
	ctrlOutletIndex		INTEGER,
	ctrlOutletName		DisplayString,
	ctrlOutletStatus		Gauge32,
	ctrlOutletFeedback		Gauge32,
	ctrlOutletPending		Gauge32,
	ctrlOutletDeciAmps		Gauge32,
	ctrlOutletGroup		DisplayString,
	ctrlOutletUpDelay		Gauge32,
	ctrlOutletDwnDelay		Gauge32,
	ctrlOutletRbtDuration		Gauge32,
	ctrlOutletURL		DisplayString,
	ctrlOutletPOAAction		Gauge32,
	ctrlOutletPOADelay		Gauge32,
	ctrlOutletkWattHrs		Gauge32,
	ctrlOutletPower		Gauge32,
	ctrlOutletRbtDelay		Gauge32,
	ctrlOutletStatusTime		Gauge32
}

ctrlOutletIndex OBJECT-TYPE
	SYNTAX  INTEGER(1..100)
	MAX-ACCESS  not-accessible
	STATUS current
	DESCRIPTION "Outlet Number"
	::= { ctrlOutletEntry  1 }
	
ctrlOutletName OBJECT-TYPE
	SYNTAX  DisplayString
	MAX-ACCESS  read-write
	STATUS current
	DESCRIPTION "Outlet Friendly Name"
	::= { ctrlOutletEntry  2 }
	
ctrlOutletStatus OBJECT-TYPE
	SYNTAX  Gauge32
	MAX-ACCESS  read-write
	STATUS current
	DESCRIPTION "Current Outlet Status: 0 = Off, 1 = On | Outlet Action Write: 0 = Cancel Pending, 1 = On, 2 = On Delayed, 3 = Off Immediate, 4 = Off Delayed, 5 = Reboot, 6 = Reboot Delayed, 7 = Clear kWh (POA units only)"
	::= { ctrlOutletEntry  3 }
	
ctrlOutletFeedback OBJECT-TYPE
	SYNTAX  Gauge32
	MAX-ACCESS  read-only
	STATUS current
	DESCRIPTION "Outlet Feedback Value, should be equal to status"
	::= { ctrlOutletEntry  4 }
	
ctrlOutletPending OBJECT-TYPE
	SYNTAX  Gauge32
	MAX-ACCESS  read-write
	STATUS current
	DESCRIPTION "Outlet Status Read to change to: 0 = Off, 1 = On | Outlet Action Write: 0 = Cancel Pending, 1 = On, 2 = On Delayed, 3 = Off Immediate, 4 = Off Delayed, 5 = Reboot, 6 = Reboot Delayed, 7 = Clear kWh (POA units only)"
	::= { ctrlOutletEntry  5 }
	
ctrlOutletDeciAmps OBJECT-TYPE
	SYNTAX  Gauge32
	UNITS "0.1 Amps (rms)"
	MAX-ACCESS  read-only
	STATUS current
	DESCRIPTION "Outlet DeciAmps reading"
	::= { ctrlOutletEntry  6 }
	
ctrlOutletGroup OBJECT-TYPE
	SYNTAX  DisplayString
	MAX-ACCESS  read-only
	STATUS current
	DESCRIPTION "Outlet Group (A to G)"
	::= { ctrlOutletEntry  7 }
	
ctrlOutletUpDelay OBJECT-TYPE
	SYNTAX  Gauge32
	UNITS "seconds"
	MAX-ACCESS  read-write
	STATUS current
	DESCRIPTION "Outlet Power Up Delay"
	::= { ctrlOutletEntry  8 }
	
ctrlOutletDwnDelay OBJECT-TYPE
	SYNTAX  Gauge32
	UNITS "seconds"
	MAX-ACCESS  read-write
	STATUS current
	DESCRIPTION "Outlet Power Down Delay"
	::= { ctrlOutletEntry  9 }
	
ctrlOutletRbtDuration OBJECT-TYPE
	SYNTAX  Gauge32
	UNITS "seconds"
	MAX-ACCESS  read-write
	STATUS current
	DESCRIPTION "Outlet Reboot Duration"
	::= { ctrlOutletEntry  10 }
	
ctrlOutletURL OBJECT-TYPE
	SYNTAX  DisplayString
	MAX-ACCESS  read-write
	STATUS current
	DESCRIPTION "Outlet URL"
	::= { ctrlOutletEntry  11 }
	
ctrlOutletPOAAction OBJECT-TYPE
	SYNTAX  Gauge32
	MAX-ACCESS  read-write
	STATUS current
	DESCRIPTION "POA Action: 1 = Off, 2 = On, 3 = Last, 0 = POA not supported on this unit type"
	::= { ctrlOutletEntry  12 }
	
ctrlOutletPOADelay OBJECT-TYPE
	SYNTAX  Gauge32
	UNITS "seconds"
	MAX-ACCESS  read-write
	STATUS current
	DESCRIPTION "POA Delay"
	::= { ctrlOutletEntry  13 }
	
ctrlOutletkWattHrs OBJECT-TYPE
	SYNTAX  Gauge32
	UNITS "kWh"
	MAX-ACCESS  read-only
	STATUS current
	DESCRIPTION "Current Reading for kWatt-Hours"
	::= { ctrlOutletEntry  14 }
	
ctrlOutletPower OBJECT-TYPE
	SYNTAX  Gauge32
	UNITS "Watts"
	MAX-ACCESS  read-only
	STATUS current
	DESCRIPTION "Current reading for Power"
	::= { ctrlOutletEntry  15 }
	
ctrlOutletRbtDelay OBJECT-TYPE
	SYNTAX  Gauge32
	UNITS "seconds"
	MAX-ACCESS  read-write
	STATUS current
	DESCRIPTION "Outlet Reboot Delay"
	::= { ctrlOutletEntry  16 }
	
ctrlOutletStatusTime OBJECT-TYPE
	SYNTAX  Gauge32
	UNITS "seconds"
	MAX-ACCESS  read-only
	STATUS current
	DESCRIPTION "Seconds Since Outlet Last Changed Its Status"
	::= { ctrlOutletEntry  17 }
	
dewPointSensorEntry OBJECT-TYPE
	SYNTAX  DewPointSensorEntry
	MAX-ACCESS  not-accessible
	STATUS current
	DESCRIPTION 
		"Entry in the dew point sensor table: each entry contains
an index (dewPointSensorIndex) and other sensor details"
	INDEX { dewPointSensorIndex }
	::= { dewPointSensorTable 1 }

DewPointSensorEntry ::= SEQUENCE {
	dewPointSensorIndex		INTEGER,
	dewPointSensorSerial		DisplayString,
	dewPointSensorName		DisplayString,
	dewPointSensorAvail		Gauge32,
	dewPointSensorTempC		INTEGER,
	dewPointSensorTempF		INTEGER,
	dewPointSensorHumidity		INTEGER,
	dewPointSensorDewPointC		INTEGER,
	dewPointSensorDewPointF		INTEGER
}

dewPointSensorIndex OBJECT-TYPE
	SYNTAX  INTEGER(1..100)
	MAX-ACCESS  not-accessible
	STATUS current
	DESCRIPTION "Table entry index value"
	::= { dewPointSensorEntry  1 }
	
dewPointSensorSerial OBJECT-TYPE
	SYNTAX  DisplayString
	MAX-ACCESS  read-only
	STATUS current
	DESCRIPTION "Serial Number"
	::= { dewPointSensorEntry  2 }
	
dewPointSensorName OBJECT-TYPE
	SYNTAX  DisplayString
	MAX-ACCESS  read-only
	STATUS current
	DESCRIPTION "Friendly Name"
	::= { dewPointSensorEntry  3 }
	
dewPointSensorAvail OBJECT-TYPE
	SYNTAX  Gauge32
	MAX-ACCESS  read-only
	STATUS current
	DESCRIPTION "Is device currently plugged in?"
	::= { dewPointSensorEntry  4 }
	
dewPointSensorTempC OBJECT-TYPE
	SYNTAX  INTEGER(-50..100)
	UNITS "Degrees Celsius"
	MAX-ACCESS  read-only
	STATUS current
	DESCRIPTION "Temperature reading in C"
	::= { dewPointSensorEntry  5 }
	
dewPointSensorTempF OBJECT-TYPE
	SYNTAX  INTEGER(-58..212)
	UNITS "Degrees Fahrenheit"
	MAX-ACCESS  read-only
	STATUS current
	DESCRIPTION "Temperature reading in F"
	::= { dewPointSensorEntry  6 }
	
dewPointSensorHumidity OBJECT-TYPE
	SYNTAX  INTEGER(0..100)
	UNITS "%"
	MAX-ACCESS  read-only
	STATUS current
	DESCRIPTION "Humidity reading"
	::= { dewPointSensorEntry  7 }
	
dewPointSensorDewPointC OBJECT-TYPE
	SYNTAX  INTEGER(-50..100)
	UNITS "Degrees Celsius"
	MAX-ACCESS  read-only
	STATUS current
	DESCRIPTION "Dew point reading in C"
	::= { dewPointSensorEntry  8 }
	
dewPointSensorDewPointF OBJECT-TYPE
	SYNTAX  INTEGER(-58..212)
	UNITS "Degrees Fahrenheit"
	MAX-ACCESS  read-only
	STATUS current
	DESCRIPTION "Dew point reading in F"
	::= { dewPointSensorEntry  9 }
	
digitalSensorEntry OBJECT-TYPE
	SYNTAX  DigitalSensorEntry
	MAX-ACCESS  not-accessible
	STATUS current
	DESCRIPTION 
		"Entry in the digital sensor table: each entry contains
an index (digitalSensorIndex) and other sensor details"
	INDEX { digitalSensorIndex }
	::= { digitalSensorTable 1 }

DigitalSensorEntry ::= SEQUENCE {
	digitalSensorIndex		INTEGER,
	digitalSensorSerial		DisplayString,
	digitalSensorName		DisplayString,
	digitalSensorAvail		Gauge32,
	digitalSensorDigital		INTEGER
}

digitalSensorIndex OBJECT-TYPE
	SYNTAX  INTEGER(1..100)
	MAX-ACCESS  not-accessible
	STATUS current
	DESCRIPTION "Table entry index value"
	::= { digitalSensorEntry  1 }
	
digitalSensorSerial OBJECT-TYPE
	SYNTAX  DisplayString
	MAX-ACCESS  read-only
	STATUS current
	DESCRIPTION "Serial Number"
	::= { digitalSensorEntry  2 }
	
digitalSensorName OBJECT-TYPE
	SYNTAX  DisplayString
	MAX-ACCESS  read-only
	STATUS current
	DESCRIPTION "Friendly Name"
	::= { digitalSensorEntry  3 }
	
digitalSensorAvail OBJECT-TYPE
	SYNTAX  Gauge32
	MAX-ACCESS  read-only
	STATUS current
	DESCRIPTION "Is device currently plugged in?"
	::= { digitalSensorEntry  4 }
	
digitalSensorDigital OBJECT-TYPE
	SYNTAX  INTEGER(0..100)
	MAX-ACCESS  read-only
	STATUS current
	DESCRIPTION "Digital sensor status"
	::= { digitalSensorEntry  5 }
	
dstsEntry OBJECT-TYPE
	SYNTAX  DstsEntry
	MAX-ACCESS  not-accessible
	STATUS current
	DESCRIPTION 
		"Entry in the DSTS table: each entry contains
an index (dstsIndex) and other details"
	INDEX { dstsIndex }
	::= { dstsTable 1 }

DstsEntry ::= SEQUENCE {
	dstsIndex		INTEGER,
	dstsSerial		DisplayString,
	dstsName		DisplayString,
	dstsAvail		Gauge32,
	dstsVoltsA		Gauge32,
	dstsDeciAmpsA		Gauge32,
	dstsVoltsB		Gauge32,
	dstsDeciAmpsB		Gauge32,
	dstsSourceAActive		Gauge32,
	dstsSourceBActive		Gauge32,
	dstsPowerStatusA		Gauge32,
	dstsPowerStatusB		Gauge32,
	dstsSourceATempC		INTEGER,
	dstsSourceBTempC		INTEGER
}

dstsIndex OBJECT-TYPE
	SYNTAX  INTEGER(1..1)
	MAX-ACCESS  not-accessible
	STATUS current
	DESCRIPTION "Table entry index value"
	::= { dstsEntry  1 }
	
dstsSerial OBJECT-TYPE
	SYNTAX  DisplayString
	MAX-ACCESS  read-only
	STATUS current
	DESCRIPTION "Serial Number"
	::= { dstsEntry  2 }
	
dstsName OBJECT-TYPE
	SYNTAX  DisplayString
	MAX-ACCESS  read-only
	STATUS current
	DESCRIPTION "Friendly Name"
	::= { dstsEntry  3 }
	
dstsAvail OBJECT-TYPE
	SYNTAX  Gauge32
	MAX-ACCESS  read-only
	STATUS current
	DESCRIPTION "Is device currently plugged in?"
	::= { dstsEntry  4 }
	
dstsVoltsA OBJECT-TYPE
	SYNTAX  Gauge32
	UNITS "Volts (rms)"
	MAX-ACCESS  read-only
	STATUS current
	DESCRIPTION "RMS Voltage of Side A"
	::= { dstsEntry  5 }
	
dstsDeciAmpsA OBJECT-TYPE
	SYNTAX  Gauge32
	UNITS "0.1 Amps (rms)"
	MAX-ACCESS  read-only
	STATUS current
	DESCRIPTION "RMS Current of Side A in deciamps"
	::= { dstsEntry  6 }
	
dstsVoltsB OBJECT-TYPE
	SYNTAX  Gauge32
	UNITS "Volts (rms)"
	MAX-ACCESS  read-only
	STATUS current
	DESCRIPTION "RMS Voltage of Side B"
	::= { dstsEntry  7 }
	
dstsDeciAmpsB OBJECT-TYPE
	SYNTAX  Gauge32
	UNITS "0.1 Amps (rms)"
	MAX-ACCESS  read-only
	STATUS current
	DESCRIPTION "RMS Current of Side B in deciamps"
	::= { dstsEntry  8 }
	
dstsSourceAActive OBJECT-TYPE
	SYNTAX  Gauge32
	MAX-ACCESS  read-only
	STATUS current
	DESCRIPTION "If 99, source A active"
	::= { dstsEntry  9 }
	
dstsSourceBActive OBJECT-TYPE
	SYNTAX  Gauge32
	MAX-ACCESS  read-only
	STATUS current
	DESCRIPTION "If 99, source B active"
	::= { dstsEntry  10 }
	
dstsPowerStatusA OBJECT-TYPE
	SYNTAX  Gauge32
	MAX-ACCESS  read-only
	STATUS current
	DESCRIPTION "Power Quality of source A"
	::= { dstsEntry  11 }
	
dstsPowerStatusB OBJECT-TYPE
	SYNTAX  Gauge32
	MAX-ACCESS  read-only
	STATUS current
	DESCRIPTION "Power Quality of Source B"
	::= { dstsEntry  12 }
	
dstsSourceATempC OBJECT-TYPE
	SYNTAX  INTEGER(-20..50)
	UNITS "Degrees Celsius"
	MAX-ACCESS  read-only
	STATUS current
	DESCRIPTION "Current reading for Source A temp in C"
	::= { dstsEntry  13 }
	
dstsSourceBTempC OBJECT-TYPE
	SYNTAX  INTEGER(-20..50)
	UNITS "Degrees Celsius"
	MAX-ACCESS  read-only
	STATUS current
	DESCRIPTION "Current reading for Source B temp in C"
	::= { dstsEntry  14 }
	
cpmSensorEntry OBJECT-TYPE
	SYNTAX  CpmSensorEntry
	MAX-ACCESS  not-accessible
	STATUS current
	DESCRIPTION 
		"Entry in the city power sensor table: each entry contains
an index (cpmSensorIndex) and other sensor details"
	INDEX { cpmSensorIndex }
	::= { cpmSensorTable 1 }

CpmSensorEntry ::= SEQUENCE {
	cpmSensorIndex		INTEGER,
	cpmSensorSerial		DisplayString,
	cpmSensorName		DisplayString,
	cpmSensorAvail		Gauge32,
	cpmSensorStatus		INTEGER
}

cpmSensorIndex OBJECT-TYPE
	SYNTAX  INTEGER(1..100)
	MAX-ACCESS  not-accessible
	STATUS current
	DESCRIPTION "Table entry index value"
	::= { cpmSensorEntry  1 }
	
cpmSensorSerial OBJECT-TYPE
	SYNTAX  DisplayString
	MAX-ACCESS  read-only
	STATUS current
	DESCRIPTION "Serial Number"
	::= { cpmSensorEntry  2 }
	
cpmSensorName OBJECT-TYPE
	SYNTAX  DisplayString
	MAX-ACCESS  read-only
	STATUS current
	DESCRIPTION "Friendly Name"
	::= { cpmSensorEntry  3 }
	
cpmSensorAvail OBJECT-TYPE
	SYNTAX  Gauge32
	MAX-ACCESS  read-only
	STATUS current
	DESCRIPTION "Is device currently plugged in?"
	::= { cpmSensorEntry  4 }
	
cpmSensorStatus OBJECT-TYPE
	SYNTAX  INTEGER(0..100)
	MAX-ACCESS  read-only
	STATUS current
	DESCRIPTION "City Power sensor status"
	::= { cpmSensorEntry  5 }
	
smokeAlarmEntry OBJECT-TYPE
	SYNTAX  SmokeAlarmEntry
	MAX-ACCESS  not-accessible
	STATUS current
	DESCRIPTION 
		"Entry in the smoke alarm sensor table: each entry contains
an index (smokeAlarmIndex) and other sensor details"
	INDEX { smokeAlarmIndex }
	::= { smokeAlarmTable 1 }

SmokeAlarmEntry ::= SEQUENCE {
	smokeAlarmIndex		INTEGER,
	smokeAlarmSerial		DisplayString,
	smokeAlarmName		DisplayString,
	smokeAlarmAvail		Gauge32,
	smokeAlarmStatus		INTEGER
}

smokeAlarmIndex OBJECT-TYPE
	SYNTAX  INTEGER(1..100)
	MAX-ACCESS  not-accessible
	STATUS current
	DESCRIPTION "Table entry index value"
	::= { smokeAlarmEntry  1 }
	
smokeAlarmSerial OBJECT-TYPE
	SYNTAX  DisplayString
	MAX-ACCESS  read-only
	STATUS current
	DESCRIPTION "Serial Number"
	::= { smokeAlarmEntry  2 }
	
smokeAlarmName OBJECT-TYPE
	SYNTAX  DisplayString
	MAX-ACCESS  read-only
	STATUS current
	DESCRIPTION "Friendly Name"
	::= { smokeAlarmEntry  3 }
	
smokeAlarmAvail OBJECT-TYPE
	SYNTAX  Gauge32
	MAX-ACCESS  read-only
	STATUS current
	DESCRIPTION "Is device currently plugged in?"
	::= { smokeAlarmEntry  4 }
	
smokeAlarmStatus OBJECT-TYPE
	SYNTAX  INTEGER(0..100)
	MAX-ACCESS  read-only
	STATUS current
	DESCRIPTION "Smoke alarm status"
	::= { smokeAlarmEntry  5 }
	
neg48VdcSensorEntry OBJECT-TYPE
	SYNTAX  Neg48VdcSensorEntry
	MAX-ACCESS  not-accessible
	STATUS current
	DESCRIPTION 
		"Entry in the -48Vdc sensor table: each entry contains
an index (neg48VdcSensorIndex) and other sensor details"
	INDEX { neg48VdcSensorIndex }
	::= { neg48VdcSensorTable 1 }

Neg48VdcSensorEntry ::= SEQUENCE {
	neg48VdcSensorIndex		INTEGER,
	neg48VdcSensorSerial		DisplayString,
	neg48VdcSensorName		DisplayString,
	neg48VdcSensorAvail		Gauge32,
	neg48VdcSensorVoltage		INTEGER
}

neg48VdcSensorIndex OBJECT-TYPE
	SYNTAX  INTEGER(1..100)
	MAX-ACCESS  not-accessible
	STATUS current
	DESCRIPTION "Table entry index value"
	::= { neg48VdcSensorEntry  1 }
	
neg48VdcSensorSerial OBJECT-TYPE
	SYNTAX  DisplayString
	MAX-ACCESS  read-only
	STATUS current
	DESCRIPTION "Serial Number"
	::= { neg48VdcSensorEntry  2 }
	
neg48VdcSensorName OBJECT-TYPE
	SYNTAX  DisplayString
	MAX-ACCESS  read-only
	STATUS current
	DESCRIPTION "Friendly Name"
	::= { neg48VdcSensorEntry  3 }
	
neg48VdcSensorAvail OBJECT-TYPE
	SYNTAX  Gauge32
	MAX-ACCESS  read-only
	STATUS current
	DESCRIPTION "Is device currently plugged in?"
	::= { neg48VdcSensorEntry  4 }
	
neg48VdcSensorVoltage OBJECT-TYPE
	SYNTAX  INTEGER(-100..10)
	UNITS "Volts"
	MAX-ACCESS  read-only
	STATUS current
	DESCRIPTION "-48Vdc Sensor value"
	::= { neg48VdcSensorEntry  5 }
	
pos30VdcSensorEntry OBJECT-TYPE
	SYNTAX  Pos30VdcSensorEntry
	MAX-ACCESS  not-accessible
	STATUS current
	DESCRIPTION 
		"Entry in the 30Vdc sensor table: each entry contains
an index (pos30VdcSensorIndex) and other sensor details"
	INDEX { pos30VdcSensorIndex }
	::= { pos30VdcSensorTable 1 }

Pos30VdcSensorEntry ::= SEQUENCE {
	pos30VdcSensorIndex		INTEGER,
	pos30VdcSensorSerial		DisplayString,
	pos30VdcSensorName		DisplayString,
	pos30VdcSensorAvail		Gauge32,
	pos30VdcSensorVoltage		INTEGER
}

pos30VdcSensorIndex OBJECT-TYPE
	SYNTAX  INTEGER(1..100)
	MAX-ACCESS  not-accessible
	STATUS current
	DESCRIPTION "Table entry index value"
	::= { pos30VdcSensorEntry  1 }
	
pos30VdcSensorSerial OBJECT-TYPE
	SYNTAX  DisplayString
	MAX-ACCESS  read-only
	STATUS current
	DESCRIPTION "Serial Number"
	::= { pos30VdcSensorEntry  2 }
	
pos30VdcSensorName OBJECT-TYPE
	SYNTAX  DisplayString
	MAX-ACCESS  read-only
	STATUS current
	DESCRIPTION "Friendly Name"
	::= { pos30VdcSensorEntry  3 }
	
pos30VdcSensorAvail OBJECT-TYPE
	SYNTAX  Gauge32
	MAX-ACCESS  read-only
	STATUS current
	DESCRIPTION "Is device currently plugged in?"
	::= { pos30VdcSensorEntry  4 }
	
pos30VdcSensorVoltage OBJECT-TYPE
	SYNTAX  INTEGER(-10..100)
	UNITS "Volts"
	MAX-ACCESS  read-only
	STATUS current
	DESCRIPTION "30Vdc Sensor value"
	::= { pos30VdcSensorEntry  5 }
	
analogSensorEntry OBJECT-TYPE
	SYNTAX  AnalogSensorEntry
	MAX-ACCESS  not-accessible
	STATUS current
	DESCRIPTION 
		"Entry in the analog input table: each entry contains
an index (analogSensorIndex) and other sensor details"
	INDEX { analogSensorIndex }
	::= { analogSensorTable 1 }

AnalogSensorEntry ::= SEQUENCE {
	analogSensorIndex		INTEGER,
	analogSensorSerial		DisplayString,
	analogSensorName		DisplayString,
	analogSensorAvail		Gauge32,
	analogSensorAnalog		INTEGER
}

analogSensorIndex OBJECT-TYPE
	SYNTAX  INTEGER(1..100)
	MAX-ACCESS  not-accessible
	STATUS current
	DESCRIPTION "Table entry index value"
	::= { analogSensorEntry  1 }
	
analogSensorSerial OBJECT-TYPE
	SYNTAX  DisplayString
	MAX-ACCESS  read-only
	STATUS current
	DESCRIPTION "Serial Number"
	::= { analogSensorEntry  2 }
	
analogSensorName OBJECT-TYPE
	SYNTAX  DisplayString
	MAX-ACCESS  read-only
	STATUS current
	DESCRIPTION "Friendly Name"
	::= { analogSensorEntry  3 }
	
analogSensorAvail OBJECT-TYPE
	SYNTAX  Gauge32
	MAX-ACCESS  read-only
	STATUS current
	DESCRIPTION "Is device currently plugged in?"
	::= { analogSensorEntry  4 }
	
analogSensorAnalog OBJECT-TYPE
	SYNTAX  INTEGER(0..100)
	MAX-ACCESS  read-only
	STATUS current
	DESCRIPTION "Analog Sensor Value"
	::= { analogSensorEntry  5 }
	
ctrl3ChIECEntry OBJECT-TYPE
	SYNTAX  Ctrl3ChIECEntry
	MAX-ACCESS  not-accessible
	STATUS current
	DESCRIPTION 
		"Entry in the 3 phase outlet control table: each entry contains
an index (ctrl3ChIECIndex) and other outlet control monitoring details"
	INDEX { ctrl3ChIECIndex }
	::= { ctrl3ChIECTable 1 }

Ctrl3ChIECEntry ::= SEQUENCE {
	ctrl3ChIECIndex		INTEGER,
	ctrl3ChIECSerial		DisplayString,
	ctrl3ChIECName		DisplayString,
	ctrl3ChIECAvail		Gauge32,
	ctrl3ChIECkWattHrsA		Gauge32,
	ctrl3ChIECVoltsA		Gauge32,
	ctrl3ChIECVoltPeakA		Gauge32,
	ctrl3ChIECDeciAmpsA		Gauge32,
	ctrl3ChIECDeciAmpsPeakA		Gauge32,
	ctrl3ChIECRealPowerA		Gauge32,
	ctrl3ChIECApparentPowerA		Gauge32,
	ctrl3ChIECPowerFactorA		INTEGER,
	ctrl3ChIECkWattHrsB		Gauge32,
	ctrl3ChIECVoltsB		Gauge32,
	ctrl3ChIECVoltPeakB		Gauge32,
	ctrl3ChIECDeciAmpsB		Gauge32,
	ctrl3ChIECDeciAmpsPeakB		Gauge32,
	ctrl3ChIECRealPowerB		Gauge32,
	ctrl3ChIECApparentPowerB		Gauge32,
	ctrl3ChIECPowerFactorB		INTEGER,
	ctrl3ChIECkWattHrsC		Gauge32,
	ctrl3ChIECVoltsC		Gauge32,
	ctrl3ChIECVoltPeakC		Gauge32,
	ctrl3ChIECDeciAmpsC		Gauge32,
	ctrl3ChIECDeciAmpsPeakC		Gauge32,
	ctrl3ChIECRealPowerC		Gauge32,
	ctrl3ChIECApparentPowerC		Gauge32,
	ctrl3ChIECPowerFactorC		INTEGER,
	ctrl3ChIECkWattHrsTotal		Gauge32,
	ctrl3ChIECRealPowerTotal		Gauge32
}

ctrl3ChIECIndex OBJECT-TYPE
	SYNTAX  INTEGER(1..100)
	MAX-ACCESS  not-accessible
	STATUS current
	DESCRIPTION "Table entry index value"
	::= { ctrl3ChIECEntry  1 }
	
ctrl3ChIECSerial OBJECT-TYPE
	SYNTAX  DisplayString
	MAX-ACCESS  read-only
	STATUS current
	DESCRIPTION "Serial Number"
	::= { ctrl3ChIECEntry  2 }
	
ctrl3ChIECName OBJECT-TYPE
	SYNTAX  DisplayString
	MAX-ACCESS  read-only
	STATUS current
	DESCRIPTION "Friendly Name"
	::= { ctrl3ChIECEntry  3 }
	
ctrl3ChIECAvail OBJECT-TYPE
	SYNTAX  Gauge32
	MAX-ACCESS  read-only
	STATUS current
	DESCRIPTION "Is device currently plugged in?"
	::= { ctrl3ChIECEntry  4 }
	
ctrl3ChIECkWattHrsA OBJECT-TYPE
	SYNTAX  Gauge32
	UNITS "kWh"
	MAX-ACCESS  read-only
	STATUS current
	DESCRIPTION "Current Reading for kWatt-Hours (Phase A)"
	::= { ctrl3ChIECEntry  5 }
	
ctrl3ChIECVoltsA OBJECT-TYPE
	SYNTAX  Gauge32
	UNITS "Volts (rms)"
	MAX-ACCESS  read-only
	STATUS current
	DESCRIPTION "Current reading for Volts (Phase A)"
	::= { ctrl3ChIECEntry  6 }
	
ctrl3ChIECVoltPeakA OBJECT-TYPE
	SYNTAX  Gauge32
	UNITS "Volts (rms)"
	MAX-ACCESS  read-only
	STATUS current
	DESCRIPTION "Current reading for Peak-Volts (Phase A)"
	::= { ctrl3ChIECEntry  7 }
	
ctrl3ChIECDeciAmpsA OBJECT-TYPE
	SYNTAX  Gauge32
	UNITS "0.1 Amps (rms)"
	MAX-ACCESS  read-only
	STATUS current
	DESCRIPTION "Current reading for DeciAmps (Phase A)"
	::= { ctrl3ChIECEntry  8 }
	
ctrl3ChIECDeciAmpsPeakA OBJECT-TYPE
	SYNTAX  Gauge32
	UNITS "0.1 Amps (rms)"
	MAX-ACCESS  read-only
	STATUS current
	DESCRIPTION "Current reading for Peak-DeciAmps (Phase A)"
	::= { ctrl3ChIECEntry  9 }
	
ctrl3ChIECRealPowerA OBJECT-TYPE
	SYNTAX  Gauge32
	UNITS "Watts"
	MAX-ACCESS  read-only
	STATUS current
	DESCRIPTION "Current reading for Real Power (Phase A)"
	::= { ctrl3ChIECEntry  10 }
	
ctrl3ChIECApparentPowerA OBJECT-TYPE
	SYNTAX  Gauge32
	UNITS "Volt-Amps"
	MAX-ACCESS  read-only
	STATUS current
	DESCRIPTION "Current reading for Apparent Power (Phase A)"
	::= { ctrl3ChIECEntry  11 }
	
ctrl3ChIECPowerFactorA OBJECT-TYPE
	SYNTAX  INTEGER(0..100)
	UNITS "%"
	MAX-ACCESS  read-only
	STATUS current
	DESCRIPTION "Current reading for Power Factor (Phase A)"
	::= { ctrl3ChIECEntry  12 }
	
ctrl3ChIECkWattHrsB OBJECT-TYPE
	SYNTAX  Gauge32
	UNITS "kWh"
	MAX-ACCESS  read-only
	STATUS current
	DESCRIPTION "Current Reading for kWatt-Hours (Phase B)"
	::= { ctrl3ChIECEntry  13 }
	
ctrl3ChIECVoltsB OBJECT-TYPE
	SYNTAX  Gauge32
	UNITS "Volts (rms)"
	MAX-ACCESS  read-only
	STATUS current
	DESCRIPTION "Current reading for Volts (Phase B)"
	::= { ctrl3ChIECEntry  14 }
	
ctrl3ChIECVoltPeakB OBJECT-TYPE
	SYNTAX  Gauge32
	UNITS "Volts (rms)"
	MAX-ACCESS  read-only
	STATUS current
	DESCRIPTION "Current reading for Peak-Volts (Phase B)"
	::= { ctrl3ChIECEntry  15 }
	
ctrl3ChIECDeciAmpsB OBJECT-TYPE
	SYNTAX  Gauge32
	UNITS "0.1 Amps (rms)"
	MAX-ACCESS  read-only
	STATUS current
	DESCRIPTION "Current reading for DeciAmps (Phase B)"
	::= { ctrl3ChIECEntry  16 }
	
ctrl3ChIECDeciAmpsPeakB OBJECT-TYPE
	SYNTAX  Gauge32
	UNITS "0.1 Amps (rms)"
	MAX-ACCESS  read-only
	STATUS current
	DESCRIPTION "Current reading for Peak-DeciAmps (Phase B)"
	::= { ctrl3ChIECEntry  17 }
	
ctrl3ChIECRealPowerB OBJECT-TYPE
	SYNTAX  Gauge32
	UNITS "Watts"
	MAX-ACCESS  read-only
	STATUS current
	DESCRIPTION "Current reading for Real Power (Phase B)"
	::= { ctrl3ChIECEntry  18 }
	
ctrl3ChIECApparentPowerB OBJECT-TYPE
	SYNTAX  Gauge32
	UNITS "Volt-Amps"
	MAX-ACCESS  read-only
	STATUS current
	DESCRIPTION "Current reading for Apparent Power (Phase B)"
	::= { ctrl3ChIECEntry  19 }
	
ctrl3ChIECPowerFactorB OBJECT-TYPE
	SYNTAX  INTEGER(0..100)
	UNITS "%"
	MAX-ACCESS  read-only
	STATUS current
	DESCRIPTION "Current reading for Power Factor (Phase B)"
	::= { ctrl3ChIECEntry  20 }
	
ctrl3ChIECkWattHrsC OBJECT-TYPE
	SYNTAX  Gauge32
	UNITS "kWh"
	MAX-ACCESS  read-only
	STATUS current
	DESCRIPTION "Current Reading for kWatt-Hours (Phase C)"
	::= { ctrl3ChIECEntry  21 }
	
ctrl3ChIECVoltsC OBJECT-TYPE
	SYNTAX  Gauge32
	UNITS "Volts (rms)"
	MAX-ACCESS  read-only
	STATUS current
	DESCRIPTION "Current reading for Volts (Phase C)"
	::= { ctrl3ChIECEntry  22 }
	
ctrl3ChIECVoltPeakC OBJECT-TYPE
	SYNTAX  Gauge32
	UNITS "Volts (rms)"
	MAX-ACCESS  read-only
	STATUS current
	DESCRIPTION "Current reading for Peak-Volts (Phase C)"
	::= { ctrl3ChIECEntry  23 }
	
ctrl3ChIECDeciAmpsC OBJECT-TYPE
	SYNTAX  Gauge32
	UNITS "0.1 Amps (rms)"
	MAX-ACCESS  read-only
	STATUS current
	DESCRIPTION "Current reading for DeciAmps (Phase C)"
	::= { ctrl3ChIECEntry  24 }
	
ctrl3ChIECDeciAmpsPeakC OBJECT-TYPE
	SYNTAX  Gauge32
	UNITS "0.1 Amps (rms)"
	MAX-ACCESS  read-only
	STATUS current
	DESCRIPTION "Current reading for Peak-DeciAmps (Phase C)"
	::= { ctrl3ChIECEntry  25 }
	
ctrl3ChIECRealPowerC OBJECT-TYPE
	SYNTAX  Gauge32
	UNITS "Watts"
	MAX-ACCESS  read-only
	STATUS current
	DESCRIPTION "Current reading for Real Power (Phase C)"
	::= { ctrl3ChIECEntry  26 }
	
ctrl3ChIECApparentPowerC OBJECT-TYPE
	SYNTAX  Gauge32
	UNITS "Volt-Amps"
	MAX-ACCESS  read-only
	STATUS current
	DESCRIPTION "Current reading for Apparent Power (Phase C)"
	::= { ctrl3ChIECEntry  27 }
	
ctrl3ChIECPowerFactorC OBJECT-TYPE
	SYNTAX  INTEGER(0..100)
	UNITS "%"
	MAX-ACCESS  read-only
	STATUS current
	DESCRIPTION "Current reading for Power Factor (Phase C)"
	::= { ctrl3ChIECEntry  28 }
	
ctrl3ChIECkWattHrsTotal OBJECT-TYPE
	SYNTAX  Gauge32
	UNITS "kWh"
	MAX-ACCESS  read-only
	STATUS current
	DESCRIPTION "Current Reading for kWatt-Hours (Total)"
	::= { ctrl3ChIECEntry  29 }
	
ctrl3ChIECRealPowerTotal OBJECT-TYPE
	SYNTAX  Gauge32
	UNITS "Watts"
	MAX-ACCESS  read-only
	STATUS current
	DESCRIPTION "Current reading for Watts (Total)"
	::= { ctrl3ChIECEntry  30 }
	
climateRelayEntry OBJECT-TYPE
	SYNTAX  ClimateRelayEntry
	MAX-ACCESS  not-accessible
	STATUS current
	DESCRIPTION 
		"Entry in the climate table: each entry contains
an index (climateRelayIndex) and other details"
	INDEX { climateRelayIndex }
	::= { climateRelayTable 1 }

ClimateRelayEntry ::= SEQUENCE {
	climateRelayIndex		INTEGER,
	climateRelaySerial		DisplayString,
	climateRelayName		DisplayString,
	climateRelayAvail		Gauge32,
	climateRelayTempC		INTEGER,
	climateRelayTempF		INTEGER,
	climateRelayIO1		INTEGER,
	climateRelayIO2		INTEGER,
	climateRelayIO3		INTEGER,
	climateRelayIO4		INTEGER,
	climateRelayIO5		INTEGER,
	climateRelayIO6		INTEGER
}

climateRelayIndex OBJECT-TYPE
	SYNTAX  INTEGER(1..1)
	MAX-ACCESS  not-accessible
	STATUS current
	DESCRIPTION "Table entry index value"
	::= { climateRelayEntry  1 }
	
climateRelaySerial OBJECT-TYPE
	SYNTAX  DisplayString
	MAX-ACCESS  read-only
	STATUS current
	DESCRIPTION "Serial Number"
	::= { climateRelayEntry  2 }
	
climateRelayName OBJECT-TYPE
	SYNTAX  DisplayString
	MAX-ACCESS  read-only
	STATUS current
	DESCRIPTION "Friendly Name"
	::= { climateRelayEntry  3 }
	
climateRelayAvail OBJECT-TYPE
	SYNTAX  Gauge32
	MAX-ACCESS  read-only
	STATUS current
	DESCRIPTION "Is device currently plugged in?"
	::= { climateRelayEntry  4 }
	
climateRelayTempC OBJECT-TYPE
	SYNTAX  INTEGER(-50..100)
	UNITS "Degrees Celsius"
	MAX-ACCESS  read-only
	STATUS current
	DESCRIPTION "Current reading for Temperature (C)"
	::= { climateRelayEntry  5 }
	
climateRelayTempF OBJECT-TYPE
	SYNTAX  INTEGER(-58..212)
	UNITS "Degress Fahrenheit"
	MAX-ACCESS  read-only
	STATUS current
	DESCRIPTION "Current reading for Temperature (F)"
	::= { climateRelayEntry  6 }
	
climateRelayIO1 OBJECT-TYPE
	SYNTAX  INTEGER(0..100)
	MAX-ACCESS  read-only
	STATUS current
	DESCRIPTION "Current reading for Analog Input 1"
	::= { climateRelayEntry  7 }
	
climateRelayIO2 OBJECT-TYPE
	SYNTAX  INTEGER(0..100)
	MAX-ACCESS  read-only
	STATUS current
	DESCRIPTION "Current reading for Analog Input 2"
	::= { climateRelayEntry  8 }
	
climateRelayIO3 OBJECT-TYPE
	SYNTAX  INTEGER(0..100)
	MAX-ACCESS  read-only
	STATUS current
	DESCRIPTION "Current reading for Analog Input 3"
	::= { climateRelayEntry  9 }
	
climateRelayIO4 OBJECT-TYPE
	SYNTAX  INTEGER(0..100)
	MAX-ACCESS  read-only
	STATUS current
	DESCRIPTION "Current reading for Analog Input 4"
	::= { climateRelayEntry  10 }
	
climateRelayIO5 OBJECT-TYPE
	SYNTAX  INTEGER(0..100)
	MAX-ACCESS  read-only
	STATUS current
	DESCRIPTION "Current reading for Analog Input 5"
	::= { climateRelayEntry  11 }
	
climateRelayIO6 OBJECT-TYPE
	SYNTAX  INTEGER(0..100)
	MAX-ACCESS  read-only
	STATUS current
	DESCRIPTION "Current reading for Analog Input 6"
	::= { climateRelayEntry  12 }
	
ctrlRelayEntry OBJECT-TYPE
	SYNTAX  CtrlRelayEntry
	MAX-ACCESS  not-accessible
	STATUS current
	DESCRIPTION 
		"Entry in the control relay table: each entry contains
an index (ctrlRelayIndex) and other sensor details"
	INDEX { ctrlRelayIndex }
	::= { ctrlRelayTable 1 }

CtrlRelayEntry ::= SEQUENCE {
	ctrlRelayIndex		INTEGER,
	ctrlRelayName		DisplayString,
	ctrlRelayState		Gauge32,
	ctrlRelayLatchingMode		Gauge32,
	ctrlRelayOverride		Gauge32,
	ctrlRelayAcknowledge		Gauge32
}

ctrlRelayIndex OBJECT-TYPE
	SYNTAX  INTEGER(1..100)
	MAX-ACCESS  not-accessible
	STATUS current
	DESCRIPTION "Relay Number"
	::= { ctrlRelayEntry  1 }
	
ctrlRelayName OBJECT-TYPE
	SYNTAX  DisplayString
	MAX-ACCESS  read-write
	STATUS current
	DESCRIPTION "Relay Friendly Name"
	::= { ctrlRelayEntry  2 }
	
ctrlRelayState OBJECT-TYPE
	SYNTAX  Gauge32
	MAX-ACCESS  read-only
	STATUS current
	DESCRIPTION "Current Relay Status: 0 = Off, 1 = On"
	::= { ctrlRelayEntry  3 }
	
ctrlRelayLatchingMode OBJECT-TYPE
	SYNTAX  Gauge32
	MAX-ACCESS  read-write
	STATUS current
	DESCRIPTION "Relay latching mode: 0 = Non-latching, 1 = Latching"
	::= { ctrlRelayEntry  4 }
	
ctrlRelayOverride OBJECT-TYPE
	SYNTAX  Gauge32
	MAX-ACCESS  read-write
	STATUS current
	DESCRIPTION "Relay Override Mode: 0 - None, 1 - On, 2 - Off"
	::= { ctrlRelayEntry  5 }
	
ctrlRelayAcknowledge OBJECT-TYPE
	SYNTAX  Gauge32
	MAX-ACCESS  read-write
	STATUS current
	DESCRIPTION "Acknowledge write a 1, always reads back 0"
	::= { ctrlRelayEntry  6 }
	
airSpeedSwitchSensorEntry OBJECT-TYPE
	SYNTAX  AirSpeedSwitchSensorEntry
	MAX-ACCESS  not-accessible
	STATUS current
	DESCRIPTION 
		"Entry in the air speed switch sensor table: each entry contains
an index (airSpeedSwitchIndex) and other sensor details"
	INDEX { airSpeedSwitchSensorIndex }
	::= { airSpeedSwitchSensorTable 1 }

AirSpeedSwitchSensorEntry ::= SEQUENCE {
	airSpeedSwitchSensorIndex		INTEGER,
	airSpeedSwitchSensorSerial		DisplayString,
	airSpeedSwitchSensorName		DisplayString,
	airSpeedSwitchSensorAvail		Gauge32,
	airSpeedSwitchSensorAirSpeed		INTEGER
}

airSpeedSwitchSensorIndex OBJECT-TYPE
	SYNTAX  INTEGER(1..100)
	MAX-ACCESS  not-accessible
	STATUS current
	DESCRIPTION "Table entry index value"
	::= { airSpeedSwitchSensorEntry  1 }
	
airSpeedSwitchSensorSerial OBJECT-TYPE
	SYNTAX  DisplayString
	MAX-ACCESS  read-only
	STATUS current
	DESCRIPTION "Serial Number"
	::= { airSpeedSwitchSensorEntry  2 }
	
airSpeedSwitchSensorName OBJECT-TYPE
	SYNTAX  DisplayString
	MAX-ACCESS  read-only
	STATUS current
	DESCRIPTION "Friendly Name"
	::= { airSpeedSwitchSensorEntry  3 }
	
airSpeedSwitchSensorAvail OBJECT-TYPE
	SYNTAX  Gauge32
	MAX-ACCESS  read-only
	STATUS current
	DESCRIPTION "Is device currently plugged in?"
	::= { airSpeedSwitchSensorEntry  4 }
	
airSpeedSwitchSensorAirSpeed OBJECT-TYPE
	SYNTAX  INTEGER(0..100)
	MAX-ACCESS  read-only
	STATUS current
	DESCRIPTION "Air Speed Switch Status"
	::= { airSpeedSwitchSensorEntry  5 }
	
powerDMEntry OBJECT-TYPE
	SYNTAX  PowerDMEntry
	MAX-ACCESS  not-accessible
	STATUS current
	DESCRIPTION 
		"Entry in the DM48 current monitor table: each entry contains
an index (powerDMIndex) and other sensor details"
	INDEX { powerDMIndex }
	::= { powerDMTable 1 }

PowerDMEntry ::= SEQUENCE {
	powerDMIndex		INTEGER,
	powerDMSerial		DisplayString,
	powerDMName		DisplayString,
	powerDMAvail		Gauge32,
	powerDMUnitInfoTitle		DisplayString,
	powerDMUnitInfoVersion		DisplayString,
	powerDMUnitInfoMainCount		INTEGER,
	powerDMUnitInfoAuxCount		INTEGER,
	powerDMChannelName1		DisplayString,
	powerDMChannelName2		DisplayString,
	powerDMChannelName3		DisplayString,
	powerDMChannelName4		DisplayString,
	powerDMChannelName5		DisplayString,
	powerDMChannelName6		DisplayString,
	powerDMChannelName7		DisplayString,
	powerDMChannelName8		DisplayString,
	powerDMChannelName9		DisplayString,
	powerDMChannelName10		DisplayString,
	powerDMChannelName11		DisplayString,
	powerDMChannelName12		DisplayString,
	powerDMChannelName13		DisplayString,
	powerDMChannelName14		DisplayString,
	powerDMChannelName15		DisplayString,
	powerDMChannelName16		DisplayString,
	powerDMChannelName17		DisplayString,
	powerDMChannelName18		DisplayString,
	powerDMChannelName19		DisplayString,
	powerDMChannelName20		DisplayString,
	powerDMChannelName21		DisplayString,
	powerDMChannelName22		DisplayString,
	powerDMChannelName23		DisplayString,
	powerDMChannelName24		DisplayString,
	powerDMChannelName25		DisplayString,
	powerDMChannelName26		DisplayString,
	powerDMChannelName27		DisplayString,
	powerDMChannelName28		DisplayString,
	powerDMChannelName29		DisplayString,
	powerDMChannelName30		DisplayString,
	powerDMChannelName31		DisplayString,
	powerDMChannelName32		DisplayString,
	powerDMChannelName33		DisplayString,
	powerDMChannelName34		DisplayString,
	powerDMChannelName35		DisplayString,
	powerDMChannelName36		DisplayString,
	powerDMChannelName37		DisplayString,
	powerDMChannelName38		DisplayString,
	powerDMChannelName39		DisplayString,
	powerDMChannelName40		DisplayString,
	powerDMChannelName41		DisplayString,
	powerDMChannelName42		DisplayString,
	powerDMChannelName43		DisplayString,
	powerDMChannelName44		DisplayString,
	powerDMChannelName45		DisplayString,
	powerDMChannelName46		DisplayString,
	powerDMChannelName47		DisplayString,
	powerDMChannelName48		DisplayString,
	powerDMChannelFriendly1		DisplayString,
	powerDMChannelFriendly2		DisplayString,
	powerDMChannelFriendly3		DisplayString,
	powerDMChannelFriendly4		DisplayString,
	powerDMChannelFriendly5		DisplayString,
	powerDMChannelFriendly6		DisplayString,
	powerDMChannelFriendly7		DisplayString,
	powerDMChannelFriendly8		DisplayString,
	powerDMChannelFriendly9		DisplayString,
	powerDMChannelFriendly10		DisplayString,
	powerDMChannelFriendly11		DisplayString,
	powerDMChannelFriendly12		DisplayString,
	powerDMChannelFriendly13		DisplayString,
	powerDMChannelFriendly14		DisplayString,
	powerDMChannelFriendly15		DisplayString,
	powerDMChannelFriendly16		DisplayString,
	powerDMChannelFriendly17		DisplayString,
	powerDMChannelFriendly18		DisplayString,
	powerDMChannelFriendly19		DisplayString,
	powerDMChannelFriendly20		DisplayString,
	powerDMChannelFriendly21		DisplayString,
	powerDMChannelFriendly22		DisplayString,
	powerDMChannelFriendly23		DisplayString,
	powerDMChannelFriendly24		DisplayString,
	powerDMChannelFriendly25		DisplayString,
	powerDMChannelFriendly26		DisplayString,
	powerDMChannelFriendly27		DisplayString,
	powerDMChannelFriendly28		DisplayString,
	powerDMChannelFriendly29		DisplayString,
	powerDMChannelFriendly30		DisplayString,
	powerDMChannelFriendly31		DisplayString,
	powerDMChannelFriendly32		DisplayString,
	powerDMChannelFriendly33		DisplayString,
	powerDMChannelFriendly34		DisplayString,
	powerDMChannelFriendly35		DisplayString,
	powerDMChannelFriendly36		DisplayString,
	powerDMChannelFriendly37		DisplayString,
	powerDMChannelFriendly38		DisplayString,
	powerDMChannelFriendly39		DisplayString,
	powerDMChannelFriendly40		DisplayString,
	powerDMChannelFriendly41		DisplayString,
	powerDMChannelFriendly42		DisplayString,
	powerDMChannelFriendly43		DisplayString,
	powerDMChannelFriendly44		DisplayString,
	powerDMChannelFriendly45		DisplayString,
	powerDMChannelFriendly46		DisplayString,
	powerDMChannelFriendly47		DisplayString,
	powerDMChannelFriendly48		DisplayString,
	powerDMChannelGroup1		DisplayString,
	powerDMChannelGroup2		DisplayString,
	powerDMChannelGroup3		DisplayString,
	powerDMChannelGroup4		DisplayString,
	powerDMChannelGroup5		DisplayString,
	powerDMChannelGroup6		DisplayString,
	powerDMChannelGroup7		DisplayString,
	powerDMChannelGroup8		DisplayString,
	powerDMChannelGroup9		DisplayString,
	powerDMChannelGroup10		DisplayString,
	powerDMChannelGroup11		DisplayString,
	powerDMChannelGroup12		DisplayString,
	powerDMChannelGroup13		DisplayString,
	powerDMChannelGroup14		DisplayString,
	powerDMChannelGroup15		DisplayString,
	powerDMChannelGroup16		DisplayString,
	powerDMChannelGroup17		DisplayString,
	powerDMChannelGroup18		DisplayString,
	powerDMChannelGroup19		DisplayString,
	powerDMChannelGroup20		DisplayString,
	powerDMChannelGroup21		DisplayString,
	powerDMChannelGroup22		DisplayString,
	powerDMChannelGroup23		DisplayString,
	powerDMChannelGroup24		DisplayString,
	powerDMChannelGroup25		DisplayString,
	powerDMChannelGroup26		DisplayString,
	powerDMChannelGroup27		DisplayString,
	powerDMChannelGroup28		DisplayString,
	powerDMChannelGroup29		DisplayString,
	powerDMChannelGroup30		DisplayString,
	powerDMChannelGroup31		DisplayString,
	powerDMChannelGroup32		DisplayString,
	powerDMChannelGroup33		DisplayString,
	powerDMChannelGroup34		DisplayString,
	powerDMChannelGroup35		DisplayString,
	powerDMChannelGroup36		DisplayString,
	powerDMChannelGroup37		DisplayString,
	powerDMChannelGroup38		DisplayString,
	powerDMChannelGroup39		DisplayString,
	powerDMChannelGroup40		DisplayString,
	powerDMChannelGroup41		DisplayString,
	powerDMChannelGroup42		DisplayString,
	powerDMChannelGroup43		DisplayString,
	powerDMChannelGroup44		DisplayString,
	powerDMChannelGroup45		DisplayString,
	powerDMChannelGroup46		DisplayString,
	powerDMChannelGroup47		DisplayString,
	powerDMChannelGroup48		DisplayString,
	powerDMDeciAmps1		INTEGER,
	powerDMDeciAmps2		INTEGER,
	powerDMDeciAmps3		INTEGER,
	powerDMDeciAmps4		INTEGER,
	powerDMDeciAmps5		INTEGER,
	powerDMDeciAmps6		INTEGER,
	powerDMDeciAmps7		INTEGER,
	powerDMDeciAmps8		INTEGER,
	powerDMDeciAmps9		INTEGER,
	powerDMDeciAmps10		INTEGER,
	powerDMDeciAmps11		INTEGER,
	powerDMDeciAmps12		INTEGER,
	powerDMDeciAmps13		INTEGER,
	powerDMDeciAmps14		INTEGER,
	powerDMDeciAmps15		INTEGER,
	powerDMDeciAmps16		INTEGER,
	powerDMDeciAmps17		INTEGER,
	powerDMDeciAmps18		INTEGER,
	powerDMDeciAmps19		INTEGER,
	powerDMDeciAmps20		INTEGER,
	powerDMDeciAmps21		INTEGER,
	powerDMDeciAmps22		INTEGER,
	powerDMDeciAmps23		INTEGER,
	powerDMDeciAmps24		INTEGER,
	powerDMDeciAmps25		INTEGER,
	powerDMDeciAmps26		INTEGER,
	powerDMDeciAmps27		INTEGER,
	powerDMDeciAmps28		INTEGER,
	powerDMDeciAmps29		INTEGER,
	powerDMDeciAmps30		INTEGER,
	powerDMDeciAmps31		INTEGER,
	powerDMDeciAmps32		INTEGER,
	powerDMDeciAmps33		INTEGER,
	powerDMDeciAmps34		INTEGER,
	powerDMDeciAmps35		INTEGER,
	powerDMDeciAmps36		INTEGER,
	powerDMDeciAmps37		INTEGER,
	powerDMDeciAmps38		INTEGER,
	powerDMDeciAmps39		INTEGER,
	powerDMDeciAmps40		INTEGER,
	powerDMDeciAmps41		INTEGER,
	powerDMDeciAmps42		INTEGER,
	powerDMDeciAmps43		INTEGER,
	powerDMDeciAmps44		INTEGER,
	powerDMDeciAmps45		INTEGER,
	powerDMDeciAmps46		INTEGER,
	powerDMDeciAmps47		INTEGER,
	powerDMDeciAmps48		INTEGER
}

powerDMIndex OBJECT-TYPE
	SYNTAX  INTEGER(1..100)
	MAX-ACCESS  not-accessible
	STATUS current
	DESCRIPTION "Table entry index value"
	::= { powerDMEntry  1 }
	
powerDMSerial OBJECT-TYPE
	SYNTAX  DisplayString
	MAX-ACCESS  read-only
	STATUS current
	DESCRIPTION "Serial Number"
	::= { powerDMEntry  2 }
	
powerDMName OBJECT-TYPE
	SYNTAX  DisplayString
	MAX-ACCESS  read-only
	STATUS current
	DESCRIPTION "Friendly Name"
	::= { powerDMEntry  3 }
	
powerDMAvail OBJECT-TYPE
	SYNTAX  Gauge32
	MAX-ACCESS  read-only
	STATUS current
	DESCRIPTION "Is device currently plugged in?"
	::= { powerDMEntry  4 }
	
powerDMUnitInfoTitle OBJECT-TYPE
	SYNTAX  DisplayString
	MAX-ACCESS  read-only
	STATUS current
	DESCRIPTION "Type of Unit"
	::= { powerDMEntry  5 }
	
powerDMUnitInfoVersion OBJECT-TYPE
	SYNTAX  DisplayString
	MAX-ACCESS  read-only
	STATUS current
	DESCRIPTION "Unit Version Number"
	::= { powerDMEntry  6 }
	
powerDMUnitInfoMainCount OBJECT-TYPE
	SYNTAX  INTEGER(0..16)
	MAX-ACCESS  read-only
	STATUS current
	DESCRIPTION "Number of Main (Total Amps) Channels on the Unit"
	::= { powerDMEntry  7 }
	
powerDMUnitInfoAuxCount OBJECT-TYPE
	SYNTAX  INTEGER(0..48)
	MAX-ACCESS  read-only
	STATUS current
	DESCRIPTION "Number of Auxiliary (Outlet) Channels on the Unit"
	::= { powerDMEntry  8 }
	
powerDMChannelName1 OBJECT-TYPE
	SYNTAX  DisplayString
	MAX-ACCESS  read-only
	STATUS current
	DESCRIPTION "Channel 1 Factory Name"
	::= { powerDMEntry  9 }
	
powerDMChannelName2 OBJECT-TYPE
	SYNTAX  DisplayString
	MAX-ACCESS  read-only
	STATUS current
	DESCRIPTION "Channel 2 Factory Name"
	::= { powerDMEntry  10 }
	
powerDMChannelName3 OBJECT-TYPE
	SYNTAX  DisplayString
	MAX-ACCESS  read-only
	STATUS current
	DESCRIPTION "Channel 3 Factory Name"
	::= { powerDMEntry  11 }
	
powerDMChannelName4 OBJECT-TYPE
	SYNTAX  DisplayString
	MAX-ACCESS  read-only
	STATUS current
	DESCRIPTION "Channel 4 Factory Name"
	::= { powerDMEntry  12 }
	
powerDMChannelName5 OBJECT-TYPE
	SYNTAX  DisplayString
	MAX-ACCESS  read-only
	STATUS current
	DESCRIPTION "Channel 5 Factory Name"
	::= { powerDMEntry  13 }
	
powerDMChannelName6 OBJECT-TYPE
	SYNTAX  DisplayString
	MAX-ACCESS  read-only
	STATUS current
	DESCRIPTION "Channel 6 Factory Name"
	::= { powerDMEntry  14 }
	
powerDMChannelName7 OBJECT-TYPE
	SYNTAX  DisplayString
	MAX-ACCESS  read-only
	STATUS current
	DESCRIPTION "Channel 7 Factory Name"
	::= { powerDMEntry  15 }
	
powerDMChannelName8 OBJECT-TYPE
	SYNTAX  DisplayString
	MAX-ACCESS  read-only
	STATUS current
	DESCRIPTION "Channel 8 Factory Name"
	::= { powerDMEntry  16 }
	
powerDMChannelName9 OBJECT-TYPE
	SYNTAX  DisplayString
	MAX-ACCESS  read-only
	STATUS current
	DESCRIPTION "Channel 9 Factory Name"
	::= { powerDMEntry  17 }
	
powerDMChannelName10 OBJECT-TYPE
	SYNTAX  DisplayString
	MAX-ACCESS  read-only
	STATUS current
	DESCRIPTION "Channel 10 Factory Name"
	::= { powerDMEntry  18 }
	
powerDMChannelName11 OBJECT-TYPE
	SYNTAX  DisplayString
	MAX-ACCESS  read-only
	STATUS current
	DESCRIPTION "Channel 11 Factory Name"
	::= { powerDMEntry  19 }
	
powerDMChannelName12 OBJECT-TYPE
	SYNTAX  DisplayString
	MAX-ACCESS  read-only
	STATUS current
	DESCRIPTION "Channel 12 Factory Name"
	::= { powerDMEntry  20 }
	
powerDMChannelName13 OBJECT-TYPE
	SYNTAX  DisplayString
	MAX-ACCESS  read-only
	STATUS current
	DESCRIPTION "Channel 13 Factory Name"
	::= { powerDMEntry  21 }
	
powerDMChannelName14 OBJECT-TYPE
	SYNTAX  DisplayString
	MAX-ACCESS  read-only
	STATUS current
	DESCRIPTION "Channel 14 Factory Name"
	::= { powerDMEntry  22 }
	
powerDMChannelName15 OBJECT-TYPE
	SYNTAX  DisplayString
	MAX-ACCESS  read-only
	STATUS current
	DESCRIPTION "Channel 15 Factory Name"
	::= { powerDMEntry  23 }
	
powerDMChannelName16 OBJECT-TYPE
	SYNTAX  DisplayString
	MAX-ACCESS  read-only
	STATUS current
	DESCRIPTION "Channel 16 Factory Name"
	::= { powerDMEntry  24 }
	
powerDMChannelName17 OBJECT-TYPE
	SYNTAX  DisplayString
	MAX-ACCESS  read-only
	STATUS current
	DESCRIPTION "Channel 17 Factory Name"
	::= { powerDMEntry  25 }
	
powerDMChannelName18 OBJECT-TYPE
	SYNTAX  DisplayString
	MAX-ACCESS  read-only
	STATUS current
	DESCRIPTION "Channel 18 Factory Name"
	::= { powerDMEntry  26 }
	
powerDMChannelName19 OBJECT-TYPE
	SYNTAX  DisplayString
	MAX-ACCESS  read-only
	STATUS current
	DESCRIPTION "Channel 19 Factory Name"
	::= { powerDMEntry  27 }
	
powerDMChannelName20 OBJECT-TYPE
	SYNTAX  DisplayString
	MAX-ACCESS  read-only
	STATUS current
	DESCRIPTION "Channel 20 Factory Name"
	::= { powerDMEntry  28 }
	
powerDMChannelName21 OBJECT-TYPE
	SYNTAX  DisplayString
	MAX-ACCESS  read-only
	STATUS current
	DESCRIPTION "Channel 21 Factory Name"
	::= { powerDMEntry  29 }
	
powerDMChannelName22 OBJECT-TYPE
	SYNTAX  DisplayString
	MAX-ACCESS  read-only
	STATUS current
	DESCRIPTION "Channel 22 Factory Name"
	::= { powerDMEntry  30 }
	
powerDMChannelName23 OBJECT-TYPE
	SYNTAX  DisplayString
	MAX-ACCESS  read-only
	STATUS current
	DESCRIPTION "Channel 23 Factory Name"
	::= { powerDMEntry  31 }
	
powerDMChannelName24 OBJECT-TYPE
	SYNTAX  DisplayString
	MAX-ACCESS  read-only
	STATUS current
	DESCRIPTION "Channel 24 Factory Name"
	::= { powerDMEntry  32 }
	
powerDMChannelName25 OBJECT-TYPE
	SYNTAX  DisplayString
	MAX-ACCESS  read-only
	STATUS current
	DESCRIPTION "Channel 25 Factory Name"
	::= { powerDMEntry  33 }
	
powerDMChannelName26 OBJECT-TYPE
	SYNTAX  DisplayString
	MAX-ACCESS  read-only
	STATUS current
	DESCRIPTION "Channel 26 Factory Name"
	::= { powerDMEntry  34 }
	
powerDMChannelName27 OBJECT-TYPE
	SYNTAX  DisplayString
	MAX-ACCESS  read-only
	STATUS current
	DESCRIPTION "Channel 27 Factory Name"
	::= { powerDMEntry  35 }
	
powerDMChannelName28 OBJECT-TYPE
	SYNTAX  DisplayString
	MAX-ACCESS  read-only
	STATUS current
	DESCRIPTION "Channel 28 Factory Name"
	::= { powerDMEntry  36 }
	
powerDMChannelName29 OBJECT-TYPE
	SYNTAX  DisplayString
	MAX-ACCESS  read-only
	STATUS current
	DESCRIPTION "Channel 29 Factory Name"
	::= { powerDMEntry  37 }
	
powerDMChannelName30 OBJECT-TYPE
	SYNTAX  DisplayString
	MAX-ACCESS  read-only
	STATUS current
	DESCRIPTION "Channel 30 Factory Name"
	::= { powerDMEntry  38 }
	
powerDMChannelName31 OBJECT-TYPE
	SYNTAX  DisplayString
	MAX-ACCESS  read-only
	STATUS current
	DESCRIPTION "Channel 31 Factory Name"
	::= { powerDMEntry  39 }
	
powerDMChannelName32 OBJECT-TYPE
	SYNTAX  DisplayString
	MAX-ACCESS  read-only
	STATUS current
	DESCRIPTION "Channel 32 Factory Name"
	::= { powerDMEntry  40 }
	
powerDMChannelName33 OBJECT-TYPE
	SYNTAX  DisplayString
	MAX-ACCESS  read-only
	STATUS current
	DESCRIPTION "Channel 33 Factory Name"
	::= { powerDMEntry  41 }
	
powerDMChannelName34 OBJECT-TYPE
	SYNTAX  DisplayString
	MAX-ACCESS  read-only
	STATUS current
	DESCRIPTION "Channel 34 Factory Name"
	::= { powerDMEntry  42 }
	
powerDMChannelName35 OBJECT-TYPE
	SYNTAX  DisplayString
	MAX-ACCESS  read-only
	STATUS current
	DESCRIPTION "Channel 35 Factory Name"
	::= { powerDMEntry  43 }
	
powerDMChannelName36 OBJECT-TYPE
	SYNTAX  DisplayString
	MAX-ACCESS  read-only
	STATUS current
	DESCRIPTION "Channel 36 Factory Name"
	::= { powerDMEntry  44 }
	
powerDMChannelName37 OBJECT-TYPE
	SYNTAX  DisplayString
	MAX-ACCESS  read-only
	STATUS current
	DESCRIPTION "Channel 37 Factory Name"
	::= { powerDMEntry  45 }
	
powerDMChannelName38 OBJECT-TYPE
	SYNTAX  DisplayString
	MAX-ACCESS  read-only
	STATUS current
	DESCRIPTION "Channel 38 Factory Name"
	::= { powerDMEntry  46 }
	
powerDMChannelName39 OBJECT-TYPE
	SYNTAX  DisplayString
	MAX-ACCESS  read-only
	STATUS current
	DESCRIPTION "Channel 39 Factory Name"
	::= { powerDMEntry  47 }
	
powerDMChannelName40 OBJECT-TYPE
	SYNTAX  DisplayString
	MAX-ACCESS  read-only
	STATUS current
	DESCRIPTION "Channel 40 Factory Name"
	::= { powerDMEntry  48 }
	
powerDMChannelName41 OBJECT-TYPE
	SYNTAX  DisplayString
	MAX-ACCESS  read-only
	STATUS current
	DESCRIPTION "Channel 41 Factory Name"
	::= { powerDMEntry  49 }
	
powerDMChannelName42 OBJECT-TYPE
	SYNTAX  DisplayString
	MAX-ACCESS  read-only
	STATUS current
	DESCRIPTION "Channel 42 Factory Name"
	::= { powerDMEntry  50 }
	
powerDMChannelName43 OBJECT-TYPE
	SYNTAX  DisplayString
	MAX-ACCESS  read-only
	STATUS current
	DESCRIPTION "Channel 43 Factory Name"
	::= { powerDMEntry  51 }
	
powerDMChannelName44 OBJECT-TYPE
	SYNTAX  DisplayString
	MAX-ACCESS  read-only
	STATUS current
	DESCRIPTION "Channel 44 Factory Name"
	::= { powerDMEntry  52 }
	
powerDMChannelName45 OBJECT-TYPE
	SYNTAX  DisplayString
	MAX-ACCESS  read-only
	STATUS current
	DESCRIPTION "Channel 45 Factory Name"
	::= { powerDMEntry  53 }
	
powerDMChannelName46 OBJECT-TYPE
	SYNTAX  DisplayString
	MAX-ACCESS  read-only
	STATUS current
	DESCRIPTION "Channel 46 Factory Name"
	::= { powerDMEntry  54 }
	
powerDMChannelName47 OBJECT-TYPE
	SYNTAX  DisplayString
	MAX-ACCESS  read-only
	STATUS current
	DESCRIPTION "Channel 47 Factory Name"
	::= { powerDMEntry  55 }
	
powerDMChannelName48 OBJECT-TYPE
	SYNTAX  DisplayString
	MAX-ACCESS  read-only
	STATUS current
	DESCRIPTION "Channel 48 Factory Name"
	::= { powerDMEntry  56 }
	
powerDMChannelFriendly1 OBJECT-TYPE
	SYNTAX  DisplayString
	MAX-ACCESS  read-only
	STATUS current
	DESCRIPTION "Channel 1 Friendly Name"
	::= { powerDMEntry  57 }
	
powerDMChannelFriendly2 OBJECT-TYPE
	SYNTAX  DisplayString
	MAX-ACCESS  read-only
	STATUS current
	DESCRIPTION "Channel 2 Friendly Name"
	::= { powerDMEntry  58 }
	
powerDMChannelFriendly3 OBJECT-TYPE
	SYNTAX  DisplayString
	MAX-ACCESS  read-only
	STATUS current
	DESCRIPTION "Channel 3 Friendly Name"
	::= { powerDMEntry  59 }
	
powerDMChannelFriendly4 OBJECT-TYPE
	SYNTAX  DisplayString
	MAX-ACCESS  read-only
	STATUS current
	DESCRIPTION "Channel 4 Friendly Name"
	::= { powerDMEntry  60 }
	
powerDMChannelFriendly5 OBJECT-TYPE
	SYNTAX  DisplayString
	MAX-ACCESS  read-only
	STATUS current
	DESCRIPTION "Channel 5 Friendly Name"
	::= { powerDMEntry  61 }
	
powerDMChannelFriendly6 OBJECT-TYPE
	SYNTAX  DisplayString
	MAX-ACCESS  read-only
	STATUS current
	DESCRIPTION "Channel 6 Friendly Name"
	::= { powerDMEntry  62 }
	
powerDMChannelFriendly7 OBJECT-TYPE
	SYNTAX  DisplayString
	MAX-ACCESS  read-only
	STATUS current
	DESCRIPTION "Channel 7 Friendly Name"
	::= { powerDMEntry  63 }
	
powerDMChannelFriendly8 OBJECT-TYPE
	SYNTAX  DisplayString
	MAX-ACCESS  read-only
	STATUS current
	DESCRIPTION "Channel 8 Friendly Name"
	::= { powerDMEntry  64 }
	
powerDMChannelFriendly9 OBJECT-TYPE
	SYNTAX  DisplayString
	MAX-ACCESS  read-only
	STATUS current
	DESCRIPTION "Channel 9 Friendly Name"
	::= { powerDMEntry  65 }
	
powerDMChannelFriendly10 OBJECT-TYPE
	SYNTAX  DisplayString
	MAX-ACCESS  read-only
	STATUS current
	DESCRIPTION "Channel 10 Friendly Name"
	::= { powerDMEntry  66 }
	
powerDMChannelFriendly11 OBJECT-TYPE
	SYNTAX  DisplayString
	MAX-ACCESS  read-only
	STATUS current
	DESCRIPTION "Channel 11 Friendly Name"
	::= { powerDMEntry  67 }
	
powerDMChannelFriendly12 OBJECT-TYPE
	SYNTAX  DisplayString
	MAX-ACCESS  read-only
	STATUS current
	DESCRIPTION "Channel 12 Friendly Name"
	::= { powerDMEntry  68 }
	
powerDMChannelFriendly13 OBJECT-TYPE
	SYNTAX  DisplayString
	MAX-ACCESS  read-only
	STATUS current
	DESCRIPTION "Channel 13 Friendly Name"
	::= { powerDMEntry  69 }
	
powerDMChannelFriendly14 OBJECT-TYPE
	SYNTAX  DisplayString
	MAX-ACCESS  read-only
	STATUS current
	DESCRIPTION "Channel 14 Friendly Name"
	::= { powerDMEntry  70 }
	
powerDMChannelFriendly15 OBJECT-TYPE
	SYNTAX  DisplayString
	MAX-ACCESS  read-only
	STATUS current
	DESCRIPTION "Channel 15 Friendly Name"
	::= { powerDMEntry  71 }
	
powerDMChannelFriendly16 OBJECT-TYPE
	SYNTAX  DisplayString
	MAX-ACCESS  read-only
	STATUS current
	DESCRIPTION "Channel 16 Friendly Name"
	::= { powerDMEntry  72 }
	
powerDMChannelFriendly17 OBJECT-TYPE
	SYNTAX  DisplayString
	MAX-ACCESS  read-only
	STATUS current
	DESCRIPTION "Channel 17 Friendly Name"
	::= { powerDMEntry  73 }
	
powerDMChannelFriendly18 OBJECT-TYPE
	SYNTAX  DisplayString
	MAX-ACCESS  read-only
	STATUS current
	DESCRIPTION "Channel 18 Friendly Name"
	::= { powerDMEntry  74 }
	
powerDMChannelFriendly19 OBJECT-TYPE
	SYNTAX  DisplayString
	MAX-ACCESS  read-only
	STATUS current
	DESCRIPTION "Channel 19 Friendly Name"
	::= { powerDMEntry  75 }
	
powerDMChannelFriendly20 OBJECT-TYPE
	SYNTAX  DisplayString
	MAX-ACCESS  read-only
	STATUS current
	DESCRIPTION "Channel 20 Friendly Name"
	::= { powerDMEntry  76 }
	
powerDMChannelFriendly21 OBJECT-TYPE
	SYNTAX  DisplayString
	MAX-ACCESS  read-only
	STATUS current
	DESCRIPTION "Channel 21 Friendly Name"
	::= { powerDMEntry  77 }
	
powerDMChannelFriendly22 OBJECT-TYPE
	SYNTAX  DisplayString
	MAX-ACCESS  read-only
	STATUS current
	DESCRIPTION "Channel 22 Friendly Name"
	::= { powerDMEntry  78 }
	
powerDMChannelFriendly23 OBJECT-TYPE
	SYNTAX  DisplayString
	MAX-ACCESS  read-only
	STATUS current
	DESCRIPTION "Channel 23 Friendly Name"
	::= { powerDMEntry  79 }
	
powerDMChannelFriendly24 OBJECT-TYPE
	SYNTAX  DisplayString
	MAX-ACCESS  read-only
	STATUS current
	DESCRIPTION "Channel 24 Friendly Name"
	::= { powerDMEntry  80 }
	
powerDMChannelFriendly25 OBJECT-TYPE
	SYNTAX  DisplayString
	MAX-ACCESS  read-only
	STATUS current
	DESCRIPTION "Channel 25 Friendly Name"
	::= { powerDMEntry  81 }
	
powerDMChannelFriendly26 OBJECT-TYPE
	SYNTAX  DisplayString
	MAX-ACCESS  read-only
	STATUS current
	DESCRIPTION "Channel 26 Friendly Name"
	::= { powerDMEntry  82 }
	
powerDMChannelFriendly27 OBJECT-TYPE
	SYNTAX  DisplayString
	MAX-ACCESS  read-only
	STATUS current
	DESCRIPTION "Channel 27 Friendly Name"
	::= { powerDMEntry  83 }
	
powerDMChannelFriendly28 OBJECT-TYPE
	SYNTAX  DisplayString
	MAX-ACCESS  read-only
	STATUS current
	DESCRIPTION "Channel 28 Friendly Name"
	::= { powerDMEntry  84 }
	
powerDMChannelFriendly29 OBJECT-TYPE
	SYNTAX  DisplayString
	MAX-ACCESS  read-only
	STATUS current
	DESCRIPTION "Channel 29 Friendly Name"
	::= { powerDMEntry  85 }
	
powerDMChannelFriendly30 OBJECT-TYPE
	SYNTAX  DisplayString
	MAX-ACCESS  read-only
	STATUS current
	DESCRIPTION "Channel 30 Friendly Name"
	::= { powerDMEntry  86 }
	
powerDMChannelFriendly31 OBJECT-TYPE
	SYNTAX  DisplayString
	MAX-ACCESS  read-only
	STATUS current
	DESCRIPTION "Channel 31 Friendly Name"
	::= { powerDMEntry  87 }
	
powerDMChannelFriendly32 OBJECT-TYPE
	SYNTAX  DisplayString
	MAX-ACCESS  read-only
	STATUS current
	DESCRIPTION "Channel 32 Friendly Name"
	::= { powerDMEntry  88 }
	
powerDMChannelFriendly33 OBJECT-TYPE
	SYNTAX  DisplayString
	MAX-ACCESS  read-only
	STATUS current
	DESCRIPTION "Channel 33 Friendly Name"
	::= { powerDMEntry  89 }
	
powerDMChannelFriendly34 OBJECT-TYPE
	SYNTAX  DisplayString
	MAX-ACCESS  read-only
	STATUS current
	DESCRIPTION "Channel 34 Friendly Name"
	::= { powerDMEntry  90 }
	
powerDMChannelFriendly35 OBJECT-TYPE
	SYNTAX  DisplayString
	MAX-ACCESS  read-only
	STATUS current
	DESCRIPTION "Channel 35 Friendly Name"
	::= { powerDMEntry  91 }
	
powerDMChannelFriendly36 OBJECT-TYPE
	SYNTAX  DisplayString
	MAX-ACCESS  read-only
	STATUS current
	DESCRIPTION "Channel 36 Friendly Name"
	::= { powerDMEntry  92 }
	
powerDMChannelFriendly37 OBJECT-TYPE
	SYNTAX  DisplayString
	MAX-ACCESS  read-only
	STATUS current
	DESCRIPTION "Channel 37 Friendly Name"
	::= { powerDMEntry  93 }
	
powerDMChannelFriendly38 OBJECT-TYPE
	SYNTAX  DisplayString
	MAX-ACCESS  read-only
	STATUS current
	DESCRIPTION "Channel 38 Friendly Name"
	::= { powerDMEntry  94 }
	
powerDMChannelFriendly39 OBJECT-TYPE
	SYNTAX  DisplayString
	MAX-ACCESS  read-only
	STATUS current
	DESCRIPTION "Channel 39 Friendly Name"
	::= { powerDMEntry  95 }
	
powerDMChannelFriendly40 OBJECT-TYPE
	SYNTAX  DisplayString
	MAX-ACCESS  read-only
	STATUS current
	DESCRIPTION "Channel 40 Friendly Name"
	::= { powerDMEntry  96 }
	
powerDMChannelFriendly41 OBJECT-TYPE
	SYNTAX  DisplayString
	MAX-ACCESS  read-only
	STATUS current
	DESCRIPTION "Channel 41 Friendly Name"
	::= { powerDMEntry  97 }
	
powerDMChannelFriendly42 OBJECT-TYPE
	SYNTAX  DisplayString
	MAX-ACCESS  read-only
	STATUS current
	DESCRIPTION "Channel 42 Friendly Name"
	::= { powerDMEntry  98 }
	
powerDMChannelFriendly43 OBJECT-TYPE
	SYNTAX  DisplayString
	MAX-ACCESS  read-only
	STATUS current
	DESCRIPTION "Channel 43 Friendly Name"
	::= { powerDMEntry  99 }
	
powerDMChannelFriendly44 OBJECT-TYPE
	SYNTAX  DisplayString
	MAX-ACCESS  read-only
	STATUS current
	DESCRIPTION "Channel 44 Friendly Name"
	::= { powerDMEntry  100 }
	
powerDMChannelFriendly45 OBJECT-TYPE
	SYNTAX  DisplayString
	MAX-ACCESS  read-only
	STATUS current
	DESCRIPTION "Channel 45 Friendly Name"
	::= { powerDMEntry  101 }
	
powerDMChannelFriendly46 OBJECT-TYPE
	SYNTAX  DisplayString
	MAX-ACCESS  read-only
	STATUS current
	DESCRIPTION "Channel 46 Friendly Name"
	::= { powerDMEntry  102 }
	
powerDMChannelFriendly47 OBJECT-TYPE
	SYNTAX  DisplayString
	MAX-ACCESS  read-only
	STATUS current
	DESCRIPTION "Channel 47 Friendly Name"
	::= { powerDMEntry  103 }
	
powerDMChannelFriendly48 OBJECT-TYPE
	SYNTAX  DisplayString
	MAX-ACCESS  read-only
	STATUS current
	DESCRIPTION "Channel 48 Friendly Name"
	::= { powerDMEntry  104 }
	
powerDMChannelGroup1 OBJECT-TYPE
	SYNTAX  DisplayString
	MAX-ACCESS  read-only
	STATUS current
	DESCRIPTION "Channel 1 Group"
	::= { powerDMEntry  105 }
	
powerDMChannelGroup2 OBJECT-TYPE
	SYNTAX  DisplayString
	MAX-ACCESS  read-only
	STATUS current
	DESCRIPTION "Channel 2 Group"
	::= { powerDMEntry  106 }
	
powerDMChannelGroup3 OBJECT-TYPE
	SYNTAX  DisplayString
	MAX-ACCESS  read-only
	STATUS current
	DESCRIPTION "Channel 3 Group"
	::= { powerDMEntry  107 }
	
powerDMChannelGroup4 OBJECT-TYPE
	SYNTAX  DisplayString
	MAX-ACCESS  read-only
	STATUS current
	DESCRIPTION "Channel 4 Group"
	::= { powerDMEntry  108 }
	
powerDMChannelGroup5 OBJECT-TYPE
	SYNTAX  DisplayString
	MAX-ACCESS  read-only
	STATUS current
	DESCRIPTION "Channel 5 Group"
	::= { powerDMEntry  109 }
	
powerDMChannelGroup6 OBJECT-TYPE
	SYNTAX  DisplayString
	MAX-ACCESS  read-only
	STATUS current
	DESCRIPTION "Channel 6 Group"
	::= { powerDMEntry  110 }
	
powerDMChannelGroup7 OBJECT-TYPE
	SYNTAX  DisplayString
	MAX-ACCESS  read-only
	STATUS current
	DESCRIPTION "Channel 7 Group"
	::= { powerDMEntry  111 }
	
powerDMChannelGroup8 OBJECT-TYPE
	SYNTAX  DisplayString
	MAX-ACCESS  read-only
	STATUS current
	DESCRIPTION "Channel 8 Group"
	::= { powerDMEntry  112 }
	
powerDMChannelGroup9 OBJECT-TYPE
	SYNTAX  DisplayString
	MAX-ACCESS  read-only
	STATUS current
	DESCRIPTION "Channel 9 Group"
	::= { powerDMEntry  113 }
	
powerDMChannelGroup10 OBJECT-TYPE
	SYNTAX  DisplayString
	MAX-ACCESS  read-only
	STATUS current
	DESCRIPTION "Channel 10 Group"
	::= { powerDMEntry  114 }
	
powerDMChannelGroup11 OBJECT-TYPE
	SYNTAX  DisplayString
	MAX-ACCESS  read-only
	STATUS current
	DESCRIPTION "Channel 11 Group"
	::= { powerDMEntry  115 }
	
powerDMChannelGroup12 OBJECT-TYPE
	SYNTAX  DisplayString
	MAX-ACCESS  read-only
	STATUS current
	DESCRIPTION "Channel 12 Group"
	::= { powerDMEntry  116 }
	
powerDMChannelGroup13 OBJECT-TYPE
	SYNTAX  DisplayString
	MAX-ACCESS  read-only
	STATUS current
	DESCRIPTION "Channel 13 Group"
	::= { powerDMEntry  117 }
	
powerDMChannelGroup14 OBJECT-TYPE
	SYNTAX  DisplayString
	MAX-ACCESS  read-only
	STATUS current
	DESCRIPTION "Channel 14 Group"
	::= { powerDMEntry  118 }
	
powerDMChannelGroup15 OBJECT-TYPE
	SYNTAX  DisplayString
	MAX-ACCESS  read-only
	STATUS current
	DESCRIPTION "Channel 15 Group"
	::= { powerDMEntry  119 }
	
powerDMChannelGroup16 OBJECT-TYPE
	SYNTAX  DisplayString
	MAX-ACCESS  read-only
	STATUS current
	DESCRIPTION "Channel 16 Group"
	::= { powerDMEntry  120 }
	
powerDMChannelGroup17 OBJECT-TYPE
	SYNTAX  DisplayString
	MAX-ACCESS  read-only
	STATUS current
	DESCRIPTION "Channel 17 Group"
	::= { powerDMEntry  121 }
	
powerDMChannelGroup18 OBJECT-TYPE
	SYNTAX  DisplayString
	MAX-ACCESS  read-only
	STATUS current
	DESCRIPTION "Channel 18 Group"
	::= { powerDMEntry  122 }
	
powerDMChannelGroup19 OBJECT-TYPE
	SYNTAX  DisplayString
	MAX-ACCESS  read-only
	STATUS current
	DESCRIPTION "Channel 19 Group"
	::= { powerDMEntry  123 }
	
powerDMChannelGroup20 OBJECT-TYPE
	SYNTAX  DisplayString
	MAX-ACCESS  read-only
	STATUS current
	DESCRIPTION "Channel 20 Group"
	::= { powerDMEntry  124 }
	
powerDMChannelGroup21 OBJECT-TYPE
	SYNTAX  DisplayString
	MAX-ACCESS  read-only
	STATUS current
	DESCRIPTION "Channel 21 Group"
	::= { powerDMEntry  125 }
	
powerDMChannelGroup22 OBJECT-TYPE
	SYNTAX  DisplayString
	MAX-ACCESS  read-only
	STATUS current
	DESCRIPTION "Channel 22 Group"
	::= { powerDMEntry  126 }
	
powerDMChannelGroup23 OBJECT-TYPE
	SYNTAX  DisplayString
	MAX-ACCESS  read-only
	STATUS current
	DESCRIPTION "Channel 23 Group"
	::= { powerDMEntry  127 }
	
powerDMChannelGroup24 OBJECT-TYPE
	SYNTAX  DisplayString
	MAX-ACCESS  read-only
	STATUS current
	DESCRIPTION "Channel 24 Group"
	::= { powerDMEntry  128 }
	
powerDMChannelGroup25 OBJECT-TYPE
	SYNTAX  DisplayString
	MAX-ACCESS  read-only
	STATUS current
	DESCRIPTION "Channel 25 Group"
	::= { powerDMEntry  129 }
	
powerDMChannelGroup26 OBJECT-TYPE
	SYNTAX  DisplayString
	MAX-ACCESS  read-only
	STATUS current
	DESCRIPTION "Channel 26 Group"
	::= { powerDMEntry  130 }
	
powerDMChannelGroup27 OBJECT-TYPE
	SYNTAX  DisplayString
	MAX-ACCESS  read-only
	STATUS current
	DESCRIPTION "Channel 27 Group"
	::= { powerDMEntry  131 }
	
powerDMChannelGroup28 OBJECT-TYPE
	SYNTAX  DisplayString
	MAX-ACCESS  read-only
	STATUS current
	DESCRIPTION "Channel 28 Group"
	::= { powerDMEntry  132 }
	
powerDMChannelGroup29 OBJECT-TYPE
	SYNTAX  DisplayString
	MAX-ACCESS  read-only
	STATUS current
	DESCRIPTION "Channel 29 Group"
	::= { powerDMEntry  133 }
	
powerDMChannelGroup30 OBJECT-TYPE
	SYNTAX  DisplayString
	MAX-ACCESS  read-only
	STATUS current
	DESCRIPTION "Channel 30 Group"
	::= { powerDMEntry  134 }
	
powerDMChannelGroup31 OBJECT-TYPE
	SYNTAX  DisplayString
	MAX-ACCESS  read-only
	STATUS current
	DESCRIPTION "Channel 31 Group"
	::= { powerDMEntry  135 }
	
powerDMChannelGroup32 OBJECT-TYPE
	SYNTAX  DisplayString
	MAX-ACCESS  read-only
	STATUS current
	DESCRIPTION "Channel 32 Group"
	::= { powerDMEntry  136 }
	
powerDMChannelGroup33 OBJECT-TYPE
	SYNTAX  DisplayString
	MAX-ACCESS  read-only
	STATUS current
	DESCRIPTION "Channel 33 Group"
	::= { powerDMEntry  137 }
	
powerDMChannelGroup34 OBJECT-TYPE
	SYNTAX  DisplayString
	MAX-ACCESS  read-only
	STATUS current
	DESCRIPTION "Channel 34 Group"
	::= { powerDMEntry  138 }
	
powerDMChannelGroup35 OBJECT-TYPE
	SYNTAX  DisplayString
	MAX-ACCESS  read-only
	STATUS current
	DESCRIPTION "Channel 35 Group"
	::= { powerDMEntry  139 }
	
powerDMChannelGroup36 OBJECT-TYPE
	SYNTAX  DisplayString
	MAX-ACCESS  read-only
	STATUS current
	DESCRIPTION "Channel 36 Group"
	::= { powerDMEntry  140 }
	
powerDMChannelGroup37 OBJECT-TYPE
	SYNTAX  DisplayString
	MAX-ACCESS  read-only
	STATUS current
	DESCRIPTION "Channel 37 Group"
	::= { powerDMEntry  141 }
	
powerDMChannelGroup38 OBJECT-TYPE
	SYNTAX  DisplayString
	MAX-ACCESS  read-only
	STATUS current
	DESCRIPTION "Channel 38 Group"
	::= { powerDMEntry  142 }
	
powerDMChannelGroup39 OBJECT-TYPE
	SYNTAX  DisplayString
	MAX-ACCESS  read-only
	STATUS current
	DESCRIPTION "Channel 39 Group"
	::= { powerDMEntry  143 }
	
powerDMChannelGroup40 OBJECT-TYPE
	SYNTAX  DisplayString
	MAX-ACCESS  read-only
	STATUS current
	DESCRIPTION "Channel 40 Group"
	::= { powerDMEntry  144 }
	
powerDMChannelGroup41 OBJECT-TYPE
	SYNTAX  DisplayString
	MAX-ACCESS  read-only
	STATUS current
	DESCRIPTION "Channel 41 Group"
	::= { powerDMEntry  145 }
	
powerDMChannelGroup42 OBJECT-TYPE
	SYNTAX  DisplayString
	MAX-ACCESS  read-only
	STATUS current
	DESCRIPTION "Channel 42 Group"
	::= { powerDMEntry  146 }
	
powerDMChannelGroup43 OBJECT-TYPE
	SYNTAX  DisplayString
	MAX-ACCESS  read-only
	STATUS current
	DESCRIPTION "Channel 43 Group"
	::= { powerDMEntry  147 }
	
powerDMChannelGroup44 OBJECT-TYPE
	SYNTAX  DisplayString
	MAX-ACCESS  read-only
	STATUS current
	DESCRIPTION "Channel 44 Group"
	::= { powerDMEntry  148 }
	
powerDMChannelGroup45 OBJECT-TYPE
	SYNTAX  DisplayString
	MAX-ACCESS  read-only
	STATUS current
	DESCRIPTION "Channel 45 Group"
	::= { powerDMEntry  149 }
	
powerDMChannelGroup46 OBJECT-TYPE
	SYNTAX  DisplayString
	MAX-ACCESS  read-only
	STATUS current
	DESCRIPTION "Channel 46 Group"
	::= { powerDMEntry  150 }
	
powerDMChannelGroup47 OBJECT-TYPE
	SYNTAX  DisplayString
	MAX-ACCESS  read-only
	STATUS current
	DESCRIPTION "Channel 47 Group"
	::= { powerDMEntry  151 }
	
powerDMChannelGroup48 OBJECT-TYPE
	SYNTAX  DisplayString
	MAX-ACCESS  read-only
	STATUS current
	DESCRIPTION "Channel 48 Group"
	::= { powerDMEntry  152 }
	
powerDMDeciAmps1 OBJECT-TYPE
	SYNTAX  INTEGER(0..1209)
	UNITS "0.1 Amps"
	MAX-ACCESS  read-only
	STATUS current
	DESCRIPTION "Current in deciamps"
	::= { powerDMEntry  153 }
	
powerDMDeciAmps2 OBJECT-TYPE
	SYNTAX  INTEGER(0..1209)
	UNITS "0.1 Amps"
	MAX-ACCESS  read-only
	STATUS current
	DESCRIPTION "Current in deciamps"
	::= { powerDMEntry  154 }
	
powerDMDeciAmps3 OBJECT-TYPE
	SYNTAX  INTEGER(0..1209)
	UNITS "0.1 Amps"
	MAX-ACCESS  read-only
	STATUS current
	DESCRIPTION "Current in deciamps"
	::= { powerDMEntry  155 }
	
powerDMDeciAmps4 OBJECT-TYPE
	SYNTAX  INTEGER(0..1209)
	UNITS "0.1 Amps"
	MAX-ACCESS  read-only
	STATUS current
	DESCRIPTION "Current in deciamps"
	::= { powerDMEntry  156 }
	
powerDMDeciAmps5 OBJECT-TYPE
	SYNTAX  INTEGER(0..1209)
	UNITS "0.1 Amps"
	MAX-ACCESS  read-only
	STATUS current
	DESCRIPTION "Current in deciamps"
	::= { powerDMEntry  157 }
	
powerDMDeciAmps6 OBJECT-TYPE
	SYNTAX  INTEGER(0..1209)
	UNITS "0.1 Amps"
	MAX-ACCESS  read-only
	STATUS current
	DESCRIPTION "Current in deciamps"
	::= { powerDMEntry  158 }
	
powerDMDeciAmps7 OBJECT-TYPE
	SYNTAX  INTEGER(0..1209)
	UNITS "0.1 Amps"
	MAX-ACCESS  read-only
	STATUS current
	DESCRIPTION "Current in deciamps"
	::= { powerDMEntry  159 }
	
powerDMDeciAmps8 OBJECT-TYPE
	SYNTAX  INTEGER(0..1209)
	UNITS "0.1 Amps"
	MAX-ACCESS  read-only
	STATUS current
	DESCRIPTION "Current in deciamps"
	::= { powerDMEntry  160 }
	
powerDMDeciAmps9 OBJECT-TYPE
	SYNTAX  INTEGER(0..1209)
	UNITS "0.1 Amps"
	MAX-ACCESS  read-only
	STATUS current
	DESCRIPTION "Current in deciamps"
	::= { powerDMEntry  161 }
	
powerDMDeciAmps10 OBJECT-TYPE
	SYNTAX  INTEGER(0..1209)
	UNITS "0.1 Amps"
	MAX-ACCESS  read-only
	STATUS current
	DESCRIPTION "Current in deciamps"
	::= { powerDMEntry  162 }
	
powerDMDeciAmps11 OBJECT-TYPE
	SYNTAX  INTEGER(0..1209)
	UNITS "0.1 Amps"
	MAX-ACCESS  read-only
	STATUS current
	DESCRIPTION "Current in deciamps"
	::= { powerDMEntry  163 }
	
powerDMDeciAmps12 OBJECT-TYPE
	SYNTAX  INTEGER(0..1209)
	UNITS "0.1 Amps"
	MAX-ACCESS  read-only
	STATUS current
	DESCRIPTION "Current in deciamps"
	::= { powerDMEntry  164 }
	
powerDMDeciAmps13 OBJECT-TYPE
	SYNTAX  INTEGER(0..1209)
	UNITS "0.1 Amps"
	MAX-ACCESS  read-only
	STATUS current
	DESCRIPTION "Current in deciamps"
	::= { powerDMEntry  165 }
	
powerDMDeciAmps14 OBJECT-TYPE
	SYNTAX  INTEGER(0..1209)
	UNITS "0.1 Amps"
	MAX-ACCESS  read-only
	STATUS current
	DESCRIPTION "Current in deciamps"
	::= { powerDMEntry  166 }
	
powerDMDeciAmps15 OBJECT-TYPE
	SYNTAX  INTEGER(0..1209)
	UNITS "0.1 Amps"
	MAX-ACCESS  read-only
	STATUS current
	DESCRIPTION "Current in deciamps"
	::= { powerDMEntry  167 }
	
powerDMDeciAmps16 OBJECT-TYPE
	SYNTAX  INTEGER(0..1209)
	UNITS "0.1 Amps"
	MAX-ACCESS  read-only
	STATUS current
	DESCRIPTION "Current in deciamps"
	::= { powerDMEntry  168 }
	
powerDMDeciAmps17 OBJECT-TYPE
	SYNTAX  INTEGER(0..1209)
	UNITS "0.1 Amps"
	MAX-ACCESS  read-only
	STATUS current
	DESCRIPTION "Current in deciamps"
	::= { powerDMEntry  169 }
	
powerDMDeciAmps18 OBJECT-TYPE
	SYNTAX  INTEGER(0..1209)
	UNITS "0.1 Amps"
	MAX-ACCESS  read-only
	STATUS current
	DESCRIPTION "Current in deciamps"
	::= { powerDMEntry  170 }
	
powerDMDeciAmps19 OBJECT-TYPE
	SYNTAX  INTEGER(0..1209)
	UNITS "0.1 Amps"
	MAX-ACCESS  read-only
	STATUS current
	DESCRIPTION "Current in deciamps"
	::= { powerDMEntry  171 }
	
powerDMDeciAmps20 OBJECT-TYPE
	SYNTAX  INTEGER(0..1209)
	UNITS "0.1 Amps"
	MAX-ACCESS  read-only
	STATUS current
	DESCRIPTION "Current in deciamps"
	::= { powerDMEntry  172 }
	
powerDMDeciAmps21 OBJECT-TYPE
	SYNTAX  INTEGER(0..1209)
	UNITS "0.1 Amps"
	MAX-ACCESS  read-only
	STATUS current
	DESCRIPTION "Current in deciamps"
	::= { powerDMEntry  173 }
	
powerDMDeciAmps22 OBJECT-TYPE
	SYNTAX  INTEGER(0..1209)
	UNITS "0.1 Amps"
	MAX-ACCESS  read-only
	STATUS current
	DESCRIPTION "Current in deciamps"
	::= { powerDMEntry  174 }
	
powerDMDeciAmps23 OBJECT-TYPE
	SYNTAX  INTEGER(0..1209)
	UNITS "0.1 Amps"
	MAX-ACCESS  read-only
	STATUS current
	DESCRIPTION "Current in deciamps"
	::= { powerDMEntry  175 }
	
powerDMDeciAmps24 OBJECT-TYPE
	SYNTAX  INTEGER(0..1209)
	UNITS "0.1 Amps"
	MAX-ACCESS  read-only
	STATUS current
	DESCRIPTION "Current in deciamps"
	::= { powerDMEntry  176 }
	
powerDMDeciAmps25 OBJECT-TYPE
	SYNTAX  INTEGER(0..1209)
	UNITS "0.1 Amps"
	MAX-ACCESS  read-only
	STATUS current
	DESCRIPTION "Current in deciamps"
	::= { powerDMEntry  177 }
	
powerDMDeciAmps26 OBJECT-TYPE
	SYNTAX  INTEGER(0..1209)
	UNITS "0.1 Amps"
	MAX-ACCESS  read-only
	STATUS current
	DESCRIPTION "Current in deciamps"
	::= { powerDMEntry  178 }
	
powerDMDeciAmps27 OBJECT-TYPE
	SYNTAX  INTEGER(0..1209)
	UNITS "0.1 Amps"
	MAX-ACCESS  read-only
	STATUS current
	DESCRIPTION "Current in deciamps"
	::= { powerDMEntry  179 }
	
powerDMDeciAmps28 OBJECT-TYPE
	SYNTAX  INTEGER(0..1209)
	UNITS "0.1 Amps"
	MAX-ACCESS  read-only
	STATUS current
	DESCRIPTION "Current in deciamps"
	::= { powerDMEntry  180 }
	
powerDMDeciAmps29 OBJECT-TYPE
	SYNTAX  INTEGER(0..1209)
	UNITS "0.1 Amps"
	MAX-ACCESS  read-only
	STATUS current
	DESCRIPTION "Current in deciamps"
	::= { powerDMEntry  181 }
	
powerDMDeciAmps30 OBJECT-TYPE
	SYNTAX  INTEGER(0..1209)
	UNITS "0.1 Amps"
	MAX-ACCESS  read-only
	STATUS current
	DESCRIPTION "Current in deciamps"
	::= { powerDMEntry  182 }
	
powerDMDeciAmps31 OBJECT-TYPE
	SYNTAX  INTEGER(0..1209)
	UNITS "0.1 Amps"
	MAX-ACCESS  read-only
	STATUS current
	DESCRIPTION "Current in deciamps"
	::= { powerDMEntry  183 }
	
powerDMDeciAmps32 OBJECT-TYPE
	SYNTAX  INTEGER(0..1209)
	UNITS "0.1 Amps"
	MAX-ACCESS  read-only
	STATUS current
	DESCRIPTION "Current in deciamps"
	::= { powerDMEntry  184 }
	
powerDMDeciAmps33 OBJECT-TYPE
	SYNTAX  INTEGER(0..1209)
	UNITS "0.1 Amps"
	MAX-ACCESS  read-only
	STATUS current
	DESCRIPTION "Current in deciamps"
	::= { powerDMEntry  185 }
	
powerDMDeciAmps34 OBJECT-TYPE
	SYNTAX  INTEGER(0..1209)
	UNITS "0.1 Amps"
	MAX-ACCESS  read-only
	STATUS current
	DESCRIPTION "Current in deciamps"
	::= { powerDMEntry  186 }
	
powerDMDeciAmps35 OBJECT-TYPE
	SYNTAX  INTEGER(0..1209)
	UNITS "0.1 Amps"
	MAX-ACCESS  read-only
	STATUS current
	DESCRIPTION "Current in deciamps"
	::= { powerDMEntry  187 }
	
powerDMDeciAmps36 OBJECT-TYPE
	SYNTAX  INTEGER(0..1209)
	UNITS "0.1 Amps"
	MAX-ACCESS  read-only
	STATUS current
	DESCRIPTION "Current in deciamps"
	::= { powerDMEntry  188 }
	
powerDMDeciAmps37 OBJECT-TYPE
	SYNTAX  INTEGER(0..1209)
	UNITS "0.1 Amps"
	MAX-ACCESS  read-only
	STATUS current
	DESCRIPTION "Current in deciamps"
	::= { powerDMEntry  189 }
	
powerDMDeciAmps38 OBJECT-TYPE
	SYNTAX  INTEGER(0..1209)
	UNITS "0.1 Amps"
	MAX-ACCESS  read-only
	STATUS current
	DESCRIPTION "Current in deciamps"
	::= { powerDMEntry  190 }
	
powerDMDeciAmps39 OBJECT-TYPE
	SYNTAX  INTEGER(0..1209)
	UNITS "0.1 Amps"
	MAX-ACCESS  read-only
	STATUS current
	DESCRIPTION "Current in deciamps"
	::= { powerDMEntry  191 }
	
powerDMDeciAmps40 OBJECT-TYPE
	SYNTAX  INTEGER(0..1209)
	UNITS "0.1 Amps"
	MAX-ACCESS  read-only
	STATUS current
	DESCRIPTION "Current in deciamps"
	::= { powerDMEntry  192 }
	
powerDMDeciAmps41 OBJECT-TYPE
	SYNTAX  INTEGER(0..1209)
	UNITS "0.1 Amps"
	MAX-ACCESS  read-only
	STATUS current
	DESCRIPTION "Current in deciamps"
	::= { powerDMEntry  193 }
	
powerDMDeciAmps42 OBJECT-TYPE
	SYNTAX  INTEGER(0..1209)
	UNITS "0.1 Amps"
	MAX-ACCESS  read-only
	STATUS current
	DESCRIPTION "Current in deciamps"
	::= { powerDMEntry  194 }
	
powerDMDeciAmps43 OBJECT-TYPE
	SYNTAX  INTEGER(0..1209)
	UNITS "0.1 Amps"
	MAX-ACCESS  read-only
	STATUS current
	DESCRIPTION "Current in deciamps"
	::= { powerDMEntry  195 }
	
powerDMDeciAmps44 OBJECT-TYPE
	SYNTAX  INTEGER(0..1209)
	UNITS "0.1 Amps"
	MAX-ACCESS  read-only
	STATUS current
	DESCRIPTION "Current in deciamps"
	::= { powerDMEntry  196 }
	
powerDMDeciAmps45 OBJECT-TYPE
	SYNTAX  INTEGER(0..1209)
	UNITS "0.1 Amps"
	MAX-ACCESS  read-only
	STATUS current
	DESCRIPTION "Current in deciamps"
	::= { powerDMEntry  197 }
	
powerDMDeciAmps46 OBJECT-TYPE
	SYNTAX  INTEGER(0..1209)
	UNITS "0.1 Amps"
	MAX-ACCESS  read-only
	STATUS current
	DESCRIPTION "Current in deciamps"
	::= { powerDMEntry  198 }
	
powerDMDeciAmps47 OBJECT-TYPE
	SYNTAX  INTEGER(0..1209)
	UNITS "0.1 Amps"
	MAX-ACCESS  read-only
	STATUS current
	DESCRIPTION "Current in deciamps"
	::= { powerDMEntry  199 }
	
powerDMDeciAmps48 OBJECT-TYPE
	SYNTAX  INTEGER(0..1209)
	UNITS "0.1 Amps"
	MAX-ACCESS  read-only
	STATUS current
	DESCRIPTION "Current in deciamps"
	::= { powerDMEntry  200 }
	
ioExpanderEntry OBJECT-TYPE
	SYNTAX  IoExpanderEntry
	MAX-ACCESS  not-accessible
	STATUS current
	DESCRIPTION 
		"Entry in the IO Expander table: each entry contains
an index (ioExpanderIndex) and other details"
	INDEX { ioExpanderIndex }
	::= { ioExpanderTable 1 }

IoExpanderEntry ::= SEQUENCE {
	ioExpanderIndex		INTEGER,
	ioExpanderSerial		DisplayString,
	ioExpanderName		DisplayString,
	ioExpanderAvail		Gauge32,
	ioExpanderFriendlyName1		DisplayString,
	ioExpanderFriendlyName2		DisplayString,
	ioExpanderFriendlyName3		DisplayString,
	ioExpanderFriendlyName4		DisplayString,
	ioExpanderFriendlyName5		DisplayString,
	ioExpanderFriendlyName6		DisplayString,
	ioExpanderFriendlyName7		DisplayString,
	ioExpanderFriendlyName8		DisplayString,
	ioExpanderFriendlyName9		DisplayString,
	ioExpanderFriendlyName10		DisplayString,
	ioExpanderFriendlyName11		DisplayString,
	ioExpanderFriendlyName12		DisplayString,
	ioExpanderFriendlyName13		DisplayString,
	ioExpanderFriendlyName14		DisplayString,
	ioExpanderFriendlyName15		DisplayString,
	ioExpanderFriendlyName16		DisplayString,
	ioExpanderFriendlyName17		DisplayString,
	ioExpanderFriendlyName18		DisplayString,
	ioExpanderFriendlyName19		DisplayString,
	ioExpanderFriendlyName20		DisplayString,
	ioExpanderFriendlyName21		DisplayString,
	ioExpanderFriendlyName22		DisplayString,
	ioExpanderFriendlyName23		DisplayString,
	ioExpanderFriendlyName24		DisplayString,
	ioExpanderFriendlyName25		DisplayString,
	ioExpanderFriendlyName26		DisplayString,
	ioExpanderFriendlyName27		DisplayString,
	ioExpanderFriendlyName28		DisplayString,
	ioExpanderFriendlyName29		DisplayString,
	ioExpanderFriendlyName30		DisplayString,
	ioExpanderFriendlyName31		DisplayString,
	ioExpanderFriendlyName32		DisplayString,
	ioExpanderIO1		INTEGER,
	ioExpanderIO2		INTEGER,
	ioExpanderIO3		INTEGER,
	ioExpanderIO4		INTEGER,
	ioExpanderIO5		INTEGER,
	ioExpanderIO6		INTEGER,
	ioExpanderIO7		INTEGER,
	ioExpanderIO8		INTEGER,
	ioExpanderIO9		INTEGER,
	ioExpanderIO10		INTEGER,
	ioExpanderIO11		INTEGER,
	ioExpanderIO12		INTEGER,
	ioExpanderIO13		INTEGER,
	ioExpanderIO14		INTEGER,
	ioExpanderIO15		INTEGER,
	ioExpanderIO16		INTEGER,
	ioExpanderIO17		INTEGER,
	ioExpanderIO18		INTEGER,
	ioExpanderIO19		INTEGER,
	ioExpanderIO20		INTEGER,
	ioExpanderIO21		INTEGER,
	ioExpanderIO22		INTEGER,
	ioExpanderIO23		INTEGER,
	ioExpanderIO24		INTEGER,
	ioExpanderIO25		INTEGER,
	ioExpanderIO26		INTEGER,
	ioExpanderIO27		INTEGER,
	ioExpanderIO28		INTEGER,
	ioExpanderIO29		INTEGER,
	ioExpanderIO30		INTEGER,
	ioExpanderIO31		INTEGER,
	ioExpanderIO32		INTEGER,
	ioExpanderRelayName1		DisplayString,
	ioExpanderRelayState1		Gauge32,
	ioExpanderRelayLatchingMode1		Gauge32,
	ioExpanderRelayOverride1		Gauge32,
	ioExpanderRelayAcknowledge1		Gauge32,
	ioExpanderRelayName2		DisplayString,
	ioExpanderRelayState2		Gauge32,
	ioExpanderRelayLatchingMode2		Gauge32,
	ioExpanderRelayOverride2		Gauge32,
	ioExpanderRelayAcknowledge2		Gauge32,
	ioExpanderRelayName3		DisplayString,
	ioExpanderRelayState3		Gauge32,
	ioExpanderRelayLatchingMode3		Gauge32,
	ioExpanderRelayOverride3		Gauge32,
	ioExpanderRelayAcknowledge3		Gauge32
}

ioExpanderIndex OBJECT-TYPE
	SYNTAX  INTEGER(1..1)
	MAX-ACCESS  not-accessible
	STATUS current
	DESCRIPTION "Table entry index value"
	::= { ioExpanderEntry  1 }
	
ioExpanderSerial OBJECT-TYPE
	SYNTAX  DisplayString
	MAX-ACCESS  read-only
	STATUS current
	DESCRIPTION "Serial Number"
	::= { ioExpanderEntry  2 }
	
ioExpanderName OBJECT-TYPE
	SYNTAX  DisplayString
	MAX-ACCESS  read-only
	STATUS current
	DESCRIPTION "Friendly Name"
	::= { ioExpanderEntry  3 }
	
ioExpanderAvail OBJECT-TYPE
	SYNTAX  Gauge32
	MAX-ACCESS  read-only
	STATUS current
	DESCRIPTION "Is device currently plugged in?"
	::= { ioExpanderEntry  4 }
	
ioExpanderFriendlyName1 OBJECT-TYPE
	SYNTAX  DisplayString
	MAX-ACCESS  read-only
	STATUS current
	DESCRIPTION "IO 1 Friendly Name"
	::= { ioExpanderEntry  5 }
	
ioExpanderFriendlyName2 OBJECT-TYPE
	SYNTAX  DisplayString
	MAX-ACCESS  read-only
	STATUS current
	DESCRIPTION "IO 2 Friendly Name"
	::= { ioExpanderEntry  6 }
	
ioExpanderFriendlyName3 OBJECT-TYPE
	SYNTAX  DisplayString
	MAX-ACCESS  read-only
	STATUS current
	DESCRIPTION "IO 3 Friendly Name"
	::= { ioExpanderEntry  7 }
	
ioExpanderFriendlyName4 OBJECT-TYPE
	SYNTAX  DisplayString
	MAX-ACCESS  read-only
	STATUS current
	DESCRIPTION "IO 4 Friendly Name"
	::= { ioExpanderEntry  8 }
	
ioExpanderFriendlyName5 OBJECT-TYPE
	SYNTAX  DisplayString
	MAX-ACCESS  read-only
	STATUS current
	DESCRIPTION "IO 5 Friendly Name"
	::= { ioExpanderEntry  9 }
	
ioExpanderFriendlyName6 OBJECT-TYPE
	SYNTAX  DisplayString
	MAX-ACCESS  read-only
	STATUS current
	DESCRIPTION "IO 6 Friendly Name"
	::= { ioExpanderEntry  10 }
	
ioExpanderFriendlyName7 OBJECT-TYPE
	SYNTAX  DisplayString
	MAX-ACCESS  read-only
	STATUS current
	DESCRIPTION "IO 7 Friendly Name"
	::= { ioExpanderEntry  11 }
	
ioExpanderFriendlyName8 OBJECT-TYPE
	SYNTAX  DisplayString
	MAX-ACCESS  read-only
	STATUS current
	DESCRIPTION "IO 8 Friendly Name"
	::= { ioExpanderEntry  12 }
	
ioExpanderFriendlyName9 OBJECT-TYPE
	SYNTAX  DisplayString
	MAX-ACCESS  read-only
	STATUS current
	DESCRIPTION "IO 9 Friendly Name"
	::= { ioExpanderEntry  13 }
	
ioExpanderFriendlyName10 OBJECT-TYPE
	SYNTAX  DisplayString
	MAX-ACCESS  read-only
	STATUS current
	DESCRIPTION "IO 10 Friendly Name"
	::= { ioExpanderEntry  14 }
	
ioExpanderFriendlyName11 OBJECT-TYPE
	SYNTAX  DisplayString
	MAX-ACCESS  read-only
	STATUS current
	DESCRIPTION "IO 11 Friendly Name"
	::= { ioExpanderEntry  15 }
	
ioExpanderFriendlyName12 OBJECT-TYPE
	SYNTAX  DisplayString
	MAX-ACCESS  read-only
	STATUS current
	DESCRIPTION "IO 12 Friendly Name"
	::= { ioExpanderEntry  16 }
	
ioExpanderFriendlyName13 OBJECT-TYPE
	SYNTAX  DisplayString
	MAX-ACCESS  read-only
	STATUS current
	DESCRIPTION "IO 13 Friendly Name"
	::= { ioExpanderEntry  17 }
	
ioExpanderFriendlyName14 OBJECT-TYPE
	SYNTAX  DisplayString
	MAX-ACCESS  read-only
	STATUS current
	DESCRIPTION "IO 14 Friendly Name"
	::= { ioExpanderEntry  18 }
	
ioExpanderFriendlyName15 OBJECT-TYPE
	SYNTAX  DisplayString
	MAX-ACCESS  read-only
	STATUS current
	DESCRIPTION "IO 15 Friendly Name"
	::= { ioExpanderEntry  19 }
	
ioExpanderFriendlyName16 OBJECT-TYPE
	SYNTAX  DisplayString
	MAX-ACCESS  read-only
	STATUS current
	DESCRIPTION "IO 16 Friendly Name"
	::= { ioExpanderEntry  20 }
	
ioExpanderFriendlyName17 OBJECT-TYPE
	SYNTAX  DisplayString
	MAX-ACCESS  read-only
	STATUS current
	DESCRIPTION "IO 17 Friendly Name"
	::= { ioExpanderEntry  21 }
	
ioExpanderFriendlyName18 OBJECT-TYPE
	SYNTAX  DisplayString
	MAX-ACCESS  read-only
	STATUS current
	DESCRIPTION "IO 18 Friendly Name"
	::= { ioExpanderEntry  22 }
	
ioExpanderFriendlyName19 OBJECT-TYPE
	SYNTAX  DisplayString
	MAX-ACCESS  read-only
	STATUS current
	DESCRIPTION "IO 19 Friendly Name"
	::= { ioExpanderEntry  23 }
	
ioExpanderFriendlyName20 OBJECT-TYPE
	SYNTAX  DisplayString
	MAX-ACCESS  read-only
	STATUS current
	DESCRIPTION "IO 20 Friendly Name"
	::= { ioExpanderEntry  24 }
	
ioExpanderFriendlyName21 OBJECT-TYPE
	SYNTAX  DisplayString
	MAX-ACCESS  read-only
	STATUS current
	DESCRIPTION "IO 21 Friendly Name"
	::= { ioExpanderEntry  25 }
	
ioExpanderFriendlyName22 OBJECT-TYPE
	SYNTAX  DisplayString
	MAX-ACCESS  read-only
	STATUS current
	DESCRIPTION "IO 22 Friendly Name"
	::= { ioExpanderEntry  26 }
	
ioExpanderFriendlyName23 OBJECT-TYPE
	SYNTAX  DisplayString
	MAX-ACCESS  read-only
	STATUS current
	DESCRIPTION "IO 23 Friendly Name"
	::= { ioExpanderEntry  27 }
	
ioExpanderFriendlyName24 OBJECT-TYPE
	SYNTAX  DisplayString
	MAX-ACCESS  read-only
	STATUS current
	DESCRIPTION "IO 24 Friendly Name"
	::= { ioExpanderEntry  28 }
	
ioExpanderFriendlyName25 OBJECT-TYPE
	SYNTAX  DisplayString
	MAX-ACCESS  read-only
	STATUS current
	DESCRIPTION "IO 25 Friendly Name"
	::= { ioExpanderEntry  29 }
	
ioExpanderFriendlyName26 OBJECT-TYPE
	SYNTAX  DisplayString
	MAX-ACCESS  read-only
	STATUS current
	DESCRIPTION "IO 26 Friendly Name"
	::= { ioExpanderEntry  30 }
	
ioExpanderFriendlyName27 OBJECT-TYPE
	SYNTAX  DisplayString
	MAX-ACCESS  read-only
	STATUS current
	DESCRIPTION "IO 27 Friendly Name"
	::= { ioExpanderEntry  31 }
	
ioExpanderFriendlyName28 OBJECT-TYPE
	SYNTAX  DisplayString
	MAX-ACCESS  read-only
	STATUS current
	DESCRIPTION "IO 28 Friendly Name"
	::= { ioExpanderEntry  32 }
	
ioExpanderFriendlyName29 OBJECT-TYPE
	SYNTAX  DisplayString
	MAX-ACCESS  read-only
	STATUS current
	DESCRIPTION "IO 29 Friendly Name"
	::= { ioExpanderEntry  33 }
	
ioExpanderFriendlyName30 OBJECT-TYPE
	SYNTAX  DisplayString
	MAX-ACCESS  read-only
	STATUS current
	DESCRIPTION "IO 30 Friendly Name"
	::= { ioExpanderEntry  34 }
	
ioExpanderFriendlyName31 OBJECT-TYPE
	SYNTAX  DisplayString
	MAX-ACCESS  read-only
	STATUS current
	DESCRIPTION "IO 31 Friendly Name"
	::= { ioExpanderEntry  35 }
	
ioExpanderFriendlyName32 OBJECT-TYPE
	SYNTAX  DisplayString
	MAX-ACCESS  read-only
	STATUS current
	DESCRIPTION "IO 32 Friendly Name"
	::= { ioExpanderEntry  36 }
	
ioExpanderIO1 OBJECT-TYPE
	SYNTAX  INTEGER(0..100)
	MAX-ACCESS  read-only
	STATUS current
	DESCRIPTION "Current reading for Analog Input 1"
	::= { ioExpanderEntry  37 }
	
ioExpanderIO2 OBJECT-TYPE
	SYNTAX  INTEGER(0..100)
	MAX-ACCESS  read-only
	STATUS current
	DESCRIPTION "Current reading for Analog Input 2"
	::= { ioExpanderEntry  38 }
	
ioExpanderIO3 OBJECT-TYPE
	SYNTAX  INTEGER(0..100)
	MAX-ACCESS  read-only
	STATUS current
	DESCRIPTION "Current reading for Analog Input 3"
	::= { ioExpanderEntry  39 }
	
ioExpanderIO4 OBJECT-TYPE
	SYNTAX  INTEGER(0..100)
	MAX-ACCESS  read-only
	STATUS current
	DESCRIPTION "Current reading for Analog Input 4"
	::= { ioExpanderEntry  40 }
	
ioExpanderIO5 OBJECT-TYPE
	SYNTAX  INTEGER(0..100)
	MAX-ACCESS  read-only
	STATUS current
	DESCRIPTION "Current reading for Analog Input 5"
	::= { ioExpanderEntry  41 }
	
ioExpanderIO6 OBJECT-TYPE
	SYNTAX  INTEGER(0..100)
	MAX-ACCESS  read-only
	STATUS current
	DESCRIPTION "Current reading for Analog Input 6"
	::= { ioExpanderEntry  42 }
	
ioExpanderIO7 OBJECT-TYPE
	SYNTAX  INTEGER(0..100)
	MAX-ACCESS  read-only
	STATUS current
	DESCRIPTION "Current reading for Analog Input 7"
	::= { ioExpanderEntry  43 }
	
ioExpanderIO8 OBJECT-TYPE
	SYNTAX  INTEGER(0..100)
	MAX-ACCESS  read-only
	STATUS current
	DESCRIPTION "Current reading for Analog Input 8"
	::= { ioExpanderEntry  44 }
	
ioExpanderIO9 OBJECT-TYPE
	SYNTAX  INTEGER(0..100)
	MAX-ACCESS  read-only
	STATUS current
	DESCRIPTION "Current reading for Analog Input 9"
	::= { ioExpanderEntry  45 }
	
ioExpanderIO10 OBJECT-TYPE
	SYNTAX  INTEGER(0..100)
	MAX-ACCESS  read-only
	STATUS current
	DESCRIPTION "Current reading for Analog Input 10"
	::= { ioExpanderEntry  46 }
	
ioExpanderIO11 OBJECT-TYPE
	SYNTAX  INTEGER(0..100)
	MAX-ACCESS  read-only
	STATUS current
	DESCRIPTION "Current reading for Analog Input 11"
	::= { ioExpanderEntry  47 }
	
ioExpanderIO12 OBJECT-TYPE
	SYNTAX  INTEGER(0..100)
	MAX-ACCESS  read-only
	STATUS current
	DESCRIPTION "Current reading for Analog Input 12"
	::= { ioExpanderEntry  48 }
	
ioExpanderIO13 OBJECT-TYPE
	SYNTAX  INTEGER(0..100)
	MAX-ACCESS  read-only
	STATUS current
	DESCRIPTION "Current reading for Analog Input 13"
	::= { ioExpanderEntry  49 }
	
ioExpanderIO14 OBJECT-TYPE
	SYNTAX  INTEGER(0..100)
	MAX-ACCESS  read-only
	STATUS current
	DESCRIPTION "Current reading for Analog Input 14"
	::= { ioExpanderEntry  50 }
	
ioExpanderIO15 OBJECT-TYPE
	SYNTAX  INTEGER(0..100)
	MAX-ACCESS  read-only
	STATUS current
	DESCRIPTION "Current reading for Analog Input 15"
	::= { ioExpanderEntry  51 }
	
ioExpanderIO16 OBJECT-TYPE
	SYNTAX  INTEGER(0..100)
	MAX-ACCESS  read-only
	STATUS current
	DESCRIPTION "Current reading for Analog Input 16"
	::= { ioExpanderEntry  52 }
	
ioExpanderIO17 OBJECT-TYPE
	SYNTAX  INTEGER(0..100)
	MAX-ACCESS  read-only
	STATUS current
	DESCRIPTION "Current reading for Analog Input 17"
	::= { ioExpanderEntry  53 }
	
ioExpanderIO18 OBJECT-TYPE
	SYNTAX  INTEGER(0..100)
	MAX-ACCESS  read-only
	STATUS current
	DESCRIPTION "Current reading for Analog Input 18"
	::= { ioExpanderEntry  54 }
	
ioExpanderIO19 OBJECT-TYPE
	SYNTAX  INTEGER(0..100)
	MAX-ACCESS  read-only
	STATUS current
	DESCRIPTION "Current reading for Analog Input 19"
	::= { ioExpanderEntry  55 }
	
ioExpanderIO20 OBJECT-TYPE
	SYNTAX  INTEGER(0..100)
	MAX-ACCESS  read-only
	STATUS current
	DESCRIPTION "Current reading for Analog Input 20"
	::= { ioExpanderEntry  56 }
	
ioExpanderIO21 OBJECT-TYPE
	SYNTAX  INTEGER(0..100)
	MAX-ACCESS  read-only
	STATUS current
	DESCRIPTION "Current reading for Analog Input 21"
	::= { ioExpanderEntry  57 }
	
ioExpanderIO22 OBJECT-TYPE
	SYNTAX  INTEGER(0..100)
	MAX-ACCESS  read-only
	STATUS current
	DESCRIPTION "Current reading for Analog Input 22"
	::= { ioExpanderEntry  58 }
	
ioExpanderIO23 OBJECT-TYPE
	SYNTAX  INTEGER(0..100)
	MAX-ACCESS  read-only
	STATUS current
	DESCRIPTION "Current reading for Analog Input 23"
	::= { ioExpanderEntry  59 }
	
ioExpanderIO24 OBJECT-TYPE
	SYNTAX  INTEGER(0..100)
	MAX-ACCESS  read-only
	STATUS current
	DESCRIPTION "Current reading for Analog Input 24"
	::= { ioExpanderEntry  60 }
	
ioExpanderIO25 OBJECT-TYPE
	SYNTAX  INTEGER(0..100)
	MAX-ACCESS  read-only
	STATUS current
	DESCRIPTION "Current reading for Analog Input 25"
	::= { ioExpanderEntry  61 }
	
ioExpanderIO26 OBJECT-TYPE
	SYNTAX  INTEGER(0..100)
	MAX-ACCESS  read-only
	STATUS current
	DESCRIPTION "Current reading for Analog Input 26"
	::= { ioExpanderEntry  62 }
	
ioExpanderIO27 OBJECT-TYPE
	SYNTAX  INTEGER(0..100)
	MAX-ACCESS  read-only
	STATUS current
	DESCRIPTION "Current reading for Analog Input 27"
	::= { ioExpanderEntry  63 }
	
ioExpanderIO28 OBJECT-TYPE
	SYNTAX  INTEGER(0..100)
	MAX-ACCESS  read-only
	STATUS current
	DESCRIPTION "Current reading for Analog Input 28"
	::= { ioExpanderEntry  64 }
	
ioExpanderIO29 OBJECT-TYPE
	SYNTAX  INTEGER(0..100)
	MAX-ACCESS  read-only
	STATUS current
	DESCRIPTION "Current reading for Analog Input 29"
	::= { ioExpanderEntry  65 }
	
ioExpanderIO30 OBJECT-TYPE
	SYNTAX  INTEGER(0..100)
	MAX-ACCESS  read-only
	STATUS current
	DESCRIPTION "Current reading for Analog Input 30"
	::= { ioExpanderEntry  66 }
	
ioExpanderIO31 OBJECT-TYPE
	SYNTAX  INTEGER(0..100)
	MAX-ACCESS  read-only
	STATUS current
	DESCRIPTION "Current reading for Analog Input 31"
	::= { ioExpanderEntry  67 }
	
ioExpanderIO32 OBJECT-TYPE
	SYNTAX  INTEGER(0..100)
	MAX-ACCESS  read-only
	STATUS current
	DESCRIPTION "Current reading for Analog Input 32"
	::= { ioExpanderEntry  68 }
	
ioExpanderRelayName1 OBJECT-TYPE
	SYNTAX  DisplayString
	MAX-ACCESS  read-write
	STATUS current
	DESCRIPTION "Relay1 Friendly Name"
	::= { ioExpanderEntry  69 }
	
ioExpanderRelayState1 OBJECT-TYPE
	SYNTAX  Gauge32
	MAX-ACCESS  read-only
	STATUS current
	DESCRIPTION "Relay1 Current Status: 0 = Off, 1 = On"
	::= { ioExpanderEntry  70 }
	
ioExpanderRelayLatchingMode1 OBJECT-TYPE
	SYNTAX  Gauge32
	MAX-ACCESS  read-write
	STATUS current
	DESCRIPTION "Relay1 Latching mode: 0 = Non-latching, 1 = Latching"
	::= { ioExpanderEntry  71 }
	
ioExpanderRelayOverride1 OBJECT-TYPE
	SYNTAX  Gauge32
	MAX-ACCESS  read-write
	STATUS current
	DESCRIPTION "Relay1 Override Mode: 0 - None, 1 - On, 2 - Off"
	::= { ioExpanderEntry  72 }
	
ioExpanderRelayAcknowledge1 OBJECT-TYPE
	SYNTAX  Gauge32
	MAX-ACCESS  read-write
	STATUS current
	DESCRIPTION "Relay1 Acknowledge write a 1, always reads back 0"
	::= { ioExpanderEntry  73 }
	
ioExpanderRelayName2 OBJECT-TYPE
	SYNTAX  DisplayString
	MAX-ACCESS  read-write
	STATUS current
	DESCRIPTION "Relay2 Friendly Name"
	::= { ioExpanderEntry  74 }
	
ioExpanderRelayState2 OBJECT-TYPE
	SYNTAX  Gauge32
	MAX-ACCESS  read-only
	STATUS current
	DESCRIPTION "Relay2 Current Status: 0 = Off, 1 = On"
	::= { ioExpanderEntry  75 }
	
ioExpanderRelayLatchingMode2 OBJECT-TYPE
	SYNTAX  Gauge32
	MAX-ACCESS  read-write
	STATUS current
	DESCRIPTION "Relay2 Latching mode: 0 = Non-latching, 1 = Latching"
	::= { ioExpanderEntry  76 }
	
ioExpanderRelayOverride2 OBJECT-TYPE
	SYNTAX  Gauge32
	MAX-ACCESS  read-write
	STATUS current
	DESCRIPTION "Relay2 Override Mode: 0 - None, 1 - On, 2 - Off"
	::= { ioExpanderEntry  77 }
	
ioExpanderRelayAcknowledge2 OBJECT-TYPE
	SYNTAX  Gauge32
	MAX-ACCESS  read-write
	STATUS current
	DESCRIPTION "Relay2 Acknowledge write a 1, always reads back 0"
	::= { ioExpanderEntry  78 }
	
ioExpanderRelayName3 OBJECT-TYPE
	SYNTAX  DisplayString
	MAX-ACCESS  read-write
	STATUS current
	DESCRIPTION "Relay3 Friendly Name"
	::= { ioExpanderEntry  79 }
	
ioExpanderRelayState3 OBJECT-TYPE
	SYNTAX  Gauge32
	MAX-ACCESS  read-only
	STATUS current
	DESCRIPTION "Relay3 Current Status: 0 = Off, 1 = On"
	::= { ioExpanderEntry  80 }
	
ioExpanderRelayLatchingMode3 OBJECT-TYPE
	SYNTAX  Gauge32
	MAX-ACCESS  read-write
	STATUS current
	DESCRIPTION "Relay3 Latching mode: 0 = Non-latching, 1 = Latching"
	::= { ioExpanderEntry  81 }
	
ioExpanderRelayOverride3 OBJECT-TYPE
	SYNTAX  Gauge32
	MAX-ACCESS  read-write
	STATUS current
	DESCRIPTION "Relay3 Override Mode: 0 - None, 1 - On, 2 - Off"
	::= { ioExpanderEntry  82 }
	
ioExpanderRelayAcknowledge3 OBJECT-TYPE
	SYNTAX  Gauge32
	MAX-ACCESS  read-write
	STATUS current
	DESCRIPTION "Relay3 Acknowledge write a 1, always reads back 0"
	::= { ioExpanderEntry  83 }
	
t3hdSensorEntry OBJECT-TYPE
	SYNTAX  T3hdSensorEntry
	MAX-ACCESS  not-accessible
	STATUS current
	DESCRIPTION 
		"Entry in the T3HD sensor table: each entry contains
an index (t3hdIndex) and other sensor details"
	INDEX { t3hdSensorIndex }
	::= { t3hdSensorTable 1 }

T3hdSensorEntry ::= SEQUENCE {
	t3hdSensorIndex		INTEGER,
	t3hdSensorSerial		DisplayString,
	t3hdSensorName		DisplayString,
	t3hdSensorAvail		Gauge32,
	t3hdSensorIntName		DisplayString,
	t3hdSensorIntTempC		INTEGER,
	t3hdSensorIntTempF		INTEGER,
	t3hdSensorIntHumidity		INTEGER,
	t3hdSensorIntDewPointC		INTEGER,
	t3hdSensorIntDewPointF		INTEGER,
	t3hdSensorExt1Avail		Gauge32,
	t3hdSensorExt1Name		DisplayString,
	t3hdSensorExt1TempC		INTEGER,
	t3hdSensorExt1TempF		INTEGER,
	t3hdSensorExt2Avail		Gauge32,
	t3hdSensorExt2Name		DisplayString,
	t3hdSensorExt2TempC		INTEGER,
	t3hdSensorExt2TempF		INTEGER
}

t3hdSensorIndex OBJECT-TYPE
	SYNTAX  INTEGER(1..100)
	MAX-ACCESS  not-accessible
	STATUS current
	DESCRIPTION "Table entry index value"
	::= { t3hdSensorEntry  1 }
	
t3hdSensorSerial OBJECT-TYPE
	SYNTAX  DisplayString
	MAX-ACCESS  read-only
	STATUS current
	DESCRIPTION "Serial Number"
	::= { t3hdSensorEntry  2 }
	
t3hdSensorName OBJECT-TYPE
	SYNTAX  DisplayString
	MAX-ACCESS  read-only
	STATUS current
	DESCRIPTION "Friendly Name"
	::= { t3hdSensorEntry  3 }
	
t3hdSensorAvail OBJECT-TYPE
	SYNTAX  Gauge32
	MAX-ACCESS  read-only
	STATUS current
	DESCRIPTION "Is device currently plugged in?"
	::= { t3hdSensorEntry  4 }
	
t3hdSensorIntName OBJECT-TYPE
	SYNTAX  DisplayString
	MAX-ACCESS  read-only
	STATUS current
	DESCRIPTION "Internal Friendly Name"
	::= { t3hdSensorEntry  5 }
	
t3hdSensorIntTempC OBJECT-TYPE
	SYNTAX  INTEGER(-50..100)
	UNITS "Degrees Celsius"
	MAX-ACCESS  read-only
	STATUS current
	DESCRIPTION "Internal Temperature reading in C"
	::= { t3hdSensorEntry  6 }
	
t3hdSensorIntTempF OBJECT-TYPE
	SYNTAX  INTEGER(-58..212)
	UNITS "Degrees Fahrenheit"
	MAX-ACCESS  read-only
	STATUS current
	DESCRIPTION "Internal Temperature reading in F"
	::= { t3hdSensorEntry  7 }
	
t3hdSensorIntHumidity OBJECT-TYPE
	SYNTAX  INTEGER(0..100)
	UNITS "%"
	MAX-ACCESS  read-only
	STATUS current
	DESCRIPTION "Internal Humidity reading"
	::= { t3hdSensorEntry  8 }
	
t3hdSensorIntDewPointC OBJECT-TYPE
	SYNTAX  INTEGER(-50..100)
	UNITS "Degrees Celsius"
	MAX-ACCESS  read-only
	STATUS current
	DESCRIPTION "Internal Dew Point reading in C"
	::= { t3hdSensorEntry  9 }
	
t3hdSensorIntDewPointF OBJECT-TYPE
	SYNTAX  INTEGER(-58..212)
	UNITS "Degress Fahrenheit"
	MAX-ACCESS  read-only
	STATUS current
	DESCRIPTION "Internal Dew Point reading in F"
	::= { t3hdSensorEntry  10 }
	
t3hdSensorExt1Avail OBJECT-TYPE
	SYNTAX  Gauge32
	MAX-ACCESS  read-only
	STATUS current
	DESCRIPTION "External 1 status: 0 = unplugged, 1 = normal operation, 2 = device error"
	::= { t3hdSensorEntry  11 }
	
t3hdSensorExt1Name OBJECT-TYPE
	SYNTAX  DisplayString
	MAX-ACCESS  read-only
	STATUS current
	DESCRIPTION "External 1 Friendly Name"
	::= { t3hdSensorEntry  12 }
	
t3hdSensorExt1TempC OBJECT-TYPE
	SYNTAX  INTEGER(-50..100)
	UNITS "Degrees Celsius"
	MAX-ACCESS  read-only
	STATUS current
	DESCRIPTION "External 1 Temperature reading in C"
	::= { t3hdSensorEntry  13 }
	
t3hdSensorExt1TempF OBJECT-TYPE
	SYNTAX  INTEGER(-58..212)
	UNITS "Degress Fahrenheit"
	MAX-ACCESS  read-only
	STATUS current
	DESCRIPTION "External 1 Temperature reading in F"
	::= { t3hdSensorEntry  14 }
	
t3hdSensorExt2Avail OBJECT-TYPE
	SYNTAX  Gauge32
	MAX-ACCESS  read-only
	STATUS current
	DESCRIPTION "External 2 status: 0 = unplugged, 1 = normal operation, 2 = device error"
	::= { t3hdSensorEntry  15 }
	
t3hdSensorExt2Name OBJECT-TYPE
	SYNTAX  DisplayString
	MAX-ACCESS  read-only
	STATUS current
	DESCRIPTION "External 2 Friendly Name"
	::= { t3hdSensorEntry  16 }
	
t3hdSensorExt2TempC OBJECT-TYPE
	SYNTAX  INTEGER(-50..100)
	UNITS "Degrees Celsius"
	MAX-ACCESS  read-only
	STATUS current
	DESCRIPTION "External 2 Temperature reading in C"
	::= { t3hdSensorEntry  17 }
	
t3hdSensorExt2TempF OBJECT-TYPE
	SYNTAX  INTEGER(-58..212)
	UNITS "Degress Fahrenheit"
	MAX-ACCESS  read-only
	STATUS current
	DESCRIPTION "External 2 Temperature reading in F"
	::= { t3hdSensorEntry  18 }
	
thdSensorEntry OBJECT-TYPE
	SYNTAX  ThdSensorEntry
	MAX-ACCESS  not-accessible
	STATUS current
	DESCRIPTION 
		"Entry in the THD sensor table: each entry contains
an index (thdIndex) and other sensor details"
	INDEX { thdSensorIndex }
	::= { thdSensorTable 1 }

ThdSensorEntry ::= SEQUENCE {
	thdSensorIndex		INTEGER,
	thdSensorSerial		DisplayString,
	thdSensorName		DisplayString,
	thdSensorAvail		Gauge32,
	thdSensorTempC		INTEGER,
	thdSensorTempF		INTEGER,
	thdSensorHumidity		INTEGER,
	thdSensorDewPointC		INTEGER,
	thdSensorDewPointF		INTEGER
}

thdSensorIndex OBJECT-TYPE
	SYNTAX  INTEGER(1..100)
	MAX-ACCESS  not-accessible
	STATUS current
	DESCRIPTION "Table entry index value"
	::= { thdSensorEntry  1 }
	
thdSensorSerial OBJECT-TYPE
	SYNTAX  DisplayString
	MAX-ACCESS  read-only
	STATUS current
	DESCRIPTION "Serial Number"
	::= { thdSensorEntry  2 }
	
thdSensorName OBJECT-TYPE
	SYNTAX  DisplayString
	MAX-ACCESS  read-only
	STATUS current
	DESCRIPTION "Friendly Name"
	::= { thdSensorEntry  3 }
	
thdSensorAvail OBJECT-TYPE
	SYNTAX  Gauge32
	MAX-ACCESS  read-only
	STATUS current
	DESCRIPTION "Is device currently plugged in?"
	::= { thdSensorEntry  4 }
	
thdSensorTempC OBJECT-TYPE
	SYNTAX  INTEGER(-50..100)
	UNITS "Degrees Celsius"
	MAX-ACCESS  read-only
	STATUS current
	DESCRIPTION "Temperature reading in C"
	::= { thdSensorEntry  5 }
	
thdSensorTempF OBJECT-TYPE
	SYNTAX  INTEGER(-58..212)
	UNITS "Degrees Fahrenheit"
	MAX-ACCESS  read-only
	STATUS current
	DESCRIPTION "Temperature reading in F"
	::= { thdSensorEntry  6 }
	
thdSensorHumidity OBJECT-TYPE
	SYNTAX  INTEGER(0..100)
	UNITS "%"
	MAX-ACCESS  read-only
	STATUS current
	DESCRIPTION "Humidity reading"
	::= { thdSensorEntry  7 }
	
thdSensorDewPointC OBJECT-TYPE
	SYNTAX  INTEGER(-50..100)
	UNITS "Degrees Celsius"
	MAX-ACCESS  read-only
	STATUS current
	DESCRIPTION "Dew Point reading in C"
	::= { thdSensorEntry  8 }
	
thdSensorDewPointF OBJECT-TYPE
	SYNTAX  INTEGER(-58..212)
	UNITS "Degress Fahrenheit"
	MAX-ACCESS  read-only
	STATUS current
	DESCRIPTION "Dew Point reading in F"
	::= { thdSensorEntry  9 }
	
pos60VdcSensorEntry OBJECT-TYPE
	SYNTAX  Pos60VdcSensorEntry
	MAX-ACCESS  not-accessible
	STATUS current
	DESCRIPTION 
		"Entry in the 60Vdc sensor table: each entry contains
an index (pos60VdcSensorIndex) and other sensor details"
	INDEX { pos60VdcSensorIndex }
	::= { pos60VdcSensorTable 1 }

Pos60VdcSensorEntry ::= SEQUENCE {
	pos60VdcSensorIndex		INTEGER,
	pos60VdcSensorSerial		DisplayString,
	pos60VdcSensorName		DisplayString,
	pos60VdcSensorAvail		Gauge32,
	pos60VdcSensorVoltage		INTEGER
}

pos60VdcSensorIndex OBJECT-TYPE
	SYNTAX  INTEGER(1..100)
	MAX-ACCESS  not-accessible
	STATUS current
	DESCRIPTION "Table entry index value"
	::= { pos60VdcSensorEntry  1 }
	
pos60VdcSensorSerial OBJECT-TYPE
	SYNTAX  DisplayString
	MAX-ACCESS  read-only
	STATUS current
	DESCRIPTION "Serial Number"
	::= { pos60VdcSensorEntry  2 }
	
pos60VdcSensorName OBJECT-TYPE
	SYNTAX  DisplayString
	MAX-ACCESS  read-only
	STATUS current
	DESCRIPTION "Friendly Name"
	::= { pos60VdcSensorEntry  3 }
	
pos60VdcSensorAvail OBJECT-TYPE
	SYNTAX  Gauge32
	MAX-ACCESS  read-only
	STATUS current
	DESCRIPTION "Is device currently plugged in?"
	::= { pos60VdcSensorEntry  4 }
	
pos60VdcSensorVoltage OBJECT-TYPE
	SYNTAX  INTEGER(-10..100)
	UNITS "Volts"
	MAX-ACCESS  read-only
	STATUS current
	DESCRIPTION "60Vdc Sensor value"
	::= { pos60VdcSensorEntry  5 }
	
ctrl2CirTotEntry OBJECT-TYPE
	SYNTAX  Ctrl2CirTotEntry
	MAX-ACCESS  not-accessible
	STATUS current
	DESCRIPTION 
		"Entry in the 3 phase outlet control table: each entry contains
an index (ctrl2CirTotIndex) and other outlet control monitoring details"
	INDEX { ctrl2CirTotIndex }
	::= { ctrl2CirTotTable 1 }

Ctrl2CirTotEntry ::= SEQUENCE {
	ctrl2CirTotIndex		INTEGER,
	ctrl2CirTotSerial		DisplayString,
	ctrl2CirTotName		DisplayString,
	ctrl2CirTotAvail		Gauge32,
	ctrl2CirTotkWattHrsTot		Gauge32,
	ctrl2CirTotVoltsTot		Gauge32,
	ctrl2CirTotVoltPeakTot		Gauge32,
	ctrl2CirTotDeciAmpsTot		Gauge32,
	ctrl2CirTotDeciAmpsPeakTot		Gauge32,
	ctrl2CirTotRealPowerTot		Gauge32,
	ctrl2CirTotApparentPowerTot		Gauge32,
	ctrl2CirTotPowerFactorTot		INTEGER,
	ctrl2CirTotkWattHrsA		Gauge32,
	ctrl2CirTotVoltsA		Gauge32,
	ctrl2CirTotVoltPeakA		Gauge32,
	ctrl2CirTotDeciAmpsA		Gauge32,
	ctrl2CirTotDeciAmpsPeakA		Gauge32,
	ctrl2CirTotRealPowerA		Gauge32,
	ctrl2CirTotApparentPowerA		Gauge32,
	ctrl2CirTotPowerFactorA		INTEGER,
	ctrl2CirTotkWattHrsB		Gauge32,
	ctrl2CirTotVoltsB		Gauge32,
	ctrl2CirTotVoltPeakB		Gauge32,
	ctrl2CirTotDeciAmpsB		Gauge32,
	ctrl2CirTotDeciAmpsPeakB		Gauge32,
	ctrl2CirTotRealPowerB		Gauge32,
	ctrl2CirTotApparentPowerB		Gauge32,
	ctrl2CirTotPowerFactorB		INTEGER
}

ctrl2CirTotIndex OBJECT-TYPE
	SYNTAX  INTEGER(1..100)
	MAX-ACCESS  not-accessible
	STATUS current
	DESCRIPTION "Table entry index value"
	::= { ctrl2CirTotEntry  1 }
	
ctrl2CirTotSerial OBJECT-TYPE
	SYNTAX  DisplayString
	MAX-ACCESS  read-only
	STATUS current
	DESCRIPTION "Serial Number"
	::= { ctrl2CirTotEntry  2 }
	
ctrl2CirTotName OBJECT-TYPE
	SYNTAX  DisplayString
	MAX-ACCESS  read-only
	STATUS current
	DESCRIPTION "Friendly Name"
	::= { ctrl2CirTotEntry  3 }
	
ctrl2CirTotAvail OBJECT-TYPE
	SYNTAX  Gauge32
	MAX-ACCESS  read-only
	STATUS current
	DESCRIPTION "Is device currently plugged in?"
	::= { ctrl2CirTotEntry  4 }
	
ctrl2CirTotkWattHrsTot OBJECT-TYPE
	SYNTAX  Gauge32
	UNITS "kWh"
	MAX-ACCESS  read-only
	STATUS current
	DESCRIPTION "Current Reading for kWatt-Hours (Total)"
	::= { ctrl2CirTotEntry  5 }
	
ctrl2CirTotVoltsTot OBJECT-TYPE
	SYNTAX  Gauge32
	UNITS "Volts (rms)"
	MAX-ACCESS  read-only
	STATUS current
	DESCRIPTION "Current reading for Volts (Total)"
	::= { ctrl2CirTotEntry  6 }
	
ctrl2CirTotVoltPeakTot OBJECT-TYPE
	SYNTAX  Gauge32
	UNITS "Volts (rms)"
	MAX-ACCESS  read-only
	STATUS current
	DESCRIPTION "Current reading for Peak-Volts (Total)"
	::= { ctrl2CirTotEntry  7 }
	
ctrl2CirTotDeciAmpsTot OBJECT-TYPE
	SYNTAX  Gauge32
	UNITS "0.1 Amps (rms)"
	MAX-ACCESS  read-only
	STATUS current
	DESCRIPTION "Current reading for DeciAmps (Total)"
	::= { ctrl2CirTotEntry  8 }
	
ctrl2CirTotDeciAmpsPeakTot OBJECT-TYPE
	SYNTAX  Gauge32
	UNITS "0.1 Amps (rms)"
	MAX-ACCESS  read-only
	STATUS current
	DESCRIPTION "Current reading for Peak-DeciAmps (Total)"
	::= { ctrl2CirTotEntry  9 }
	
ctrl2CirTotRealPowerTot OBJECT-TYPE
	SYNTAX  Gauge32
	UNITS "Watts"
	MAX-ACCESS  read-only
	STATUS current
	DESCRIPTION "Current reading for Real Power (Total)"
	::= { ctrl2CirTotEntry  10 }
	
ctrl2CirTotApparentPowerTot OBJECT-TYPE
	SYNTAX  Gauge32
	UNITS "Volt-Amps"
	MAX-ACCESS  read-only
	STATUS current
	DESCRIPTION "Current reading for Apparent Power (Total)"
	::= { ctrl2CirTotEntry  11 }
	
ctrl2CirTotPowerFactorTot OBJECT-TYPE
	SYNTAX  INTEGER(0..100)
	UNITS "%"
	MAX-ACCESS  read-only
	STATUS current
	DESCRIPTION "Current reading for Power Factor (Total)"
	::= { ctrl2CirTotEntry  12 }
	
ctrl2CirTotkWattHrsA OBJECT-TYPE
	SYNTAX  Gauge32
	UNITS "kWh"
	MAX-ACCESS  read-only
	STATUS current
	DESCRIPTION "Current Reading for kWatt-Hours (Phase A)"
	::= { ctrl2CirTotEntry  13 }
	
ctrl2CirTotVoltsA OBJECT-TYPE
	SYNTAX  Gauge32
	UNITS "Volts (rms)"
	MAX-ACCESS  read-only
	STATUS current
	DESCRIPTION "Current reading for Volts (Phase A)"
	::= { ctrl2CirTotEntry  14 }
	
ctrl2CirTotVoltPeakA OBJECT-TYPE
	SYNTAX  Gauge32
	UNITS "Volts (rms)"
	MAX-ACCESS  read-only
	STATUS current
	DESCRIPTION "Current reading for Peak-Volts (Phase A)"
	::= { ctrl2CirTotEntry  15 }
	
ctrl2CirTotDeciAmpsA OBJECT-TYPE
	SYNTAX  Gauge32
	UNITS "0.1 Amps (rms)"
	MAX-ACCESS  read-only
	STATUS current
	DESCRIPTION "Current reading for DeciAmps (Phase A)"
	::= { ctrl2CirTotEntry  16 }
	
ctrl2CirTotDeciAmpsPeakA OBJECT-TYPE
	SYNTAX  Gauge32
	UNITS "0.1 Amps (rms)"
	MAX-ACCESS  read-only
	STATUS current
	DESCRIPTION "Current reading for Peak-DeciAmps (Phase A)"
	::= { ctrl2CirTotEntry  17 }
	
ctrl2CirTotRealPowerA OBJECT-TYPE
	SYNTAX  Gauge32
	UNITS "Watts"
	MAX-ACCESS  read-only
	STATUS current
	DESCRIPTION "Current reading for Real Power (Phase A)"
	::= { ctrl2CirTotEntry  18 }
	
ctrl2CirTotApparentPowerA OBJECT-TYPE
	SYNTAX  Gauge32
	UNITS "Volt-Amps"
	MAX-ACCESS  read-only
	STATUS current
	DESCRIPTION "Current reading for Apparent Power (Phase A)"
	::= { ctrl2CirTotEntry  19 }
	
ctrl2CirTotPowerFactorA OBJECT-TYPE
	SYNTAX  INTEGER(0..100)
	UNITS "%"
	MAX-ACCESS  read-only
	STATUS current
	DESCRIPTION "Current reading for Power Factor (Phase A)"
	::= { ctrl2CirTotEntry  20 }
	
ctrl2CirTotkWattHrsB OBJECT-TYPE
	SYNTAX  Gauge32
	UNITS "kWh"
	MAX-ACCESS  read-only
	STATUS current
	DESCRIPTION "Current Reading for kWatt-Hours (Phase B)"
	::= { ctrl2CirTotEntry  21 }
	
ctrl2CirTotVoltsB OBJECT-TYPE
	SYNTAX  Gauge32
	UNITS "Volts (rms)"
	MAX-ACCESS  read-only
	STATUS current
	DESCRIPTION "Current reading for Volts (Phase B)"
	::= { ctrl2CirTotEntry  22 }
	
ctrl2CirTotVoltPeakB OBJECT-TYPE
	SYNTAX  Gauge32
	UNITS "Volts (rms)"
	MAX-ACCESS  read-only
	STATUS current
	DESCRIPTION "Current reading for Peak-Volts (Phase B)"
	::= { ctrl2CirTotEntry  23 }
	
ctrl2CirTotDeciAmpsB OBJECT-TYPE
	SYNTAX  Gauge32
	UNITS "0.1 Amps (rms)"
	MAX-ACCESS  read-only
	STATUS current
	DESCRIPTION "Current reading for DeciAmps (Phase B)"
	::= { ctrl2CirTotEntry  24 }
	
ctrl2CirTotDeciAmpsPeakB OBJECT-TYPE
	SYNTAX  Gauge32
	UNITS "0.1 Amps (rms)"
	MAX-ACCESS  read-only
	STATUS current
	DESCRIPTION "Current reading for Peak-DeciAmps (Phase B)"
	::= { ctrl2CirTotEntry  25 }
	
ctrl2CirTotRealPowerB OBJECT-TYPE
	SYNTAX  Gauge32
	UNITS "Watts"
	MAX-ACCESS  read-only
	STATUS current
	DESCRIPTION "Current reading for Real Power (Phase B)"
	::= { ctrl2CirTotEntry  26 }
	
ctrl2CirTotApparentPowerB OBJECT-TYPE
	SYNTAX  Gauge32
	UNITS "Volt-Amps"
	MAX-ACCESS  read-only
	STATUS current
	DESCRIPTION "Current reading for Apparent Power (Phase B)"
	::= { ctrl2CirTotEntry  27 }
	
ctrl2CirTotPowerFactorB OBJECT-TYPE
	SYNTAX  INTEGER(0..100)
	UNITS "%"
	MAX-ACCESS  read-only
	STATUS current
	DESCRIPTION "Current reading for Power Factor (Phase B)"
	::= { ctrl2CirTotEntry  28 }
	
sc10Entry OBJECT-TYPE
	SYNTAX  Sc10Entry
	MAX-ACCESS  not-accessible
	STATUS current
	DESCRIPTION 
		"Entry in the sc10 table: each entry contains
an index (sc10Index) and other details"
	INDEX { sc10Index }
	::= { sc10Table 1 }

Sc10Entry ::= SEQUENCE {
	sc10Index		INTEGER,
	sc10Serial		DisplayString,
	sc10Name		DisplayString,
	sc10Avail		Gauge32,
	sc10ControlMode		INTEGER,
	sc10SetpointC		INTEGER,
	sc10SetpointF		INTEGER,
	sc10TempC		INTEGER,
	sc10TempF		INTEGER,
	sc10Capacity		INTEGER
}

sc10Index OBJECT-TYPE
	SYNTAX  INTEGER(1..1)
	MAX-ACCESS  not-accessible
	STATUS current
	DESCRIPTION "Table entry index value"
	::= { sc10Entry  1 }
	
sc10Serial OBJECT-TYPE
	SYNTAX  DisplayString
	MAX-ACCESS  read-only
	STATUS current
	DESCRIPTION "Serial Number"
	::= { sc10Entry  2 }
	
sc10Name OBJECT-TYPE
	SYNTAX  DisplayString
	MAX-ACCESS  read-only
	STATUS current
	DESCRIPTION "Friendly Name"
	::= { sc10Entry  3 }
	
sc10Avail OBJECT-TYPE
	SYNTAX  Gauge32
	MAX-ACCESS  read-only
	STATUS current
	DESCRIPTION "Is device currently plugged in?"
	::= { sc10Entry  4 }
	
sc10ControlMode OBJECT-TYPE
	SYNTAX  INTEGER { setpoint(0), capacity(1) }
	MAX-ACCESS  read-only
	STATUS current
	DESCRIPTION "Control Mode setting indicator"
	::= { sc10Entry  5 }
	
sc10SetpointC OBJECT-TYPE
	SYNTAX  INTEGER(0..100)
	UNITS "Degrees Celsius"
	MAX-ACCESS  read-only
	STATUS current
	DESCRIPTION "Current temperature set point in C"
	::= { sc10Entry  6 }
	
sc10SetpointF OBJECT-TYPE
	SYNTAX  INTEGER(32..212)
	UNITS "Degrees Fahrenheit"
	MAX-ACCESS  read-only
	STATUS current
	DESCRIPTION "Current temperature set point in F"
	::= { sc10Entry  7 }
	
sc10TempC OBJECT-TYPE
	SYNTAX  INTEGER(0..100)
	UNITS "Degrees Celsius"
	MAX-ACCESS  read-only
	STATUS current
	DESCRIPTION "Current internal temperature reading in C"
	::= { sc10Entry  8 }
	
sc10TempF OBJECT-TYPE
	SYNTAX  INTEGER(32..212)
	UNITS "Degrees Fahrenheit"
	MAX-ACCESS  read-only
	STATUS current
	DESCRIPTION "Current internal temperature reading in F"
	::= { sc10Entry  9 }
	
sc10Capacity OBJECT-TYPE
	SYNTAX  INTEGER(0..100)
	UNITS "%"
	MAX-ACCESS  read-only
	STATUS current
	DESCRIPTION "Current capacity for Fan Speed"
	::= { sc10Entry  10 }
	


alarmSystem OBJECT IDENTIFIER
	::= { owl 101 }

	
alarmCfgTable OBJECT-TYPE
	SYNTAX SEQUENCE OF AlarmCfgEntry
	MAX-ACCESS  not-accessible
	STATUS current
	DESCRIPTION "Provides access for alarm configuration. Each row represents an alarm."
	::= { alarmSystem 1 }

	
alarmCfgEntry OBJECT-TYPE
	SYNTAX  AlarmCfgEntry          
	MAX-ACCESS  not-accessible
	STATUS current
	DESCRIPTION 
		"Entry in the alarm cfg table: each entry contains
		an index (alarmCfgIndex) and other details"
	INDEX { alarmCfgIndex }
	::= { alarmCfgTable 1 }

AlarmCfgEntry ::= SEQUENCE {
	alarmCfgIndex		INTEGER,              
	alarmCfgReadingID	OBJECT IDENTIFIER,
	alarmCfgThreshold	Integer32,
	alarmCfgTripSelect	INTEGER
}


alarmCfgIndex OBJECT-TYPE
	SYNTAX  INTEGER(1..200)
	MAX-ACCESS  not-accessible
	STATUS current                      
	DESCRIPTION 
		"Table entry index value. Provides unique ID for
		alarm, numbered from 1 to 200"
	::= { alarmCfgEntry  1 }

alarmCfgReadingID OBJECT-TYPE
	SYNTAX  OBJECT IDENTIFIER
	MAX-ACCESS  read-create
	STATUS current
	DESCRIPTION 
		"OID of a particular measurement to monitor. This object
		is also used to create or delete a row. To create a new
		row, set the Sensor ID on a row that doesn't exist. Set
		the ReadingID to 0.0 to destroy a row."
	::= { alarmCfgEntry  2 }

alarmCfgThreshold OBJECT-TYPE
	SYNTAX  Integer32
	UNITS "Tenths"      
	MAX-ACCESS  read-create
	STATUS current
	DESCRIPTION 
		"Depending on TripSelect this value acts as an upper or
		lower boundary for the sensor value. The value is in
		units of tenths. 
		SNMP Threshold = Actual Value * 10
		Example: 45 Threshold = 4.5 Amps"
	::= { alarmCfgEntry  3 }

alarmCfgTripSelect OBJECT-TYPE
	SYNTAX  INTEGER { tripBelow(0), tripAbove(1) }
	MAX-ACCESS  read-create        
	STATUS current
	DESCRIPTION 
		"Tells if alarm trips above or below the threshold value"
	::= { alarmCfgEntry  4 }


cmTrap OBJECT IDENTIFIER ::= { owl 32767 }
cmTrapPrefix OBJECT IDENTIFIER ::= { cmTrap 0 }

cmTestNOTIFY NOTIFICATION-TYPE
	STATUS current
	DESCRIPTION "Test SNMP Trap"
	::= { cmTrapPrefix 10101 }
	
cmClimateTempCNOTIFY NOTIFICATION-TYPE
OBJECTS { climateTempC, climateName, productFriendlyName, alarmTripType, temperaturePrecision, alarmTrigger, alarmInstance }
STATUS current
DESCRIPTION "Climate Temperature Sensor Trap"
::= { cmTrapPrefix 10205 }

cmClimateTempFNOTIFY NOTIFICATION-TYPE
OBJECTS { climateTempF, climateName, productFriendlyName, alarmTripType, temperaturePrecision, alarmTrigger, alarmInstance }
STATUS current
DESCRIPTION "Climate Temperature Sensor Trap"
::= { cmTrapPrefix 10206 }

cmClimateHumidityNOTIFY NOTIFICATION-TYPE
OBJECTS { climateHumidity, climateName, productFriendlyName, alarmTripType, alarmTrigger, alarmInstance }
STATUS current
DESCRIPTION "Climate Humidity Sensor Trap"
::= { cmTrapPrefix 10207 }

cmClimateLightNOTIFY NOTIFICATION-TYPE
OBJECTS { climateLight, climateName, productFriendlyName, alarmTripType, alarmTrigger, alarmInstance }
STATUS current
DESCRIPTION "Climate Light Sensor Trap"
::= { cmTrapPrefix 10208 }

cmClimateAirflowNOTIFY NOTIFICATION-TYPE
OBJECTS { climateAirflow, climateName, productFriendlyName, alarmTripType, alarmTrigger, alarmInstance }
STATUS current
DESCRIPTION "Climate Air Flow Sensor Trap"
::= { cmTrapPrefix 10209 }

cmClimateSoundNOTIFY NOTIFICATION-TYPE
OBJECTS { climateSound, climateName, productFriendlyName, alarmTripType, alarmTrigger, alarmInstance }
STATUS current
DESCRIPTION "Climate Sound Sensor Trap"
::= { cmTrapPrefix 10210 }

cmClimateIO1NOTIFY NOTIFICATION-TYPE
OBJECTS { climateIO1, climateName, productFriendlyName, alarmTripType, alarmTrigger, alarmInstance }
STATUS current
DESCRIPTION "Climate IO1 Sensor Trap"
::= { cmTrapPrefix 10211 }

cmClimateIO2NOTIFY NOTIFICATION-TYPE
OBJECTS { climateIO2, climateName, productFriendlyName, alarmTripType, alarmTrigger, alarmInstance }
STATUS current
DESCRIPTION "Climate IO2 Sensor Trap"
::= { cmTrapPrefix 10212 }

cmClimateIO3NOTIFY NOTIFICATION-TYPE
OBJECTS { climateIO3, climateName, productFriendlyName, alarmTripType, alarmTrigger, alarmInstance }
STATUS current
DESCRIPTION "Climate IO3 Sensor Trap"
::= { cmTrapPrefix 10213 }

cmClimateDewPointCNOTIFY NOTIFICATION-TYPE
OBJECTS { climateDewPointC, climateName, productFriendlyName, alarmTripType, temperaturePrecision, alarmTrigger, alarmInstance }
STATUS current
DESCRIPTION "Climate Dew Point Sensor Trap"
::= { cmTrapPrefix 10214 }

cmClimateDewPointFNOTIFY NOTIFICATION-TYPE
OBJECTS { climateDewPointF, climateName, productFriendlyName, alarmTripType, temperaturePrecision, alarmTrigger, alarmInstance }
STATUS current
DESCRIPTION "Climate Dew Point Sensor Trap"
::= { cmTrapPrefix 10215 }

cmPowMonkWattHrsNOTIFY NOTIFICATION-TYPE
OBJECTS { powMonkWattHrs, powMonName, productFriendlyName, alarmTripType, alarmTrigger, alarmInstance }
STATUS current
DESCRIPTION "Kilo Watt Hours Trap"
::= { cmTrapPrefix 10305 }

cmPowMonVoltsNOTIFY NOTIFICATION-TYPE
OBJECTS { powMonVolts, powMonName, productFriendlyName, alarmTripType, alarmTrigger, alarmInstance }
STATUS current
DESCRIPTION "Volts Trap"
::= { cmTrapPrefix 10306 }

cmPowMonVoltMaxNOTIFY NOTIFICATION-TYPE
OBJECTS { powMonVoltMax, powMonName, productFriendlyName, alarmTripType, alarmTrigger, alarmInstance }
STATUS current
DESCRIPTION "Volts Max Trap"
::= { cmTrapPrefix 10307 }

cmPowMonVoltMinNOTIFY NOTIFICATION-TYPE
OBJECTS { powMonVoltMin, powMonName, productFriendlyName, alarmTripType, alarmTrigger, alarmInstance }
STATUS current
DESCRIPTION "Volts Min Trap"
::= { cmTrapPrefix 10308 }

cmPowMonVoltPeakNOTIFY NOTIFICATION-TYPE
OBJECTS { powMonVoltPeak, powMonName, productFriendlyName, alarmTripType, alarmTrigger, alarmInstance }
STATUS current
DESCRIPTION "Volt Peak Trap"
::= { cmTrapPrefix 10309 }

cmPowMonDeciAmpsNOTIFY NOTIFICATION-TYPE
OBJECTS { powMonDeciAmps, powMonName, productFriendlyName, alarmTripType, alarmTrigger, alarmInstance }
STATUS current
DESCRIPTION "DeciAmps Trap"
::= { cmTrapPrefix 10310 }

cmPowMonRealPowerNOTIFY NOTIFICATION-TYPE
OBJECTS { powMonRealPower, powMonName, productFriendlyName, alarmTripType, alarmTrigger, alarmInstance }
STATUS current
DESCRIPTION "Real Power Trap"
::= { cmTrapPrefix 10311 }

cmPowMonApparentPowerNOTIFY NOTIFICATION-TYPE
OBJECTS { powMonApparentPower, powMonName, productFriendlyName, alarmTripType, alarmTrigger, alarmInstance }
STATUS current
DESCRIPTION "Apparent Power Trap"
::= { cmTrapPrefix 10312 }

cmPowMonPowerFactorNOTIFY NOTIFICATION-TYPE
OBJECTS { powMonPowerFactor, powMonName, productFriendlyName, alarmTripType, alarmTrigger, alarmInstance }
STATUS current
DESCRIPTION "Power Factor Trap"
::= { cmTrapPrefix 10313 }

cmPowMonOutlet1NOTIFY NOTIFICATION-TYPE
OBJECTS { powMonOutlet1, powMonName, productFriendlyName, alarmTripType, alarmTrigger, alarmInstance }
STATUS current
DESCRIPTION "Outlet 1 Clear Trap"
::= { cmTrapPrefix 10314 }

cmPowMonOutlet2NOTIFY NOTIFICATION-TYPE
OBJECTS { powMonOutlet2, powMonName, productFriendlyName, alarmTripType, alarmTrigger, alarmInstance }
STATUS current
DESCRIPTION "Outlet 2 Clear Trap"
::= { cmTrapPrefix 10315 }

cmPowMonOutlet1StatusTimeNOTIFY NOTIFICATION-TYPE
OBJECTS { powMonOutlet1StatusTime, powMonName, productFriendlyName, alarmTripType, alarmTrigger, alarmInstance }
STATUS current
DESCRIPTION "Outlet1StatusTime Trip Trap"
::= { cmTrapPrefix 10316 }

cmPowMonOutlet2StatusTimeNOTIFY NOTIFICATION-TYPE
OBJECTS { powMonOutlet2StatusTime, powMonName, productFriendlyName, alarmTripType, alarmTrigger, alarmInstance }
STATUS current
DESCRIPTION "Outlet2StatusTime Trip Trap"
::= { cmTrapPrefix 10317 }

cmTempSensorTempCNOTIFY NOTIFICATION-TYPE
OBJECTS { tempSensorTempC, tempSensorName, productFriendlyName, alarmTripType, temperaturePrecision, alarmTrigger, alarmInstance }
STATUS current
DESCRIPTION "Remote Temp Sensor - Temperature Trap"
::= { cmTrapPrefix 10405 }

cmTempSensorTempFNOTIFY NOTIFICATION-TYPE
OBJECTS { tempSensorTempF, tempSensorName, productFriendlyName, alarmTripType, temperaturePrecision, alarmTrigger, alarmInstance }
STATUS current
DESCRIPTION "Remote Temp Sensor - Temperature Trap"
::= { cmTrapPrefix 10406 }

cmAirFlowSensorTempCNOTIFY NOTIFICATION-TYPE
OBJECTS { airFlowSensorTempC, airFlowSensorName, productFriendlyName, alarmTripType, temperaturePrecision, alarmTrigger, alarmInstance }
STATUS current
DESCRIPTION "Remote Air Flow Sensor - Temperature Trap"
::= { cmTrapPrefix 10505 }

cmAirFlowSensorTempFNOTIFY NOTIFICATION-TYPE
OBJECTS { airFlowSensorTempF, airFlowSensorName, productFriendlyName, alarmTripType, temperaturePrecision, alarmTrigger, alarmInstance }
STATUS current
DESCRIPTION "Remote Air Flow Sensor - Temperature Trap"
::= { cmTrapPrefix 10506 }

cmAirFlowSensorFlowNOTIFY NOTIFICATION-TYPE
OBJECTS { airFlowSensorFlow, airFlowSensorName, productFriendlyName, alarmTripType, alarmTrigger, alarmInstance }
STATUS current
DESCRIPTION "Remote Air Flow Sensor - Air Flow Trap"
::= { cmTrapPrefix 10507 }

cmAirFlowSensorHumidityNOTIFY NOTIFICATION-TYPE
OBJECTS { airFlowSensorHumidity, airFlowSensorName, productFriendlyName, alarmTripType, alarmTrigger, alarmInstance }
STATUS current
DESCRIPTION "Remote Air Flow Sensor - Humidity"
::= { cmTrapPrefix 10508 }

cmAirFlowSensorDewPointCNOTIFY NOTIFICATION-TYPE
OBJECTS { airFlowSensorDewPointC, airFlowSensorName, productFriendlyName, alarmTripType, temperaturePrecision, alarmTrigger, alarmInstance }
STATUS current
DESCRIPTION "Remote Air Flow Sensor - Dew Point Trap"
::= { cmTrapPrefix 10509 }

cmAirFlowSensorDewPointFNOTIFY NOTIFICATION-TYPE
OBJECTS { airFlowSensorDewPointF, airFlowSensorName, productFriendlyName, alarmTripType, temperaturePrecision, alarmTrigger, alarmInstance }
STATUS current
DESCRIPTION "Remote Air Flow Sensor - Dew Point Trap"
::= { cmTrapPrefix 10510 }

cmCtrl3ChDELTADeciAmpsANOTIFY NOTIFICATION-TYPE
OBJECTS { ctrl3ChDELTADeciAmpsA, ctrl3ChDELTAName, productFriendlyName, alarmTripType, alarmTrigger, alarmInstance }
STATUS current
DESCRIPTION "Deciamps A Trap"
::= { cmTrapPrefix 10606 }

cmCtrl3ChDELTADeciAmpsBNOTIFY NOTIFICATION-TYPE
OBJECTS { ctrl3ChDELTADeciAmpsB, ctrl3ChDELTAName, productFriendlyName, alarmTripType, alarmTrigger, alarmInstance }
STATUS current
DESCRIPTION "Deciamps B Trap"
::= { cmTrapPrefix 10607 }

cmCtrl3ChDELTADeciAmpsCNOTIFY NOTIFICATION-TYPE
OBJECTS { ctrl3ChDELTADeciAmpsC, ctrl3ChDELTAName, productFriendlyName, alarmTripType, alarmTrigger, alarmInstance }
STATUS current
DESCRIPTION "Deciamps C Trap"
::= { cmTrapPrefix 10608 }

cmCtrl3ChDELTAkWattHrsTotalNOTIFY NOTIFICATION-TYPE
OBJECTS { ctrl3ChDELTAkWattHrsTotal, ctrl3ChDELTAName, productFriendlyName, alarmTripType, alarmTrigger, alarmInstance }
STATUS current
DESCRIPTION "Kilo Watt Hours Total Trap"
::= { cmTrapPrefix 10609 }

cmCtrl3ChDELTARealPowerTotalNOTIFY NOTIFICATION-TYPE
OBJECTS { ctrl3ChDELTARealPowerTotal, ctrl3ChDELTAName, productFriendlyName, alarmTripType, alarmTrigger, alarmInstance }
STATUS current
DESCRIPTION "Watts Total Trap"
::= { cmTrapPrefix 10610 }

cmCtrl3ChDELTAkWattHrsABNOTIFY NOTIFICATION-TYPE
OBJECTS { ctrl3ChDELTAkWattHrsAB, ctrl3ChDELTAName, productFriendlyName, alarmTripType, alarmTrigger, alarmInstance }
STATUS current
DESCRIPTION "Kilo Watt Hours A Trap"
::= { cmTrapPrefix 10611 }

cmCtrl3ChDELTAVoltsABNOTIFY NOTIFICATION-TYPE
OBJECTS { ctrl3ChDELTAVoltsAB, ctrl3ChDELTAName, productFriendlyName, alarmTripType, alarmTrigger, alarmInstance }
STATUS current
DESCRIPTION "Volts AB Trap"
::= { cmTrapPrefix 10612 }

cmCtrl3ChDELTAVoltPeakABNOTIFY NOTIFICATION-TYPE
OBJECTS { ctrl3ChDELTAVoltPeakAB, ctrl3ChDELTAName, productFriendlyName, alarmTripType, alarmTrigger, alarmInstance }
STATUS current
DESCRIPTION "Volts Peak AB Trap"
::= { cmTrapPrefix 10613 }

cmCtrl3ChDELTARealPowerABNOTIFY NOTIFICATION-TYPE
OBJECTS { ctrl3ChDELTARealPowerAB, ctrl3ChDELTAName, productFriendlyName, alarmTripType, alarmTrigger, alarmInstance }
STATUS current
DESCRIPTION "Real Power AB Trap"
::= { cmTrapPrefix 10614 }

cmCtrl3ChDELTAApparentPowerABNOTIFY NOTIFICATION-TYPE
OBJECTS { ctrl3ChDELTAApparentPowerAB, ctrl3ChDELTAName, productFriendlyName, alarmTripType, alarmTrigger, alarmInstance }
STATUS current
DESCRIPTION "VoltAmps AB Trap"
::= { cmTrapPrefix 10615 }

cmCtrl3ChDELTAPowerFactorABNOTIFY NOTIFICATION-TYPE
OBJECTS { ctrl3ChDELTAPowerFactorAB, ctrl3ChDELTAName, productFriendlyName, alarmTripType, alarmTrigger, alarmInstance }
STATUS current
DESCRIPTION "Power Factor AB Trap"
::= { cmTrapPrefix 10616 }

cmCtrl3ChDELTAkWattHrsBCNOTIFY NOTIFICATION-TYPE
OBJECTS { ctrl3ChDELTAkWattHrsBC, ctrl3ChDELTAName, productFriendlyName, alarmTripType, alarmTrigger, alarmInstance }
STATUS current
DESCRIPTION "Kilo Watt Hours BC Trap"
::= { cmTrapPrefix 10617 }

cmCtrl3ChDELTAVoltsBCNOTIFY NOTIFICATION-TYPE
OBJECTS { ctrl3ChDELTAVoltsBC, ctrl3ChDELTAName, productFriendlyName, alarmTripType, alarmTrigger, alarmInstance }
STATUS current
DESCRIPTION "Volts BC Trap"
::= { cmTrapPrefix 10618 }

cmCtrl3ChDELTAVoltPeakBCNOTIFY NOTIFICATION-TYPE
OBJECTS { ctrl3ChDELTAVoltPeakBC, ctrl3ChDELTAName, productFriendlyName, alarmTripType, alarmTrigger, alarmInstance }
STATUS current
DESCRIPTION "Volts Peak BC Trap"
::= { cmTrapPrefix 10619 }

cmCtrl3ChDELTARealPowerBCNOTIFY NOTIFICATION-TYPE
OBJECTS { ctrl3ChDELTARealPowerBC, ctrl3ChDELTAName, productFriendlyName, alarmTripType, alarmTrigger, alarmInstance }
STATUS current
DESCRIPTION "Real Power BC Trap"
::= { cmTrapPrefix 10620 }

cmCtrl3ChDELTAApparentPowerBCNOTIFY NOTIFICATION-TYPE
OBJECTS { ctrl3ChDELTAApparentPowerBC, ctrl3ChDELTAName, productFriendlyName, alarmTripType, alarmTrigger, alarmInstance }
STATUS current
DESCRIPTION "VoltAmps BC Trap"
::= { cmTrapPrefix 10621 }

cmCtrl3ChDELTAPowerFactorBCNOTIFY NOTIFICATION-TYPE
OBJECTS { ctrl3ChDELTAPowerFactorBC, ctrl3ChDELTAName, productFriendlyName, alarmTripType, alarmTrigger, alarmInstance }
STATUS current
DESCRIPTION "Power Factor BC Trap"
::= { cmTrapPrefix 10622 }

cmCtrl3ChDELTAkWattHrsCANOTIFY NOTIFICATION-TYPE
OBJECTS { ctrl3ChDELTAkWattHrsCA, ctrl3ChDELTAName, productFriendlyName, alarmTripType, alarmTrigger, alarmInstance }
STATUS current
DESCRIPTION "Kilo Watt Hours CA Trap"
::= { cmTrapPrefix 10623 }

cmCtrl3ChDELTAVoltsCANOTIFY NOTIFICATION-TYPE
OBJECTS { ctrl3ChDELTAVoltsCA, ctrl3ChDELTAName, productFriendlyName, alarmTripType, alarmTrigger, alarmInstance }
STATUS current
DESCRIPTION "Volts CA Trap"
::= { cmTrapPrefix 10624 }

cmCtrl3ChDELTAVoltPeakCANOTIFY NOTIFICATION-TYPE
OBJECTS { ctrl3ChDELTAVoltPeakCA, ctrl3ChDELTAName, productFriendlyName, alarmTripType, alarmTrigger, alarmInstance }
STATUS current
DESCRIPTION "Volts Peak CA Trap"
::= { cmTrapPrefix 10625 }

cmCtrl3ChDELTARealPowerCANOTIFY NOTIFICATION-TYPE
OBJECTS { ctrl3ChDELTARealPowerCA, ctrl3ChDELTAName, productFriendlyName, alarmTripType, alarmTrigger, alarmInstance }
STATUS current
DESCRIPTION "Real Power CA Trap"
::= { cmTrapPrefix 10626 }

cmCtrl3ChDELTAApparentPowerCANOTIFY NOTIFICATION-TYPE
OBJECTS { ctrl3ChDELTAApparentPowerCA, ctrl3ChDELTAName, productFriendlyName, alarmTripType, alarmTrigger, alarmInstance }
STATUS current
DESCRIPTION "VoltAmps CA Trap"
::= { cmTrapPrefix 10627 }

cmCtrl3ChDELTAPowerFactorCANOTIFY NOTIFICATION-TYPE
OBJECTS { ctrl3ChDELTAPowerFactorCA, ctrl3ChDELTAName, productFriendlyName, alarmTripType, alarmTrigger, alarmInstance }
STATUS current
DESCRIPTION "Power Factor CA Trap"
::= { cmTrapPrefix 10628 }

cmDoorSensorStatusNOTIFY NOTIFICATION-TYPE
OBJECTS { doorSensorStatus, doorSensorName, productFriendlyName, alarmTripType, alarmTrigger, alarmInstance }
STATUS current
DESCRIPTION "Door sensor Trap"
::= { cmTrapPrefix 10705 }

cmWaterSensorDampnessNOTIFY NOTIFICATION-TYPE
OBJECTS { waterSensorDampness, waterSensorName, productFriendlyName, alarmTripType, alarmTrigger, alarmInstance }
STATUS current
DESCRIPTION "Water sensor Trap"
::= { cmTrapPrefix 10805 }

cmCurrentMonitorDeciAmpsNOTIFY NOTIFICATION-TYPE
OBJECTS { currentMonitorDeciAmps, currentMonitorName, productFriendlyName, alarmTripType, alarmTrigger, alarmInstance }
STATUS current
DESCRIPTION "Current Monitor Amps Trap"
::= { cmTrapPrefix 10905 }

cmMillivoltMonitorMVNOTIFY NOTIFICATION-TYPE
OBJECTS { millivoltMonitorMV, millivoltMonitorName, productFriendlyName, alarmTripType, alarmTrigger, alarmInstance }
STATUS current
DESCRIPTION "Millivolt Monitor Trap"
::= { cmTrapPrefix 11005 }

cmPow3ChkWattHrsANOTIFY NOTIFICATION-TYPE
OBJECTS { pow3ChkWattHrsA, pow3ChName, productFriendlyName, alarmTripType, alarmTrigger, alarmInstance }
STATUS current
DESCRIPTION "Kilo Watt Hours A Trap"
::= { cmTrapPrefix 11105 }

cmPow3ChVoltsANOTIFY NOTIFICATION-TYPE
OBJECTS { pow3ChVoltsA, pow3ChName, productFriendlyName, alarmTripType, alarmTrigger, alarmInstance }
STATUS current
DESCRIPTION "Volts A Trap"
::= { cmTrapPrefix 11106 }

cmPow3ChVoltMaxANOTIFY NOTIFICATION-TYPE
OBJECTS { pow3ChVoltMaxA, pow3ChName, productFriendlyName, alarmTripType, alarmTrigger, alarmInstance }
STATUS current
DESCRIPTION "Volts Max A Trap"
::= { cmTrapPrefix 11107 }

cmPow3ChVoltMinANOTIFY NOTIFICATION-TYPE
OBJECTS { pow3ChVoltMinA, pow3ChName, productFriendlyName, alarmTripType, alarmTrigger, alarmInstance }
STATUS current
DESCRIPTION "Volts Min A Trap"
::= { cmTrapPrefix 11108 }

cmPow3ChVoltPeakANOTIFY NOTIFICATION-TYPE
OBJECTS { pow3ChVoltPeakA, pow3ChName, productFriendlyName, alarmTripType, alarmTrigger, alarmInstance }
STATUS current
DESCRIPTION "Volt Peak A Trap"
::= { cmTrapPrefix 11109 }

cmPow3ChDeciAmpsANOTIFY NOTIFICATION-TYPE
OBJECTS { pow3ChDeciAmpsA, pow3ChName, productFriendlyName, alarmTripType, alarmTrigger, alarmInstance }
STATUS current
DESCRIPTION "Deciamps A Trap"
::= { cmTrapPrefix 11110 }

cmPow3ChRealPowerANOTIFY NOTIFICATION-TYPE
OBJECTS { pow3ChRealPowerA, pow3ChName, productFriendlyName, alarmTripType, alarmTrigger, alarmInstance }
STATUS current
DESCRIPTION "Real Power A Trap"
::= { cmTrapPrefix 11111 }

cmPow3ChApparentPowerANOTIFY NOTIFICATION-TYPE
OBJECTS { pow3ChApparentPowerA, pow3ChName, productFriendlyName, alarmTripType, alarmTrigger, alarmInstance }
STATUS current
DESCRIPTION "Apparent Power A Trap"
::= { cmTrapPrefix 11112 }

cmPow3ChPowerFactorANOTIFY NOTIFICATION-TYPE
OBJECTS { pow3ChPowerFactorA, pow3ChName, productFriendlyName, alarmTripType, alarmTrigger, alarmInstance }
STATUS current
DESCRIPTION "Power Factor A Trap"
::= { cmTrapPrefix 11113 }

cmPow3ChkWattHrsBNOTIFY NOTIFICATION-TYPE
OBJECTS { pow3ChkWattHrsB, pow3ChName, productFriendlyName, alarmTripType, alarmTrigger, alarmInstance }
STATUS current
DESCRIPTION "Kilo Watt Hours B Trap"
::= { cmTrapPrefix 11114 }

cmPow3ChVoltsBNOTIFY NOTIFICATION-TYPE
OBJECTS { pow3ChVoltsB, pow3ChName, productFriendlyName, alarmTripType, alarmTrigger, alarmInstance }
STATUS current
DESCRIPTION "Volts B Trap"
::= { cmTrapPrefix 11115 }

cmPow3ChVoltMaxBNOTIFY NOTIFICATION-TYPE
OBJECTS { pow3ChVoltMaxB, pow3ChName, productFriendlyName, alarmTripType, alarmTrigger, alarmInstance }
STATUS current
DESCRIPTION "Volts Max B Trap"
::= { cmTrapPrefix 11116 }

cmPow3ChVoltMinBNOTIFY NOTIFICATION-TYPE
OBJECTS { pow3ChVoltMinB, pow3ChName, productFriendlyName, alarmTripType, alarmTrigger, alarmInstance }
STATUS current
DESCRIPTION "Volts Min B Trap"
::= { cmTrapPrefix 11117 }

cmPow3ChVoltPeakBNOTIFY NOTIFICATION-TYPE
OBJECTS { pow3ChVoltPeakB, pow3ChName, productFriendlyName, alarmTripType, alarmTrigger, alarmInstance }
STATUS current
DESCRIPTION "Volt Peak B Trap"
::= { cmTrapPrefix 11118 }

cmPow3ChDeciAmpsBNOTIFY NOTIFICATION-TYPE
OBJECTS { pow3ChDeciAmpsB, pow3ChName, productFriendlyName, alarmTripType, alarmTrigger, alarmInstance }
STATUS current
DESCRIPTION "Deciamps B Trap"
::= { cmTrapPrefix 11119 }

cmPow3ChRealPowerBNOTIFY NOTIFICATION-TYPE
OBJECTS { pow3ChRealPowerB, pow3ChName, productFriendlyName, alarmTripType, alarmTrigger, alarmInstance }
STATUS current
DESCRIPTION "Real Power B Trap"
::= { cmTrapPrefix 11120 }

cmPow3ChApparentPowerBNOTIFY NOTIFICATION-TYPE
OBJECTS { pow3ChApparentPowerB, pow3ChName, productFriendlyName, alarmTripType, alarmTrigger, alarmInstance }
STATUS current
DESCRIPTION "Apparent Power B Trap"
::= { cmTrapPrefix 11121 }

cmPow3ChPowerFactorBNOTIFY NOTIFICATION-TYPE
OBJECTS { pow3ChPowerFactorB, pow3ChName, productFriendlyName, alarmTripType, alarmTrigger, alarmInstance }
STATUS current
DESCRIPTION "Power Factor B Trap"
::= { cmTrapPrefix 11122 }

cmPow3ChkWattHrsCNOTIFY NOTIFICATION-TYPE
OBJECTS { pow3ChkWattHrsC, pow3ChName, productFriendlyName, alarmTripType, alarmTrigger, alarmInstance }
STATUS current
DESCRIPTION "Kilo Watt Hours C Trap"
::= { cmTrapPrefix 11123 }

cmPow3ChVoltsCNOTIFY NOTIFICATION-TYPE
OBJECTS { pow3ChVoltsC, pow3ChName, productFriendlyName, alarmTripType, alarmTrigger, alarmInstance }
STATUS current
DESCRIPTION "Volts C Trap"
::= { cmTrapPrefix 11124 }

cmPow3ChVoltMaxCNOTIFY NOTIFICATION-TYPE
OBJECTS { pow3ChVoltMaxC, pow3ChName, productFriendlyName, alarmTripType, alarmTrigger, alarmInstance }
STATUS current
DESCRIPTION "Volts Max C Trap"
::= { cmTrapPrefix 11125 }

cmPow3ChVoltMinCNOTIFY NOTIFICATION-TYPE
OBJECTS { pow3ChVoltMinC, pow3ChName, productFriendlyName, alarmTripType, alarmTrigger, alarmInstance }
STATUS current
DESCRIPTION "Volts Min C Trap"
::= { cmTrapPrefix 11126 }

cmPow3ChVoltPeakCNOTIFY NOTIFICATION-TYPE
OBJECTS { pow3ChVoltPeakC, pow3ChName, productFriendlyName, alarmTripType, alarmTrigger, alarmInstance }
STATUS current
DESCRIPTION "Volt Peak C Trap"
::= { cmTrapPrefix 11127 }

cmPow3ChDeciAmpsCNOTIFY NOTIFICATION-TYPE
OBJECTS { pow3ChDeciAmpsC, pow3ChName, productFriendlyName, alarmTripType, alarmTrigger, alarmInstance }
STATUS current
DESCRIPTION "Deciamps C Trap"
::= { cmTrapPrefix 11128 }

cmPow3ChRealPowerCNOTIFY NOTIFICATION-TYPE
OBJECTS { pow3ChRealPowerC, pow3ChName, productFriendlyName, alarmTripType, alarmTrigger, alarmInstance }
STATUS current
DESCRIPTION "Real Power C Trap"
::= { cmTrapPrefix 11129 }

cmPow3ChApparentPowerCNOTIFY NOTIFICATION-TYPE
OBJECTS { pow3ChApparentPowerC, pow3ChName, productFriendlyName, alarmTripType, alarmTrigger, alarmInstance }
STATUS current
DESCRIPTION "Apparent Power C Trap"
::= { cmTrapPrefix 11130 }

cmPow3ChPowerFactorCNOTIFY NOTIFICATION-TYPE
OBJECTS { pow3ChPowerFactorC, pow3ChName, productFriendlyName, alarmTripType, alarmTrigger, alarmInstance }
STATUS current
DESCRIPTION "Power Factor C Trap"
::= { cmTrapPrefix 11131 }

cmPow3ChkWattHrsTotalNOTIFY NOTIFICATION-TYPE
OBJECTS { pow3ChkWattHrsTotal, pow3ChName, productFriendlyName, alarmTripType, alarmTrigger, alarmInstance }
STATUS current
DESCRIPTION "Kilo Watt Hours Total Trap"
::= { cmTrapPrefix 11132 }

cmPow3ChRealPowerTotalNOTIFY NOTIFICATION-TYPE
OBJECTS { pow3ChRealPowerTotal, pow3ChName, productFriendlyName, alarmTripType, alarmTrigger, alarmInstance }
STATUS current
DESCRIPTION "Real Power Total Trap"
::= { cmTrapPrefix 11133 }

cmOutlet1StatusNOTIFY NOTIFICATION-TYPE
OBJECTS { outlet1Status, outletName, productFriendlyName, alarmTripType, alarmTrigger, alarmInstance }
STATUS current
DESCRIPTION "Outlet 1 Status Trap"
::= { cmTrapPrefix 11205 }

cmOutlet2StatusNOTIFY NOTIFICATION-TYPE
OBJECTS { outlet2Status, outletName, productFriendlyName, alarmTripType, alarmTrigger, alarmInstance }
STATUS current
DESCRIPTION "Outlet 2 Status Trap"
::= { cmTrapPrefix 11206 }

cmVsfcSetPointCNOTIFY NOTIFICATION-TYPE
OBJECTS { vsfcSetPointC, vsfcName, productFriendlyName, alarmTripType, alarmTrigger, alarmInstance }
STATUS current
DESCRIPTION "Vsfc Temp Set Point Sensor Trap"
::= { cmTrapPrefix 11305 }

cmVsfcSetPointFNOTIFY NOTIFICATION-TYPE
OBJECTS { vsfcSetPointF, vsfcName, productFriendlyName, alarmTripType, alarmTrigger, alarmInstance }
STATUS current
DESCRIPTION "Vsfc Temp Set Point Sensor Trap"
::= { cmTrapPrefix 11306 }

cmVsfcFanSpeedNOTIFY NOTIFICATION-TYPE
OBJECTS { vsfcFanSpeed, vsfcName, productFriendlyName, alarmTripType, alarmTrigger, alarmInstance }
STATUS current
DESCRIPTION "Vsfc Fan Speed Sensor Trap"
::= { cmTrapPrefix 11307 }

cmVsfcIntTempCNOTIFY NOTIFICATION-TYPE
OBJECTS { vsfcIntTempC, vsfcName, productFriendlyName, alarmTripType, temperaturePrecision, alarmTrigger, alarmInstance }
STATUS current
DESCRIPTION "Vsfc Internal Temp Sensor Trap"
::= { cmTrapPrefix 11308 }

cmVsfcIntTempFNOTIFY NOTIFICATION-TYPE
OBJECTS { vsfcIntTempF, vsfcName, productFriendlyName, alarmTripType, temperaturePrecision, alarmTrigger, alarmInstance }
STATUS current
DESCRIPTION "Vsfc Internal Temp Sensor Trap"
::= { cmTrapPrefix 11309 }

cmVsfcExt1TempCNOTIFY NOTIFICATION-TYPE
OBJECTS { vsfcExt1TempC, vsfcName, productFriendlyName, alarmTripType, temperaturePrecision, alarmTrigger, alarmInstance }
STATUS current
DESCRIPTION "Vsfc External Temp 1 Sensor Trap"
::= { cmTrapPrefix 11310 }

cmVsfcExt1TempFNOTIFY NOTIFICATION-TYPE
OBJECTS { vsfcExt1TempF, vsfcName, productFriendlyName, alarmTripType, temperaturePrecision, alarmTrigger, alarmInstance }
STATUS current
DESCRIPTION "Vsfc External Temp 1 Sensor Trap"
::= { cmTrapPrefix 11311 }

cmVsfcExt2TempCNOTIFY NOTIFICATION-TYPE
OBJECTS { vsfcExt2TempC, vsfcName, productFriendlyName, alarmTripType, temperaturePrecision, alarmTrigger, alarmInstance }
STATUS current
DESCRIPTION "Vsfc External Temp 2 Sensor Trap"
::= { cmTrapPrefix 11312 }

cmVsfcExt2TempFNOTIFY NOTIFICATION-TYPE
OBJECTS { vsfcExt2TempF, vsfcName, productFriendlyName, alarmTripType, temperaturePrecision, alarmTrigger, alarmInstance }
STATUS current
DESCRIPTION "Vsfc External Temp 1 Sensor Trap"
::= { cmTrapPrefix 11313 }

cmVsfcExt3TempCNOTIFY NOTIFICATION-TYPE
OBJECTS { vsfcExt3TempC, vsfcName, productFriendlyName, alarmTripType, temperaturePrecision, alarmTrigger, alarmInstance }
STATUS current
DESCRIPTION "Vsfc External Temp 3 Sensor Trap"
::= { cmTrapPrefix 11314 }

cmVsfcExt3TempFNOTIFY NOTIFICATION-TYPE
OBJECTS { vsfcExt3TempF, vsfcName, productFriendlyName, alarmTripType, temperaturePrecision, alarmTrigger, alarmInstance }
STATUS current
DESCRIPTION "Vsfc External Temp 1 Sensor Trap"
::= { cmTrapPrefix 11315 }

cmVsfcExt4TempCNOTIFY NOTIFICATION-TYPE
OBJECTS { vsfcExt4TempC, vsfcName, productFriendlyName, alarmTripType, temperaturePrecision, alarmTrigger, alarmInstance }
STATUS current
DESCRIPTION "Vsfc External Temp 4 Sensor Trap"
::= { cmTrapPrefix 11316 }

cmVsfcExt4TempFNOTIFY NOTIFICATION-TYPE
OBJECTS { vsfcExt4TempF, vsfcName, productFriendlyName, alarmTripType, temperaturePrecision, alarmTrigger, alarmInstance }
STATUS current
DESCRIPTION "Vsfc External Temp 1 Sensor Trap"
::= { cmTrapPrefix 11317 }

cmCtrl3ChVoltsANOTIFY NOTIFICATION-TYPE
OBJECTS { ctrl3ChVoltsA, ctrl3ChName, productFriendlyName, alarmTripType, alarmTrigger, alarmInstance }
STATUS current
DESCRIPTION "Volts A Trap"
::= { cmTrapPrefix 11405 }

cmCtrl3ChVoltPeakANOTIFY NOTIFICATION-TYPE
OBJECTS { ctrl3ChVoltPeakA, ctrl3ChName, productFriendlyName, alarmTripType, alarmTrigger, alarmInstance }
STATUS current
DESCRIPTION "Volts Peak A Trap"
::= { cmTrapPrefix 11406 }

cmCtrl3ChDeciAmpsANOTIFY NOTIFICATION-TYPE
OBJECTS { ctrl3ChDeciAmpsA, ctrl3ChName, productFriendlyName, alarmTripType, alarmTrigger, alarmInstance }
STATUS current
DESCRIPTION "Deciamps A Trap"
::= { cmTrapPrefix 11407 }

cmCtrl3ChDeciAmpsPeakANOTIFY NOTIFICATION-TYPE
OBJECTS { ctrl3ChDeciAmpsPeakA, ctrl3ChName, productFriendlyName, alarmTripType, alarmTrigger, alarmInstance }
STATUS current
DESCRIPTION "Deciamps Peak A Trap"
::= { cmTrapPrefix 11408 }

cmCtrl3ChRealPowerANOTIFY NOTIFICATION-TYPE
OBJECTS { ctrl3ChRealPowerA, ctrl3ChName, productFriendlyName, alarmTripType, alarmTrigger, alarmInstance }
STATUS current
DESCRIPTION "Real Power A Trap"
::= { cmTrapPrefix 11409 }

cmCtrl3ChApparentPowerANOTIFY NOTIFICATION-TYPE
OBJECTS { ctrl3ChApparentPowerA, ctrl3ChName, productFriendlyName, alarmTripType, alarmTrigger, alarmInstance }
STATUS current
DESCRIPTION "Apparent Power A Trap"
::= { cmTrapPrefix 11410 }

cmCtrl3ChPowerFactorANOTIFY NOTIFICATION-TYPE
OBJECTS { ctrl3ChPowerFactorA, ctrl3ChName, productFriendlyName, alarmTripType, alarmTrigger, alarmInstance }
STATUS current
DESCRIPTION "Power Factor A Trap"
::= { cmTrapPrefix 11411 }

cmCtrl3ChVoltsBNOTIFY NOTIFICATION-TYPE
OBJECTS { ctrl3ChVoltsB, ctrl3ChName, productFriendlyName, alarmTripType, alarmTrigger, alarmInstance }
STATUS current
DESCRIPTION "Volts B Trap"
::= { cmTrapPrefix 11412 }

cmCtrl3ChVoltPeakBNOTIFY NOTIFICATION-TYPE
OBJECTS { ctrl3ChVoltPeakB, ctrl3ChName, productFriendlyName, alarmTripType, alarmTrigger, alarmInstance }
STATUS current
DESCRIPTION "Volts Peak B Trap"
::= { cmTrapPrefix 11413 }

cmCtrl3ChDeciAmpsBNOTIFY NOTIFICATION-TYPE
OBJECTS { ctrl3ChDeciAmpsB, ctrl3ChName, productFriendlyName, alarmTripType, alarmTrigger, alarmInstance }
STATUS current
DESCRIPTION "Deciamps B Trap"
::= { cmTrapPrefix 11414 }

cmCtrl3ChDeciAmpsPeakBNOTIFY NOTIFICATION-TYPE
OBJECTS { ctrl3ChDeciAmpsPeakB, ctrl3ChName, productFriendlyName, alarmTripType, alarmTrigger, alarmInstance }
STATUS current
DESCRIPTION "Deciamps Peak B Trap"
::= { cmTrapPrefix 11415 }

cmCtrl3ChRealPowerBNOTIFY NOTIFICATION-TYPE
OBJECTS { ctrl3ChRealPowerB, ctrl3ChName, productFriendlyName, alarmTripType, alarmTrigger, alarmInstance }
STATUS current
DESCRIPTION "Real Power B Trap"
::= { cmTrapPrefix 11416 }

cmCtrl3ChApparentPowerBNOTIFY NOTIFICATION-TYPE
OBJECTS { ctrl3ChApparentPowerB, ctrl3ChName, productFriendlyName, alarmTripType, alarmTrigger, alarmInstance }
STATUS current
DESCRIPTION "Apparent Power B Trap"
::= { cmTrapPrefix 11417 }

cmCtrl3ChPowerFactorBNOTIFY NOTIFICATION-TYPE
OBJECTS { ctrl3ChPowerFactorB, ctrl3ChName, productFriendlyName, alarmTripType, alarmTrigger, alarmInstance }
STATUS current
DESCRIPTION "Power Factor B Trap"
::= { cmTrapPrefix 11418 }

cmCtrl3ChVoltsCNOTIFY NOTIFICATION-TYPE
OBJECTS { ctrl3ChVoltsC, ctrl3ChName, productFriendlyName, alarmTripType, alarmTrigger, alarmInstance }
STATUS current
DESCRIPTION "Volts C Trap"
::= { cmTrapPrefix 11419 }

cmCtrl3ChVoltPeakCNOTIFY NOTIFICATION-TYPE
OBJECTS { ctrl3ChVoltPeakC, ctrl3ChName, productFriendlyName, alarmTripType, alarmTrigger, alarmInstance }
STATUS current
DESCRIPTION "Volts Peak C Trap"
::= { cmTrapPrefix 11420 }

cmCtrl3ChDeciAmpsCNOTIFY NOTIFICATION-TYPE
OBJECTS { ctrl3ChDeciAmpsC, ctrl3ChName, productFriendlyName, alarmTripType, alarmTrigger, alarmInstance }
STATUS current
DESCRIPTION "Deciamps C Trap"
::= { cmTrapPrefix 11421 }

cmCtrl3ChDeciAmpsPeakCNOTIFY NOTIFICATION-TYPE
OBJECTS { ctrl3ChDeciAmpsPeakC, ctrl3ChName, productFriendlyName, alarmTripType, alarmTrigger, alarmInstance }
STATUS current
DESCRIPTION "Deciamps Peak C Trap"
::= { cmTrapPrefix 11422 }

cmCtrl3ChRealPowerCNOTIFY NOTIFICATION-TYPE
OBJECTS { ctrl3ChRealPowerC, ctrl3ChName, productFriendlyName, alarmTripType, alarmTrigger, alarmInstance }
STATUS current
DESCRIPTION "Real Power C Trap"
::= { cmTrapPrefix 11423 }

cmCtrl3ChApparentPowerCNOTIFY NOTIFICATION-TYPE
OBJECTS { ctrl3ChApparentPowerC, ctrl3ChName, productFriendlyName, alarmTripType, alarmTrigger, alarmInstance }
STATUS current
DESCRIPTION "Apparent Power C Trap"
::= { cmTrapPrefix 11424 }

cmCtrl3ChPowerFactorCNOTIFY NOTIFICATION-TYPE
OBJECTS { ctrl3ChPowerFactorC, ctrl3ChName, productFriendlyName, alarmTripType, alarmTrigger, alarmInstance }
STATUS current
DESCRIPTION "Power Factor C Trap"
::= { cmTrapPrefix 11425 }

cmCtrlGrpAmpsANOTIFY NOTIFICATION-TYPE
OBJECTS { ctrlGrpAmpsA, ctrlGrpAmpsName, productFriendlyName, alarmTripType, alarmTrigger, alarmInstance }
STATUS current
DESCRIPTION "Group A DeciAmps Trap"
::= { cmTrapPrefix 11505 }

cmCtrlGrpAmpsBNOTIFY NOTIFICATION-TYPE
OBJECTS { ctrlGrpAmpsB, ctrlGrpAmpsName, productFriendlyName, alarmTripType, alarmTrigger, alarmInstance }
STATUS current
DESCRIPTION "Group B DeciAmps Trap"
::= { cmTrapPrefix 11506 }

cmCtrlGrpAmpsCNOTIFY NOTIFICATION-TYPE
OBJECTS { ctrlGrpAmpsC, ctrlGrpAmpsName, productFriendlyName, alarmTripType, alarmTrigger, alarmInstance }
STATUS current
DESCRIPTION "Group C DeciAmps Trap"
::= { cmTrapPrefix 11507 }

cmCtrlGrpAmpsDNOTIFY NOTIFICATION-TYPE
OBJECTS { ctrlGrpAmpsD, ctrlGrpAmpsName, productFriendlyName, alarmTripType, alarmTrigger, alarmInstance }
STATUS current
DESCRIPTION "Group D DeciAmps Trap"
::= { cmTrapPrefix 11508 }

cmCtrlGrpAmpsENOTIFY NOTIFICATION-TYPE
OBJECTS { ctrlGrpAmpsE, ctrlGrpAmpsName, productFriendlyName, alarmTripType, alarmTrigger, alarmInstance }
STATUS current
DESCRIPTION "Group E DeciAmps Trap"
::= { cmTrapPrefix 11509 }

cmCtrlGrpAmpsFNOTIFY NOTIFICATION-TYPE
OBJECTS { ctrlGrpAmpsF, ctrlGrpAmpsName, productFriendlyName, alarmTripType, alarmTrigger, alarmInstance }
STATUS current
DESCRIPTION "Group F DeciAmps Trap"
::= { cmTrapPrefix 11510 }

cmCtrlGrpAmpsGNOTIFY NOTIFICATION-TYPE
OBJECTS { ctrlGrpAmpsG, ctrlGrpAmpsName, productFriendlyName, alarmTripType, alarmTrigger, alarmInstance }
STATUS current
DESCRIPTION "Group G DeciAmps Trap"
::= { cmTrapPrefix 11511 }

cmCtrlGrpAmpsHNOTIFY NOTIFICATION-TYPE
OBJECTS { ctrlGrpAmpsH, ctrlGrpAmpsName, productFriendlyName, alarmTripType, alarmTrigger, alarmInstance }
STATUS current
DESCRIPTION "Group H DeciAmps Trap"
::= { cmTrapPrefix 11512 }

cmCtrlGrpAmpsAVoltsNOTIFY NOTIFICATION-TYPE
OBJECTS { ctrlGrpAmpsAVolts, ctrlGrpAmpsName, productFriendlyName, alarmTripType, alarmTrigger, alarmInstance }
STATUS current
DESCRIPTION "AVolts Trip Trap"
::= { cmTrapPrefix 11513 }

cmCtrlGrpAmpsBVoltsNOTIFY NOTIFICATION-TYPE
OBJECTS { ctrlGrpAmpsBVolts, ctrlGrpAmpsName, productFriendlyName, alarmTripType, alarmTrigger, alarmInstance }
STATUS current
DESCRIPTION "BVolts Trip Trap"
::= { cmTrapPrefix 11514 }

cmCtrlGrpAmpsCVoltsNOTIFY NOTIFICATION-TYPE
OBJECTS { ctrlGrpAmpsCVolts, ctrlGrpAmpsName, productFriendlyName, alarmTripType, alarmTrigger, alarmInstance }
STATUS current
DESCRIPTION "CVolts Trip Trap"
::= { cmTrapPrefix 11515 }

cmCtrlGrpAmpsDVoltsNOTIFY NOTIFICATION-TYPE
OBJECTS { ctrlGrpAmpsDVolts, ctrlGrpAmpsName, productFriendlyName, alarmTripType, alarmTrigger, alarmInstance }
STATUS current
DESCRIPTION "DVolts Trip Trap"
::= { cmTrapPrefix 11516 }

cmCtrlGrpAmpsEVoltsNOTIFY NOTIFICATION-TYPE
OBJECTS { ctrlGrpAmpsEVolts, ctrlGrpAmpsName, productFriendlyName, alarmTripType, alarmTrigger, alarmInstance }
STATUS current
DESCRIPTION "EVolts Trip Trap"
::= { cmTrapPrefix 11517 }

cmCtrlGrpAmpsFVoltsNOTIFY NOTIFICATION-TYPE
OBJECTS { ctrlGrpAmpsFVolts, ctrlGrpAmpsName, productFriendlyName, alarmTripType, alarmTrigger, alarmInstance }
STATUS current
DESCRIPTION "FVolts Trip Trap"
::= { cmTrapPrefix 11518 }

cmCtrlGrpAmpsGVoltsNOTIFY NOTIFICATION-TYPE
OBJECTS { ctrlGrpAmpsGVolts, ctrlGrpAmpsName, productFriendlyName, alarmTripType, alarmTrigger, alarmInstance }
STATUS current
DESCRIPTION "GVolts Trip Trap"
::= { cmTrapPrefix 11519 }

cmCtrlGrpAmpsHVoltsNOTIFY NOTIFICATION-TYPE
OBJECTS { ctrlGrpAmpsHVolts, ctrlGrpAmpsName, productFriendlyName, alarmTripType, alarmTrigger, alarmInstance }
STATUS current
DESCRIPTION "HVolts Trip Trap"
::= { cmTrapPrefix 11520 }

cmCtrlGrpAmpsINOTIFY NOTIFICATION-TYPE
OBJECTS { ctrlGrpAmpsI, ctrlGrpAmpsName, productFriendlyName, alarmTripType, alarmTrigger, alarmInstance }
STATUS current
DESCRIPTION "Group I DeciAmps Trap"
::= { cmTrapPrefix 11521 }

cmCtrlGrpAmpsJNOTIFY NOTIFICATION-TYPE
OBJECTS { ctrlGrpAmpsJ, ctrlGrpAmpsName, productFriendlyName, alarmTripType, alarmTrigger, alarmInstance }
STATUS current
DESCRIPTION "Group J DeciAmps Trap"
::= { cmTrapPrefix 11522 }

cmCtrlGrpAmpsKNOTIFY NOTIFICATION-TYPE
OBJECTS { ctrlGrpAmpsK, ctrlGrpAmpsName, productFriendlyName, alarmTripType, alarmTrigger, alarmInstance }
STATUS current
DESCRIPTION "Group K DeciAmps Trap"
::= { cmTrapPrefix 11523 }

cmCtrlGrpAmpsLNOTIFY NOTIFICATION-TYPE
OBJECTS { ctrlGrpAmpsL, ctrlGrpAmpsName, productFriendlyName, alarmTripType, alarmTrigger, alarmInstance }
STATUS current
DESCRIPTION "Group L DeciAmps Trap"
::= { cmTrapPrefix 11524 }

cmCtrlGrpAmpsMNOTIFY NOTIFICATION-TYPE
OBJECTS { ctrlGrpAmpsM, ctrlGrpAmpsName, productFriendlyName, alarmTripType, alarmTrigger, alarmInstance }
STATUS current
DESCRIPTION "Group M DeciAmps Trap"
::= { cmTrapPrefix 11525 }

cmCtrlGrpAmpsNNOTIFY NOTIFICATION-TYPE
OBJECTS { ctrlGrpAmpsN, ctrlGrpAmpsName, productFriendlyName, alarmTripType, alarmTrigger, alarmInstance }
STATUS current
DESCRIPTION "Group N DeciAmps Trap"
::= { cmTrapPrefix 11526 }

cmCtrlGrpAmpsONOTIFY NOTIFICATION-TYPE
OBJECTS { ctrlGrpAmpsO, ctrlGrpAmpsName, productFriendlyName, alarmTripType, alarmTrigger, alarmInstance }
STATUS current
DESCRIPTION "Group O DeciAmps Trap"
::= { cmTrapPrefix 11527 }

cmCtrlGrpAmpsPNOTIFY NOTIFICATION-TYPE
OBJECTS { ctrlGrpAmpsP, ctrlGrpAmpsName, productFriendlyName, alarmTripType, alarmTrigger, alarmInstance }
STATUS current
DESCRIPTION "Group P DeciAmps Trap"
::= { cmTrapPrefix 11528 }

cmCtrlGrpAmpsIVoltsNOTIFY NOTIFICATION-TYPE
OBJECTS { ctrlGrpAmpsIVolts, ctrlGrpAmpsName, productFriendlyName, alarmTripType, alarmTrigger, alarmInstance }
STATUS current
DESCRIPTION "IVolts Trip Trap"
::= { cmTrapPrefix 11529 }

cmCtrlGrpAmpsJVoltsNOTIFY NOTIFICATION-TYPE
OBJECTS { ctrlGrpAmpsJVolts, ctrlGrpAmpsName, productFriendlyName, alarmTripType, alarmTrigger, alarmInstance }
STATUS current
DESCRIPTION "JVolts Trip Trap"
::= { cmTrapPrefix 11530 }

cmCtrlGrpAmpsKVoltsNOTIFY NOTIFICATION-TYPE
OBJECTS { ctrlGrpAmpsKVolts, ctrlGrpAmpsName, productFriendlyName, alarmTripType, alarmTrigger, alarmInstance }
STATUS current
DESCRIPTION "KVolts Trip Trap"
::= { cmTrapPrefix 11531 }

cmCtrlGrpAmpsLVoltsNOTIFY NOTIFICATION-TYPE
OBJECTS { ctrlGrpAmpsLVolts, ctrlGrpAmpsName, productFriendlyName, alarmTripType, alarmTrigger, alarmInstance }
STATUS current
DESCRIPTION "LVolts Trip Trap"
::= { cmTrapPrefix 11532 }

cmCtrlGrpAmpsMVoltsNOTIFY NOTIFICATION-TYPE
OBJECTS { ctrlGrpAmpsMVolts, ctrlGrpAmpsName, productFriendlyName, alarmTripType, alarmTrigger, alarmInstance }
STATUS current
DESCRIPTION "MVolts Trip Trap"
::= { cmTrapPrefix 11533 }

cmCtrlGrpAmpsNVoltsNOTIFY NOTIFICATION-TYPE
OBJECTS { ctrlGrpAmpsNVolts, ctrlGrpAmpsName, productFriendlyName, alarmTripType, alarmTrigger, alarmInstance }
STATUS current
DESCRIPTION "NVolts Trip Trap"
::= { cmTrapPrefix 11534 }

cmCtrlGrpAmpsOVoltsNOTIFY NOTIFICATION-TYPE
OBJECTS { ctrlGrpAmpsOVolts, ctrlGrpAmpsName, productFriendlyName, alarmTripType, alarmTrigger, alarmInstance }
STATUS current
DESCRIPTION "OVolts Trip Trap"
::= { cmTrapPrefix 11535 }

cmCtrlGrpAmpsPVoltsNOTIFY NOTIFICATION-TYPE
OBJECTS { ctrlGrpAmpsPVolts, ctrlGrpAmpsName, productFriendlyName, alarmTripType, alarmTrigger, alarmInstance }
STATUS current
DESCRIPTION "PVolts Trip Trap"
::= { cmTrapPrefix 11536 }

cmCtrlOutletPendingNOTIFY NOTIFICATION-TYPE
OBJECTS { ctrlOutletPending, ctrlOutletStatus, productFriendlyName, alarmTripType, alarmTrigger, alarmInstance }
STATUS current
DESCRIPTION "Pending Trip Trap"
::= { cmTrapPrefix 11605 }

cmCtrlOutletDeciAmpsNOTIFY NOTIFICATION-TYPE
OBJECTS { ctrlOutletDeciAmps, ctrlOutletStatus, productFriendlyName, alarmTripType, alarmTrigger, alarmInstance }
STATUS current
DESCRIPTION "Outlet DeciAmps Trap"
::= { cmTrapPrefix 11606 }

cmCtrlOutletGroupNOTIFY NOTIFICATION-TYPE
OBJECTS { ctrlOutletGroup, ctrlOutletStatus, productFriendlyName, alarmTripType, alarmTrigger, alarmInstance }
STATUS current
DESCRIPTION "Group Trip Trap"
::= { cmTrapPrefix 11607 }

cmCtrlOutletUpDelayNOTIFY NOTIFICATION-TYPE
OBJECTS { ctrlOutletUpDelay, ctrlOutletStatus, productFriendlyName, alarmTripType, alarmTrigger, alarmInstance }
STATUS current
DESCRIPTION "UpDelay Trip Trap"
::= { cmTrapPrefix 11608 }

cmCtrlOutletDwnDelayNOTIFY NOTIFICATION-TYPE
OBJECTS { ctrlOutletDwnDelay, ctrlOutletStatus, productFriendlyName, alarmTripType, alarmTrigger, alarmInstance }
STATUS current
DESCRIPTION "DwnDelay Trip Trap"
::= { cmTrapPrefix 11609 }

cmCtrlOutletRbtDurationNOTIFY NOTIFICATION-TYPE
OBJECTS { ctrlOutletRbtDuration, ctrlOutletStatus, productFriendlyName, alarmTripType, alarmTrigger, alarmInstance }
STATUS current
DESCRIPTION "RbtDuration Trip Trap"
::= { cmTrapPrefix 11610 }

cmCtrlOutletURLNOTIFY NOTIFICATION-TYPE
OBJECTS { ctrlOutletURL, ctrlOutletStatus, productFriendlyName, alarmTripType, alarmTrigger, alarmInstance }
STATUS current
DESCRIPTION "URL Trip Trap"
::= { cmTrapPrefix 11611 }

cmCtrlOutletPOAActionNOTIFY NOTIFICATION-TYPE
OBJECTS { ctrlOutletPOAAction, ctrlOutletStatus, productFriendlyName, alarmTripType, alarmTrigger, alarmInstance }
STATUS current
DESCRIPTION "POAAction Trip Trap"
::= { cmTrapPrefix 11612 }

cmCtrlOutletPOADelayNOTIFY NOTIFICATION-TYPE
OBJECTS { ctrlOutletPOADelay, ctrlOutletStatus, productFriendlyName, alarmTripType, alarmTrigger, alarmInstance }
STATUS current
DESCRIPTION "POADelay Trip Trap"
::= { cmTrapPrefix 11613 }

cmCtrlOutletkWattHrsNOTIFY NOTIFICATION-TYPE
OBJECTS { ctrlOutletkWattHrs, ctrlOutletStatus, productFriendlyName, alarmTripType, alarmTrigger, alarmInstance }
STATUS current
DESCRIPTION "kWattHrs Trip Trap"
::= { cmTrapPrefix 11614 }

cmCtrlOutletPowerNOTIFY NOTIFICATION-TYPE
OBJECTS { ctrlOutletPower, ctrlOutletStatus, productFriendlyName, alarmTripType, alarmTrigger, alarmInstance }
STATUS current
DESCRIPTION "Power Trip Trap"
::= { cmTrapPrefix 11615 }

cmCtrlOutletRbtDelayNOTIFY NOTIFICATION-TYPE
OBJECTS { ctrlOutletRbtDelay, ctrlOutletStatus, productFriendlyName, alarmTripType, alarmTrigger, alarmInstance }
STATUS current
DESCRIPTION "RbtDelay Trip Trap"
::= { cmTrapPrefix 11616 }

cmCtrlOutletStatusTimeNOTIFY NOTIFICATION-TYPE
OBJECTS { ctrlOutletStatusTime, ctrlOutletStatus, productFriendlyName, alarmTripType, alarmTrigger, alarmInstance }
STATUS current
DESCRIPTION "StatusTime Trip Trap"
::= { cmTrapPrefix 11617 }

cmDewPointSensorTempCNOTIFY NOTIFICATION-TYPE
OBJECTS { dewPointSensorTempC, dewPointSensorName, productFriendlyName, alarmTripType, temperaturePrecision, alarmTrigger, alarmInstance }
STATUS current
DESCRIPTION "Remote Dew Point Sensor - Temperature Trap"
::= { cmTrapPrefix 11705 }

cmDewPointSensorTempFNOTIFY NOTIFICATION-TYPE
OBJECTS { dewPointSensorTempF, dewPointSensorName, productFriendlyName, alarmTripType, temperaturePrecision, alarmTrigger, alarmInstance }
STATUS current
DESCRIPTION "Remote Dew Point Sensor - Temperature Trap"
::= { cmTrapPrefix 11706 }

cmDewPointSensorHumidityNOTIFY NOTIFICATION-TYPE
OBJECTS { dewPointSensorHumidity, dewPointSensorName, productFriendlyName, alarmTripType, alarmTrigger, alarmInstance }
STATUS current
DESCRIPTION "Remote Dew Point Sensor - Humidity"
::= { cmTrapPrefix 11707 }

cmDewPointSensorDewPointCNOTIFY NOTIFICATION-TYPE
OBJECTS { dewPointSensorDewPointC, dewPointSensorName, productFriendlyName, alarmTripType, temperaturePrecision, alarmTrigger, alarmInstance }
STATUS current
DESCRIPTION "Remote Dew Point Sensor - Dew Point Trap"
::= { cmTrapPrefix 11708 }

cmDewPointSensorDewPointFNOTIFY NOTIFICATION-TYPE
OBJECTS { dewPointSensorDewPointF, dewPointSensorName, productFriendlyName, alarmTripType, temperaturePrecision, alarmTrigger, alarmInstance }
STATUS current
DESCRIPTION "Remote Dew Point Sensor - Dew Point Trap"
::= { cmTrapPrefix 11709 }

cmDigitalSensorDigitalNOTIFY NOTIFICATION-TYPE
OBJECTS { digitalSensorDigital, digitalSensorName, productFriendlyName, alarmTripType, alarmTrigger, alarmInstance }
STATUS current
DESCRIPTION "Digital sensor Trap"
::= { cmTrapPrefix 11805 }

cmDstsVoltsANOTIFY NOTIFICATION-TYPE
OBJECTS { dstsVoltsA, dstsName, productFriendlyName, alarmTripType, alarmTrigger, alarmInstance }
STATUS current
DESCRIPTION "RMS Voltage of Side A Set Point Sensor Trap"
::= { cmTrapPrefix 11905 }

cmDstsDeciAmpsANOTIFY NOTIFICATION-TYPE
OBJECTS { dstsDeciAmpsA, dstsName, productFriendlyName, alarmTripType, alarmTrigger, alarmInstance }
STATUS current
DESCRIPTION "RMS Current of Side A Set Point Sensor Trap"
::= { cmTrapPrefix 11906 }

cmDstsVoltsBNOTIFY NOTIFICATION-TYPE
OBJECTS { dstsVoltsB, dstsName, productFriendlyName, alarmTripType, alarmTrigger, alarmInstance }
STATUS current
DESCRIPTION "RMS Voltage of Side B Set Point Sensor Trap"
::= { cmTrapPrefix 11907 }

cmDstsDeciAmpsBNOTIFY NOTIFICATION-TYPE
OBJECTS { dstsDeciAmpsB, dstsName, productFriendlyName, alarmTripType, alarmTrigger, alarmInstance }
STATUS current
DESCRIPTION "RMS Current of Side B Set Point Sensor Trap"
::= { cmTrapPrefix 11908 }

cmDstsSourceAActiveNOTIFY NOTIFICATION-TYPE
OBJECTS { dstsSourceAActive, dstsName, productFriendlyName, alarmTripType, alarmTrigger, alarmInstance }
STATUS current
DESCRIPTION "Source A Active Set Point Sensor Trap"
::= { cmTrapPrefix 11909 }

cmDstsSourceBActiveNOTIFY NOTIFICATION-TYPE
OBJECTS { dstsSourceBActive, dstsName, productFriendlyName, alarmTripType, alarmTrigger, alarmInstance }
STATUS current
DESCRIPTION "Source B Active Set Point Sensor Trap"
::= { cmTrapPrefix 11910 }

cmDstsPowerStatusANOTIFY NOTIFICATION-TYPE
OBJECTS { dstsPowerStatusA, dstsName, productFriendlyName, alarmTripType, alarmTrigger, alarmInstance }
STATUS current
DESCRIPTION "Source A Power Qualilty Active Set Point Sensor Trap"
::= { cmTrapPrefix 11911 }

cmDstsPowerStatusBNOTIFY NOTIFICATION-TYPE
OBJECTS { dstsPowerStatusB, dstsName, productFriendlyName, alarmTripType, alarmTrigger, alarmInstance }
STATUS current
DESCRIPTION "Source B Power Qualilty Active Set Point Sensor Trap"
::= { cmTrapPrefix 11912 }

cmDstsSourceATempCNOTIFY NOTIFICATION-TYPE
OBJECTS { dstsSourceATempC, dstsName, productFriendlyName, alarmTripType, temperaturePrecision, alarmTrigger, alarmInstance }
STATUS current
DESCRIPTION "Source A Temp Sensor Trap"
::= { cmTrapPrefix 11913 }

cmDstsSourceBTempCNOTIFY NOTIFICATION-TYPE
OBJECTS { dstsSourceBTempC, dstsName, productFriendlyName, alarmTripType, temperaturePrecision, alarmTrigger, alarmInstance }
STATUS current
DESCRIPTION "Source B Temp Sensor Trap"
::= { cmTrapPrefix 11914 }

cmCpmSensorStatusNOTIFY NOTIFICATION-TYPE
OBJECTS { cpmSensorStatus, cpmSensorName, productFriendlyName, alarmTripType, alarmTrigger, alarmInstance }
STATUS current
DESCRIPTION "City Power sensor Trap"
::= { cmTrapPrefix 12005 }

cmSmokeAlarmStatusNOTIFY NOTIFICATION-TYPE
OBJECTS { smokeAlarmStatus, smokeAlarmName, productFriendlyName, alarmTripType, alarmTrigger, alarmInstance }
STATUS current
DESCRIPTION "Smoke alarm Trap"
::= { cmTrapPrefix 12105 }

cmNeg48VdcSensorVoltageNOTIFY NOTIFICATION-TYPE
OBJECTS { neg48VdcSensorVoltage, neg48VdcSensorName, productFriendlyName, alarmTripType, alarmTrigger, alarmInstance }
STATUS current
DESCRIPTION "-48Vdc Sensor Trap"
::= { cmTrapPrefix 12205 }

cmPos30VdcSensorVoltageNOTIFY NOTIFICATION-TYPE
OBJECTS { pos30VdcSensorVoltage, pos30VdcSensorName, productFriendlyName, alarmTripType, alarmTrigger, alarmInstance }
STATUS current
DESCRIPTION "30Vdc Sensor Trap"
::= { cmTrapPrefix 12305 }

cmAnalogSensorAnalogNOTIFY NOTIFICATION-TYPE
OBJECTS { analogSensorAnalog, analogSensorName, productFriendlyName, alarmTripType, alarmTrigger, alarmInstance }
STATUS current
DESCRIPTION "Analog Sensor Trap"
::= { cmTrapPrefix 12405 }

cmCtrl3ChIECkWattHrsANOTIFY NOTIFICATION-TYPE
OBJECTS { ctrl3ChIECkWattHrsA, ctrl3ChIECName, productFriendlyName, alarmTripType, alarmTrigger, alarmInstance }
STATUS current
DESCRIPTION "Kilo Watt Hours A Trap"
::= { cmTrapPrefix 12505 }

cmCtrl3ChIECVoltsANOTIFY NOTIFICATION-TYPE
OBJECTS { ctrl3ChIECVoltsA, ctrl3ChIECName, productFriendlyName, alarmTripType, alarmTrigger, alarmInstance }
STATUS current
DESCRIPTION "Volts A Trap"
::= { cmTrapPrefix 12506 }

cmCtrl3ChIECVoltPeakANOTIFY NOTIFICATION-TYPE
OBJECTS { ctrl3ChIECVoltPeakA, ctrl3ChIECName, productFriendlyName, alarmTripType, alarmTrigger, alarmInstance }
STATUS current
DESCRIPTION "Volts Peak A Trap"
::= { cmTrapPrefix 12507 }

cmCtrl3ChIECDeciAmpsANOTIFY NOTIFICATION-TYPE
OBJECTS { ctrl3ChIECDeciAmpsA, ctrl3ChIECName, productFriendlyName, alarmTripType, alarmTrigger, alarmInstance }
STATUS current
DESCRIPTION "Deciamps A Trap"
::= { cmTrapPrefix 12508 }

cmCtrl3ChIECDeciAmpsPeakANOTIFY NOTIFICATION-TYPE
OBJECTS { ctrl3ChIECDeciAmpsPeakA, ctrl3ChIECName, productFriendlyName, alarmTripType, alarmTrigger, alarmInstance }
STATUS current
DESCRIPTION "Deciamps Peak A Trap"
::= { cmTrapPrefix 12509 }

cmCtrl3ChIECRealPowerANOTIFY NOTIFICATION-TYPE
OBJECTS { ctrl3ChIECRealPowerA, ctrl3ChIECName, productFriendlyName, alarmTripType, alarmTrigger, alarmInstance }
STATUS current
DESCRIPTION "Real Power A Trap"
::= { cmTrapPrefix 12510 }

cmCtrl3ChIECApparentPowerANOTIFY NOTIFICATION-TYPE
OBJECTS { ctrl3ChIECApparentPowerA, ctrl3ChIECName, productFriendlyName, alarmTripType, alarmTrigger, alarmInstance }
STATUS current
DESCRIPTION "Apparent Power A Trap"
::= { cmTrapPrefix 12511 }

cmCtrl3ChIECPowerFactorANOTIFY NOTIFICATION-TYPE
OBJECTS { ctrl3ChIECPowerFactorA, ctrl3ChIECName, productFriendlyName, alarmTripType, alarmTrigger, alarmInstance }
STATUS current
DESCRIPTION "Power Factor A Trap"
::= { cmTrapPrefix 12512 }

cmCtrl3ChIECkWattHrsBNOTIFY NOTIFICATION-TYPE
OBJECTS { ctrl3ChIECkWattHrsB, ctrl3ChIECName, productFriendlyName, alarmTripType, alarmTrigger, alarmInstance }
STATUS current
DESCRIPTION "Kilo Watt Hours B Trap"
::= { cmTrapPrefix 12513 }

cmCtrl3ChIECVoltsBNOTIFY NOTIFICATION-TYPE
OBJECTS { ctrl3ChIECVoltsB, ctrl3ChIECName, productFriendlyName, alarmTripType, alarmTrigger, alarmInstance }
STATUS current
DESCRIPTION "Volts B Trap"
::= { cmTrapPrefix 12514 }

cmCtrl3ChIECVoltPeakBNOTIFY NOTIFICATION-TYPE
OBJECTS { ctrl3ChIECVoltPeakB, ctrl3ChIECName, productFriendlyName, alarmTripType, alarmTrigger, alarmInstance }
STATUS current
DESCRIPTION "Volts Peak B Trap"
::= { cmTrapPrefix 12515 }

cmCtrl3ChIECDeciAmpsBNOTIFY NOTIFICATION-TYPE
OBJECTS { ctrl3ChIECDeciAmpsB, ctrl3ChIECName, productFriendlyName, alarmTripType, alarmTrigger, alarmInstance }
STATUS current
DESCRIPTION "Deciamps B Trap"
::= { cmTrapPrefix 12516 }

cmCtrl3ChIECDeciAmpsPeakBNOTIFY NOTIFICATION-TYPE
OBJECTS { ctrl3ChIECDeciAmpsPeakB, ctrl3ChIECName, productFriendlyName, alarmTripType, alarmTrigger, alarmInstance }
STATUS current
DESCRIPTION "Deciamps Peak B Trap"
::= { cmTrapPrefix 12517 }

cmCtrl3ChIECRealPowerBNOTIFY NOTIFICATION-TYPE
OBJECTS { ctrl3ChIECRealPowerB, ctrl3ChIECName, productFriendlyName, alarmTripType, alarmTrigger, alarmInstance }
STATUS current
DESCRIPTION "Real Power B Trap"
::= { cmTrapPrefix 12518 }

cmCtrl3ChIECApparentPowerBNOTIFY NOTIFICATION-TYPE
OBJECTS { ctrl3ChIECApparentPowerB, ctrl3ChIECName, productFriendlyName, alarmTripType, alarmTrigger, alarmInstance }
STATUS current
DESCRIPTION "Apparent Power B Trap"
::= { cmTrapPrefix 12519 }

cmCtrl3ChIECPowerFactorBNOTIFY NOTIFICATION-TYPE
OBJECTS { ctrl3ChIECPowerFactorB, ctrl3ChIECName, productFriendlyName, alarmTripType, alarmTrigger, alarmInstance }
STATUS current
DESCRIPTION "Power Factor B Trap"
::= { cmTrapPrefix 12520 }

cmCtrl3ChIECkWattHrsCNOTIFY NOTIFICATION-TYPE
OBJECTS { ctrl3ChIECkWattHrsC, ctrl3ChIECName, productFriendlyName, alarmTripType, alarmTrigger, alarmInstance }
STATUS current
DESCRIPTION "Kilo Watt Hours C Trap"
::= { cmTrapPrefix 12521 }

cmCtrl3ChIECVoltsCNOTIFY NOTIFICATION-TYPE
OBJECTS { ctrl3ChIECVoltsC, ctrl3ChIECName, productFriendlyName, alarmTripType, alarmTrigger, alarmInstance }
STATUS current
DESCRIPTION "Volts C Trap"
::= { cmTrapPrefix 12522 }

cmCtrl3ChIECVoltPeakCNOTIFY NOTIFICATION-TYPE
OBJECTS { ctrl3ChIECVoltPeakC, ctrl3ChIECName, productFriendlyName, alarmTripType, alarmTrigger, alarmInstance }
STATUS current
DESCRIPTION "Volts Peak C Trap"
::= { cmTrapPrefix 12523 }

cmCtrl3ChIECDeciAmpsCNOTIFY NOTIFICATION-TYPE
OBJECTS { ctrl3ChIECDeciAmpsC, ctrl3ChIECName, productFriendlyName, alarmTripType, alarmTrigger, alarmInstance }
STATUS current
DESCRIPTION "Deciamps C Trap"
::= { cmTrapPrefix 12524 }

cmCtrl3ChIECDeciAmpsPeakCNOTIFY NOTIFICATION-TYPE
OBJECTS { ctrl3ChIECDeciAmpsPeakC, ctrl3ChIECName, productFriendlyName, alarmTripType, alarmTrigger, alarmInstance }
STATUS current
DESCRIPTION "Deciamps Peak C Trap"
::= { cmTrapPrefix 12525 }

cmCtrl3ChIECRealPowerCNOTIFY NOTIFICATION-TYPE
OBJECTS { ctrl3ChIECRealPowerC, ctrl3ChIECName, productFriendlyName, alarmTripType, alarmTrigger, alarmInstance }
STATUS current
DESCRIPTION "Real Power C Trap"
::= { cmTrapPrefix 12526 }

cmCtrl3ChIECApparentPowerCNOTIFY NOTIFICATION-TYPE
OBJECTS { ctrl3ChIECApparentPowerC, ctrl3ChIECName, productFriendlyName, alarmTripType, alarmTrigger, alarmInstance }
STATUS current
DESCRIPTION "Apparent Power C Trap"
::= { cmTrapPrefix 12527 }

cmCtrl3ChIECPowerFactorCNOTIFY NOTIFICATION-TYPE
OBJECTS { ctrl3ChIECPowerFactorC, ctrl3ChIECName, productFriendlyName, alarmTripType, alarmTrigger, alarmInstance }
STATUS current
DESCRIPTION "Power Factor C Trap"
::= { cmTrapPrefix 12528 }

cmCtrl3ChIECkWattHrsTotalNOTIFY NOTIFICATION-TYPE
OBJECTS { ctrl3ChIECkWattHrsTotal, ctrl3ChIECName, productFriendlyName, alarmTripType, alarmTrigger, alarmInstance }
STATUS current
DESCRIPTION "Kilo Watt Hours Total Trap"
::= { cmTrapPrefix 12529 }

cmCtrl3ChIECRealPowerTotalNOTIFY NOTIFICATION-TYPE
OBJECTS { ctrl3ChIECRealPowerTotal, ctrl3ChIECName, productFriendlyName, alarmTripType, alarmTrigger, alarmInstance }
STATUS current
DESCRIPTION "Watts Total Trap"
::= { cmTrapPrefix 12530 }

cmClimateRelayTempCNOTIFY NOTIFICATION-TYPE
OBJECTS { climateRelayTempC, climateRelayName, productFriendlyName, alarmTripType, temperaturePrecision, alarmTrigger, alarmInstance }
STATUS current
DESCRIPTION "Climate Relay Temperature Sensor Trap"
::= { cmTrapPrefix 12605 }

cmClimateRelayTempFNOTIFY NOTIFICATION-TYPE
OBJECTS { climateRelayTempF, climateRelayName, productFriendlyName, alarmTripType, temperaturePrecision, alarmTrigger, alarmInstance }
STATUS current
DESCRIPTION "Climate Relay Temperature Sensor Trap"
::= { cmTrapPrefix 12606 }

cmClimateRelayIO1NOTIFY NOTIFICATION-TYPE
OBJECTS { climateRelayIO1, climateRelayName, productFriendlyName, alarmTripType, alarmTrigger, alarmInstance }
STATUS current
DESCRIPTION "Climate Relay IO1 Sensor Trap"
::= { cmTrapPrefix 12607 }

cmClimateRelayIO2NOTIFY NOTIFICATION-TYPE
OBJECTS { climateRelayIO2, climateRelayName, productFriendlyName, alarmTripType, alarmTrigger, alarmInstance }
STATUS current
DESCRIPTION "Climate Relay IO2 Sensor Trap"
::= { cmTrapPrefix 12608 }

cmClimateRelayIO3NOTIFY NOTIFICATION-TYPE
OBJECTS { climateRelayIO3, climateRelayName, productFriendlyName, alarmTripType, alarmTrigger, alarmInstance }
STATUS current
DESCRIPTION "Climate Relay IO3 Sensor Trap"
::= { cmTrapPrefix 12609 }

cmClimateRelayIO4NOTIFY NOTIFICATION-TYPE
OBJECTS { climateRelayIO4, climateRelayName, productFriendlyName, alarmTripType, alarmTrigger, alarmInstance }
STATUS current
DESCRIPTION "Climate Relay IO4 Sensor Trap"
::= { cmTrapPrefix 12610 }

cmClimateRelayIO5NOTIFY NOTIFICATION-TYPE
OBJECTS { climateRelayIO5, climateRelayName, productFriendlyName, alarmTripType, alarmTrigger, alarmInstance }
STATUS current
DESCRIPTION "Climate Relay IO5 Sensor Trap"
::= { cmTrapPrefix 12611 }

cmClimateRelayIO6NOTIFY NOTIFICATION-TYPE
OBJECTS { climateRelayIO6, climateRelayName, productFriendlyName, alarmTripType, alarmTrigger, alarmInstance }
STATUS current
DESCRIPTION "Climate Relay IO6 Sensor Trap"
::= { cmTrapPrefix 12612 }

cmAirSpeedSwitchSensorAirSpeedNOTIFY NOTIFICATION-TYPE
OBJECTS { airSpeedSwitchSensorAirSpeed, airSpeedSwitchSensorName, productFriendlyName, alarmTripType, alarmTrigger, alarmInstance }
STATUS current
DESCRIPTION "Air Speed Switch Trap"
::= { cmTrapPrefix 12805 }

cmPowerDMDeciAmps1NOTIFY NOTIFICATION-TYPE
OBJECTS { powerDMDeciAmps1, powerDMName, productFriendlyName, alarmTripType, alarmTrigger, alarmInstance }
STATUS current
DESCRIPTION "DM48 Current Monitor Amps Trap"
::= { cmTrapPrefix 129153 }

cmPowerDMDeciAmps2NOTIFY NOTIFICATION-TYPE
OBJECTS { powerDMDeciAmps2, powerDMName, productFriendlyName, alarmTripType, alarmTrigger, alarmInstance }
STATUS current
DESCRIPTION "DM48 Current Monitor Amps Trap"
::= { cmTrapPrefix 129154 }

cmPowerDMDeciAmps3NOTIFY NOTIFICATION-TYPE
OBJECTS { powerDMDeciAmps3, powerDMName, productFriendlyName, alarmTripType, alarmTrigger, alarmInstance }
STATUS current
DESCRIPTION "DM48 Current Monitor Amps Trap"
::= { cmTrapPrefix 129155 }

cmPowerDMDeciAmps4NOTIFY NOTIFICATION-TYPE
OBJECTS { powerDMDeciAmps4, powerDMName, productFriendlyName, alarmTripType, alarmTrigger, alarmInstance }
STATUS current
DESCRIPTION "DM48 Current Monitor Amps Trap"
::= { cmTrapPrefix 129156 }

cmPowerDMDeciAmps5NOTIFY NOTIFICATION-TYPE
OBJECTS { powerDMDeciAmps5, powerDMName, productFriendlyName, alarmTripType, alarmTrigger, alarmInstance }
STATUS current
DESCRIPTION "DM48 Current Monitor Amps Trap"
::= { cmTrapPrefix 129157 }

cmPowerDMDeciAmps6NOTIFY NOTIFICATION-TYPE
OBJECTS { powerDMDeciAmps6, powerDMName, productFriendlyName, alarmTripType, alarmTrigger, alarmInstance }
STATUS current
DESCRIPTION "DM48 Current Monitor Amps Trap"
::= { cmTrapPrefix 129158 }

cmPowerDMDeciAmps7NOTIFY NOTIFICATION-TYPE
OBJECTS { powerDMDeciAmps7, powerDMName, productFriendlyName, alarmTripType, alarmTrigger, alarmInstance }
STATUS current
DESCRIPTION "DM48 Current Monitor Amps Trap"
::= { cmTrapPrefix 129159 }

cmPowerDMDeciAmps8NOTIFY NOTIFICATION-TYPE
OBJECTS { powerDMDeciAmps8, powerDMName, productFriendlyName, alarmTripType, alarmTrigger, alarmInstance }
STATUS current
DESCRIPTION "DM48 Current Monitor Amps Trap"
::= { cmTrapPrefix 129160 }

cmPowerDMDeciAmps9NOTIFY NOTIFICATION-TYPE
OBJECTS { powerDMDeciAmps9, powerDMName, productFriendlyName, alarmTripType, alarmTrigger, alarmInstance }
STATUS current
DESCRIPTION "DM48 Current Monitor Amps Trap"
::= { cmTrapPrefix 129161 }

cmPowerDMDeciAmps10NOTIFY NOTIFICATION-TYPE
OBJECTS { powerDMDeciAmps10, powerDMName, productFriendlyName, alarmTripType, alarmTrigger, alarmInstance }
STATUS current
DESCRIPTION "DM48 Current Monitor Amps Trap"
::= { cmTrapPrefix 129162 }

cmPowerDMDeciAmps11NOTIFY NOTIFICATION-TYPE
OBJECTS { powerDMDeciAmps11, powerDMName, productFriendlyName, alarmTripType, alarmTrigger, alarmInstance }
STATUS current
DESCRIPTION "DM48 Current Monitor Amps Trap"
::= { cmTrapPrefix 129163 }

cmPowerDMDeciAmps12NOTIFY NOTIFICATION-TYPE
OBJECTS { powerDMDeciAmps12, powerDMName, productFriendlyName, alarmTripType, alarmTrigger, alarmInstance }
STATUS current
DESCRIPTION "DM48 Current Monitor Amps Trap"
::= { cmTrapPrefix 129164 }

cmPowerDMDeciAmps13NOTIFY NOTIFICATION-TYPE
OBJECTS { powerDMDeciAmps13, powerDMName, productFriendlyName, alarmTripType, alarmTrigger, alarmInstance }
STATUS current
DESCRIPTION "DM48 Current Monitor Amps Trap"
::= { cmTrapPrefix 129165 }

cmPowerDMDeciAmps14NOTIFY NOTIFICATION-TYPE
OBJECTS { powerDMDeciAmps14, powerDMName, productFriendlyName, alarmTripType, alarmTrigger, alarmInstance }
STATUS current
DESCRIPTION "DM48 Current Monitor Amps Trap"
::= { cmTrapPrefix 129166 }

cmPowerDMDeciAmps15NOTIFY NOTIFICATION-TYPE
OBJECTS { powerDMDeciAmps15, powerDMName, productFriendlyName, alarmTripType, alarmTrigger, alarmInstance }
STATUS current
DESCRIPTION "DM48 Current Monitor Amps Trap"
::= { cmTrapPrefix 129167 }

cmPowerDMDeciAmps16NOTIFY NOTIFICATION-TYPE
OBJECTS { powerDMDeciAmps16, powerDMName, productFriendlyName, alarmTripType, alarmTrigger, alarmInstance }
STATUS current
DESCRIPTION "DM48 Current Monitor Amps Trap"
::= { cmTrapPrefix 129168 }

cmPowerDMDeciAmps17NOTIFY NOTIFICATION-TYPE
OBJECTS { powerDMDeciAmps17, powerDMName, productFriendlyName, alarmTripType, alarmTrigger, alarmInstance }
STATUS current
DESCRIPTION "DM48 Current Monitor Amps Trap"
::= { cmTrapPrefix 129169 }

cmPowerDMDeciAmps18NOTIFY NOTIFICATION-TYPE
OBJECTS { powerDMDeciAmps18, powerDMName, productFriendlyName, alarmTripType, alarmTrigger, alarmInstance }
STATUS current
DESCRIPTION "DM48 Current Monitor Amps Trap"
::= { cmTrapPrefix 129170 }

cmPowerDMDeciAmps19NOTIFY NOTIFICATION-TYPE
OBJECTS { powerDMDeciAmps19, powerDMName, productFriendlyName, alarmTripType, alarmTrigger, alarmInstance }
STATUS current
DESCRIPTION "DM48 Current Monitor Amps Trap"
::= { cmTrapPrefix 129171 }

cmPowerDMDeciAmps20NOTIFY NOTIFICATION-TYPE
OBJECTS { powerDMDeciAmps20, powerDMName, productFriendlyName, alarmTripType, alarmTrigger, alarmInstance }
STATUS current
DESCRIPTION "DM48 Current Monitor Amps Trap"
::= { cmTrapPrefix 129172 }

cmPowerDMDeciAmps21NOTIFY NOTIFICATION-TYPE
OBJECTS { powerDMDeciAmps21, powerDMName, productFriendlyName, alarmTripType, alarmTrigger, alarmInstance }
STATUS current
DESCRIPTION "DM48 Current Monitor Amps Trap"
::= { cmTrapPrefix 129173 }

cmPowerDMDeciAmps22NOTIFY NOTIFICATION-TYPE
OBJECTS { powerDMDeciAmps22, powerDMName, productFriendlyName, alarmTripType, alarmTrigger, alarmInstance }
STATUS current
DESCRIPTION "DM48 Current Monitor Amps Trap"
::= { cmTrapPrefix 129174 }

cmPowerDMDeciAmps23NOTIFY NOTIFICATION-TYPE
OBJECTS { powerDMDeciAmps23, powerDMName, productFriendlyName, alarmTripType, alarmTrigger, alarmInstance }
STATUS current
DESCRIPTION "DM48 Current Monitor Amps Trap"
::= { cmTrapPrefix 129175 }

cmPowerDMDeciAmps24NOTIFY NOTIFICATION-TYPE
OBJECTS { powerDMDeciAmps24, powerDMName, productFriendlyName, alarmTripType, alarmTrigger, alarmInstance }
STATUS current
DESCRIPTION "DM48 Current Monitor Amps Trap"
::= { cmTrapPrefix 129176 }

cmPowerDMDeciAmps25NOTIFY NOTIFICATION-TYPE
OBJECTS { powerDMDeciAmps25, powerDMName, productFriendlyName, alarmTripType, alarmTrigger, alarmInstance }
STATUS current
DESCRIPTION "DM48 Current Monitor Amps Trap"
::= { cmTrapPrefix 129177 }

cmPowerDMDeciAmps26NOTIFY NOTIFICATION-TYPE
OBJECTS { powerDMDeciAmps26, powerDMName, productFriendlyName, alarmTripType, alarmTrigger, alarmInstance }
STATUS current
DESCRIPTION "DM48 Current Monitor Amps Trap"
::= { cmTrapPrefix 129178 }

cmPowerDMDeciAmps27NOTIFY NOTIFICATION-TYPE
OBJECTS { powerDMDeciAmps27, powerDMName, productFriendlyName, alarmTripType, alarmTrigger, alarmInstance }
STATUS current
DESCRIPTION "DM48 Current Monitor Amps Trap"
::= { cmTrapPrefix 129179 }

cmPowerDMDeciAmps28NOTIFY NOTIFICATION-TYPE
OBJECTS { powerDMDeciAmps28, powerDMName, productFriendlyName, alarmTripType, alarmTrigger, alarmInstance }
STATUS current
DESCRIPTION "DM48 Current Monitor Amps Trap"
::= { cmTrapPrefix 129180 }

cmPowerDMDeciAmps29NOTIFY NOTIFICATION-TYPE
OBJECTS { powerDMDeciAmps29, powerDMName, productFriendlyName, alarmTripType, alarmTrigger, alarmInstance }
STATUS current
DESCRIPTION "DM48 Current Monitor Amps Trap"
::= { cmTrapPrefix 129181 }

cmPowerDMDeciAmps30NOTIFY NOTIFICATION-TYPE
OBJECTS { powerDMDeciAmps30, powerDMName, productFriendlyName, alarmTripType, alarmTrigger, alarmInstance }
STATUS current
DESCRIPTION "DM48 Current Monitor Amps Trap"
::= { cmTrapPrefix 129182 }

cmPowerDMDeciAmps31NOTIFY NOTIFICATION-TYPE
OBJECTS { powerDMDeciAmps31, powerDMName, productFriendlyName, alarmTripType, alarmTrigger, alarmInstance }
STATUS current
DESCRIPTION "DM48 Current Monitor Amps Trap"
::= { cmTrapPrefix 129183 }

cmPowerDMDeciAmps32NOTIFY NOTIFICATION-TYPE
OBJECTS { powerDMDeciAmps32, powerDMName, productFriendlyName, alarmTripType, alarmTrigger, alarmInstance }
STATUS current
DESCRIPTION "DM48 Current Monitor Amps Trap"
::= { cmTrapPrefix 129184 }

cmPowerDMDeciAmps33NOTIFY NOTIFICATION-TYPE
OBJECTS { powerDMDeciAmps33, powerDMName, productFriendlyName, alarmTripType, alarmTrigger, alarmInstance }
STATUS current
DESCRIPTION "DM48 Current Monitor Amps Trap"
::= { cmTrapPrefix 129185 }

cmPowerDMDeciAmps34NOTIFY NOTIFICATION-TYPE
OBJECTS { powerDMDeciAmps34, powerDMName, productFriendlyName, alarmTripType, alarmTrigger, alarmInstance }
STATUS current
DESCRIPTION "DM48 Current Monitor Amps Trap"
::= { cmTrapPrefix 129186 }

cmPowerDMDeciAmps35NOTIFY NOTIFICATION-TYPE
OBJECTS { powerDMDeciAmps35, powerDMName, productFriendlyName, alarmTripType, alarmTrigger, alarmInstance }
STATUS current
DESCRIPTION "DM48 Current Monitor Amps Trap"
::= { cmTrapPrefix 129187 }

cmPowerDMDeciAmps36NOTIFY NOTIFICATION-TYPE
OBJECTS { powerDMDeciAmps36, powerDMName, productFriendlyName, alarmTripType, alarmTrigger, alarmInstance }
STATUS current
DESCRIPTION "DM48 Current Monitor Amps Trap"
::= { cmTrapPrefix 129188 }

cmPowerDMDeciAmps37NOTIFY NOTIFICATION-TYPE
OBJECTS { powerDMDeciAmps37, powerDMName, productFriendlyName, alarmTripType, alarmTrigger, alarmInstance }
STATUS current
DESCRIPTION "DM48 Current Monitor Amps Trap"
::= { cmTrapPrefix 129189 }

cmPowerDMDeciAmps38NOTIFY NOTIFICATION-TYPE
OBJECTS { powerDMDeciAmps38, powerDMName, productFriendlyName, alarmTripType, alarmTrigger, alarmInstance }
STATUS current
DESCRIPTION "DM48 Current Monitor Amps Trap"
::= { cmTrapPrefix 129190 }

cmPowerDMDeciAmps39NOTIFY NOTIFICATION-TYPE
OBJECTS { powerDMDeciAmps39, powerDMName, productFriendlyName, alarmTripType, alarmTrigger, alarmInstance }
STATUS current
DESCRIPTION "DM48 Current Monitor Amps Trap"
::= { cmTrapPrefix 129191 }

cmPowerDMDeciAmps40NOTIFY NOTIFICATION-TYPE
OBJECTS { powerDMDeciAmps40, powerDMName, productFriendlyName, alarmTripType, alarmTrigger, alarmInstance }
STATUS current
DESCRIPTION "DM48 Current Monitor Amps Trap"
::= { cmTrapPrefix 129192 }

cmPowerDMDeciAmps41NOTIFY NOTIFICATION-TYPE
OBJECTS { powerDMDeciAmps41, powerDMName, productFriendlyName, alarmTripType, alarmTrigger, alarmInstance }
STATUS current
DESCRIPTION "DM48 Current Monitor Amps Trap"
::= { cmTrapPrefix 129193 }

cmPowerDMDeciAmps42NOTIFY NOTIFICATION-TYPE
OBJECTS { powerDMDeciAmps42, powerDMName, productFriendlyName, alarmTripType, alarmTrigger, alarmInstance }
STATUS current
DESCRIPTION "DM48 Current Monitor Amps Trap"
::= { cmTrapPrefix 129194 }

cmPowerDMDeciAmps43NOTIFY NOTIFICATION-TYPE
OBJECTS { powerDMDeciAmps43, powerDMName, productFriendlyName, alarmTripType, alarmTrigger, alarmInstance }
STATUS current
DESCRIPTION "DM48 Current Monitor Amps Trap"
::= { cmTrapPrefix 129195 }

cmPowerDMDeciAmps44NOTIFY NOTIFICATION-TYPE
OBJECTS { powerDMDeciAmps44, powerDMName, productFriendlyName, alarmTripType, alarmTrigger, alarmInstance }
STATUS current
DESCRIPTION "DM48 Current Monitor Amps Trap"
::= { cmTrapPrefix 129196 }

cmPowerDMDeciAmps45NOTIFY NOTIFICATION-TYPE
OBJECTS { powerDMDeciAmps45, powerDMName, productFriendlyName, alarmTripType, alarmTrigger, alarmInstance }
STATUS current
DESCRIPTION "DM48 Current Monitor Amps Trap"
::= { cmTrapPrefix 129197 }

cmPowerDMDeciAmps46NOTIFY NOTIFICATION-TYPE
OBJECTS { powerDMDeciAmps46, powerDMName, productFriendlyName, alarmTripType, alarmTrigger, alarmInstance }
STATUS current
DESCRIPTION "DM48 Current Monitor Amps Trap"
::= { cmTrapPrefix 129198 }

cmPowerDMDeciAmps47NOTIFY NOTIFICATION-TYPE
OBJECTS { powerDMDeciAmps47, powerDMName, productFriendlyName, alarmTripType, alarmTrigger, alarmInstance }
STATUS current
DESCRIPTION "DM48 Current Monitor Amps Trap"
::= { cmTrapPrefix 129199 }

cmPowerDMDeciAmps48NOTIFY NOTIFICATION-TYPE
OBJECTS { powerDMDeciAmps48, powerDMName, productFriendlyName, alarmTripType, alarmTrigger, alarmInstance }
STATUS current
DESCRIPTION "DM48 Current Monitor Amps Trap"
::= { cmTrapPrefix 129200 }

cmIoExpanderIO1NOTIFY NOTIFICATION-TYPE
OBJECTS { ioExpanderIO1, ioExpanderName, productFriendlyName, alarmTripType, alarmTrigger, alarmInstance }
STATUS current
DESCRIPTION "Climate Relay IO1 Sensor Trap"
::= { cmTrapPrefix 13037 }

cmIoExpanderIO2NOTIFY NOTIFICATION-TYPE
OBJECTS { ioExpanderIO2, ioExpanderName, productFriendlyName, alarmTripType, alarmTrigger, alarmInstance }
STATUS current
DESCRIPTION "Climate Relay IO2 Sensor Trap"
::= { cmTrapPrefix 13038 }

cmIoExpanderIO3NOTIFY NOTIFICATION-TYPE
OBJECTS { ioExpanderIO3, ioExpanderName, productFriendlyName, alarmTripType, alarmTrigger, alarmInstance }
STATUS current
DESCRIPTION "Climate Relay IO3 Sensor Trap"
::= { cmTrapPrefix 13039 }

cmIoExpanderIO4NOTIFY NOTIFICATION-TYPE
OBJECTS { ioExpanderIO4, ioExpanderName, productFriendlyName, alarmTripType, alarmTrigger, alarmInstance }
STATUS current
DESCRIPTION "Climate Relay IO4 Sensor Trap"
::= { cmTrapPrefix 13040 }

cmIoExpanderIO5NOTIFY NOTIFICATION-TYPE
OBJECTS { ioExpanderIO5, ioExpanderName, productFriendlyName, alarmTripType, alarmTrigger, alarmInstance }
STATUS current
DESCRIPTION "Climate Relay IO5 Sensor Trap"
::= { cmTrapPrefix 13041 }

cmIoExpanderIO6NOTIFY NOTIFICATION-TYPE
OBJECTS { ioExpanderIO6, ioExpanderName, productFriendlyName, alarmTripType, alarmTrigger, alarmInstance }
STATUS current
DESCRIPTION "Climate Relay IO6 Sensor Trap"
::= { cmTrapPrefix 13042 }

cmIoExpanderIO7NOTIFY NOTIFICATION-TYPE
OBJECTS { ioExpanderIO7, ioExpanderName, productFriendlyName, alarmTripType, alarmTrigger, alarmInstance }
STATUS current
DESCRIPTION "Climate Relay IO7 Sensor Trap"
::= { cmTrapPrefix 13043 }

cmIoExpanderIO8NOTIFY NOTIFICATION-TYPE
OBJECTS { ioExpanderIO8, ioExpanderName, productFriendlyName, alarmTripType, alarmTrigger, alarmInstance }
STATUS current
DESCRIPTION "Climate Relay IO8 Sensor Trap"
::= { cmTrapPrefix 13044 }

cmIoExpanderIO9NOTIFY NOTIFICATION-TYPE
OBJECTS { ioExpanderIO9, ioExpanderName, productFriendlyName, alarmTripType, alarmTrigger, alarmInstance }
STATUS current
DESCRIPTION "Climate Relay IO9 Sensor Trap"
::= { cmTrapPrefix 13045 }

cmIoExpanderIO10NOTIFY NOTIFICATION-TYPE
OBJECTS { ioExpanderIO10, ioExpanderName, productFriendlyName, alarmTripType, alarmTrigger, alarmInstance }
STATUS current
DESCRIPTION "Climate Relay IO10 Sensor Trap"
::= { cmTrapPrefix 13046 }

cmIoExpanderIO11NOTIFY NOTIFICATION-TYPE
OBJECTS { ioExpanderIO11, ioExpanderName, productFriendlyName, alarmTripType, alarmTrigger, alarmInstance }
STATUS current
DESCRIPTION "Climate Relay IO11 Sensor Trap"
::= { cmTrapPrefix 13047 }

cmIoExpanderIO12NOTIFY NOTIFICATION-TYPE
OBJECTS { ioExpanderIO12, ioExpanderName, productFriendlyName, alarmTripType, alarmTrigger, alarmInstance }
STATUS current
DESCRIPTION "Climate Relay IO12 Sensor Trap"
::= { cmTrapPrefix 13048 }

cmIoExpanderIO13NOTIFY NOTIFICATION-TYPE
OBJECTS { ioExpanderIO13, ioExpanderName, productFriendlyName, alarmTripType, alarmTrigger, alarmInstance }
STATUS current
DESCRIPTION "Climate Relay IO13 Sensor Trap"
::= { cmTrapPrefix 13049 }

cmIoExpanderIO14NOTIFY NOTIFICATION-TYPE
OBJECTS { ioExpanderIO14, ioExpanderName, productFriendlyName, alarmTripType, alarmTrigger, alarmInstance }
STATUS current
DESCRIPTION "Climate Relay IO14 Sensor Trap"
::= { cmTrapPrefix 13050 }

cmIoExpanderIO15NOTIFY NOTIFICATION-TYPE
OBJECTS { ioExpanderIO15, ioExpanderName, productFriendlyName, alarmTripType, alarmTrigger, alarmInstance }
STATUS current
DESCRIPTION "Climate Relay IO15 Sensor Trap"
::= { cmTrapPrefix 13051 }

cmIoExpanderIO16NOTIFY NOTIFICATION-TYPE
OBJECTS { ioExpanderIO16, ioExpanderName, productFriendlyName, alarmTripType, alarmTrigger, alarmInstance }
STATUS current
DESCRIPTION "Climate Relay IO16 Sensor Trap"
::= { cmTrapPrefix 13052 }

cmIoExpanderIO17NOTIFY NOTIFICATION-TYPE
OBJECTS { ioExpanderIO17, ioExpanderName, productFriendlyName, alarmTripType, alarmTrigger, alarmInstance }
STATUS current
DESCRIPTION "Climate Relay IO17 Sensor Trap"
::= { cmTrapPrefix 13053 }

cmIoExpanderIO18NOTIFY NOTIFICATION-TYPE
OBJECTS { ioExpanderIO18, ioExpanderName, productFriendlyName, alarmTripType, alarmTrigger, alarmInstance }
STATUS current
DESCRIPTION "Climate Relay IO18 Sensor Trap"
::= { cmTrapPrefix 13054 }

cmIoExpanderIO19NOTIFY NOTIFICATION-TYPE
OBJECTS { ioExpanderIO19, ioExpanderName, productFriendlyName, alarmTripType, alarmTrigger, alarmInstance }
STATUS current
DESCRIPTION "Climate Relay IO19 Sensor Trap"
::= { cmTrapPrefix 13055 }

cmIoExpanderIO20NOTIFY NOTIFICATION-TYPE
OBJECTS { ioExpanderIO20, ioExpanderName, productFriendlyName, alarmTripType, alarmTrigger, alarmInstance }
STATUS current
DESCRIPTION "Climate Relay IO20 Sensor Trap"
::= { cmTrapPrefix 13056 }

cmIoExpanderIO21NOTIFY NOTIFICATION-TYPE
OBJECTS { ioExpanderIO21, ioExpanderName, productFriendlyName, alarmTripType, alarmTrigger, alarmInstance }
STATUS current
DESCRIPTION "Climate Relay IO21 Sensor Trap"
::= { cmTrapPrefix 13057 }

cmIoExpanderIO22NOTIFY NOTIFICATION-TYPE
OBJECTS { ioExpanderIO22, ioExpanderName, productFriendlyName, alarmTripType, alarmTrigger, alarmInstance }
STATUS current
DESCRIPTION "Climate Relay IO22 Sensor Trap"
::= { cmTrapPrefix 13058 }

cmIoExpanderIO23NOTIFY NOTIFICATION-TYPE
OBJECTS { ioExpanderIO23, ioExpanderName, productFriendlyName, alarmTripType, alarmTrigger, alarmInstance }
STATUS current
DESCRIPTION "Climate Relay IO23 Sensor Trap"
::= { cmTrapPrefix 13059 }

cmIoExpanderIO24NOTIFY NOTIFICATION-TYPE
OBJECTS { ioExpanderIO24, ioExpanderName, productFriendlyName, alarmTripType, alarmTrigger, alarmInstance }
STATUS current
DESCRIPTION "Climate Relay IO24 Sensor Trap"
::= { cmTrapPrefix 13060 }

cmIoExpanderIO25NOTIFY NOTIFICATION-TYPE
OBJECTS { ioExpanderIO25, ioExpanderName, productFriendlyName, alarmTripType, alarmTrigger, alarmInstance }
STATUS current
DESCRIPTION "Climate Relay IO25 Sensor Trap"
::= { cmTrapPrefix 13061 }

cmIoExpanderIO26NOTIFY NOTIFICATION-TYPE
OBJECTS { ioExpanderIO26, ioExpanderName, productFriendlyName, alarmTripType, alarmTrigger, alarmInstance }
STATUS current
DESCRIPTION "Climate Relay IO26 Sensor Trap"
::= { cmTrapPrefix 13062 }

cmIoExpanderIO27NOTIFY NOTIFICATION-TYPE
OBJECTS { ioExpanderIO27, ioExpanderName, productFriendlyName, alarmTripType, alarmTrigger, alarmInstance }
STATUS current
DESCRIPTION "Climate Relay IO27 Sensor Trap"
::= { cmTrapPrefix 13063 }

cmIoExpanderIO28NOTIFY NOTIFICATION-TYPE
OBJECTS { ioExpanderIO28, ioExpanderName, productFriendlyName, alarmTripType, alarmTrigger, alarmInstance }
STATUS current
DESCRIPTION "Climate Relay IO28 Sensor Trap"
::= { cmTrapPrefix 13064 }

cmIoExpanderIO29NOTIFY NOTIFICATION-TYPE
OBJECTS { ioExpanderIO29, ioExpanderName, productFriendlyName, alarmTripType, alarmTrigger, alarmInstance }
STATUS current
DESCRIPTION "Climate Relay IO29 Sensor Trap"
::= { cmTrapPrefix 13065 }

cmIoExpanderIO30NOTIFY NOTIFICATION-TYPE
OBJECTS { ioExpanderIO30, ioExpanderName, productFriendlyName, alarmTripType, alarmTrigger, alarmInstance }
STATUS current
DESCRIPTION "Climate Relay IO30 Sensor Trap"
::= { cmTrapPrefix 13066 }

cmIoExpanderIO31NOTIFY NOTIFICATION-TYPE
OBJECTS { ioExpanderIO31, ioExpanderName, productFriendlyName, alarmTripType, alarmTrigger, alarmInstance }
STATUS current
DESCRIPTION "Climate Relay IO31 Sensor Trap"
::= { cmTrapPrefix 13067 }

cmIoExpanderIO32NOTIFY NOTIFICATION-TYPE
OBJECTS { ioExpanderIO32, ioExpanderName, productFriendlyName, alarmTripType, alarmTrigger, alarmInstance }
STATUS current
DESCRIPTION "Climate Relay IO32 Sensor Trap"
::= { cmTrapPrefix 13068 }

cmT3hdSensorIntTempCNOTIFY NOTIFICATION-TYPE
OBJECTS { t3hdSensorIntTempC, t3hdSensorName, productFriendlyName, alarmTripType, temperaturePrecision, alarmTrigger, alarmInstance }
STATUS current
DESCRIPTION "T3HD - Internal Temperature C Trap"
::= { cmTrapPrefix 13106 }

cmT3hdSensorIntTempFNOTIFY NOTIFICATION-TYPE
OBJECTS { t3hdSensorIntTempF, t3hdSensorName, productFriendlyName, alarmTripType, temperaturePrecision, alarmTrigger, alarmInstance }
STATUS current
DESCRIPTION "T3HD - Internal Temperature F Trap"
::= { cmTrapPrefix 13107 }

cmT3hdSensorIntHumidityNOTIFY NOTIFICATION-TYPE
OBJECTS { t3hdSensorIntHumidity, t3hdSensorName, productFriendlyName, alarmTripType, alarmTrigger, alarmInstance }
STATUS current
DESCRIPTION "T3HD - Internal Humidity Trap"
::= { cmTrapPrefix 13108 }

cmT3hdSensorIntDewPointCNOTIFY NOTIFICATION-TYPE
OBJECTS { t3hdSensorIntDewPointC, t3hdSensorName, productFriendlyName, alarmTripType, temperaturePrecision, alarmTrigger, alarmInstance }
STATUS current
DESCRIPTION "T3HD - Internal Dew Point C Trap"
::= { cmTrapPrefix 13109 }

cmT3hdSensorIntDewPointFNOTIFY NOTIFICATION-TYPE
OBJECTS { t3hdSensorIntDewPointF, t3hdSensorName, productFriendlyName, alarmTripType, temperaturePrecision, alarmTrigger, alarmInstance }
STATUS current
DESCRIPTION "T3HD - Internal Dew Point F Trap"
::= { cmTrapPrefix 13110 }

cmT3hdSensorExt1TempCNOTIFY NOTIFICATION-TYPE
OBJECTS { t3hdSensorExt1TempC, t3hdSensorName, productFriendlyName, alarmTripType, temperaturePrecision, alarmTrigger, alarmInstance }
STATUS current
DESCRIPTION "T3HD - External 1 Temperature C Trap"
::= { cmTrapPrefix 13113 }

cmT3hdSensorExt1TempFNOTIFY NOTIFICATION-TYPE
OBJECTS { t3hdSensorExt1TempF, t3hdSensorName, productFriendlyName, alarmTripType, temperaturePrecision, alarmTrigger, alarmInstance }
STATUS current
DESCRIPTION "T3HD - External 1 Temperature F Trap"
::= { cmTrapPrefix 13114 }

cmT3hdSensorExt2TempCNOTIFY NOTIFICATION-TYPE
OBJECTS { t3hdSensorExt2TempC, t3hdSensorName, productFriendlyName, alarmTripType, temperaturePrecision, alarmTrigger, alarmInstance }
STATUS current
DESCRIPTION "T3HD - External 2 Temperature C Trap"
::= { cmTrapPrefix 13117 }

cmT3hdSensorExt2TempFNOTIFY NOTIFICATION-TYPE
OBJECTS { t3hdSensorExt2TempF, t3hdSensorName, productFriendlyName, alarmTripType, temperaturePrecision, alarmTrigger, alarmInstance }
STATUS current
DESCRIPTION "T3HD - External 2 Temperature F Trap"
::= { cmTrapPrefix 13118 }

cmThdSensorTempCNOTIFY NOTIFICATION-TYPE
OBJECTS { thdSensorTempC, thdSensorName, productFriendlyName, alarmTripType, temperaturePrecision, alarmTrigger, alarmInstance }
STATUS current
DESCRIPTION "THD - Temperature C Trap"
::= { cmTrapPrefix 13205 }

cmThdSensorTempFNOTIFY NOTIFICATION-TYPE
OBJECTS { thdSensorTempF, thdSensorName, productFriendlyName, alarmTripType, temperaturePrecision, alarmTrigger, alarmInstance }
STATUS current
DESCRIPTION "THD - Temperature F Trap"
::= { cmTrapPrefix 13206 }

cmThdSensorHumidityNOTIFY NOTIFICATION-TYPE
OBJECTS { thdSensorHumidity, thdSensorName, productFriendlyName, alarmTripType, alarmTrigger, alarmInstance }
STATUS current
DESCRIPTION "THD - Humidity Trap"
::= { cmTrapPrefix 13207 }

cmThdSensorDewPointCNOTIFY NOTIFICATION-TYPE
OBJECTS { thdSensorDewPointC, thdSensorName, productFriendlyName, alarmTripType, temperaturePrecision, alarmTrigger, alarmInstance }
STATUS current
DESCRIPTION "THD - Dew Point C Trap"
::= { cmTrapPrefix 13208 }

cmThdSensorDewPointFNOTIFY NOTIFICATION-TYPE
OBJECTS { thdSensorDewPointF, thdSensorName, productFriendlyName, alarmTripType, temperaturePrecision, alarmTrigger, alarmInstance }
STATUS current
DESCRIPTION "THD - Dew Point F Trap"
::= { cmTrapPrefix 13209 }

cmPos60VdcSensorVoltageNOTIFY NOTIFICATION-TYPE
OBJECTS { pos60VdcSensorVoltage, pos60VdcSensorName, productFriendlyName, alarmTripType, alarmTrigger, alarmInstance }
STATUS current
DESCRIPTION "60Vdc Sensor Trap"
::= { cmTrapPrefix 13305 }

cmCtrl2CirTotkWattHrsTotNOTIFY NOTIFICATION-TYPE
OBJECTS { ctrl2CirTotkWattHrsTot, ctrl2CirTotName, productFriendlyName, alarmTripType, alarmTrigger, alarmInstance }
STATUS current
DESCRIPTION "Kilo Watt Hours Total Trap"
::= { cmTrapPrefix 13405 }

cmCtrl2CirTotVoltsTotNOTIFY NOTIFICATION-TYPE
OBJECTS { ctrl2CirTotVoltsTot, ctrl2CirTotName, productFriendlyName, alarmTripType, alarmTrigger, alarmInstance }
STATUS current
DESCRIPTION "Volts A Trap"
::= { cmTrapPrefix 13406 }

cmCtrl2CirTotVoltPeakTotNOTIFY NOTIFICATION-TYPE
OBJECTS { ctrl2CirTotVoltPeakTot, ctrl2CirTotName, productFriendlyName, alarmTripType, alarmTrigger, alarmInstance }
STATUS current
DESCRIPTION "Volts Peak Total Trap"
::= { cmTrapPrefix 13407 }

cmCtrl2CirTotDeciAmpsTotNOTIFY NOTIFICATION-TYPE
OBJECTS { ctrl2CirTotDeciAmpsTot, ctrl2CirTotName, productFriendlyName, alarmTripType, alarmTrigger, alarmInstance }
STATUS current
DESCRIPTION "Deciamps Total Trap"
::= { cmTrapPrefix 13408 }

cmCtrl2CirTotDeciAmpsPeakTotNOTIFY NOTIFICATION-TYPE
OBJECTS { ctrl2CirTotDeciAmpsPeakTot, ctrl2CirTotName, productFriendlyName, alarmTripType, alarmTrigger, alarmInstance }
STATUS current
DESCRIPTION "Deciamps Peak Total Trap"
::= { cmTrapPrefix 13409 }

cmCtrl2CirTotRealPowerTotNOTIFY NOTIFICATION-TYPE
OBJECTS { ctrl2CirTotRealPowerTot, ctrl2CirTotName, productFriendlyName, alarmTripType, alarmTrigger, alarmInstance }
STATUS current
DESCRIPTION "Real Power Total Trap"
::= { cmTrapPrefix 13410 }

cmCtrl2CirTotApparentPowerTotNOTIFY NOTIFICATION-TYPE
OBJECTS { ctrl2CirTotApparentPowerTot, ctrl2CirTotName, productFriendlyName, alarmTripType, alarmTrigger, alarmInstance }
STATUS current
DESCRIPTION "Apparent Power Total Trap"
::= { cmTrapPrefix 13411 }

cmCtrl2CirTotPowerFactorTotNOTIFY NOTIFICATION-TYPE
OBJECTS { ctrl2CirTotPowerFactorTot, ctrl2CirTotName, productFriendlyName, alarmTripType, alarmTrigger, alarmInstance }
STATUS current
DESCRIPTION "Power Factor Total Trap"
::= { cmTrapPrefix 13412 }

cmCtrl2CirTotkWattHrsANOTIFY NOTIFICATION-TYPE
OBJECTS { ctrl2CirTotkWattHrsA, ctrl2CirTotName, productFriendlyName, alarmTripType, alarmTrigger, alarmInstance }
STATUS current
DESCRIPTION "Kilo Watt Hours A Trap"
::= { cmTrapPrefix 13413 }

cmCtrl2CirTotVoltsANOTIFY NOTIFICATION-TYPE
OBJECTS { ctrl2CirTotVoltsA, ctrl2CirTotName, productFriendlyName, alarmTripType, alarmTrigger, alarmInstance }
STATUS current
DESCRIPTION "Volts A Trap"
::= { cmTrapPrefix 13414 }

cmCtrl2CirTotVoltPeakANOTIFY NOTIFICATION-TYPE
OBJECTS { ctrl2CirTotVoltPeakA, ctrl2CirTotName, productFriendlyName, alarmTripType, alarmTrigger, alarmInstance }
STATUS current
DESCRIPTION "Volts Peak A Trap"
::= { cmTrapPrefix 13415 }

cmCtrl2CirTotDeciAmpsANOTIFY NOTIFICATION-TYPE
OBJECTS { ctrl2CirTotDeciAmpsA, ctrl2CirTotName, productFriendlyName, alarmTripType, alarmTrigger, alarmInstance }
STATUS current
DESCRIPTION "Deciamps A Trap"
::= { cmTrapPrefix 13416 }

cmCtrl2CirTotDeciAmpsPeakANOTIFY NOTIFICATION-TYPE
OBJECTS { ctrl2CirTotDeciAmpsPeakA, ctrl2CirTotName, productFriendlyName, alarmTripType, alarmTrigger, alarmInstance }
STATUS current
DESCRIPTION "Deciamps Peak A Trap"
::= { cmTrapPrefix 13417 }

cmCtrl2CirTotRealPowerANOTIFY NOTIFICATION-TYPE
OBJECTS { ctrl2CirTotRealPowerA, ctrl2CirTotName, productFriendlyName, alarmTripType, alarmTrigger, alarmInstance }
STATUS current
DESCRIPTION "Real Power A Trap"
::= { cmTrapPrefix 13418 }

cmCtrl2CirTotApparentPowerANOTIFY NOTIFICATION-TYPE
OBJECTS { ctrl2CirTotApparentPowerA, ctrl2CirTotName, productFriendlyName, alarmTripType, alarmTrigger, alarmInstance }
STATUS current
DESCRIPTION "Apparent Power A Trap"
::= { cmTrapPrefix 13419 }

cmCtrl2CirTotPowerFactorANOTIFY NOTIFICATION-TYPE
OBJECTS { ctrl2CirTotPowerFactorA, ctrl2CirTotName, productFriendlyName, alarmTripType, alarmTrigger, alarmInstance }
STATUS current
DESCRIPTION "Power Factor A Trap"
::= { cmTrapPrefix 13420 }

cmCtrl2CirTotkWattHrsBNOTIFY NOTIFICATION-TYPE
OBJECTS { ctrl2CirTotkWattHrsB, ctrl2CirTotName, productFriendlyName, alarmTripType, alarmTrigger, alarmInstance }
STATUS current
DESCRIPTION "Kilo Watt Hours B Trap"
::= { cmTrapPrefix 13421 }

cmCtrl2CirTotVoltsBNOTIFY NOTIFICATION-TYPE
OBJECTS { ctrl2CirTotVoltsB, ctrl2CirTotName, productFriendlyName, alarmTripType, alarmTrigger, alarmInstance }
STATUS current
DESCRIPTION "Volts B Trap"
::= { cmTrapPrefix 13422 }

cmCtrl2CirTotVoltPeakBNOTIFY NOTIFICATION-TYPE
OBJECTS { ctrl2CirTotVoltPeakB, ctrl2CirTotName, productFriendlyName, alarmTripType, alarmTrigger, alarmInstance }
STATUS current
DESCRIPTION "Volts Peak B Trap"
::= { cmTrapPrefix 13423 }

cmCtrl2CirTotDeciAmpsBNOTIFY NOTIFICATION-TYPE
OBJECTS { ctrl2CirTotDeciAmpsB, ctrl2CirTotName, productFriendlyName, alarmTripType, alarmTrigger, alarmInstance }
STATUS current
DESCRIPTION "Deciamps B Trap"
::= { cmTrapPrefix 13424 }

cmCtrl2CirTotDeciAmpsPeakBNOTIFY NOTIFICATION-TYPE
OBJECTS { ctrl2CirTotDeciAmpsPeakB, ctrl2CirTotName, productFriendlyName, alarmTripType, alarmTrigger, alarmInstance }
STATUS current
DESCRIPTION "Deciamps Peak B Trap"
::= { cmTrapPrefix 13425 }

cmCtrl2CirTotRealPowerBNOTIFY NOTIFICATION-TYPE
OBJECTS { ctrl2CirTotRealPowerB, ctrl2CirTotName, productFriendlyName, alarmTripType, alarmTrigger, alarmInstance }
STATUS current
DESCRIPTION "Real Power B Trap"
::= { cmTrapPrefix 13426 }

cmCtrl2CirTotApparentPowerBNOTIFY NOTIFICATION-TYPE
OBJECTS { ctrl2CirTotApparentPowerB, ctrl2CirTotName, productFriendlyName, alarmTripType, alarmTrigger, alarmInstance }
STATUS current
DESCRIPTION "Apparent Power B Trap"
::= { cmTrapPrefix 13427 }

cmCtrl2CirTotPowerFactorBNOTIFY NOTIFICATION-TYPE
OBJECTS { ctrl2CirTotPowerFactorB, ctrl2CirTotName, productFriendlyName, alarmTripType, alarmTrigger, alarmInstance }
STATUS current
DESCRIPTION "Power Factor B Trap"
::= { cmTrapPrefix 13428 }

cmSc10ControlModeNOTIFY NOTIFICATION-TYPE
OBJECTS { sc10ControlMode, sc10Name, productFriendlyName, alarmTripType, alarmTrigger, alarmInstance }
STATUS current
DESCRIPTION "SC10 Control Mode Sensor Trap"
::= { cmTrapPrefix 13505 }

cmSc10SetpointCNOTIFY NOTIFICATION-TYPE
OBJECTS { sc10SetpointC, sc10Name, productFriendlyName, alarmTripType, alarmTrigger, alarmInstance }
STATUS current
DESCRIPTION "SC10 Temp Set Point Sensor Trap"
::= { cmTrapPrefix 13506 }

cmSc10SetpointFNOTIFY NOTIFICATION-TYPE
OBJECTS { sc10SetpointF, sc10Name, productFriendlyName, alarmTripType, alarmTrigger, alarmInstance }
STATUS current
DESCRIPTION "SC10 Temp Set Point Sensor Trap"
::= { cmTrapPrefix 13507 }

cmSc10TempCNOTIFY NOTIFICATION-TYPE
OBJECTS { sc10TempC, sc10Name, productFriendlyName, alarmTripType, temperaturePrecision, alarmTrigger, alarmInstance }
STATUS current
DESCRIPTION "SC10 Internal Temp Sensor Trap"
::= { cmTrapPrefix 13508 }

cmSc10TempFNOTIFY NOTIFICATION-TYPE
OBJECTS { sc10TempF, sc10Name, productFriendlyName, alarmTripType, temperaturePrecision, alarmTrigger, alarmInstance }
STATUS current
DESCRIPTION "SC10 Internal Temp Sensor Trap"
::= { cmTrapPrefix 13509 }

cmSc10CapacityNOTIFY NOTIFICATION-TYPE
OBJECTS { sc10Capacity, sc10Name, productFriendlyName, alarmTripType, alarmTrigger, alarmInstance }
STATUS current
DESCRIPTION "SC10 Fan Speed Sensor Trap"
::= { cmTrapPrefix 13510 }

cmClimateTempCCLEAR NOTIFICATION-TYPE
OBJECTS { climateTempC, climateName, productFriendlyName, alarmTripType, temperaturePrecision, alarmTrigger, alarmInstance }
STATUS current
DESCRIPTION "Climate Temperature Sensor Clear Trap"
::= { cmTrapPrefix 20205 }

cmClimateTempFCLEAR NOTIFICATION-TYPE
OBJECTS { climateTempF, climateName, productFriendlyName, alarmTripType, temperaturePrecision, alarmTrigger, alarmInstance }
STATUS current
DESCRIPTION "Climate Temperature Sensor Clear Trap"
::= { cmTrapPrefix 20206 }

cmClimateHumidityCLEAR NOTIFICATION-TYPE
OBJECTS { climateHumidity, climateName, productFriendlyName, alarmTripType, alarmTrigger, alarmInstance }
STATUS current
DESCRIPTION "Climate Humidity Sensor Clear Trap"
::= { cmTrapPrefix 20207 }

cmClimateLightCLEAR NOTIFICATION-TYPE
OBJECTS { climateLight, climateName, productFriendlyName, alarmTripType, alarmTrigger, alarmInstance }
STATUS current
DESCRIPTION "Climate Light Sensor Clear Trap"
::= { cmTrapPrefix 20208 }

cmClimateAirflowCLEAR NOTIFICATION-TYPE
OBJECTS { climateAirflow, climateName, productFriendlyName, alarmTripType, alarmTrigger, alarmInstance }
STATUS current
DESCRIPTION "Climate Air Flow Sensor Clear Trap"
::= { cmTrapPrefix 20209 }

cmClimateSoundCLEAR NOTIFICATION-TYPE
OBJECTS { climateSound, climateName, productFriendlyName, alarmTripType, alarmTrigger, alarmInstance }
STATUS current
DESCRIPTION "Climate Sound Sensor Clear Trap"
::= { cmTrapPrefix 20210 }

cmClimateIO1CLEAR NOTIFICATION-TYPE
OBJECTS { climateIO1, climateName, productFriendlyName, alarmTripType, alarmTrigger, alarmInstance }
STATUS current
DESCRIPTION "Climate IO1 Sensor Clear Trap"
::= { cmTrapPrefix 20211 }

cmClimateIO2CLEAR NOTIFICATION-TYPE
OBJECTS { climateIO2, climateName, productFriendlyName, alarmTripType, alarmTrigger, alarmInstance }
STATUS current
DESCRIPTION "Climate IO2 Sensor Clear Trap"
::= { cmTrapPrefix 20212 }

cmClimateIO3CLEAR NOTIFICATION-TYPE
OBJECTS { climateIO3, climateName, productFriendlyName, alarmTripType, alarmTrigger, alarmInstance }
STATUS current
DESCRIPTION "Climate IO3 Sensor Clear Trap"
::= { cmTrapPrefix 20213 }

cmClimateDewPointCCLEAR NOTIFICATION-TYPE
OBJECTS { climateDewPointC, climateName, productFriendlyName, alarmTripType, temperaturePrecision, alarmTrigger, alarmInstance }
STATUS current
DESCRIPTION "Climate Dew Point Sensor Clear Trap"
::= { cmTrapPrefix 20214 }

cmClimateDewPointFCLEAR NOTIFICATION-TYPE
OBJECTS { climateDewPointF, climateName, productFriendlyName, alarmTripType, temperaturePrecision, alarmTrigger, alarmInstance }
STATUS current
DESCRIPTION "Climate Dew Point Sensor Clear Trap"
::= { cmTrapPrefix 20215 }

cmPowMonkWattHrsCLEAR NOTIFICATION-TYPE
OBJECTS { powMonkWattHrs, powMonName, productFriendlyName, alarmTripType, alarmTrigger, alarmInstance }
STATUS current
DESCRIPTION "Kilo Watt Hours Clear Trap"
::= { cmTrapPrefix 20305 }

cmPowMonVoltsCLEAR NOTIFICATION-TYPE
OBJECTS { powMonVolts, powMonName, productFriendlyName, alarmTripType, alarmTrigger, alarmInstance }
STATUS current
DESCRIPTION "Volts Clear Trap"
::= { cmTrapPrefix 20306 }

cmPowMonVoltMaxCLEAR NOTIFICATION-TYPE
OBJECTS { powMonVoltMax, powMonName, productFriendlyName, alarmTripType, alarmTrigger, alarmInstance }
STATUS current
DESCRIPTION "Volts Max Clear Trap"
::= { cmTrapPrefix 20307 }

cmPowMonVoltMinCLEAR NOTIFICATION-TYPE
OBJECTS { powMonVoltMin, powMonName, productFriendlyName, alarmTripType, alarmTrigger, alarmInstance }
STATUS current
DESCRIPTION "Volts Min Clear Trap"
::= { cmTrapPrefix 20308 }

cmPowMonVoltPeakCLEAR NOTIFICATION-TYPE
OBJECTS { powMonVoltPeak, powMonName, productFriendlyName, alarmTripType, alarmTrigger, alarmInstance }
STATUS current
DESCRIPTION "Volt Peak Clear Trap"
::= { cmTrapPrefix 20309 }

cmPowMonDeciAmpsCLEAR NOTIFICATION-TYPE
OBJECTS { powMonDeciAmps, powMonName, productFriendlyName, alarmTripType, alarmTrigger, alarmInstance }
STATUS current
DESCRIPTION "DeciAmps Clear Trap"
::= { cmTrapPrefix 20310 }

cmPowMonRealPowerCLEAR NOTIFICATION-TYPE
OBJECTS { powMonRealPower, powMonName, productFriendlyName, alarmTripType, alarmTrigger, alarmInstance }
STATUS current
DESCRIPTION "Real Power Clear Trap"
::= { cmTrapPrefix 20311 }

cmPowMonApparentPowerCLEAR NOTIFICATION-TYPE
OBJECTS { powMonApparentPower, powMonName, productFriendlyName, alarmTripType, alarmTrigger, alarmInstance }
STATUS current
DESCRIPTION "Apparent Power Clear Trap"
::= { cmTrapPrefix 20312 }

cmPowMonPowerFactorCLEAR NOTIFICATION-TYPE
OBJECTS { powMonPowerFactor, powMonName, productFriendlyName, alarmTripType, alarmTrigger, alarmInstance }
STATUS current
DESCRIPTION "Power Factor Clear Trap"
::= { cmTrapPrefix 20313 }

cmPowMonOutlet1CLEAR NOTIFICATION-TYPE
OBJECTS { powMonOutlet1, powMonName, productFriendlyName, alarmTripType, alarmTrigger, alarmInstance }
STATUS current
DESCRIPTION "Outlet1 Clear Trap"
::= { cmTrapPrefix 20314 }

cmPowMonOutlet2CLEAR NOTIFICATION-TYPE
OBJECTS { powMonOutlet2, powMonName, productFriendlyName, alarmTripType, alarmTrigger, alarmInstance }
STATUS current
DESCRIPTION "Outlet2 Clear Trap"
::= { cmTrapPrefix 20315 }

cmPowMonOutlet1StatusTimeCLEAR NOTIFICATION-TYPE
OBJECTS { powMonOutlet1StatusTime, powMonName, productFriendlyName, alarmTripType, alarmTrigger, alarmInstance }
STATUS current
DESCRIPTION "Outlet1StatusTime Clear Trap"
::= { cmTrapPrefix 20316 }

cmPowMonOutlet2StatusTimeCLEAR NOTIFICATION-TYPE
OBJECTS { powMonOutlet2StatusTime, powMonName, productFriendlyName, alarmTripType, alarmTrigger, alarmInstance }
STATUS current
DESCRIPTION "Outlet2StatusTime Clear Trap"
::= { cmTrapPrefix 20317 }

cmTempSensorTempCCLEAR NOTIFICATION-TYPE
OBJECTS { tempSensorTempC, tempSensorName, productFriendlyName, alarmTripType, temperaturePrecision, alarmTrigger, alarmInstance }
STATUS current
DESCRIPTION "Remote Temp Sensor - Temperature Clear Trap"
::= { cmTrapPrefix 20405 }

cmTempSensorTempFCLEAR NOTIFICATION-TYPE
OBJECTS { tempSensorTempF, tempSensorName, productFriendlyName, alarmTripType, temperaturePrecision, alarmTrigger, alarmInstance }
STATUS current
DESCRIPTION "Remote Temp Sensor - Temperature Clear Trap"
::= { cmTrapPrefix 20406 }

cmAirFlowSensorTempCCLEAR NOTIFICATION-TYPE
OBJECTS { airFlowSensorTempC, airFlowSensorName, productFriendlyName, alarmTripType, temperaturePrecision, alarmTrigger, alarmInstance }
STATUS current
DESCRIPTION "Remote Air Flow Sensor - Temperature Clear Trap"
::= { cmTrapPrefix 20505 }

cmAirFlowSensorTempFCLEAR NOTIFICATION-TYPE
OBJECTS { airFlowSensorTempF, airFlowSensorName, productFriendlyName, alarmTripType, temperaturePrecision, alarmTrigger, alarmInstance }
STATUS current
DESCRIPTION "Remote Air Flow Sensor - Temperature Clear Trap"
::= { cmTrapPrefix 20506 }

cmAirFlowSensorFlowCLEAR NOTIFICATION-TYPE
OBJECTS { airFlowSensorFlow, airFlowSensorName, productFriendlyName, alarmTripType, alarmTrigger, alarmInstance }
STATUS current
DESCRIPTION "Remote Air Flow Sensor - Air Flow Clear Trap"
::= { cmTrapPrefix 20507 }

cmAirFlowSensorHumidityCLEAR NOTIFICATION-TYPE
OBJECTS { airFlowSensorHumidity, airFlowSensorName, productFriendlyName, alarmTripType, alarmTrigger, alarmInstance }
STATUS current
DESCRIPTION "Remote Air Flow Sensor - Humidity Clear Trap"
::= { cmTrapPrefix 20508 }

cmAirFlowSensorDewPointCCLEAR NOTIFICATION-TYPE
OBJECTS { airFlowSensorDewPointC, airFlowSensorName, productFriendlyName, alarmTripType, temperaturePrecision, alarmTrigger, alarmInstance }
STATUS current
DESCRIPTION "Remote Air Flow Sensor - Dew Point Clear Trap"
::= { cmTrapPrefix 20509 }

cmAirFlowSensorDewPointFCLEAR NOTIFICATION-TYPE
OBJECTS { airFlowSensorDewPointF, airFlowSensorName, productFriendlyName, alarmTripType, temperaturePrecision, alarmTrigger, alarmInstance }
STATUS current
DESCRIPTION "Remote Air Flow Sensor - Dew Point Clear Trap"
::= { cmTrapPrefix 20510 }

cmCtrl3ChDELTADeciAmpsACLEAR NOTIFICATION-TYPE
OBJECTS { ctrl3ChDELTADeciAmpsA, ctrl3ChDELTAName, productFriendlyName, alarmTripType, alarmTrigger, alarmInstance }
STATUS current
DESCRIPTION "Deciamps A Clear Trap"
::= { cmTrapPrefix 20606 }

cmCtrl3ChDELTADeciAmpsBCLEAR NOTIFICATION-TYPE
OBJECTS { ctrl3ChDELTADeciAmpsB, ctrl3ChDELTAName, productFriendlyName, alarmTripType, alarmTrigger, alarmInstance }
STATUS current
DESCRIPTION "Deciamps B Clear Trap"
::= { cmTrapPrefix 20607 }

cmCtrl3ChDELTADeciAmpsCCLEAR NOTIFICATION-TYPE
OBJECTS { ctrl3ChDELTADeciAmpsC, ctrl3ChDELTAName, productFriendlyName, alarmTripType, alarmTrigger, alarmInstance }
STATUS current
DESCRIPTION "Deciamps C Clear Trap"
::= { cmTrapPrefix 20608 }

cmCtrl3ChDELTAkWattHrsTotalCLEAR NOTIFICATION-TYPE
OBJECTS { ctrl3ChDELTAkWattHrsTotal, ctrl3ChDELTAName, productFriendlyName, alarmTripType, alarmTrigger, alarmInstance }
STATUS current
DESCRIPTION "Kilo Watt Hours Total Clear Trap"
::= { cmTrapPrefix 20609 }

cmCtrl3ChDELTARealPowerTotalCLEAR NOTIFICATION-TYPE
OBJECTS { ctrl3ChDELTARealPowerTotal, ctrl3ChDELTAName, productFriendlyName, alarmTripType, alarmTrigger, alarmInstance }
STATUS current
DESCRIPTION "Watts Total Clear Trap"
::= { cmTrapPrefix 20610 }

cmCtrl3ChDELTAkWattHrsABCLEAR NOTIFICATION-TYPE
OBJECTS { ctrl3ChDELTAkWattHrsAB, ctrl3ChDELTAName, productFriendlyName, alarmTripType, alarmTrigger, alarmInstance }
STATUS current
DESCRIPTION "Kilo Watt Hours A Clear Trap"
::= { cmTrapPrefix 20611 }

cmCtrl3ChDELTAVoltsABCLEAR NOTIFICATION-TYPE
OBJECTS { ctrl3ChDELTAVoltsAB, ctrl3ChDELTAName, productFriendlyName, alarmTripType, alarmTrigger, alarmInstance }
STATUS current
DESCRIPTION "Volts AB Clear Trap"
::= { cmTrapPrefix 20612 }

cmCtrl3ChDELTAVoltPeakABCLEAR NOTIFICATION-TYPE
OBJECTS { ctrl3ChDELTAVoltPeakAB, ctrl3ChDELTAName, productFriendlyName, alarmTripType, alarmTrigger, alarmInstance }
STATUS current
DESCRIPTION "Volts Peak AB Clear Trap"
::= { cmTrapPrefix 20613 }

cmCtrl3ChDELTARealPowerABCLEAR NOTIFICATION-TYPE
OBJECTS { ctrl3ChDELTARealPowerAB, ctrl3ChDELTAName, productFriendlyName, alarmTripType, alarmTrigger, alarmInstance }
STATUS current
DESCRIPTION "Real Power AB Clear Trap"
::= { cmTrapPrefix 20614 }

cmCtrl3ChDELTAApparentPowerABCLEAR NOTIFICATION-TYPE
OBJECTS { ctrl3ChDELTAApparentPowerAB, ctrl3ChDELTAName, productFriendlyName, alarmTripType, alarmTrigger, alarmInstance }
STATUS current
DESCRIPTION "VoltAmps AB Clear Trap"
::= { cmTrapPrefix 20615 }

cmCtrl3ChDELTAPowerFactorABCLEAR NOTIFICATION-TYPE
OBJECTS { ctrl3ChDELTAPowerFactorAB, ctrl3ChDELTAName, productFriendlyName, alarmTripType, alarmTrigger, alarmInstance }
STATUS current
DESCRIPTION "Power Factor AB Clear Trap"
::= { cmTrapPrefix 20616 }

cmCtrl3ChDELTAkWattHrsBCCLEAR NOTIFICATION-TYPE
OBJECTS { ctrl3ChDELTAkWattHrsBC, ctrl3ChDELTAName, productFriendlyName, alarmTripType, alarmTrigger, alarmInstance }
STATUS current
DESCRIPTION "Kilo Watt Hours BC Clear Trap"
::= { cmTrapPrefix 20617 }

cmCtrl3ChDELTAVoltsBCCLEAR NOTIFICATION-TYPE
OBJECTS { ctrl3ChDELTAVoltsBC, ctrl3ChDELTAName, productFriendlyName, alarmTripType, alarmTrigger, alarmInstance }
STATUS current
DESCRIPTION "Volts BC Clear Trap"
::= { cmTrapPrefix 20618 }

cmCtrl3ChDELTAVoltPeakBCCLEAR NOTIFICATION-TYPE
OBJECTS { ctrl3ChDELTAVoltPeakBC, ctrl3ChDELTAName, productFriendlyName, alarmTripType, alarmTrigger, alarmInstance }
STATUS current
DESCRIPTION "Volts Peak BC Clear Trap"
::= { cmTrapPrefix 20619 }

cmCtrl3ChDELTARealPowerBCCLEAR NOTIFICATION-TYPE
OBJECTS { ctrl3ChDELTARealPowerBC, ctrl3ChDELTAName, productFriendlyName, alarmTripType, alarmTrigger, alarmInstance }
STATUS current
DESCRIPTION "Real Power BC Clear Trap"
::= { cmTrapPrefix 20620 }

cmCtrl3ChDELTAApparentPowerBCCLEAR NOTIFICATION-TYPE
OBJECTS { ctrl3ChDELTAApparentPowerBC, ctrl3ChDELTAName, productFriendlyName, alarmTripType, alarmTrigger, alarmInstance }
STATUS current
DESCRIPTION "VoltAmps BC Clear Trap"
::= { cmTrapPrefix 20621 }

cmCtrl3ChDELTAPowerFactorBCCLEAR NOTIFICATION-TYPE
OBJECTS { ctrl3ChDELTAPowerFactorBC, ctrl3ChDELTAName, productFriendlyName, alarmTripType, alarmTrigger, alarmInstance }
STATUS current
DESCRIPTION "Power Factor BC Clear Trap"
::= { cmTrapPrefix 20622 }

cmCtrl3ChDELTAkWattHrsCACLEAR NOTIFICATION-TYPE
OBJECTS { ctrl3ChDELTAkWattHrsCA, ctrl3ChDELTAName, productFriendlyName, alarmTripType, alarmTrigger, alarmInstance }
STATUS current
DESCRIPTION "Kilo Watt Hours CA Clear Trap"
::= { cmTrapPrefix 20623 }

cmCtrl3ChDELTAVoltsCACLEAR NOTIFICATION-TYPE
OBJECTS { ctrl3ChDELTAVoltsCA, ctrl3ChDELTAName, productFriendlyName, alarmTripType, alarmTrigger, alarmInstance }
STATUS current
DESCRIPTION "Volts CA Clear Trap"
::= { cmTrapPrefix 20624 }

cmCtrl3ChDELTAVoltPeakCACLEAR NOTIFICATION-TYPE
OBJECTS { ctrl3ChDELTAVoltPeakCA, ctrl3ChDELTAName, productFriendlyName, alarmTripType, alarmTrigger, alarmInstance }
STATUS current
DESCRIPTION "Volts Peak CA Clear Trap"
::= { cmTrapPrefix 20625 }

cmCtrl3ChDELTARealPowerCACLEAR NOTIFICATION-TYPE
OBJECTS { ctrl3ChDELTARealPowerCA, ctrl3ChDELTAName, productFriendlyName, alarmTripType, alarmTrigger, alarmInstance }
STATUS current
DESCRIPTION "Real Power CA Clear Trap"
::= { cmTrapPrefix 20626 }

cmCtrl3ChDELTAApparentPowerCACLEAR NOTIFICATION-TYPE
OBJECTS { ctrl3ChDELTAApparentPowerCA, ctrl3ChDELTAName, productFriendlyName, alarmTripType, alarmTrigger, alarmInstance }
STATUS current
DESCRIPTION "VoltAmps CA Clear Trap"
::= { cmTrapPrefix 20627 }

cmCtrl3ChDELTAPowerFactorCACLEAR NOTIFICATION-TYPE
OBJECTS { ctrl3ChDELTAPowerFactorCA, ctrl3ChDELTAName, productFriendlyName, alarmTripType, alarmTrigger, alarmInstance }
STATUS current
DESCRIPTION "Power Factor CA Clear Trap"
::= { cmTrapPrefix 20628 }

cmDoorSensorStatusCLEAR NOTIFICATION-TYPE
OBJECTS { doorSensorStatus, doorSensorName, productFriendlyName, alarmTripType, alarmTrigger, alarmInstance }
STATUS current
DESCRIPTION "Door sensor Clear Trap"
::= { cmTrapPrefix 20705 }

cmWaterSensorDampnessCLEAR NOTIFICATION-TYPE
OBJECTS { waterSensorDampness, waterSensorName, productFriendlyName, alarmTripType, alarmTrigger, alarmInstance }
STATUS current
DESCRIPTION "Water sensor Clear Trap"
::= { cmTrapPrefix 20805 }

cmCurrentMonitorDeciAmpsCLEAR NOTIFICATION-TYPE
OBJECTS { currentMonitorDeciAmps, currentMonitorName, productFriendlyName, alarmTripType, alarmTrigger, alarmInstance }
STATUS current
DESCRIPTION "Current Monitor Amps Clear Trap"
::= { cmTrapPrefix 20905 }

cmMillivoltMonitorMVCLEAR NOTIFICATION-TYPE
OBJECTS { millivoltMonitorMV, millivoltMonitorName, productFriendlyName, alarmTripType, alarmTrigger, alarmInstance }
STATUS current
DESCRIPTION "Millivolt Monitor Clear Trap"
::= { cmTrapPrefix 21005 }

cmPow3ChkWattHrsACLEAR NOTIFICATION-TYPE
OBJECTS { pow3ChkWattHrsA, pow3ChName, productFriendlyName, alarmTripType, alarmTrigger, alarmInstance }
STATUS current
DESCRIPTION "Kilo Watt Hours A Clear Trap"
::= { cmTrapPrefix 21105 }

cmPow3ChVoltsACLEAR NOTIFICATION-TYPE
OBJECTS { pow3ChVoltsA, pow3ChName, productFriendlyName, alarmTripType, alarmTrigger, alarmInstance }
STATUS current
DESCRIPTION "Volts A Clear Trap"
::= { cmTrapPrefix 21106 }

cmPow3ChVoltMaxACLEAR NOTIFICATION-TYPE
OBJECTS { pow3ChVoltMaxA, pow3ChName, productFriendlyName, alarmTripType, alarmTrigger, alarmInstance }
STATUS current
DESCRIPTION "Volts Max A Clear Trap"
::= { cmTrapPrefix 21107 }

cmPow3ChVoltMinACLEAR NOTIFICATION-TYPE
OBJECTS { pow3ChVoltMinA, pow3ChName, productFriendlyName, alarmTripType, alarmTrigger, alarmInstance }
STATUS current
DESCRIPTION "Volts Min A Clear Trap"
::= { cmTrapPrefix 21108 }

cmPow3ChVoltPeakACLEAR NOTIFICATION-TYPE
OBJECTS { pow3ChVoltPeakA, pow3ChName, productFriendlyName, alarmTripType, alarmTrigger, alarmInstance }
STATUS current
DESCRIPTION "Volt Peak A Clear Trap"
::= { cmTrapPrefix 21109 }

cmPow3ChDeciAmpsACLEAR NOTIFICATION-TYPE
OBJECTS { pow3ChDeciAmpsA, pow3ChName, productFriendlyName, alarmTripType, alarmTrigger, alarmInstance }
STATUS current
DESCRIPTION "Deciamps A Clear Trap"
::= { cmTrapPrefix 21110 }

cmPow3ChRealPowerACLEAR NOTIFICATION-TYPE
OBJECTS { pow3ChRealPowerA, pow3ChName, productFriendlyName, alarmTripType, alarmTrigger, alarmInstance }
STATUS current
DESCRIPTION "Real Power A Clear Trap"
::= { cmTrapPrefix 21111 }

cmPow3ChApparentPowerACLEAR NOTIFICATION-TYPE
OBJECTS { pow3ChApparentPowerA, pow3ChName, productFriendlyName, alarmTripType, alarmTrigger, alarmInstance }
STATUS current
DESCRIPTION "Apparent Power A Clear Trap"
::= { cmTrapPrefix 21112 }

cmPow3ChPowerFactorACLEAR NOTIFICATION-TYPE
OBJECTS { pow3ChPowerFactorA, pow3ChName, productFriendlyName, alarmTripType, alarmTrigger, alarmInstance }
STATUS current
DESCRIPTION "Power Factor A Clear Trap"
::= { cmTrapPrefix 21113 }

cmPow3ChkWattHrsBCLEAR NOTIFICATION-TYPE
OBJECTS { pow3ChkWattHrsB, pow3ChName, productFriendlyName, alarmTripType, alarmTrigger, alarmInstance }
STATUS current
DESCRIPTION "Kilo Watt Hours B Clear Trap"
::= { cmTrapPrefix 21114 }

cmPow3ChVoltsBCLEAR NOTIFICATION-TYPE
OBJECTS { pow3ChVoltsB, pow3ChName, productFriendlyName, alarmTripType, alarmTrigger, alarmInstance }
STATUS current
DESCRIPTION "Volts B Clear Trap"
::= { cmTrapPrefix 21115 }

cmPow3ChVoltMaxBCLEAR NOTIFICATION-TYPE
OBJECTS { pow3ChVoltMaxB, pow3ChName, productFriendlyName, alarmTripType, alarmTrigger, alarmInstance }
STATUS current
DESCRIPTION "Volts Max B Clear Trap"
::= { cmTrapPrefix 21116 }

cmPow3ChVoltMinBCLEAR NOTIFICATION-TYPE
OBJECTS { pow3ChVoltMinB, pow3ChName, productFriendlyName, alarmTripType, alarmTrigger, alarmInstance }
STATUS current
DESCRIPTION "Volts Min B Clear Trap"
::= { cmTrapPrefix 21117 }

cmPow3ChVoltPeakBCLEAR NOTIFICATION-TYPE
OBJECTS { pow3ChVoltPeakB, pow3ChName, productFriendlyName, alarmTripType, alarmTrigger, alarmInstance }
STATUS current
DESCRIPTION "Volt Peak B Clear Trap"
::= { cmTrapPrefix 21118 }

cmPow3ChDeciAmpsBCLEAR NOTIFICATION-TYPE
OBJECTS { pow3ChDeciAmpsB, pow3ChName, productFriendlyName, alarmTripType, alarmTrigger, alarmInstance }
STATUS current
DESCRIPTION "Deciamps B Clear Trap"
::= { cmTrapPrefix 21119 }

cmPow3ChRealPowerBCLEAR NOTIFICATION-TYPE
OBJECTS { pow3ChRealPowerB, pow3ChName, productFriendlyName, alarmTripType, alarmTrigger, alarmInstance }
STATUS current
DESCRIPTION "Real Power B Clear Trap"
::= { cmTrapPrefix 21120 }

cmPow3ChApparentPowerBCLEAR NOTIFICATION-TYPE
OBJECTS { pow3ChApparentPowerB, pow3ChName, productFriendlyName, alarmTripType, alarmTrigger, alarmInstance }
STATUS current
DESCRIPTION "Apparent Power B Clear Trap"
::= { cmTrapPrefix 21121 }

cmPow3ChPowerFactorBCLEAR NOTIFICATION-TYPE
OBJECTS { pow3ChPowerFactorB, pow3ChName, productFriendlyName, alarmTripType, alarmTrigger, alarmInstance }
STATUS current
DESCRIPTION "Power Factor B Clear Trap"
::= { cmTrapPrefix 21122 }

cmPow3ChkWattHrsCCLEAR NOTIFICATION-TYPE
OBJECTS { pow3ChkWattHrsC, pow3ChName, productFriendlyName, alarmTripType, alarmTrigger, alarmInstance }
STATUS current
DESCRIPTION "Kilo Watt Hours C Clear Trap"
::= { cmTrapPrefix 21123 }

cmPow3ChVoltsCCLEAR NOTIFICATION-TYPE
OBJECTS { pow3ChVoltsC, pow3ChName, productFriendlyName, alarmTripType, alarmTrigger, alarmInstance }
STATUS current
DESCRIPTION "Volts C Clear Trap"
::= { cmTrapPrefix 21124 }

cmPow3ChVoltMaxCCLEAR NOTIFICATION-TYPE
OBJECTS { pow3ChVoltMaxC, pow3ChName, productFriendlyName, alarmTripType, alarmTrigger, alarmInstance }
STATUS current
DESCRIPTION "Volts Max C Clear Trap"
::= { cmTrapPrefix 21125 }

cmPow3ChVoltMinCCLEAR NOTIFICATION-TYPE
OBJECTS { pow3ChVoltMinC, pow3ChName, productFriendlyName, alarmTripType, alarmTrigger, alarmInstance }
STATUS current
DESCRIPTION "Volts Min C Clear Trap"
::= { cmTrapPrefix 21126 }

cmPow3ChVoltPeakCCLEAR NOTIFICATION-TYPE
OBJECTS { pow3ChVoltPeakC, pow3ChName, productFriendlyName, alarmTripType, alarmTrigger, alarmInstance }
STATUS current
DESCRIPTION "Volt Peak C Clear Trap"
::= { cmTrapPrefix 21127 }

cmPow3ChDeciAmpsCCLEAR NOTIFICATION-TYPE
OBJECTS { pow3ChDeciAmpsC, pow3ChName, productFriendlyName, alarmTripType, alarmTrigger, alarmInstance }
STATUS current
DESCRIPTION "Deciamps C Clear Trap"
::= { cmTrapPrefix 21128 }

cmPow3ChRealPowerCCLEAR NOTIFICATION-TYPE
OBJECTS { pow3ChRealPowerC, pow3ChName, productFriendlyName, alarmTripType, alarmTrigger, alarmInstance }
STATUS current
DESCRIPTION "Real Power C Clear Trap"
::= { cmTrapPrefix 21129 }

cmPow3ChApparentPowerCCLEAR NOTIFICATION-TYPE
OBJECTS { pow3ChApparentPowerC, pow3ChName, productFriendlyName, alarmTripType, alarmTrigger, alarmInstance }
STATUS current
DESCRIPTION "Apparent Power C Clear Trap"
::= { cmTrapPrefix 21130 }

cmPow3ChPowerFactorCCLEAR NOTIFICATION-TYPE
OBJECTS { pow3ChPowerFactorC, pow3ChName, productFriendlyName, alarmTripType, alarmTrigger, alarmInstance }
STATUS current
DESCRIPTION "Power Factor C Clear Trap"
::= { cmTrapPrefix 21131 }

cmPow3ChkWattHrsTotalCLEAR NOTIFICATION-TYPE
OBJECTS { pow3ChkWattHrsTotal, pow3ChName, productFriendlyName, alarmTripType, alarmTrigger, alarmInstance }
STATUS current
DESCRIPTION "Kilo Watt Hours Total Clear Trap"
::= { cmTrapPrefix 21132 }

cmPow3ChRealPowerTotalCLEAR NOTIFICATION-TYPE
OBJECTS { pow3ChRealPowerTotal, pow3ChName, productFriendlyName, alarmTripType, alarmTrigger, alarmInstance }
STATUS current
DESCRIPTION "Real Power Total Clear Trap"
::= { cmTrapPrefix 21133 }

cmOutlet1StatusCLEAR NOTIFICATION-TYPE
OBJECTS { outlet1Status, outletName, productFriendlyName, alarmTripType, alarmTrigger, alarmInstance }
STATUS current
DESCRIPTION "Outlet 1 Status Clear Trap"
::= { cmTrapPrefix 21205 }

cmOutlet2StatusCLEAR NOTIFICATION-TYPE
OBJECTS { outlet2Status, outletName, productFriendlyName, alarmTripType, alarmTrigger, alarmInstance }
STATUS current
DESCRIPTION "Outlet 2 Status Clear Trap"
::= { cmTrapPrefix 21206 }

cmVsfcSetPointCCLEAR NOTIFICATION-TYPE
OBJECTS { vsfcSetPointC, vsfcName, productFriendlyName, alarmTripType, alarmTrigger, alarmInstance }
STATUS current
DESCRIPTION "Vsfc Temp Set Point Sensor Clear"
::= { cmTrapPrefix 21305 }

cmVsfcSetPointFCLEAR NOTIFICATION-TYPE
OBJECTS { vsfcSetPointF, vsfcName, productFriendlyName, alarmTripType, alarmTrigger, alarmInstance }
STATUS current
DESCRIPTION "Vsfc Temp Set Point Sensor Clear"
::= { cmTrapPrefix 21306 }

cmVsfcFanSpeedCLEAR NOTIFICATION-TYPE
OBJECTS { vsfcFanSpeed, vsfcName, productFriendlyName, alarmTripType, alarmTrigger, alarmInstance }
STATUS current
DESCRIPTION "Vsfc Fan Speed Sensor Clear"
::= { cmTrapPrefix 21307 }

cmVsfcIntTempCCLEAR NOTIFICATION-TYPE
OBJECTS { vsfcIntTempC, vsfcName, productFriendlyName, alarmTripType, temperaturePrecision, alarmTrigger, alarmInstance }
STATUS current
DESCRIPTION "Vsfc Internal Temp Sensor Clear"
::= { cmTrapPrefix 21308 }

cmVsfcIntTempFCLEAR NOTIFICATION-TYPE
OBJECTS { vsfcIntTempF, vsfcName, productFriendlyName, alarmTripType, temperaturePrecision, alarmTrigger, alarmInstance }
STATUS current
DESCRIPTION "Vsfc Internal Temp Sensor Clear"
::= { cmTrapPrefix 21309 }

cmVsfcExt1TempCCLEAR NOTIFICATION-TYPE
OBJECTS { vsfcExt1TempC, vsfcName, productFriendlyName, alarmTripType, temperaturePrecision, alarmTrigger, alarmInstance }
STATUS current
DESCRIPTION "Vsfc External Temp 1 Sensor Clear"
::= { cmTrapPrefix 21310 }

cmVsfcExt1TempFCLEAR NOTIFICATION-TYPE
OBJECTS { vsfcExt1TempF, vsfcName, productFriendlyName, alarmTripType, temperaturePrecision, alarmTrigger, alarmInstance }
STATUS current
DESCRIPTION "Vsfc External Temp 1 Sensor Clear"
::= { cmTrapPrefix 21311 }

cmVsfcExt2TempCCLEAR NOTIFICATION-TYPE
OBJECTS { vsfcExt2TempC, vsfcName, productFriendlyName, alarmTripType, temperaturePrecision, alarmTrigger, alarmInstance }
STATUS current
DESCRIPTION "Vsfc External Temp 2 Sensor Clear"
::= { cmTrapPrefix 21312 }

cmVsfcExt2TempFCLEAR NOTIFICATION-TYPE
OBJECTS { vsfcExt2TempF, vsfcName, productFriendlyName, alarmTripType, temperaturePrecision, alarmTrigger, alarmInstance }
STATUS current
DESCRIPTION "Vsfc External Temp 1 Sensor Clear"
::= { cmTrapPrefix 21313 }

cmVsfcExt3TempCCLEAR NOTIFICATION-TYPE
OBJECTS { vsfcExt3TempC, vsfcName, productFriendlyName, alarmTripType, temperaturePrecision, alarmTrigger, alarmInstance }
STATUS current
DESCRIPTION "Vsfc External Temp 3 Sensor Clear"
::= { cmTrapPrefix 21314 }

cmVsfcExt3TempFCLEAR NOTIFICATION-TYPE
OBJECTS { vsfcExt3TempF, vsfcName, productFriendlyName, alarmTripType, temperaturePrecision, alarmTrigger, alarmInstance }
STATUS current
DESCRIPTION "Vsfc External Temp 1 Sensor Clear"
::= { cmTrapPrefix 21315 }

cmVsfcExt4TempCCLEAR NOTIFICATION-TYPE
OBJECTS { vsfcExt4TempC, vsfcName, productFriendlyName, alarmTripType, temperaturePrecision, alarmTrigger, alarmInstance }
STATUS current
DESCRIPTION "Vsfc External Temp 4 Sensor Clear"
::= { cmTrapPrefix 21316 }

cmVsfcExt4TempFCLEAR NOTIFICATION-TYPE
OBJECTS { vsfcExt4TempF, vsfcName, productFriendlyName, alarmTripType, temperaturePrecision, alarmTrigger, alarmInstance }
STATUS current
DESCRIPTION "Vsfc External Temp 1 Sensor Clear"
::= { cmTrapPrefix 21317 }

cmCtrl3ChVoltsACLEAR NOTIFICATION-TYPE
OBJECTS { ctrl3ChVoltsA, ctrl3ChName, productFriendlyName, alarmTripType, alarmTrigger, alarmInstance }
STATUS current
DESCRIPTION "Volts A Clear Trap"
::= { cmTrapPrefix 21405 }

cmCtrl3ChVoltPeakACLEAR NOTIFICATION-TYPE
OBJECTS { ctrl3ChVoltPeakA, ctrl3ChName, productFriendlyName, alarmTripType, alarmTrigger, alarmInstance }
STATUS current
DESCRIPTION "Volts Peak A Clear Trap"
::= { cmTrapPrefix 21406 }

cmCtrl3ChDeciAmpsACLEAR NOTIFICATION-TYPE
OBJECTS { ctrl3ChDeciAmpsA, ctrl3ChName, productFriendlyName, alarmTripType, alarmTrigger, alarmInstance }
STATUS current
DESCRIPTION "Deciamps A Clear Trap"
::= { cmTrapPrefix 21407 }

cmCtrl3ChDeciAmpsPeakACLEAR NOTIFICATION-TYPE
OBJECTS { ctrl3ChDeciAmpsPeakA, ctrl3ChName, productFriendlyName, alarmTripType, alarmTrigger, alarmInstance }
STATUS current
DESCRIPTION "Deciamps Peak A Clear Trap"
::= { cmTrapPrefix 21408 }

cmCtrl3ChRealPowerACLEAR NOTIFICATION-TYPE
OBJECTS { ctrl3ChRealPowerA, ctrl3ChName, productFriendlyName, alarmTripType, alarmTrigger, alarmInstance }
STATUS current
DESCRIPTION "Real Power A Clear Trap"
::= { cmTrapPrefix 21409 }

cmCtrl3ChApparentPowerACLEAR NOTIFICATION-TYPE
OBJECTS { ctrl3ChApparentPowerA, ctrl3ChName, productFriendlyName, alarmTripType, alarmTrigger, alarmInstance }
STATUS current
DESCRIPTION "Apparent Power A Clear Trap"
::= { cmTrapPrefix 21410 }

cmCtrl3ChPowerFactorACLEAR NOTIFICATION-TYPE
OBJECTS { ctrl3ChPowerFactorA, ctrl3ChName, productFriendlyName, alarmTripType, alarmTrigger, alarmInstance }
STATUS current
DESCRIPTION "Power Factor A Clear Trap"
::= { cmTrapPrefix 21411 }

cmCtrl3ChVoltsBCLEAR NOTIFICATION-TYPE
OBJECTS { ctrl3ChVoltsB, ctrl3ChName, productFriendlyName, alarmTripType, alarmTrigger, alarmInstance }
STATUS current
DESCRIPTION "Volts B Clear Trap"
::= { cmTrapPrefix 21412 }

cmCtrl3ChVoltPeakBCLEAR NOTIFICATION-TYPE
OBJECTS { ctrl3ChVoltPeakB, ctrl3ChName, productFriendlyName, alarmTripType, alarmTrigger, alarmInstance }
STATUS current
DESCRIPTION "Volts Peak B Clear Trap"
::= { cmTrapPrefix 21413 }

cmCtrl3ChDeciAmpsBCLEAR NOTIFICATION-TYPE
OBJECTS { ctrl3ChDeciAmpsB, ctrl3ChName, productFriendlyName, alarmTripType, alarmTrigger, alarmInstance }
STATUS current
DESCRIPTION "Deciamps B Clear Trap"
::= { cmTrapPrefix 21414 }

cmCtrl3ChDeciAmpsPeakBCLEAR NOTIFICATION-TYPE
OBJECTS { ctrl3ChDeciAmpsPeakB, ctrl3ChName, productFriendlyName, alarmTripType, alarmTrigger, alarmInstance }
STATUS current
DESCRIPTION "Deciamps Peak B Clear Trap"
::= { cmTrapPrefix 21415 }

cmCtrl3ChRealPowerBCLEAR NOTIFICATION-TYPE
OBJECTS { ctrl3ChRealPowerB, ctrl3ChName, productFriendlyName, alarmTripType, alarmTrigger, alarmInstance }
STATUS current
DESCRIPTION "Real Power B Clear Trap"
::= { cmTrapPrefix 21416 }

cmCtrl3ChApparentPowerBCLEAR NOTIFICATION-TYPE
OBJECTS { ctrl3ChApparentPowerB, ctrl3ChName, productFriendlyName, alarmTripType, alarmTrigger, alarmInstance }
STATUS current
DESCRIPTION "Apparent Power B Clear Trap"
::= { cmTrapPrefix 21417 }

cmCtrl3ChPowerFactorBCLEAR NOTIFICATION-TYPE
OBJECTS { ctrl3ChPowerFactorB, ctrl3ChName, productFriendlyName, alarmTripType, alarmTrigger, alarmInstance }
STATUS current
DESCRIPTION "Power Factor B Clear Trap"
::= { cmTrapPrefix 21418 }

cmCtrl3ChVoltsCCLEAR NOTIFICATION-TYPE
OBJECTS { ctrl3ChVoltsC, ctrl3ChName, productFriendlyName, alarmTripType, alarmTrigger, alarmInstance }
STATUS current
DESCRIPTION "Volts C Clear Trap"
::= { cmTrapPrefix 21419 }

cmCtrl3ChVoltPeakCCLEAR NOTIFICATION-TYPE
OBJECTS { ctrl3ChVoltPeakC, ctrl3ChName, productFriendlyName, alarmTripType, alarmTrigger, alarmInstance }
STATUS current
DESCRIPTION "Volts Peak C Clear Trap"
::= { cmTrapPrefix 21420 }

cmCtrl3ChDeciAmpsCCLEAR NOTIFICATION-TYPE
OBJECTS { ctrl3ChDeciAmpsC, ctrl3ChName, productFriendlyName, alarmTripType, alarmTrigger, alarmInstance }
STATUS current
DESCRIPTION "Deciamps C Clear Trap"
::= { cmTrapPrefix 21421 }

cmCtrl3ChDeciAmpsPeakCCLEAR NOTIFICATION-TYPE
OBJECTS { ctrl3ChDeciAmpsPeakC, ctrl3ChName, productFriendlyName, alarmTripType, alarmTrigger, alarmInstance }
STATUS current
DESCRIPTION "Deciamps Peak C Clear Trap"
::= { cmTrapPrefix 21422 }

cmCtrl3ChRealPowerCCLEAR NOTIFICATION-TYPE
OBJECTS { ctrl3ChRealPowerC, ctrl3ChName, productFriendlyName, alarmTripType, alarmTrigger, alarmInstance }
STATUS current
DESCRIPTION "Real Power C Clear Trap"
::= { cmTrapPrefix 21423 }

cmCtrl3ChApparentPowerCCLEAR NOTIFICATION-TYPE
OBJECTS { ctrl3ChApparentPowerC, ctrl3ChName, productFriendlyName, alarmTripType, alarmTrigger, alarmInstance }
STATUS current
DESCRIPTION "Apparent Power C Clear Trap"
::= { cmTrapPrefix 21424 }

cmCtrl3ChPowerFactorCCLEAR NOTIFICATION-TYPE
OBJECTS { ctrl3ChPowerFactorC, ctrl3ChName, productFriendlyName, alarmTripType, alarmTrigger, alarmInstance }
STATUS current
DESCRIPTION "Power Factor C Clear Trap"
::= { cmTrapPrefix 21425 }

cmCtrlGrpAmpsACLEAR NOTIFICATION-TYPE
OBJECTS { ctrlGrpAmpsA, ctrlGrpAmpsName, productFriendlyName, alarmTripType, alarmTrigger, alarmInstance }
STATUS current
DESCRIPTION "Group A DeciAmps Clear Trap"
::= { cmTrapPrefix 21505 }

cmCtrlGrpAmpsBCLEAR NOTIFICATION-TYPE
OBJECTS { ctrlGrpAmpsB, ctrlGrpAmpsName, productFriendlyName, alarmTripType, alarmTrigger, alarmInstance }
STATUS current
DESCRIPTION "Group B DeciAmps Clear Trap"
::= { cmTrapPrefix 21506 }

cmCtrlGrpAmpsCCLEAR NOTIFICATION-TYPE
OBJECTS { ctrlGrpAmpsC, ctrlGrpAmpsName, productFriendlyName, alarmTripType, alarmTrigger, alarmInstance }
STATUS current
DESCRIPTION "Group C DeciAmps Clear Trap"
::= { cmTrapPrefix 21507 }

cmCtrlGrpAmpsDCLEAR NOTIFICATION-TYPE
OBJECTS { ctrlGrpAmpsD, ctrlGrpAmpsName, productFriendlyName, alarmTripType, alarmTrigger, alarmInstance }
STATUS current
DESCRIPTION "Group D DeciAmps Clear Trap"
::= { cmTrapPrefix 21508 }

cmCtrlGrpAmpsECLEAR NOTIFICATION-TYPE
OBJECTS { ctrlGrpAmpsE, ctrlGrpAmpsName, productFriendlyName, alarmTripType, alarmTrigger, alarmInstance }
STATUS current
DESCRIPTION "Group E DeciAmps Clear Trap"
::= { cmTrapPrefix 21509 }

cmCtrlGrpAmpsFCLEAR NOTIFICATION-TYPE
OBJECTS { ctrlGrpAmpsF, ctrlGrpAmpsName, productFriendlyName, alarmTripType, alarmTrigger, alarmInstance }
STATUS current
DESCRIPTION "Group F DeciAmps Clear Trap"
::= { cmTrapPrefix 21510 }

cmCtrlGrpAmpsGCLEAR NOTIFICATION-TYPE
OBJECTS { ctrlGrpAmpsG, ctrlGrpAmpsName, productFriendlyName, alarmTripType, alarmTrigger, alarmInstance }
STATUS current
DESCRIPTION "Group G DeciAmps Clear Trap"
::= { cmTrapPrefix 21511 }

cmCtrlGrpAmpsHCLEAR NOTIFICATION-TYPE
OBJECTS { ctrlGrpAmpsH, ctrlGrpAmpsName, productFriendlyName, alarmTripType, alarmTrigger, alarmInstance }
STATUS current
DESCRIPTION "Group H DeciAmps Clear Trap"
::= { cmTrapPrefix 21512 }

cmCtrlGrpAmpsAVoltsCLEAR NOTIFICATION-TYPE
OBJECTS { ctrlGrpAmpsAVolts, ctrlGrpAmpsName, productFriendlyName, alarmTripType, alarmTrigger, alarmInstance }
STATUS current
DESCRIPTION "AVolts Clear Trap"
::= { cmTrapPrefix 21513 }

cmCtrlGrpAmpsBVoltsCLEAR NOTIFICATION-TYPE
OBJECTS { ctrlGrpAmpsBVolts, ctrlGrpAmpsName, productFriendlyName, alarmTripType, alarmTrigger, alarmInstance }
STATUS current
DESCRIPTION "BVolts Clear Trap"
::= { cmTrapPrefix 21514 }

cmCtrlGrpAmpsCVoltsCLEAR NOTIFICATION-TYPE
OBJECTS { ctrlGrpAmpsCVolts, ctrlGrpAmpsName, productFriendlyName, alarmTripType, alarmTrigger, alarmInstance }
STATUS current
DESCRIPTION "CVolts Clear Trap"
::= { cmTrapPrefix 21515 }

cmCtrlGrpAmpsDVoltsCLEAR NOTIFICATION-TYPE
OBJECTS { ctrlGrpAmpsDVolts, ctrlGrpAmpsName, productFriendlyName, alarmTripType, alarmTrigger, alarmInstance }
STATUS current
DESCRIPTION "DVolts Clear Trap"
::= { cmTrapPrefix 21516 }

cmCtrlGrpAmpsEVoltsCLEAR NOTIFICATION-TYPE
OBJECTS { ctrlGrpAmpsEVolts, ctrlGrpAmpsName, productFriendlyName, alarmTripType, alarmTrigger, alarmInstance }
STATUS current
DESCRIPTION "EVolts Clear Trap"
::= { cmTrapPrefix 21517 }

cmCtrlGrpAmpsFVoltsCLEAR NOTIFICATION-TYPE
OBJECTS { ctrlGrpAmpsFVolts, ctrlGrpAmpsName, productFriendlyName, alarmTripType, alarmTrigger, alarmInstance }
STATUS current
DESCRIPTION "FVolts Clear Trap"
::= { cmTrapPrefix 21518 }

cmCtrlGrpAmpsGVoltsCLEAR NOTIFICATION-TYPE
OBJECTS { ctrlGrpAmpsGVolts, ctrlGrpAmpsName, productFriendlyName, alarmTripType, alarmTrigger, alarmInstance }
STATUS current
DESCRIPTION "GVolts Clear Trap"
::= { cmTrapPrefix 21519 }

cmCtrlGrpAmpsHVoltsCLEAR NOTIFICATION-TYPE
OBJECTS { ctrlGrpAmpsHVolts, ctrlGrpAmpsName, productFriendlyName, alarmTripType, alarmTrigger, alarmInstance }
STATUS current
DESCRIPTION "HVolts Clear Trap"
::= { cmTrapPrefix 21520 }

cmCtrlGrpAmpsICLEAR NOTIFICATION-TYPE
OBJECTS { ctrlGrpAmpsI, ctrlGrpAmpsName, productFriendlyName, alarmTripType, alarmTrigger, alarmInstance }
STATUS current
DESCRIPTION "Group I DeciAmps Clear Trap"
::= { cmTrapPrefix 21521 }

cmCtrlGrpAmpsJCLEAR NOTIFICATION-TYPE
OBJECTS { ctrlGrpAmpsJ, ctrlGrpAmpsName, productFriendlyName, alarmTripType, alarmTrigger, alarmInstance }
STATUS current
DESCRIPTION "Group J DeciAmps Clear Trap"
::= { cmTrapPrefix 21522 }

cmCtrlGrpAmpsKCLEAR NOTIFICATION-TYPE
OBJECTS { ctrlGrpAmpsK, ctrlGrpAmpsName, productFriendlyName, alarmTripType, alarmTrigger, alarmInstance }
STATUS current
DESCRIPTION "Group K DeciAmps Clear Trap"
::= { cmTrapPrefix 21523 }

cmCtrlGrpAmpsLCLEAR NOTIFICATION-TYPE
OBJECTS { ctrlGrpAmpsL, ctrlGrpAmpsName, productFriendlyName, alarmTripType, alarmTrigger, alarmInstance }
STATUS current
DESCRIPTION "Group L DeciAmps Clear Trap"
::= { cmTrapPrefix 21524 }

cmCtrlGrpAmpsMCLEAR NOTIFICATION-TYPE
OBJECTS { ctrlGrpAmpsM, ctrlGrpAmpsName, productFriendlyName, alarmTripType, alarmTrigger, alarmInstance }
STATUS current
DESCRIPTION "Group M DeciAmps Clear Trap"
::= { cmTrapPrefix 21525 }

cmCtrlGrpAmpsNCLEAR NOTIFICATION-TYPE
OBJECTS { ctrlGrpAmpsN, ctrlGrpAmpsName, productFriendlyName, alarmTripType, alarmTrigger, alarmInstance }
STATUS current
DESCRIPTION "Group N DeciAmps Clear Trap"
::= { cmTrapPrefix 21526 }

cmCtrlGrpAmpsOCLEAR NOTIFICATION-TYPE
OBJECTS { ctrlGrpAmpsO, ctrlGrpAmpsName, productFriendlyName, alarmTripType, alarmTrigger, alarmInstance }
STATUS current
DESCRIPTION "Group O DeciAmps Clear Trap"
::= { cmTrapPrefix 21527 }

cmCtrlGrpAmpsPCLEAR NOTIFICATION-TYPE
OBJECTS { ctrlGrpAmpsP, ctrlGrpAmpsName, productFriendlyName, alarmTripType, alarmTrigger, alarmInstance }
STATUS current
DESCRIPTION "Group P DeciAmps Clear Trap"
::= { cmTrapPrefix 21528 }

cmCtrlGrpAmpsIVoltsCLEAR NOTIFICATION-TYPE
OBJECTS { ctrlGrpAmpsIVolts, ctrlGrpAmpsName, productFriendlyName, alarmTripType, alarmTrigger, alarmInstance }
STATUS current
DESCRIPTION "IVolts Clear Trap"
::= { cmTrapPrefix 21529 }

cmCtrlGrpAmpsJVoltsCLEAR NOTIFICATION-TYPE
OBJECTS { ctrlGrpAmpsJVolts, ctrlGrpAmpsName, productFriendlyName, alarmTripType, alarmTrigger, alarmInstance }
STATUS current
DESCRIPTION "JVolts Clear Trap"
::= { cmTrapPrefix 21530 }

cmCtrlGrpAmpsKVoltsCLEAR NOTIFICATION-TYPE
OBJECTS { ctrlGrpAmpsKVolts, ctrlGrpAmpsName, productFriendlyName, alarmTripType, alarmTrigger, alarmInstance }
STATUS current
DESCRIPTION "KVolts Clear Trap"
::= { cmTrapPrefix 21531 }

cmCtrlGrpAmpsLVoltsCLEAR NOTIFICATION-TYPE
OBJECTS { ctrlGrpAmpsLVolts, ctrlGrpAmpsName, productFriendlyName, alarmTripType, alarmTrigger, alarmInstance }
STATUS current
DESCRIPTION "LVolts Clear Trap"
::= { cmTrapPrefix 21532 }

cmCtrlGrpAmpsMVoltsCLEAR NOTIFICATION-TYPE
OBJECTS { ctrlGrpAmpsMVolts, ctrlGrpAmpsName, productFriendlyName, alarmTripType, alarmTrigger, alarmInstance }
STATUS current
DESCRIPTION "MVolts Clear Trap"
::= { cmTrapPrefix 21533 }

cmCtrlGrpAmpsNVoltsCLEAR NOTIFICATION-TYPE
OBJECTS { ctrlGrpAmpsNVolts, ctrlGrpAmpsName, productFriendlyName, alarmTripType, alarmTrigger, alarmInstance }
STATUS current
DESCRIPTION "NVolts Clear Trap"
::= { cmTrapPrefix 21534 }

cmCtrlGrpAmpsOVoltsCLEAR NOTIFICATION-TYPE
OBJECTS { ctrlGrpAmpsOVolts, ctrlGrpAmpsName, productFriendlyName, alarmTripType, alarmTrigger, alarmInstance }
STATUS current
DESCRIPTION "OVolts Clear Trap"
::= { cmTrapPrefix 21535 }

cmCtrlGrpAmpsPVoltsCLEAR NOTIFICATION-TYPE
OBJECTS { ctrlGrpAmpsPVolts, ctrlGrpAmpsName, productFriendlyName, alarmTripType, alarmTrigger, alarmInstance }
STATUS current
DESCRIPTION "PVolts Clear Trap"
::= { cmTrapPrefix 21536 }

cmCtrlOutletPendingCLEAR NOTIFICATION-TYPE
OBJECTS { ctrlOutletPending, ctrlOutletStatus, productFriendlyName, alarmTripType, alarmTrigger, alarmInstance }
STATUS current
DESCRIPTION "Pending Clear Trap"
::= { cmTrapPrefix 21605 }

cmCtrlOutletDeciAmpsCLEAR NOTIFICATION-TYPE
OBJECTS { ctrlOutletDeciAmps, ctrlOutletStatus, productFriendlyName, alarmTripType, alarmTrigger, alarmInstance }
STATUS current
DESCRIPTION "Outlet DeciAmps Clear Trap"
::= { cmTrapPrefix 21606 }

cmCtrlOutletGroupCLEAR NOTIFICATION-TYPE
OBJECTS { ctrlOutletGroup, ctrlOutletStatus, productFriendlyName, alarmTripType, alarmTrigger, alarmInstance }
STATUS current
DESCRIPTION "Group Clear Trap"
::= { cmTrapPrefix 21607 }

cmCtrlOutletUpDelayCLEAR NOTIFICATION-TYPE
OBJECTS { ctrlOutletUpDelay, ctrlOutletStatus, productFriendlyName, alarmTripType, alarmTrigger, alarmInstance }
STATUS current
DESCRIPTION "UpDelay Clear Trap"
::= { cmTrapPrefix 21608 }

cmCtrlOutletDwnDelayCLEAR NOTIFICATION-TYPE
OBJECTS { ctrlOutletDwnDelay, ctrlOutletStatus, productFriendlyName, alarmTripType, alarmTrigger, alarmInstance }
STATUS current
DESCRIPTION "DwnDelay Clear Trap"
::= { cmTrapPrefix 21609 }

cmCtrlOutletRbtDurationCLEAR NOTIFICATION-TYPE
OBJECTS { ctrlOutletRbtDuration, ctrlOutletStatus, productFriendlyName, alarmTripType, alarmTrigger, alarmInstance }
STATUS current
DESCRIPTION "RbtDuration Clear Trap"
::= { cmTrapPrefix 21610 }

cmCtrlOutletURLCLEAR NOTIFICATION-TYPE
OBJECTS { ctrlOutletURL, ctrlOutletStatus, productFriendlyName, alarmTripType, alarmTrigger, alarmInstance }
STATUS current
DESCRIPTION "URL Clear Trap"
::= { cmTrapPrefix 21611 }

cmCtrlOutletPOAActionCLEAR NOTIFICATION-TYPE
OBJECTS { ctrlOutletPOAAction, ctrlOutletStatus, productFriendlyName, alarmTripType, alarmTrigger, alarmInstance }
STATUS current
DESCRIPTION "POAAction Clear Trap"
::= { cmTrapPrefix 21612 }

cmCtrlOutletPOADelayCLEAR NOTIFICATION-TYPE
OBJECTS { ctrlOutletPOADelay, ctrlOutletStatus, productFriendlyName, alarmTripType, alarmTrigger, alarmInstance }
STATUS current
DESCRIPTION "POADelay Clear Trap"
::= { cmTrapPrefix 21613 }

cmCtrlOutletkWattHrsCLEAR NOTIFICATION-TYPE
OBJECTS { ctrlOutletkWattHrs, ctrlOutletStatus, productFriendlyName, alarmTripType, alarmTrigger, alarmInstance }
STATUS current
DESCRIPTION "kWattHrs Clear Trap"
::= { cmTrapPrefix 21614 }

cmCtrlOutletPowerCLEAR NOTIFICATION-TYPE
OBJECTS { ctrlOutletPower, ctrlOutletStatus, productFriendlyName, alarmTripType, alarmTrigger, alarmInstance }
STATUS current
DESCRIPTION "Power Clear Trap"
::= { cmTrapPrefix 21615 }

cmCtrlOutletRbtDelayCLEAR NOTIFICATION-TYPE
OBJECTS { ctrlOutletRbtDelay, ctrlOutletStatus, productFriendlyName, alarmTripType, alarmTrigger, alarmInstance }
STATUS current
DESCRIPTION "RbtDelay Clear Trap"
::= { cmTrapPrefix 21616 }

cmCtrlOutletStatusTimeCLEAR NOTIFICATION-TYPE
OBJECTS { ctrlOutletStatusTime, ctrlOutletStatus, productFriendlyName, alarmTripType, alarmTrigger, alarmInstance }
STATUS current
DESCRIPTION "StatusTime Clear Trap"
::= { cmTrapPrefix 21617 }

cmDewPointSensorTempCCLEAR NOTIFICATION-TYPE
OBJECTS { dewPointSensorTempC, dewPointSensorName, productFriendlyName, alarmTripType, temperaturePrecision, alarmTrigger, alarmInstance }
STATUS current
DESCRIPTION "Remote Dew Point Sensor - Temperature Clear Trap"
::= { cmTrapPrefix 21705 }

cmDewPointSensorTempFCLEAR NOTIFICATION-TYPE
OBJECTS { dewPointSensorTempF, dewPointSensorName, productFriendlyName, alarmTripType, temperaturePrecision, alarmTrigger, alarmInstance }
STATUS current
DESCRIPTION "Remote Dew Point Sensor - Temperature Clear Trap"
::= { cmTrapPrefix 21706 }

cmDewPointSensorHumidityCLEAR NOTIFICATION-TYPE
OBJECTS { dewPointSensorHumidity, dewPointSensorName, productFriendlyName, alarmTripType, alarmTrigger, alarmInstance }
STATUS current
DESCRIPTION "Remote Dew Point Sensor - Humidity Clear Trap"
::= { cmTrapPrefix 21707 }

cmDewPointSensorDewPointCCLEAR NOTIFICATION-TYPE
OBJECTS { dewPointSensorDewPointC, dewPointSensorName, productFriendlyName, alarmTripType, temperaturePrecision, alarmTrigger, alarmInstance }
STATUS current
DESCRIPTION "Remote Dew Point Sensor - Dew Point Clear Trap"
::= { cmTrapPrefix 21708 }

cmDewPointSensorDewPointFCLEAR NOTIFICATION-TYPE
OBJECTS { dewPointSensorDewPointF, dewPointSensorName, productFriendlyName, alarmTripType, temperaturePrecision, alarmTrigger, alarmInstance }
STATUS current
DESCRIPTION "Remote Dew Point Sensor - Dew Point Clear Trap"
::= { cmTrapPrefix 21709 }

cmDigitalSensorDigitalCLEAR NOTIFICATION-TYPE
OBJECTS { digitalSensorDigital, digitalSensorName, productFriendlyName, alarmTripType, alarmTrigger, alarmInstance }
STATUS current
DESCRIPTION "Digital sensor Clear Trap"
::= { cmTrapPrefix 21805 }

cmDstsVoltsACLEAR NOTIFICATION-TYPE
OBJECTS { dstsVoltsA, dstsName, productFriendlyName, alarmTripType, alarmTrigger, alarmInstance }
STATUS current
DESCRIPTION "RMS Voltage of Side A Set Point Sensor Clear"
::= { cmTrapPrefix 21905 }

cmDstsDeciAmpsACLEAR NOTIFICATION-TYPE
OBJECTS { dstsDeciAmpsA, dstsName, productFriendlyName, alarmTripType, alarmTrigger, alarmInstance }
STATUS current
DESCRIPTION "RMS Current of Side A Set Point Sensor Clear"
::= { cmTrapPrefix 21906 }

cmDstsVoltsBCLEAR NOTIFICATION-TYPE
OBJECTS { dstsVoltsB, dstsName, productFriendlyName, alarmTripType, alarmTrigger, alarmInstance }
STATUS current
DESCRIPTION "RMS Voltage of Side B Set Point Sensor Clear"
::= { cmTrapPrefix 21907 }

cmDstsDeciAmpsBCLEAR NOTIFICATION-TYPE
OBJECTS { dstsDeciAmpsB, dstsName, productFriendlyName, alarmTripType, alarmTrigger, alarmInstance }
STATUS current
DESCRIPTION "RMS Current of Side B Set Point Sensor Clear"
::= { cmTrapPrefix 21908 }

cmDstsSourceAActiveCLEAR NOTIFICATION-TYPE
OBJECTS { dstsSourceAActive, dstsName, productFriendlyName, alarmTripType, alarmTrigger, alarmInstance }
STATUS current
DESCRIPTION "Source A Active Set Point Sensor Clear"
::= { cmTrapPrefix 21909 }

cmDstsSourceBActiveCLEAR NOTIFICATION-TYPE
OBJECTS { dstsSourceBActive, dstsName, productFriendlyName, alarmTripType, alarmTrigger, alarmInstance }
STATUS current
DESCRIPTION "Source B Active Set Point Sensor Clear"
::= { cmTrapPrefix 21910 }

cmDstsPowerStatusACLEAR NOTIFICATION-TYPE
OBJECTS { dstsPowerStatusA, dstsName, productFriendlyName, alarmTripType, alarmTrigger, alarmInstance }
STATUS current
DESCRIPTION "Source A Power Qualilty Active Set Point Sensor Clear"
::= { cmTrapPrefix 21911 }

cmDstsPowerStatusBCLEAR NOTIFICATION-TYPE
OBJECTS { dstsPowerStatusB, dstsName, productFriendlyName, alarmTripType, alarmTrigger, alarmInstance }
STATUS current
DESCRIPTION "Source B Power Qualilty Active Set Point Sensor Clear"
::= { cmTrapPrefix 21912 }

cmDstsSourceATempCCLEAR NOTIFICATION-TYPE
OBJECTS { dstsSourceATempC, dstsName, productFriendlyName, alarmTripType, temperaturePrecision, alarmTrigger, alarmInstance }
STATUS current
DESCRIPTION "Source A Temp Sensor Clear"
::= { cmTrapPrefix 21913 }

cmDstsSourceBTempCCLEAR NOTIFICATION-TYPE
OBJECTS { dstsSourceBTempC, dstsName, productFriendlyName, alarmTripType, temperaturePrecision, alarmTrigger, alarmInstance }
STATUS current
DESCRIPTION "Source B Temp Sensor Clear"
::= { cmTrapPrefix 21914 }

cmCpmSensorStatusCLEAR NOTIFICATION-TYPE
OBJECTS { cpmSensorStatus, cpmSensorName, productFriendlyName, alarmTripType, alarmTrigger, alarmInstance }
STATUS current
DESCRIPTION "City Power sensor Clear Trap"
::= { cmTrapPrefix 22005 }

cmSmokeAlarmStatusCLEAR NOTIFICATION-TYPE
OBJECTS { smokeAlarmStatus, smokeAlarmName, productFriendlyName, alarmTripType, alarmTrigger, alarmInstance }
STATUS current
DESCRIPTION "Smoke alarm Clear Trap"
::= { cmTrapPrefix 22105 }

cmNeg48VdcSensorVoltageCLEAR NOTIFICATION-TYPE
OBJECTS { neg48VdcSensorVoltage, neg48VdcSensorName, productFriendlyName, alarmTripType, alarmTrigger, alarmInstance }
STATUS current
DESCRIPTION "-48Vdc Sensor Clear Trap"
::= { cmTrapPrefix 22205 }

cmPos30VdcSensorVoltageCLEAR NOTIFICATION-TYPE
OBJECTS { pos30VdcSensorVoltage, pos30VdcSensorName, productFriendlyName, alarmTripType, alarmTrigger, alarmInstance }
STATUS current
DESCRIPTION "30Vdc Sensor Clear Trap"
::= { cmTrapPrefix 22305 }

cmAnalogSensorAnalogCLEAR NOTIFICATION-TYPE
OBJECTS { analogSensorAnalog, analogSensorName, productFriendlyName, alarmTripType, alarmTrigger, alarmInstance }
STATUS current
DESCRIPTION "Analog Sensor Clear Trap"
::= { cmTrapPrefix 22405 }

cmCtrl3ChIECkWattHrsACLEAR NOTIFICATION-TYPE
OBJECTS { ctrl3ChIECkWattHrsA, ctrl3ChIECName, productFriendlyName, alarmTripType, alarmTrigger, alarmInstance }
STATUS current
DESCRIPTION "Kilo Watt Hours A Clear Trap"
::= { cmTrapPrefix 22505 }

cmCtrl3ChIECVoltsACLEAR NOTIFICATION-TYPE
OBJECTS { ctrl3ChIECVoltsA, ctrl3ChIECName, productFriendlyName, alarmTripType, alarmTrigger, alarmInstance }
STATUS current
DESCRIPTION "Volts A Clear Trap"
::= { cmTrapPrefix 22506 }

cmCtrl3ChIECVoltPeakACLEAR NOTIFICATION-TYPE
OBJECTS { ctrl3ChIECVoltPeakA, ctrl3ChIECName, productFriendlyName, alarmTripType, alarmTrigger, alarmInstance }
STATUS current
DESCRIPTION "Volts Peak A Clear Trap"
::= { cmTrapPrefix 22507 }

cmCtrl3ChIECDeciAmpsACLEAR NOTIFICATION-TYPE
OBJECTS { ctrl3ChIECDeciAmpsA, ctrl3ChIECName, productFriendlyName, alarmTripType, alarmTrigger, alarmInstance }
STATUS current
DESCRIPTION "Deciamps A Clear Trap"
::= { cmTrapPrefix 22508 }

cmCtrl3ChIECDeciAmpsPeakACLEAR NOTIFICATION-TYPE
OBJECTS { ctrl3ChIECDeciAmpsPeakA, ctrl3ChIECName, productFriendlyName, alarmTripType, alarmTrigger, alarmInstance }
STATUS current
DESCRIPTION "Deciamps Peak A Clear Trap"
::= { cmTrapPrefix 22509 }

cmCtrl3ChIECRealPowerACLEAR NOTIFICATION-TYPE
OBJECTS { ctrl3ChIECRealPowerA, ctrl3ChIECName, productFriendlyName, alarmTripType, alarmTrigger, alarmInstance }
STATUS current
DESCRIPTION "Real Power A Clear Trap"
::= { cmTrapPrefix 22510 }

cmCtrl3ChIECApparentPowerACLEAR NOTIFICATION-TYPE
OBJECTS { ctrl3ChIECApparentPowerA, ctrl3ChIECName, productFriendlyName, alarmTripType, alarmTrigger, alarmInstance }
STATUS current
DESCRIPTION "Apparent Power A Clear Trap"
::= { cmTrapPrefix 22511 }

cmCtrl3ChIECPowerFactorACLEAR NOTIFICATION-TYPE
OBJECTS { ctrl3ChIECPowerFactorA, ctrl3ChIECName, productFriendlyName, alarmTripType, alarmTrigger, alarmInstance }
STATUS current
DESCRIPTION "Power Factor A Clear Trap"
::= { cmTrapPrefix 22512 }

cmCtrl3ChIECkWattHrsBCLEAR NOTIFICATION-TYPE
OBJECTS { ctrl3ChIECkWattHrsB, ctrl3ChIECName, productFriendlyName, alarmTripType, alarmTrigger, alarmInstance }
STATUS current
DESCRIPTION "Kilo Watt Hours B Clear Trap"
::= { cmTrapPrefix 22513 }

cmCtrl3ChIECVoltsBCLEAR NOTIFICATION-TYPE
OBJECTS { ctrl3ChIECVoltsB, ctrl3ChIECName, productFriendlyName, alarmTripType, alarmTrigger, alarmInstance }
STATUS current
DESCRIPTION "Volts B Clear Trap"
::= { cmTrapPrefix 22514 }

cmCtrl3ChIECVoltPeakBCLEAR NOTIFICATION-TYPE
OBJECTS { ctrl3ChIECVoltPeakB, ctrl3ChIECName, productFriendlyName, alarmTripType, alarmTrigger, alarmInstance }
STATUS current
DESCRIPTION "Volts Peak B Clear Trap"
::= { cmTrapPrefix 22515 }

cmCtrl3ChIECDeciAmpsBCLEAR NOTIFICATION-TYPE
OBJECTS { ctrl3ChIECDeciAmpsB, ctrl3ChIECName, productFriendlyName, alarmTripType, alarmTrigger, alarmInstance }
STATUS current
DESCRIPTION "Deciamps B Clear Trap"
::= { cmTrapPrefix 22516 }

cmCtrl3ChIECDeciAmpsPeakBCLEAR NOTIFICATION-TYPE
OBJECTS { ctrl3ChIECDeciAmpsPeakB, ctrl3ChIECName, productFriendlyName, alarmTripType, alarmTrigger, alarmInstance }
STATUS current
DESCRIPTION "Deciamps Peak B Clear Trap"
::= { cmTrapPrefix 22517 }

cmCtrl3ChIECRealPowerBCLEAR NOTIFICATION-TYPE
OBJECTS { ctrl3ChIECRealPowerB, ctrl3ChIECName, productFriendlyName, alarmTripType, alarmTrigger, alarmInstance }
STATUS current
DESCRIPTION "Real Power B Clear Trap"
::= { cmTrapPrefix 22518 }

cmCtrl3ChIECApparentPowerBCLEAR NOTIFICATION-TYPE
OBJECTS { ctrl3ChIECApparentPowerB, ctrl3ChIECName, productFriendlyName, alarmTripType, alarmTrigger, alarmInstance }
STATUS current
DESCRIPTION "Apparent Power B Clear Trap"
::= { cmTrapPrefix 22519 }

cmCtrl3ChIECPowerFactorBCLEAR NOTIFICATION-TYPE
OBJECTS { ctrl3ChIECPowerFactorB, ctrl3ChIECName, productFriendlyName, alarmTripType, alarmTrigger, alarmInstance }
STATUS current
DESCRIPTION "Power Factor B Clear Trap"
::= { cmTrapPrefix 22520 }

cmCtrl3ChIECkWattHrsCCLEAR NOTIFICATION-TYPE
OBJECTS { ctrl3ChIECkWattHrsC, ctrl3ChIECName, productFriendlyName, alarmTripType, alarmTrigger, alarmInstance }
STATUS current
DESCRIPTION "Kilo Watt Hours C Clear Trap"
::= { cmTrapPrefix 22521 }

cmCtrl3ChIECVoltsCCLEAR NOTIFICATION-TYPE
OBJECTS { ctrl3ChIECVoltsC, ctrl3ChIECName, productFriendlyName, alarmTripType, alarmTrigger, alarmInstance }
STATUS current
DESCRIPTION "Volts C Clear Trap"
::= { cmTrapPrefix 22522 }

cmCtrl3ChIECVoltPeakCCLEAR NOTIFICATION-TYPE
OBJECTS { ctrl3ChIECVoltPeakC, ctrl3ChIECName, productFriendlyName, alarmTripType, alarmTrigger, alarmInstance }
STATUS current
DESCRIPTION "Volts Peak C Clear Trap"
::= { cmTrapPrefix 22523 }

cmCtrl3ChIECDeciAmpsCCLEAR NOTIFICATION-TYPE
OBJECTS { ctrl3ChIECDeciAmpsC, ctrl3ChIECName, productFriendlyName, alarmTripType, alarmTrigger, alarmInstance }
STATUS current
DESCRIPTION "Deciamps C Clear Trap"
::= { cmTrapPrefix 22524 }

cmCtrl3ChIECDeciAmpsPeakCCLEAR NOTIFICATION-TYPE
OBJECTS { ctrl3ChIECDeciAmpsPeakC, ctrl3ChIECName, productFriendlyName, alarmTripType, alarmTrigger, alarmInstance }
STATUS current
DESCRIPTION "Deciamps Peak C Clear Trap"
::= { cmTrapPrefix 22525 }

cmCtrl3ChIECRealPowerCCLEAR NOTIFICATION-TYPE
OBJECTS { ctrl3ChIECRealPowerC, ctrl3ChIECName, productFriendlyName, alarmTripType, alarmTrigger, alarmInstance }
STATUS current
DESCRIPTION "Real Power C Clear Trap"
::= { cmTrapPrefix 22526 }

cmCtrl3ChIECApparentPowerCCLEAR NOTIFICATION-TYPE
OBJECTS { ctrl3ChIECApparentPowerC, ctrl3ChIECName, productFriendlyName, alarmTripType, alarmTrigger, alarmInstance }
STATUS current
DESCRIPTION "Apparent Power C Clear Trap"
::= { cmTrapPrefix 22527 }

cmCtrl3ChIECPowerFactorCCLEAR NOTIFICATION-TYPE
OBJECTS { ctrl3ChIECPowerFactorC, ctrl3ChIECName, productFriendlyName, alarmTripType, alarmTrigger, alarmInstance }
STATUS current
DESCRIPTION "Power Factor C Clear Trap"
::= { cmTrapPrefix 22528 }

cmCtrl3ChIECkWattHrsTotalCLEAR NOTIFICATION-TYPE
OBJECTS { ctrl3ChIECkWattHrsTotal, ctrl3ChIECName, productFriendlyName, alarmTripType, alarmTrigger, alarmInstance }
STATUS current
DESCRIPTION "Kilo Watt Hours Total Clear Trap"
::= { cmTrapPrefix 22529 }

cmCtrl3ChIECRealPowerTotalCLEAR NOTIFICATION-TYPE
OBJECTS { ctrl3ChIECRealPowerTotal, ctrl3ChIECName, productFriendlyName, alarmTripType, alarmTrigger, alarmInstance }
STATUS current
DESCRIPTION "Watts Total Clear Trap"
::= { cmTrapPrefix 22530 }

cmClimateRelayTempCCLEAR NOTIFICATION-TYPE
OBJECTS { climateRelayTempC, climateRelayName, productFriendlyName, alarmTripType, temperaturePrecision, alarmTrigger, alarmInstance }
STATUS current
DESCRIPTION "Climate Relay Temperature Sensor Clear Trap"
::= { cmTrapPrefix 22605 }

cmClimateRelayTempFCLEAR NOTIFICATION-TYPE
OBJECTS { climateRelayTempF, climateRelayName, productFriendlyName, alarmTripType, temperaturePrecision, alarmTrigger, alarmInstance }
STATUS current
DESCRIPTION "Climate Relay Temperature Sensor Clear Trap"
::= { cmTrapPrefix 22606 }

cmClimateRelayIO1CLEAR NOTIFICATION-TYPE
OBJECTS { climateRelayIO1, climateRelayName, productFriendlyName, alarmTripType, alarmTrigger, alarmInstance }
STATUS current
DESCRIPTION "Climate Relay IO1 Sensor Clear Trap"
::= { cmTrapPrefix 22607 }

cmClimateRelayIO2CLEAR NOTIFICATION-TYPE
OBJECTS { climateRelayIO2, climateRelayName, productFriendlyName, alarmTripType, alarmTrigger, alarmInstance }
STATUS current
DESCRIPTION "Climate Relay IO2 Sensor Clear Trap"
::= { cmTrapPrefix 22608 }

cmClimateRelayIO3CLEAR NOTIFICATION-TYPE
OBJECTS { climateRelayIO3, climateRelayName, productFriendlyName, alarmTripType, alarmTrigger, alarmInstance }
STATUS current
DESCRIPTION "Climate Relay IO3 Sensor Clear Trap"
::= { cmTrapPrefix 22609 }

cmClimateRelayIO4CLEAR NOTIFICATION-TYPE
OBJECTS { climateRelayIO4, climateRelayName, productFriendlyName, alarmTripType, alarmTrigger, alarmInstance }
STATUS current
DESCRIPTION "Climate Relay IO4 Sensor Clear Trap"
::= { cmTrapPrefix 22610 }

cmClimateRelayIO5CLEAR NOTIFICATION-TYPE
OBJECTS { climateRelayIO5, climateRelayName, productFriendlyName, alarmTripType, alarmTrigger, alarmInstance }
STATUS current
DESCRIPTION "Climate Relay IO5 Sensor Clear Trap"
::= { cmTrapPrefix 22611 }

cmClimateRelayIO6CLEAR NOTIFICATION-TYPE
OBJECTS { climateRelayIO6, climateRelayName, productFriendlyName, alarmTripType, alarmTrigger, alarmInstance }
STATUS current
DESCRIPTION "Climate Relay IO6 Sensor Clear Trap"
::= { cmTrapPrefix 22612 }

cmAirSpeedSwitchSensorAirSpeedCLEAR NOTIFICATION-TYPE
OBJECTS { airSpeedSwitchSensorAirSpeed, airSpeedSwitchSensorName, productFriendlyName, alarmTripType, alarmTrigger, alarmInstance }
STATUS current
DESCRIPTION "Air Speed Switch Clear Trap"
::= { cmTrapPrefix 22805 }

cmPowerDMDeciAmps1CLEAR NOTIFICATION-TYPE
OBJECTS { powerDMDeciAmps1, powerDMName, productFriendlyName, alarmTripType, alarmTrigger, alarmInstance }
STATUS current
DESCRIPTION "DM48 Current Monitor Amps Clear Trap"
::= { cmTrapPrefix 139153 }

cmPowerDMDeciAmps2CLEAR NOTIFICATION-TYPE
OBJECTS { powerDMDeciAmps2, powerDMName, productFriendlyName, alarmTripType, alarmTrigger, alarmInstance }
STATUS current
DESCRIPTION "DM48 Current Monitor Amps Clear Trap"
::= { cmTrapPrefix 139154 }

cmPowerDMDeciAmps3CLEAR NOTIFICATION-TYPE
OBJECTS { powerDMDeciAmps3, powerDMName, productFriendlyName, alarmTripType, alarmTrigger, alarmInstance }
STATUS current
DESCRIPTION "DM48 Current Monitor Amps Clear Trap"
::= { cmTrapPrefix 139155 }

cmPowerDMDeciAmps4CLEAR NOTIFICATION-TYPE
OBJECTS { powerDMDeciAmps4, powerDMName, productFriendlyName, alarmTripType, alarmTrigger, alarmInstance }
STATUS current
DESCRIPTION "DM48 Current Monitor Amps Clear Trap"
::= { cmTrapPrefix 139156 }

cmPowerDMDeciAmps5CLEAR NOTIFICATION-TYPE
OBJECTS { powerDMDeciAmps5, powerDMName, productFriendlyName, alarmTripType, alarmTrigger, alarmInstance }
STATUS current
DESCRIPTION "DM48 Current Monitor Amps Clear Trap"
::= { cmTrapPrefix 139157 }

cmPowerDMDeciAmps6CLEAR NOTIFICATION-TYPE
OBJECTS { powerDMDeciAmps6, powerDMName, productFriendlyName, alarmTripType, alarmTrigger, alarmInstance }
STATUS current
DESCRIPTION "DM48 Current Monitor Amps Clear Trap"
::= { cmTrapPrefix 139158 }

cmPowerDMDeciAmps7CLEAR NOTIFICATION-TYPE
OBJECTS { powerDMDeciAmps7, powerDMName, productFriendlyName, alarmTripType, alarmTrigger, alarmInstance }
STATUS current
DESCRIPTION "DM48 Current Monitor Amps Clear Trap"
::= { cmTrapPrefix 139159 }

cmPowerDMDeciAmps8CLEAR NOTIFICATION-TYPE
OBJECTS { powerDMDeciAmps8, powerDMName, productFriendlyName, alarmTripType, alarmTrigger, alarmInstance }
STATUS current
DESCRIPTION "DM48 Current Monitor Amps Clear Trap"
::= { cmTrapPrefix 139160 }

cmPowerDMDeciAmps9CLEAR NOTIFICATION-TYPE
OBJECTS { powerDMDeciAmps9, powerDMName, productFriendlyName, alarmTripType, alarmTrigger, alarmInstance }
STATUS current
DESCRIPTION "DM48 Current Monitor Amps Clear Trap"
::= { cmTrapPrefix 139161 }

cmPowerDMDeciAmps10CLEAR NOTIFICATION-TYPE
OBJECTS { powerDMDeciAmps10, powerDMName, productFriendlyName, alarmTripType, alarmTrigger, alarmInstance }
STATUS current
DESCRIPTION "DM48 Current Monitor Amps Clear Trap"
::= { cmTrapPrefix 139162 }

cmPowerDMDeciAmps11CLEAR NOTIFICATION-TYPE
OBJECTS { powerDMDeciAmps11, powerDMName, productFriendlyName, alarmTripType, alarmTrigger, alarmInstance }
STATUS current
DESCRIPTION "DM48 Current Monitor Amps Clear Trap"
::= { cmTrapPrefix 139163 }

cmPowerDMDeciAmps12CLEAR NOTIFICATION-TYPE
OBJECTS { powerDMDeciAmps12, powerDMName, productFriendlyName, alarmTripType, alarmTrigger, alarmInstance }
STATUS current
DESCRIPTION "DM48 Current Monitor Amps Clear Trap"
::= { cmTrapPrefix 139164 }

cmPowerDMDeciAmps13CLEAR NOTIFICATION-TYPE
OBJECTS { powerDMDeciAmps13, powerDMName, productFriendlyName, alarmTripType, alarmTrigger, alarmInstance }
STATUS current
DESCRIPTION "DM48 Current Monitor Amps Clear Trap"
::= { cmTrapPrefix 139165 }

cmPowerDMDeciAmps14CLEAR NOTIFICATION-TYPE
OBJECTS { powerDMDeciAmps14, powerDMName, productFriendlyName, alarmTripType, alarmTrigger, alarmInstance }
STATUS current
DESCRIPTION "DM48 Current Monitor Amps Clear Trap"
::= { cmTrapPrefix 139166 }

cmPowerDMDeciAmps15CLEAR NOTIFICATION-TYPE
OBJECTS { powerDMDeciAmps15, powerDMName, productFriendlyName, alarmTripType, alarmTrigger, alarmInstance }
STATUS current
DESCRIPTION "DM48 Current Monitor Amps Clear Trap"
::= { cmTrapPrefix 139167 }

cmPowerDMDeciAmps16CLEAR NOTIFICATION-TYPE
OBJECTS { powerDMDeciAmps16, powerDMName, productFriendlyName, alarmTripType, alarmTrigger, alarmInstance }
STATUS current
DESCRIPTION "DM48 Current Monitor Amps Clear Trap"
::= { cmTrapPrefix 139168 }

cmPowerDMDeciAmps17CLEAR NOTIFICATION-TYPE
OBJECTS { powerDMDeciAmps17, powerDMName, productFriendlyName, alarmTripType, alarmTrigger, alarmInstance }
STATUS current
DESCRIPTION "DM48 Current Monitor Amps Clear Trap"
::= { cmTrapPrefix 139169 }

cmPowerDMDeciAmps18CLEAR NOTIFICATION-TYPE
OBJECTS { powerDMDeciAmps18, powerDMName, productFriendlyName, alarmTripType, alarmTrigger, alarmInstance }
STATUS current
DESCRIPTION "DM48 Current Monitor Amps Clear Trap"
::= { cmTrapPrefix 139170 }

cmPowerDMDeciAmps19CLEAR NOTIFICATION-TYPE
OBJECTS { powerDMDeciAmps19, powerDMName, productFriendlyName, alarmTripType, alarmTrigger, alarmInstance }
STATUS current
DESCRIPTION "DM48 Current Monitor Amps Clear Trap"
::= { cmTrapPrefix 139171 }

cmPowerDMDeciAmps20CLEAR NOTIFICATION-TYPE
OBJECTS { powerDMDeciAmps20, powerDMName, productFriendlyName, alarmTripType, alarmTrigger, alarmInstance }
STATUS current
DESCRIPTION "DM48 Current Monitor Amps Clear Trap"
::= { cmTrapPrefix 139172 }

cmPowerDMDeciAmps21CLEAR NOTIFICATION-TYPE
OBJECTS { powerDMDeciAmps21, powerDMName, productFriendlyName, alarmTripType, alarmTrigger, alarmInstance }
STATUS current
DESCRIPTION "DM48 Current Monitor Amps Clear Trap"
::= { cmTrapPrefix 139173 }

cmPowerDMDeciAmps22CLEAR NOTIFICATION-TYPE
OBJECTS { powerDMDeciAmps22, powerDMName, productFriendlyName, alarmTripType, alarmTrigger, alarmInstance }
STATUS current
DESCRIPTION "DM48 Current Monitor Amps Clear Trap"
::= { cmTrapPrefix 139174 }

cmPowerDMDeciAmps23CLEAR NOTIFICATION-TYPE
OBJECTS { powerDMDeciAmps23, powerDMName, productFriendlyName, alarmTripType, alarmTrigger, alarmInstance }
STATUS current
DESCRIPTION "DM48 Current Monitor Amps Clear Trap"
::= { cmTrapPrefix 139175 }

cmPowerDMDeciAmps24CLEAR NOTIFICATION-TYPE
OBJECTS { powerDMDeciAmps24, powerDMName, productFriendlyName, alarmTripType, alarmTrigger, alarmInstance }
STATUS current
DESCRIPTION "DM48 Current Monitor Amps Clear Trap"
::= { cmTrapPrefix 139176 }

cmPowerDMDeciAmps25CLEAR NOTIFICATION-TYPE
OBJECTS { powerDMDeciAmps25, powerDMName, productFriendlyName, alarmTripType, alarmTrigger, alarmInstance }
STATUS current
DESCRIPTION "DM48 Current Monitor Amps Clear Trap"
::= { cmTrapPrefix 139177 }

cmPowerDMDeciAmps26CLEAR NOTIFICATION-TYPE
OBJECTS { powerDMDeciAmps26, powerDMName, productFriendlyName, alarmTripType, alarmTrigger, alarmInstance }
STATUS current
DESCRIPTION "DM48 Current Monitor Amps Clear Trap"
::= { cmTrapPrefix 139178 }

cmPowerDMDeciAmps27CLEAR NOTIFICATION-TYPE
OBJECTS { powerDMDeciAmps27, powerDMName, productFriendlyName, alarmTripType, alarmTrigger, alarmInstance }
STATUS current
DESCRIPTION "DM48 Current Monitor Amps Clear Trap"
::= { cmTrapPrefix 139179 }

cmPowerDMDeciAmps28CLEAR NOTIFICATION-TYPE
OBJECTS { powerDMDeciAmps28, powerDMName, productFriendlyName, alarmTripType, alarmTrigger, alarmInstance }
STATUS current
DESCRIPTION "DM48 Current Monitor Amps Clear Trap"
::= { cmTrapPrefix 139180 }

cmPowerDMDeciAmps29CLEAR NOTIFICATION-TYPE
OBJECTS { powerDMDeciAmps29, powerDMName, productFriendlyName, alarmTripType, alarmTrigger, alarmInstance }
STATUS current
DESCRIPTION "DM48 Current Monitor Amps Clear Trap"
::= { cmTrapPrefix 139181 }

cmPowerDMDeciAmps30CLEAR NOTIFICATION-TYPE
OBJECTS { powerDMDeciAmps30, powerDMName, productFriendlyName, alarmTripType, alarmTrigger, alarmInstance }
STATUS current
DESCRIPTION "DM48 Current Monitor Amps Clear Trap"
::= { cmTrapPrefix 139182 }

cmPowerDMDeciAmps31CLEAR NOTIFICATION-TYPE
OBJECTS { powerDMDeciAmps31, powerDMName, productFriendlyName, alarmTripType, alarmTrigger, alarmInstance }
STATUS current
DESCRIPTION "DM48 Current Monitor Amps Clear Trap"
::= { cmTrapPrefix 139183 }

cmPowerDMDeciAmps32CLEAR NOTIFICATION-TYPE
OBJECTS { powerDMDeciAmps32, powerDMName, productFriendlyName, alarmTripType, alarmTrigger, alarmInstance }
STATUS current
DESCRIPTION "DM48 Current Monitor Amps Clear Trap"
::= { cmTrapPrefix 139184 }

cmPowerDMDeciAmps33CLEAR NOTIFICATION-TYPE
OBJECTS { powerDMDeciAmps33, powerDMName, productFriendlyName, alarmTripType, alarmTrigger, alarmInstance }
STATUS current
DESCRIPTION "DM48 Current Monitor Amps Clear Trap"
::= { cmTrapPrefix 139185 }

cmPowerDMDeciAmps34CLEAR NOTIFICATION-TYPE
OBJECTS { powerDMDeciAmps34, powerDMName, productFriendlyName, alarmTripType, alarmTrigger, alarmInstance }
STATUS current
DESCRIPTION "DM48 Current Monitor Amps Clear Trap"
::= { cmTrapPrefix 139186 }

cmPowerDMDeciAmps35CLEAR NOTIFICATION-TYPE
OBJECTS { powerDMDeciAmps35, powerDMName, productFriendlyName, alarmTripType, alarmTrigger, alarmInstance }
STATUS current
DESCRIPTION "DM48 Current Monitor Amps Clear Trap"
::= { cmTrapPrefix 139187 }

cmPowerDMDeciAmps36CLEAR NOTIFICATION-TYPE
OBJECTS { powerDMDeciAmps36, powerDMName, productFriendlyName, alarmTripType, alarmTrigger, alarmInstance }
STATUS current
DESCRIPTION "DM48 Current Monitor Amps Clear Trap"
::= { cmTrapPrefix 139188 }

cmPowerDMDeciAmps37CLEAR NOTIFICATION-TYPE
OBJECTS { powerDMDeciAmps37, powerDMName, productFriendlyName, alarmTripType, alarmTrigger, alarmInstance }
STATUS current
DESCRIPTION "DM48 Current Monitor Amps Clear Trap"
::= { cmTrapPrefix 139189 }

cmPowerDMDeciAmps38CLEAR NOTIFICATION-TYPE
OBJECTS { powerDMDeciAmps38, powerDMName, productFriendlyName, alarmTripType, alarmTrigger, alarmInstance }
STATUS current
DESCRIPTION "DM48 Current Monitor Amps Clear Trap"
::= { cmTrapPrefix 139190 }

cmPowerDMDeciAmps39CLEAR NOTIFICATION-TYPE
OBJECTS { powerDMDeciAmps39, powerDMName, productFriendlyName, alarmTripType, alarmTrigger, alarmInstance }
STATUS current
DESCRIPTION "DM48 Current Monitor Amps Clear Trap"
::= { cmTrapPrefix 139191 }

cmPowerDMDeciAmps40CLEAR NOTIFICATION-TYPE
OBJECTS { powerDMDeciAmps40, powerDMName, productFriendlyName, alarmTripType, alarmTrigger, alarmInstance }
STATUS current
DESCRIPTION "DM48 Current Monitor Amps Clear Trap"
::= { cmTrapPrefix 139192 }

cmPowerDMDeciAmps41CLEAR NOTIFICATION-TYPE
OBJECTS { powerDMDeciAmps41, powerDMName, productFriendlyName, alarmTripType, alarmTrigger, alarmInstance }
STATUS current
DESCRIPTION "DM48 Current Monitor Amps Clear Trap"
::= { cmTrapPrefix 139193 }

cmPowerDMDeciAmps42CLEAR NOTIFICATION-TYPE
OBJECTS { powerDMDeciAmps42, powerDMName, productFriendlyName, alarmTripType, alarmTrigger, alarmInstance }
STATUS current
DESCRIPTION "DM48 Current Monitor Amps Clear Trap"
::= { cmTrapPrefix 139194 }

cmPowerDMDeciAmps43CLEAR NOTIFICATION-TYPE
OBJECTS { powerDMDeciAmps43, powerDMName, productFriendlyName, alarmTripType, alarmTrigger, alarmInstance }
STATUS current
DESCRIPTION "DM48 Current Monitor Amps Clear Trap"
::= { cmTrapPrefix 139195 }

cmPowerDMDeciAmps44CLEAR NOTIFICATION-TYPE
OBJECTS { powerDMDeciAmps44, powerDMName, productFriendlyName, alarmTripType, alarmTrigger, alarmInstance }
STATUS current
DESCRIPTION "DM48 Current Monitor Amps Clear Trap"
::= { cmTrapPrefix 139196 }

cmPowerDMDeciAmps45CLEAR NOTIFICATION-TYPE
OBJECTS { powerDMDeciAmps45, powerDMName, productFriendlyName, alarmTripType, alarmTrigger, alarmInstance }
STATUS current
DESCRIPTION "DM48 Current Monitor Amps Clear Trap"
::= { cmTrapPrefix 139197 }

cmPowerDMDeciAmps46CLEAR NOTIFICATION-TYPE
OBJECTS { powerDMDeciAmps46, powerDMName, productFriendlyName, alarmTripType, alarmTrigger, alarmInstance }
STATUS current
DESCRIPTION "DM48 Current Monitor Amps Clear Trap"
::= { cmTrapPrefix 139198 }

cmPowerDMDeciAmps47CLEAR NOTIFICATION-TYPE
OBJECTS { powerDMDeciAmps47, powerDMName, productFriendlyName, alarmTripType, alarmTrigger, alarmInstance }
STATUS current
DESCRIPTION "DM48 Current Monitor Amps Clear Trap"
::= { cmTrapPrefix 139199 }

cmPowerDMDeciAmps48CLEAR NOTIFICATION-TYPE
OBJECTS { powerDMDeciAmps48, powerDMName, productFriendlyName, alarmTripType, alarmTrigger, alarmInstance }
STATUS current
DESCRIPTION "DM48 Current Monitor Amps Clear Trap"
::= { cmTrapPrefix 139200 }

cmIoExpanderIO1CLEAR NOTIFICATION-TYPE
OBJECTS { ioExpanderIO1, ioExpanderName, productFriendlyName, alarmTripType, alarmTrigger, alarmInstance }
STATUS current
DESCRIPTION "Climate Relay IO1 Sensor Clear Trap"
::= { cmTrapPrefix 23037 }

cmIoExpanderIO2CLEAR NOTIFICATION-TYPE
OBJECTS { ioExpanderIO2, ioExpanderName, productFriendlyName, alarmTripType, alarmTrigger, alarmInstance }
STATUS current
DESCRIPTION "Climate Relay IO2 Sensor Clear Trap"
::= { cmTrapPrefix 23038 }

cmIoExpanderIO3CLEAR NOTIFICATION-TYPE
OBJECTS { ioExpanderIO3, ioExpanderName, productFriendlyName, alarmTripType, alarmTrigger, alarmInstance }
STATUS current
DESCRIPTION "Climate Relay IO3 Sensor Clear Trap"
::= { cmTrapPrefix 23039 }

cmIoExpanderIO4CLEAR NOTIFICATION-TYPE
OBJECTS { ioExpanderIO4, ioExpanderName, productFriendlyName, alarmTripType, alarmTrigger, alarmInstance }
STATUS current
DESCRIPTION "Climate Relay IO4 Sensor Clear Trap"
::= { cmTrapPrefix 23040 }

cmIoExpanderIO5CLEAR NOTIFICATION-TYPE
OBJECTS { ioExpanderIO5, ioExpanderName, productFriendlyName, alarmTripType, alarmTrigger, alarmInstance }
STATUS current
DESCRIPTION "Climate Relay IO5 Sensor Clear Trap"
::= { cmTrapPrefix 23041 }

cmIoExpanderIO6CLEAR NOTIFICATION-TYPE
OBJECTS { ioExpanderIO6, ioExpanderName, productFriendlyName, alarmTripType, alarmTrigger, alarmInstance }
STATUS current
DESCRIPTION "Climate Relay IO6 Sensor Clear Trap"
::= { cmTrapPrefix 23042 }

cmIoExpanderIO7CLEAR NOTIFICATION-TYPE
OBJECTS { ioExpanderIO7, ioExpanderName, productFriendlyName, alarmTripType, alarmTrigger, alarmInstance }
STATUS current
DESCRIPTION "Climate Relay IO7 Sensor Clear Trap"
::= { cmTrapPrefix 23043 }

cmIoExpanderIO8CLEAR NOTIFICATION-TYPE
OBJECTS { ioExpanderIO8, ioExpanderName, productFriendlyName, alarmTripType, alarmTrigger, alarmInstance }
STATUS current
DESCRIPTION "Climate Relay IO8 Sensor Clear Trap"
::= { cmTrapPrefix 23044 }

cmIoExpanderIO9CLEAR NOTIFICATION-TYPE
OBJECTS { ioExpanderIO9, ioExpanderName, productFriendlyName, alarmTripType, alarmTrigger, alarmInstance }
STATUS current
DESCRIPTION "Climate Relay IO9 Sensor Clear Trap"
::= { cmTrapPrefix 23045 }

cmIoExpanderIO10CLEAR NOTIFICATION-TYPE
OBJECTS { ioExpanderIO10, ioExpanderName, productFriendlyName, alarmTripType, alarmTrigger, alarmInstance }
STATUS current
DESCRIPTION "Climate Relay IO10 Sensor Clear Trap"
::= { cmTrapPrefix 23046 }

cmIoExpanderIO11CLEAR NOTIFICATION-TYPE
OBJECTS { ioExpanderIO11, ioExpanderName, productFriendlyName, alarmTripType, alarmTrigger, alarmInstance }
STATUS current
DESCRIPTION "Climate Relay IO11 Sensor Clear Trap"
::= { cmTrapPrefix 23047 }

cmIoExpanderIO12CLEAR NOTIFICATION-TYPE
OBJECTS { ioExpanderIO12, ioExpanderName, productFriendlyName, alarmTripType, alarmTrigger, alarmInstance }
STATUS current
DESCRIPTION "Climate Relay IO12 Sensor Clear Trap"
::= { cmTrapPrefix 23048 }

cmIoExpanderIO13CLEAR NOTIFICATION-TYPE
OBJECTS { ioExpanderIO13, ioExpanderName, productFriendlyName, alarmTripType, alarmTrigger, alarmInstance }
STATUS current
DESCRIPTION "Climate Relay IO13 Sensor Clear Trap"
::= { cmTrapPrefix 23049 }

cmIoExpanderIO14CLEAR NOTIFICATION-TYPE
OBJECTS { ioExpanderIO14, ioExpanderName, productFriendlyName, alarmTripType, alarmTrigger, alarmInstance }
STATUS current
DESCRIPTION "Climate Relay IO14 Sensor Clear Trap"
::= { cmTrapPrefix 23050 }

cmIoExpanderIO15CLEAR NOTIFICATION-TYPE
OBJECTS { ioExpanderIO15, ioExpanderName, productFriendlyName, alarmTripType, alarmTrigger, alarmInstance }
STATUS current
DESCRIPTION "Climate Relay IO15 Sensor Clear Trap"
::= { cmTrapPrefix 23051 }

cmIoExpanderIO16CLEAR NOTIFICATION-TYPE
OBJECTS { ioExpanderIO16, ioExpanderName, productFriendlyName, alarmTripType, alarmTrigger, alarmInstance }
STATUS current
DESCRIPTION "Climate Relay IO16 Sensor Clear Trap"
::= { cmTrapPrefix 23052 }

cmIoExpanderIO17CLEAR NOTIFICATION-TYPE
OBJECTS { ioExpanderIO17, ioExpanderName, productFriendlyName, alarmTripType, alarmTrigger, alarmInstance }
STATUS current
DESCRIPTION "Climate Relay IO17 Sensor Clear Trap"
::= { cmTrapPrefix 23053 }

cmIoExpanderIO18CLEAR NOTIFICATION-TYPE
OBJECTS { ioExpanderIO18, ioExpanderName, productFriendlyName, alarmTripType, alarmTrigger, alarmInstance }
STATUS current
DESCRIPTION "Climate Relay IO18 Sensor Clear Trap"
::= { cmTrapPrefix 23054 }

cmIoExpanderIO19CLEAR NOTIFICATION-TYPE
OBJECTS { ioExpanderIO19, ioExpanderName, productFriendlyName, alarmTripType, alarmTrigger, alarmInstance }
STATUS current
DESCRIPTION "Climate Relay IO19 Sensor Clear Trap"
::= { cmTrapPrefix 23055 }

cmIoExpanderIO20CLEAR NOTIFICATION-TYPE
OBJECTS { ioExpanderIO20, ioExpanderName, productFriendlyName, alarmTripType, alarmTrigger, alarmInstance }
STATUS current
DESCRIPTION "Climate Relay IO20 Sensor Clear Trap"
::= { cmTrapPrefix 23056 }

cmIoExpanderIO21CLEAR NOTIFICATION-TYPE
OBJECTS { ioExpanderIO21, ioExpanderName, productFriendlyName, alarmTripType, alarmTrigger, alarmInstance }
STATUS current
DESCRIPTION "Climate Relay IO21 Sensor Clear Trap"
::= { cmTrapPrefix 23057 }

cmIoExpanderIO22CLEAR NOTIFICATION-TYPE
OBJECTS { ioExpanderIO22, ioExpanderName, productFriendlyName, alarmTripType, alarmTrigger, alarmInstance }
STATUS current
DESCRIPTION "Climate Relay IO22 Sensor Clear Trap"
::= { cmTrapPrefix 23058 }

cmIoExpanderIO23CLEAR NOTIFICATION-TYPE
OBJECTS { ioExpanderIO23, ioExpanderName, productFriendlyName, alarmTripType, alarmTrigger, alarmInstance }
STATUS current
DESCRIPTION "Climate Relay IO23 Sensor Clear Trap"
::= { cmTrapPrefix 23059 }

cmIoExpanderIO24CLEAR NOTIFICATION-TYPE
OBJECTS { ioExpanderIO24, ioExpanderName, productFriendlyName, alarmTripType, alarmTrigger, alarmInstance }
STATUS current
DESCRIPTION "Climate Relay IO24 Sensor Clear Trap"
::= { cmTrapPrefix 23060 }

cmIoExpanderIO25CLEAR NOTIFICATION-TYPE
OBJECTS { ioExpanderIO25, ioExpanderName, productFriendlyName, alarmTripType, alarmTrigger, alarmInstance }
STATUS current
DESCRIPTION "Climate Relay IO25 Sensor Clear Trap"
::= { cmTrapPrefix 23061 }

cmIoExpanderIO26CLEAR NOTIFICATION-TYPE
OBJECTS { ioExpanderIO26, ioExpanderName, productFriendlyName, alarmTripType, alarmTrigger, alarmInstance }
STATUS current
DESCRIPTION "Climate Relay IO26 Sensor Clear Trap"
::= { cmTrapPrefix 23062 }

cmIoExpanderIO27CLEAR NOTIFICATION-TYPE
OBJECTS { ioExpanderIO27, ioExpanderName, productFriendlyName, alarmTripType, alarmTrigger, alarmInstance }
STATUS current
DESCRIPTION "Climate Relay IO27 Sensor Clear Trap"
::= { cmTrapPrefix 23063 }

cmIoExpanderIO28CLEAR NOTIFICATION-TYPE
OBJECTS { ioExpanderIO28, ioExpanderName, productFriendlyName, alarmTripType, alarmTrigger, alarmInstance }
STATUS current
DESCRIPTION "Climate Relay IO28 Sensor Clear Trap"
::= { cmTrapPrefix 23064 }

cmIoExpanderIO29CLEAR NOTIFICATION-TYPE
OBJECTS { ioExpanderIO29, ioExpanderName, productFriendlyName, alarmTripType, alarmTrigger, alarmInstance }
STATUS current
DESCRIPTION "Climate Relay IO29 Sensor Clear Trap"
::= { cmTrapPrefix 23065 }

cmIoExpanderIO30CLEAR NOTIFICATION-TYPE
OBJECTS { ioExpanderIO30, ioExpanderName, productFriendlyName, alarmTripType, alarmTrigger, alarmInstance }
STATUS current
DESCRIPTION "Climate Relay IO30 Sensor Clear Trap"
::= { cmTrapPrefix 23066 }

cmIoExpanderIO31CLEAR NOTIFICATION-TYPE
OBJECTS { ioExpanderIO31, ioExpanderName, productFriendlyName, alarmTripType, alarmTrigger, alarmInstance }
STATUS current
DESCRIPTION "Climate Relay IO31 Sensor Clear Trap"
::= { cmTrapPrefix 23067 }

cmIoExpanderIO32CLEAR NOTIFICATION-TYPE
OBJECTS { ioExpanderIO32, ioExpanderName, productFriendlyName, alarmTripType, alarmTrigger, alarmInstance }
STATUS current
DESCRIPTION "Climate Relay IO32 Sensor Clear Trap"
::= { cmTrapPrefix 23068 }

cmT3hdSensorIntTempCCLEAR NOTIFICATION-TYPE
OBJECTS { t3hdSensorIntTempC, t3hdSensorName, productFriendlyName, alarmTripType, temperaturePrecision, alarmTrigger, alarmInstance }
STATUS current
DESCRIPTION "T3HD - Internal Temperature C Clear Trap"
::= { cmTrapPrefix 23106 }

cmT3hdSensorIntTempFCLEAR NOTIFICATION-TYPE
OBJECTS { t3hdSensorIntTempF, t3hdSensorName, productFriendlyName, alarmTripType, temperaturePrecision, alarmTrigger, alarmInstance }
STATUS current
DESCRIPTION "T3HD - Internal Temperature F Clear Trap"
::= { cmTrapPrefix 23107 }

cmT3hdSensorIntHumidityCLEAR NOTIFICATION-TYPE
OBJECTS { t3hdSensorIntHumidity, t3hdSensorName, productFriendlyName, alarmTripType, alarmTrigger, alarmInstance }
STATUS current
DESCRIPTION "T3HD - Internal Humidity Clear Trap"
::= { cmTrapPrefix 23108 }

cmT3hdSensorIntDewPointCCLEAR NOTIFICATION-TYPE
OBJECTS { t3hdSensorIntDewPointC, t3hdSensorName, productFriendlyName, alarmTripType, temperaturePrecision, alarmTrigger, alarmInstance }
STATUS current
DESCRIPTION "T3HD - Internal Dew Point C Clear Trap"
::= { cmTrapPrefix 23109 }

cmT3hdSensorIntDewPointFCLEAR NOTIFICATION-TYPE
OBJECTS { t3hdSensorIntDewPointF, t3hdSensorName, productFriendlyName, alarmTripType, temperaturePrecision, alarmTrigger, alarmInstance }
STATUS current
DESCRIPTION "T3HD - Internal Dew Point F Clear Trap"
::= { cmTrapPrefix 23110 }

cmT3hdSensorExt1TempCCLEAR NOTIFICATION-TYPE
OBJECTS { t3hdSensorExt1TempC, t3hdSensorName, productFriendlyName, alarmTripType, temperaturePrecision, alarmTrigger, alarmInstance }
STATUS current
DESCRIPTION "T3HD - External 1 Temperature C Clear Trap"
::= { cmTrapPrefix 23113 }

cmT3hdSensorExt1TempFCLEAR NOTIFICATION-TYPE
OBJECTS { t3hdSensorExt1TempF, t3hdSensorName, productFriendlyName, alarmTripType, temperaturePrecision, alarmTrigger, alarmInstance }
STATUS current
DESCRIPTION "T3HD - External 1 Temperature F Clear Trap"
::= { cmTrapPrefix 23114 }

cmT3hdSensorExt2TempCCLEAR NOTIFICATION-TYPE
OBJECTS { t3hdSensorExt2TempC, t3hdSensorName, productFriendlyName, alarmTripType, temperaturePrecision, alarmTrigger, alarmInstance }
STATUS current
DESCRIPTION "T3HD - External 2 Temperature C Clear Trap"
::= { cmTrapPrefix 23117 }

cmT3hdSensorExt2TempFCLEAR NOTIFICATION-TYPE
OBJECTS { t3hdSensorExt2TempF, t3hdSensorName, productFriendlyName, alarmTripType, temperaturePrecision, alarmTrigger, alarmInstance }
STATUS current
DESCRIPTION "T3HD - External 2 Temperature F Clear Trap"
::= { cmTrapPrefix 23118 }

cmThdSensorTempCCLEAR NOTIFICATION-TYPE
OBJECTS { thdSensorTempC, thdSensorName, productFriendlyName, alarmTripType, temperaturePrecision, alarmTrigger, alarmInstance }
STATUS current
DESCRIPTION "THD - Temperature C Clear Trap"
::= { cmTrapPrefix 23205 }

cmThdSensorTempFCLEAR NOTIFICATION-TYPE
OBJECTS { thdSensorTempF, thdSensorName, productFriendlyName, alarmTripType, temperaturePrecision, alarmTrigger, alarmInstance }
STATUS current
DESCRIPTION "THD - Temperature F Clear Trap"
::= { cmTrapPrefix 23206 }

cmThdSensorHumidityCLEAR NOTIFICATION-TYPE
OBJECTS { thdSensorHumidity, thdSensorName, productFriendlyName, alarmTripType, alarmTrigger, alarmInstance }
STATUS current
DESCRIPTION "THD - Humidity Clear Trap"
::= { cmTrapPrefix 23207 }

cmThdSensorDewPointCCLEAR NOTIFICATION-TYPE
OBJECTS { thdSensorDewPointC, thdSensorName, productFriendlyName, alarmTripType, temperaturePrecision, alarmTrigger, alarmInstance }
STATUS current
DESCRIPTION "THD - Dew Point C Clear Trap"
::= { cmTrapPrefix 23208 }

cmThdSensorDewPointFCLEAR NOTIFICATION-TYPE
OBJECTS { thdSensorDewPointF, thdSensorName, productFriendlyName, alarmTripType, temperaturePrecision, alarmTrigger, alarmInstance }
STATUS current
DESCRIPTION "THD - Dew Point F Clear Trap"
::= { cmTrapPrefix 23209 }

cmPos60VdcSensorVoltageCLEAR NOTIFICATION-TYPE
OBJECTS { pos60VdcSensorVoltage, pos60VdcSensorName, productFriendlyName, alarmTripType, alarmTrigger, alarmInstance }
STATUS current
DESCRIPTION "60Vdc Sensor Clear Trap"
::= { cmTrapPrefix 23305 }

cmCtrl2CirTotkWattHrsTotCLEAR NOTIFICATION-TYPE
OBJECTS { ctrl2CirTotkWattHrsTot, ctrl2CirTotName, productFriendlyName, alarmTripType, alarmTrigger, alarmInstance }
STATUS current
DESCRIPTION "Kilo Watt Hours Total Clear Trap"
::= { cmTrapPrefix 23405 }

cmCtrl2CirTotVoltsTotCLEAR NOTIFICATION-TYPE
OBJECTS { ctrl2CirTotVoltsTot, ctrl2CirTotName, productFriendlyName, alarmTripType, alarmTrigger, alarmInstance }
STATUS current
DESCRIPTION "Volts Total Clear Trap"
::= { cmTrapPrefix 23406 }

cmCtrl2CirTotVoltPeakTotCLEAR NOTIFICATION-TYPE
OBJECTS { ctrl2CirTotVoltPeakTot, ctrl2CirTotName, productFriendlyName, alarmTripType, alarmTrigger, alarmInstance }
STATUS current
DESCRIPTION "Volts Peak Total Clear Trap"
::= { cmTrapPrefix 23407 }

cmCtrl2CirTotDeciAmpsTotCLEAR NOTIFICATION-TYPE
OBJECTS { ctrl2CirTotDeciAmpsTot, ctrl2CirTotName, productFriendlyName, alarmTripType, alarmTrigger, alarmInstance }
STATUS current
DESCRIPTION "Deciamps Total Clear Trap"
::= { cmTrapPrefix 23408 }

cmCtrl2CirTotDeciAmpsPeakTotCLEAR NOTIFICATION-TYPE
OBJECTS { ctrl2CirTotDeciAmpsPeakTot, ctrl2CirTotName, productFriendlyName, alarmTripType, alarmTrigger, alarmInstance }
STATUS current
DESCRIPTION "Deciamps Peak Total Clear Trap"
::= { cmTrapPrefix 23409 }

cmCtrl2CirTotRealPowerTotCLEAR NOTIFICATION-TYPE
OBJECTS { ctrl2CirTotRealPowerTot, ctrl2CirTotName, productFriendlyName, alarmTripType, alarmTrigger, alarmInstance }
STATUS current
DESCRIPTION "Real Power Total Clear Trap"
::= { cmTrapPrefix 23410 }

cmCtrl2CirTotApparentPowerTotCLEAR NOTIFICATION-TYPE
OBJECTS { ctrl2CirTotApparentPowerTot, ctrl2CirTotName, productFriendlyName, alarmTripType, alarmTrigger, alarmInstance }
STATUS current
DESCRIPTION "Apparent Power Total Clear Trap"
::= { cmTrapPrefix 23411 }

cmCtrl2CirTotPowerFactorTotCLEAR NOTIFICATION-TYPE
OBJECTS { ctrl2CirTotPowerFactorTot, ctrl2CirTotName, productFriendlyName, alarmTripType, alarmTrigger, alarmInstance }
STATUS current
DESCRIPTION "Power Factor Total Clear Trap"
::= { cmTrapPrefix 23412 }

cmCtrl2CirTotkWattHrsACLEAR NOTIFICATION-TYPE
OBJECTS { ctrl2CirTotkWattHrsA, ctrl2CirTotName, productFriendlyName, alarmTripType, alarmTrigger, alarmInstance }
STATUS current
DESCRIPTION "Kilo Watt Hours A Clear Trap"
::= { cmTrapPrefix 23413 }

cmCtrl2CirTotVoltsACLEAR NOTIFICATION-TYPE
OBJECTS { ctrl2CirTotVoltsA, ctrl2CirTotName, productFriendlyName, alarmTripType, alarmTrigger, alarmInstance }
STATUS current
DESCRIPTION "Volts A Clear Trap"
::= { cmTrapPrefix 23414 }

cmCtrl2CirTotVoltPeakACLEAR NOTIFICATION-TYPE
OBJECTS { ctrl2CirTotVoltPeakA, ctrl2CirTotName, productFriendlyName, alarmTripType, alarmTrigger, alarmInstance }
STATUS current
DESCRIPTION "Volts Peak A Clear Trap"
::= { cmTrapPrefix 23415 }

cmCtrl2CirTotDeciAmpsACLEAR NOTIFICATION-TYPE
OBJECTS { ctrl2CirTotDeciAmpsA, ctrl2CirTotName, productFriendlyName, alarmTripType, alarmTrigger, alarmInstance }
STATUS current
DESCRIPTION "Deciamps A Clear Trap"
::= { cmTrapPrefix 23416 }

cmCtrl2CirTotDeciAmpsPeakACLEAR NOTIFICATION-TYPE
OBJECTS { ctrl2CirTotDeciAmpsPeakA, ctrl2CirTotName, productFriendlyName, alarmTripType, alarmTrigger, alarmInstance }
STATUS current
DESCRIPTION "Deciamps Peak A Clear Trap"
::= { cmTrapPrefix 23417 }

cmCtrl2CirTotRealPowerACLEAR NOTIFICATION-TYPE
OBJECTS { ctrl2CirTotRealPowerA, ctrl2CirTotName, productFriendlyName, alarmTripType, alarmTrigger, alarmInstance }
STATUS current
DESCRIPTION "Real Power A Clear Trap"
::= { cmTrapPrefix 23418 }

cmCtrl2CirTotApparentPowerACLEAR NOTIFICATION-TYPE
OBJECTS { ctrl2CirTotApparentPowerA, ctrl2CirTotName, productFriendlyName, alarmTripType, alarmTrigger, alarmInstance }
STATUS current
DESCRIPTION "Apparent Power A Clear Trap"
::= { cmTrapPrefix 23419 }

cmCtrl2CirTotPowerFactorACLEAR NOTIFICATION-TYPE
OBJECTS { ctrl2CirTotPowerFactorA, ctrl2CirTotName, productFriendlyName, alarmTripType, alarmTrigger, alarmInstance }
STATUS current
DESCRIPTION "Power Factor A Clear Trap"
::= { cmTrapPrefix 23420 }

cmCtrl2CirTotkWattHrsBCLEAR NOTIFICATION-TYPE
OBJECTS { ctrl2CirTotkWattHrsB, ctrl2CirTotName, productFriendlyName, alarmTripType, alarmTrigger, alarmInstance }
STATUS current
DESCRIPTION "Kilo Watt Hours B Clear Trap"
::= { cmTrapPrefix 23421 }

cmCtrl2CirTotVoltsBCLEAR NOTIFICATION-TYPE
OBJECTS { ctrl2CirTotVoltsB, ctrl2CirTotName, productFriendlyName, alarmTripType, alarmTrigger, alarmInstance }
STATUS current
DESCRIPTION "Volts B Clear Trap"
::= { cmTrapPrefix 23422 }

cmCtrl2CirTotVoltPeakBCLEAR NOTIFICATION-TYPE
OBJECTS { ctrl2CirTotVoltPeakB, ctrl2CirTotName, productFriendlyName, alarmTripType, alarmTrigger, alarmInstance }
STATUS current
DESCRIPTION "Volts Peak B Clear Trap"
::= { cmTrapPrefix 23423 }

cmCtrl2CirTotDeciAmpsBCLEAR NOTIFICATION-TYPE
OBJECTS { ctrl2CirTotDeciAmpsB, ctrl2CirTotName, productFriendlyName, alarmTripType, alarmTrigger, alarmInstance }
STATUS current
DESCRIPTION "Deciamps B Clear Trap"
::= { cmTrapPrefix 23424 }

cmCtrl2CirTotDeciAmpsPeakBCLEAR NOTIFICATION-TYPE
OBJECTS { ctrl2CirTotDeciAmpsPeakB, ctrl2CirTotName, productFriendlyName, alarmTripType, alarmTrigger, alarmInstance }
STATUS current
DESCRIPTION "Deciamps Peak B Clear Trap"
::= { cmTrapPrefix 23425 }

cmCtrl2CirTotRealPowerBCLEAR NOTIFICATION-TYPE
OBJECTS { ctrl2CirTotRealPowerB, ctrl2CirTotName, productFriendlyName, alarmTripType, alarmTrigger, alarmInstance }
STATUS current
DESCRIPTION "Real Power B Clear Trap"
::= { cmTrapPrefix 23426 }

cmCtrl2CirTotApparentPowerBCLEAR NOTIFICATION-TYPE
OBJECTS { ctrl2CirTotApparentPowerB, ctrl2CirTotName, productFriendlyName, alarmTripType, alarmTrigger, alarmInstance }
STATUS current
DESCRIPTION "Apparent Power B Clear Trap"
::= { cmTrapPrefix 23427 }

cmCtrl2CirTotPowerFactorBCLEAR NOTIFICATION-TYPE
OBJECTS { ctrl2CirTotPowerFactorB, ctrl2CirTotName, productFriendlyName, alarmTripType, alarmTrigger, alarmInstance }
STATUS current
DESCRIPTION "Power Factor B Clear Trap"
::= { cmTrapPrefix 23428 }

cmSc10ControlModeCLEAR NOTIFICATION-TYPE
OBJECTS { sc10ControlMode, sc10Name, productFriendlyName, alarmTripType, alarmTrigger, alarmInstance }
STATUS current
DESCRIPTION "SC10 Control Mode Sensor Clear"
::= { cmTrapPrefix 23505 }

cmSc10SetpointCCLEAR NOTIFICATION-TYPE
OBJECTS { sc10SetpointC, sc10Name, productFriendlyName, alarmTripType, alarmTrigger, alarmInstance }
STATUS current
DESCRIPTION "SC10 Temp Set Point Sensor Clear"
::= { cmTrapPrefix 23506 }

cmSc10SetpointFCLEAR NOTIFICATION-TYPE
OBJECTS { sc10SetpointF, sc10Name, productFriendlyName, alarmTripType, alarmTrigger, alarmInstance }
STATUS current
DESCRIPTION "SC10 Temp Set Point Sensor Clear"
::= { cmTrapPrefix 23507 }

cmSc10TempCCLEAR NOTIFICATION-TYPE
OBJECTS { sc10TempC, sc10Name, productFriendlyName, alarmTripType, temperaturePrecision, alarmTrigger, alarmInstance }
STATUS current
DESCRIPTION "SC10 Internal Temp Sensor Clear"
::= { cmTrapPrefix 23508 }

cmSc10TempFCLEAR NOTIFICATION-TYPE
OBJECTS { sc10TempF, sc10Name, productFriendlyName, alarmTripType, temperaturePrecision, alarmTrigger, alarmInstance }
STATUS current
DESCRIPTION "SC10 Internal Temp Sensor Clear"
::= { cmTrapPrefix 23509 }

cmSc10CapacityCLEAR NOTIFICATION-TYPE
OBJECTS { sc10Capacity, sc10Name, productFriendlyName, alarmTripType, alarmTrigger, alarmInstance }
STATUS current
DESCRIPTION "SC10 Fan Speed Sensor Clear"
::= { cmTrapPrefix 23510 }

END
