-- ****************************************************************************
--                             InnovxCascadeLiu.mib
-- ****************************************************************************

-- INNOVX Access Probe - Cascade Port Line Interface Unit MIB


-- Copyright 1999 General DataComm Inc., All Rights Reserved.

-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.

-- This Specification is supplied "AS IS," and GDC makes no warranty,
-- either expressed or implied, as to the use operation, condition, or
-- performance of the Specification.


-- Objects in this mib may be controlled or influenced by objects
-- in the Innovx Access Probe Core mib: InnovxCore.mib



--
-- ****************************************************************************
--                        Revision History
-- ****************************************************************************

-- Version   Date	Name/Comments

-- 1.00A     24-Feb-99	S. Veillette
--			1) Initial revision

-- 1.00B     23-Mar-99  S. Veillette
--                      1) Modify alarm window and threshold values
--                         for BPV, CRC and LAD alarms.
--
-- 1.00C     3-Aug-99   A. Limoncelli
--                      1) added DSU config, diagnostics, statistics sections
--
--                      2) changed cascadeDS0Fmt to read-only
--
--                      3) removed cascadeEsfMode, cascadeDS0AllocationScheme,
--			   cascadeDS0Fmt, cascadeStartingDS0, 
--			   cascadeLIUAggregateRate,cascadeInbandLoop
-- 			4) removed stats.
--
--			5) removed Tx/Rx frame counts
--
-- 1.00D     11-Nov-99   A. Limoncelli
--                      1) added cascadePortStatus
--
-- 1.00E     16-Dec-99   A. Limoncelli
--                      1) added cascadeDropAndInsertTable
--			2) changed values between WEBFLAG for cascadeDropAndInsert
--
-- ****************************************************************************




--
-- ****************************************************************************
--                       mib definitions begin
-- ****************************************************************************


INNOVX-CASCADE-LIU-MIB DEFINITIONS ::= BEGIN

IMPORTS	
Gauge			FROM RFC1155-SMI
OBJECT-TYPE		FROM RFC-1212
DisplayString		FROM RFC1213-MIB
casGroup		FROM INNOVX-CORE-MIB;


adminGroup        	OBJECT IDENTIFIER ::= { casGroup  1 }

configGroup   		OBJECT IDENTIFIER ::= { casGroup  2 }

alarmCfgGroup         	OBJECT IDENTIFIER ::= { casGroup  3 }

diagnostics         	OBJECT IDENTIFIER ::= { casGroup  4 }

statusGroup         	OBJECT IDENTIFIER ::= { casGroup  5 }


--
-- ****************************************************************************
--                            Administrative Group
-- ****************************************************************************


cascadeMIBversion OBJECT-TYPE
    SYNTAX DisplayString (SIZE (5))
    ACCESS read-only
    STATUS mandatory
    DESCRIPTION
    "Identifies the version of the MIB as `X.YZT' where:

	X: Major Revision         (1-9)
	Y: Minor Revision         (0-9)
	Z: Typographical Revision (0-9)
	T: Test Revision          (A-Z)

    Upon formal release, the test revision will not be present."

    ::= { adminGroup 1 }



--
-- ****************************************************************************
--              Configuration - Cascade Interface Group
-- ****************************************************************************


cascadeInService OBJECT-TYPE
    SYNTAX INTEGER
    {
        inService     (1),  -- cascade port is in service
        outOfService  (2)   -- cascade port is out of service
    }
    ACCESS  read-write
    STATUS  mandatory
    DESCRIPTION
    "Defines the cascade interface port state.
    WEBFLAG
    In Service
    Out Of Service
    WEBEND"

    ::= { configGroup 1 }


cascadeSetFrameType OBJECT-TYPE
    SYNTAX INTEGER
    {
        esf   (1),  -- extended superframe format
        d4    (2),  -- D4 framing format
        auto  (3)   -- the unit will determine framing format
    }
    ACCESS  read-write
    STATUS  mandatory
    DESCRIPTION
    "Defines the line interface framing type as follows:
    `esf'  sets extended superframe format,
    `d4'   sets D4 framing format,
    `auto' instructs the unit to determine framing
    WEBFLAG
    ESF
    D4
    Automatic
    WEBEND"

    ::= { configGroup 2 }


cascadeOperFrameType OBJECT-TYPE
    SYNTAX INTEGER
    {
        esf   (1),  -- extended superframe format
        d4    (2),  -- D4 framing format
        auto  (3)   -- the unit is `acquiring', frame type is indeterminate
    }
    ACCESS  read-only
    STATUS  mandatory
    DESCRIPTION
    "Identifies the line interface framing type acquired by the unit as
    defined by the `cascadeNetSetFrameType' object as follows:
    `esf'  indicates extended superframe format,
    `d4'   indicates D4 framing format,
    `auto' indicates the unit is still `acquiring', frame type
    is indeterminate at this time.
    WEBFLAG
    ESF
    D4
    Automatic
    WEBEND"

    ::= { configGroup 3 }




cascadeLineCoding OBJECT-TYPE
    SYNTAX  INTEGER
    {
        b8zs  (1),  -- binary eight zero substitution
        ami   (2)   -- alternate mark inversion
    }
    ACCESS  read-write
    STATUS  mandatory
    DESCRIPTION
    "Defines the Zero Code Suppression mechanism for the interface.

    `b8zs' defines the use of a specified  pattern  of  normal bits and
    bipolar violations used to replace a sequence of eight zero bits.

    `ami' (alternate mark inversion) defines a mode wherein no zero code
    suppression is provided. Therefore ami line encoding does not protect
    against inadequate ones density.

    The DSU will enforce an 8x(N+1) minimum ones density requirement when
    ap553CasLineCoding == `ami' and cascadeDS0Format == `nx64k' and
    cascadeDS0AllocationScheme == `consecutive'.
    WEBFLAG
    B8ZS
    AMI
    WEBEND"

    ::= { configGroup 4 }


cascadeIntfType OBJECT-TYPE
    SYNTAX INTEGER
    {
	ds1-auto-lbo      (1),  -- ds1, automatic line buildout
	ds1-zero-dB       (2),  -- ds1,line buildout of   0.0 dB
	ds1-neg7pt5-dB    (3),  -- ds1,line buildout of -07.5 dB
        ds1-neg15pt0-dB   (4),  -- ds1,line buildout of -15.0 dB
        ds1-neg22pt5-dB   (5),  -- ds1,line buildout of -22.5 dB
        dsx1-preeq130-ft  (6),  -- dsx1, transmitter gain for   0 < 130 feet
        dsx1-preeq260-ft  (7),  -- dsx1, transmitter gain for 130 < 260 feet
        dsx1-preeq390-ft  (8),  -- dsx1, transmitter gain for 260 < 390 feet
        dsx1-preeq530-ft  (9),  -- dsx1, transmitter gain for 390 < 530 feet
        dsx1-preeq655-ft (10)   -- dsx1, transmitter gain for 530 < 655 feet
    }
    ACCESS read-write
    STATUS mandatory
    DESCRIPTION
    "Defines the operating mode of the interface, and the attenuation or gain.

    The following values specify operation as a standard DS1 interface, with
    the specified attenuation:
    `ds1-auto-lbo' allows the unit to determine the transmit buildout value.
    `ds1-zero-dB' sets the transmit buildout to 0.0 dB.
    `ds1-neg7pt5-dB' sets the transmit buildout to -7.5dB.
    `ds1-neg15pt0-dB' sets the transmit buildout to -15.0dB.
    `ds1-neg22pt5-dB' sets the transmit buildout to -22.5dB.

    The following values specify operation as a standard cross-connect DSX-1
    interface, with the specified transmitter gain:
    `dsx1-preeq130-ft'  -- transmitter gain for 0 < 130 feet
    `dsx1-preeq260-ft'  -- transmitter gain for 130 < 260 feet
    `dsx1-preeq390-ft'  -- transmitter gain for 260 < 390 feet
    `dsx1-preeq530-ft'  -- transmitter gain for 390 < 530 feet
    `dsx1-preeq655-ft'  -- transmitter gain for 530 < 655 feet
    WEBFLAG
    DS1     Auto Line Buildout
    DS1    0.0dB Line Buildout
    DS1   -7.5dB Line Buildout    
    DS1  -15.0dB Line Buildout
    DS1  -22.5dB Line Buildout
    DSX1   0 - 133 ft Pre-equalization
    DSX1 133 - 266 ft Pre-equalization
    DSX1 266 - 399 ft Pre-equalization
    DSX1 399 - 533 ft Pre-equalization
    DSX1 533 - 655 ft Pre-equalization
    WEBEND"

    ::= { configGroup 5 }


cascadeDS1IntfRcvLevel OBJECT-TYPE
    SYNTAX INTEGER 
    {
	noSignal             (1),  --  no T1 signal detected
	pos2toNeg7pt5-dB     (2),  --  + 2.0dB  to  - 7.5dB
	neg7pt5toNeg15-dB    (3),  --  - 7.5dB  to  -15.0dB
	neg15toNeg22pt5-dB   (4),  --  -15.0dB  to  -22.5dB
	lessThanNeg22pt5-dB  (5),  --  less than -22.5dB
        invalidDSX1intf      (6)   --  invalid, interface is DSX1
     }
    ACCESS read-only
    STATUS mandatory
    DESCRIPTION
    "Identifies the Cascade Interface Receive level for a DS1 type interface.
    `noSignal' indicates that no T1 signal is detected on the interface, (the
    `NS' LED on the unit's front panel will be on.
    `pos2toNeg7pt5-dB'=> + 2.0dB  to  - 7.5dB DS1 interface receive level
    `neg7pt5toNeg15-dB'=> - 7.5dB  to  -15.0dB DS1 interface receive level
    `neg15toNeg22pt5-dB'=> -15.0dB  to  -22.5dB DS1 interface receive level
    `lessThanNeg22pt5-dB'=> less than -22.5dB DS1 interface receive level
    `invalidDSX1intf=> invalid object, interface type is DSX1
    WEBFLAG
    + 2.0dB  to - 7.5dB
    - 7.5dB  to -15.0dB
    -15.0dB  to -22.5dB
    less than -22.5dB
    not applicable
    WEBEND"

    ::= { configGroup 6 }

 


cascadeDropAndInsertTable OBJECT-TYPE
    SYNTAX SEQUENCE OF ChannelEntry
    ACCESS not-accessible
    STATUS mandatory
    DESCRIPTION
    "This table defines the channel type for each of the timeslots passthru
     from LIU to Cascade.  This contiguous timeslot bundle is defined via the
     objects ap553StartingDS0 and ap553NumDS0s from AP553Liu.mib."
      ::={ configGroup 7 }

channelEntry OBJECT-TYPE
     SYNTAX ChannelEntry
     ACCESS not-accessible
     STATUS mandatory
     DESCRIPTION
     " Identifies an entry (row) in cascadeDropAndInsertMapTable table."
     INDEX { channelIndex }
     ::={ cascadeDropAndInsertTable 1 }

ChannelEntry ::=
      SEQUENCE {
                  channelIndex			INTEGER,
                  cascadeDropAndInsert		INTEGER

               }

channelIndex OBJECT-TYPE
      SYNTAX INTEGER (1..32)
      ACCESS  read-only
      STATUS mandatory
      DESCRIPTION
      " Identifies a channel (row)for the time slots - 1-24 for T1 and 
        1-32 for E1. For E1, 1 = TS0 and 32 = TS31."
      ::={ channelEntry 1 }

cascadeDropAndInsert OBJECT-TYPE
     SYNTAX INTEGER
     {
	none  			(1),
	clearChannel    	(2),
        signallingChannel       (3),
        casChannel       	(4),
        tsNotAvailable       	(5) 
    }
      ACCESS  read-write
      STATUS mandatory
      DESCRIPTION
      " 
    Rules:
    1)  For a T1 interface timeslots 25 - 32 are not available
        and will contain 5 for each of these timeslots.

    2)  For an E1 interface timeslot 0 is not available and
        will contain 5 for this timeslot.

    3)  For an E1 interface timeslot 16 is not available if CAS is enabled. 
	and will contain 4 for this timeslot.


    		CHANNEL TYPE

                     none(1)              - This timeslot is dropped at DTE
					    port.

                     clearChannel(2)      - all eight bits are passed through
					    to cascade port.
 
                     signallingChannel(3) - used for voice channels with 
					   robbed-bit signalling (for T1
					    networks).

		     casChannel(4)	  - used for timeslot 16 when CAS is
		     			    on when LIU is E1 interface.
  		    
		     tsNotAvailable(5)    - Used for timeslots 25 - 32
                                            when LIU is T1 interface. Used for
                                            timeslot 0 when LIU is E1
					    interface.
    WEBFLAG
    DTE Channel
    Clear Channel
    Voice Channel
    CAS Channel
    TS Not Avail
    WEBEND"

      ::={ channelEntry 2 }


--
-- ****************************************************************************
--          Cascade Alarm Mask, Window & Threshold Configuration Group
-- ****************************************************************************


cascadeBpvTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Bipolar
    Violations Alarm when this event occurs and meets the window and threshold
    requirements for reporting as specified by the associated window and
    threshold object values below.
    WEBFLAG
    Inhibit
    Critical
    Major
    Minor
    Warning
    Info
    WEBEND"

    ::= { alarmCfgGroup 1 }


cascadeBpvWindow OBJECT-TYPE
    SYNTAX INTEGER
    {
        oneMinute   	(1), -- 1 minute sampling window, report one event only
        fifteenMinutes  (2), -- 15 minutes sampling window, report one event
        oneHour    	(3)  -- 1 hour sampling window, report one event only
    }
    ACCESS read-write
    STATUS mandatory
    DESCRIPTION
    "Specifies the sampling window in which to report the Cascade Bipolar 
    Violationslarm condition as active.

    All other values specify the size of the sampling window in which the 
    event may be reported one time as active, as controlled by the associated
    mask object value, when the associated obj's threshold condition is met.
     WEBFLAG
    One Minute
    Fifteen Minutes
    One Hour
    WEBEND"

    ::= { alarmCfgGroup 2 }


cascadeBpvThresh OBJECT-TYPE
    SYNTAX INTEGER
    {
	thr1      (1),
	thr10     (2),
	thr100    (3),
	thr1000   (4),
	thr10000  (5)
    }
    ACCESS read-write
    STATUS mandatory
    DESCRIPTION
    "Specifies the threshold of events to be exceeded for reporting the
    Cascade Bipolar Violations alarm condition. When the associated window 
    object value is `report_all' the value of this object is ignored.
    WEBFLAG
     1
    10
    100
    1,000
    10,000
    WEBEND"

    ::= { alarmCfgGroup 3 }


cascadeCrcTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Cyclical
    Redundancy Check Alarm when this event occurs and meets the window and
    threshold requirements for reporting as specified by the associated window
    and threshold object values below.
    WEBFLAG
    Inhibit
    Critical
    Major
    Minor
    Warning
    Info
    WEBEND"

    ::= { alarmCfgGroup 4 }


cascadeCrcWindow OBJECT-TYPE
    SYNTAX INTEGER
    {
        oneMinute   	(1), -- 1 minute sampling window, report one event only
        fifteenMinutes  (2), -- 15 minutes sampling window, report one event
        oneHour    	(3)  -- 1 hour sampling window, report one event only
    }
    ACCESS read-write
    STATUS mandatory
    DESCRIPTION
    "Specifies the sampling window in which to report the Cascade Cyclical
    Redundancy Check alarm condition as active.

    All other values specify the size of the sampling window in which the 
    event may be reported one time as active, as controlled by the associated
    mask object value, when the associated obj's threshold condition is met.
    WEBFLAG
    One Minute
    Fifteen Minutes
    One Hour
    WEBEND"

    ::= { alarmCfgGroup 5 }


cascadeCrcThresh OBJECT-TYPE
    SYNTAX INTEGER
    {
	thr1      (1),
	thr10     (2),
	thr100    (3),
	thr1000   (4),
	thr10000  (5)
    }
    ACCESS read-write
    STATUS mandatory
    DESCRIPTION
    "Specifies the threshold of events to be exceeded for reporting the 
    Cascade Cyclical Redundancy Check alarm condition. When the associated
    window object value is `report_all' the value of this object is ignored.
    WEBFLAG
    1
    10
    100
    1,000
    10,000
    WEBEND"

    ::= { alarmCfgGroup 6 }


cascadeLadTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Low
    Average Density Alarm when this event occurs and meets the window and
    threshold requirements for reporting as specified by the associated
    window and threshold object values below.
    WEBFLAG
    Inhibit
    Critical
    Major
    Minor
    Warning
    Info
    WEBEND"

    ::= { alarmCfgGroup 7 }


cascadeLadWindow OBJECT-TYPE
    SYNTAX INTEGER
    {
        oneMinute   	(1), -- 1 minute sampling window, report one event only
        fifteenMinutes  (2), -- 15 minutes sampling window, report one event
        oneHour    	(3)  -- 1 hour sampling window, report one event only
    }
    ACCESS read-write
    STATUS mandatory
    DESCRIPTION
    "Specifies the sampling window in which to report the Cascade Low Average
    Density alarm condition as active.

 
    All other values specify the size of the sampling window in which the 
    event may be reported one time as active, as controlled by the associated
    mask object value, when the associated obj's threshold condition is met.
    WEBFLAG
    One Minute
    Fifteen Minutes
    One Hour
    WEBEND"

    ::= { alarmCfgGroup 8 }


cascadeLadThresh OBJECT-TYPE
    SYNTAX INTEGER
    {
	thr1      (1),
	thr10     (2),
	thr100    (3),
	thr1000   (4),
	thr10000  (5)
    }
    ACCESS read-write
    STATUS mandatory
    DESCRIPTION
    "Specifies the threshold of events to be exceeded for reporting the
    Cascade Low Average Density alarm condition. When the associated window
    object value is `reportAll' the value of this object is ignored.
    WEBFLAG
    1
    10
    100
    1,000
    10,000
    WEBEND"

    ::= { alarmCfgGroup 9 }


cascadeAisTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Alarm
    Indication Signal Alarm when this event occurs.
    WEBFLAG
    Inhibit
    Critical
    Major
    Minor
    Warning
    Info
    WEBEND"

    ::= { alarmCfgGroup 10 }


cascadeLosTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Loss of
    Signal Alarm when this event occurs.
    WEBFLAG
    Inhibit
    Critical
    Major
    Minor
    Warning
    Info
    WEBEND"

    ::= { alarmCfgGroup 11 }


cascadeOofTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Out of
    Frame Alarm when this event occurs.
    WEBFLAG
    Inhibit
    Critical
    Major
    Minor
    Warning
    Info
    WEBEND"

    ::= { alarmCfgGroup 12 }


cascadeRcdYelTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade Received
    Yellow Alarm when this event occurs.
    WEBFLAG
    Inhibit
    Critical
    Major
    Minor
    Warning
    Info
    WEBEND"

    ::= { alarmCfgGroup 13 }


cascadeUssTrapSeverity OBJECT-TYPE
    SYNTAX INTEGER
    {
	inhibit   (1),  -- alarm not reported
	critical  (2),  -- report as critical
        major     (3),  -- report as major
        minor     (4),  -- report as minor
        warning   (5),  -- report as warning
        info      (6)   -- report as info
    }
    ACCESS read-write
    STATUS mandatory
    DESCRIPTION
    "Controls the reporting and defines the severity of the Cascade
    Unavailable Signal State Alarm when this event occurs.
    WEBFLAG
    Inhibit
    Critical
    Major
    Minor
    Warning
    Info
    WEBEND"

    ::= { alarmCfgGroup 14 }



--
-- ****************************************************************************
--                        Diagnostics Group
-- ****************************************************************************


cascadeDiagTest OBJECT-TYPE
    SYNTAX INTEGER 
    {
	cascadeLineLoopback        (1),
	cascadePayLoadLoopback     (2),
	cascadeStopTest            (3)
    }
    ACCESS read-write
    STATUS mandatory
    DESCRIPTION 
    "Specifies the test to be executed, or stops the current test."

    ::= { diagnostics 1 }


cascadeDiagTestDuration OBJECT-TYPE
    SYNTAX INTEGER
    {
        testTime1Min    (1),
        testTime5Mins   (2),
        testTime10Mins  (3),
        testTime20Mins  (4)
    }
    ACCESS read-write
    STATUS mandatory
    DESCRIPTION
    "Defines the length of all LIU diagnostic tests."

    ::= { diagnostics 2 }


cascadeDiagTestStatus OBJECT-TYPE
    SYNTAX INTEGER
    {

	statcascadeLineLoopback        (1),
	statcascadePayLoadLoopback     (2),
	statNoTestinProgress      (3)
    }
    ACCESS read-only
    STATUS mandatory
    DESCRIPTION
    "Displays the test in progress, if any."

    ::= { diagnostics 3 }


--^L
-- ****************************************************************************
--                             Status Group
-- ****************************************************************************


cascadePortStatus OBJECT-TYPE
    SYNTAX  OCTET STRING (SIZE(1))
    ACCESS  read-only
    STATUS  mandatory
    DESCRIPTION
    "A bitwise snapshot of interface port status conditions and EIA signals,
    where 0 = condition not present, and 1 = condition present, as follows:

    Octet 1 - CASCADE Interface Port Status
 		bit 7 - n/u
               	bit 6 - n/u
                bit 5 - n/u
                bit 4 - n/u
                bit 3 - Alarm Indication Signal
                bit 2 - Out Of Frame Alarm
                bit 1 - Loss Of Signal Alarm
                bit 0 - Remote Alarm"

    ::= { statusGroup 1 }



-- ****************************************************************************
--                       mib definitions end
-- ****************************************************************************





END
