IBM-AS400-RWS-MIB DEFINITIONS ::= BEGIN

-- *
-- * AS/400 remote workstation controller MIB
-- *
-- * This is an IBM enterprise MIB for AS/400 remote workstation (RWS)
-- * controllers (e.g. 5494).
-- *

IMPORTS
  OBJECT-TYPE   FROM RFC-1212
  DisplayString FROM RFC1213-MIB
  enterprises   FROM RFC1155-SMI  ;

ibm                OBJECT IDENTIFIER ::= { enterprises 2 }
ibmProd            OBJECT IDENTIFIER ::= { ibm 6 }
ibmAs400Agent      OBJECT IDENTIFIER ::= { ibmProd 11 }
ibmAs400Rws        OBJECT IDENTIFIER ::= { ibmAs400Agent 1 }

rwsGeneralInfo     OBJECT IDENTIFIER ::= { ibmAs400Rws 99 }

rwsNumCtls OBJECT-TYPE
  SYNTAX INTEGER
  ACCESS read-only
  STATUS mandatory
  DESCRIPTION
    "Number of RWS controllers (rows in rwsTable)."
  ::= { rwsGeneralInfo 1 }
-- Note this object is defined as ibmAs400Rws.99.1, lexicographically
-- following the last table defined in this MIB now and in the future.
-- This "protects" managers from hitting a low-performing MIB when
-- doing a MIB walk off the end of this MIB.

--
-- RWS table
--

rwsTable OBJECT-TYPE
  SYNTAX SEQUENCE OF RwsEntry
  ACCESS not-accessible
  STATUS mandatory
  DESCRIPTION
    "Table of AS/400 remote workstation (RWS) controllers."
  ::= { ibmAs400Rws 1 }

rwsEntry OBJECT-TYPE
  SYNTAX RwsEntry
  ACCESS not-accessible
  STATUS mandatory
  DESCRIPTION
    "An entry for each RWS controller.
     Table is indexed by rwsCtlName."
  INDEX { rwsCtlName }
  ::= { rwsTable 1 }

RwsEntry ::= SEQUENCE {
  rwsCtlName       DisplayString,
  rwsOperState     INTEGER,
  rwsAppcDevName   DisplayString,
  rwsAppcDevState  INTEGER,
  rwsAppcCtlName   DisplayString,
  rwsCpName        DisplayString,
  rwsType          DisplayString,
  rwsModel         DisplayString,
  rwsSerial        DisplayString,
  rwsRelease       DisplayString
  }

rwsCtlName OBJECT-TYPE
  SYNTAX DisplayString(SIZE(1..10))
  ACCESS read-only
  STATUS mandatory
  DESCRIPTION
    "RWS controller description name."
  ::= { rwsEntry 1 }

rwsOperState OBJECT-TYPE
  SYNTAX INTEGER {
         unavailable(0),
         inactive(1),
         pendactive(2),
         active(3),
         pendinact(4)
         }
  ACCESS read-write
  STATUS mandatory
  DESCRIPTION
    "Operational state of the RWS controller description."
  ::= { rwsEntry 2 }

rwsAppcDevName OBJECT-TYPE
  SYNTAX DisplayString(SIZE(1..10))
  ACCESS read-only
  STATUS mandatory
  DESCRIPTION
    "Name of the APPC device description associated with the RWS
     controller."
  ::= { rwsEntry 3 }

rwsAppcDevState OBJECT-TYPE
  SYNTAX INTEGER {
         unavailable(0),
         inactive(1),
         pendactive(2),
         active(3),
         pendinact(4)
         }
  ACCESS read-write
  STATUS mandatory
  DESCRIPTION
    "Operational state of the associated APPC device."
  ::= { rwsEntry 4 }

rwsAppcCtlName OBJECT-TYPE
  SYNTAX DisplayString(SIZE(1..10))
  ACCESS read-only
  STATUS mandatory
  DESCRIPTION
    "Name of the APPC controller associated with the RWS controller.
     The associated APPN MIB instance of ibmappnNodeLsState gives
     its operational state."
  ::= { rwsEntry 5 }

rwsCpName OBJECT-TYPE
  SYNTAX DisplayString(SIZE(1..17))
  ACCESS read-only
  STATUS mandatory
  DESCRIPTION
    "Fully-qualified control point name of the remote control unit.
     Format is NETID.CPNAME."
  ::= { rwsEntry 6 }

rwsType OBJECT-TYPE
  SYNTAX DisplayString(SIZE(1..10))
  ACCESS read-only
  STATUS mandatory
  DESCRIPTION
    "Machine type of the RWS controller."
  ::= { rwsEntry 7 }

rwsModel OBJECT-TYPE
  SYNTAX DisplayString(SIZE(1..10))
  ACCESS read-only
  STATUS mandatory
  DESCRIPTION
    "Model number of the RWS controller."
  ::= { rwsEntry 8 }

rwsSerial OBJECT-TYPE
  SYNTAX DisplayString(SIZE(8..10))
  ACCESS read-only
  STATUS mandatory
  DESCRIPTION
    "Serial number value in format xx-yyyyyyy, from the customer setup
     (CSU) field.
     In general, xx is the Plant of Manufacture, and yyyyyyy is the
     serial number.  However the user may configure any valid value
     for each digit.  Valid values for each digit are A-Z and 0-0.
     Note this value is not guaranteed to be current when the value
     of rwsAppcDevState is not active."
-- Note: this format is the same as the 9-digit serial number format
--       in the PSID and in SNA alerts.
  ::= { rwsEntry 9 }

rwsRelease OBJECT-TYPE
  SYNTAX DisplayString(SIZE(1..8))
  ACCESS read-only
  STATUS mandatory
  DESCRIPTION
    "Microcode release, modification and patch level.
     For a 5494, the format is rrrrmmpp,
     For a 5394 BB, the format is rrpp,
     where r=release digit, m=modification digit, p=patch digit.
     Example: rel. 1.1 mod. 2 patch 3 would be 01010203.
     Note this value is not guaranteed to be current when the value
     of rwsAppcDevState is not active."
  ::= { rwsEntry 10 }

--
-- Device table
--

rwsDevTable OBJECT-TYPE
  SYNTAX SEQUENCE OF RwsDevEntry
  ACCESS not-accessible
  STATUS mandatory
  DESCRIPTION
    "Table of nonprogrammable devices attached to RWS controllers."
  ::= { ibmAs400Rws 2 }

rwsDevEntry OBJECT-TYPE
  SYNTAX RwsDevEntry
  ACCESS not-accessible
  STATUS mandatory
  DESCRIPTION
    "An entry for each nonprogrammable device attached to an RWS
     controller.  Table is indexed by rwsCtlName and rwsDevName."
  INDEX { rwsDevCtlName, rwsDevName }
  ::= { rwsDevTable 1 }

RwsDevEntry ::= SEQUENCE {
  rwsDevCtlName    DisplayString,
  rwsDevName       DisplayString,
  rwsDevOperState  INTEGER,
  rwsDevSerial     DisplayString
  }

rwsDevCtlName OBJECT-TYPE
  SYNTAX DisplayString(SIZE(1..10))
  ACCESS read-only
  STATUS mandatory
  DESCRIPTION
    "Controller name associated with device."
  ::= { rwsDevEntry 1 }

rwsDevName OBJECT-TYPE
  SYNTAX DisplayString(SIZE(1..10))
  ACCESS read-only
  STATUS mandatory
  DESCRIPTION
    "Device name."
  ::= { rwsDevEntry 2 }

rwsDevOperState OBJECT-TYPE
  SYNTAX INTEGER {
         unavailable(0),
         inactive(1),
         pendactive(2),
         active(3),
         pendinact(4)
         }
  ACCESS read-write
  STATUS mandatory
  DESCRIPTION
    "Operational state of device."
  ::= { rwsDevEntry 3 }

rwsDevSerial OBJECT-TYPE
  SYNTAX DisplayString(SIZE(8..10))
  ACCESS read-only
  STATUS mandatory
  DESCRIPTION
    "Serial number value in format xx-yyyyyyy, reported by the RWS
     control unit for the device.
     In general, xx is the Plant of Manufacture, and yyyyyyy is the
     serial number.
     Note this value is not guaranteed to be current when the value
     of rwsDevState is not active."
  ::= { rwsDevEntry 4 }
END
