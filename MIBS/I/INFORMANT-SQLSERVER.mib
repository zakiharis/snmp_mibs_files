INFORMANT-SQLSERVER DEFINITIONS ::= BEGIN

IMPORTS
    MODULE-IDENTITY, OBJECT-TYPE, OBJECT-IDENTITY, Gauge32, Integer32
        FROM SNMPv2-SMI
    InstanceName, informant
        FROM WTCS;

sqlServer MODULE-IDENTITY
    LAST-UPDATED "200409102047Z"
    ORGANIZATION "Informant Systems, Inc."
    CONTACT-INFO
            "        Garth Williams
                Tel: +1 780 433 7973
             E-mail: garth.williams@wtcs.org"
    DESCRIPTION
            "The MIB module for SNMP Informant SQLServer
             performance counter entries."
    REVISION      "200409102047Z"
    DESCRIPTION
            "Added entries to support multiple instances
             of installed SQL Server. Also added counters
             for SQL Server 2005."
    REVISION      "200402290623Z"
    DESCRIPTION
            "Changed the syntax of the datapoints from
			 integer to gauge."
    REVISION      "200401200855Z"
    DESCRIPTION
            "The initial revision of this MIB module."
    ::= { informant 3 }

analysisServerAggCache OBJECT-IDENTITY
    STATUS     current
    DESCRIPTION
	    "The Agg Cache object counters provide
	    information about the aggregation cache."
    ::= { sqlServer 1 }

asacBytesAddedPerSec OBJECT-TYPE
    SYNTAX     Gauge32
    MAX-ACCESS read-only
    STATUS     current
    DESCRIPTION
	    "Rate of bytes added to the cache."
    ::= { analysisServerAggCache 1 }

asacCurrentBytes OBJECT-TYPE
    SYNTAX     Gauge32
    MAX-ACCESS read-only
    STATUS     current
    DESCRIPTION
	    "Current number of bytes used by the
	    aggregation cache."
    ::= { analysisServerAggCache 2 }

asacCurrentEntries OBJECT-TYPE
    SYNTAX     Gauge32
    MAX-ACCESS read-only
    STATUS     current
    DESCRIPTION
	    "Current number of cache entries."
    ::= { analysisServerAggCache 3 }

asacDirectHitRatio OBJECT-TYPE
    SYNTAX     Gauge32
    MAX-ACCESS read-only
    STATUS     current
    DESCRIPTION
	    "Ratio of cache direct hits to cache lookups,
	    for the period between obtaining counter
	    values."
    ::= { analysisServerAggCache 4 }

asacDirectHitsPerSec OBJECT-TYPE
    SYNTAX     Gauge32
    MAX-ACCESS read-only
    STATUS     current
    DESCRIPTION
	    "Rate of cache direct hits.  Queries were
	    answered from an existing cache entry."
    ::= { analysisServerAggCache 5 }

asacEvictionsPerSec OBJECT-TYPE
    SYNTAX     Gauge32
    MAX-ACCESS read-only
    STATUS     current
    DESCRIPTION
	    "Rate of evictions from the cache.	This is per
	    partition per cube per database.  Typically due
	    to background cleaner."
    ::= { analysisServerAggCache 6 }

asacFilterHitRatio OBJECT-TYPE
    SYNTAX     Gauge32
    MAX-ACCESS read-only
    STATUS     current
    DESCRIPTION
	    "Ratio of cache filter hits to cache lookups,
	    for the period between obtaining counter
	    values."
    ::= { analysisServerAggCache 7 }

asacFilterHitsPerSec OBJECT-TYPE
    SYNTAX     Gauge32
    MAX-ACCESS read-only
    STATUS     current
    DESCRIPTION
	    "Rate of cache filter hits.  Queries were
	    answered by filtering an existing cache entry."
    ::= { analysisServerAggCache 8 }

asacInsertsPerSec OBJECT-TYPE
    SYNTAX     Gauge32
    MAX-ACCESS read-only
    STATUS     current
    DESCRIPTION
	    "Rate of insertions into the cache.  This is
	    per partition per cube per database."
    ::= { analysisServerAggCache 9 }

asacLookupsPerSec OBJECT-TYPE
    SYNTAX     Gauge32
    MAX-ACCESS read-only
    STATUS     current
    DESCRIPTION
	    "Rate of cache lookups."
    ::= { analysisServerAggCache 10 }

asacMissesPerSec OBJECT-TYPE
    SYNTAX     Gauge32
    MAX-ACCESS read-only
    STATUS     current
    DESCRIPTION
	    "Rate of cache misses."
    ::= { analysisServerAggCache 11 }

asacTotalDirectHits OBJECT-TYPE
    SYNTAX     Gauge32
    MAX-ACCESS read-only
    STATUS     current
    DESCRIPTION
	    "Total count of direct cache hits.	Queries
	    were answered from existing cache entries."
    ::= { analysisServerAggCache 12 }

asacTotalEvictions OBJECT-TYPE
    SYNTAX     Gauge32
    MAX-ACCESS read-only
    STATUS     current
    DESCRIPTION
	    "Evictions from the cache.	This is per
	    partition per cube per database.  Typically due
	    to background cleaner."
    ::= { analysisServerAggCache 13 }

asacTotalFilterHits OBJECT-TYPE
    SYNTAX     Gauge32
    MAX-ACCESS read-only
    STATUS     current
    DESCRIPTION
	    "Total count of filter cache hits.	Queries
	    were answered by filtering existing cache
	    entries."
    ::= { analysisServerAggCache 14 }

asacTotalInserts OBJECT-TYPE
    SYNTAX     Gauge32
    MAX-ACCESS read-only
    STATUS     current
    DESCRIPTION
	    "Insertions into the cache.  This is per
	    partition per cube per database."
    ::= { analysisServerAggCache 15 }

asacTotalLookups OBJECT-TYPE
    SYNTAX     Gauge32
    MAX-ACCESS read-only
    STATUS     current
    DESCRIPTION
	    "Total number of lookups into the cache.  Note
	    that each MDX query has zero or more server
	    round trips, and each partition will be
	    queried."
    ::= { analysisServerAggCache 16 }

asacTotalMisses OBJECT-TYPE
    SYNTAX     Gauge32
    MAX-ACCESS read-only
    STATUS     current
    DESCRIPTION
	    "Total count of cache misses."
    ::= { analysisServerAggCache 17 }

analysisServerConnection OBJECT-IDENTITY
    STATUS     current
    DESCRIPTION
	    "The Connection object counters provide
	    information about server activity in general.
	    They can be used to monitor the performance of
	    user connections with Analysis Services."
    ::= { sqlServer 2 }

ascAuthenticationsPerSec OBJECT-TYPE
    SYNTAX     Gauge32
    MAX-ACCESS read-only
    STATUS     current
    DESCRIPTION
	    "Rate of user authentications."
    ::= { analysisServerConnection 1 }

ascCompletionsPerSec OBJECT-TYPE
    SYNTAX     Gauge32
    MAX-ACCESS read-only
    STATUS     current
    DESCRIPTION
	    "Rate of connection completions.  This includes
	    successful and failed connection attempts."
    ::= { analysisServerConnection 2 }

ascCurrentAgents OBJECT-TYPE
    SYNTAX     Gauge32
    MAX-ACCESS read-only
    STATUS     current
    DESCRIPTION
	    "Current number of agents on server."
    ::= { analysisServerConnection 3 }

ascCurrentAuthentications OBJECT-TYPE
    SYNTAX     Gauge32
    MAX-ACCESS read-only
    STATUS     current
    DESCRIPTION
	    "Current number of authentications in
	    progress."
    ::= { analysisServerConnection 4 }

ascCurrentConnections OBJECT-TYPE
    SYNTAX     Gauge32
    MAX-ACCESS read-only
    STATUS     current
    DESCRIPTION
	    "Current number of client connections
	    established."
    ::= { analysisServerConnection 5 }

ascCurrentConnectionsInProgress OBJECT-TYPE
    SYNTAX     Gauge32
    MAX-ACCESS read-only
    STATUS     current
    DESCRIPTION
	    "Current number of connections pending
	    completion."
    ::= { analysisServerConnection 6 }

ascCurrentHttpConnections OBJECT-TYPE
    SYNTAX     Gauge32
    MAX-ACCESS read-only
    STATUS     current
    DESCRIPTION
	    "Current number of http connections
	    established."
    ::= { analysisServerConnection 7 }

ascFailuresPerSec OBJECT-TYPE
    SYNTAX     Gauge32
    MAX-ACCESS read-only
    STATUS     current
    DESCRIPTION
	    "Rate of connection failures."
    ::= { analysisServerConnection 8 }

ascRequestsPerSec OBJECT-TYPE
    SYNTAX     Gauge32
    MAX-ACCESS read-only
    STATUS     current
    DESCRIPTION
	    "Rate of connection requests.  These are
	    arrivals."
    ::= { analysisServerConnection 9 }

ascSuccessesPerSec OBJECT-TYPE
    SYNTAX     Gauge32
    MAX-ACCESS read-only
    STATUS     current
    DESCRIPTION
	    "Rate of successful connection completions."
    ::= { analysisServerConnection 10 }

ascTotalAuthentications OBJECT-TYPE
    SYNTAX     Gauge32
    MAX-ACCESS read-only
    STATUS     current
    DESCRIPTION
	    "Total user authentications."
    ::= { analysisServerConnection 11 }

ascTotalCompletions OBJECT-TYPE
    SYNTAX     Gauge32
    MAX-ACCESS read-only
    STATUS     current
    DESCRIPTION
	    "Total connection completions."
    ::= { analysisServerConnection 12 }

ascTotalFailures OBJECT-TYPE
    SYNTAX     Gauge32
    MAX-ACCESS read-only
    STATUS     current
    DESCRIPTION
	    "Total failed connection attempts."
    ::= { analysisServerConnection 13 }

ascTotalRequests OBJECT-TYPE
    SYNTAX     Gauge32
    MAX-ACCESS read-only
    STATUS     current
    DESCRIPTION
	    "Total connection requests.  These are
	    arrivals."
    ::= { analysisServerConnection 14 }

ascTotalSuccesses OBJECT-TYPE
    SYNTAX     Gauge32
    MAX-ACCESS read-only
    STATUS     current
    DESCRIPTION
	    "Total successful connections."
    ::= { analysisServerConnection 15 }

analysisServerLastQuery OBJECT-IDENTITY
    STATUS     current
    DESCRIPTION
	    "The Last Query object counters provide
	    information about processing on the last
	    query."
    ::= { sqlServer 3 }

aslqAnswerFromCacheDirect OBJECT-TYPE
    SYNTAX     Gauge32
    MAX-ACCESS read-only
    STATUS     current
    DESCRIPTION
	    "Number of partitions answered directly from
	    cache."
    ::= { analysisServerLastQuery 1 }

aslqAnswerFromCacheFiltered OBJECT-TYPE
    SYNTAX     Gauge32
    MAX-ACCESS read-only
    STATUS     current
    DESCRIPTION
	    "Number of partitions answered by filtering
	    from other cache entries."
    ::= { analysisServerLastQuery 2 }

aslqAnswerFromFile OBJECT-TYPE
    SYNTAX     Gauge32
    MAX-ACCESS read-only
    STATUS     current
    DESCRIPTION
	    "Number of partitions answered from files."
    ::= { analysisServerLastQuery 3 }

aslqDSNRequested OBJECT-TYPE
    SYNTAX     Gauge32
    MAX-ACCESS read-only
    STATUS     current
    DESCRIPTION
	    "Data Set Name requested as the query to the
	    server.  (Levels used for each dimension.)"
    ::= { analysisServerLastQuery 4 }

aslqDSNUsed OBJECT-TYPE
    SYNTAX     Gauge32
    MAX-ACCESS read-only
    STATUS     current
    DESCRIPTION
	    "Data Set Name used to answer the query. 
	    (Levels used for each dimension.)"
    ::= { analysisServerLastQuery 5 }

aslqDataAvgBytesPerRead OBJECT-TYPE
    SYNTAX     Gauge32
    MAX-ACCESS read-only
    STATUS     current
    DESCRIPTION
	    "Average bytes per data file read operation."
    ::= { analysisServerLastQuery 6 }

aslqDataAvgBytesPerRow OBJECT-TYPE
    SYNTAX     Gauge32
    MAX-ACCESS read-only
    STATUS     current
    DESCRIPTION
	    "Average bytes per row read."
    ::= { analysisServerLastQuery 7 }

aslqDataAvgRowsPerRead OBJECT-TYPE
    SYNTAX     Gauge32
    MAX-ACCESS read-only
    STATUS     current
    DESCRIPTION
	    "Average num rows read per data file read
	    operation."
    ::= { analysisServerLastQuery 8 }

aslqDataBytes OBJECT-TYPE
    SYNTAX     Gauge32
    MAX-ACCESS read-only
    STATUS     current
    DESCRIPTION
	    "Bytes read from the Data file."
    ::= { analysisServerLastQuery 9 }

aslqDataReads OBJECT-TYPE
    SYNTAX     Gauge32
    MAX-ACCESS read-only
    STATUS     current
    DESCRIPTION
	    "Number of logical read operations using the
	    Data file."
    ::= { analysisServerLastQuery 10 }

aslqIndexBytes OBJECT-TYPE
    SYNTAX     Gauge32
    MAX-ACCESS read-only
    STATUS     current
    DESCRIPTION
	    "Bytes read from the Index file."
    ::= { analysisServerLastQuery 11 }

aslqIndexReads OBJECT-TYPE
    SYNTAX     Gauge32
    MAX-ACCESS read-only
    STATUS     current
    DESCRIPTION
	    "Number of logical read operations using the
	    Index file."
    ::= { analysisServerLastQuery 12 }

aslqMapBytes OBJECT-TYPE
    SYNTAX     Gauge32
    MAX-ACCESS read-only
    STATUS     current
    DESCRIPTION
	    "Bytes read from the Map file."
    ::= { analysisServerLastQuery 13 }

aslqMapReads OBJECT-TYPE
    SYNTAX     Gauge32
    MAX-ACCESS read-only
    STATUS     current
    DESCRIPTION
	    "Number of logical read operations using the
	    Map file."
    ::= { analysisServerLastQuery 14 }

aslqQueryNum OBJECT-TYPE
    SYNTAX     Gauge32
    MAX-ACCESS read-only
    STATUS     current
    DESCRIPTION
	    "Monotonically increasing query count.  Might
	    be useful for tools to check which query this
	    information applies to."
    ::= { analysisServerLastQuery 15 }

aslqRowsCreated OBJECT-TYPE
    SYNTAX     Gauge32
    MAX-ACCESS read-only
    STATUS     current
    DESCRIPTION
	    "Number of rows created, which forms the final
	    answer in the aggregation set."
    ::= { analysisServerLastQuery 16 }

aslqRowsFilterExcluded OBJECT-TYPE
    SYNTAX     Gauge32
    MAX-ACCESS read-only
    STATUS     current
    DESCRIPTION
	    "Number of rows which were excluded by
	    filtering."
    ::= { analysisServerLastQuery 17 }

aslqRowsFilterIncluded OBJECT-TYPE
    SYNTAX     Gauge32
    MAX-ACCESS read-only
    STATUS     current
    DESCRIPTION
	    "Number of rows which were included by
	    filtering."
    ::= { analysisServerLastQuery 18 }

aslqRowsFiltered OBJECT-TYPE
    SYNTAX     Gauge32
    MAX-ACCESS read-only
    STATUS     current
    DESCRIPTION
	    "Number of rows against which a filtering
	    operation was applied."
    ::= { analysisServerLastQuery 19 }

aslqRowsRead OBJECT-TYPE
    SYNTAX     Gauge32
    MAX-ACCESS read-only
    STATUS     current
    DESCRIPTION
	    "Number of rows read from disk or from the
	    aggregation cache (in memory)."
    ::= { analysisServerLastQuery 20 }

aslqTimeMs OBJECT-TYPE
    SYNTAX     Gauge32
    MAX-ACCESS read-only
    STATUS     current
    DESCRIPTION
	    "Elapsed time in millisec."
    ::= { analysisServerLastQuery 21 }

aslqTotalBytes OBJECT-TYPE
    SYNTAX     Gauge32
    MAX-ACCESS read-only
    STATUS     current
    DESCRIPTION
	    "Bytes read from all files."
    ::= { analysisServerLastQuery 22 }

aslqTotalReads OBJECT-TYPE
    SYNTAX     Gauge32
    MAX-ACCESS read-only
    STATUS     current
    DESCRIPTION
	    "Number of logical read operations for all
	    files."
    ::= { analysisServerLastQuery 23 }

analysisServerLocks OBJECT-IDENTITY
    STATUS     current
    DESCRIPTION
	    "The Locks object counters provide information
	    about latching and locking activity. They can
	    be used to monitor the performance of latches
	    and locks with Analysis Services."
    ::= { sqlServer 4 }

aslCurrentLatchWaits OBJECT-TYPE
    SYNTAX     Gauge32
    MAX-ACCESS read-only
    STATUS     current
    DESCRIPTION
	    "Current number of threads waiting for a latch.
	     These are latch requests that could not be
	    given immediate grants and are in a wait
	    state."
    ::= { analysisServerLocks 1 }

aslCurrentLockWaits OBJECT-TYPE
    SYNTAX     Gauge32
    MAX-ACCESS read-only
    STATUS     current
    DESCRIPTION
	    "Current number of clients waiting for a lock."
    ::= { analysisServerLocks 2 }

aslCurrentLocks OBJECT-TYPE
    SYNTAX     Gauge32
    MAX-ACCESS read-only
    STATUS     current
    DESCRIPTION
	    "Current number of locked objects."
    ::= { analysisServerLocks 3 }

aslLatchWaitsPerSec OBJECT-TYPE
    SYNTAX     Gauge32
    MAX-ACCESS read-only
    STATUS     current
    DESCRIPTION
	    "Rate of latch requests that could not be
	    granted immediately and had to wait before
	    being granted."
    ::= { analysisServerLocks 4 }

aslLockDenialsPerSec OBJECT-TYPE
    SYNTAX     Gauge32
    MAX-ACCESS read-only
    STATUS     current
    DESCRIPTION
	    "Rate of lock denials."
    ::= { analysisServerLocks 5 }

aslLockGrantsPerSec OBJECT-TYPE
    SYNTAX     Gauge32
    MAX-ACCESS read-only
    STATUS     current
    DESCRIPTION
	    "Number of lock grants per second."
    ::= { analysisServerLocks 6 }

aslLockRequestsPerSec OBJECT-TYPE
    SYNTAX     Gauge32
    MAX-ACCESS read-only
    STATUS     current
    DESCRIPTION
	    "Number of lock requests per second."
    ::= { analysisServerLocks 7 }

aslLockWaitsPerSec OBJECT-TYPE
    SYNTAX     Gauge32
    MAX-ACCESS read-only
    STATUS     current
    DESCRIPTION
	    "Number of lock waits per second.  These are
	    lock requests that could not be given immediate
	    lock grants and were put in a wait state."
    ::= { analysisServerLocks 8 }

aslUnlockRequestsPerSec OBJECT-TYPE
    SYNTAX     Gauge32
    MAX-ACCESS read-only
    STATUS     current
    DESCRIPTION
	    "Number of unlock requests per second."
    ::= { analysisServerLocks 9 }

analysisServerProc OBJECT-IDENTITY
    STATUS     current
    DESCRIPTION
	    "The Proc object counters provide information
	    about processing data."
    ::= { sqlServer 5 }

aspCurrentPartitions OBJECT-TYPE
    SYNTAX     Gauge32
    MAX-ACCESS read-only
    STATUS     current
    DESCRIPTION
	    "Current number of partitions being processed."
    ::= { analysisServerProc 1 }

aspCurrentThreads OBJECT-TYPE
    SYNTAX     Gauge32
    MAX-ACCESS read-only
    STATUS     current
    DESCRIPTION
	    "Current number of threads working on
	    processing."
    ::= { analysisServerProc 2 }

aspCurrentThreadsMerging OBJECT-TYPE
    SYNTAX     Gauge32
    MAX-ACCESS read-only
    STATUS     current
    DESCRIPTION
	    "Current number of threads merging data. 
	    Decremented when blocked by pipeline of work."
    ::= { analysisServerProc 3 }

aspCurrentThreadsReading OBJECT-TYPE
    SYNTAX     Gauge32
    MAX-ACCESS read-only
    STATUS     current
    DESCRIPTION
	    "Current number of threads reading source data.
	     Decremented when blocked by pipeline of work."
    ::= { analysisServerProc 4 }

aspCurrentThreadsWriting OBJECT-TYPE
    SYNTAX     Gauge32
    MAX-ACCESS read-only
    STATUS     current
    DESCRIPTION
	    "Current number of threads writing data to
	    disk.  Decremented when blocked by pipeline of
	    work."
    ::= { analysisServerProc 5 }

aspFileBytesWrittenPerSec OBJECT-TYPE
    SYNTAX     Gauge32
    MAX-ACCESS read-only
    STATUS     current
    DESCRIPTION
	    "Rate of writing bytes to a MOLAP file."
    ::= { analysisServerProc 6 }

aspFileRowsWrittenPerSec OBJECT-TYPE
    SYNTAX     Gauge32
    MAX-ACCESS read-only
    STATUS     current
    DESCRIPTION
	    "Rate of writing rows to a MOLAP file."
    ::= { analysisServerProc 7 }

aspMemorySizeBytes OBJECT-TYPE
    SYNTAX     Gauge32
    MAX-ACCESS read-only
    STATUS     current
    DESCRIPTION
	    "Size of current rows in memory.  This count is
	    an estimate."
    ::= { analysisServerProc 8 }

aspMemorySizeRows OBJECT-TYPE
    SYNTAX     Gauge32
    MAX-ACCESS read-only
    STATUS     current
    DESCRIPTION
	    "Size of current rows in memory.  This count is
	    an estimate."
    ::= { analysisServerProc 9 }

aspRowsCreatedPerSec OBJECT-TYPE
    SYNTAX     Gauge32
    MAX-ACCESS read-only
    STATUS     current
    DESCRIPTION
	    "Rate of aggregation rows created.	This will
	    be different than rows read/sec if duplicates
	    exist."
    ::= { analysisServerProc 10 }

aspRowsMergedPerSec OBJECT-TYPE
    SYNTAX     Gauge32
    MAX-ACCESS read-only
    STATUS     current
    DESCRIPTION
	    "Rate of rows merged or inserted.  Compare with
	    rows/sec."
    ::= { analysisServerProc 11 }

aspRowsReadPerSec OBJECT-TYPE
    SYNTAX     Gauge32
    MAX-ACCESS read-only
    STATUS     current
    DESCRIPTION
	    "Rate of rows read from source database."
    ::= { analysisServerProc 12 }

aspTotalPartitions OBJECT-TYPE
    SYNTAX     Gauge32
    MAX-ACCESS read-only
    STATUS     current
    DESCRIPTION
	    "Accumulating count of partitions finished
	    processing.  This count is incremented if
	    processing is successful or not."
    ::= { analysisServerProc 13 }

aspTotalRows OBJECT-TYPE
    SYNTAX     Gauge32
    MAX-ACCESS read-only
    STATUS     current
    DESCRIPTION
	    "Count of rows read from source database."
    ::= { analysisServerProc 14 }

analysisServerProcAggs OBJECT-IDENTITY
    STATUS     current
    DESCRIPTION
	    "The Proc Aggs object counters provide
	    information about processing aggregations."
    ::= { sqlServer 6 }

aspaCurrentPartitions OBJECT-TYPE
    SYNTAX     Gauge32
    MAX-ACCESS read-only
    STATUS     current
    DESCRIPTION
	    "Current number of partitions being processed."
    ::= { analysisServerProcAggs 1 }

aspaMemorySizeBytes OBJECT-TYPE
    SYNTAX     Gauge32
    MAX-ACCESS read-only
    STATUS     current
    DESCRIPTION
	    "Size of current aggregations in memory.  This
	    count is an estimate."
    ::= { analysisServerProcAggs 2 }

aspaMemorySizeRows OBJECT-TYPE
    SYNTAX     Gauge32
    MAX-ACCESS read-only
    STATUS     current
    DESCRIPTION
	    "Size of current aggregations in memory.  This
	    count is an estimate."
    ::= { analysisServerProcAggs 3 }

aspaRowsCreatedPerSec OBJECT-TYPE
    SYNTAX     Gauge32
    MAX-ACCESS read-only
    STATUS     current
    DESCRIPTION
	    "Rate of aggregation rows created."
    ::= { analysisServerProcAggs 4 }

aspaRowsMergedPerSec OBJECT-TYPE
    SYNTAX     Gauge32
    MAX-ACCESS read-only
    STATUS     current
    DESCRIPTION
	    "Rate of rows merged or inserted into an
	    aggregation."
    ::= { analysisServerProcAggs 5 }

aspaTempFileBytesWrittenPerSec OBJECT-TYPE
    SYNTAX     Gauge32
    MAX-ACCESS read-only
    STATUS     current
    DESCRIPTION
	    "Rate of writing bytes to a temporary file. 
	    Temporary files are written when aggregations
	    exceed memory limits."
    ::= { analysisServerProcAggs 6 }

aspaTempFileRowsWrittenPerSec OBJECT-TYPE
    SYNTAX     Gauge32
    MAX-ACCESS read-only
    STATUS     current
    DESCRIPTION
	    "Rate of writing rows to a temporary file. 
	    Temporary files are written when aggregations
	    exceed memory limits."
    ::= { analysisServerProcAggs 7 }

aspaTotalPartitions OBJECT-TYPE
    SYNTAX     Gauge32
    MAX-ACCESS read-only
    STATUS     current
    DESCRIPTION
	    "Total number of partitions processed
	    (successfully or otherwise)."
    ::= { analysisServerProcAggs 8 }

analysisServerProcIndexes OBJECT-IDENTITY
    STATUS     current
    DESCRIPTION
	    "The Proc Indexes object counters provide
	    information about processing indexes."
    ::= { sqlServer 7 }

aspiCurrentPartitions OBJECT-TYPE
    SYNTAX     Gauge32
    MAX-ACCESS read-only
    STATUS     current
    DESCRIPTION
	    "Current number of partitions being processed."
    ::= { analysisServerProcIndexes 1 }

aspiRowsPerSec OBJECT-TYPE
    SYNTAX     Gauge32
    MAX-ACCESS read-only
    STATUS     current
    DESCRIPTION
	    "Rate of rows from MOLAP files used to create
	    indexes."
    ::= { analysisServerProcIndexes 2 }

aspiTotalPartitions OBJECT-TYPE
    SYNTAX     Gauge32
    MAX-ACCESS read-only
    STATUS     current
    DESCRIPTION
	    "Total number of partitions processed
	    (successfully or otherwise)."
    ::= { analysisServerProcIndexes 3 }

aspiTotalRows OBJECT-TYPE
    SYNTAX     Gauge32
    MAX-ACCESS read-only
    STATUS     current
    DESCRIPTION
	    "Total rows from MOLAP files used to create
	    indexes."
    ::= { analysisServerProcIndexes 4 }

analysisServerQuery OBJECT-IDENTITY
    STATUS     current
    DESCRIPTION
	    "The Query object counters provide information
	    about processing on the last query, such as
	    elapsed time in milliseconds of the last query
	    processed."
    ::= { sqlServer 8 }

asqAvgTimePerQuery OBJECT-TYPE
    SYNTAX     Gauge32
    MAX-ACCESS read-only
    STATUS     current
    DESCRIPTION
	    "Average time per query, in milliseconds. 
	    Response time based on queries answered since
	    the last counter measurement."
    ::= { analysisServerQuery 1 }

asqBytesSentPerSec OBJECT-TYPE
    SYNTAX     Gauge32
    MAX-ACCESS read-only
    STATUS     current
    DESCRIPTION
	    "Rate of bytes sent by server to clients, in
	    response to queries."
    ::= { analysisServerQuery 2 }

asqCurrentProcessThreadPool OBJECT-TYPE
    SYNTAX     Gauge32
    MAX-ACCESS read-only
    STATUS     current
    DESCRIPTION
	    "Count of threads in processing thread pool. 
	    These threads resolve queries."
    ::= { analysisServerQuery 3 }

asqCurrentProcessThreadQueueLen OBJECT-TYPE
    SYNTAX     Gauge32
    MAX-ACCESS read-only
    STATUS     current
    DESCRIPTION
	    "Current length of queue for processing thread
	    pool work items."
    ::= { analysisServerQuery 4 }

asqCurrentProcessThreadsActive OBJECT-TYPE
    SYNTAX     Gauge32
    MAX-ACCESS read-only
    STATUS     current
    DESCRIPTION
	    "Current number of process threads actively
	    working on queries."
    ::= { analysisServerQuery 5 }

asqCurrentPyramidOperations OBJECT-TYPE
    SYNTAX     Gauge32
    MAX-ACCESS read-only
    STATUS     current
    DESCRIPTION
	    "Current number of pyramid operations in
	    progress."
    ::= { analysisServerQuery 6 }

asqCurrentQueries OBJECT-TYPE
    SYNTAX     Gauge32
    MAX-ACCESS read-only
    STATUS     current
    DESCRIPTION
	    "Current number of queries being actively
	    worked on."
    ::= { analysisServerQuery 7 }

asqCurrentThreads OBJECT-TYPE
    SYNTAX     Gauge32
    MAX-ACCESS read-only
    STATUS     current
    DESCRIPTION
	    "Current number of threads working on queries."
    ::= { analysisServerQuery 8 }

asqCurrentWorkerThreadPool OBJECT-TYPE
    SYNTAX     Gauge32
    MAX-ACCESS read-only
    STATUS     current
    DESCRIPTION
	    "Count of threads in worker thread pool.  These
	    threads answer requests from clients."
    ::= { analysisServerQuery 9 }

asqCurrentWorkerThreadsActive OBJECT-TYPE
    SYNTAX     Gauge32
    MAX-ACCESS read-only
    STATUS     current
    DESCRIPTION
	    "Current number of worker threads active."
    ::= { analysisServerQuery 10 }

asqDataBytesPerSec OBJECT-TYPE
    SYNTAX     Gauge32
    MAX-ACCESS read-only
    STATUS     current
    DESCRIPTION
	    "Bytes read from the Data file."
    ::= { analysisServerQuery 11 }

asqDataReadsPerSec OBJECT-TYPE
    SYNTAX     Gauge32
    MAX-ACCESS read-only
    STATUS     current
    DESCRIPTION
	    "Number of logical read operations using the
	    Data file."
    ::= { analysisServerQuery 12 }

asqFilterRowsExcludedPerSec OBJECT-TYPE
    SYNTAX     Gauge32
    MAX-ACCESS read-only
    STATUS     current
    DESCRIPTION
	    "Rate of filtered rows excluded."
    ::= { analysisServerQuery 13 }

asqFilterRowsIncludedPerSec OBJECT-TYPE
    SYNTAX     Gauge32
    MAX-ACCESS read-only
    STATUS     current
    DESCRIPTION
	    "Rate of filtered rows included."
    ::= { analysisServerQuery 14 }

asqFilteredRowsPerSec OBJECT-TYPE
    SYNTAX     Gauge32
    MAX-ACCESS read-only
    STATUS     current
    DESCRIPTION
	    "Rate of rows filtered."
    ::= { analysisServerQuery 15 }

asqIndexBytesPerSec OBJECT-TYPE
    SYNTAX     Gauge32
    MAX-ACCESS read-only
    STATUS     current
    DESCRIPTION
	    "Bytes read from the Index file."
    ::= { analysisServerQuery 16 }

asqIndexReadsPerSec OBJECT-TYPE
    SYNTAX     Gauge32
    MAX-ACCESS read-only
    STATUS     current
    DESCRIPTION
	    "Number of logical read operations using the
	    Index file."
    ::= { analysisServerQuery 17 }

asqMapBytesPerSec OBJECT-TYPE
    SYNTAX     Gauge32
    MAX-ACCESS read-only
    STATUS     current
    DESCRIPTION
	    "Bytes read from the Map file."
    ::= { analysisServerQuery 18 }

asqMapReadsPerSec OBJECT-TYPE
    SYNTAX     Gauge32
    MAX-ACCESS read-only
    STATUS     current
    DESCRIPTION
	    "Number of logical read operations using the
	    Map file."
    ::= { analysisServerQuery 19 }

asqNetworkRoundTripsPerSec OBJECT-TYPE
    SYNTAX     Gauge32
    MAX-ACCESS read-only
    STATUS     current
    DESCRIPTION
	    "Rate of network round trips.  This includes
	    all client/server communication."
    ::= { analysisServerQuery 20 }

asqPyramidOperationsPerSec OBJECT-TYPE
    SYNTAX     Gauge32
    MAX-ACCESS read-only
    STATUS     current
    DESCRIPTION
	    "Rate of pyramid operations started."
    ::= { analysisServerQuery 21 }

asqQueriesAnsweredPerSec OBJECT-TYPE
    SYNTAX     Gauge32
    MAX-ACCESS read-only
    STATUS     current
    DESCRIPTION
	    "Rate of queries answered."
    ::= { analysisServerQuery 22 }

asqQueriesFromCacheDirectPerSec OBJECT-TYPE
    SYNTAX     Gauge32
    MAX-ACCESS read-only
    STATUS     current
    DESCRIPTION
	    "Rate of queries answered from cache directly."
    ::= { analysisServerQuery 23 }

asqQueriesFromCacheFilterPerSec OBJECT-TYPE
    SYNTAX     Gauge32
    MAX-ACCESS read-only
    STATUS     current
    DESCRIPTION
	    "Rate of queries answered by filtering existing
	    cache entry."
    ::= { analysisServerQuery 24 }

asqQueriesFromFilePerSec OBJECT-TYPE
    SYNTAX     Gauge32
    MAX-ACCESS read-only
    STATUS     current
    DESCRIPTION
	    "Rate of queries answered from files."
    ::= { analysisServerQuery 25 }

asqQueriesRequestedPerSec OBJECT-TYPE
    SYNTAX     Gauge32
    MAX-ACCESS read-only
    STATUS     current
    DESCRIPTION
	    "Rate of query requests arriving at the
	    server."
    ::= { analysisServerQuery 26 }

asqRowsReadPerSec OBJECT-TYPE
    SYNTAX     Gauge32
    MAX-ACCESS read-only
    STATUS     current
    DESCRIPTION
	    "Rate of rows read."
    ::= { analysisServerQuery 27 }

asqRowsSentPerSec OBJECT-TYPE
    SYNTAX     Gauge32
    MAX-ACCESS read-only
    STATUS     current
    DESCRIPTION
	    "Rate of rows sent by server to clients."
    ::= { analysisServerQuery 28 }

asqTotalBytesSent OBJECT-TYPE
    SYNTAX     Gauge32
    MAX-ACCESS read-only
    STATUS     current
    DESCRIPTION
	    "Total bytes sent by server to clients, in
	    response to queries."
    ::= { analysisServerQuery 29 }

asqTotalNetworkRoundTrips OBJECT-TYPE
    SYNTAX     Gauge32
    MAX-ACCESS read-only
    STATUS     current
    DESCRIPTION
	    "Total network round trips.  This includes all
	    client/server communication."
    ::= { analysisServerQuery 30 }

asqTotalPyramidOperations OBJECT-TYPE
    SYNTAX     Gauge32
    MAX-ACCESS read-only
    STATUS     current
    DESCRIPTION
	    "Total number of pyramid operations."
    ::= { analysisServerQuery 31 }

asqTotalQueriesAnswered OBJECT-TYPE
    SYNTAX     Gauge32
    MAX-ACCESS read-only
    STATUS     current
    DESCRIPTION
	    "Total number of queries answered."
    ::= { analysisServerQuery 32 }

asqTotalQueriesFromCacheDirect OBJECT-TYPE
    SYNTAX     Gauge32
    MAX-ACCESS read-only
    STATUS     current
    DESCRIPTION
	    "Total number of queries derived directly from
	    cache.  Note that this is per partition."
    ::= { analysisServerQuery 33 }

asqTotalQueriesFromCacheFiltered OBJECT-TYPE
    SYNTAX     Gauge32
    MAX-ACCESS read-only
    STATUS     current
    DESCRIPTION
	    "Total queries answered by filtering existing
	    cache entries."
    ::= { analysisServerQuery 34 }

asqTotalQueriesFromFile OBJECT-TYPE
    SYNTAX     Gauge32
    MAX-ACCESS read-only
    STATUS     current
    DESCRIPTION
	    "Total number of queries answered from files."
    ::= { analysisServerQuery 35 }

asqTotalQueriesRequested OBJECT-TYPE
    SYNTAX     Gauge32
    MAX-ACCESS read-only
    STATUS     current
    DESCRIPTION
	    "Total number of queries requested."
    ::= { analysisServerQuery 36 }

asqTotalRowsSent OBJECT-TYPE
    SYNTAX     Gauge32
    MAX-ACCESS read-only
    STATUS     current
    DESCRIPTION
	    "Total rows sent by server to clients."
    ::= { analysisServerQuery 37 }

analysisServerQueryDims OBJECT-IDENTITY
    STATUS     current
    DESCRIPTION
	    "The Query Dims object counters provide
	    information about processing queries
	    dimensions."
    ::= { sqlServer 9 }

asqdBytesPerSec OBJECT-TYPE
    SYNTAX     Gauge32
    MAX-ACCESS read-only
    STATUS     current
    DESCRIPTION
	    "Rate of sending bytes."
    ::= { analysisServerQueryDims 1 }

asqdCurrentRequests OBJECT-TYPE
    SYNTAX     Gauge32
    MAX-ACCESS read-only
    STATUS     current
    DESCRIPTION
	    "Current number of requests for part of the
	    member tree or for member properties."
    ::= { analysisServerQueryDims 2 }

asqdMembersPerSec OBJECT-TYPE
    SYNTAX     Gauge32
    MAX-ACCESS read-only
    STATUS     current
    DESCRIPTION
	    "Rate of sending members."
    ::= { analysisServerQueryDims 3 }

asqdRequestsPerSec OBJECT-TYPE
    SYNTAX     Gauge32
    MAX-ACCESS read-only
    STATUS     current
    DESCRIPTION
	    "Rate of requests for part of the member tree
	    or for member properties.  Consider increasing
	    Large Level Threshold if this counter is
	    excessive."
    ::= { analysisServerQueryDims 4 }

asqdTotalVLDMRequests OBJECT-TYPE
    SYNTAX     Gauge32
    MAX-ACCESS read-only
    STATUS     current
    DESCRIPTION
	    "Total VLDM (Very Large Dimension Manager)
	    requests sent."
    ::= { analysisServerQueryDims 5 }

asqdTotalBytes OBJECT-TYPE
    SYNTAX     Gauge32
    MAX-ACCESS read-only
    STATUS     current
    DESCRIPTION
	    "Total bytes sent."
    ::= { analysisServerQueryDims 6 }

asqdTotalMembers OBJECT-TYPE
    SYNTAX     Gauge32
    MAX-ACCESS read-only
    STATUS     current
    DESCRIPTION
	    "Total members sent."
    ::= { analysisServerQueryDims 7 }

asqdTotalRequests OBJECT-TYPE
    SYNTAX     Gauge32
    MAX-ACCESS read-only
    STATUS     current
    DESCRIPTION
	    "Total number of requests for part of the
	    member tree or for member properties."
    ::= { analysisServerQueryDims 8 }

asqdVLDMRequestsPerSec OBJECT-TYPE
    SYNTAX     Gauge32
    MAX-ACCESS read-only
    STATUS     current
    DESCRIPTION
	    "Rate of VLDM (Very Large Dimension Manager)
	    requests."
    ::= { analysisServerQueryDims 9 }

analysisServerStartup OBJECT-IDENTITY
    STATUS     current
    DESCRIPTION
	    "The Startup object counters provide
	    information about processing startups."
    ::= { sqlServer 10 }

assBytesPerSec OBJECT-TYPE
    SYNTAX     Gauge32
    MAX-ACCESS read-only
    STATUS     current
    DESCRIPTION
	    "Rate of bytes read from dimension files."
    ::= { analysisServerStartup 1 }

assMembersPerSec OBJECT-TYPE
    SYNTAX     Gauge32
    MAX-ACCESS read-only
    STATUS     current
    DESCRIPTION
	    "Rate of loading members."
    ::= { analysisServerStartup 2 }

assPropertiesPerSec OBJECT-TYPE
    SYNTAX     Gauge32
    MAX-ACCESS read-only
    STATUS     current
    DESCRIPTION
	    "Rate of loading properties."
    ::= { analysisServerStartup 3 }

assServerUptime OBJECT-TYPE
    SYNTAX     Gauge32
    MAX-ACCESS read-only
    STATUS     current
    DESCRIPTION
	    "Time server has been running."
    ::= { analysisServerStartup 4 }

assTotalBytes OBJECT-TYPE
    SYNTAX     Gauge32
    MAX-ACCESS read-only
    STATUS     current
    DESCRIPTION
	    "Total bytes read from dimension files."
    ::= { analysisServerStartup 5 }

assTotalDimensions OBJECT-TYPE
    SYNTAX     Gauge32
    MAX-ACCESS read-only
    STATUS     current
    DESCRIPTION
	    "Total number of dimensions loaded."
    ::= { analysisServerStartup 6 }

assTotalMembers OBJECT-TYPE
    SYNTAX     Gauge32
    MAX-ACCESS read-only
    STATUS     current
    DESCRIPTION
	    "Total number of members loaded."
    ::= { analysisServerStartup 7 }

assTotalProperties OBJECT-TYPE
    SYNTAX     Gauge32
    MAX-ACCESS read-only
    STATUS     current
    DESCRIPTION
	    "Total number of properties loaded."
    ::= { analysisServerStartup 8 }

microsoftGatherer OBJECT IDENTIFIER
    ::= { sqlServer 11 }

mgAccessingRobotsTxtFile OBJECT-TYPE
    SYNTAX     Gauge32
    MAX-ACCESS read-only
    STATUS     current
    DESCRIPTION
	    "The number of current requests for robots.txt.
	    Robots.txt is requested by the system
	    implicitly, for every host, through HTTP."
    ::= { microsoftGatherer 1 }

mgActiveQueueLength OBJECT-TYPE
    SYNTAX     Gauge32
    MAX-ACCESS read-only
    STATUS     current
    DESCRIPTION
	    "The number of documents waiting for robot
	    threads. If this number is not 0, all threads
	    should be filtering."
    ::= { microsoftGatherer 2 }

mgAdminClients OBJECT-TYPE
    SYNTAX     Gauge32
    MAX-ACCESS read-only
    STATUS     current
    DESCRIPTION
	    "The number of currently connected
	    administrative clients."
    ::= { microsoftGatherer 3 }

mgAllNotificationsReceived OBJECT-TYPE
    SYNTAX     Gauge32
    MAX-ACCESS read-only
    STATUS     current
    DESCRIPTION
	    "The total number of notifications received
	    from all notification sources including file
	    system."
    ::= { microsoftGatherer 4 }

mgDelayedDocuments OBJECT-TYPE
    SYNTAX     Gauge32
    MAX-ACCESS read-only
    STATUS     current
    DESCRIPTION
	    "The number of documents delayed due to site
	    hit frequency rules."
    ::= { microsoftGatherer 5 }

mgDocumentEntries OBJECT-TYPE
    SYNTAX     Gauge32
    MAX-ACCESS read-only
    STATUS     current
    DESCRIPTION
	    "The number of document entries currently in
	    memory. Zero means no indexing activity is
	    going on."
    ::= { microsoftGatherer 6 }

mgDocumentsDelayedRetry OBJECT-TYPE
    SYNTAX     Gauge32
    MAX-ACCESS read-only
    STATUS     current
    DESCRIPTION
	    "The number of documents that will be retried
	    after time-out. When this is non-zero, it means
	    that the local server it is crawling is shut
	    down."
    ::= { microsoftGatherer 7 }

mgDocumentsFiltered OBJECT-TYPE
    SYNTAX     Gauge32
    MAX-ACCESS read-only
    STATUS     current
    DESCRIPTION
	    "The number of times a filter object was
	    created. This corresponds to the total number
	    of documents filtered in the system since
	    startup."
    ::= { microsoftGatherer 8 }

mgDocumentsFilteredRate OBJECT-TYPE
    SYNTAX     Gauge32
    MAX-ACCESS read-only
    STATUS     current
    DESCRIPTION
	    "The number of documents filtered per second."
    ::= { microsoftGatherer 9 }

mgDocumentsSuccessfullyFiltered OBJECT-TYPE
    SYNTAX     Gauge32
    MAX-ACCESS read-only
    STATUS     current
    DESCRIPTION
	    "The number of documents successfully
	    filtered."
    ::= { microsoftGatherer 10 }

mgDocumentsSuccessfulFilterRate OBJECT-TYPE
    SYNTAX     Gauge32
    MAX-ACCESS read-only
    STATUS     current
    DESCRIPTION
	    "The number of successfully filtered documents
	    per second."
    ::= { microsoftGatherer 11 }

mgExtNotificationsRate OBJECT-TYPE
    SYNTAX     Gauge32
    MAX-ACCESS read-only
    STATUS     current
    DESCRIPTION
	    "The rate of external notifications received
	    per second."
    ::= { microsoftGatherer 12 }

mgExtNotificationsReceived OBJECT-TYPE
    SYNTAX     Gauge32
    MAX-ACCESS read-only
    STATUS     current
    DESCRIPTION
	    "The total number of notifications received
	    from all notification sources excluding file
	    system."
    ::= { microsoftGatherer 13 }

mgFilterObjects OBJECT-TYPE
    SYNTAX     Gauge32
    MAX-ACCESS read-only
    STATUS     current
    DESCRIPTION
	    "The number of filter objects in the system.
	    Each filter object corresponds to a URL
	    currently being filtered."
    ::= { microsoftGatherer 14 }

mgFilterProcessCreated OBJECT-TYPE
    SYNTAX     Gauge32
    MAX-ACCESS read-only
    STATUS     current
    DESCRIPTION
	    "The total number of times a filter process was
	    created or restarted. Having too many filter
	    processes created indicates that filtering is
	    having trouble with the data in the documents."
    ::= { microsoftGatherer 15 }

mgFilterProcesses OBJECT-TYPE
    SYNTAX     Gauge32
    MAX-ACCESS read-only
    STATUS     current
    DESCRIPTION
	    "The number of filtering processes in the
	    system."
    ::= { microsoftGatherer 16 }

mgFilterProcessesMax OBJECT-TYPE
    SYNTAX     Gauge32
    MAX-ACCESS read-only
    STATUS     current
    DESCRIPTION
	    "The maximum number of filtering processes that
	    have existed in the system since startup."
    ::= { microsoftGatherer 17 }

mgFilteringThreads OBJECT-TYPE
    SYNTAX     Gauge32
    MAX-ACCESS read-only
    STATUS     current
    DESCRIPTION
	    "The total number of filtering threads in the
	    system. This number is calculated based on your
	    system resources."
    ::= { microsoftGatherer 18 }

mgHeartbeats OBJECT-TYPE
    SYNTAX     Gauge32
    MAX-ACCESS read-only
    STATUS     current
    DESCRIPTION
	    "The total number of heartbeats counted since
	    startup. A heartbeat occurs once every 10
	    seconds while the service is running. If the
	    service is not running there will be no
	    heartbeat and the number of ticks will not be
	    incremented."
    ::= { microsoftGatherer 19 }

mgHeartbeatsRate OBJECT-TYPE
    SYNTAX     Gauge32
    MAX-ACCESS read-only
    STATUS     current
    DESCRIPTION
	    "Displays one heartbeat every 10 seconds."
    ::= { microsoftGatherer 20 }

mgIdleThreads OBJECT-TYPE
    SYNTAX     Gauge32
    MAX-ACCESS read-only
    STATUS     current
    DESCRIPTION
	    "The number of threads waiting for documents."
    ::= { microsoftGatherer 21 }

mgNotificationSources OBJECT-TYPE
    SYNTAX     Gauge32
    MAX-ACCESS read-only
    STATUS     current
    DESCRIPTION
	    "Currently connected external notification
	    sources."
    ::= { microsoftGatherer 22 }

mgNotificationsRate OBJECT-TYPE
    SYNTAX     Gauge32
    MAX-ACCESS read-only
    STATUS     current
    DESCRIPTION
	    "The rate of external notifications received
	    per second."
    ::= { microsoftGatherer 23 }

mgPerformanceLevel OBJECT-TYPE
    SYNTAX     Gauge32
    MAX-ACCESS read-only
    STATUS     current
    DESCRIPTION
	    "Indicates the level of the amount of system
	    resources that the Gatherer service is allowed
	    to use."
    ::= { microsoftGatherer 24 }

mgReasonToBackOff OBJECT-TYPE
    SYNTAX     Gauge32
    MAX-ACCESS read-only
    STATUS     current
    DESCRIPTION
	    "The code describing why the Gatherer service
	    went into back off state. 0 - up and running 1
	    - high system IO traffic 2 - high notifications
	    rate 3 - delayed recovery in progress (not
	    implemented) 4 - back off due to user activity
	    5 - Battery Low 6 - Memory Low 99 - back off
	    for some internal reason (forced by Search
	    itself) While backing off, no indexing is
	    performed. To resume the indexing you must
	    eliminate the reason for back off. If the
	    Gatherer service is in back off state, the
	    Search service is paused and there is a message
	    in the event log."
    ::= { microsoftGatherer 25 }

mgRobotsTxtRequests OBJECT-TYPE
    SYNTAX     Gauge32
    MAX-ACCESS read-only
    STATUS     current
    DESCRIPTION
	    "The total number of requests for robots.txt."
    ::= { microsoftGatherer 26 }

mgServerObjects OBJECT-TYPE
    SYNTAX     Gauge32
    MAX-ACCESS read-only
    STATUS     current
    DESCRIPTION
	    "The number of servers recently accessed by the
	    system."
    ::= { microsoftGatherer 27 }

mgServerObjectsCreated OBJECT-TYPE
    SYNTAX     Gauge32
    MAX-ACCESS read-only
    STATUS     current
    DESCRIPTION
	    "The number of times a new server object had to
	    be created."
    ::= { microsoftGatherer 28 }

mgServersCurrentlyUnavailable OBJECT-TYPE
    SYNTAX     Gauge32
    MAX-ACCESS read-only
    STATUS     current
    DESCRIPTION
	    "A server becomes unavailable when a number of
	    requests to that server time out."
    ::= { microsoftGatherer 29 }

mgServersUnavailable OBJECT-TYPE
    SYNTAX     Gauge32
    MAX-ACCESS read-only
    STATUS     current
    DESCRIPTION
	    "A server becomes unavailable when a number of
	    requests to that server time out."
    ::= { microsoftGatherer 30 }

mgStemmersCached OBJECT-TYPE
    SYNTAX     Gauge32
    MAX-ACCESS read-only
    STATUS     current
    DESCRIPTION
	    "Number of available cached stemmer instances.
	    Too many may indicate a resource usage
	    problem."
    ::= { microsoftGatherer 31 }

mgSystemIOTrafficRate OBJECT-TYPE
    SYNTAX     Gauge32
    MAX-ACCESS read-only
    STATUS     current
    DESCRIPTION
	    "System IO (disk) traffic rate in KB/s detected
	    by back off logic"
    ::= { microsoftGatherer 32 }

mgThreadsAccessingNetwork OBJECT-TYPE
    SYNTAX     Gauge32
    MAX-ACCESS read-only
    STATUS     current
    DESCRIPTION
	    "The number of threads waiting for a response
	    from the filter process. If no activity is
	    going on and this number is equal to number of
	    filtering threads, it may indicate a network
	    problem or unavailability of the server it is
	    crawling."
    ::= { microsoftGatherer 33 }

mgThreadsInPlugIns OBJECT-TYPE
    SYNTAX     Gauge32
    MAX-ACCESS read-only
    STATUS     current
    DESCRIPTION
	    "The number of threads waiting for plug-ins to
	    complete an operation."
    ::= { microsoftGatherer 34 }

mgThreadsBlockedDueToBackOff OBJECT-TYPE
    SYNTAX     Gauge32
    MAX-ACCESS read-only
    STATUS     current
    DESCRIPTION
	    "The number of threads blocked due to back off
	    event"
    ::= { microsoftGatherer 35 }

mgTimeOuts OBJECT-TYPE
    SYNTAX     Gauge32
    MAX-ACCESS read-only
    STATUS     current
    DESCRIPTION
	    "The total number of timeouts detected by the
	    system since startup."
    ::= { microsoftGatherer 36 }

mgWordBreakersCached OBJECT-TYPE
    SYNTAX     Gauge32
    MAX-ACCESS read-only
    STATUS     current
    DESCRIPTION
	    "Number of available cached word breakers
	    instances"
    ::= { microsoftGatherer 37 }

microsoftGathererProjectsTable OBJECT-TYPE
    SYNTAX     SEQUENCE OF MicrosoftGathererProjectsEntry
    MAX-ACCESS not-accessible
    STATUS     current
    DESCRIPTION
	    "Counters for the Microsoft Gatherer Project
	    object"
    ::= { sqlServer 12 }

microsoftGathererProjectsEntry OBJECT-TYPE
    SYNTAX     MicrosoftGathererProjectsEntry
    MAX-ACCESS not-accessible
    STATUS     current
    DESCRIPTION
	    "Performance information for one particular
	    instance of 'Microsoft Gatherer Projects'
	    object."
    INDEX      { mgpInstance }
    ::= { microsoftGathererProjectsTable 1 }

MicrosoftGathererProjectsEntry ::= SEQUENCE {
    mgpInstance InstanceName,
    mgpAccessedFileRate Gauge32,
    mgpAccessedFiles Gauge32,
    mgpAccessedHTTP Gauge32,
    mgpAccessedHTTPRate Gauge32,
    mgpAdaptiveCrawlAccepts Gauge32,
    mgpAdaptiveCrawlErrorSamples Gauge32,
    mgpAdaptiveCrawlErrors Gauge32,
    mgpAdaptiveCrawlExcludes Gauge32,
    mgpAdaptiveCrawlFalsePositives Gauge32,
    mgpAdaptiveCrawlTotal Gauge32,
    mgpChangedDocuments Gauge32,
    mgpDelayedDocuments Gauge32,
    mgpDocumentAddRate Gauge32,
    mgpDocumentAdditions Gauge32,
    mgpDocumentDeleteRate Gauge32,
    mgpDocumentDeletes Gauge32,
    mgpDocumentModifies Gauge32,
    mgpDocumentModifiesRate Gauge32,
    mgpDocumentMoveAndRenameRate Gauge32,
    mgpDocumentMovesPerRenames Gauge32,
    mgpDocumentsInProgress Gauge32,
    mgpDocumentsOnHold Gauge32,
    mgpErrorRate Gauge32,
    mgpFileErrors Gauge32,
    mgpFileErrorsRate Gauge32,
    mgpFilteredHTML Gauge32,
    mgpFilteredHTMLRate Gauge32,
    mgpFilteredOffice Gauge32,
    mgpFilteredOfficeRate Gauge32,
    mgpFilteredText Gauge32,
    mgpFilteredTextRate Gauge32,
    mgpFilteringDocuments Gauge32,
    mgpGathererPausedFlag Gauge32,
    mgpHTTPErrors Gauge32,
    mgpHTTPErrorsRate Gauge32,
    mgpHistoryRecoveryProgress Gauge32,
    mgpIterateHistoryInProgressFlag Gauge32,
    mgpNotModified Gauge32,
    mgpProcessedDocuments Gauge32,
    mgpProcessedDocumentsRate Gauge32,
    mgpRecoveryInProgressFlag Gauge32,
    mgpRetries Gauge32,
    mgpRetriesRate Gauge32,
    mgpStartedDocuments Gauge32,
    mgpStatusError Gauge32,
    mgpStatusSuccess Gauge32,
    mgpSuccessRate Gauge32,
    mgpURLsInHistory Gauge32,
    mgpUniqueDocuments Gauge32,
    mgpWaitingDocuments Gauge32
}

mgpInstance OBJECT-TYPE
    SYNTAX     InstanceName
    MAX-ACCESS read-only
    STATUS     current
    DESCRIPTION
	    "Instance name."
    ::= { microsoftGathererProjectsEntry 1 }

mgpAccessedFileRate OBJECT-TYPE
    SYNTAX     Gauge32
    MAX-ACCESS read-only
    STATUS     current
    DESCRIPTION
	    "The number of documents accessed via file
	    system per second."
    ::= { microsoftGathererProjectsEntry 2 }

mgpAccessedFiles OBJECT-TYPE
    SYNTAX     Gauge32
    MAX-ACCESS read-only
    STATUS     current
    DESCRIPTION
	    "The number of documents accessed via file
	    system."
    ::= { microsoftGathererProjectsEntry 3 }

mgpAccessedHTTP OBJECT-TYPE
    SYNTAX     Gauge32
    MAX-ACCESS read-only
    STATUS     current
    DESCRIPTION
	    "The number of documents accessed via HTTP."
    ::= { microsoftGathererProjectsEntry 4 }

mgpAccessedHTTPRate OBJECT-TYPE
    SYNTAX     Gauge32
    MAX-ACCESS read-only
    STATUS     current
    DESCRIPTION
	    "The number of documents accessed via HTTP per
	    second."
    ::= { microsoftGathererProjectsEntry 5 }

mgpAdaptiveCrawlAccepts OBJECT-TYPE
    SYNTAX     Gauge32
    MAX-ACCESS read-only
    STATUS     current
    DESCRIPTION
	    "Documents accepted by adaptive crawl"
    ::= { microsoftGathererProjectsEntry 6 }

mgpAdaptiveCrawlErrorSamples OBJECT-TYPE
    SYNTAX     Gauge32
    MAX-ACCESS read-only
    STATUS     current
    DESCRIPTION
	    "Documents accessed for error sampling"
    ::= { microsoftGathererProjectsEntry 7 }

mgpAdaptiveCrawlErrors OBJECT-TYPE
    SYNTAX     Gauge32
    MAX-ACCESS read-only
    STATUS     current
    DESCRIPTION
	    "Documents incorrectly rejected by adaptive
	    crawl"
    ::= { microsoftGathererProjectsEntry 8 }

mgpAdaptiveCrawlExcludes OBJECT-TYPE
    SYNTAX     Gauge32
    MAX-ACCESS read-only
    STATUS     current
    DESCRIPTION
	    "Documents excluded by adaptive crawl"
    ::= { microsoftGathererProjectsEntry 9 }

mgpAdaptiveCrawlFalsePositives OBJECT-TYPE
    SYNTAX     Gauge32
    MAX-ACCESS read-only
    STATUS     current
    DESCRIPTION
	    "Documents incorrectly accepted by adaptive
	    crawl"
    ::= { microsoftGathererProjectsEntry 10 }

mgpAdaptiveCrawlTotal OBJECT-TYPE
    SYNTAX     Gauge32
    MAX-ACCESS read-only
    STATUS     current
    DESCRIPTION
	    "Documents to which adaptive crawl logic was
	    applied"
    ::= { microsoftGathererProjectsEntry 11 }

mgpChangedDocuments OBJECT-TYPE
    SYNTAX     Gauge32
    MAX-ACCESS read-only
    STATUS     current
    DESCRIPTION
	    "Changed Documents"
    ::= { microsoftGathererProjectsEntry 12 }

mgpDelayedDocuments OBJECT-TYPE
    SYNTAX     Gauge32
    MAX-ACCESS read-only
    STATUS     current
    DESCRIPTION
	    "The number of documents delayed due to site
	    hit frequency rules."
    ::= { microsoftGathererProjectsEntry 13 }

mgpDocumentAddRate OBJECT-TYPE
    SYNTAX     Gauge32
    MAX-ACCESS read-only
    STATUS     current
    DESCRIPTION
	    "The number of document additions per second."
    ::= { microsoftGathererProjectsEntry 14 }

mgpDocumentAdditions OBJECT-TYPE
    SYNTAX     Gauge32
    MAX-ACCESS read-only
    STATUS     current
    DESCRIPTION
	    "The number of add notifications."
    ::= { microsoftGathererProjectsEntry 15 }

mgpDocumentDeleteRate OBJECT-TYPE
    SYNTAX     Gauge32
    MAX-ACCESS read-only
    STATUS     current
    DESCRIPTION
	    "The number of document deletes per second."
    ::= { microsoftGathererProjectsEntry 16 }

mgpDocumentDeletes OBJECT-TYPE
    SYNTAX     Gauge32
    MAX-ACCESS read-only
    STATUS     current
    DESCRIPTION
	    "The number of delete notifications."
    ::= { microsoftGathererProjectsEntry 17 }

mgpDocumentModifies OBJECT-TYPE
    SYNTAX     Gauge32
    MAX-ACCESS read-only
    STATUS     current
    DESCRIPTION
	    "The number of modify notifications."
    ::= { microsoftGathererProjectsEntry 18 }

mgpDocumentModifiesRate OBJECT-TYPE
    SYNTAX     Gauge32
    MAX-ACCESS read-only
    STATUS     current
    DESCRIPTION
	    "The number of modify notifications per
	    second."
    ::= { microsoftGathererProjectsEntry 19 }

mgpDocumentMoveAndRenameRate OBJECT-TYPE
    SYNTAX     Gauge32
    MAX-ACCESS read-only
    STATUS     current
    DESCRIPTION
	    "The number of document Moves and Renames per
	    second."
    ::= { microsoftGathererProjectsEntry 20 }

mgpDocumentMovesPerRenames OBJECT-TYPE
    SYNTAX     Gauge32
    MAX-ACCESS read-only
    STATUS     current
    DESCRIPTION
	    "The number of Move/Rename notifications."
    ::= { microsoftGathererProjectsEntry 21 }

mgpDocumentsInProgress OBJECT-TYPE
    SYNTAX     Gauge32
    MAX-ACCESS read-only
    STATUS     current
    DESCRIPTION
	    "The number of documents in progress."
    ::= { microsoftGathererProjectsEntry 22 }

mgpDocumentsOnHold OBJECT-TYPE
    SYNTAX     Gauge32
    MAX-ACCESS read-only
    STATUS     current
    DESCRIPTION
	    "The number of documents on hold because a
	    document with the same URL is currently in
	    process."
    ::= { microsoftGathererProjectsEntry 23 }

mgpErrorRate OBJECT-TYPE
    SYNTAX     Gauge32
    MAX-ACCESS read-only
    STATUS     current
    DESCRIPTION
	    "The number of filtered documents which
	    returned an error per second."
    ::= { microsoftGathererProjectsEntry 24 }

mgpFileErrors OBJECT-TYPE
    SYNTAX     Gauge32
    MAX-ACCESS read-only
    STATUS     current
    DESCRIPTION
	    "The number of file protocol errors received
	    while getting documents."
    ::= { microsoftGathererProjectsEntry 25 }

mgpFileErrorsRate OBJECT-TYPE
    SYNTAX     Gauge32
    MAX-ACCESS read-only
    STATUS     current
    DESCRIPTION
	    "The number of file protocol errors received
	    per second."
    ::= { microsoftGathererProjectsEntry 26 }

mgpFilteredHTML OBJECT-TYPE
    SYNTAX     Gauge32
    MAX-ACCESS read-only
    STATUS     current
    DESCRIPTION
	    "The number of HTML documents filtered."
    ::= { microsoftGathererProjectsEntry 27 }

mgpFilteredHTMLRate OBJECT-TYPE
    SYNTAX     Gauge32
    MAX-ACCESS read-only
    STATUS     current
    DESCRIPTION
	    "The number of HTML documents filtered per
	    second."
    ::= { microsoftGathererProjectsEntry 28 }

mgpFilteredOffice OBJECT-TYPE
    SYNTAX     Gauge32
    MAX-ACCESS read-only
    STATUS     current
    DESCRIPTION
	    "The number of office documents filtered."
    ::= { microsoftGathererProjectsEntry 29 }

mgpFilteredOfficeRate OBJECT-TYPE
    SYNTAX     Gauge32
    MAX-ACCESS read-only
    STATUS     current
    DESCRIPTION
	    "The number of office documents filtered per
	    second."
    ::= { microsoftGathererProjectsEntry 30 }

mgpFilteredText OBJECT-TYPE
    SYNTAX     Gauge32
    MAX-ACCESS read-only
    STATUS     current
    DESCRIPTION
	    "The number of text documents filtered."
    ::= { microsoftGathererProjectsEntry 31 }

mgpFilteredTextRate OBJECT-TYPE
    SYNTAX     Gauge32
    MAX-ACCESS read-only
    STATUS     current
    DESCRIPTION
	    "The number of text documents filtered per
	    second."
    ::= { microsoftGathererProjectsEntry 32 }

mgpFilteringDocuments OBJECT-TYPE
    SYNTAX     Gauge32
    MAX-ACCESS read-only
    STATUS     current
    DESCRIPTION
	    "The number of documents currently being
	    filtered."
    ::= { microsoftGathererProjectsEntry 33 }

mgpGathererPausedFlag OBJECT-TYPE
    SYNTAX     Gauge32
    MAX-ACCESS read-only
    STATUS     current
    DESCRIPTION
	    "The Gatherer paused flag indicates if the
	    Gatherer has been paused."
    ::= { microsoftGathererProjectsEntry 34 }

mgpHTTPErrors OBJECT-TYPE
    SYNTAX     Gauge32
    MAX-ACCESS read-only
    STATUS     current
    DESCRIPTION
	    "The number of HTTP errors received."
    ::= { microsoftGathererProjectsEntry 35 }

mgpHTTPErrorsRate OBJECT-TYPE
    SYNTAX     Gauge32
    MAX-ACCESS read-only
    STATUS     current
    DESCRIPTION
	    "The number of HTTP errors received per second"
    ::= { microsoftGathererProjectsEntry 36 }

mgpHistoryRecoveryProgress OBJECT-TYPE
    SYNTAX     Gauge32
    MAX-ACCESS read-only
    STATUS     current
    DESCRIPTION
	    "Percentage of the history recovery completed"
    ::= { microsoftGathererProjectsEntry 37 }

mgpIterateHistoryInProgressFlag OBJECT-TYPE
    SYNTAX     Gauge32
    MAX-ACCESS read-only
    STATUS     current
    DESCRIPTION
	    "The Iterating history in progress flag
	    indicates if the Gatherer is currently
	    iterating over the URL history."
    ::= { microsoftGathererProjectsEntry 38 }

mgpNotModified OBJECT-TYPE
    SYNTAX     Gauge32
    MAX-ACCESS read-only
    STATUS     current
    DESCRIPTION
	    "The number of documents which were not
	    filtered because no modification was detected
	    since the last crawl."
    ::= { microsoftGathererProjectsEntry 39 }

mgpProcessedDocuments OBJECT-TYPE
    SYNTAX     Gauge32
    MAX-ACCESS read-only
    STATUS     current
    DESCRIPTION
	    "The number of documents processed since the
	    history has been reset."
    ::= { microsoftGathererProjectsEntry 40 }

mgpProcessedDocumentsRate OBJECT-TYPE
    SYNTAX     Gauge32
    MAX-ACCESS read-only
    STATUS     current
    DESCRIPTION
	    "The number of documents processed per second."
    ::= { microsoftGathererProjectsEntry 41 }

mgpRecoveryInProgressFlag OBJECT-TYPE
    SYNTAX     Gauge32
    MAX-ACCESS read-only
    STATUS     current
    DESCRIPTION
	    "The Recovery in progress flag indicates if
	    recovery is currently in progress.	"
    ::= { microsoftGathererProjectsEntry 42 }

mgpRetries OBJECT-TYPE
    SYNTAX     Gauge32
    MAX-ACCESS read-only
    STATUS     current
    DESCRIPTION
	    "The total number of times a document access
	    has been retried."
    ::= { microsoftGathererProjectsEntry 43 }

mgpRetriesRate OBJECT-TYPE
    SYNTAX     Gauge32
    MAX-ACCESS read-only
    STATUS     current
    DESCRIPTION
	    "The number of retries per second."
    ::= { microsoftGathererProjectsEntry 44 }

mgpStartedDocuments OBJECT-TYPE
    SYNTAX     Gauge32
    MAX-ACCESS read-only
    STATUS     current
    DESCRIPTION
	    "The number of documents initiated into the
	    Gatherer service. This includes the number of
	    documents on hold, in the active queue, and
	    currently filtered."
    ::= { microsoftGathererProjectsEntry 45 }

mgpStatusError OBJECT-TYPE
    SYNTAX     Gauge32
    MAX-ACCESS read-only
    STATUS     current
    DESCRIPTION
	    "The number of filtered documents which
	    returned an error."
    ::= { microsoftGathererProjectsEntry 46 }

mgpStatusSuccess OBJECT-TYPE
    SYNTAX     Gauge32
    MAX-ACCESS read-only
    STATUS     current
    DESCRIPTION
	    "The number of successfully filtered
	    documents."
    ::= { microsoftGathererProjectsEntry 47 }

mgpSuccessRate OBJECT-TYPE
    SYNTAX     Gauge32
    MAX-ACCESS read-only
    STATUS     current
    DESCRIPTION
	    "The number of successfully filtered documents
	    per second."
    ::= { microsoftGathererProjectsEntry 48 }

mgpURLsInHistory OBJECT-TYPE
    SYNTAX     Gauge32
    MAX-ACCESS read-only
    STATUS     current
    DESCRIPTION
	    "The number of files (URLs) in the history
	    list."
    ::= { microsoftGathererProjectsEntry 49 }

mgpUniqueDocuments OBJECT-TYPE
    SYNTAX     Gauge32
    MAX-ACCESS read-only
    STATUS     current
    DESCRIPTION
	    "Number of unique documents in the system.
	    Documents are considered not unique if their
	    contents is the same."
    ::= { microsoftGathererProjectsEntry 50 }

mgpWaitingDocuments OBJECT-TYPE
    SYNTAX     Gauge32
    MAX-ACCESS read-only
    STATUS     current
    DESCRIPTION
	    "The number of documents waiting to be
	    processed."
    ::= { microsoftGathererProjectsEntry 51 }

microsoftSearch OBJECT-IDENTITY
    STATUS     current
    DESCRIPTION
	    "Global counters in the Microsoft search
	    service."
    ::= { sqlServer 13 }

msActiveThreads OBJECT-TYPE
    SYNTAX     Gauge32
    MAX-ACCESS read-only
    STATUS     current
    DESCRIPTION
	    "The total number of threads currently
	    servicing queries."
    ::= { microsoftSearch 1 }

msCurrentConnections OBJECT-TYPE
    SYNTAX     Gauge32
    MAX-ACCESS read-only
    STATUS     current
    DESCRIPTION
	    "The number of currently established
	    connections between the Search service and all
	    clients."
    ::= { microsoftSearch 2 }

msFailedQueries OBJECT-TYPE
    SYNTAX     Gauge32
    MAX-ACCESS read-only
    STATUS     current
    DESCRIPTION
	    "The number of queries that have failed."
    ::= { microsoftSearch 3 }

msFailedQueryRate OBJECT-TYPE
    SYNTAX     Gauge32
    MAX-ACCESS read-only
    STATUS     current
    DESCRIPTION
	    "The number of failed queries per second."
    ::= { microsoftSearch 4 }

msQueries OBJECT-TYPE
    SYNTAX     Gauge32
    MAX-ACCESS read-only
    STATUS     current
    DESCRIPTION
	    "Cumulative number of queries posted to the
	    server."
    ::= { microsoftSearch 5 }

msQueryRate OBJECT-TYPE
    SYNTAX     Gauge32
    MAX-ACCESS read-only
    STATUS     current
    DESCRIPTION
	    "The number of queries posted to the server per
	    second."
    ::= { microsoftSearch 6 }

msResultRate OBJECT-TYPE
    SYNTAX     Gauge32
    MAX-ACCESS read-only
    STATUS     current
    DESCRIPTION
	    "The number of results returned to the client
	    per second."
    ::= { microsoftSearch 7 }

msResults OBJECT-TYPE
    SYNTAX     Gauge32
    MAX-ACCESS read-only
    STATUS     current
    DESCRIPTION
	    "The cumulative number of results returned to
	    clients."
    ::= { microsoftSearch 8 }

msSucceededQueries OBJECT-TYPE
    SYNTAX     Gauge32
    MAX-ACCESS read-only
    STATUS     current
    DESCRIPTION
	    "The number of queries that produce successful
	    searches."
    ::= { microsoftSearch 9 }

msSucceededQueryRate OBJECT-TYPE
    SYNTAX     Gauge32
    MAX-ACCESS read-only
    STATUS     current
    DESCRIPTION
	    "The number of queries per second that produce
	    successful searches."
    ::= { microsoftSearch 10 }

msThreads OBJECT-TYPE
    SYNTAX     Gauge32
    MAX-ACCESS read-only
    STATUS     current
    DESCRIPTION
	    "The total number of threads avaliable for
	    servicing queries."
    ::= { microsoftSearch 11 }

microsoftSearchCatalogsTable OBJECT-TYPE
    SYNTAX     SEQUENCE OF MicrosoftSearchCatalogsEntry
    MAX-ACCESS not-accessible
    STATUS     current
    DESCRIPTION
	    "Represents a single catalog in the Microsoft
	    Search service."
    ::= { sqlServer 14 }

microsoftSearchCatalogsEntry OBJECT-TYPE
    SYNTAX     MicrosoftSearchCatalogsEntry
    MAX-ACCESS not-accessible
    STATUS     current
    DESCRIPTION
	    "Performance information for one particular
	    instance of 'Microsoft Search Catalogs'
	    object."
    INDEX      { mscInstance }
    ::= { microsoftSearchCatalogsTable 1 }

MicrosoftSearchCatalogsEntry ::= SEQUENCE {
    mscInstance InstanceName,
    mscCatalogSizeMBytes Gauge32,
    mscFailedQueries Gauge32,
    mscFailedQueriesRate Gauge32,
    mscNumberOfDocuments Gauge32,
    mscPersistentIndexes Gauge32,
    mscQueries Gauge32,
    mscQueriesRate Gauge32,
    mscResults Gauge32,
    mscResultsRate Gauge32,
    mscSuccessfulQueries Gauge32,
    mscSuccessfulQueriesRate Gauge32,
    mscUniqueKeys Gauge32
}

mscInstance OBJECT-TYPE
    SYNTAX     InstanceName
    MAX-ACCESS read-only
    STATUS     current
    DESCRIPTION
	    "Instance name."
    ::= { microsoftSearchCatalogsEntry 1 }

mscCatalogSizeMBytes OBJECT-TYPE
    SYNTAX     Gauge32
    MAX-ACCESS read-only
    STATUS     current
    DESCRIPTION
	    "Size of catalog data in megabytes."
    ::= { microsoftSearchCatalogsEntry 2 }

mscFailedQueries OBJECT-TYPE
    SYNTAX     Gauge32
    MAX-ACCESS read-only
    STATUS     current
    DESCRIPTION
	    "The number of queries that have failed."
    ::= { microsoftSearchCatalogsEntry 3 }

mscFailedQueriesRate OBJECT-TYPE
    SYNTAX     Gauge32
    MAX-ACCESS read-only
    STATUS     current
    DESCRIPTION
	    "The number of failed queries per second."
    ::= { microsoftSearchCatalogsEntry 4 }

mscNumberOfDocuments OBJECT-TYPE
    SYNTAX     Gauge32
    MAX-ACCESS read-only
    STATUS     current
    DESCRIPTION
	    "The total number of documents in the catalog."
    ::= { microsoftSearchCatalogsEntry 5 }

mscPersistentIndexes OBJECT-TYPE
    SYNTAX     Gauge32
    MAX-ACCESS read-only
    STATUS     current
    DESCRIPTION
	    "The number of persistent indexes."
    ::= { microsoftSearchCatalogsEntry 6 }

mscQueries OBJECT-TYPE
    SYNTAX     Gauge32
    MAX-ACCESS read-only
    STATUS     current
    DESCRIPTION
	    "Cumulative number of queries posted to the
	    catalog."
    ::= { microsoftSearchCatalogsEntry 7 }

mscQueriesRate OBJECT-TYPE
    SYNTAX     Gauge32
    MAX-ACCESS read-only
    STATUS     current
    DESCRIPTION
	    "The number of queries posted to the catalog
	    per second."
    ::= { microsoftSearchCatalogsEntry 8 }

mscResults OBJECT-TYPE
    SYNTAX     Gauge32
    MAX-ACCESS read-only
    STATUS     current
    DESCRIPTION
	    "The cumulative number of results returned to
	    clients."
    ::= { microsoftSearchCatalogsEntry 9 }

mscResultsRate OBJECT-TYPE
    SYNTAX     Gauge32
    MAX-ACCESS read-only
    STATUS     current
    DESCRIPTION
	    "The number of results returned to the client
	    per second."
    ::= { microsoftSearchCatalogsEntry 10 }

mscSuccessfulQueries OBJECT-TYPE
    SYNTAX     Gauge32
    MAX-ACCESS read-only
    STATUS     current
    DESCRIPTION
	    "The number of queries that produce successful
	    searches."
    ::= { microsoftSearchCatalogsEntry 11 }

mscSuccessfulQueriesRate OBJECT-TYPE
    SYNTAX     Gauge32
    MAX-ACCESS read-only
    STATUS     current
    DESCRIPTION
	    "The number of queries per second that produce
	    successful searches."
    ::= { microsoftSearchCatalogsEntry 12 }

mscUniqueKeys OBJECT-TYPE
    SYNTAX     Gauge32
    MAX-ACCESS read-only
    STATUS     current
    DESCRIPTION
	    "Number of unique words and properties in the
	    catalog."
    ::= { microsoftSearchCatalogsEntry 13 }

microsoftSearchIndexCatalogTable OBJECT-TYPE
    SYNTAX     SEQUENCE OF MicrosoftSearchIndexCatalogEntry
    MAX-ACCESS not-accessible
    STATUS     current
    DESCRIPTION
	    "Counters for the Microsoft Search Indexer"
    ::= { sqlServer 15 }

microsoftSearchIndexCatalogEntry OBJECT-TYPE
    SYNTAX     MicrosoftSearchIndexCatalogEntry
    MAX-ACCESS not-accessible
    STATUS     current
    DESCRIPTION
	    "Performance information for one particular
	    instance of 'Microsoft Search Indexer Catalogs'
	    object."
    INDEX      { msicInstance }
    ::= { microsoftSearchIndexCatalogTable 1 }

MicrosoftSearchIndexCatalogEntry ::= SEQUENCE {
    msicInstance InstanceName,
    msicActiveDocuments Gauge32,
    msicBuildInProgress Gauge32,
    msicDocumentsFiltered Gauge32,
    msicDocumentsInProgress Gauge32,
    msicFilesToBeFiltered Gauge32,
    msicIndexSizeMBytes Gauge32,
    msicMergeProgress Gauge32,
    msicNumberOfPropagations Gauge32,
    msicNumberOfDocuments Gauge32,
    msicPersistentIndexes Gauge32,
    msicUniqueKeys Gauge32,
    msicWordlists Gauge32
}

msicInstance OBJECT-TYPE
    SYNTAX     InstanceName
    MAX-ACCESS read-only
    STATUS     current
    DESCRIPTION
	    "Instance name."
    ::= { microsoftSearchIndexCatalogEntry 1 }

msicActiveDocuments OBJECT-TYPE
    SYNTAX     Gauge32
    MAX-ACCESS read-only
    STATUS     current
    DESCRIPTION
	    "The number of documents currently active in
	    Content Index"
    ::= { microsoftSearchIndexCatalogEntry 2 }

msicBuildInProgress OBJECT-TYPE
    SYNTAX     Gauge32
    MAX-ACCESS read-only
    STATUS     current
    DESCRIPTION
	    "An index build is in progress"
    ::= { microsoftSearchIndexCatalogEntry 3 }

msicDocumentsFiltered OBJECT-TYPE
    SYNTAX     Gauge32
    MAX-ACCESS read-only
    STATUS     current
    DESCRIPTION
	    "The number of documents filtered since the
	    catalog was mounted."
    ::= { microsoftSearchIndexCatalogEntry 4 }

msicDocumentsInProgress OBJECT-TYPE
    SYNTAX     Gauge32
    MAX-ACCESS read-only
    STATUS     current
    DESCRIPTION
	    "The number of documents for which data is
	    being added."
    ::= { microsoftSearchIndexCatalogEntry 5 }

msicFilesToBeFiltered OBJECT-TYPE
    SYNTAX     Gauge32
    MAX-ACCESS read-only
    STATUS     current
    DESCRIPTION
	    "The number of files waiting to be filtered and
	    added to the catalog."
    ::= { microsoftSearchIndexCatalogEntry 6 }

msicIndexSizeMBytes OBJECT-TYPE
    SYNTAX     Gauge32
    MAX-ACCESS read-only
    STATUS     current
    DESCRIPTION
	    "The current size of Index data in megabytes."
    ::= { microsoftSearchIndexCatalogEntry 7 }

msicMergeProgress OBJECT-TYPE
    SYNTAX     Gauge32
    MAX-ACCESS read-only
    STATUS     current
    DESCRIPTION
	    "The percentage of merge complete for the
	    current merge."
    ::= { microsoftSearchIndexCatalogEntry 8 }

msicNumberOfPropagations OBJECT-TYPE
    SYNTAX     Gauge32
    MAX-ACCESS read-only
    STATUS     current
    DESCRIPTION
	    "The number of propagations in progress."
    ::= { microsoftSearchIndexCatalogEntry 9 }

msicNumberOfDocuments OBJECT-TYPE
    SYNTAX     Gauge32
    MAX-ACCESS read-only
    STATUS     current
    DESCRIPTION
	    "The number of documents in the catalog."
    ::= { microsoftSearchIndexCatalogEntry 10 }

msicPersistentIndexes OBJECT-TYPE
    SYNTAX     Gauge32
    MAX-ACCESS read-only
    STATUS     current
    DESCRIPTION
	    "The number of persistent indexes."
    ::= { microsoftSearchIndexCatalogEntry 11 }

msicUniqueKeys OBJECT-TYPE
    SYNTAX     Gauge32
    MAX-ACCESS read-only
    STATUS     current
    DESCRIPTION
	    "The number of unique words and properties in
	    the catalog."
    ::= { microsoftSearchIndexCatalogEntry 12 }

msicWordlists OBJECT-TYPE
    SYNTAX     Gauge32
    MAX-ACCESS read-only
    STATUS     current
    DESCRIPTION
	    "The total number of wordlists."
    ::= { microsoftSearchIndexCatalogEntry 13 }

sqlServerNameTable OBJECT-TYPE
    SYNTAX     SEQUENCE OF SqlServerNameEntry
    MAX-ACCESS not-accessible
    STATUS     current
    DESCRIPTION
	    "This table contains the list of SQL Server
	    instance names installed. The
	    sqlServerNameIndex is used to refer to all
	    other SQL Server SNMP entries."
    ::= { sqlServer 16 }

sqlServerNameEntry OBJECT-TYPE
    SYNTAX     SqlServerNameEntry
    MAX-ACCESS not-accessible
    STATUS     current
    DESCRIPTION
	    "Performance information for one SQL Server
	    name instance."
    INDEX      { sqlServerNameIndex }
    ::= { sqlServerNameTable 1 }

SqlServerNameEntry ::= SEQUENCE {
    sqlServerNameIndex Integer32,
    sqlServerNameInstance InstanceName
}

sqlServerNameIndex OBJECT-TYPE
    SYNTAX     Integer32 (1..999)
    MAX-ACCESS read-only
    STATUS     current
    DESCRIPTION
	    "The index number associated with the instance
	    name"
    ::= { sqlServerNameEntry 1 }

sqlServerNameInstance OBJECT-TYPE
    SYNTAX     InstanceName
    MAX-ACCESS read-only
    STATUS     current
    DESCRIPTION
	    "The name of the SQL Server installed
	    instance."
    ::= { sqlServerNameEntry 2 }

sqlServerAccessMethodsTable OBJECT-TYPE
    SYNTAX     SEQUENCE OF SqlServerAccessMethodsEntry
    MAX-ACCESS not-accessible
    STATUS     current
    DESCRIPTION
	    "The Access Methods object in Microsoft SQL
	    Server provides counters to monitor how the
	    logical pages within the database are accessed.
	    Physical access to the database pages on disk
	    is monitored using the Buffer Manager counters.
	    Monitoring the methods used to access database
	    pages can help you to determine whether query
	    performance can be improved by adding or
	    modifying indexes or by rewriting queries. The
	    Access Methods counters can also be used to
	    monitor the amount of data, indexes, and free
	    space within the database, thereby indicating
	    data volume and fragmentation (excessive
	    fragmentation can impair performance)."
    ::= { sqlServer 17 }

sqlServerAccessMethodsEntry OBJECT-TYPE
    SYNTAX     SqlServerAccessMethodsEntry
    MAX-ACCESS not-accessible
    STATUS     current
    DESCRIPTION
	    "Performance information for one SQL Server
	    name instance."
    INDEX      { sqlServerNameIndex }
    ::= { sqlServerAccessMethodsTable 1 }

SqlServerAccessMethodsEntry ::= SEQUENCE {
    ssamAUCleanupBatchesPerSec Gauge32,
    ssamAUCleanupsPerSec Gauge32,
    ssamDeferredDroppedRowsets Gauge32,
    ssamDeferredDroppedAUs Gauge32,
    ssamDroppedRowsetCleanupsPerSec Gauge32,
    ssamDroppedRowsetsSkippedPerSec Gauge32,
    ssamExtentDeallocationsPerSec Gauge32,
    ssamExtentsAllocatedPerSec Gauge32,
    ssamFailedAUCleanupBatchesPerSec Gauge32,
    ssamFailedLeafPageCookie Gauge32,
    ssamFailedTreePageCookie Gauge32,
    ssamForwardedRecordsPerSec Gauge32,
    ssamFreeSpacePageFetchesPerSec Gauge32,
    ssamFreeSpaceScansPerSec Gauge32,
    ssamFullScansPerSec Gauge32,
    ssamIndexSearchesPerSec Gauge32,
    ssamMixedPageAllocationsPerSec Gauge32,
    ssamPageDeallocationsPerSec Gauge32,
    ssamPageSplitsPerSec Gauge32,
    ssamPagesAllocatedPerSec Gauge32,
    ssamProbeScansPerSec Gauge32,
    ssamRangeScansPerSec Gauge32,
    ssamScanPointRevalidationsPerSec Gauge32,
    ssamSkippedGhostedRecordsPerSec Gauge32,
    ssamTableLockEscalationsPerSec Gauge32,
    ssamUsedLeafPageCookie Gauge32,
    ssamUsedTreePageCookie Gauge32,
    ssamWorkfilesCreatedPerSec Gauge32,
    ssamWorktablesCreatedPerSec Gauge32,
    ssamWorktablesFromCacheRatio Gauge32
}

ssamAUCleanupBatchesPerSec OBJECT-TYPE
    SYNTAX     Gauge32
    MAX-ACCESS read-only
    STATUS     current
    DESCRIPTION
	    "The number of deferred dropped alloc unit
	    cleanup batches that completed sucessfully."
    ::= { sqlServerAccessMethodsEntry 1 }

ssamAUCleanupsPerSec OBJECT-TYPE
    SYNTAX     Gauge32
    MAX-ACCESS read-only
    STATUS     current
    DESCRIPTION
	    "The number of deferred dropped alloc units
	    that were successfully cleaned up."
    ::= { sqlServerAccessMethodsEntry 2 }

ssamDeferredDroppedRowsets OBJECT-TYPE
    SYNTAX     Gauge32
    MAX-ACCESS read-only
    STATUS     current
    DESCRIPTION
	    "The number of items on the deferred dropped
	    rowset cleanup queue."
    ::= { sqlServerAccessMethodsEntry 3 }

ssamDeferredDroppedAUs OBJECT-TYPE
    SYNTAX     Gauge32
    MAX-ACCESS read-only
    STATUS     current
    DESCRIPTION
	    "The number of items on the deferred dropped
	    alloc unit cleanup queue."
    ::= { sqlServerAccessMethodsEntry 4 }

ssamDroppedRowsetCleanupsPerSec OBJECT-TYPE
    SYNTAX     Gauge32
    MAX-ACCESS read-only
    STATUS     current
    DESCRIPTION
	    "The number of deferred dropped rowsets that
	    were successfully cleanedup."
    ::= { sqlServerAccessMethodsEntry 5 }

ssamDroppedRowsetsSkippedPerSec OBJECT-TYPE
    SYNTAX     Gauge32
    MAX-ACCESS read-only
    STATUS     current
    DESCRIPTION
	    "The number of deferred dropped rowsets that
	    were skipped."
    ::= { sqlServerAccessMethodsEntry 6 }

ssamExtentDeallocationsPerSec OBJECT-TYPE
    SYNTAX     Gauge32
    MAX-ACCESS read-only
    STATUS     current
    DESCRIPTION
	    "Number of extents deallocated from database
	    objects."
    ::= { sqlServerAccessMethodsEntry 7 }

ssamExtentsAllocatedPerSec OBJECT-TYPE
    SYNTAX     Gauge32
    MAX-ACCESS read-only
    STATUS     current
    DESCRIPTION
	    "Number of extents allocated to database
	    objects for storing index or data records."
    ::= { sqlServerAccessMethodsEntry 8 }

ssamFailedAUCleanupBatchesPerSec OBJECT-TYPE
    SYNTAX     Gauge32
    MAX-ACCESS read-only
    STATUS     current
    DESCRIPTION
	    "The number of deferred dropped alloc unit
	    cleanup batches that failed."
    ::= { sqlServerAccessMethodsEntry 9 }

ssamFailedLeafPageCookie OBJECT-TYPE
    SYNTAX     Gauge32
    MAX-ACCESS read-only
    STATUS     current
    DESCRIPTION
	    "Failed to use leaf page cookie since changes
	    happened on leaf."
    ::= { sqlServerAccessMethodsEntry 10 }

ssamFailedTreePageCookie OBJECT-TYPE
    SYNTAX     Gauge32
    MAX-ACCESS read-only
    STATUS     current
    DESCRIPTION
	    "Failed to use tree page cookie since changes
	    happened on parent."
    ::= { sqlServerAccessMethodsEntry 11 }

ssamForwardedRecordsPerSec OBJECT-TYPE
    SYNTAX     Gauge32
    MAX-ACCESS read-only
    STATUS     current
    DESCRIPTION
	    "Number of records fetched through forwarded
	    record pointers."
    ::= { sqlServerAccessMethodsEntry 12 }

ssamFreeSpacePageFetchesPerSec OBJECT-TYPE
    SYNTAX     Gauge32
    MAX-ACCESS read-only
    STATUS     current
    DESCRIPTION
	    "Number of pages returned by free space scans
	    to satisfy requests to insert record
	    fragments."
    ::= { sqlServerAccessMethodsEntry 13 }

ssamFreeSpaceScansPerSec OBJECT-TYPE
    SYNTAX     Gauge32
    MAX-ACCESS read-only
    STATUS     current
    DESCRIPTION
	    "Number of scans initiated to search for free
	    space to insert a new record fragment."
    ::= { sqlServerAccessMethodsEntry 14 }

ssamFullScansPerSec OBJECT-TYPE
    SYNTAX     Gauge32
    MAX-ACCESS read-only
    STATUS     current
    DESCRIPTION
	    "Number of unrestricted full scans. These can
	    either be base table or full index scans."
    ::= { sqlServerAccessMethodsEntry 15 }

ssamIndexSearchesPerSec OBJECT-TYPE
    SYNTAX     Gauge32
    MAX-ACCESS read-only
    STATUS     current
    DESCRIPTION
	    "Number of index searches. Index searches are
	    used to start range scans, single index record
	    fetches, and to reposition within an index."
    ::= { sqlServerAccessMethodsEntry 16 }

ssamMixedPageAllocationsPerSec OBJECT-TYPE
    SYNTAX     Gauge32
    MAX-ACCESS read-only
    STATUS     current
    DESCRIPTION
	    "Number of pages allocated from mixed extents.
	    Used for storing the first eight pages
	    allocated to an index or table."
    ::= { sqlServerAccessMethodsEntry 17 }

ssamPageDeallocationsPerSec OBJECT-TYPE
    SYNTAX     Gauge32
    MAX-ACCESS read-only
    STATUS     current
    DESCRIPTION
	    "Number of pages deallocated."
    ::= { sqlServerAccessMethodsEntry 18 }

ssamPageSplitsPerSec OBJECT-TYPE
    SYNTAX     Gauge32
    MAX-ACCESS read-only
    STATUS     current
    DESCRIPTION
	    "Number of page splits occurring as the result
	    of index pages overflowing."
    ::= { sqlServerAccessMethodsEntry 19 }

ssamPagesAllocatedPerSec OBJECT-TYPE
    SYNTAX     Gauge32
    MAX-ACCESS read-only
    STATUS     current
    DESCRIPTION
	    "Number of pages allocated to database objects
	    for storing index or data records."
    ::= { sqlServerAccessMethodsEntry 20 }

ssamProbeScansPerSec OBJECT-TYPE
    SYNTAX     Gauge32
    MAX-ACCESS read-only
    STATUS     current
    DESCRIPTION
	    "Number of probe scans. A probe scan is used to
	    directly look up rows in an index or base
	    table."
    ::= { sqlServerAccessMethodsEntry 21 }

ssamRangeScansPerSec OBJECT-TYPE
    SYNTAX     Gauge32
    MAX-ACCESS read-only
    STATUS     current
    DESCRIPTION
	    "Number of qualified range scans through
	    indexes."
    ::= { sqlServerAccessMethodsEntry 22 }

ssamScanPointRevalidationsPerSec OBJECT-TYPE
    SYNTAX     Gauge32
    MAX-ACCESS read-only
    STATUS     current
    DESCRIPTION
	    "Number of times the scan point had to be
	    revalidated to continue the scan."
    ::= { sqlServerAccessMethodsEntry 23 }

ssamSkippedGhostedRecordsPerSec OBJECT-TYPE
    SYNTAX     Gauge32
    MAX-ACCESS read-only
    STATUS     current
    DESCRIPTION
	    "Number of ghosted records skipped during
	    scans."
    ::= { sqlServerAccessMethodsEntry 24 }

ssamTableLockEscalationsPerSec OBJECT-TYPE
    SYNTAX     Gauge32
    MAX-ACCESS read-only
    STATUS     current
    DESCRIPTION
	    "The number of times locks on a table were
	    escalated."
    ::= { sqlServerAccessMethodsEntry 25 }

ssamUsedLeafPageCookie OBJECT-TYPE
    SYNTAX     Gauge32
    MAX-ACCESS read-only
    STATUS     current
    DESCRIPTION
	    "Successfully used leaf page cookie since no
	    change happened on leaf."
    ::= { sqlServerAccessMethodsEntry 26 }

ssamUsedTreePageCookie OBJECT-TYPE
    SYNTAX     Gauge32
    MAX-ACCESS read-only
    STATUS     current
    DESCRIPTION
	    "Successfully used tree page cookie since no
	    change happened on parent."
    ::= { sqlServerAccessMethodsEntry 27 }

ssamWorkfilesCreatedPerSec OBJECT-TYPE
    SYNTAX     Gauge32
    MAX-ACCESS read-only
    STATUS     current
    DESCRIPTION
	    "Number of workfiles created in the last
	    second."
    ::= { sqlServerAccessMethodsEntry 28 }

ssamWorktablesCreatedPerSec OBJECT-TYPE
    SYNTAX     Gauge32
    MAX-ACCESS read-only
    STATUS     current
    DESCRIPTION
	    "Number of worktables created in the last
	    second."
    ::= { sqlServerAccessMethodsEntry 29 }

ssamWorktablesFromCacheRatio OBJECT-TYPE
    SYNTAX     Gauge32
    MAX-ACCESS read-only
    STATUS     current
    DESCRIPTION
	    "Percent of worktables created where the
	    initial pages were available in the worktable
	    cache."
    ::= { sqlServerAccessMethodsEntry 30 }

sqlServerBackupDeviceTable OBJECT-TYPE
    SYNTAX     SEQUENCE OF SQLServerBackupDeviceEntry
    MAX-ACCESS not-accessible
    STATUS     current
    DESCRIPTION
	    "The Backup Device object provides counters to
	    monitor Microsoft SQL Server backup devices
	    used for backup and restore operations. Monitor
	    backup devices when you want to determine the
	    throughput or the progress and performance of
	    your backup and restore operations on a per
	    device basis. To monitor the throughput of the
	    entire database backup or restore operation,
	    use the Backup/Restore Throughput/sec counter
	    of the SQL Server Databases object. For more
	    information, see SQL Server: Databases Object."
    ::= { sqlServer 18 }

sqlServerBackupDeviceEntry OBJECT-TYPE
    SYNTAX     SQLServerBackupDeviceEntry
    MAX-ACCESS not-accessible
    STATUS     current
    DESCRIPTION
	    "Performance information for one particular SQL
	    Server name instance of 'SQLServer:Backup
	    Device' object."
    INDEX      { sqlServerNameIndex, ssbdInstance }
    ::= { sqlServerBackupDeviceTable 1 }

SQLServerBackupDeviceEntry ::= SEQUENCE {
    ssbdInstance InstanceName,
    ssbdDeviceThroughputBytesPerSec Gauge32
}

ssbdInstance OBJECT-TYPE
    SYNTAX     InstanceName
    MAX-ACCESS read-only
    STATUS     current
    DESCRIPTION
	    "Instance name."
    ::= { sqlServerBackupDeviceEntry 1 }

ssbdDeviceThroughputBytesPerSec OBJECT-TYPE
    SYNTAX     Gauge32
    MAX-ACCESS read-only
    STATUS     current
    DESCRIPTION
	    "No description available"
    ::= { sqlServerBackupDeviceEntry 2 }

sqlServerBrokerActivationTable OBJECT-TYPE
    SYNTAX     SEQUENCE OF SqlServerBrokerActivationEntry
    MAX-ACCESS not-accessible
    STATUS     current
    DESCRIPTION
	    "Service Broker Activation"
    ::= { sqlServer 19 }

sqlServerBrokerActivationEntry OBJECT-TYPE
    SYNTAX     SqlServerBrokerActivationEntry
    MAX-ACCESS not-accessible
    STATUS     current
    DESCRIPTION
	    "Performance information for one particular SQL
	    Server name instance of 'Broker Activation'
	    object."
    INDEX      { sqlServerNameIndex, ssbaInstance }
    ::= { sqlServerBrokerActivationTable 1 }

SqlServerBrokerActivationEntry ::= SEQUENCE {
    ssbaInstance InstanceName,
    ssbaStoredProceduresInvokedPerSec Gauge32,
    ssbaTaskLimitReached Gauge32,
    ssbaTaskLimitReachedPerSec Gauge32,
    ssbaTasksAbortedPerSec Gauge32,
    ssbaTasksRunning Gauge32,
    ssbaTasksStartedPerSec Gauge32
}

ssbaInstance OBJECT-TYPE
    SYNTAX     InstanceName
    MAX-ACCESS read-only
    STATUS     current
    DESCRIPTION
	    "Instance name."
    ::= { sqlServerBrokerActivationEntry 1 }

ssbaStoredProceduresInvokedPerSec OBJECT-TYPE
    SYNTAX     Gauge32
    MAX-ACCESS read-only
    STATUS     current
    DESCRIPTION
	    "The number of stored procedures that are being
	    invoked per second."
    ::= { sqlServerBrokerActivationEntry 2 }

ssbaTaskLimitReached OBJECT-TYPE
    SYNTAX     Gauge32
    MAX-ACCESS read-only
    STATUS     current
    DESCRIPTION
	    "The total number of times the activated task
	    limit on a queue has been reached."
    ::= { sqlServerBrokerActivationEntry 3 }

ssbaTaskLimitReachedPerSec OBJECT-TYPE
    SYNTAX     Gauge32
    MAX-ACCESS read-only
    STATUS     current
    DESCRIPTION
	    "The number of times the activated task limit
	    on a queue has been reached per second."
    ::= { sqlServerBrokerActivationEntry 4 }

ssbaTasksAbortedPerSec OBJECT-TYPE
    SYNTAX     Gauge32
    MAX-ACCESS read-only
    STATUS     current
    DESCRIPTION
	    "The number of activated tasks that are being
	    aborted per second."
    ::= { sqlServerBrokerActivationEntry 5 }

ssbaTasksRunning OBJECT-TYPE
    SYNTAX     Gauge32
    MAX-ACCESS read-only
    STATUS     current
    DESCRIPTION
	    "The total number of activated tasks that are
	    currently running."
    ::= { sqlServerBrokerActivationEntry 6 }

ssbaTasksStartedPerSec OBJECT-TYPE
    SYNTAX     Gauge32
    MAX-ACCESS read-only
    STATUS     current
    DESCRIPTION
	    "The number of activated tasks that are being
	    started per second."
    ::= { sqlServerBrokerActivationEntry 7 }

sqlServerBrokerStatisticsTable OBJECT-TYPE
    SYNTAX     SEQUENCE OF SqlServerBrokerStatisticsEntry
    MAX-ACCESS not-accessible
    STATUS     current
    DESCRIPTION
	    "Service Broker Statistics"
    ::= { sqlServer 20 }

sqlServerBrokerStatisticsEntry OBJECT-TYPE
    SYNTAX     SqlServerBrokerStatisticsEntry
    MAX-ACCESS not-accessible
    STATUS     current
    DESCRIPTION
	    "Performance information for one SQL Server
	    name instance."
    INDEX      { sqlServerNameIndex }
    ::= { sqlServerBrokerStatisticsTable 1 }

SqlServerBrokerStatisticsEntry ::= SEQUENCE {
    ssbsBrokerTransactionRollbacks Gauge32,
    ssbsDialogTimerEventCount Gauge32,
    ssbsEnqueuedLocalMessagesTotal Gauge32,
    ssbsEnqueuedLocalMessagesPerSec Gauge32,
    ssbsEnqueuedMessagesTotal Gauge32,
    ssbsEnqueuedMessagesPerSec Gauge32,
    ssbsEnqueuedTransportMsgFragTot Gauge32,
    ssbsEnqueuedTransportMsgFragsPerSec Gauge32,
    ssbsEnqueuedTransportMsgsTotal Gauge32,
    ssbsEnqueuedTransportMsgsPerSec Gauge32,
    ssbsForwardedMessagesTotal Gauge32,
    ssbsForwardedMessagesPerSec Gauge32,
    ssbsForwardedMsgByteTotal Gauge32,
    ssbsForwardedMsgBytesPerSec Gauge32,
    ssbsForwardedMsgDiscardedTotal Gauge32,
    ssbsForwardedMsgsDiscardedPerSec Gauge32,
    ssbsForwardedPendingMsgBytes Gauge32,
    ssbsForwardedPendingMsgCount Gauge32,
    ssbsSQLRECEIVETotal Gauge32,
    ssbsSQLRECEIVEsPerSec Gauge32,
    ssbsSQLSENDTotal Gauge32,
    ssbsSQLSENDsPerSec Gauge32,
    ssbsTransportTimerEventCount Gauge32
}

ssbsBrokerTransactionRollbacks OBJECT-TYPE
    SYNTAX     Gauge32
    MAX-ACCESS read-only
    STATUS     current
    DESCRIPTION
	    "The number of Service Broker related
	    transactions that have rolled back."
    ::= { sqlServerBrokerStatisticsEntry 1 }

ssbsDialogTimerEventCount OBJECT-TYPE
    SYNTAX     Gauge32
    MAX-ACCESS read-only
    STATUS     current
    DESCRIPTION
	    "The number of dialog endpoint related timer
	    events in the Broker."
    ::= { sqlServerBrokerStatisticsEntry 2 }

ssbsEnqueuedLocalMessagesTotal OBJECT-TYPE
    SYNTAX     Gauge32
    MAX-ACCESS read-only
    STATUS     current
    DESCRIPTION
	    "Total number of message fragments from local
	    endpoints that are successfully delivered as
	    ready into queues."
    ::= { sqlServerBrokerStatisticsEntry 3 }

ssbsEnqueuedLocalMessagesPerSec OBJECT-TYPE
    SYNTAX     Gauge32
    MAX-ACCESS read-only
    STATUS     current
    DESCRIPTION
	    "The number of messages from local endpoints
	    that are successfully delivered as ready into
	    queues per second."
    ::= { sqlServerBrokerStatisticsEntry 4 }

ssbsEnqueuedMessagesTotal OBJECT-TYPE
    SYNTAX     Gauge32
    MAX-ACCESS read-only
    STATUS     current
    DESCRIPTION
	    "Total number of message fragments from local
	    endpoints and the transport that are
	    successfully delivered as ready into queues."
    ::= { sqlServerBrokerStatisticsEntry 5 }

ssbsEnqueuedMessagesPerSec OBJECT-TYPE
    SYNTAX     Gauge32
    MAX-ACCESS read-only
    STATUS     current
    DESCRIPTION
	    "The number of messages from local endpoints
	    and the transport that are successfully
	    delivered as ready into queues per second."
    ::= { sqlServerBrokerStatisticsEntry 6 }

ssbsEnqueuedTransportMsgFragTot OBJECT-TYPE
    SYNTAX     Gauge32
    MAX-ACCESS read-only
    STATUS     current
    DESCRIPTION
	    "Total number of message fragments from the
	    transport that are successfully delivered into
	    queues. Note the cooresponding message may not
	    be complete yet or may be out of order, and
	    therefore the message can be in the queue as
	    disabled."
    ::= { sqlServerBrokerStatisticsEntry 7 }

ssbsEnqueuedTransportMsgFragsPerSec OBJECT-TYPE
    SYNTAX     Gauge32
    MAX-ACCESS read-only
    STATUS     current
    DESCRIPTION
	    "The number of message fragments from the
	    transport that are successfully delivered into
	    queues per second. Note the cooresponding
	    message may not be complete yet or may be out
	    of order, and therefore the message can be in
	    the queue as disabled."
    ::= { sqlServerBrokerStatisticsEntry 8 }

ssbsEnqueuedTransportMsgsTotal OBJECT-TYPE
    SYNTAX     Gauge32
    MAX-ACCESS read-only
    STATUS     current
    DESCRIPTION
	    "Total number of messages from the transport
	    that are successfully delivered as ready into
	    queues."
    ::= { sqlServerBrokerStatisticsEntry 9 }

ssbsEnqueuedTransportMsgsPerSec OBJECT-TYPE
    SYNTAX     Gauge32
    MAX-ACCESS read-only
    STATUS     current
    DESCRIPTION
	    "The number of messages from the transport that
	    are successfully delivered as ready into queues
	    per second."
    ::= { sqlServerBrokerStatisticsEntry 10 }

ssbsForwardedMessagesTotal OBJECT-TYPE
    SYNTAX     Gauge32
    MAX-ACCESS read-only
    STATUS     current
    DESCRIPTION
	    "Total number of forwarded messages
	    successfully sent."
    ::= { sqlServerBrokerStatisticsEntry 11 }

ssbsForwardedMessagesPerSec OBJECT-TYPE
    SYNTAX     Gauge32
    MAX-ACCESS read-only
    STATUS     current
    DESCRIPTION
	    "The number of forwarded messages successfully
	    sent per second."
    ::= { sqlServerBrokerStatisticsEntry 12 }

ssbsForwardedMsgByteTotal OBJECT-TYPE
    SYNTAX     Gauge32
    MAX-ACCESS read-only
    STATUS     current
    DESCRIPTION
	    "Total number of forwarded message bytes
	    successfully sent."
    ::= { sqlServerBrokerStatisticsEntry 13 }

ssbsForwardedMsgBytesPerSec OBJECT-TYPE
    SYNTAX     Gauge32
    MAX-ACCESS read-only
    STATUS     current
    DESCRIPTION
	    "The number of forwarded message bytes
	    successfully sent per second."
    ::= { sqlServerBrokerStatisticsEntry 14 }

ssbsForwardedMsgDiscardedTotal OBJECT-TYPE
    SYNTAX     Gauge32
    MAX-ACCESS read-only
    STATUS     current
    DESCRIPTION
	    "Total number of forwarded messages discarded
	    due to forwarded message memory limits, age
	    limits, etc."
    ::= { sqlServerBrokerStatisticsEntry 15 }

ssbsForwardedMsgsDiscardedPerSec OBJECT-TYPE
    SYNTAX     Gauge32
    MAX-ACCESS read-only
    STATUS     current
    DESCRIPTION
	    "The number of forwarded messages that were
	    discarded per second due to forwarded message
	    memory limits, age limits, etc."
    ::= { sqlServerBrokerStatisticsEntry 16 }

ssbsForwardedPendingMsgBytes OBJECT-TYPE
    SYNTAX     Gauge32
    MAX-ACCESS read-only
    STATUS     current
    DESCRIPTION
	    "The number of forwarded message bytes that
	    have not been successfully sent yet."
    ::= { sqlServerBrokerStatisticsEntry 17 }

ssbsForwardedPendingMsgCount OBJECT-TYPE
    SYNTAX     Gauge32
    MAX-ACCESS read-only
    STATUS     current
    DESCRIPTION
	    "The number of forwarded messages that have not
	    been successfully sent yet."
    ::= { sqlServerBrokerStatisticsEntry 18 }

ssbsSQLRECEIVETotal OBJECT-TYPE
    SYNTAX     Gauge32
    MAX-ACCESS read-only
    STATUS     current
    DESCRIPTION
	    "Total number of SQL RECEIVE commands processed
	    by the Broker."
    ::= { sqlServerBrokerStatisticsEntry 19 }

ssbsSQLRECEIVEsPerSec OBJECT-TYPE
    SYNTAX     Gauge32
    MAX-ACCESS read-only
    STATUS     current
    DESCRIPTION
	    "The number of SQL RECEIVE commands processed
	    by the Broker per second."
    ::= { sqlServerBrokerStatisticsEntry 20 }

ssbsSQLSENDTotal OBJECT-TYPE
    SYNTAX     Gauge32
    MAX-ACCESS read-only
    STATUS     current
    DESCRIPTION
	    "Total number of SQL SEND commands processed by
	    the Broker."
    ::= { sqlServerBrokerStatisticsEntry 21 }

ssbsSQLSENDsPerSec OBJECT-TYPE
    SYNTAX     Gauge32
    MAX-ACCESS read-only
    STATUS     current
    DESCRIPTION
	    "The number of SQL SEND commands processed by
	    the Broker per second."
    ::= { sqlServerBrokerStatisticsEntry 22 }

ssbsTransportTimerEventCount OBJECT-TYPE
    SYNTAX     Gauge32
    MAX-ACCESS read-only
    STATUS     current
    DESCRIPTION
	    "The number of transport related timer events
	    in the Broker."
    ::= { sqlServerBrokerStatisticsEntry 23 }

sqlServerBrokerTransportTable OBJECT-TYPE
    SYNTAX     SEQUENCE OF SqlServerBrokerTransportEntry
    MAX-ACCESS not-accessible
    STATUS     current
    DESCRIPTION
	    "Service Broker Transport Statistics"
    ::= { sqlServer 21 }

sqlServerBrokerTransportEntry OBJECT-TYPE
    SYNTAX     SqlServerBrokerTransportEntry
    MAX-ACCESS not-accessible
    STATUS     current
    DESCRIPTION
	    "Performance information for one SQL Server
	    name instance."
    INDEX      { sqlServerNameIndex }
    ::= { sqlServerBrokerTransportTable 1 }

SqlServerBrokerTransportEntry ::= SEQUENCE {
    ssbtCurrentBytesForRecvIO Gauge32,
    ssbtCurrentBytesForSendIO Gauge32,
    ssbtCurrentMsgFragsForSendIO Gauge32,
    ssbtMessageFragmentReceiveTotal Gauge32,
    ssbtMessageFragmentReceivesPerSec Gauge32,
    ssbtMessageFragmentSendTotal Gauge32,
    ssbtMessageFragmentSendsPerSec Gauge32,
    ssbtMsgFragmentRecvSizeAvg Gauge32,
    ssbtMsgFragmentSendSizeAvg Gauge32,
    ssbtOpenConnectionCount Gauge32,
    ssbtPendingBytesForRecvIO Gauge32,
    ssbtPendingBytesForSendIO Gauge32,
    ssbtPendingMsgFragsForRecvIO Gauge32,
    ssbtPendingMsgFragsForSendIO Gauge32,
    ssbtReceiveIOBytesTotal Gauge32,
    ssbtReceiveIOLenAvg Gauge32,
    ssbtReceiveIOBytesPerSec Gauge32,
    ssbtReceiveIOsPerSec Gauge32,
    ssbtSendIOBytesTotal Gauge32,
    ssbtSendIOLenAvg Gauge32,
    ssbtSendIOBytesPerSec Gauge32,
    ssbtSendIOsPerSec Gauge32
}

ssbtCurrentBytesForRecvIO OBJECT-TYPE
    SYNTAX     Gauge32
    MAX-ACCESS read-only
    STATUS     current
    DESCRIPTION
	    "The number of bytes associated with current
	    transport receive I/O operations that haven't
	    completed."
    ::= { sqlServerBrokerTransportEntry 1 }

ssbtCurrentBytesForSendIO OBJECT-TYPE
    SYNTAX     Gauge32
    MAX-ACCESS read-only
    STATUS     current
    DESCRIPTION
	    "The number of buffer bytes associated with
	    current transport send I/O operations that
	    haven't completed."
    ::= { sqlServerBrokerTransportEntry 2 }

ssbtCurrentMsgFragsForSendIO OBJECT-TYPE
    SYNTAX     Gauge32
    MAX-ACCESS read-only
    STATUS     current
    DESCRIPTION
	    "The current number of message fragments
	    associated with current transport send I/O
	    operations that haven't completed."
    ::= { sqlServerBrokerTransportEntry 3 }

ssbtMessageFragmentReceiveTotal OBJECT-TYPE
    SYNTAX     Gauge32
    MAX-ACCESS read-only
    STATUS     current
    DESCRIPTION
	    "The total number of message fragments received
	    in transport receive I/O operations."
    ::= { sqlServerBrokerTransportEntry 4 }

ssbtMessageFragmentReceivesPerSec OBJECT-TYPE
    SYNTAX     Gauge32
    MAX-ACCESS read-only
    STATUS     current
    DESCRIPTION
	    "The number of message fragments received per
	    second in transport receive I/O operations."
    ::= { sqlServerBrokerTransportEntry 5 }

ssbtMessageFragmentSendTotal OBJECT-TYPE
    SYNTAX     Gauge32
    MAX-ACCESS read-only
    STATUS     current
    DESCRIPTION
	    "The total number of message fragments sent in
	    transport send I/O operations."
    ::= { sqlServerBrokerTransportEntry 6 }

ssbtMessageFragmentSendsPerSec OBJECT-TYPE
    SYNTAX     Gauge32
    MAX-ACCESS read-only
    STATUS     current
    DESCRIPTION
	    "The number of message fragments sent per
	    second in transport send I/O operations."
    ::= { sqlServerBrokerTransportEntry 7 }

ssbtMsgFragmentRecvSizeAvg OBJECT-TYPE
    SYNTAX     Gauge32
    MAX-ACCESS read-only
    STATUS     current
    DESCRIPTION
	    "The average byte size of message fragments
	    received in transport receive I/O operations."
    ::= { sqlServerBrokerTransportEntry 8 }

ssbtMsgFragmentSendSizeAvg OBJECT-TYPE
    SYNTAX     Gauge32
    MAX-ACCESS read-only
    STATUS     current
    DESCRIPTION
	    "The average byte size of message fragments
	    sent in transport send I/O operations."
    ::= { sqlServerBrokerTransportEntry 9 }

ssbtOpenConnectionCount OBJECT-TYPE
    SYNTAX     Gauge32
    MAX-ACCESS read-only
    STATUS     current
    DESCRIPTION
	    "The total number of Service Broker transport
	    connections currently open."
    ::= { sqlServerBrokerTransportEntry 10 }

ssbtPendingBytesForRecvIO OBJECT-TYPE
    SYNTAX     Gauge32
    MAX-ACCESS read-only
    STATUS     current
    DESCRIPTION
	    "The number of bytes associated with in
	    completed transport receive I/O operations
	    whose message fragments haven't been enqueued
	    (or rejected) yet."
    ::= { sqlServerBrokerTransportEntry 11 }

ssbtPendingBytesForSendIO OBJECT-TYPE
    SYNTAX     Gauge32
    MAX-ACCESS read-only
    STATUS     current
    DESCRIPTION
	    "The number of buffer bytes associated with
	    message fragments being marshalled, or
	    marshalled and ready to be sent with send I/O
	    operations."
    ::= { sqlServerBrokerTransportEntry 12 }

ssbtPendingMsgFragsForRecvIO OBJECT-TYPE
    SYNTAX     Gauge32
    MAX-ACCESS read-only
    STATUS     current
    DESCRIPTION
	    "The current number of message fragments
	    received in transport receive I/O operations
	    that have not been enqueued (or rejected) yet."
    ::= { sqlServerBrokerTransportEntry 13 }

ssbtPendingMsgFragsForSendIO OBJECT-TYPE
    SYNTAX     Gauge32
    MAX-ACCESS read-only
    STATUS     current
    DESCRIPTION
	    "The current number of message fragments that
	    are being marshalled, or marshalled and ready
	    to be sent via the transport layer."
    ::= { sqlServerBrokerTransportEntry 14 }

ssbtReceiveIOBytesTotal OBJECT-TYPE
    SYNTAX     Gauge32
    MAX-ACCESS read-only
    STATUS     current
    DESCRIPTION
	    "The total number of bytes received in
	    transport receive I/O operations."
    ::= { sqlServerBrokerTransportEntry 15 }

ssbtReceiveIOLenAvg OBJECT-TYPE
    SYNTAX     Gauge32
    MAX-ACCESS read-only
    STATUS     current
    DESCRIPTION
	    "The average byte length of transport receive
	    I/O operations."
    ::= { sqlServerBrokerTransportEntry 16 }

ssbtReceiveIOBytesPerSec OBJECT-TYPE
    SYNTAX     Gauge32
    MAX-ACCESS read-only
    STATUS     current
    DESCRIPTION
	    "The number of transport receive I/O bytes per
	    second."
    ::= { sqlServerBrokerTransportEntry 17 }

ssbtReceiveIOsPerSec OBJECT-TYPE
    SYNTAX     Gauge32
    MAX-ACCESS read-only
    STATUS     current
    DESCRIPTION
	    "The number of transport receives I/O per
	    second. Note that a transport receive I/O may
	    contain more than one message fragment."
    ::= { sqlServerBrokerTransportEntry 18 }

ssbtSendIOBytesTotal OBJECT-TYPE
    SYNTAX     Gauge32
    MAX-ACCESS read-only
    STATUS     current
    DESCRIPTION
	    "The total number of bytes sent in transport
	    send I/O operations."
    ::= { sqlServerBrokerTransportEntry 19 }

ssbtSendIOLenAvg OBJECT-TYPE
    SYNTAX     Gauge32
    MAX-ACCESS read-only
    STATUS     current
    DESCRIPTION
	    "The average byte length of transport send I/O
	    operations."
    ::= { sqlServerBrokerTransportEntry 20 }

ssbtSendIOBytesPerSec OBJECT-TYPE
    SYNTAX     Gauge32
    MAX-ACCESS read-only
    STATUS     current
    DESCRIPTION
	    "The number of transport send I/O bytes per
	    second."
    ::= { sqlServerBrokerTransportEntry 21 }

ssbtSendIOsPerSec OBJECT-TYPE
    SYNTAX     Gauge32
    MAX-ACCESS read-only
    STATUS     current
    DESCRIPTION
	    "The number of transport send I/Os per second.
	    Note that a transport send I/O may contain more
	    than one message fragment."
    ::= { sqlServerBrokerTransportEntry 22 }

sqlServerBufferManagerTable OBJECT-TYPE
    SYNTAX     SEQUENCE OF SqlServerBufferManagerEntry
    MAX-ACCESS not-accessible
    STATUS     current
    DESCRIPTION
	    "The Buffer Manager object provides counters to
	    monitor how Microsoft SQL Server uses: Memory
	    to store data pages, internal data structures,
	    and the procedure cache; Counters to monitor
	    the physical I/O as SQL Server reads database
	    pages from and writes database pages to disk. "
    ::= { sqlServer 22 }

sqlServerBufferManagerEntry OBJECT-TYPE
    SYNTAX     SqlServerBufferManagerEntry
    MAX-ACCESS not-accessible
    STATUS     current
    DESCRIPTION
	    "Performance information for one SQL Server
	    name instance."
    INDEX      { sqlServerNameIndex }
    ::= { sqlServerBufferManagerTable 1 }

SqlServerBufferManagerEntry ::= SEQUENCE {
    ssbmAWELookupMapsPerSec Gauge32,
    ssbmAWEStolenMapsPerSec Gauge32,
    ssbmAWEUnmapCallsPerSec Gauge32,
    ssbmAWEUnmapPagesPerSec Gauge32,
    ssbmAWEWriteMapsPerSec Gauge32,
    ssbmBufferCacheHitRatio Gauge32,
    ssbmCheckpointPagesPerSec Gauge32,
    ssbmDatabasePages Gauge32,
    ssbmFreeListStallsPerSec Gauge32,
    ssbmFreePages Gauge32,
    ssbmLazyWritesPerSec Gauge32,
    ssbmPageLifeExpectancy Gauge32,
    ssbmPageLookupsPerSec Gauge32,
    ssbmPageReadsPerSec Gauge32,
    ssbmPageWritesPerSec Gauge32,
    ssbmProcedureCachePages Gauge32,
    ssbmReadaheadPagesPerSec Gauge32,
    ssbmReservedPages Gauge32,
    ssbmStolenPages Gauge32,
    ssbmTargetPages Gauge32,
    ssbmTotalPages Gauge32
}

ssbmAWELookupMapsPerSec OBJECT-TYPE
    SYNTAX     Gauge32
    MAX-ACCESS read-only
    STATUS     current
    DESCRIPTION
	    "Number of AWE map calls made for pages found
	    in the buffer pool."
    ::= { sqlServerBufferManagerEntry 1 }

ssbmAWEStolenMapsPerSec OBJECT-TYPE
    SYNTAX     Gauge32
    MAX-ACCESS read-only
    STATUS     current
    DESCRIPTION
	    "Number of AWE map calls made for pages stolen
	    from the buffer pool."
    ::= { sqlServerBufferManagerEntry 2 }

ssbmAWEUnmapCallsPerSec OBJECT-TYPE
    SYNTAX     Gauge32
    MAX-ACCESS read-only
    STATUS     current
    DESCRIPTION
	    "Number of AWE unmap calls."
    ::= { sqlServerBufferManagerEntry 3 }

ssbmAWEUnmapPagesPerSec OBJECT-TYPE
    SYNTAX     Gauge32
    MAX-ACCESS read-only
    STATUS     current
    DESCRIPTION
	    "Number of AWE pages unmapped."
    ::= { sqlServerBufferManagerEntry 4 }

ssbmAWEWriteMapsPerSec OBJECT-TYPE
    SYNTAX     Gauge32
    MAX-ACCESS read-only
    STATUS     current
    DESCRIPTION
	    "Number of AWE map calls made for pages to be
	    written to disk."
    ::= { sqlServerBufferManagerEntry 5 }

ssbmBufferCacheHitRatio OBJECT-TYPE
    SYNTAX     Gauge32
    MAX-ACCESS read-only
    STATUS     current
    DESCRIPTION
	    "Percentage of pages that were found in the
	    buffer pool without having to incur a read from
	    disk."
    ::= { sqlServerBufferManagerEntry 6 }

ssbmCheckpointPagesPerSec OBJECT-TYPE
    SYNTAX     Gauge32
    MAX-ACCESS read-only
    STATUS     current
    DESCRIPTION
	    "Number of pages flushed by checkpoint or other
	    operations that require all dirty pages to be
	    flushed."
    ::= { sqlServerBufferManagerEntry 7 }

ssbmDatabasePages OBJECT-TYPE
    SYNTAX     Gauge32
    MAX-ACCESS read-only
    STATUS     current
    DESCRIPTION
	    "Number of pages in the buffer pool with
	    database content."
    ::= { sqlServerBufferManagerEntry 8 }

ssbmFreeListStallsPerSec OBJECT-TYPE
    SYNTAX     Gauge32
    MAX-ACCESS read-only
    STATUS     current
    DESCRIPTION
	    "Number of requests that had to wait for a free
	    page."
    ::= { sqlServerBufferManagerEntry 9 }

ssbmFreePages OBJECT-TYPE
    SYNTAX     Gauge32
    MAX-ACCESS read-only
    STATUS     current
    DESCRIPTION
	    "Total number of pages on all free lists."
    ::= { sqlServerBufferManagerEntry 10 }

ssbmLazyWritesPerSec OBJECT-TYPE
    SYNTAX     Gauge32
    MAX-ACCESS read-only
    STATUS     current
    DESCRIPTION
	    "Number of buffers written by buffer manager's
	    lazy writer."
    ::= { sqlServerBufferManagerEntry 11 }

ssbmPageLifeExpectancy OBJECT-TYPE
    SYNTAX     Gauge32
    MAX-ACCESS read-only
    STATUS     current
    DESCRIPTION
	    "Number of seconds a page will stay in the
	    buffer pool without references."
    ::= { sqlServerBufferManagerEntry 12 }

ssbmPageLookupsPerSec OBJECT-TYPE
    SYNTAX     Gauge32
    MAX-ACCESS read-only
    STATUS     current
    DESCRIPTION
	    "Number of requests to find a page in the
	    buffer pool."
    ::= { sqlServerBufferManagerEntry 13 }

ssbmPageReadsPerSec OBJECT-TYPE
    SYNTAX     Gauge32
    MAX-ACCESS read-only
    STATUS     current
    DESCRIPTION
	    "Number of physical database page reads
	    issued."
    ::= { sqlServerBufferManagerEntry 14 }

ssbmPageWritesPerSec OBJECT-TYPE
    SYNTAX     Gauge32
    MAX-ACCESS read-only
    STATUS     current
    DESCRIPTION
	    "Number of physical database page writes
	    issued."
    ::= { sqlServerBufferManagerEntry 15 }

ssbmProcedureCachePages OBJECT-TYPE
    SYNTAX     Gauge32
    MAX-ACCESS read-only
    STATUS     current
    DESCRIPTION
	    "Number of pages used to store compiled
	    queries."
    ::= { sqlServerBufferManagerEntry 16 }

ssbmReadaheadPagesPerSec OBJECT-TYPE
    SYNTAX     Gauge32
    MAX-ACCESS read-only
    STATUS     current
    DESCRIPTION
	    "Number of pages read in anticipation of use."
    ::= { sqlServerBufferManagerEntry 17 }

ssbmReservedPages OBJECT-TYPE
    SYNTAX     Gauge32
    MAX-ACCESS read-only
    STATUS     current
    DESCRIPTION
	    "Number of buffer pool reserved pages."
    ::= { sqlServerBufferManagerEntry 18 }

ssbmStolenPages OBJECT-TYPE
    SYNTAX     Gauge32
    MAX-ACCESS read-only
    STATUS     current
    DESCRIPTION
	    "Number of pages used for miscellaneous server
	    purposes (including procedure cache)."
    ::= { sqlServerBufferManagerEntry 19 }

ssbmTargetPages OBJECT-TYPE
    SYNTAX     Gauge32
    MAX-ACCESS read-only
    STATUS     current
    DESCRIPTION
	    "Ideal number of pages in the buffer pool."
    ::= { sqlServerBufferManagerEntry 20 }

ssbmTotalPages OBJECT-TYPE
    SYNTAX     Gauge32
    MAX-ACCESS read-only
    STATUS     current
    DESCRIPTION
	    "Number of pages in the buffer pool (includes
	    database, free, and stolen)."
    ::= { sqlServerBufferManagerEntry 21 }

sqlServerBufferPartitionTable OBJECT-TYPE
    SYNTAX     SEQUENCE OF SQLServerBufferPartitionEntry
    MAX-ACCESS not-accessible
    STATUS     current
    DESCRIPTION
	    "The Buffer Partition object provides counters
	    to monitor how Microsoft SQL Server uses free
	    pages."
    ::= { sqlServer 23 }

sqlServerBufferPartitionEntry OBJECT-TYPE
    SYNTAX     SQLServerBufferPartitionEntry
    MAX-ACCESS not-accessible
    STATUS     current
    DESCRIPTION
	    "Performance information for one particular SQL
	    Server name instance of 'SQLServer:Buffer
	    Partition' object."
    INDEX      { sqlServerNameIndex, ssbpInstance }
    ::= { sqlServerBufferPartitionTable 1 }

SQLServerBufferPartitionEntry ::= SEQUENCE {
    ssbpInstance InstanceName,
    ssbpFreeListEmptyPerSec Gauge32,
    ssbpFreeListRequestsPerSec Gauge32,
    ssbpFreePages Gauge32
}

ssbpInstance OBJECT-TYPE
    SYNTAX     InstanceName
    MAX-ACCESS read-only
    STATUS     current
    DESCRIPTION
	    "Instance name."
    ::= { sqlServerBufferPartitionEntry 1 }

ssbpFreeListEmptyPerSec OBJECT-TYPE
    SYNTAX     Gauge32
    MAX-ACCESS read-only
    STATUS     current
    DESCRIPTION
	    "Number of times a free page was requested and
	    none were available."
    ::= { sqlServerBufferPartitionEntry 2 }

ssbpFreeListRequestsPerSec OBJECT-TYPE
    SYNTAX     Gauge32
    MAX-ACCESS read-only
    STATUS     current
    DESCRIPTION
	    "Number of times a free page was requested."
    ::= { sqlServerBufferPartitionEntry 3 }

ssbpFreePages OBJECT-TYPE
    SYNTAX     Gauge32
    MAX-ACCESS read-only
    STATUS     current
    DESCRIPTION
	    "Total number of pages on all free lists."
    ::= { sqlServerBufferPartitionEntry 4 }

sqlServerCacheManagerTable OBJECT-TYPE
    SYNTAX     SEQUENCE OF SQLServerCacheManagerEntry
    MAX-ACCESS not-accessible
    STATUS     current
    DESCRIPTION
	    "The Cache Manager object provides counters to
	    monitor how Microsoft SQL Server uses memory to
	    store objects such as stored procedures, ad hoc
	    and prepared Transact-SQL statements, and
	    triggers. Multiple instances of the Cache
	    Manager object can be monitored at the same
	    time, with each instance representing a
	    different type of plan to monitor."
    ::= { sqlServer 24 }

sqlServerCacheManagerEntry OBJECT-TYPE
    SYNTAX     SQLServerCacheManagerEntry
    MAX-ACCESS not-accessible
    STATUS     current
    DESCRIPTION
	    "Performance information for one particular SQL
	    Server name instance of 'SQLServer:Cache
	    Manager' object."
    INDEX      { sqlServerNameIndex, sscmInstance }
    ::= { sqlServerCacheManagerTable 1 }

SQLServerCacheManagerEntry ::= SEQUENCE {
    sscmInstance InstanceName,
    sscmCacheHitRatio Gauge32,
    sscmCacheObjectCounts Gauge32,
    sscmCachePages Gauge32,
    sscmCacheUseCountsPerSec Gauge32
}

sscmInstance OBJECT-TYPE
    SYNTAX     InstanceName
    MAX-ACCESS read-only
    STATUS     current
    DESCRIPTION
	    "Instance name."
    ::= { sqlServerCacheManagerEntry 1 }

sscmCacheHitRatio OBJECT-TYPE
    SYNTAX     Gauge32
    MAX-ACCESS read-only
    STATUS     current
    DESCRIPTION
	    "Ratio between cache hits and lookups"
    ::= { sqlServerCacheManagerEntry 2 }

sscmCacheObjectCounts OBJECT-TYPE
    SYNTAX     Gauge32
    MAX-ACCESS read-only
    STATUS     current
    DESCRIPTION
	    "Number of cache objects in the cache"
    ::= { sqlServerCacheManagerEntry 3 }

sscmCachePages OBJECT-TYPE
    SYNTAX     Gauge32
    MAX-ACCESS read-only
    STATUS     current
    DESCRIPTION
	    "Number of 8k pages used by cache objects"
    ::= { sqlServerCacheManagerEntry 4 }

sscmCacheUseCountsPerSec OBJECT-TYPE
    SYNTAX     Gauge32
    MAX-ACCESS read-only
    STATUS     current
    DESCRIPTION
	    "Times each type of cache object has been used"
    ::= { sqlServerCacheManagerEntry 5 }

sqlServerCursorManagerTotalTable OBJECT-TYPE
    SYNTAX     SEQUENCE OF SqlServerCursorManagerTotalEntry
    MAX-ACCESS not-accessible
    STATUS     current
    DESCRIPTION
	    "Counters for cursor properties not grouped by
	    type"
    ::= { sqlServer 25 }

sqlServerCursorManagerTotalEntry OBJECT-TYPE
    SYNTAX     SqlServerCursorManagerTotalEntry
    MAX-ACCESS not-accessible
    STATUS     current
    DESCRIPTION
	    "Performance information for one SQL Server
	    name instance."
    INDEX      { sqlServerNameIndex }
    ::= { sqlServerCursorManagerTotalTable 1 }

SqlServerCursorManagerTotalEntry ::= SEQUENCE {
    sscmtAsyncPopulationCount Gauge32,
    sscmtCursorConversionRate Gauge32,
    sscmtCursorFlushes Gauge32
}

sscmtAsyncPopulationCount OBJECT-TYPE
    SYNTAX     Gauge32
    MAX-ACCESS read-only
    STATUS     current
    DESCRIPTION
	    "Number of cursor being populated
	    asynchronously."
    ::= { sqlServerCursorManagerTotalEntry 1 }

sscmtCursorConversionRate OBJECT-TYPE
    SYNTAX     Gauge32
    MAX-ACCESS read-only
    STATUS     current
    DESCRIPTION
	    "Number of cursors conversions/sec."
    ::= { sqlServerCursorManagerTotalEntry 2 }

sscmtCursorFlushes OBJECT-TYPE
    SYNTAX     Gauge32
    MAX-ACCESS read-only
    STATUS     current
    DESCRIPTION
	    "Total number of times a flush for a cursor
	    xstmt occured."
    ::= { sqlServerCursorManagerTotalEntry 3 }

sqlServerCursorManagerByTypeTable OBJECT-TYPE
    SYNTAX     SEQUENCE OF SqlServerCursorManagerByTypeEntry
    MAX-ACCESS not-accessible
    STATUS     current
    DESCRIPTION
	    "Counters for cursor properties grouped by
	    type"
    ::= { sqlServer 26 }

sqlServerCursorManagerByTypeEntry OBJECT-TYPE
    SYNTAX     SqlServerCursorManagerByTypeEntry
    MAX-ACCESS not-accessible
    STATUS     current
    DESCRIPTION
	    "Performance information for one particular SQL
	    Server name instance of 'Cursor Manager by
	    Type' object."
    INDEX      { sqlServerNameIndex, sscmbtInstance }
    ::= { sqlServerCursorManagerByTypeTable 1 }

SqlServerCursorManagerByTypeEntry ::= SEQUENCE {
    sscmbtInstance InstanceName,
    sscmbtActiveCursors Gauge32,
    sscmbtCacheHitRatio Gauge32,
    sscmbtCachedCursorCounts Gauge32,
    sscmbtCursorCacheUseCountsPerSec Gauge32,
    sscmbtCursorRequestsPerSec Gauge32,
    sscmbtCursorMemoryUsage Gauge32,
    sscmbtCursorWorktableUsage Gauge32,
    sscmbtNumberOfActiveCursorPlans Gauge32
}

sscmbtInstance OBJECT-TYPE
    SYNTAX     InstanceName
    MAX-ACCESS read-only
    STATUS     current
    DESCRIPTION
	    "Instance name."
    ::= { sqlServerCursorManagerByTypeEntry 1 }

sscmbtActiveCursors OBJECT-TYPE
    SYNTAX     Gauge32
    MAX-ACCESS read-only
    STATUS     current
    DESCRIPTION
	    "Number of active cursors."
    ::= { sqlServerCursorManagerByTypeEntry 2 }

sscmbtCacheHitRatio OBJECT-TYPE
    SYNTAX     Gauge32
    MAX-ACCESS read-only
    STATUS     current
    DESCRIPTION
	    "Ratio between cache hits and lookups"
    ::= { sqlServerCursorManagerByTypeEntry 3 }

sscmbtCachedCursorCounts OBJECT-TYPE
    SYNTAX     Gauge32
    MAX-ACCESS read-only
    STATUS     current
    DESCRIPTION
	    "Number of cursors of a given type in the
	    cache"
    ::= { sqlServerCursorManagerByTypeEntry 4 }

sscmbtCursorCacheUseCountsPerSec OBJECT-TYPE
    SYNTAX     Gauge32
    MAX-ACCESS read-only
    STATUS     current
    DESCRIPTION
	    "Times each type of cached cursor has been
	    used"
    ::= { sqlServerCursorManagerByTypeEntry 5 }

sscmbtCursorRequestsPerSec OBJECT-TYPE
    SYNTAX     Gauge32
    MAX-ACCESS read-only
    STATUS     current
    DESCRIPTION
	    "Number of SQL cursor requests received by
	    server."
    ::= { sqlServerCursorManagerByTypeEntry 6 }

sscmbtCursorMemoryUsage OBJECT-TYPE
    SYNTAX     Gauge32
    MAX-ACCESS read-only
    STATUS     current
    DESCRIPTION
	    "Amount of memory consumed by cursors (KB)."
    ::= { sqlServerCursorManagerByTypeEntry 7 }

sscmbtCursorWorktableUsage OBJECT-TYPE
    SYNTAX     Gauge32
    MAX-ACCESS read-only
    STATUS     current
    DESCRIPTION
	    "Number of worktables used by cursors."
    ::= { sqlServerCursorManagerByTypeEntry 8 }

sscmbtNumberOfActiveCursorPlans OBJECT-TYPE
    SYNTAX     Gauge32
    MAX-ACCESS read-only
    STATUS     current
    DESCRIPTION
	    "Number of cursor plans."
    ::= { sqlServerCursorManagerByTypeEntry 9 }

sqlServerDatabasesTable OBJECT-TYPE
    SYNTAX     SEQUENCE OF SqlServerDatabasesEntry
    MAX-ACCESS not-accessible
    STATUS     current
    DESCRIPTION
	    "The Databases object in Microsoft SQL Server
	    provides counters to monitor bulk copy
	    operations, backup and restore throughput, and
	    transaction log activities. Monitor
	    transactions and the transaction log to
	    determine how much user activity is occurring
	    in the database and how full the transaction
	    log is becoming. The amount of user activity
	    can determine the performance of the database
	    and affect log size, locking, and replication.
	    Monitoring low-level log activity to gauge user
	    activity and resource usage can help you to
	    identify performance bottlenecks. Multiple
	    instances of the Databases object, each
	    representing a single database, can be
	    monitored at the same time."
    ::= { sqlServer 27 }

sqlServerDatabasesEntry OBJECT-TYPE
    SYNTAX     SqlServerDatabasesEntry
    MAX-ACCESS not-accessible
    STATUS     current
    DESCRIPTION
	    "Performance information for one particular SQL
	    Server name instance of 'Databases' object."
    INDEX      { sqlServerNameIndex, ssdInstance }
    ::= { sqlServerDatabasesTable 1 }

SqlServerDatabasesEntry ::= SEQUENCE {
    ssdInstance InstanceName,
    ssdActiveTransactions Gauge32,
    ssdBackupPerRestoreThroughputPerSec Gauge32,
    ssdBulkCopyRowsPerSec Gauge32,
    ssdBulkCopyThroughputPerSec Gauge32,
    ssdDBCCLogicalScanBytesPerSec Gauge32,
    ssdDataFileSSizeKB Gauge32,
    ssdLogBytesFlushedPerSec Gauge32,
    ssdLogCacheHitRatio Gauge32,
    ssdLogCacheReadsPerSec Gauge32,
    ssdLogFileSSizeKB Gauge32,
    ssdLogFileSUsedSizeKB Gauge32,
    ssdLogFlushWaitTime Gauge32,
    ssdLogFlushWaitsPerSec Gauge32,
    ssdLogFlushesPerSec Gauge32,
    ssdLogGrowths Gauge32,
    ssdLogShrinks Gauge32,
    ssdLogTruncations Gauge32,
    ssdMirroringAcksReceivedPerSec Gauge32,
    ssdMirroringBytesSentPerSec Gauge32,
    ssdMirroringPagesSentPerSec Gauge32,
    ssdMirroringSendsPerSec Gauge32,
    ssdMirroringTotalAcksReceived Gauge32,
    ssdMirroringTotalBytesSent Gauge32,
    ssdMirroringTotalPagesSent Gauge32,
    ssdMirroringTotalSends Gauge32,
    ssdMirroringTransactionDelay Gauge32,
    ssdPercentLogUsed Gauge32,
    ssdReplPendingXacts Gauge32,
    ssdReplTransRate Gauge32,
    ssdShrinkDataMovementBytesPerSec Gauge32,
    ssdTransactionsPerSec Gauge32
}

ssdInstance OBJECT-TYPE
    SYNTAX     InstanceName
    MAX-ACCESS read-only
    STATUS     current
    DESCRIPTION
	    "Instance name."
    ::= { sqlServerDatabasesEntry 1 }

ssdActiveTransactions OBJECT-TYPE
    SYNTAX     Gauge32
    MAX-ACCESS read-only
    STATUS     current
    DESCRIPTION
	    "Number of active update transactions for the
	    database."
    ::= { sqlServerDatabasesEntry 2 }

ssdBackupPerRestoreThroughputPerSec OBJECT-TYPE
    SYNTAX     Gauge32
    MAX-ACCESS read-only
    STATUS     current
    DESCRIPTION
	    "Read/write throughput for backup/restore of a
	    database."
    ::= { sqlServerDatabasesEntry 3 }

ssdBulkCopyRowsPerSec OBJECT-TYPE
    SYNTAX     Gauge32
    MAX-ACCESS read-only
    STATUS     current
    DESCRIPTION
	    "Number of rows bulk copied."
    ::= { sqlServerDatabasesEntry 4 }

ssdBulkCopyThroughputPerSec OBJECT-TYPE
    SYNTAX     Gauge32
    MAX-ACCESS read-only
    STATUS     current
    DESCRIPTION
	    "KiloBytes bulk copied."
    ::= { sqlServerDatabasesEntry 5 }

ssdDBCCLogicalScanBytesPerSec OBJECT-TYPE
    SYNTAX     Gauge32
    MAX-ACCESS read-only
    STATUS     current
    DESCRIPTION
	    "Logical read scan rate for DBCC commands"
    ::= { sqlServerDatabasesEntry 6 }

ssdDataFileSSizeKB OBJECT-TYPE
    SYNTAX     Gauge32
    MAX-ACCESS read-only
    STATUS     current
    DESCRIPTION
	    "The cumulative size of all the data files in
	    the database."
    ::= { sqlServerDatabasesEntry 7 }

ssdLogBytesFlushedPerSec OBJECT-TYPE
    SYNTAX     Gauge32
    MAX-ACCESS read-only
    STATUS     current
    DESCRIPTION
	    "Total number of log bytes flushed."
    ::= { sqlServerDatabasesEntry 8 }

ssdLogCacheHitRatio OBJECT-TYPE
    SYNTAX     Gauge32
    MAX-ACCESS read-only
    STATUS     current
    DESCRIPTION
	    "Percentage of log cache reads that were
	    satisfied from the log cache."
    ::= { sqlServerDatabasesEntry 9 }

ssdLogCacheReadsPerSec OBJECT-TYPE
    SYNTAX     Gauge32
    MAX-ACCESS read-only
    STATUS     current
    DESCRIPTION
	    "Reads performed through the log manager
	    cache."
    ::= { sqlServerDatabasesEntry 10 }

ssdLogFileSSizeKB OBJECT-TYPE
    SYNTAX     Gauge32
    MAX-ACCESS read-only
    STATUS     current
    DESCRIPTION
	    "The cumulative size of all the log files in
	    the database."
    ::= { sqlServerDatabasesEntry 11 }

ssdLogFileSUsedSizeKB OBJECT-TYPE
    SYNTAX     Gauge32
    MAX-ACCESS read-only
    STATUS     current
    DESCRIPTION
	    "The cumulative used size of all the log files
	    in the database."
    ::= { sqlServerDatabasesEntry 12 }

ssdLogFlushWaitTime OBJECT-TYPE
    SYNTAX     Gauge32
    MAX-ACCESS read-only
    STATUS     current
    DESCRIPTION
	    "Total wait time (milliseconds)."
    ::= { sqlServerDatabasesEntry 13 }

ssdLogFlushWaitsPerSec OBJECT-TYPE
    SYNTAX     Gauge32
    MAX-ACCESS read-only
    STATUS     current
    DESCRIPTION
	    "Number of commits waiting on log flush."
    ::= { sqlServerDatabasesEntry 14 }

ssdLogFlushesPerSec OBJECT-TYPE
    SYNTAX     Gauge32
    MAX-ACCESS read-only
    STATUS     current
    DESCRIPTION
	    "Number of log flushes."
    ::= { sqlServerDatabasesEntry 15 }

ssdLogGrowths OBJECT-TYPE
    SYNTAX     Gauge32
    MAX-ACCESS read-only
    STATUS     current
    DESCRIPTION
	    "Total number of log growths for this
	    database."
    ::= { sqlServerDatabasesEntry 16 }

ssdLogShrinks OBJECT-TYPE
    SYNTAX     Gauge32
    MAX-ACCESS read-only
    STATUS     current
    DESCRIPTION
	    "Total number of log shrinks for this
	    database."
    ::= { sqlServerDatabasesEntry 17 }

ssdLogTruncations OBJECT-TYPE
    SYNTAX     Gauge32
    MAX-ACCESS read-only
    STATUS     current
    DESCRIPTION
	    "Total number of log truncations for this
	    database."
    ::= { sqlServerDatabasesEntry 18 }

ssdMirroringAcksReceivedPerSec OBJECT-TYPE
    SYNTAX     Gauge32
    MAX-ACCESS read-only
    STATUS     current
    DESCRIPTION
	    "Number of acknowledgements received per
	    second"
    ::= { sqlServerDatabasesEntry 19 }

ssdMirroringBytesSentPerSec OBJECT-TYPE
    SYNTAX     Gauge32
    MAX-ACCESS read-only
    STATUS     current
    DESCRIPTION
	    "Number of bytes sent per second"
    ::= { sqlServerDatabasesEntry 20 }

ssdMirroringPagesSentPerSec OBJECT-TYPE
    SYNTAX     Gauge32
    MAX-ACCESS read-only
    STATUS     current
    DESCRIPTION
	    "Number of pages sent per second"
    ::= { sqlServerDatabasesEntry 21 }

ssdMirroringSendsPerSec OBJECT-TYPE
    SYNTAX     Gauge32
    MAX-ACCESS read-only
    STATUS     current
    DESCRIPTION
	    "Number of sends initiated per second"
    ::= { sqlServerDatabasesEntry 22 }

ssdMirroringTotalAcksReceived OBJECT-TYPE
    SYNTAX     Gauge32
    MAX-ACCESS read-only
    STATUS     current
    DESCRIPTION
	    "Total number of acknowledgements received"
    ::= { sqlServerDatabasesEntry 23 }

ssdMirroringTotalBytesSent OBJECT-TYPE
    SYNTAX     Gauge32
    MAX-ACCESS read-only
    STATUS     current
    DESCRIPTION
	    "Total number of bytes sent"
    ::= { sqlServerDatabasesEntry 24 }

ssdMirroringTotalPagesSent OBJECT-TYPE
    SYNTAX     Gauge32
    MAX-ACCESS read-only
    STATUS     current
    DESCRIPTION
	    "Total number of pages sent"
    ::= { sqlServerDatabasesEntry 25 }

ssdMirroringTotalSends OBJECT-TYPE
    SYNTAX     Gauge32
    MAX-ACCESS read-only
    STATUS     current
    DESCRIPTION
	    "Total number of sends initiated"
    ::= { sqlServerDatabasesEntry 26 }

ssdMirroringTransactionDelay OBJECT-TYPE
    SYNTAX     Gauge32
    MAX-ACCESS read-only
    STATUS     current
    DESCRIPTION
	    "Average delay in transaction termination
	    waiting for acknowledgement"
    ::= { sqlServerDatabasesEntry 27 }

ssdPercentLogUsed OBJECT-TYPE
    SYNTAX     Gauge32
    MAX-ACCESS read-only
    STATUS     current
    DESCRIPTION
	    "The percent of space in the log that is in
	    use."
    ::= { sqlServerDatabasesEntry 28 }

ssdReplPendingXacts OBJECT-TYPE
    SYNTAX     Gauge32
    MAX-ACCESS read-only
    STATUS     current
    DESCRIPTION
	    "Number of pending replication transactions in
	    the database."
    ::= { sqlServerDatabasesEntry 29 }

ssdReplTransRate OBJECT-TYPE
    SYNTAX     Gauge32
    MAX-ACCESS read-only
    STATUS     current
    DESCRIPTION
	    "Replication transaction rate (replicated
	    transactions/sec.)."
    ::= { sqlServerDatabasesEntry 30 }

ssdShrinkDataMovementBytesPerSec OBJECT-TYPE
    SYNTAX     Gauge32
    MAX-ACCESS read-only
    STATUS     current
    DESCRIPTION
	    "The rate data is being moved by Autoshrink,
	    DBCC SHRINKDATABASE or SHRINKFILE."
    ::= { sqlServerDatabasesEntry 31 }

ssdTransactionsPerSec OBJECT-TYPE
    SYNTAX     Gauge32
    MAX-ACCESS read-only
    STATUS     current
    DESCRIPTION
	    "Number of transactions started for the
	    database."
    ::= { sqlServerDatabasesEntry 32 }

sqlServerExecStatisticsTable OBJECT-TYPE
    SYNTAX     SEQUENCE OF SqlServerExecStatisticsEntry
    MAX-ACCESS not-accessible
    STATUS     current
    DESCRIPTION
	    "Execution statistics for external calls"
    ::= { sqlServer 28 }

sqlServerExecStatisticsEntry OBJECT-TYPE
    SYNTAX     SqlServerExecStatisticsEntry
    MAX-ACCESS not-accessible
    STATUS     current
    DESCRIPTION
	    "Performance information for one particular SQL
	    Server name instance of 'ExecStatistics'
	    object."
    INDEX      { sqlServerNameIndex, ssesInstance }
    ::= { sqlServerExecStatisticsTable 1 }

SqlServerExecStatisticsEntry ::= SEQUENCE {
    ssesInstance InstanceName,
    ssesDTCCalls Gauge32,
    ssesDistributedQuery Gauge32,
    ssesExtendedProcedures Gauge32,
    ssesOLEDBCalls Gauge32
}

ssesInstance OBJECT-TYPE
    SYNTAX     InstanceName
    MAX-ACCESS read-only
    STATUS     current
    DESCRIPTION
	    "Instance name."
    ::= { sqlServerExecStatisticsEntry 1 }

ssesDTCCalls OBJECT-TYPE
    SYNTAX     Gauge32
    MAX-ACCESS read-only
    STATUS     current
    DESCRIPTION
	    "Statistics relevant to execution of DTC
	    calls."
    ::= { sqlServerExecStatisticsEntry 2 }

ssesDistributedQuery OBJECT-TYPE
    SYNTAX     Gauge32
    MAX-ACCESS read-only
    STATUS     current
    DESCRIPTION
	    "Statistics relevant to execution of
	    distributed queries."
    ::= { sqlServerExecStatisticsEntry 3 }

ssesExtendedProcedures OBJECT-TYPE
    SYNTAX     Gauge32
    MAX-ACCESS read-only
    STATUS     current
    DESCRIPTION
	    "Statistics relevant to execution of XP calls."
    ::= { sqlServerExecStatisticsEntry 4 }

ssesOLEDBCalls OBJECT-TYPE
    SYNTAX     Gauge32
    MAX-ACCESS read-only
    STATUS     current
    DESCRIPTION
	    "Statistics relevant to execution of OLEDB
	    calls."
    ::= { sqlServerExecStatisticsEntry 5 }

sqlServerGeneralStatisticsTable OBJECT-TYPE
    SYNTAX     SEQUENCE OF SqlServerGeneralStatisticsEntry
    MAX-ACCESS not-accessible
    STATUS     current
    DESCRIPTION
	    "The General Statistics object in Microsoft SQL
	    Server provides counters to monitor general
	    server-wide activity, such as the number of
	    current connections and the number of users
	    connecting and disconnecting per second from
	    computers running an instance of SQL Server.
	    This can be useful when you are working on
	    large online transaction processing (OLTP) type
	    systems where there are many clients connecting
	    and disconnecting from an instance of SQL
	    Server."
    ::= { sqlServer 29 }

sqlServerGeneralStatisticsEntry OBJECT-TYPE
    SYNTAX     SqlServerGeneralStatisticsEntry
    MAX-ACCESS not-accessible
    STATUS     current
    DESCRIPTION
	    "Performance information for one SQL Server
	    name instance."
    INDEX      { sqlServerNameIndex }
    ::= { sqlServerGeneralStatisticsTable 1 }

SqlServerGeneralStatisticsEntry ::= SEQUENCE {
    ssgsHTTPAnonymousRequests Gauge32,
    ssgsHTTPAuthenticatedRequests Gauge32,
    ssgsLogicalConnections Gauge32,
    ssgsLoginsPerSec Gauge32,
    ssgsLogoutsPerSec Gauge32,
    ssgsMarsDeadlocks Gauge32,
    ssgsNonAtomicYieldRate Gauge32,
    ssgsProcessesBlocked Gauge32,
    ssgsSOAPEmptyRequests Gauge32,
    ssgsSOAPMethodInvocations Gauge32,
    ssgsSOAPSQLRequests Gauge32,
    ssgsSOAPSessionInitiateRequests Gauge32,
    ssgsSOAPSessionTerminateRequests Gauge32,
    ssgsSOAPWSDLRequests Gauge32,
    ssgsTempTablesCreationRate Gauge32,
    ssgsTransactions Gauge32,
    ssgsUserConnections Gauge32
}

ssgsHTTPAnonymousRequests OBJECT-TYPE
    SYNTAX     Gauge32
    MAX-ACCESS read-only
    STATUS     current
    DESCRIPTION
	    "Number of anonymous HTTP requests started per
	    second."
    ::= { sqlServerGeneralStatisticsEntry 1 }

ssgsHTTPAuthenticatedRequests OBJECT-TYPE
    SYNTAX     Gauge32
    MAX-ACCESS read-only
    STATUS     current
    DESCRIPTION
	    "Number of authenticated HTTP requests started
	    per second."
    ::= { sqlServerGeneralStatisticsEntry 2 }

ssgsLogicalConnections OBJECT-TYPE
    SYNTAX     Gauge32
    MAX-ACCESS read-only
    STATUS     current
    DESCRIPTION
	    "Number of logical connections to the system."
    ::= { sqlServerGeneralStatisticsEntry 3 }

ssgsLoginsPerSec OBJECT-TYPE
    SYNTAX     Gauge32
    MAX-ACCESS read-only
    STATUS     current
    DESCRIPTION
	    "Total number of logins started per second."
    ::= { sqlServerGeneralStatisticsEntry 4 }

ssgsLogoutsPerSec OBJECT-TYPE
    SYNTAX     Gauge32
    MAX-ACCESS read-only
    STATUS     current
    DESCRIPTION
	    "Total number of logouts started per second."
    ::= { sqlServerGeneralStatisticsEntry 5 }

ssgsMarsDeadlocks OBJECT-TYPE
    SYNTAX     Gauge32
    MAX-ACCESS read-only
    STATUS     current
    DESCRIPTION
	    "Number of Mars Deadlocks detected."
    ::= { sqlServerGeneralStatisticsEntry 6 }

ssgsNonAtomicYieldRate OBJECT-TYPE
    SYNTAX     Gauge32
    MAX-ACCESS read-only
    STATUS     current
    DESCRIPTION
	    "Number of non-atomic yields per second."
    ::= { sqlServerGeneralStatisticsEntry 7 }

ssgsProcessesBlocked OBJECT-TYPE
    SYNTAX     Gauge32
    MAX-ACCESS read-only
    STATUS     current
    DESCRIPTION
	    "Number of currently blocked processes."
    ::= { sqlServerGeneralStatisticsEntry 8 }

ssgsSOAPEmptyRequests OBJECT-TYPE
    SYNTAX     Gauge32
    MAX-ACCESS read-only
    STATUS     current
    DESCRIPTION
	    "Number of empty SOAP requests started per
	    second."
    ::= { sqlServerGeneralStatisticsEntry 9 }

ssgsSOAPMethodInvocations OBJECT-TYPE
    SYNTAX     Gauge32
    MAX-ACCESS read-only
    STATUS     current
    DESCRIPTION
	    "Number of SOAP method invocations started per
	    second."
    ::= { sqlServerGeneralStatisticsEntry 10 }

ssgsSOAPSQLRequests OBJECT-TYPE
    SYNTAX     Gauge32
    MAX-ACCESS read-only
    STATUS     current
    DESCRIPTION
	    "Number of SOAP SQL requests started per
	    second."
    ::= { sqlServerGeneralStatisticsEntry 11 }

ssgsSOAPSessionInitiateRequests OBJECT-TYPE
    SYNTAX     Gauge32
    MAX-ACCESS read-only
    STATUS     current
    DESCRIPTION
	    "Number of SOAP Session initiate requests
	    started per second."
    ::= { sqlServerGeneralStatisticsEntry 12 }

ssgsSOAPSessionTerminateRequests OBJECT-TYPE
    SYNTAX     Gauge32
    MAX-ACCESS read-only
    STATUS     current
    DESCRIPTION
	    "Number of SOAP Session terminate requests
	    started per second."
    ::= { sqlServerGeneralStatisticsEntry 13 }

ssgsSOAPWSDLRequests OBJECT-TYPE
    SYNTAX     Gauge32
    MAX-ACCESS read-only
    STATUS     current
    DESCRIPTION
	    "Number of SOAP Web Service Description
	    Language requests started per second."
    ::= { sqlServerGeneralStatisticsEntry 14 }

ssgsTempTablesCreationRate OBJECT-TYPE
    SYNTAX     Gauge32
    MAX-ACCESS read-only
    STATUS     current
    DESCRIPTION
	    "Number of temporary tables/table variables
	    created/sec"
    ::= { sqlServerGeneralStatisticsEntry 15 }

ssgsTransactions OBJECT-TYPE
    SYNTAX     Gauge32
    MAX-ACCESS read-only
    STATUS     current
    DESCRIPTION
	    "Number of transaction enlistments (local, dtc,
	    bound all combined)."
    ::= { sqlServerGeneralStatisticsEntry 16 }

ssgsUserConnections OBJECT-TYPE
    SYNTAX     Gauge32
    MAX-ACCESS read-only
    STATUS     current
    DESCRIPTION
	    "Number of users connected to the system."
    ::= { sqlServerGeneralStatisticsEntry 17 }

sqlServerLatchesTable OBJECT-TYPE
    SYNTAX     SEQUENCE OF SqlServerLatchesEntry
    MAX-ACCESS not-accessible
    STATUS     current
    DESCRIPTION
	    "The Latches object in Microsoft SQL Server
	    provides counters to monitor internal SQL
	    Server resource locks called latches.
	    Monitoring the latches to determine user
	    activity and resource usage can help you to
	    identify performance bottlenecks."
    ::= { sqlServer 30 }

sqlServerLatchesEntry OBJECT-TYPE
    SYNTAX     SqlServerLatchesEntry
    MAX-ACCESS not-accessible
    STATUS     current
    DESCRIPTION
	    "Performance information for one SQL Server
	    name instance."
    INDEX      { sqlServerNameIndex }
    ::= { sqlServerLatchesTable 1 }

SqlServerLatchesEntry ::= SEQUENCE {
    ssltAverageLatchWaitTimeMs Gauge32,
    ssltLatchWaitsPerSec Gauge32,
    ssltTotalLatchWaitTimeMs Gauge32
}

ssltAverageLatchWaitTimeMs OBJECT-TYPE
    SYNTAX     Gauge32
    MAX-ACCESS read-only
    STATUS     current
    DESCRIPTION
	    "Average latch wait time (milliseconds) for
	    latch requests that had to wait."
    ::= { sqlServerLatchesEntry 1 }

ssltLatchWaitsPerSec OBJECT-TYPE
    SYNTAX     Gauge32
    MAX-ACCESS read-only
    STATUS     current
    DESCRIPTION
	    "Number of latch requests that could not be
	    granted immediately and had to wait before
	    being granted."
    ::= { sqlServerLatchesEntry 2 }

ssltTotalLatchWaitTimeMs OBJECT-TYPE
    SYNTAX     Gauge32
    MAX-ACCESS read-only
    STATUS     current
    DESCRIPTION
	    "Total latch wait time (milliseconds) for latch
	    requests that had to wait in the last second."
    ::= { sqlServerLatchesEntry 3 }

sqlServerLocksTable OBJECT-TYPE
    SYNTAX     SEQUENCE OF SQLServerLocksEntry
    MAX-ACCESS not-accessible
    STATUS     current
    DESCRIPTION
	    "The Locks object in Microsoft SQL Server
	    provides information about SQL Server locks on
	    individual resource types. Locks are held on
	    SQL Server resources, such as rows read or
	    modified during a transaction, to prevent
	    concurrent use of resources by multiple
	    transactions. For example, if an exclusive (X)
	    lock is held on a row within a table by a
	    transaction, no other transaction can modify
	    that row until the lock is released. Minimizing
	    locks increases concurrency, which can improve
	    performance. Multiple instances of the Locks
	    object can be monitored at the same time, with
	    each instance representing a lock on a resource
	    type."
    ::= { sqlServer 31 }

sqlServerLocksEntry OBJECT-TYPE
    SYNTAX     SQLServerLocksEntry
    MAX-ACCESS not-accessible
    STATUS     current
    DESCRIPTION
	    "Performance information for one particular SQL
	    Server name instance of 'SQLServer:Locks'
	    object."
    INDEX      { sqlServerNameIndex, sslkInstance }
    ::= { sqlServerLocksTable 1 }

SQLServerLocksEntry ::= SEQUENCE {
    sslkInstance InstanceName,
    sslkAverageWaitTimeMs Gauge32,
    sslkLockRequestsPerSec Gauge32,
    sslkLockTimeoutsTimeoutGT0PerSec Gauge32,
    sslkLockTimeoutsPerSec Gauge32,
    sslkLockWaitTimeMs Gauge32,
    sslkLockWaitsPerSec Gauge32,
    sslkNumberOfDeadlocksPerSec Gauge32
}

sslkInstance OBJECT-TYPE
    SYNTAX     InstanceName
    MAX-ACCESS read-only
    STATUS     current
    DESCRIPTION
	    "Instance name."
    ::= { sqlServerLocksEntry 1 }

sslkAverageWaitTimeMs OBJECT-TYPE
    SYNTAX     Gauge32
    MAX-ACCESS read-only
    STATUS     current
    DESCRIPTION
	    "The average amount of wait time (milliseconds)
	    for each lock request that resulted in a wait."
    ::= { sqlServerLocksEntry 2 }

sslkLockRequestsPerSec OBJECT-TYPE
    SYNTAX     Gauge32
    MAX-ACCESS read-only
    STATUS     current
    DESCRIPTION
	    "Number of new locks and lock conversions
	    requested from the lock manager."
    ::= { sqlServerLocksEntry 3 }

sslkLockTimeoutsTimeoutGT0PerSec OBJECT-TYPE
    SYNTAX     Gauge32
    MAX-ACCESS read-only
    STATUS     current
    DESCRIPTION
	    "Number of lock requests that timed out. This
	    does not include requests for NOWAIT locks."
    ::= { sqlServerLocksEntry 4 }

sslkLockTimeoutsPerSec OBJECT-TYPE
    SYNTAX     Gauge32
    MAX-ACCESS read-only
    STATUS     current
    DESCRIPTION
	    "Number of lock requests that timed out. This
	    includes requests for NOWAIT locks."
    ::= { sqlServerLocksEntry 5 }

sslkLockWaitTimeMs OBJECT-TYPE
    SYNTAX     Gauge32
    MAX-ACCESS read-only
    STATUS     current
    DESCRIPTION
	    "Total wait time (milliseconds) for locks in
	    the last second."
    ::= { sqlServerLocksEntry 6 }

sslkLockWaitsPerSec OBJECT-TYPE
    SYNTAX     Gauge32
    MAX-ACCESS read-only
    STATUS     current
    DESCRIPTION
	    "Number of lock requests that could not be
	    satisfied immediately and required the caller
	    to wait before being granted the lock."
    ::= { sqlServerLocksEntry 7 }

sslkNumberOfDeadlocksPerSec OBJECT-TYPE
    SYNTAX     Gauge32
    MAX-ACCESS read-only
    STATUS     current
    DESCRIPTION
	    "Number of lock requests that resulted in a
	    deadlock."
    ::= { sqlServerLocksEntry 8 }

sqlServerMemoryManagerTable OBJECT-TYPE
    SYNTAX     SEQUENCE OF SqlServerMemoryManagerEntry
    MAX-ACCESS not-accessible
    STATUS     current
    DESCRIPTION
	    "The Memory Manager object in Microsoft SQL
	    Server provides counters to monitor overall
	    server memory usage. Monitoring overall server
	    memory usage to gauge user activity and
	    resource usage can help you to identify
	    performance bottlenecks. Monitoring the memory
	    used by an instance of SQL Server can help
	    determine: If bottlenecks exist due to a lack
	    of available physical memory for storing
	    frequently accessed data in cache. If so, SQL
	    Server must retrieve the data from disk; If
	    query performance can be improved by adding
	    more memory or by making more memory available
	    to the data cache or SQL Server internal
	    structures."
    ::= { sqlServer 32 }

sqlServerMemoryManagerEntry OBJECT-TYPE
    SYNTAX     SqlServerMemoryManagerEntry
    MAX-ACCESS not-accessible
    STATUS     current
    DESCRIPTION
	    "Performance information for one SQL Server
	    name instance."
    INDEX      { sqlServerNameIndex }
    ::= { sqlServerMemoryManagerTable 1 }

SqlServerMemoryManagerEntry ::= SEQUENCE {
    ssmmConnectionMemoryKB Gauge32,
    ssmmGrantedWorkspaceMemoryKB Gauge32,
    ssmmLockBlocks Gauge32,
    ssmmLockBlocksAllocated Gauge32,
    ssmmLockMemoryKB Gauge32,
    ssmmLockOwnerBlocks Gauge32,
    ssmmLockOwnerBlocksAllocated Gauge32,
    ssmmMaximumWorkspaceMemoryKB Gauge32,
    ssmmMemoryGrantsOutstanding Gauge32,
    ssmmMemoryGrantsPending Gauge32,
    ssmmOptimizerMemoryKB Gauge32,
    ssmmSQLCacheMemoryKB Gauge32,
    ssmmTargetServerMemoryKB Gauge32,
    ssmmTotalServerMemoryKB Gauge32
}

ssmmConnectionMemoryKB OBJECT-TYPE
    SYNTAX     Gauge32
    MAX-ACCESS read-only
    STATUS     current
    DESCRIPTION
	    "Total amount of dynamic memory the server is
	    using for maintaining connections"
    ::= { sqlServerMemoryManagerEntry 1 }

ssmmGrantedWorkspaceMemoryKB OBJECT-TYPE
    SYNTAX     Gauge32
    MAX-ACCESS read-only
    STATUS     current
    DESCRIPTION
	    "Total amount of memory granted to executing
	    processes. This memory is used for hash, sort
	    and create index operations."
    ::= { sqlServerMemoryManagerEntry 2 }

ssmmLockBlocks OBJECT-TYPE
    SYNTAX     Gauge32
    MAX-ACCESS read-only
    STATUS     current
    DESCRIPTION
	    "The current number of lock blocks that are in
	    use on the server. Refreshed periodically."
    ::= { sqlServerMemoryManagerEntry 3 }

ssmmLockBlocksAllocated OBJECT-TYPE
    SYNTAX     Gauge32
    MAX-ACCESS read-only
    STATUS     current
    DESCRIPTION
	    "The current number of allocated lock blocks."
    ::= { sqlServerMemoryManagerEntry 4 }

ssmmLockMemoryKB OBJECT-TYPE
    SYNTAX     Gauge32
    MAX-ACCESS read-only
    STATUS     current
    DESCRIPTION
	    "Total amount of dynamic memory the server is
	    using for locks"
    ::= { sqlServerMemoryManagerEntry 5 }

ssmmLockOwnerBlocks OBJECT-TYPE
    SYNTAX     Gauge32
    MAX-ACCESS read-only
    STATUS     current
    DESCRIPTION
	    "The number of lock owner blocks that are
	    currently in use on the server. Refreshed
	    periodically."
    ::= { sqlServerMemoryManagerEntry 6 }

ssmmLockOwnerBlocksAllocated OBJECT-TYPE
    SYNTAX     Gauge32
    MAX-ACCESS read-only
    STATUS     current
    DESCRIPTION
	    "The current number of allocated lock owner
	    blocks."
    ::= { sqlServerMemoryManagerEntry 7 }

ssmmMaximumWorkspaceMemoryKB OBJECT-TYPE
    SYNTAX     Gauge32
    MAX-ACCESS read-only
    STATUS     current
    DESCRIPTION
	    "Total amount of memory granted to executing
	    processes. This memory is used primarily for
	    hash, sort and create index operations."
    ::= { sqlServerMemoryManagerEntry 8 }

ssmmMemoryGrantsOutstanding OBJECT-TYPE
    SYNTAX     Gauge32
    MAX-ACCESS read-only
    STATUS     current
    DESCRIPTION
	    "Current number of processes that have
	    successfully acquired a workspace memory grant"
    ::= { sqlServerMemoryManagerEntry 9 }

ssmmMemoryGrantsPending OBJECT-TYPE
    SYNTAX     Gauge32
    MAX-ACCESS read-only
    STATUS     current
    DESCRIPTION
	    "Current number of processes waiting for a
	    workspace memory grant"
    ::= { sqlServerMemoryManagerEntry 10 }

ssmmOptimizerMemoryKB OBJECT-TYPE
    SYNTAX     Gauge32
    MAX-ACCESS read-only
    STATUS     current
    DESCRIPTION
	    "Total amount of dynamic memory the server is
	    using for query optimization"
    ::= { sqlServerMemoryManagerEntry 11 }

ssmmSQLCacheMemoryKB OBJECT-TYPE
    SYNTAX     Gauge32
    MAX-ACCESS read-only
    STATUS     current
    DESCRIPTION
	    "Total amount of dynamic memory the server is
	    using for the dynamic SQL cache"
    ::= { sqlServerMemoryManagerEntry 12 }

ssmmTargetServerMemoryKB OBJECT-TYPE
    SYNTAX     Gauge32
    MAX-ACCESS read-only
    STATUS     current
    DESCRIPTION
	    "Total amount of dynamic memory the server is
	    willing to consume"
    ::= { sqlServerMemoryManagerEntry 13 }

ssmmTotalServerMemoryKB OBJECT-TYPE
    SYNTAX     Gauge32
    MAX-ACCESS read-only
    STATUS     current
    DESCRIPTION
	    "Total amount of dynamic memory the server is
	    currently consuming"
    ::= { sqlServerMemoryManagerEntry 14 }

sqlServerReplicateLogreaderTable OBJECT-TYPE
    SYNTAX     SEQUENCE OF SQLServerReplicateLogreaderEntry
    MAX-ACCESS not-accessible
    STATUS     current
    DESCRIPTION
	    "The Replication Logreader object in Microsoft
	    SQL Server provides counters to monitor the Log
	    Reader Agent."
    ::= { sqlServer 33 }

sqlServerReplicateLogreaderEntry OBJECT-TYPE
    SYNTAX     SQLServerReplicateLogreaderEntry
    MAX-ACCESS not-accessible
    STATUS     current
    DESCRIPTION
	    "Performance information for one particular SQL
	    Server name instance of 'SQLServer:Replication
	    Logreader' object."
    INDEX      { sqlServerNameIndex, ssrlInstance }
    ::= { sqlServerReplicateLogreaderTable 1 }

SQLServerReplicateLogreaderEntry ::= SEQUENCE {
    ssrlInstance InstanceName,
    ssrlLogreaderDeliveredCmdsPerSec Gauge32,
    ssrlLogreaderDelivereTransPerSec Gauge32,
    ssrlLogreaderDeliveryLatency Gauge32
}

ssrlInstance OBJECT-TYPE
    SYNTAX     InstanceName
    MAX-ACCESS read-only
    STATUS     current
    DESCRIPTION
	    "Instance name."
    ::= { sqlServerReplicateLogreaderEntry 1 }

ssrlLogreaderDeliveredCmdsPerSec OBJECT-TYPE
    SYNTAX     Gauge32
    MAX-ACCESS read-only
    STATUS     current
    DESCRIPTION
	    "Number of Log Reader Agent commands delivered
	    per second to the Distributor."
    ::= { sqlServerReplicateLogreaderEntry 2 }

ssrlLogreaderDelivereTransPerSec OBJECT-TYPE
    SYNTAX     Gauge32
    MAX-ACCESS read-only
    STATUS     current
    DESCRIPTION
	    "Number of Log Reader Agent transactions
	    delivered per second to the Distributor."
    ::= { sqlServerReplicateLogreaderEntry 3 }

ssrlLogreaderDeliveryLatency OBJECT-TYPE
    SYNTAX     Gauge32
    MAX-ACCESS read-only
    STATUS     current
    DESCRIPTION
	    "Current amount of time, in milliseconds,
	    elapsed from when transactions are applied at
	    the Publisher to when they are delivered to the
	    Distributor."
    ::= { sqlServerReplicateLogreaderEntry 4 }

sqlServerReplicateSnapshotTable OBJECT-TYPE
    SYNTAX     SEQUENCE OF SQLServerReplicateSnapshotEntry
    MAX-ACCESS not-accessible
    STATUS     current
    DESCRIPTION
	    "The Replication Snapshot object in Microsoft
	    SQL Server provides counters to monitor SQL
	    Server snapshot replication."
    ::= { sqlServer 34 }

sqlServerReplicateSnapshotEntry OBJECT-TYPE
    SYNTAX     SQLServerReplicateSnapshotEntry
    MAX-ACCESS not-accessible
    STATUS     current
    DESCRIPTION
	    "Performance information for one particular SQL
	    Server name instance of 'SQLServer:Replication
	    Snapshot' object."
    INDEX      { sqlServerNameIndex, ssrsInstance }
    ::= { sqlServerReplicateSnapshotTable 1 }

SQLServerReplicateSnapshotEntry ::= SEQUENCE {
    ssrsInstance InstanceName,
    ssrsSnapshotDeliveredCmdsPerSec Gauge32,
    ssrsSnapshotDeliveredTransPerSec Gauge32
}

ssrsInstance OBJECT-TYPE
    SYNTAX     InstanceName
    MAX-ACCESS read-only
    STATUS     current
    DESCRIPTION
	    "Instance name."
    ::= { sqlServerReplicateSnapshotEntry 1 }

ssrsSnapshotDeliveredCmdsPerSec OBJECT-TYPE
    SYNTAX     Gauge32
    MAX-ACCESS read-only
    STATUS     current
    DESCRIPTION
	    "Number of commands delivered per second to the
	    Distributor."
    ::= { sqlServerReplicateSnapshotEntry 2 }

ssrsSnapshotDeliveredTransPerSec OBJECT-TYPE
    SYNTAX     Gauge32
    MAX-ACCESS read-only
    STATUS     current
    DESCRIPTION
	    "Number of transactions delivered per second to
	    the Distributor."
    ::= { sqlServerReplicateSnapshotEntry 3 }

sqlServerReplicationAgentsTable OBJECT-TYPE
    SYNTAX     SEQUENCE OF SQLServerReplicationAgentsEntry
    MAX-ACCESS not-accessible
    STATUS     current
    DESCRIPTION
	    "The Replication Agents object in Microsoft SQL
	    Server provides counters to monitor the SQL
	    Server replication agents that are running
	    currently. Monitoring the number of running
	    Distribution and Merge Agents is useful to
	    determine the number of Subscribers to which
	    published databases are replicating. Multiple
	    instances of the Replication Agents object can
	    be monitored at the same time, with each
	    instance representing a single replication
	    agent (for example, Log Reader; Snapshot;
	    Distribution; and Merge)."
    ::= { sqlServer 35 }

sqlServerReplicationAgentsEntry OBJECT-TYPE
    SYNTAX     SQLServerReplicationAgentsEntry
    MAX-ACCESS not-accessible
    STATUS     current
    DESCRIPTION
	    "Performance information for one particular SQL
	    Server name instance of 'SQLServer:Replication
	    Agents' object."
    INDEX      { sqlServerNameIndex, ssraInstance }
    ::= { sqlServerReplicationAgentsTable 1 }

SQLServerReplicationAgentsEntry ::= SEQUENCE {
    ssraInstance InstanceName,
    ssraRunning Gauge32
}

ssraInstance OBJECT-TYPE
    SYNTAX     InstanceName
    MAX-ACCESS read-only
    STATUS     current
    DESCRIPTION
	    "Instance name."
    ::= { sqlServerReplicationAgentsEntry 1 }

ssraRunning OBJECT-TYPE
    SYNTAX     Gauge32
    MAX-ACCESS read-only
    STATUS     current
    DESCRIPTION
	    "Number of instances of a given replication
	    agent running currently."
    ::= { sqlServerReplicationAgentsEntry 2 }

sqlServerReplicationDistTable OBJECT-TYPE
    SYNTAX     SEQUENCE OF SQLServerReplicationDistEntry
    MAX-ACCESS not-accessible
    STATUS     current
    DESCRIPTION
	    "The Replication Dist. object in Microsoft SQL
	    Server provides counters to monitor the number
	    of commands and transactions read from the
	    distribution database and delivered to the
	    subscriber databases by the SQL Server
	    Distribution Agent."
    ::= { sqlServer 36 }

sqlServerReplicationDistEntry OBJECT-TYPE
    SYNTAX     SQLServerReplicationDistEntry
    MAX-ACCESS not-accessible
    STATUS     current
    DESCRIPTION
	    "Performance information for one particular SQL
	    Server name instance of 'SQLServer:Replication
	    Dist.' object."
    INDEX      { sqlServerNameIndex, ssrdInstance }
    ::= { sqlServerReplicationDistTable 1 }

SQLServerReplicationDistEntry ::= SEQUENCE {
    ssrdInstance InstanceName,
    ssrdDistDeliveredCmdsPerSec Gauge32,
    ssrdDistDeliveredTransPerSec Gauge32,
    ssrdDistDeliveryLatency Gauge32
}

ssrdInstance OBJECT-TYPE
    SYNTAX     InstanceName
    MAX-ACCESS read-only
    STATUS     current
    DESCRIPTION
	    "Instance name."
    ::= { sqlServerReplicationDistEntry 1 }

ssrdDistDeliveredCmdsPerSec OBJECT-TYPE
    SYNTAX     Gauge32
    MAX-ACCESS read-only
    STATUS     current
    DESCRIPTION
	    "Number of distribution commands delivered per
	    second to the Subscriber."
    ::= { sqlServerReplicationDistEntry 2 }

ssrdDistDeliveredTransPerSec OBJECT-TYPE
    SYNTAX     Gauge32
    MAX-ACCESS read-only
    STATUS     current
    DESCRIPTION
	    "Number of distribution transactions delivered
	    per second to the Subscriber."
    ::= { sqlServerReplicationDistEntry 3 }

ssrdDistDeliveryLatency OBJECT-TYPE
    SYNTAX     Gauge32
    MAX-ACCESS read-only
    STATUS     current
    DESCRIPTION
	    "Distribution latency (in milliseconds). The
	    time it takes for transactions to be delivered
	    to the Distributor and applied at the
	    Subscriber."
    ::= { sqlServerReplicationDistEntry 4 }

sqlServerReplicationMergeTable OBJECT-TYPE
    SYNTAX     SEQUENCE OF SQLServerReplicationMergeEntry
    MAX-ACCESS not-accessible
    STATUS     current
    DESCRIPTION
	    "The Replication Merge object in Microsoft SQL
	    Server provides counters to monitor each SQL
	    Server merge execution that moves data changes
	    up from a merge replication Subscriber to the
	    Publisher, and down from the Publisher to the
	    Subscriber."
    ::= { sqlServer 37 }

sqlServerReplicationMergeEntry OBJECT-TYPE
    SYNTAX     SQLServerReplicationMergeEntry
    MAX-ACCESS not-accessible
    STATUS     current
    DESCRIPTION
	    "Performance information for one particular SQL
	    Server name instance of 'SQLServer:Replication
	    Merge' object."
    INDEX      { sqlServerNameIndex, ssrmInstance }
    ::= { sqlServerReplicationMergeTable 1 }

SQLServerReplicationMergeEntry ::= SEQUENCE {
    ssrmInstance InstanceName,
    ssrmConflictsPerSec Gauge32,
    ssrmDownloadedChangesPerSec Gauge32,
    ssrmUploadedChangesPerSec Gauge32
}

ssrmInstance OBJECT-TYPE
    SYNTAX     InstanceName
    MAX-ACCESS read-only
    STATUS     current
    DESCRIPTION
	    "Instance name."
    ::= { sqlServerReplicationMergeEntry 1 }

ssrmConflictsPerSec OBJECT-TYPE
    SYNTAX     Gauge32
    MAX-ACCESS read-only
    STATUS     current
    DESCRIPTION
	    "Number of conflicts per second that occurred
	    in the Publisher/Subscriber upload and
	    download. This value should always be zero. A
	    nonzero value may require notifying the losing
	    side, overriding the conflict, and so on."
    ::= { sqlServerReplicationMergeEntry 2 }

ssrmDownloadedChangesPerSec OBJECT-TYPE
    SYNTAX     Gauge32
    MAX-ACCESS read-only
    STATUS     current
    DESCRIPTION
	    "Number of rows per second merged (inserted,
	    updated, and deleted) from the Publisher to the
	    Subscriber."
    ::= { sqlServerReplicationMergeEntry 3 }

ssrmUploadedChangesPerSec OBJECT-TYPE
    SYNTAX     Gauge32
    MAX-ACCESS read-only
    STATUS     current
    DESCRIPTION
	    "Number of rows per second merged (inserted,
	    updated, and deleted) from the Subscriber to
	    the Publisher."
    ::= { sqlServerReplicationMergeEntry 4 }

sqlServerSQLErrorsTable OBJECT-TYPE
    SYNTAX     SEQUENCE OF SqlServerSQLErrorsEntry
    MAX-ACCESS not-accessible
    STATUS     current
    DESCRIPTION
	    "Statistics about errors in SQL Server"
    ::= { sqlServer 38 }

sqlServerSQLErrorsEntry OBJECT-TYPE
    SYNTAX     SqlServerSQLErrorsEntry
    MAX-ACCESS not-accessible
    STATUS     current
    DESCRIPTION
	    "Performance information for one particular SQL
	    Server name instance of 'SQL Errors' object."
    INDEX      { sqlServerNameIndex, sseInstance }
    ::= { sqlServerSQLErrorsTable 1 }

SqlServerSQLErrorsEntry ::= SEQUENCE {
    sseInstance InstanceName,
    sseErrorsPerSec Gauge32
}

sseInstance OBJECT-TYPE
    SYNTAX     InstanceName
    MAX-ACCESS read-only
    STATUS     current
    DESCRIPTION
	    "Instance name."
    ::= { sqlServerSQLErrorsEntry 1 }

sseErrorsPerSec OBJECT-TYPE
    SYNTAX     Gauge32
    MAX-ACCESS read-only
    STATUS     current
    DESCRIPTION
	    "Number of errors/sec"
    ::= { sqlServerSQLErrorsEntry 2 }

sqlServerSQLStatisticsTable OBJECT-TYPE
    SYNTAX     SEQUENCE OF SqlServerSQLStatisticsEntry
    MAX-ACCESS not-accessible
    STATUS     current
    DESCRIPTION
	    "The SQL Statistics object in Microsoft SQL
	    Server provides counters to monitor compilation
	    and the type of requests sent to an instance of
	    SQL Server. Monitoring the number of query
	    compilations and recompilations and the number
	    of batches received by an instance of SQL
	    Server gives you an indication of how quickly
	    SQL Server is processing user queries and how
	    effectively the query optimizer is processing
	    the queries. Compilation is a significant part
	    of a query's turnaround time. The objective of
	    the cache is to reduce compilation by storing
	    compiled queries for later reuse, thus
	    eliminating the need to recompile queries when
	    later executed. However, each unique query must
	    be compiled at least once. Query recompilations
	    can be caused by the following factors: Schema
	    changes, including base schema changes such as
	    adding columns or indexes to a table, or
	    statistics schema changes such as inserting or
	    deleting a significant number of rows from a
	    table; Environment (SET statement) changes.
	    Changes in session settings such as
	    ANSI_PADDING or ANSI_NULLS can cause a query to
	    be recompiled."
    ::= { sqlServer 39 }

sqlServerSQLStatisticsEntry OBJECT-TYPE
    SYNTAX     SqlServerSQLStatisticsEntry
    MAX-ACCESS not-accessible
    STATUS     current
    DESCRIPTION
	    "Performance information for one SQL Server
	    name instance."
    INDEX      { sqlServerNameIndex }
    ::= { sqlServerSQLStatisticsTable 1 }

SqlServerSQLStatisticsEntry ::= SEQUENCE {
    ssssAutoParamAttemptsPerSec Gauge32,
    ssssBatchRequestsPerSec Gauge32,
    ssssFailedAutoParamsPerSec Gauge32,
    ssssSQLAttentionRate Gauge32,
    ssssSQLCompilationsPerSec Gauge32,
    ssssSQLReCompilationsPerSec Gauge32,
    ssssSafeAutoParamsPerSec Gauge32,
    ssssUnsafeAutoParamsPerSec Gauge32
}

ssssAutoParamAttemptsPerSec OBJECT-TYPE
    SYNTAX     Gauge32
    MAX-ACCESS read-only
    STATUS     current
    DESCRIPTION
	    "Number of auto-parameterization attempts."
    ::= { sqlServerSQLStatisticsEntry 1 }

ssssBatchRequestsPerSec OBJECT-TYPE
    SYNTAX     Gauge32
    MAX-ACCESS read-only
    STATUS     current
    DESCRIPTION
	    "Number of SQL batch requests received by
	    server."
    ::= { sqlServerSQLStatisticsEntry 2 }

ssssFailedAutoParamsPerSec OBJECT-TYPE
    SYNTAX     Gauge32
    MAX-ACCESS read-only
    STATUS     current
    DESCRIPTION
	    "Number of failed auto-parameterizations."
    ::= { sqlServerSQLStatisticsEntry 3 }

ssssSQLAttentionRate OBJECT-TYPE
    SYNTAX     Gauge32
    MAX-ACCESS read-only
    STATUS     current
    DESCRIPTION
	    "Number of attentions per second."
    ::= { sqlServerSQLStatisticsEntry 4 }

ssssSQLCompilationsPerSec OBJECT-TYPE
    SYNTAX     Gauge32
    MAX-ACCESS read-only
    STATUS     current
    DESCRIPTION
	    "Number of SQL compilations."
    ::= { sqlServerSQLStatisticsEntry 5 }

ssssSQLReCompilationsPerSec OBJECT-TYPE
    SYNTAX     Gauge32
    MAX-ACCESS read-only
    STATUS     current
    DESCRIPTION
	    "Number of SQL re-compiles."
    ::= { sqlServerSQLStatisticsEntry 6 }

ssssSafeAutoParamsPerSec OBJECT-TYPE
    SYNTAX     Gauge32
    MAX-ACCESS read-only
    STATUS     current
    DESCRIPTION
	    "Number of safe auto-parameterizations."
    ::= { sqlServerSQLStatisticsEntry 7 }

ssssUnsafeAutoParamsPerSec OBJECT-TYPE
    SYNTAX     Gauge32
    MAX-ACCESS read-only
    STATUS     current
    DESCRIPTION
	    "Number of unsafe auto-parameterizations."
    ::= { sqlServerSQLStatisticsEntry 8 }

sqlServerTransactionsTable OBJECT-TYPE
    SYNTAX     SEQUENCE OF SqlServerTransactionsEntry
    MAX-ACCESS not-accessible
    STATUS     current
    DESCRIPTION
	    "Statistics related to SQL Server
	    transactions."
    ::= { sqlServer 40 }

sqlServerTransactionsEntry OBJECT-TYPE
    SYNTAX     SqlServerTransactionsEntry
    MAX-ACCESS not-accessible
    STATUS     current
    DESCRIPTION
	    "Performance information for one SQL Server
	    name instance."
    INDEX      { sqlServerNameIndex }
    ::= { sqlServerTransactionsTable 1 }

SqlServerTransactionsEntry ::= SEQUENCE {
    sstFreeSpaceInTempdbKB Gauge32,
    sstLongestTransactionRunningTime Gauge32,
    sstNonSnapshotVersionTransactions Gauge32,
    sstSnapshotTransactions Gauge32,
    sstTransactions Gauge32,
    sstUpdateSnapshotTransactions Gauge32,
    sstUpdateConflictRatio Gauge32,
    sstVersionCleanupRateKBPerS Gauge32,
    sstVersionGenerationRateKBPerS Gauge32,
    sstVersionStoreSizeKB Gauge32,
    sstVersionStoreUnitCount Gauge32,
    sstVersionStoreUnitCreation Gauge32,
    sstVersionStoreUnitTruncation Gauge32
}

sstFreeSpaceInTempdbKB OBJECT-TYPE
    SYNTAX     Gauge32
    MAX-ACCESS read-only
    STATUS     current
    DESCRIPTION
	    "The free space in tempdb in KB."
    ::= { sqlServerTransactionsEntry 1 }

sstLongestTransactionRunningTime OBJECT-TYPE
    SYNTAX     Gauge32
    MAX-ACCESS read-only
    STATUS     current
    DESCRIPTION
	    "The longest running time of any transcation in
	    seconds."
    ::= { sqlServerTransactionsEntry 2 }

sstNonSnapshotVersionTransactions OBJECT-TYPE
    SYNTAX     Gauge32
    MAX-ACCESS read-only
    STATUS     current
    DESCRIPTION
	    "The total number of active non-snapshot
	    transactions that generate version records."
    ::= { sqlServerTransactionsEntry 3 }

sstSnapshotTransactions OBJECT-TYPE
    SYNTAX     Gauge32
    MAX-ACCESS read-only
    STATUS     current
    DESCRIPTION
	    "The total number of active snapshot
	    transactions."
    ::= { sqlServerTransactionsEntry 4 }

sstTransactions OBJECT-TYPE
    SYNTAX     Gauge32
    MAX-ACCESS read-only
    STATUS     current
    DESCRIPTION
	    "Number of transaction enlistments (local, dtc,
	    bound all combined)."
    ::= { sqlServerTransactionsEntry 5 }

sstUpdateSnapshotTransactions OBJECT-TYPE
    SYNTAX     Gauge32
    MAX-ACCESS read-only
    STATUS     current
    DESCRIPTION
	    "The total number of active snapshot
	    transactions that do updates."
    ::= { sqlServerTransactionsEntry 6 }

sstUpdateConflictRatio OBJECT-TYPE
    SYNTAX     Gauge32
    MAX-ACCESS read-only
    STATUS     current
    DESCRIPTION
	    "The fraction of update snapshot transactions
	    that have update conflicts to the total number
	    of update snapshot transactions."
    ::= { sqlServerTransactionsEntry 7 }

sstVersionCleanupRateKBPerS OBJECT-TYPE
    SYNTAX     Gauge32
    MAX-ACCESS read-only
    STATUS     current
    DESCRIPTION
	    "The version cleanup rate in KB per seconds."
    ::= { sqlServerTransactionsEntry 8 }

sstVersionGenerationRateKBPerS OBJECT-TYPE
    SYNTAX     Gauge32
    MAX-ACCESS read-only
    STATUS     current
    DESCRIPTION
	    "The version generation rate in KB per
	    seconds."
    ::= { sqlServerTransactionsEntry 9 }

sstVersionStoreSizeKB OBJECT-TYPE
    SYNTAX     Gauge32
    MAX-ACCESS read-only
    STATUS     current
    DESCRIPTION
	    "The size of the version store in KB."
    ::= { sqlServerTransactionsEntry 10 }

sstVersionStoreUnitCount OBJECT-TYPE
    SYNTAX     Gauge32
    MAX-ACCESS read-only
    STATUS     current
    DESCRIPTION
	    "Number of unit in Version Store."
    ::= { sqlServerTransactionsEntry 11 }

sstVersionStoreUnitCreation OBJECT-TYPE
    SYNTAX     Gauge32
    MAX-ACCESS read-only
    STATUS     current
    DESCRIPTION
	    "Creation of new unit in Version Store."
    ::= { sqlServerTransactionsEntry 12 }

sstVersionStoreUnitTruncation OBJECT-TYPE
    SYNTAX     Gauge32
    MAX-ACCESS read-only
    STATUS     current
    DESCRIPTION
	    "Truncation of unit in Version Store."
    ::= { sqlServerTransactionsEntry 13 }

sqlServerUserSettableTable OBJECT-TYPE
    SYNTAX     SEQUENCE OF SQLServerUserSettableEntry
    MAX-ACCESS not-accessible
    STATUS     current
    DESCRIPTION
	    "The User Settable object in Microsoft SQL
	    Server allows you to create custom counter
	    instances. Use custom counter instances to
	    monitor aspects of the server not monitored by
	    existing counters, such as components unique to
	    your SQL Server database (for example, the
	    number of customer orders logged or the product
	    inventory). The SQL Server User Settable object
	    contains 10 instances of the query counter:
	    User counter 1 through User counter 10. These
	    counters map to the SQL Server stored
	    procedures sp_user_counter1 through
	    sp_user_counter10. As these stored procedures
	    are executed by user applications, the values
	    set by the stored procedures are displayed in
	    System Monitor (Performance Monitor in
	    Microsoft Windows NT 4.0). A counter can
	    monitor any single integer value (for example,
	    a stored procedure that counts how many orders
	    for a particular product have occurred in one
	    day). See MSDN on how to enable the counter."
    ::= { sqlServer 41 }

sqlServerUserSettableEntry OBJECT-TYPE
    SYNTAX     SQLServerUserSettableEntry
    MAX-ACCESS not-accessible
    STATUS     current
    DESCRIPTION
	    "Performance information for one particular SQL
	    Server name instance of 'SQLServer:User
	    Settable' object."
    INDEX      { sqlServerNameIndex, ssusInstance }
    ::= { sqlServerUserSettableTable 1 }

SQLServerUserSettableEntry ::= SEQUENCE {
    ssusInstance InstanceName,
    ssusQuery Gauge32
}

ssusInstance OBJECT-TYPE
    SYNTAX     InstanceName
    MAX-ACCESS read-only
    STATUS     current
    DESCRIPTION
	    "Instance name."
    ::= { sqlServerUserSettableEntry 1 }

ssusQuery OBJECT-TYPE
    SYNTAX     Gauge32
    MAX-ACCESS read-only
    STATUS     current
    DESCRIPTION
	    "As defined by the user."
    ::= { sqlServerUserSettableEntry 2 }

sqlServerWaitStatisticsTable OBJECT-TYPE
    SYNTAX     SEQUENCE OF SqlServerWaitStatisticsEntry
    MAX-ACCESS not-accessible
    STATUS     current
    DESCRIPTION
	    "Wait Statistics"
    ::= { sqlServer 42 }

sqlServerWaitStatisticsEntry OBJECT-TYPE
    SYNTAX     SqlServerWaitStatisticsEntry
    MAX-ACCESS not-accessible
    STATUS     current
    DESCRIPTION
	    "Performance information for one particular SQL
	    Server name instance of 'Wait Statistics'
	    object."
    INDEX      { sqlServerNameIndex, sswsInstance }
    ::= { sqlServerWaitStatisticsTable 1 }

SqlServerWaitStatisticsEntry ::= SEQUENCE {
    sswsInstance InstanceName,
    sswsLockWaits Gauge32,
    sswsLogBufferWaits Gauge32,
    sswsLogWriteWaits Gauge32,
    sswsMemoryGrantQueueWaits Gauge32,
    sswsNetworkIOWaits Gauge32,
    sswsNonPageLatchWaits Gauge32,
    sswsPageIOLatchWaits Gauge32,
    sswsPageLatchWaits Gauge32,
    sswsThreadSafeMemoryObjectsWaits Gauge32,
    sswsTransactionOwnershipWaits Gauge32,
    sswsWaitForTheWorker Gauge32,
    sswsWorkspaceSyncronizationWaits Gauge32
}

sswsInstance OBJECT-TYPE
    SYNTAX     InstanceName
    MAX-ACCESS read-only
    STATUS     current
    DESCRIPTION
	    "Instance name."
    ::= { sqlServerWaitStatisticsEntry 1 }

sswsLockWaits OBJECT-TYPE
    SYNTAX     Gauge32
    MAX-ACCESS read-only
    STATUS     current
    DESCRIPTION
	    "Statistics for processes waiting on a lock."
    ::= { sqlServerWaitStatisticsEntry 2 }

sswsLogBufferWaits OBJECT-TYPE
    SYNTAX     Gauge32
    MAX-ACCESS read-only
    STATUS     current
    DESCRIPTION
	    "Statistics for processes waiting for log
	    buffer to be available."
    ::= { sqlServerWaitStatisticsEntry 3 }

sswsLogWriteWaits OBJECT-TYPE
    SYNTAX     Gauge32
    MAX-ACCESS read-only
    STATUS     current
    DESCRIPTION
	    "Statistics for processes waiting for log
	    buffer to be written."
    ::= { sqlServerWaitStatisticsEntry 4 }

sswsMemoryGrantQueueWaits OBJECT-TYPE
    SYNTAX     Gauge32
    MAX-ACCESS read-only
    STATUS     current
    DESCRIPTION
	    "Statistics for processes waiting for memory
	    grant to become available."
    ::= { sqlServerWaitStatisticsEntry 5 }

sswsNetworkIOWaits OBJECT-TYPE
    SYNTAX     Gauge32
    MAX-ACCESS read-only
    STATUS     current
    DESCRIPTION
	    "Statistics relevant to wait on network IO."
    ::= { sqlServerWaitStatisticsEntry 6 }

sswsNonPageLatchWaits OBJECT-TYPE
    SYNTAX     Gauge32
    MAX-ACCESS read-only
    STATUS     current
    DESCRIPTION
	    "Statistics relevant to non-page latches."
    ::= { sqlServerWaitStatisticsEntry 7 }

sswsPageIOLatchWaits OBJECT-TYPE
    SYNTAX     Gauge32
    MAX-ACCESS read-only
    STATUS     current
    DESCRIPTION
	    "Statistics relevant to page IO latches."
    ::= { sqlServerWaitStatisticsEntry 8 }

sswsPageLatchWaits OBJECT-TYPE
    SYNTAX     Gauge32
    MAX-ACCESS read-only
    STATUS     current
    DESCRIPTION
	    "Statistics relevant to page latches."
    ::= { sqlServerWaitStatisticsEntry 9 }

sswsThreadSafeMemoryObjectsWaits OBJECT-TYPE
    SYNTAX     Gauge32
    MAX-ACCESS read-only
    STATUS     current
    DESCRIPTION
	    "Statistics for processes waiting on
	    thread-safe memory allocators."
    ::= { sqlServerWaitStatisticsEntry 10 }

sswsTransactionOwnershipWaits OBJECT-TYPE
    SYNTAX     Gauge32
    MAX-ACCESS read-only
    STATUS     current
    DESCRIPTION
	    "Statistics relevant to processes synchronizing
	    access to transaction."
    ::= { sqlServerWaitStatisticsEntry 11 }

sswsWaitForTheWorker OBJECT-TYPE
    SYNTAX     Gauge32
    MAX-ACCESS read-only
    STATUS     current
    DESCRIPTION
	    "Statistics relevant to processes waiting for
	    worker to become available."
    ::= { sqlServerWaitStatisticsEntry 12 }

sswsWorkspaceSyncronizationWaits OBJECT-TYPE
    SYNTAX     Gauge32
    MAX-ACCESS read-only
    STATUS     current
    DESCRIPTION
	    "Statistics relevant to processes synchronizing
	    access to workspace."
    ::= { sqlServerWaitStatisticsEntry 13 }

END
