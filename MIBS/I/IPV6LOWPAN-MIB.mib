-- extracted from draft-daniel-lowpan-mib-00.txt
-- at Thu Mar  1 06:08:22 2007

IPV6LOWPAN-MIB    DEFINITIONS ::= BEGIN
    IMPORTS
        TruthValue
            FROM SNMPv2-TC
        OBJECT-GROUP, MODULE-COMPLIANCE
            FROM SNMPv2-CONF
        MODULE-IDENTITY, OBJECT-TYPE, Unsigned32, mib-2
            FROM SNMPv2-SMI
        LowpanIEEEEUI64Address, LowpanShortAddress
            FROM LOWPAN-TC-MIB;

    lowpanMIB    MODULE-IDENTITY
        LAST-UPDATED    "200701231307Z"
        ORGANIZATION    "IETF 6lowpan Working Group"
        CONTACT-INFO    "Ki-Hyung Kim, Editor
                        Ajou University
                        San 5 Wonchun-dong, Yeongtong-gu
                        Suwon-si, Gyeonggi-do  442-749
                        KOREA

                        Phone: +82 31 219 2433
                        Email: kkim86@ajou.ac.kr


                        Seung Wha Yoo
                        Ajou University
                        San 5 Wonchun-dong, Yeongtong-gu
                        Suwon-si, Gyeonggi-do  442-749
                        KOREA

                        Phone: +82 31 219 1603
                        Email: swyoo@ajou.ac.kr


                        Hamid Mukhtar
                        Ajou University
                        San 5 Wonchun-dong, Yeongtong-gu
                        Suwon-si, Gyeonggi-do  442-749
                        KOREA

                        Phone: +82 10 2892 2469
                        Email: hamid@ajou.ac.kr


                        Soohong Daniel Park, Editor
                        Mobile Platform Laboratory, SAMSUNG Electronics
                        416 Maetan-3dong, Yeongtong-gu
                        Suwon-si, Gyeonggi-do  442-742
                        KOREA

                        Phone: +82 31 200 4508
                        Email: soohong.park@samsung.com

                        Support Group E-mail: 6lowpan@ietf.org"

        DESCRIPTION     "The MIB module for monitoring 6lowpan
                        entities.

                        Copyright (C) The Internet Society 2007.  This
                        version of this MIB module is part of RFC XXXX;
                        see the RFC itself for full legal notices."
      -- RFC Ed.: replace XXXX with actual RFC number & remove this note

        REVISION        "200701231307Z"
        DESCRIPTION        "Initial version, published as RFC XXXX."
    -- RFC Ed.: replace XXXX with actual RFC number & remove this note

        ::=  {  mib-2  1  } -- will be assigned by IANA

      -- IANA Reg.: Please assign a value for "YYY" under the 'mib-2'
      -- subtree and record the assignment in the SMI Numbers registry.

      -- RFC Ed.: When the above assignment has been made, please
      --     remove the above note
      --     replace "YYY" here with the assigned value and
      --     remove this note.

       -- The major groups

       lowpanNotifications        OBJECT IDENTIFIER ::= { lowpanMIB 0 }
       lowpanObjects              OBJECT IDENTIFIER ::= { lowpanMIB 1 }
       lowpanConformance          OBJECT IDENTIFIER ::= { lowpanMIB 2 }

    lowpanDeviceRole    OBJECT-TYPE
        SYNTAX            INTEGER  { coordinator ( 0 ) , router ( 1 ) ,
                        endDevice ( 2 ) }
        MAX-ACCESS        read-only
        STATUS            current
        DESCRIPTION     "The device in 6lowpan can play three roles.
                        coordinator(0) indicates that the device is a
                        PAN Coordinator which is the primary controller
                        of the PAN. Its a full-function device (FFD).
                        It MAY initiate the synchronization of the
                        entire 6LoWPAN by transmitting beacons.
                        router(1)  a FFD which has the capability of
                        routing packets to the next hop device in
                        6LoWPAN.
                        endDevice(2) RFD (Reduced function device) or
                        FFD in a 6LoWPAN, which is neither the
                        coordinator nor a router."
        ::=  {  lowpanObjects  1  }

    lowpanDeviceCapabilities     OBJECT-TYPE
        SYNTAX            BITS  { alternatePANcoordinator ( 0 ) ,
                        deviceType ( 1 ) , powerSource ( 2 ) ,
                        recieverOnWhenIdle ( 3 ) , securityCapability
                        ( 6 ) , allocateAddress ( 7 ) }
        MAX-ACCESS        read-only
        STATUS            current
        DESCRIPTION     "alternatePANcoordinator(0)- The alternate PAN
                        coordinator subfield shall be set to 1 if the
                        device is capable of becoming a PAN
                        coordinator. Otherwise, the alternate PAN
                        coordinator subfield shall be set to 0.

                        deviceType(1) -The device type subfield shall
                        be set to 1 if the device is an FFD.
                        Otherwise, the device type subfield shall be
                        set to 0 to indicate an RFD.

                        powerSource(2)- The power source subfield
                        shall be set to 1 if the device is receiving
                        power from the alternating current mains.
                        Otherwise, the power source subfield shall
                        be set to 0.

                        recieverOnWhenIdle(3) - The receiver on when
                        idle shall be set to 1 if the device does not
                        disable its receiver to conserve power
                        during idle periods. Otherwise, the receiver
                        on when idle subfield shall be set to 0.
                        securityCapability(6)- The security capability
                        subfield shall be set to 1 if the device is
                        capable of sending and receiving MAC frames
                        secured using the security suite. Otherwise
                        the security capability subfield shall be
                        set to 0.

                        allocateAddress(7)- The allocate address
                        subfield shall be set to 1 if the device
                        wishes the coordinator to allocate a short
                        address as a result of the association
                        procedure. If this subfield is set to 0, the
                        special short address of 0 x fffe shall be
                        allocated to the device and returned through
                        the association response command. In this
                        case, the device shall communicate on the
                        PAN using only its 64 bit extended address.

                        BITS 4-5 are reserved."
        REFERENCE       "IEEE Std 802.15.4 specifications section
                        7.3.1.1.2"
        ::=  {  lowpanObjects  2  }


    lowpanRoutingTable  OBJECT-TYPE
        SYNTAX          SEQUENCE  OF  LowpanRoutingEntry
        MAX-ACCESS      not-accessible
        STATUS          current
        DESCRIPTION     "The routing table entries of a device."
        ::=  { lowpanObjects  3 }

    lowpanRoutingEntry  OBJECT-TYPE
        SYNTAX          LowpanRoutingEntry
        MAX-ACCESS      not-accessible
        STATUS          current
        DESCRIPTION     "This entry represents a conceptual row in the
                        routing table.  It represents a single routing
                        entry."
        INDEX        {  lowpanRouteDestAddress  }
        ::=  { lowpanRoutingTable 1 }

    LowpanRoutingEntry  ::=  SEQUENCE {
        lowpanRouteDestAddress  LowpanShortAddress,
        lowpanRouteNextHopAddress  LowpanShortAddress,
        lowpanRouteProtocol  INTEGER
        }

    lowpanRouteDestAddress    OBJECT-TYPE
        SYNTAX          LowpanShortAddress
        MAX-ACCESS      not-accessible
        STATUS          current
        DESCRIPTION     "The 16-bit short address of destination of this
                        route."
        ::=  {  lowpanRoutingEntry  1  }


    lowpanRouteNextHopAddress    OBJECT-TYPE
        SYNTAX          LowpanShortAddress
        MAX-ACCESS      read-only
        STATUS          current
        DESCRIPTION     "The short address of the next hop which leads
                        to the destination."
        ::=  {  lowpanRoutingEntry  2  }


    lowpanRouteProtocol    OBJECT-TYPE
        SYNTAX            INTEGER  { other ( 0 ), dymoLow ( 1 ), hiLow
                        ( 2 ) , load ( 3 ) }
        MAX-ACCESS      read-only
        STATUS          current
        DESCRIPTION     "6lowpan currently supports three routing
                        protocols
                        dymoLow(1) - Dynamic MANET On-demand routing
                        for 6LoWPAN
                        hiLow(2) - Hierarchical Routing over 6LoWPAN
                        load(3) -Ad Hoc On-Demand Distance Vector
                        Routing for 6lowpan"
        REFERENCE       "IETF 6lowpan WG
                        draft-daniel-6lowpan-load-adhoc-routing
                        (Work in progress), IETF 6lowpan WG
                        draft-montenegro-6lowpan-dymo-low-routing
                        (Work in progress), IETF 6lowpan WG
                        draft-daniel-6lowpan-hilow-hierarchical-routing
                        (Work in progress)"
        ::=  {  lowpanRoutingEntry  3  }

    lowpanNeighborTable   OBJECT-TYPE
        SYNTAX            SEQUENCE  OF  LowpanNeighborEntry
        MAX-ACCESS        not-accessible
        STATUS            current
        DESCRIPTION       "The neighbor table entries of a device"
        ::=  { lowpanObjects  4 }

    lowpanNeighborEntry   OBJECT-TYPE
        SYNTAX            LowpanNeighborEntry
        MAX-ACCESS        not-accessible
        STATUS            current
        DESCRIPTION       "This entry represents a conceptual row in the
                          neighbor table.  It represents a single
                          neighbor table entry."
        INDEX        {  lowpanNeighborEUI64Address  }
        ::=  { lowpanNeighborTable 1 }

    LowpanNeighborEntry  ::=  SEQUENCE {
        lowpanNeighborPanID  Unsigned32,
        lowpanNeighborEUI64Address  LowpanIEEEEUI64Address,
        lowpanNeighborShortAddress  LowpanShortAddress,
        lowpanNeighborDeviceType  INTEGER,
        lowpanNeighborIsParent  TruthValue
        }

    lowpanNeighborPanID    OBJECT-TYPE
        SYNTAX            Unsigned32 (0..65536)
        MAX-ACCESS        read-only
        STATUS            current
        DESCRIPTION        "The Personal area network Identifier
                           (PanID) of the neighbor entry."
        ::=  {  lowpanNeighborEntry  1  }


    lowpanNeighborEUI64Address    OBJECT-TYPE
        SYNTAX            LowpanIEEEEUI64Address
        MAX-ACCESS        not-accessible
        STATUS            current
        DESCRIPTION       "The EUI64 bit address of the neighbor entry."
        ::=  {  lowpanNeighborEntry  2  }


    lowpanNeighborShortAddress    OBJECT-TYPE
        SYNTAX            LowpanShortAddress
        MAX-ACCESS        read-only
        STATUS            current
        DESCRIPTION    "The 16-bit short address of the neighbor entry."
        ::=  {  lowpanNeighborEntry  3  }


    lowpanNeighborDeviceType    OBJECT-TYPE
        SYNTAX            INTEGER  { coordinator ( 0 ) , router ( 1 ) ,
                          endDevice ( 2 )}
        MAX-ACCESS        read-only
        STATUS            current
        DESCRIPTION        "The device type of the neighbor entry."
        ::=  {  lowpanNeighborEntry  4  }

    lowpanNeighborIsParent    OBJECT-TYPE
        SYNTAX            TruthValue
        MAX-ACCESS        read-only
        STATUS            current
        DESCRIPTION        "The value 'true(1)' indicates that the
                           neighbor is a topological parent of the
                           device."
        ::=  {  lowpanNeighborEntry  5  }


    lowpanUseHierarchicalRouting    OBJECT-TYPE
        SYNTAX            TruthValue
        MAX-ACCESS        read-only
        STATUS            current
        DESCRIPTION       "The value 'true(1)' indicates that the
                          entity uses tree based routing. 'false(2)'
                          indicates that entity is not using
                          tree based routing."
        ::=  {  lowpanObjects  5  }

    lowpanBroadcastSequenceNumber    OBJECT-TYPE
        SYNTAX            Unsigned32 (0..65536)
        MAX-ACCESS        read-only
        STATUS            current
        DESCRIPTION       "The last value of the sequence number
                          that was added to the 6lowpan broadcast or
                          multicast frame."
        REFERENCE         "Section 11 draft-ietf-6lowpan-format (work in
                          progress)"
        ::=  {  lowpanObjects  6  }

    lowpanAckTimeout    OBJECT-TYPE
        SYNTAX            Unsigned32
        UNITS             "milli-seconds"
        MAX-ACCESS        read-write
        STATUS            current
        DESCRIPTION       "The maximum time allowed for retransmission
                           of a broadcast message"
        ::=  {  lowpanObjects  7  }

    lowpanBroadcastRetries    OBJECT-TYPE
        SYNTAX            Unsigned32
        MAX-ACCESS        read-write
        STATUS            current
        DESCRIPTION       "The maximum number of retries allowed for a
                          broadcast message."
        ::=  {  lowpanObjects  8  }

       -- Conformance information
      lowpanGroups      OBJECT IDENTIFIER ::= { lowpanConformance 1 }
      lowpanCompliances OBJECT IDENTIFIER ::= { lowpanConformance 2 }

    lowpanGeneralGroup    OBJECT-GROUP
        OBJECTS         { lowpanDeviceCapabilities , lowpanDeviceRole,
                        lowpanUseHierarchicalRouting,
                        lowpanAckTimeout, lowpanBroadcastRetries,
                        lowpanBroadcastSequenceNumber,
                        lowpanNeighborDeviceType,
                        lowpanNeighborPanID,
                        lowpanNeighborIsParent,
                        lowpanNeighborShortAddress,
                        lowpanRouteNextHopAddress,
                        lowpanRouteProtocol }
        STATUS          current
        DESCRIPTION     "A collection of objects for basic 6lowpan
                        monitoring"
        ::=  {  lowpanGroups  1  }

    lowpanCoreCompliance    MODULE-COMPLIANCE
        STATUS            current
        DESCRIPTION
                        "The compliance statement for SNMP entities
                        which implement the LOWPAN-MIB."
        MODULE  -- this module
               MANDATORY-GROUPS { lowpanGeneralGroup }

        ::=  {  lowpanCompliances  1  }

     lowpanCoreReadOnlyCompliance MODULE-COMPLIANCE
           STATUS  current
           DESCRIPTION
                  "The compliance statement for SNMP entities
                   which implement the LOWPAN-MIB without support
                   for read-write (i.e. in read-only mode) .
                  "
           MODULE  -- this module
               MANDATORY-GROUPS { lowpanGeneralGroup }

           OBJECT      lowpanAckTimeout
           MIN-ACCESS  read-only
           DESCRIPTION
                  "Write access is not required."

                   OBJECT      lowpanBroadcastRetries
           MIN-ACCESS  read-only
           DESCRIPTION
                  "Write access is not required."

           ::= { lowpanCompliances  2 }



END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
