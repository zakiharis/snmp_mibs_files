INFORMANT-WMI-CITRIX DEFINITIONS ::= BEGIN

IMPORTS
    MODULE-IDENTITY, OBJECT-IDENTITY, OBJECT-TYPE, Gauge32, Integer32, Counter64
        FROM SNMPv2-SMI
    DateAndTime, TruthValue, DisplayString
        FROM SNMPv2-TC
    informant
        FROM WTCS;

citrixWmi MODULE-IDENTITY
    LAST-UPDATED "200806021714Z"
    ORGANIZATION "Informant Systems, Inc."
    CONTACT-INFO
            "Garth Williams
             11135-23A Ave
             Edmonton, AB  T6J4W5  Canada
             Tel: +1 780 434 4113
             E-mail: garth.williams.org"
    DESCRIPTION
            "The MIB module for informant Citrix WMI
            entities."
    REVISION      "200806021714Z"
    DESCRIPTION
            "The initial revision of this MIB module."
    ::= { informant 42 }

citrixWmiCitrix OBJECT-IDENTITY
    STATUS     current
    DESCRIPTION
        "Provides WMI information on the Citrix Application Services"
    ::= { citrixWmi 1 }

citrixAccountAuthorityTable OBJECT-TYPE
    SYNTAX     SEQUENCE OF CitrixAccountAuthority
    MAX-ACCESS not-accessible
    STATUS     current
    DESCRIPTION
        "The user authentication entities, typically NT Domains.Enumerate
        this class to get all Acc Authorities in current farm"
    ::= { citrixWmiCitrix 1 }

citrixAccountAuthorityEntry OBJECT-TYPE
    SYNTAX     CitrixAccountAuthority
    MAX-ACCESS not-accessible
    STATUS     current
    DESCRIPTION
        "None"
    INDEX      { ctxAccountAuthorityIndex }
    ::= { citrixAccountAuthorityTable 1 }

CitrixAccountAuthority ::= SEQUENCE {
    ctxAccountAuthorityIndex Integer32,
    ctxAccountAuthorityName DisplayString,
    ctxAccountAuthorityType INTEGER
}

ctxAccountAuthorityIndex OBJECT-TYPE
    SYNTAX     Integer32 (1..2147483647)
    MAX-ACCESS read-only
    STATUS     current
    DESCRIPTION
        "The value of this object uniquely identifies the instance entry
        for this class."
    ::= { citrixAccountAuthorityEntry 1 }

ctxAccountAuthorityName OBJECT-TYPE
    SYNTAX     DisplayString
    MAX-ACCESS read-only
    STATUS     current
    DESCRIPTION
        "The account authority name.
        For Windows NT domain and ADS users, the account authority name is
        the domain name. For NDS, this is the NDS tree name."
    ::= { citrixAccountAuthorityEntry 2 }

ctxAccountAuthorityType OBJECT-TYPE
    SYNTAX     INTEGER {
        unknownAccountAuthority(0),
        windowsNTDomainOrADS(1)
    }
    MAX-ACCESS read-only
    STATUS     current
    DESCRIPTION
        "The account authority type."
    ::= { citrixAccountAuthorityEntry 3 }

citrixApplicationFolderTable OBJECT-TYPE
    SYNTAX     SEQUENCE OF CitrixApplicationFolder
    MAX-ACCESS not-accessible
    STATUS     current
    DESCRIPTION
        "Applications can be organised by folder for
        Administrative convenience"
    ::= { citrixWmiCitrix 2 }

citrixApplicationFolderEntry OBJECT-TYPE
    SYNTAX     CitrixApplicationFolder
    MAX-ACCESS not-accessible
    STATUS     current
    DESCRIPTION
        "None"
    INDEX      { ctxApplicationFolderIndex }
    ::= { citrixApplicationFolderTable 1 }

CitrixApplicationFolder ::= SEQUENCE {
    ctxApplicationFolderIndex Integer32,
    ctxApplicationFolderFolderDN DisplayString,
    ctxApplicationFolderFolderName DisplayString
}

ctxApplicationFolderIndex OBJECT-TYPE
    SYNTAX     Integer32 (1..2147483647)
    MAX-ACCESS read-only
    STATUS     current
    DESCRIPTION
        "The value of this object uniquely identifies the
        instance entry for this class."
    ::= { citrixApplicationFolderEntry 1 }

ctxApplicationFolderFolderDN OBJECT-TYPE
    SYNTAX     DisplayString
    MAX-ACCESS read-only
    STATUS     current
    DESCRIPTION
        "Get the folder?s distinguished name."
    ::= { citrixApplicationFolderEntry 2 }

ctxApplicationFolderFolderName OBJECT-TYPE
    SYNTAX     DisplayString
    MAX-ACCESS read-only
    STATUS     current
    DESCRIPTION
        "Get the name of the folder object."
    ::= { citrixApplicationFolderEntry 3 }

citrixGroupTable OBJECT-TYPE
    SYNTAX     SEQUENCE OF CitrixGroup
    MAX-ACCESS not-accessible
    STATUS     current
    DESCRIPTION
        "Equivalent data but deliberately kept separate
        from CIMv2 alternatives for simplicity & to avoid
        cross namespace searches. See CIMv2:Win32_Group for
        full OS settings"
    ::= { citrixWmiCitrix 3 }

citrixGroupEntry OBJECT-TYPE
    SYNTAX     CitrixGroup
    MAX-ACCESS not-accessible
    STATUS     current
    DESCRIPTION
        "None"
    INDEX      { ctxGroupIndex }
    ::= { citrixGroupTable 1 }

CitrixGroup ::= SEQUENCE {
    ctxGroupIndex Integer32,
    ctxGroupAccAuthority DisplayString,
    ctxGroupAccountType INTEGER,
    ctxGroupGroupName DisplayString
}

ctxGroupIndex OBJECT-TYPE
    SYNTAX     Integer32 (1..2147483647)
    MAX-ACCESS read-only
    STATUS     current
    DESCRIPTION
        "The value of this object uniquely identifies the
        instance entry for this class."
    ::= { citrixGroupEntry 1 }

ctxGroupAccAuthority OBJECT-TYPE
    SYNTAX     DisplayString
    MAX-ACCESS read-only
    STATUS     current
    DESCRIPTION
        "Authority in which this group exists"
    ::= { citrixGroupEntry 2 }

ctxGroupAccountType OBJECT-TYPE
    SYNTAX     INTEGER {
        unknownAccountType(0),
        localGroup(1),
        globalGroup(2),
        universalGroup(3),
        domainLocalGroup(4)
    }
    MAX-ACCESS read-only
    STATUS     current
    DESCRIPTION
        "The account authority type."
    ::= { citrixGroupEntry 3 }

ctxGroupGroupName OBJECT-TYPE
    SYNTAX     DisplayString
    MAX-ACCESS read-only
    STATUS     current
    DESCRIPTION
        "Get the group name."
    ::= { citrixGroupEntry 4 }

citrixServerFolderTable OBJECT-TYPE
    SYNTAX     SEQUENCE OF CitrixServerFolder
    MAX-ACCESS not-accessible
    STATUS     current
    DESCRIPTION
        "Servers can be grouped by Folder for
        administrative convenience"
    ::= { citrixWmiCitrix 4 }

citrixServerFolderEntry OBJECT-TYPE
    SYNTAX     CitrixServerFolder
    MAX-ACCESS not-accessible
    STATUS     current
    DESCRIPTION
        "None"
    INDEX      { ctxServerFolderIndex }
    ::= { citrixServerFolderTable 1 }

CitrixServerFolder ::= SEQUENCE {
    ctxServerFolderIndex Integer32,
    ctxServerFolderFolderDN DisplayString,
    ctxServerFolderFolderName DisplayString
}

ctxServerFolderIndex OBJECT-TYPE
    SYNTAX     Integer32 (1..2147483647)
    MAX-ACCESS read-only
    STATUS     current
    DESCRIPTION
        "The value of this object uniquely identifies the
        instance entry for this class."
    ::= { citrixServerFolderEntry 1 }

ctxServerFolderFolderDN OBJECT-TYPE
    SYNTAX     DisplayString
    MAX-ACCESS read-only
    STATUS     current
    DESCRIPTION
        "Get the folder?s distinguished name."
    ::= { citrixServerFolderEntry 2 }

ctxServerFolderFolderName OBJECT-TYPE
    SYNTAX     DisplayString
    MAX-ACCESS read-only
    STATUS     current
    DESCRIPTION
        "Get the name of the folder object."
    ::= { citrixServerFolderEntry 3 }

citrixServersInFolderTable OBJECT-TYPE
    SYNTAX     SEQUENCE OF CitrixServersInFolder
    MAX-ACCESS not-accessible
    STATUS     current
    DESCRIPTION
        "Enumeration gives all Servers currently organised
        into a particular folder"
    ::= { citrixWmiCitrix 5 }

citrixServersInFolderEntry OBJECT-TYPE
    SYNTAX     CitrixServersInFolder
    MAX-ACCESS not-accessible
    STATUS     current
    DESCRIPTION
        "None"
    INDEX      { ctxServersInFolderIndex }
    ::= { citrixServersInFolderTable 1 }

CitrixServersInFolder ::= SEQUENCE {
    ctxServersInFolderIndex Integer32,
    ctxServersInFolderAntecedent DisplayString,
    ctxServersInFolderDependent DisplayString
}

ctxServersInFolderIndex OBJECT-TYPE
    SYNTAX     Integer32 (1..2147483647)
    MAX-ACCESS read-only
    STATUS     current
    DESCRIPTION
        "The value of this object uniquely identifies the
        instance entry for this class."
    ::= { citrixServersInFolderEntry 1 }

ctxServersInFolderAntecedent OBJECT-TYPE
    SYNTAX     DisplayString
    MAX-ACCESS read-only
    STATUS     current
    DESCRIPTION
        "Get the folder?s distinguished name."
    ::= { citrixServersInFolderEntry 2 }

ctxServersInFolderDependent OBJECT-TYPE
    SYNTAX     DisplayString
    MAX-ACCESS read-only
    STATUS     current
    DESCRIPTION
        "The name of the server"
    ::= { citrixServersInFolderEntry 3 }

citrixServersInZoneTable OBJECT-TYPE
    SYNTAX     SEQUENCE OF CitrixServersInZone
    MAX-ACCESS not-accessible
    STATUS     current
    DESCRIPTION
        "Servers collected in a Zone"
    ::= { citrixWmiCitrix 6 }

citrixServersInZoneEntry OBJECT-TYPE
    SYNTAX     CitrixServersInZone
    MAX-ACCESS not-accessible
    STATUS     current
    DESCRIPTION
        "None"
    INDEX      { ctxServersInZoneIndex }
    ::= { citrixServersInZoneTable 1 }

CitrixServersInZone ::= SEQUENCE {
    ctxServersInZoneIndex Integer32,
    ctxServersInZoneServer DisplayString,
    ctxServersInZoneZone DisplayString
}

ctxServersInZoneIndex OBJECT-TYPE
    SYNTAX     Integer32 (1..2147483647)
    MAX-ACCESS read-only
    STATUS     current
    DESCRIPTION
        "The value of this object uniquely identifies the
        instance entry for this class."
    ::= { citrixServersInZoneEntry 1 }

ctxServersInZoneServer OBJECT-TYPE
    SYNTAX     DisplayString
    MAX-ACCESS read-only
    STATUS     current
    DESCRIPTION
        "The name of the server"
    ::= { citrixServersInZoneEntry 2 }

ctxServersInZoneZone OBJECT-TYPE
    SYNTAX     DisplayString
    MAX-ACCESS read-only
    STATUS     current
    DESCRIPTION
        "Zone in which this server operates"
    ::= { citrixServersInZoneEntry 3 }

citrixUserTable OBJECT-TYPE
    SYNTAX     SEQUENCE OF CitrixUser
    MAX-ACCESS not-accessible
    STATUS     current
    DESCRIPTION
        "Equivalent data but deliberately kept separate
        from CIMv2 alternatives for simplicity & to avoid
        cross namespace searches. See CIMv2:Win32_Account
        for full OS settings"
    ::= { citrixWmiCitrix 7 }

citrixUserEntry OBJECT-TYPE
    SYNTAX     CitrixUser
    MAX-ACCESS not-accessible
    STATUS     current
    DESCRIPTION
        "None"
    INDEX      { ctxUserIndex }
    ::= { citrixUserTable 1 }

CitrixUser ::= SEQUENCE {
    ctxUserIndex Integer32,
    ctxUserAccAuthority DisplayString,
    ctxUserAccountType INTEGER,
    ctxUserUserName DisplayString
}

ctxUserIndex OBJECT-TYPE
    SYNTAX     Integer32 (1..2147483647)
    MAX-ACCESS read-only
    STATUS     current
    DESCRIPTION
        "The value of this object uniquely identifies the
        instance entry for this class."
    ::= { citrixUserEntry 1 }

ctxUserAccAuthority OBJECT-TYPE
    SYNTAX     DisplayString
    MAX-ACCESS read-only
    STATUS     current
    DESCRIPTION
        "Authority in which this user exists"
    ::= { citrixUserEntry 2 }

ctxUserAccountType OBJECT-TYPE
    SYNTAX     INTEGER {
        unknownAccountType(0),
        localUser(1),
        domainUser(2)
    }
    MAX-ACCESS read-only
    STATUS     current
    DESCRIPTION
        "The account type"
    ::= { citrixUserEntry 3 }

ctxUserUserName OBJECT-TYPE
    SYNTAX     DisplayString
    MAX-ACCESS read-only
    STATUS     current
    DESCRIPTION
        "The user name"
    ::= { citrixUserEntry 4 }

citrixUsersInGroupTable OBJECT-TYPE
    SYNTAX     SEQUENCE OF CitrixUsersInGroup
    MAX-ACCESS not-accessible
    STATUS     current
    DESCRIPTION
        "No GroupsForUser at the moment unless performance
        reasons require it"
    ::= { citrixWmiCitrix 8 }

citrixUsersInGroupEntry OBJECT-TYPE
    SYNTAX     CitrixUsersInGroup
    MAX-ACCESS not-accessible
    STATUS     current
    DESCRIPTION
        "None"
    INDEX      { ctxUsersInGroupIndex }
    ::= { citrixUsersInGroupTable 1 }

CitrixUsersInGroup ::= SEQUENCE {
    ctxUsersInGroupIndex Integer32,
    ctxUsersInGroupAntecedent DisplayString,
    ctxUsersInGroupDependent DisplayString
}

ctxUsersInGroupIndex OBJECT-TYPE
    SYNTAX     Integer32 (1..2147483647)
    MAX-ACCESS read-only
    STATUS     current
    DESCRIPTION
        "The value of this object uniquely identifies the
        instance entry for this class."
    ::= { citrixUsersInGroupEntry 1 }

ctxUsersInGroupAntecedent OBJECT-TYPE
    SYNTAX     DisplayString
    MAX-ACCESS read-only
    STATUS     current
    DESCRIPTION
        "Get the group name."
    ::= { citrixUsersInGroupEntry 2 }

ctxUsersInGroupDependent OBJECT-TYPE
    SYNTAX     DisplayString
    MAX-ACCESS read-only
    STATUS     current
    DESCRIPTION
        "Get the user name"
    ::= { citrixUsersInGroupEntry 3 }

citrixZoneTable OBJECT-TYPE
    SYNTAX     SEQUENCE OF CitrixZone
    MAX-ACCESS not-accessible
    STATUS     current
    DESCRIPTION
        "Subset of servers in a Farm used for data
        collection efficiency. An enumeration of these
        instances gives all the Zones in a Farm"
    ::= { citrixWmiCitrix 9 }

citrixZoneEntry OBJECT-TYPE
    SYNTAX     CitrixZone
    MAX-ACCESS not-accessible
    STATUS     current
    DESCRIPTION
        "None"
    INDEX      { ctxZoneIndex }
    ::= { citrixZoneTable 1 }

CitrixZone ::= SEQUENCE {
    ctxZoneIndex Integer32,
    ctxZoneDataCollector DisplayString,
    ctxZoneNumServersInZone Gauge32,
    ctxZoneZoneName DisplayString
}

ctxZoneIndex OBJECT-TYPE
    SYNTAX     Integer32 (1..2147483647)
    MAX-ACCESS read-only
    STATUS     current
    DESCRIPTION
        "The value of this object uniquely identifies the
        instance entry for this class."
    ::= { citrixZoneEntry 1 }

ctxZoneDataCollector OBJECT-TYPE
    SYNTAX     DisplayString
    MAX-ACCESS read-only
    STATUS     current
    DESCRIPTION
        "One Server in a Zone is elected as the data
        collector for the other servers"
    ::= { citrixZoneEntry 2 }

ctxZoneNumServersInZone OBJECT-TYPE
    SYNTAX     Gauge32
    MAX-ACCESS read-only
    STATUS     current
    DESCRIPTION
        "Too many servers in a Zone can deteriorate data
        collection performance"
    ::= { citrixZoneEntry 3 }

ctxZoneZoneName OBJECT-TYPE
    SYNTAX     DisplayString
    MAX-ACCESS read-only
    STATUS     current
    DESCRIPTION
        "Get the name of the zone"
    ::= { citrixZoneEntry 4 }

metaframeApplLoadLevelTable OBJECT-TYPE
    SYNTAX     SEQUENCE OF MetaFrameApplicationLoadLevel
    MAX-ACCESS not-accessible
    STATUS     current
    DESCRIPTION
        "Load Manager load value for Published
        Applications. Enumeration just gives application
        load for the local server"
    ::= { citrixWmiCitrix 10 }

metaframeApplLoadLevelEntry OBJECT-TYPE
    SYNTAX     MetaFrameApplicationLoadLevel
    MAX-ACCESS not-accessible
    STATUS     current
    DESCRIPTION
        "None"
    INDEX      { mfApplicationLoadLevelIndex }
    ::= { metaframeApplLoadLevelTable 1 }

MetaFrameApplicationLoadLevel ::= SEQUENCE {
    mfApplicationLoadLevelIndex Integer32,
    mfApplicationLoadLevelAppName DisplayString,
    mfApplicationLoadLevelLoadLevel Gauge32,
    mfApplicationLoadLevelServerName DisplayString
}

mfApplicationLoadLevelIndex OBJECT-TYPE
    SYNTAX     Integer32 (1..2147483647)
    MAX-ACCESS read-only
    STATUS     current
    DESCRIPTION
        "The value of this object uniquely identifies the
        instance entry for this class."
    ::= { metaframeApplLoadLevelEntry 1 }

mfApplicationLoadLevelAppName OBJECT-TYPE
    SYNTAX     DisplayString
    MAX-ACCESS read-only
    STATUS     current
    DESCRIPTION
        "Get the application name"
    ::= { metaframeApplLoadLevelEntry 2 }

mfApplicationLoadLevelLoadLevel OBJECT-TYPE
    SYNTAX     Gauge32
    MAX-ACCESS read-only
    STATUS     current
    DESCRIPTION
        "Get the load level"
    ::= { metaframeApplLoadLevelEntry 3 }

mfApplicationLoadLevelServerName OBJECT-TYPE
    SYNTAX     DisplayString
    MAX-ACCESS read-only
    STATUS     current
    DESCRIPTION
        "Get the server name"
    ::= { metaframeApplLoadLevelEntry 4 }

metaframeApplPublishOnSvrTable OBJECT-TYPE
    SYNTAX     SEQUENCE OF MetaFrameApplPublishOnServer
    MAX-ACCESS not-accessible
    STATUS     current
    DESCRIPTION
        "The set of applications that can be run from this
        server. Enumeration gives applications published
        across the farm"
    ::= { citrixWmiCitrix 11 }

metaframeApplPublishOnSvrEntry OBJECT-TYPE
    SYNTAX     MetaFrameApplPublishOnServer
    MAX-ACCESS not-accessible
    STATUS     current
    DESCRIPTION
        "None"
    INDEX      { mfaposIndex }
    ::= { metaframeApplPublishOnSvrTable 1 }

MetaFrameApplPublishOnServer ::= SEQUENCE {
    mfaposIndex Integer32,
    mfaposCtxServer DisplayString,
    mfaposWinApp DisplayString
}

mfaposIndex OBJECT-TYPE
    SYNTAX     Integer32 (1..2147483647)
    MAX-ACCESS read-only
    STATUS     current
    DESCRIPTION
        "The value of this object uniquely identifies the
        instance entry for this class."
    ::= { metaframeApplPublishOnSvrEntry 1 }

mfaposCtxServer OBJECT-TYPE
    SYNTAX     DisplayString
    MAX-ACCESS read-only
    STATUS     current
    DESCRIPTION
        "Return the server name"
    ::= { metaframeApplPublishOnSvrEntry 2 }

mfaposWinApp OBJECT-TYPE
    SYNTAX     DisplayString
    MAX-ACCESS read-only
    STATUS     current
    DESCRIPTION
        "Return the application name."
    ::= { metaframeApplPublishOnSvrEntry 3 }

metaframeApplRunOnServerTable OBJECT-TYPE
    SYNTAX     SEQUENCE OF MetaFrameApplRunningOnServer
    MAX-ACCESS not-accessible
    STATUS     current
    DESCRIPTION
        "The set of applications that are currently
        executing on this server"
    ::= { citrixWmiCitrix 12 }

metaframeApplRunOnServerEntry OBJECT-TYPE
    SYNTAX     MetaFrameApplRunningOnServer
    MAX-ACCESS not-accessible
    STATUS     current
    DESCRIPTION
        "None"
    INDEX      { mfarosIndex }
    ::= { metaframeApplRunOnServerTable 1 }

MetaFrameApplRunningOnServer ::= SEQUENCE {
    mfarosIndex Integer32,
    mfarosApplication DisplayString,
    mfarosProcessId INTEGER,
    mfarosServer DisplayString
}

mfarosIndex OBJECT-TYPE
    SYNTAX     Integer32 (1..2147483647)
    MAX-ACCESS read-only
    STATUS     current
    DESCRIPTION
        "The value of this object uniquely identifies the
        instance entry for this class."
    ::= { metaframeApplRunOnServerEntry 1 }

mfarosApplication OBJECT-TYPE
    SYNTAX     DisplayString
    MAX-ACCESS read-only
    STATUS     current
    DESCRIPTION
        "Return the appliation name"
    ::= { metaframeApplRunOnServerEntry 2 }

mfarosProcessId OBJECT-TYPE
    SYNTAX     INTEGER
    MAX-ACCESS read-only
    STATUS     current
    DESCRIPTION
        "Return the process ID"
    ::= { metaframeApplRunOnServerEntry 3 }

mfarosServer OBJECT-TYPE
    SYNTAX     DisplayString
    MAX-ACCESS read-only
    STATUS     current
    DESCRIPTION
        "Get the name of the server."
    ::= { metaframeApplRunOnServerEntry 4 }

metaframeAppsForGroupTable OBJECT-TYPE
    SYNTAX     SEQUENCE OF MetaFrameAppsForGroup
    MAX-ACCESS not-accessible
    STATUS     current
    DESCRIPTION
        "The Applications that are published for a
        particular group"
    ::= { citrixWmiCitrix 13 }

metaframeAppsForGroupEntry OBJECT-TYPE
    SYNTAX     MetaFrameAppsForGroup
    MAX-ACCESS not-accessible
    STATUS     current
    DESCRIPTION
        "None"
    INDEX      { mfAppsForGroupIndex }
    ::= { metaframeAppsForGroupTable 1 }

MetaFrameAppsForGroup ::= SEQUENCE {
    mfAppsForGroupIndex Integer32,
    mfAppsForGroupAntecedent DisplayString,
    mfAppsForGroupDependent DisplayString
}

mfAppsForGroupIndex OBJECT-TYPE
    SYNTAX     Integer32 (1..2147483647)
    MAX-ACCESS read-only
    STATUS     current
    DESCRIPTION
        "The value of this object uniquely identifies the
        instance entry for this class."
    ::= { metaframeAppsForGroupEntry 1 }

mfAppsForGroupAntecedent OBJECT-TYPE
    SYNTAX     DisplayString
    MAX-ACCESS read-only
    STATUS     current
    DESCRIPTION
        "Get the group name."
    ::= { metaframeAppsForGroupEntry 2 }

mfAppsForGroupDependent OBJECT-TYPE
    SYNTAX     DisplayString
    MAX-ACCESS read-only
    STATUS     current
    DESCRIPTION
        "Get the application name"
    ::= { metaframeAppsForGroupEntry 3 }

metaframeAppsInFolderTable OBJECT-TYPE
    SYNTAX     SEQUENCE OF MetaFrameAppsInFolder
    MAX-ACCESS not-accessible
    STATUS     current
    DESCRIPTION
        "No Description"
    ::= { citrixWmiCitrix 14 }

metaframeAppsInFolderEntry OBJECT-TYPE
    SYNTAX     MetaFrameAppsInFolder
    MAX-ACCESS not-accessible
    STATUS     current
    DESCRIPTION
        "None"
    INDEX      { mfAppsInFolderIndex }
    ::= { metaframeAppsInFolderTable 1 }

MetaFrameAppsInFolder ::= SEQUENCE {
    mfAppsInFolderIndex Integer32,
    mfAppsInFolderAntecedent DisplayString,
    mfAppsInFolderDependent DisplayString
}

mfAppsInFolderIndex OBJECT-TYPE
    SYNTAX     Integer32 (1..2147483647)
    MAX-ACCESS read-only
    STATUS     current
    DESCRIPTION
        "The value of this object uniquely identifies the
        instance entry for this class."
    ::= { metaframeAppsInFolderEntry 1 }

mfAppsInFolderAntecedent OBJECT-TYPE
    SYNTAX     DisplayString
    MAX-ACCESS read-only
    STATUS     current
    DESCRIPTION
        "Get the name of the folder object."
    ::= { metaframeAppsInFolderEntry 2 }

mfAppsInFolderDependent OBJECT-TYPE
    SYNTAX     DisplayString
    MAX-ACCESS read-only
    STATUS     current
    DESCRIPTION
        "Get the application name"
    ::= { metaframeAppsInFolderEntry 3 }

metaframeAppsInSessionTable OBJECT-TYPE
    SYNTAX     SEQUENCE OF MetaFrameAppsInSession
    MAX-ACCESS not-accessible
    STATUS     current
    DESCRIPTION
        "Sessions have a primary app but can also enumerate
        all apps within a session"
    ::= { citrixWmiCitrix 15 }

metaframeAppsInSessionEntry OBJECT-TYPE
    SYNTAX     MetaFrameAppsInSession
    MAX-ACCESS not-accessible
    STATUS     current
    DESCRIPTION
        "None"
    INDEX      { mfAppsInSessionIndex }
    ::= { metaframeAppsInSessionTable 1 }

MetaFrameAppsInSession ::= SEQUENCE {
    mfAppsInSessionIndex Integer32,
    mfAppsInSessionAntecedent DisplayString,
    mfAppsInSessionDependent DisplayString
}

mfAppsInSessionIndex OBJECT-TYPE
    SYNTAX     Integer32 (1..2147483647)
    MAX-ACCESS read-only
    STATUS     current
    DESCRIPTION
        "The value of this object uniquely identifies the
        instance entry for this class."
    ::= { metaframeAppsInSessionEntry 1 }

mfAppsInSessionAntecedent OBJECT-TYPE
    SYNTAX     DisplayString
    MAX-ACCESS read-only
    STATUS     current
    DESCRIPTION
        "Get the session name."
    ::= { metaframeAppsInSessionEntry 2 }

mfAppsInSessionDependent OBJECT-TYPE
    SYNTAX     DisplayString
    MAX-ACCESS read-only
    STATUS     current
    DESCRIPTION
        "Get the application name."
    ::= { metaframeAppsInSessionEntry 3 }

metaframeDisconnectSessionTable OBJECT-TYPE
    SYNTAX     SEQUENCE OF MetaFrameDisconnSessionHappening
    MAX-ACCESS not-accessible
    STATUS     current
    DESCRIPTION
        "Record of Disconnected Session occurences. Note
        that timestamps are serverspecific and cannot be
        guaranteed to match across different
        machines.Generated when a session disconnect occurs
        while subscribing to MetaFrameEvent."
    ::= { citrixWmiCitrix 16 }

metaframeDisconnectSessionEntry OBJECT-TYPE
    SYNTAX     MetaFrameDisconnSessionHappening
    MAX-ACCESS not-accessible
    STATUS     current
    DESCRIPTION
        "None"
    INDEX      { mfdshIndex }
    ::= { metaframeDisconnectSessionTable 1 }

MetaFrameDisconnSessionHappening ::= SEQUENCE {
    mfdshIndex Integer32,
    mfdshHowMany INTEGER,
    mfdshWhen DateAndTime
}

mfdshIndex OBJECT-TYPE
    SYNTAX     Integer32 (1..2147483647)
    MAX-ACCESS read-only
    STATUS     current
    DESCRIPTION
        "The value of this object uniquely identifies the
        instance entry for this class."
    ::= { metaframeDisconnectSessionEntry 1 }

mfdshHowMany OBJECT-TYPE
    SYNTAX     INTEGER
    MAX-ACCESS read-only
    STATUS     current
    DESCRIPTION
        "How Many events occurred since the last Happening
        was recordedFor those events where not all
        instances can be captured"
    ::= { metaframeDisconnectSessionEntry 2 }

mfdshWhen OBJECT-TYPE
    SYNTAX     DateAndTime
    MAX-ACCESS read-only
    STATUS     current
    DESCRIPTION
        "Get the time of the last Happening event"
    ::= { metaframeDisconnectSessionEntry 3 }

metaframeICAClientTable OBJECT-TYPE
    SYNTAX     SEQUENCE OF MetaFrameICAClient
    MAX-ACCESS not-accessible
    STATUS     current
    DESCRIPTION
        "Attributes of the client used to connect to a
        session"
    ::= { citrixWmiCitrix 17 }

metaframeICAClientEntry OBJECT-TYPE
    SYNTAX     MetaFrameICAClient
    MAX-ACCESS not-accessible
    STATUS     current
    DESCRIPTION
        "None"
    INDEX      { mfICAClientIndex }
    ::= { metaframeICAClientTable 1 }

MetaFrameICAClient ::= SEQUENCE {
    mfICAClientIndex Integer32,
    mfICAClientClientAddress DisplayString,
    mfICAClientClientAddrFamily INTEGER,
    mfICAClientClientBuild INTEGER,
    mfICAClientClientCacheDisk INTEGER,
    mfICAClientClientCacheLowMem INTEGER,
    mfICAClientClientCacheTiny INTEGER,
    mfICAClientClientCacheXms INTEGER,
    mfICAClientClientColorDepth INTEGER,
    mfICAClientClientDimBitmapMin INTEGER,
    mfICAClientClientDimCacheSize INTEGER,
    mfICAClientClientDimVersion INTEGER,
    mfICAClientClientDirectory DisplayString,
    mfICAClientClientEncryption DisplayString,
    mfICAClientClientHardwareID Gauge32,
    mfICAClientClientHRes INTEGER,
    mfICAClientClientLicense DisplayString,
    mfICAClientClientModemName DisplayString,
    mfICAClientClientName DisplayString,
    mfICAClientClientProductID INTEGER,
    mfICAClientClientProductIDValue INTEGER,
    mfICAClientClientVRes INTEGER,
    mfICAClientICABufLen INTEGER
}

mfICAClientIndex OBJECT-TYPE
    SYNTAX     Integer32 (1..2147483647)
    MAX-ACCESS read-only
    STATUS     current
    DESCRIPTION
        "The value of this object uniquely identifies the
        instance entry for this class."
    ::= { metaframeICAClientEntry 1 }

mfICAClientClientAddress OBJECT-TYPE
    SYNTAX     DisplayString
    MAX-ACCESS read-only
    STATUS     current
    DESCRIPTION
        "Get the client?s address.
        The returned client address is a string; this is
        the network address of the client. The address type
        is returned by the get_ClientAddrFamily call. If
        the address is an IP address, the returned string
        is in dotted-decimal format."
    ::= { metaframeICAClientEntry 2 }

mfICAClientClientAddrFamily OBJECT-TYPE
    SYNTAX     INTEGER {
        unspecifiedProtocol(0),
        internetProtocolIP(1),
        novellIPXSPX(2),
        microsoftNetBIOS(3)
    }
    MAX-ACCESS read-only
    STATUS     current
    DESCRIPTION
        "Get the client?s address family.
        This property indicates the network protocol used
        by the client to connect to the MetaFrame XP
        server. Use the ClientAddress property to get the
        client address."
    ::= { metaframeICAClientEntry 3 }

mfICAClientClientBuild OBJECT-TYPE
    SYNTAX     INTEGER
    MAX-ACCESS read-only
    STATUS     current
    DESCRIPTION
        "Get the client?s build number."
    ::= { metaframeICAClientEntry 4 }

mfICAClientClientCacheDisk OBJECT-TYPE
    SYNTAX     INTEGER
    MAX-ACCESS read-only
    STATUS     current
    DESCRIPTION
        "Get the client?s disk cache size."
    ::= { metaframeICAClientEntry 5 }

mfICAClientClientCacheLowMem OBJECT-TYPE
    SYNTAX     INTEGER
    MAX-ACCESS read-only
    STATUS     current
    DESCRIPTION
        "Return the client cache size for low/virtual
        memory."
    ::= { metaframeICAClientEntry 6 }

mfICAClientClientCacheTiny OBJECT-TYPE
    SYNTAX     INTEGER
    MAX-ACCESS read-only
    STATUS     current
    DESCRIPTION
        "Get the client?s cache size for small objects."
    ::= { metaframeICAClientEntry 7 }

mfICAClientClientCacheXms OBJECT-TYPE
    SYNTAX     INTEGER
    MAX-ACCESS read-only
    STATUS     current
    DESCRIPTION
        "Return the client cache size for XMS memory."
    ::= { metaframeICAClientEntry 8 }

mfICAClientClientColorDepth OBJECT-TYPE
    SYNTAX     INTEGER
    MAX-ACCESS read-only
    STATUS     current
    DESCRIPTION
        "Get the client display?s color depth.
        This returns the client display?s color depth, not
        the session?s color depth."
    ::= { metaframeICAClientEntry 9 }

mfICAClientClientDimBitmapMin OBJECT-TYPE
    SYNTAX     INTEGER
    MAX-ACCESS read-only
    STATUS     current
    DESCRIPTION
        "Return the client persistent cache minimum bitmap
        size."
    ::= { metaframeICAClientEntry 10 }

mfICAClientClientDimCacheSize OBJECT-TYPE
    SYNTAX     INTEGER
    MAX-ACCESS read-only
    STATUS     current
    DESCRIPTION
        "Return the client persistent cache size."
    ::= { metaframeICAClientEntry 11 }

mfICAClientClientDimVersion OBJECT-TYPE
    SYNTAX     INTEGER
    MAX-ACCESS read-only
    STATUS     current
    DESCRIPTION
        "Get the client?s persistent cache version."
    ::= { metaframeICAClientEntry 12 }

mfICAClientClientDirectory OBJECT-TYPE
    SYNTAX     DisplayString
    MAX-ACCESS read-only
    STATUS     current
    DESCRIPTION
        "Get the client?s directory.
        This directory is the full path name on the client
        device where the client software is installed."
    ::= { metaframeICAClientEntry 13 }

mfICAClientClientEncryption OBJECT-TYPE
    SYNTAX     DisplayString
    MAX-ACCESS read-only
    STATUS     current
    DESCRIPTION
        "Get the client?s encryption level.
        This returns the encryption level at which the
        connection was made."
    ::= { metaframeICAClientEntry 14 }

mfICAClientClientHardwareID OBJECT-TYPE
    SYNTAX     Gauge32
    MAX-ACCESS read-only
    STATUS     current
    DESCRIPTION
        "Get the client?s hardware ID.
        The ID returned is a serial number generated by the
        client. Do not use this as a unique client
        identifier. Instead, use the client?s IP address or
        client name to identify a client."
    ::= { metaframeICAClientEntry 15 }

mfICAClientClientHRes OBJECT-TYPE
    SYNTAX     INTEGER
    MAX-ACCESS read-only
    STATUS     current
    DESCRIPTION
        "Get the client display?s horizontal resolution.
        This is the client system?s display resolution, not
        the session?s horizontal resolution."
    ::= { metaframeICAClientEntry 16 }

mfICAClientClientLicense OBJECT-TYPE
    SYNTAX     DisplayString
    MAX-ACCESS read-only
    STATUS     current
    DESCRIPTION
        "Get the client?s license.
        This applies only to clients that have and use
        client connection licenses. This call should be
        ignored for MetaFrame XP."
    ::= { metaframeICAClientEntry 17 }

mfICAClientClientModemName OBJECT-TYPE
    SYNTAX     DisplayString
    MAX-ACCESS read-only
    STATUS     current
    DESCRIPTION
        "Get the client?s modem name.
        This property is valid only if the session is
        connected using a dial-up line. This name is empty
        if the session is connected using a LAN."
    ::= { metaframeICAClientEntry 18 }

mfICAClientClientName OBJECT-TYPE
    SYNTAX     DisplayString
    MAX-ACCESS read-only
    STATUS     current
    DESCRIPTION
        "Return the session client name.
        The session client name is usually the client
        device name. The client user can change the client
        device name to a string that is a valid client
        name."
    ::= { metaframeICAClientEntry 19 }

mfICAClientClientProductID OBJECT-TYPE
    SYNTAX     INTEGER {
        unknownClient(0),
        windows32Bit(1),
        windows16Bit(2),
        dos32Bit(3),
        dos32Bit2(4),
        windowsCE(5),
        unix(6),
        java(7),
        web(8),
        citrixDirectICAStation(9),
        citrixTextTerminal(10),
        citrixConsole(11),
        citrixMacClient(12),
        oemAndOther(13)
    }
    MAX-ACCESS read-only
    STATUS     current
    DESCRIPTION
        "Get the client product ID."
    ::= { metaframeICAClientEntry 20 }

mfICAClientClientProductIDValue OBJECT-TYPE
    SYNTAX     INTEGER
    MAX-ACCESS read-only
    STATUS     current
    DESCRIPTION
        "Returns the client's product ID value.
        Use this property to obtain the value of the client
        product ID. The value returned by the
        ClientProductID property is the client product
        type. This property returns the actual client
        product ID as shown in the Management Console for
        MetaFrame XP."
    ::= { metaframeICAClientEntry 21 }

mfICAClientClientVRes OBJECT-TYPE
    SYNTAX     INTEGER
    MAX-ACCESS read-only
    STATUS     current
    DESCRIPTION
        "Get the client display?s vertical resolution.
        This is the client machine?s display vertical
        resolution, not the session?s vertical resolution."
    ::= { metaframeICAClientEntry 22 }

mfICAClientICABufLen OBJECT-TYPE
    SYNTAX     INTEGER
    MAX-ACCESS read-only
    STATUS     current
    DESCRIPTION
        "Return the ICA buffer length of the session."
    ::= { metaframeICAClientEntry 23 }

metaframeInstalledSoftwareTable OBJECT-TYPE
    SYNTAX     SEQUENCE OF MetaFrameInstalledSoftware
    MAX-ACCESS not-accessible
    STATUS     current
    DESCRIPTION
        "Association class used to determine the details of
        the MF software on all servers in the Farm"
    ::= { citrixWmiCitrix 18 }

metaframeInstalledSoftwareEntry OBJECT-TYPE
    SYNTAX     MetaFrameInstalledSoftware
    MAX-ACCESS not-accessible
    STATUS     current
    DESCRIPTION
        "None"
    INDEX      { mfInstalledSoftwareIndex }
    ::= { metaframeInstalledSoftwareTable 1 }

MetaFrameInstalledSoftware ::= SEQUENCE {
    mfInstalledSoftwareIndex Integer32,
    mfInstalledSoftwareServer DisplayString,
    mfInstalledSoftwareSoftware DisplayString
}

mfInstalledSoftwareIndex OBJECT-TYPE
    SYNTAX     Integer32 (1..2147483647)
    MAX-ACCESS read-only
    STATUS     current
    DESCRIPTION
        "The value of this object uniquely identifies the
        instance entry for this class."
    ::= { metaframeInstalledSoftwareEntry 1 }

mfInstalledSoftwareServer OBJECT-TYPE
    SYNTAX     DisplayString
    MAX-ACCESS read-only
    STATUS     current
    DESCRIPTION
        "Return the server name"
    ::= { metaframeInstalledSoftwareEntry 2 }

mfInstalledSoftwareSoftware OBJECT-TYPE
    SYNTAX     DisplayString
    MAX-ACCESS read-only
    STATUS     current
    DESCRIPTION
        "Return the product name"
    ::= { metaframeInstalledSoftwareEntry 3 }

metaframeProcessTable OBJECT-TYPE
    SYNTAX     SEQUENCE OF MetaFrameProcess
    MAX-ACCESS not-accessible
    STATUS     current
    DESCRIPTION
        "An OS process running within a Session. Enum gives
        all process on current serverUse the processID with
        the CIMv2:Win32_Process class for more OS details"
    ::= { citrixWmiCitrix 19 }

metaframeProcessEntry OBJECT-TYPE
    SYNTAX     MetaFrameProcess
    MAX-ACCESS not-accessible
    STATUS     current
    DESCRIPTION
        "None"
    INDEX      { mfProcessIndex }
    ::= { metaframeProcessTable 1 }

MetaFrameProcess ::= SEQUENCE {
    mfProcessIndex Integer32,
    mfProcessProcessID Gauge32,
    mfProcessProcessName DisplayString,
    mfProcessProcessState INTEGER,
    mfProcessServerName DisplayString,
    mfProcessSessionID Gauge32,
    mfProcessUserName DisplayString
}

mfProcessIndex OBJECT-TYPE
    SYNTAX     Integer32 (1..2147483647)
    MAX-ACCESS read-only
    STATUS     current
    DESCRIPTION
        "The value of this object uniquely identifies the
        instance entry for this class."
    ::= { metaframeProcessEntry 1 }

mfProcessProcessID OBJECT-TYPE
    SYNTAX     Gauge32
    MAX-ACCESS read-only
    STATUS     current
    DESCRIPTION
        "Get process ID."
    ::= { metaframeProcessEntry 2 }

mfProcessProcessName OBJECT-TYPE
    SYNTAX     DisplayString
    MAX-ACCESS read-only
    STATUS     current
    DESCRIPTION
        "Return the process name."
    ::= { metaframeProcessEntry 3 }

mfProcessProcessState OBJECT-TYPE
    SYNTAX     INTEGER {
        unknownState(0),
        processInitialized(1),
        processIsReadyToRun(2),
        processIsRunning(3),
        processIsStandingBy(4),
        processTerminated(5),
        processInTransit(6),
        waitingOnExecutive(7),
        waitingOnFreePage(8),
        waitingToBePagedIn(9),
        waitingForMemory(10),
        executionDelayed(11),
        processSuspended(12),
        waitingOnUserRequest(13),
        eventPairHigh(14),
        eventPairLow(15),
        lpcReceive(16),
        lpcReply(17),
        waitForVirtualMemory(18),
        processIsPagedOut(19),
        waitForOtherReasons(20)
    }
    MAX-ACCESS read-only
    STATUS     current
    DESCRIPTION
        "Get the state of the process."
    ::= { metaframeProcessEntry 4 }

mfProcessServerName OBJECT-TYPE
    SYNTAX     DisplayString
    MAX-ACCESS read-only
    STATUS     current
    DESCRIPTION
        "Get server name.
        This returns the name of the server on which this
        process is running."
    ::= { metaframeProcessEntry 5 }

mfProcessSessionID OBJECT-TYPE
    SYNTAX     Gauge32
    MAX-ACCESS read-only
    STATUS     current
    DESCRIPTION
        "Return the session ID.
        This returns the ID of the session in which the
        process is running."
    ::= { metaframeProcessEntry 6 }

mfProcessUserName OBJECT-TYPE
    SYNTAX     DisplayString
    MAX-ACCESS read-only
    STATUS     current
    DESCRIPTION
        "Get the user name.
        This is the name of the user who owns the current
        process. Some system processes may not have a user
        name."
    ::= { metaframeProcessEntry 7 }

metaframeProcessesInSessionTable OBJECT-TYPE
    SYNTAX     SEQUENCE OF MetaFrameProcessesInSession
    MAX-ACCESS not-accessible
    STATUS     current
    DESCRIPTION
        "No Description"
    ::= { citrixWmiCitrix 20 }

metaframeProcessesInSessionEntry OBJECT-TYPE
    SYNTAX     MetaFrameProcessesInSession
    MAX-ACCESS not-accessible
    STATUS     current
    DESCRIPTION
        "None"
    INDEX      { mfProcessesInSessionIndex }
    ::= { metaframeProcessesInSessionTable 1 }

MetaFrameProcessesInSession ::= SEQUENCE {
    mfProcessesInSessionIndex Integer32,
    mfProcessesInSessionAntecedent DisplayString,
    mfProcessesInSessionDependent DisplayString
}

mfProcessesInSessionIndex OBJECT-TYPE
    SYNTAX     Integer32 (1..2147483647)
    MAX-ACCESS read-only
    STATUS     current
    DESCRIPTION
        "The value of this object uniquely identifies the
        instance entry for this class."
    ::= { metaframeProcessesInSessionEntry 1 }

mfProcessesInSessionAntecedent OBJECT-TYPE
    SYNTAX     DisplayString
    MAX-ACCESS read-only
    STATUS     current
    DESCRIPTION
        "Get the session name."
    ::= { metaframeProcessesInSessionEntry 2 }

mfProcessesInSessionDependent OBJECT-TYPE
    SYNTAX     DisplayString
    MAX-ACCESS read-only
    STATUS     current
    DESCRIPTION
        "Return the process name."
    ::= { metaframeProcessesInSessionEntry 3 }

metaframeSchemaVersionTable OBJECT-TYPE
    SYNTAX     SEQUENCE OF MetaFrameSchemaVersion
    MAX-ACCESS not-accessible
    STATUS     current
    DESCRIPTION
        "Schema Version. Used to verify that MOF & Dynamic
        provider are in step"
    ::= { citrixWmiCitrix 21 }

metaframeSchemaVersionEntry OBJECT-TYPE
    SYNTAX     MetaFrameSchemaVersion
    MAX-ACCESS not-accessible
    STATUS     current
    DESCRIPTION
        "None"
    INDEX      { mfSchemaVersionIndex }
    ::= { metaframeSchemaVersionTable 1 }

MetaFrameSchemaVersion ::= SEQUENCE {
    mfSchemaVersionIndex Integer32,
    mfSchemaVersionVersion DisplayString
}

mfSchemaVersionIndex OBJECT-TYPE
    SYNTAX     Integer32 (1..2147483647)
    MAX-ACCESS read-only
    STATUS     current
    DESCRIPTION
        "The value of this object uniquely identifies the
        instance entry for this class."
    ::= { metaframeSchemaVersionEntry 1 }

mfSchemaVersionVersion OBJECT-TYPE
    SYNTAX     DisplayString
    MAX-ACCESS read-only
    STATUS     current
    DESCRIPTION
        "Get the schema version"
    ::= { metaframeSchemaVersionEntry 2 }

metaframeServerTable OBJECT-TYPE
    SYNTAX     SEQUENCE OF MetaFrameServer
    MAX-ACCESS not-accessible
    STATUS     current
    DESCRIPTION
        "Where the Citrix Server has MetaFrame installed
        this class applies. Enumeration just gives
        information on the local server."
    ::= { citrixWmiCitrix 22 }

metaframeServerEntry OBJECT-TYPE
    SYNTAX     MetaFrameServer
    MAX-ACCESS not-accessible
    STATUS     current
    DESCRIPTION
        "None"
    INDEX      { mfServerIndex }
    ::= { metaframeServerTable 1 }

MetaFrameServer ::= SEQUENCE {
    mfServerIndex Integer32,
    mfServerDomain DisplayString,
    mfServerFarmName DisplayString,
    mfServerIPAddress DisplayString,
    mfServerLoginsEnabled TruthValue,
    mfServerNumberOfActiveSessions INTEGER,
    mfServerNumOfDisconnectSessions INTEGER,
    mfServerNumberOfSessions INTEGER,
    mfServerServerName DisplayString,
    mfServerServerType INTEGER,
    mfServerZoneName DisplayString,
    mfServerZoneRanking INTEGER
}

mfServerIndex OBJECT-TYPE
    SYNTAX     Integer32 (1..2147483647)
    MAX-ACCESS read-only
    STATUS     current
    DESCRIPTION
        "The value of this object uniquely identifies the
        instance entry for this class."
    ::= { metaframeServerEntry 1 }

mfServerDomain OBJECT-TYPE
    SYNTAX     DisplayString
    MAX-ACCESS read-only
    STATUS     current
    DESCRIPTION
        "Primary domain of this server"
    ::= { metaframeServerEntry 2 }

mfServerFarmName OBJECT-TYPE
    SYNTAX     DisplayString
    MAX-ACCESS read-only
    STATUS     current
    DESCRIPTION
        "Farm in which this server operates"
    ::= { metaframeServerEntry 3 }

mfServerIPAddress OBJECT-TYPE
    SYNTAX     DisplayString
    MAX-ACCESS read-only
    STATUS     current
    DESCRIPTION
        "The principal IP address of the server. Some
        servers mayhave several network addresses. See
        CIMv2:Win32_NetworkAdapterConfiguration"
    ::= { metaframeServerEntry 4 }

mfServerLoginsEnabled OBJECT-TYPE
    SYNTAX     TruthValue
    MAX-ACCESS read-only
    STATUS     current
    DESCRIPTION
        "Are logins enabled on this server"
    ::= { metaframeServerEntry 5 }

mfServerNumberOfActiveSessions OBJECT-TYPE
    SYNTAX     INTEGER
    MAX-ACCESS read-only
    STATUS     current
    DESCRIPTION
        "Return the number of active sessions"
    ::= { metaframeServerEntry 6 }

mfServerNumOfDisconnectSessions OBJECT-TYPE
    SYNTAX     INTEGER
    MAX-ACCESS read-only
    STATUS     current
    DESCRIPTION
        "Return the number of disconnected sessions"
    ::= { metaframeServerEntry 7 }

mfServerNumberOfSessions OBJECT-TYPE
    SYNTAX     INTEGER
    MAX-ACCESS read-only
    STATUS     current
    DESCRIPTION
        "Return the total number of sessions"
    ::= { metaframeServerEntry 8 }

mfServerServerName OBJECT-TYPE
    SYNTAX     DisplayString
    MAX-ACCESS read-only
    STATUS     current
    DESCRIPTION
        "Get the name of the server."
    ::= { metaframeServerEntry 9 }

mfServerServerType OBJECT-TYPE
    SYNTAX     INTEGER {
        unknownObject(0),
        windowsServer(1)
    }
    MAX-ACCESS read-only
    STATUS     current
    DESCRIPTION
        "Get the type of server object.
        The only value returned is MetaFrameWinSrvObject.
        The type of object is used to identify the type of
        server. Only MetaFrame XP Server for Windows is
        supported."
    ::= { metaframeServerEntry 10 }

mfServerZoneName OBJECT-TYPE
    SYNTAX     DisplayString
    MAX-ACCESS read-only
    STATUS     current
    DESCRIPTION
        "Zone in which this server operates"
    ::= { metaframeServerEntry 11 }

mfServerZoneRanking OBJECT-TYPE
    SYNTAX     INTEGER {
        unknownRank(0),
        zoneDataCollector(1),
        backupDataCollector(2),
        serverIsAZoneMember(3),
        cannotBeDataCollector(4)
    }
    MAX-ACCESS read-only
    STATUS     current
    DESCRIPTION
        "Servers role in Zone"
    ::= { metaframeServerEntry 12 }

metaframeServerLoadLevelTable OBJECT-TYPE
    SYNTAX     SEQUENCE OF MetaFrameServerLoadLevel
    MAX-ACCESS not-accessible
    STATUS     current
    DESCRIPTION
        "Load Manager load value for MetaFrame Servers.
        Enumeration gives just the load level for the local
        server"
    ::= { citrixWmiCitrix 23 }

metaframeServerLoadLevelEntry OBJECT-TYPE
    SYNTAX     MetaFrameServerLoadLevel
    MAX-ACCESS not-accessible
    STATUS     current
    DESCRIPTION
        "None"
    INDEX      { mfServerLoadLevelIndex }
    ::= { metaframeServerLoadLevelTable 1 }

MetaFrameServerLoadLevel ::= SEQUENCE {
    mfServerLoadLevelIndex Integer32,
    mfServerLoadLevelLoadLevel Gauge32,
    mfServerLoadLevelServerName DisplayString
}

mfServerLoadLevelIndex OBJECT-TYPE
    SYNTAX     Integer32 (1..2147483647)
    MAX-ACCESS read-only
    STATUS     current
    DESCRIPTION
        "The value of this object uniquely identifies the
        instance entry for this class."
    ::= { metaframeServerLoadLevelEntry 1 }

mfServerLoadLevelLoadLevel OBJECT-TYPE
    SYNTAX     Gauge32
    MAX-ACCESS read-only
    STATUS     current
    DESCRIPTION
        "Return the load level"
    ::= { metaframeServerLoadLevelEntry 2 }

mfServerLoadLevelServerName OBJECT-TYPE
    SYNTAX     DisplayString
    MAX-ACCESS read-only
    STATUS     current
    DESCRIPTION
        "Return the server name"
    ::= { metaframeServerLoadLevelEntry 3 }

metaframeSessionTable OBJECT-TYPE
    SYNTAX     SEQUENCE OF MetaFrameSession
    MAX-ACCESS not-accessible
    STATUS     current
    DESCRIPTION
        "Attributes of a MetaFrame ICA session on a server.
        Enumeration gives all sessions on the server"
    ::= { citrixWmiCitrix 24 }

metaframeSessionEntry OBJECT-TYPE
    SYNTAX     MetaFrameSession
    MAX-ACCESS not-accessible
    STATUS     current
    DESCRIPTION
        "None"
    INDEX      { mfSessionIndex }
    ::= { metaframeSessionTable 1 }

MetaFrameSession ::= SEQUENCE {
    mfSessionIndex Integer32,
    mfSessionClient DisplayString,
    mfSessionConnectTime DateAndTime,
    mfSessionCurrentTime DateAndTime,
    mfSessionDisconnectTime DateAndTime,
    mfSessionLastInputTime DateAndTime,
    mfSessionLogonTime DateAndTime,
    mfSessionNumberOfApps INTEGER,
    mfSessionServerName DisplayString,
    mfSessionSessionID INTEGER,
    mfSessionSessionName DisplayString,
    mfSessionSessionState INTEGER,
    mfSessionSessionUser DisplayString
}

mfSessionIndex OBJECT-TYPE
    SYNTAX     Integer32 (1..2147483647)
    MAX-ACCESS read-only
    STATUS     current
    DESCRIPTION
        "The value of this object uniquely identifies the
        instance entry for this class."
    ::= { metaframeSessionEntry 1 }

mfSessionClient OBJECT-TYPE
    SYNTAX     DisplayString
    MAX-ACCESS read-only
    STATUS     current
    DESCRIPTION
        "Return the session client name.
        The session client name is usually the client
        device name. The client user can change the client
        device name to a string that is a valid client
        name."
    ::= { metaframeSessionEntry 2 }

mfSessionConnectTime OBJECT-TYPE
    SYNTAX     DateAndTime
    MAX-ACCESS read-only
    STATUS     current
    DESCRIPTION
        "Return the connect time of the session."
    ::= { metaframeSessionEntry 3 }

mfSessionCurrentTime OBJECT-TYPE
    SYNTAX     DateAndTime
    MAX-ACCESS read-only
    STATUS     current
    DESCRIPTION
        "Return the current time.
        The returned time is not the exact time at which
        this call is made. Its value reflects the time when
        one of the session?s get_XxxTime functions was
        called"
    ::= { metaframeSessionEntry 4 }

mfSessionDisconnectTime OBJECT-TYPE
    SYNTAX     DateAndTime
    MAX-ACCESS read-only
    STATUS     current
    DESCRIPTION
        "Return the last session disconnect time.
        If the session is connected, the time is 0 for all
        the values returned by the IMetaFrameTime
        interface. If the session is disconnected, it
        contains the disconnect time."
    ::= { metaframeSessionEntry 5 }

mfSessionLastInputTime OBJECT-TYPE
    SYNTAX     DateAndTime
    MAX-ACCESS read-only
    STATUS     current
    DESCRIPTION
        "Get the session?s last input time.
        To get an updated session last input time, a new
        session object should be created to read the
        updated time. The value returned by this property
        is the time when this property is read the first
        time. Subsequent calls to this property return the
        same value."
    ::= { metaframeSessionEntry 6 }

mfSessionLogonTime OBJECT-TYPE
    SYNTAX     DateAndTime
    MAX-ACCESS read-only
    STATUS     current
    DESCRIPTION
        "Return the session logon time.
        See the description for the MetaFrameTime object
        for more information about accessing the returned
        time."
    ::= { metaframeSessionEntry 7 }

mfSessionNumberOfApps OBJECT-TYPE
    SYNTAX     INTEGER
    MAX-ACCESS read-only
    STATUS     current
    DESCRIPTION
        "Return the number of applications"
    ::= { metaframeSessionEntry 8 }

mfSessionServerName OBJECT-TYPE
    SYNTAX     DisplayString
    MAX-ACCESS read-only
    STATUS     current
    DESCRIPTION
        "Included as a convenience for session summaries"
    ::= { metaframeSessionEntry 9 }

mfSessionSessionID OBJECT-TYPE
    SYNTAX     INTEGER
    MAX-ACCESS read-only
    STATUS     current
    DESCRIPTION
        "Get session ID."
    ::= { metaframeSessionEntry 10 }

mfSessionSessionName OBJECT-TYPE
    SYNTAX     DisplayString
    MAX-ACCESS read-only
    STATUS     current
    DESCRIPTION
        "Get the session name."
    ::= { metaframeSessionEntry 11 }

mfSessionSessionState OBJECT-TYPE
    SYNTAX     INTEGER {
        userLoggedOn(0),
        connectedToClient(1),
        connectingToClient(2),
        shadowingOtherSession(3),
        loggedOnButNoClient(4),
        waitingForConnection(5),
        listeningForConnection(6),
        resetInProgress(7),
        downDueToError(8),
        initializing(9)
    }
    MAX-ACCESS read-only
    STATUS     current
    DESCRIPTION
        "Return the current state of the session.
        If the returned session state is
        MFSessionStateStale, no further attempt to read
        other session properties should be made. This state
        indicates that the session may not exist anymore."
    ::= { metaframeSessionEntry 12 }

mfSessionSessionUser OBJECT-TYPE
    SYNTAX     DisplayString
    MAX-ACCESS read-only
    STATUS     current
    DESCRIPTION
        "Return the name of the user who is running the
        session."
    ::= { metaframeSessionEntry 13 }

metaframeSoftwareTable OBJECT-TYPE
    SYNTAX     SEQUENCE OF MetaFrameSoftware
    MAX-ACCESS not-accessible
    STATUS     current
    DESCRIPTION
        "Additional attributes of the MetaFrame product"
    ::= { citrixWmiCitrix 25 }

metaframeSoftwareEntry OBJECT-TYPE
    SYNTAX     MetaFrameSoftware
    MAX-ACCESS not-accessible
    STATUS     current
    DESCRIPTION
        "None"
    INDEX      { mfSoftwareIndex }
    ::= { metaframeSoftwareTable 1 }

MetaFrameSoftware ::= SEQUENCE {
    mfSoftwareIndex Integer32,
    mfSoftwareFeatureReleaseLevel Gauge32,
    mfSoftwareInstallDate DateAndTime,
    mfSoftwareMFWinProductCode DisplayString,
    mfSoftwareProductName DisplayString,
    mfSoftwareReleaseLevel DisplayString,
    mfSoftwareVersion DisplayString
}

mfSoftwareIndex OBJECT-TYPE
    SYNTAX     Integer32 (1..2147483647)
    MAX-ACCESS read-only
    STATUS     current
    DESCRIPTION
        "The value of this object uniquely identifies the
        instance entry for this class."
    ::= { metaframeSoftwareEntry 1 }

mfSoftwareFeatureReleaseLevel OBJECT-TYPE
    SYNTAX     Gauge32
    MAX-ACCESS read-only
    STATUS     current
    DESCRIPTION
        "Query the MetaFrame XP Feature Release level."
    ::= { metaframeSoftwareEntry 2 }

mfSoftwareInstallDate OBJECT-TYPE
    SYNTAX     DateAndTime
    MAX-ACCESS read-only
    STATUS     current
    DESCRIPTION
        "Query the MetaFrame XP installation date."
    ::= { metaframeSoftwareEntry 3 }

mfSoftwareMFWinProductCode OBJECT-TYPE
    SYNTAX     DisplayString
    MAX-ACCESS read-only
    STATUS     current
    DESCRIPTION
        "Return the server product code.
        A server must have the proper product code
        installed for it to accept connections from ICA
        Clients."
    ::= { metaframeSoftwareEntry 4 }

mfSoftwareProductName OBJECT-TYPE
    SYNTAX     DisplayString
    MAX-ACCESS read-only
    STATUS     current
    DESCRIPTION
        "Return the product name"
    ::= { metaframeSoftwareEntry 5 }

mfSoftwareReleaseLevel OBJECT-TYPE
    SYNTAX     DisplayString
    MAX-ACCESS read-only
    STATUS     current
    DESCRIPTION
        "Return the release level"
    ::= { metaframeSoftwareEntry 6 }

mfSoftwareVersion OBJECT-TYPE
    SYNTAX     DisplayString
    MAX-ACCESS read-only
    STATUS     current
    DESCRIPTION
        "Return the product version"
    ::= { metaframeSoftwareEntry 7 }

metaframeWinApplicationTable OBJECT-TYPE
    SYNTAX     SEQUENCE OF MetaFrameWinApplication
    MAX-ACCESS not-accessible
    STATUS     current
    DESCRIPTION
        "Additional Attributes of a published app on a
        Windows server"
    ::= { citrixWmiCitrix 26 }

metaframeWinApplicationEntry OBJECT-TYPE
    SYNTAX     MetaFrameWinApplication
    MAX-ACCESS not-accessible
    STATUS     current
    DESCRIPTION
        "None"
    INDEX      { mfWinApplIndex }
    ::= { metaframeWinApplicationTable 1 }

MetaFrameWinApplication ::= SEQUENCE {
    mfWinApplIndex Integer32,
    mfWinApplApplicationID DisplayString,
    mfWinApplAppVersion INTEGER,
    mfWinApplBrowserName DisplayString,
    mfWinApplDefaultEncryption INTEGER,
    mfWinApplDefaultInitProg DisplayString,
    mfWinApplDefaultSoundType INTEGER,
    mfWinApplDefaultWindowColor INTEGER,
    mfWinApplDefaultWindowHeight INTEGER,
    mfWinApplDefaultWindowScale INTEGER,
    mfWinApplDefaultWindowType INTEGER,
    mfWinApplDefaultWindowWidth INTEGER,
    mfWinApplDefaultWorkDir DisplayString,
    mfWinApplDescription DisplayString,
    mfWinApplDesktopIntegrate INTEGER,
    mfWinApplDistinguishedName DisplayString,
    mfWinApplEnableApp TruthValue,
    mfWinApplFarmName DisplayString,
    mfWinApplMFAttributes INTEGER,
    mfWinApplName DisplayString,
    mfWinApplParentFolderDN DisplayString,
    mfWinApplPNAttributes INTEGER,
    mfWinApplPNFolder DisplayString,
    mfWinApplPublishingFlags INTEGER,
    mfWinApplReadOnly TruthValue
}

mfWinApplIndex OBJECT-TYPE
    SYNTAX     Integer32 (1..2147483647)
    MAX-ACCESS read-only
    STATUS     current
    DESCRIPTION
        "The value of this object uniquely identifies the
        instance entry for this class."
    ::= { metaframeWinApplicationEntry 1 }

mfWinApplApplicationID OBJECT-TYPE
    SYNTAX     DisplayString
    MAX-ACCESS read-only
    STATUS     current
    DESCRIPTION
        "Get the 64 bit application ID.
        The ID is a 64-bit number that uniquely identifies
        the application even if the application name
        changed. You can access the ID data by reading the
        properties of the IMetaFrameID interface."
    ::= { metaframeWinApplicationEntry 2 }

mfWinApplAppVersion OBJECT-TYPE
    SYNTAX     INTEGER
    MAX-ACCESS read-only
    STATUS     current
    DESCRIPTION
        "Return the application version. Read-only.
        The version of an application is the version number
        of the IMA application subsystem on which this
        application was originally published. Currently
        this value is always 1.
        When an application is created, an internal version
        number is assigned to the application. This version
        number is used to make sure that the application
        data will be handled properly when a version of the
        IMA application subsystem needs to read an
        application data published by a newer version of
        the IMA application publishing subsystem."
    ::= { metaframeWinApplicationEntry 3 }

mfWinApplBrowserName OBJECT-TYPE
    SYNTAX     DisplayString
    MAX-ACCESS read-only
    STATUS     current
    DESCRIPTION
        "Get the application?s browser name.
        The browser name is another name used by the ICA
        browser."
    ::= { metaframeWinApplicationEntry 4 }

mfWinApplDefaultEncryption OBJECT-TYPE
    SYNTAX     INTEGER {
        unknownEncryption(0),
        basicEncryptionRC5Logon(1),
        rc540Bit(2),
        rc556Bit(3),
        rc5128Bit(4)
    }
    MAX-ACCESS read-only
    STATUS     current
    DESCRIPTION
        "Return the value of the default encryption level
        to specify the encryption requirements for ICA
        Clients connecting to the application.
        This specifies the encryption requirements for ICA
        Clients connecting to the application."
    ::= { metaframeWinApplicationEntry 5 }

mfWinApplDefaultInitProg OBJECT-TYPE
    SYNTAX     DisplayString
    MAX-ACCESS read-only
    STATUS     current
    DESCRIPTION
        "Return the value of the default initial program
        (command line).
        You can include the %* token in the command line to
        act as a placeholder for clientsupplied application
        parameters. When a client makes a connection
        request, the server replaces the %* token in the
        command line with application parameters provided
        by the client.
        This default initial command line is used only when
        a server doesn?t have its own command line
        specified."
    ::= { metaframeWinApplicationEntry 6 }

mfWinApplDefaultSoundType OBJECT-TYPE
    SYNTAX     INTEGER {
        unknownSoundType(0),
        noSound(1),
        basicSound(2)
    }
    MAX-ACCESS read-only
    STATUS     current
    DESCRIPTION
        "Return the value of the default sound type,
        specifying the sound requirements for ICA Clients
        connecting to the application.
        This specifies the sound requirements for ICA
        Clients connecting to the application.
        MFWinSoundNone disables audio support for the
        application. However, ICA Client users can change
        these settings for their connection.
        MFWinSoundBasic enables audio support for the
        application."
    ::= { metaframeWinApplicationEntry 7 }

mfWinApplDefaultWindowColor OBJECT-TYPE
    SYNTAX     INTEGER {
        unknownWindowColor(0),
        a16Colors(1),
        a256Colors(2),
        a65536Colors(3),
        a16MillionColors(4)
    }
    MAX-ACCESS read-only
    STATUS     current
    DESCRIPTION
        "Return the value of the default window color to
        specify how the application appears to the ICA
        Client user.
        Window color is the color depth for the
        application."
    ::= { metaframeWinApplicationEntry 8 }

mfWinApplDefaultWindowHeight OBJECT-TYPE
    SYNTAX     INTEGER
    MAX-ACCESS read-only
    STATUS     current
    DESCRIPTION
        "Return the value of the default window height to
        specify how the application appears to the ICA
        Client user.
        You must set the default window type to be custom
        resolution before applying a custom width or
        height."
    ::= { metaframeWinApplicationEntry 9 }

mfWinApplDefaultWindowScale OBJECT-TYPE
    SYNTAX     INTEGER
    MAX-ACCESS read-only
    STATUS     current
    DESCRIPTION
        "Return the value of the default window scale to
        specify how the application appears to the ICA
        Client user.
        You must set the default window type to be a
        percentage of the client desktop resolution before
        applying this scale amount.
        This specifies the size of the application window
        (scaled as a percentage of the client screen) as it
        appears to the ICA Client user."
    ::= { metaframeWinApplicationEntry 10 }

mfWinApplDefaultWindowType OBJECT-TYPE
    SYNTAX     INTEGER {
        unknownWindowType(0),
        a640x480(1),
        a800x600(2),
        a1024x768(3),
        a1280x1024(4),
        a1600x1200(5),
        custom(6),
        percent(7),
        fullscreen(8)
    }
    MAX-ACCESS read-only
    STATUS     current
    DESCRIPTION
        "Get the default window type.
        This specifies how the application appears to the
        ICA Client user.
        The window type is the default window size for ICA
        connections. You can specify window type as a
        standard resolution, custom resolution, percentage
        of the client desktop, or full screen."
    ::= { metaframeWinApplicationEntry 11 }

mfWinApplDefaultWindowWidth OBJECT-TYPE
    SYNTAX     INTEGER
    MAX-ACCESS read-only
    STATUS     current
    DESCRIPTION
        "Return the value of the default window width to
        specify how the application appears to the ICA
        Client user.
        You must set the default window type to be custom
        resolution before applying a custom width or
        height."
    ::= { metaframeWinApplicationEntry 12 }

mfWinApplDefaultWorkDir OBJECT-TYPE
    SYNTAX     DisplayString
    MAX-ACCESS read-only
    STATUS     current
    DESCRIPTION
        "Return the value of the default working directory.
        The default working directory is used if a server
        doesn?t have its own working directory specified."
    ::= { metaframeWinApplicationEntry 13 }

mfWinApplDescription OBJECT-TYPE
    SYNTAX     DisplayString
    MAX-ACCESS read-only
    STATUS     current
    DESCRIPTION
        "Return the application?s description."
    ::= { metaframeWinApplicationEntry 14 }

mfWinApplDesktopIntegrate OBJECT-TYPE
    SYNTAX     INTEGER {
        noDesktopIntegrate(0),
        startMenu(1),
        desktop(2)
    }
    MAX-ACCESS read-only
    STATUS     current
    DESCRIPTION
        "Return the value of the desktop integrate flags to
        specify how ICA Client users can access the
        application.
        These flags specify how ICA Client users can access
        the application.
        Desktop integrate flags are a combination of the
        following flags:
        MFWinAppIntegrateNone: A shortcut to this
        application is not created for the user?s local
        Start Menu or desktop.
        MFWinAppIntegrateStartMenu: A shortcut to this
        application is created in the user's local Start
        menu (ICA Win32 Clients only).
        MFWinAppIntegrateDesktop: A shortcut to this
        application is created on the user's local desktop
        (ICA Win32 Clients only)."
    ::= { metaframeWinApplicationEntry 15 }

mfWinApplDistinguishedName OBJECT-TYPE
    SYNTAX     DisplayString
    MAX-ACCESS read-only
    STATUS     current
    DESCRIPTION
        "Return the application?s distinguished name.
        The application?s distinguished name is the unique
        identifier of the application in the farm. The
        maximum length of the distinguished name is 256
        characters."
    ::= { metaframeWinApplicationEntry 16 }

mfWinApplEnableApp OBJECT-TYPE
    SYNTAX     TruthValue
    MAX-ACCESS read-only
    STATUS     current
    DESCRIPTION
        "Get the value of the 'Enable application' flag.
        When you publish an application, it is enabled by
        default. Enabled applications are then available to
        the users specified when the application was
        published. Disabled applications are not available
        to users.
        The application can become disabled internally if
        its server list becomes empty, or if its user list
        becomes empty and the application is not configured
        to accept anonymous connections.
        A disabled application is not available to ICA
        Clients.
        Another way to enable and disable an application is
        to set one of the application?s Program
        Neighborhood attributes. See the references for the
        IMetaFrameWinApp interface?s get/put_PNAttribute
        function. An application can also be internally
        enabled and disabled if its server and/or user list
        becomes empty or is no longer empty."
    ::= { metaframeWinApplicationEntry 17 }

mfWinApplFarmName OBJECT-TYPE
    SYNTAX     DisplayString
    MAX-ACCESS read-only
    STATUS     current
    DESCRIPTION
        "Get the name of the farm.
        This property is useful if the server object is
        created using the GetServer() function of a farm
        object. It is also useful when servers from
        different farms are connected to one MFCOM client
        using DCOM.
        The farm name can also be obtained from many other
        objects. If a multi-farm environment is used, this
        method is useful in identifying a server."
    ::= { metaframeWinApplicationEntry 18 }

mfWinApplMFAttributes OBJECT-TYPE
    SYNTAX     INTEGER {
        noMetaFrameAttribute(0),
        maximizeOnStartup(1),
        hideTitleBar(2)
    }
    MAX-ACCESS read-only
    STATUS     current
    DESCRIPTION
        "Return the value of the MetaFrame XP attributes to
        specify how the application appears to the ICA
        Client user.
        Value of the MetaFrame attributes. These values can
        be:
        MFWinAppMFAttrNone: No application start up setting
        is defined.
        MFWinAppMaximizeOnStartup: The application window
        is maximized to fill the ICA session window.
        MFWinAppHideTitleBar: The application?s title bar
        is not displayed at the top of the ICA session
        window."
    ::= { metaframeWinApplicationEntry 19 }

mfWinApplName OBJECT-TYPE
    SYNTAX     DisplayString
    MAX-ACCESS read-only
    STATUS     current
    DESCRIPTION
        "Return the application name."
    ::= { metaframeWinApplicationEntry 20 }

mfWinApplParentFolderDN OBJECT-TYPE
    SYNTAX     DisplayString
    MAX-ACCESS read-only
    STATUS     current
    DESCRIPTION
        "Return the parent folder?s distinguished name."
    ::= { metaframeWinApplicationEntry 21 }

mfWinApplPNAttributes OBJECT-TYPE
    SYNTAX     INTEGER
    MAX-ACCESS read-only
    STATUS     current
    DESCRIPTION
        "Get the Program Neighborhood attributes. This
        specifies how Program Neighborhood users access the
        application.
        Program Neighborhood attributes are a combination
        of the following flags:
        MFWinAppPNAttrNone: The Program Neighborhood
        attributes settings are off.
        MFWinAppDisabled: Makes the application unavailable
        to users. Published applications are enabled by
        default and are available to the users specified
        when the application was published. An alternative
        way to enable or disable the application is to use
        the IMetaFrameApplication interface?s EnableApp
        property.
        MFWinAppMinimumSound: Allows only ICA Clients with
        required audio support to connect to the
        application.
        MFWinAppMinimumEncrypt: Allows only ICA Clients
        that support the required level of encryption to
        connect to the application.
        MFWinAppDesktop: Publishes the server?s entire
        Windows desktop. The user sees a desktop interface
        from which any application installed on that server
        can be launched.
        MFWinAppAnonymous: Allows all ICA Client users to
        start the application without specifying a user
        name, domain name, or password. Users connecting
        through Program Neighborhood and the Web Interface
        for MetaFrame XP must first authenticate to the
        server. After authenticating to the server, they do
        not need to authenticate again to access the
        application."
    ::= { metaframeWinApplicationEntry 22 }

mfWinApplPNFolder OBJECT-TYPE
    SYNTAX     DisplayString
    MAX-ACCESS read-only
    STATUS     current
    DESCRIPTION
        "Query the client's Program Neighborhood folder."
    ::= { metaframeWinApplicationEntry 23 }

mfWinApplPublishingFlags OBJECT-TYPE
    SYNTAX     INTEGER {
        noEnumerationMask(0),
        browserEnumeration(1),
        pnEnumeration(2)
    }
    MAX-ACCESS read-only
    STATUS     current
    DESCRIPTION
        "Return the value of the application publishing
        flags."
    ::= { metaframeWinApplicationEntry 24 }

mfWinApplReadOnly OBJECT-TYPE
    SYNTAX     TruthValue
    MAX-ACCESS read-only
    STATUS     current
    DESCRIPTION
        "Return the value of the application ReadOnly
        flag."
    ::= { metaframeWinApplicationEntry 25 }

metaframeWinFarmTable OBJECT-TYPE
    SYNTAX     SEQUENCE OF MetaFrameWinFarm
    MAX-ACCESS not-accessible
    STATUS     current
    DESCRIPTION
        "Where the MetaFrame farm contains NT servers,
        these extra attributes apply"
    ::= { citrixWmiCitrix 27 }

metaframeWinFarmEntry OBJECT-TYPE
    SYNTAX     MetaFrameWinFarm
    MAX-ACCESS not-accessible
    STATUS     current
    DESCRIPTION
        "None"
    INDEX      { mfWinFarmIndex }
    ::= { metaframeWinFarmTable 1 }

MetaFrameWinFarm ::= SEQUENCE {
    mfWinFarmIndex Integer32,
    mfWinFarmAlternateCachingMethod TruthValue,
    mfWinFarmDCRespondToClientBdcst TruthValue,
    mfWinFarmDegradationBias INTEGER,
    mfWinFarmDisableClientLocalTmEst TruthValue,
    mfWinFarmDiscardRedundantGraphic TruthValue,
    mfWinFarmEnableAutoClientReconn TruthValue,
    mfWinFarmEnableDNSAddrResolution TruthValue,
    mfWinFarmEnableSNMPAgent TruthValue,
    mfWinFarmFarmName DisplayString,
    mfWinFarmICAVideoBufferSize INTEGER,
    mfWinFarmLegacyDisplayCompatMode TruthValue,
    mfWinFarmLegacyServerCompatMode TruthValue,
    mfWinFarmLogAutoReconnectAttempt TruthValue,
    mfWinFarmLogOverLimitDenials TruthValue,
    mfWinFarmMaxConnectionsPerUser INTEGER,
    mfWinFarmNotifyDegradation TruthValue,
    mfWinFarmRASRespondToClientBdcst TruthValue,
    mfWinFarmSNMPDisconnectTrap TruthValue,
    mfWinFarmSNMPLogoffTrap TruthValue,
    mfWinFarmSNMPLogonTrap TruthValue,
    mfWinFarmSNMPThresholdExceedTrap TruthValue,
    mfWinFarmSNMPThresholdValue INTEGER,
    mfWinFarmUseClientLocalTime TruthValue
}

mfWinFarmIndex OBJECT-TYPE
    SYNTAX     Integer32 (1..2147483647)
    MAX-ACCESS read-only
    STATUS     current
    DESCRIPTION
        "The value of this object uniquely identifies the
        instance entry for this class."
    ::= { metaframeWinFarmEntry 1 }

mfWinFarmAlternateCachingMethod OBJECT-TYPE
    SYNTAX     TruthValue
    MAX-ACCESS read-only
    STATUS     current
    DESCRIPTION
        "Return the value of the 'Alternate caching method'
        flag.
        If the 'Use farm settings for ICA display' flag is
        set to TRUE, this flag is ignored. The alternate
        caching method uses the updated caching method
        supported by MetaFrame 1.8 servers."
    ::= { metaframeWinFarmEntry 2 }

mfWinFarmDCRespondToClientBdcst OBJECT-TYPE
    SYNTAX     TruthValue
    MAX-ACCESS read-only
    STATUS     current
    DESCRIPTION
        "Return the value of the 'Data collectors respond
        to ICA client broadcast messages' flag.
        Data collectors for the farm do not respond to ICA
        Client broadcast messages. This sets up the data
        collector for the farm to respond to broadcasts
        from ICA Clients. By default, this option is
        unavailable if MetaFrame 1.8 servers are in the
        farm or other servers in the farm are responding to
        broadcast messages."
    ::= { metaframeWinFarmEntry 3 }

mfWinFarmDegradationBias OBJECT-TYPE
    SYNTAX     INTEGER {
        degradeResolutionFirst(1),
        degradeColorDepthFirst(2)
    }
    MAX-ACCESS read-only
    STATUS     current
    DESCRIPTION
        "Return the value of the ICA display degradation
        bias."
    ::= { metaframeWinFarmEntry 4 }

mfWinFarmDisableClientLocalTmEst OBJECT-TYPE
    SYNTAX     TruthValue
    MAX-ACCESS read-only
    STATUS     current
    DESCRIPTION
        "Return the value of the 'Disable client local time
        estimation' flag.
        Disable local time estimation is available after
        'Per client time zone support' mode is selected. To
        prevent estimation of local time for ICA Clients
        other than the ICA Win32 and WinCE Clients, set
        'Disable local time estimation' mode in the
        Management Console."
    ::= { metaframeWinFarmEntry 5 }

mfWinFarmDiscardRedundantGraphic OBJECT-TYPE
    SYNTAX     TruthValue
    MAX-ACCESS read-only
    STATUS     current
    DESCRIPTION
        "Return the value of the 'discard redundant graphic
        operations' flag.
        Set this flag to TRUE to discard intermediate
        graphic rendering; this improves bandwidth usage.
        For example, if an area of the display generates an
        intermediate image that is immediately replaced by
        another image, the intermediate image is discarded
        and never displayed."
    ::= { metaframeWinFarmEntry 6 }

mfWinFarmEnableAutoClientReconn OBJECT-TYPE
    SYNTAX     TruthValue
    MAX-ACCESS read-only
    STATUS     current
    DESCRIPTION
        "Query the flag to enable auto client reconnect.
        If this flag is TRUE, auto client reconnect to this
        server is enabled. This flag is ignored if the
        value of UseFarmACRSetting is TRUE."
    ::= { metaframeWinFarmEntry 7 }

mfWinFarmEnableDNSAddrResolution OBJECT-TYPE
    SYNTAX     TruthValue
    MAX-ACCESS read-only
    STATUS     current
    DESCRIPTION
        "Query the enable DNS address resolution flag.
        If this flag is set to TRUE, the DNS address
        resolution flag is enabled. If it is FALSE, it is
        disabled. This flag is a farm default value.
        Individual servers may overwrite this setting."
    ::= { metaframeWinFarmEntry 8 }

mfWinFarmEnableSNMPAgent OBJECT-TYPE
    SYNTAX     TruthValue
    MAX-ACCESS read-only
    STATUS     current
    DESCRIPTION
        "Get the value of the 'Enable SNMP agent on all
        servers' flag.
        Enabling the SNMP agent subscribes each server to
        notifications of the selected events, such as
        Session Logon, Session Logoff, Session Disconnect,
        and Session Threshold Exceeded. The SNMP service
        must be running on the servers with this flag set
        to TRUE."
    ::= { metaframeWinFarmEntry 9 }

mfWinFarmFarmName OBJECT-TYPE
    SYNTAX     DisplayString
    MAX-ACCESS read-only
    STATUS     current
    DESCRIPTION
        "Get the name of the farm.
        This property is useful if the server object is
        created using the GetServer() function of a farm
        object. It is also useful when servers from
        different farms are connected to one MFCOM client
        using DCOM. The farm name can also be obtained from
        many other objects. If a multi-farm environment is
        used, this method is useful in identifying a
        server."
    ::= { metaframeWinFarmEntry 10 }

mfWinFarmICAVideoBufferSize OBJECT-TYPE
    SYNTAX     INTEGER
    MAX-ACCESS read-only
    STATUS     current
    DESCRIPTION
        "Get the value of the ICA session video buffer
        size.
        If the 'Use farm settings for ICA display' flag is
        set to TRUE, this flag is ignored. The ICA session
        video buffer size is the maximum memory allowed for
        use as a buffer by each client connection. The
        range is between 150KB and 7500KB, in multiples of
        1K (1024 bytes)."
    ::= { metaframeWinFarmEntry 11 }

mfWinFarmLegacyDisplayCompatMode OBJECT-TYPE
    SYNTAX     TruthValue
    MAX-ACCESS read-only
    STATUS     current
    DESCRIPTION
        "Get the value of the 'Use legacy ICA display
        protocol' flag."
    ::= { metaframeWinFarmEntry 12 }

mfWinFarmLegacyServerCompatMode OBJECT-TYPE
    SYNTAX     TruthValue
    MAX-ACCESS read-only
    STATUS     current
    DESCRIPTION
        "Return the value of the 'Work with MetaFrame 1.8
        servers in the farm' flag.
        Selecting this mode allows MetaFrame 1.8 servers to
        belong to the same farm as MetaFrame XP servers."
    ::= { metaframeWinFarmEntry 13 }

mfWinFarmLogAutoReconnectAttempt OBJECT-TYPE
    SYNTAX     TruthValue
    MAX-ACCESS read-only
    STATUS     current
    DESCRIPTION
        "Query the auto client reconnect attempt logging
        flag.
        If this flag is set to TRUE, the logging of auto
        client reconnect attempt is enabled. If it is
        FALSE, it is disabled. This flag is a farm default
        value. Individual servers may overwrite this
        setting."
    ::= { metaframeWinFarmEntry 14 }

mfWinFarmLogOverLimitDenials OBJECT-TYPE
    SYNTAX     TruthValue
    MAX-ACCESS read-only
    STATUS     current
    DESCRIPTION
        "Query the logging over the connection limit denial
        count flag.
        Set this flag to TRUE or FALSE to turn on or off
        the logging of over the connection limit denial
        count. The count indicates how many times a user's
        logon attempt have been denied once the connection
        limit for that user has reached."
    ::= { metaframeWinFarmEntry 15 }

mfWinFarmMaxConnectionsPerUser OBJECT-TYPE
    SYNTAX     INTEGER
    MAX-ACCESS read-only
    STATUS     current
    DESCRIPTION
        "Query the value of maximum connections per user
        setting.
        The maximum connections per user setting limits the
        number of connections a user may make. This setting
        is a farm default value. Individual users may
        overwrite this value."
    ::= { metaframeWinFarmEntry 16 }

mfWinFarmNotifyDegradation OBJECT-TYPE
    SYNTAX     TruthValue
    MAX-ACCESS read-only
    STATUS     current
    DESCRIPTION
        "Return the value of the 'Notify user of session
        degradation' flag.
        If the 'Use farm settings for ICA display' flag is
        set to TRUE, this flag is ignored. Notifies the
        user of session degradation. A brief explanation is
        displayed when a session is degraded. Session
        degradation can be caused by the session exceeding
        its memory limit, the use of inappropriate
        licenses, or an attempt to connect with an ICA
        Client that is unable to support the requested
        parameters."
    ::= { metaframeWinFarmEntry 17 }

mfWinFarmRASRespondToClientBdcst OBJECT-TYPE
    SYNTAX     TruthValue
    MAX-ACCESS read-only
    STATUS     current
    DESCRIPTION
        "Return the value of the 'RAS servers respond to
        ICA client broadcast message' flag."
    ::= { metaframeWinFarmEntry 18 }

mfWinFarmSNMPDisconnectTrap OBJECT-TYPE
    SYNTAX     TruthValue
    MAX-ACCESS read-only
    STATUS     current
    DESCRIPTION
        "Return the value of the 'Enable SNMP session
        disconnect trap' flag.
        If the 'Use farm?s SNMP settings' flag is set to
        TRUE, this flag is ignored. The SNMP session logon
        trap notifies the server each time a user logs on.
        This is available only if the 'Enable SNMP agent'
        flag is set to TRUE."
    ::= { metaframeWinFarmEntry 19 }

mfWinFarmSNMPLogoffTrap OBJECT-TYPE
    SYNTAX     TruthValue
    MAX-ACCESS read-only
    STATUS     current
    DESCRIPTION
        "Return the value of the 'Enable SNMP session
        logoff trap' flag.
        The SNMP session logoff trap notifies the server
        each time a user logs off. This mode is available
        after 'Enable SNMP agent on all servers' mode is
        selected."
    ::= { metaframeWinFarmEntry 20 }

mfWinFarmSNMPLogonTrap OBJECT-TYPE
    SYNTAX     TruthValue
    MAX-ACCESS read-only
    STATUS     current
    DESCRIPTION
        "Return the value of the 'Enable SNMP session logon
        trap' flag.
        The SNMP session logon trap notifies the server
        each time a user logs on. This mode is available
        after 'Enable SNMP agent on all servers' mode is
        selected."
    ::= { metaframeWinFarmEntry 21 }

mfWinFarmSNMPThresholdExceedTrap OBJECT-TYPE
    SYNTAX     TruthValue
    MAX-ACCESS read-only
    STATUS     current
    DESCRIPTION
        "Return the value of the 'Enable SNMP session
        threshold exceeded trap' flag.
        If the 'Use farm?s SNMP settings' flag is set to
        TRUE, this flag is ignored. The SNMP session
        threshold exceeded trap notifies the server each
        time the number of sessions on a server exceeds the
        specified number of sessions. This is available
        only if the 'Enable SNMP agent' flag is set to
        TRUE."
    ::= { metaframeWinFarmEntry 22 }

mfWinFarmSNMPThresholdValue OBJECT-TYPE
    SYNTAX     INTEGER
    MAX-ACCESS read-only
    STATUS     current
    DESCRIPTION
        "Return an SNMP session threshold value (session
        limit per server).
        If the 'Use farm?s SNMP settings' flag is set to
        TRUE, this flag is ignored. The SNMP session
        threshold value (session limit per server) is the
        upper limit of sessions allowed to connect to each
        server in the farm. This is available only if the
        'Enable SNMP agent' and 'Enable SNMP session
        threshold exceeded trap' flags are set to TRUE."
    ::= { metaframeWinFarmEntry 23 }

mfWinFarmUseClientLocalTime OBJECT-TYPE
    SYNTAX     TruthValue
    MAX-ACCESS read-only
    STATUS     current
    DESCRIPTION
        "Return the value of the 'Use local time of ICA
        Clients' flag.
        The flag allows the use of the local time of ICA
        Clients. All timestamps for all applications are
        based on the client?s time instead of the server?s
        time."
    ::= { metaframeWinFarmEntry 24 }

ciitrixWmiCitrixLicensing OBJECT-IDENTITY
    STATUS     current
    DESCRIPTION
        "Provides WMI information on the Citrix Licensing
        Services"
    ::= { citrixWmi 2 }

citrixGTLicenseTable OBJECT-TYPE
    SYNTAX     SEQUENCE OF CitrixGTLicense
    MAX-ACCESS not-accessible
    STATUS     current
    DESCRIPTION
        "Licensing base class describing the data
        associated with a Citrix License Serial Number"
    ::= { ciitrixWmiCitrixLicensing 1 }

citrixGTLicenseEntry OBJECT-TYPE
    SYNTAX     CitrixGTLicense
    MAX-ACCESS not-accessible
    STATUS     current
    DESCRIPTION
        "None"
    INDEX      { ctxGTLicenseIndex }
    ::= { citrixGTLicenseTable 1 }

CitrixGTLicense ::= SEQUENCE {
    ctxGTLicenseIndex Integer32,
    ctxGTLicenseCount Gauge32,
    ctxGTLicenseExpirationDate DateAndTime,
    ctxGTLicenseLicenseType DisplayString,
    ctxGTLicenseOverdraft Gauge32,
    ctxGTLicensePLD DisplayString,
    ctxGTLicensePLDFullName DisplayString,
    ctxGTLicenseSerialNumber DisplayString,
    ctxGTLicenseSubscriptionDate DateAndTime
}

ctxGTLicenseIndex OBJECT-TYPE
    SYNTAX     Integer32 (1..2147483647)
    MAX-ACCESS read-only
    STATUS     current
    DESCRIPTION
        "The value of this object uniquely identifies the
        instance entry for this class."
    ::= { citrixGTLicenseEntry 1 }

ctxGTLicenseCount OBJECT-TYPE
    SYNTAX     Gauge32
    MAX-ACCESS read-only
    STATUS     current
    DESCRIPTION
        "The number of licenses installed"
    ::= { citrixGTLicenseEntry 2 }

ctxGTLicenseExpirationDate OBJECT-TYPE
    SYNTAX     DateAndTime
    MAX-ACCESS read-only
    STATUS     current
    DESCRIPTION
        "Expiration date in the format of dd-mmm-yyyy"
    ::= { citrixGTLicenseEntry 3 }

ctxGTLicenseLicenseType OBJECT-TYPE
    SYNTAX     DisplayString
    MAX-ACCESS read-only
    STATUS     current
    DESCRIPTION
        "License type - NFR(Not For Resale), Retail,
        Eval(Evaluation), and TP(Technology Preview)"
    ::= { citrixGTLicenseEntry 4 }

ctxGTLicenseOverdraft OBJECT-TYPE
    SYNTAX     Gauge32
    MAX-ACCESS read-only
    STATUS     current
    DESCRIPTION
        "The number of Overdraft for a feature/increment
        line"
    ::= { citrixGTLicenseEntry 5 }

ctxGTLicensePLD OBJECT-TYPE
    SYNTAX     DisplayString
    MAX-ACCESS read-only
    STATUS     current
    DESCRIPTION
        "Product License Descriptor (The Globetrotter
        Feature Name). Every PLD consists of the three
        fields, Product Name, Product Feature and the
        License Model, e.g., MPS_ENT_CCU"
    ::= { citrixGTLicenseEntry 6 }

ctxGTLicensePLDFullName OBJECT-TYPE
    SYNTAX     DisplayString
    MAX-ACCESS read-only
    STATUS     current
    DESCRIPTION
        "The full name of the PLD - <Product Name>|<License
        Model>"
    ::= { citrixGTLicenseEntry 7 }

ctxGTLicenseSerialNumber OBJECT-TYPE
    SYNTAX     DisplayString
    MAX-ACCESS read-only
    STATUS     current
    DESCRIPTION
        "No description"
    ::= { citrixGTLicenseEntry 8 }

ctxGTLicenseSubscriptionDate OBJECT-TYPE
    SYNTAX     DateAndTime
    MAX-ACCESS read-only
    STATUS     current
    DESCRIPTION
        "Used as Citrix Subscription Advantage Date in the
        format of yyyy.mmdd"
    ::= { citrixGTLicenseEntry 9 }

citrixGTLicensePoolTable OBJECT-TYPE
    SYNTAX     SEQUENCE OF CitrixGTLicensePool
    MAX-ACCESS not-accessible
    STATUS     current
    DESCRIPTION
        "License Pools"
    ::= { ciitrixWmiCitrixLicensing 2 }

citrixGTLicensePoolEntry OBJECT-TYPE
    SYNTAX     CitrixGTLicensePool
    MAX-ACCESS not-accessible
    STATUS     current
    DESCRIPTION
        "None"
    INDEX      { ctxGTLicensePoolIndex }
    ::= { citrixGTLicensePoolTable 1 }

CitrixGTLicensePool ::= SEQUENCE {
    ctxGTLicensePoolIndex Integer32,
    ctxGTLicensePoolCount Gauge32,
    ctxGTLicensePoolDUPGROUP Gauge32,
    ctxGTLicensePoolFLOATOK TruthValue,
    ctxGTLicensePoolHOSTBASED Gauge32,
    ctxGTLicensePoolHOSTID DisplayString,
    ctxGTLicensePoolInUseCount Gauge32,
    ctxGTLicensePoolLicenseType DisplayString,
    ctxGTLicensePoolOverdraft Gauge32,
    ctxGTLicensePoolPLATFORMS DisplayString,
    ctxGTLicensePoolPLD DisplayString,
    ctxGTLicensePoolPLDFullName DisplayString,
    ctxGTLicensePoolPooledAvailable Gauge32,
    ctxGTLicensePoolSubscriptionDate DateAndTime,
    ctxGTLicensePoolUSERBASED Gauge32,
    ctxGTLicensePoolVendorString DisplayString
}

ctxGTLicensePoolIndex OBJECT-TYPE
    SYNTAX     Integer32 (1..2147483647)
    MAX-ACCESS read-only
    STATUS     current
    DESCRIPTION
        "The value of this object uniquely identifies the
        instance entry for this class."
    ::= { citrixGTLicensePoolEntry 1 }

ctxGTLicensePoolCount OBJECT-TYPE
    SYNTAX     Gauge32
    MAX-ACCESS read-only
    STATUS     current
    DESCRIPTION
        "Overall number of licenses in license pool"
    ::= { citrixGTLicensePoolEntry 2 }

ctxGTLicensePoolDUPGROUP OBJECT-TYPE
    SYNTAX     Gauge32
    MAX-ACCESS read-only
    STATUS     current
    DESCRIPTION
        "FLEXlm duplicate grouping"
    ::= { citrixGTLicensePoolEntry 3 }

ctxGTLicensePoolFLOATOK OBJECT-TYPE
    SYNTAX     TruthValue
    MAX-ACCESS read-only
    STATUS     current
    DESCRIPTION
        "FLEXlm mobile licensing"
    ::= { citrixGTLicensePoolEntry 4 }

ctxGTLicensePoolHOSTBASED OBJECT-TYPE
    SYNTAX     Gauge32
    MAX-ACCESS read-only
    STATUS     current
    DESCRIPTION
        "FLEXlm host based license"
    ::= { citrixGTLicensePoolEntry 5 }

ctxGTLicensePoolHOSTID OBJECT-TYPE
    SYNTAX     DisplayString
    MAX-ACCESS read-only
    STATUS     current
    DESCRIPTION
        "License server host ID"
    ::= { citrixGTLicensePoolEntry 6 }

ctxGTLicensePoolInUseCount OBJECT-TYPE
    SYNTAX     Gauge32
    MAX-ACCESS read-only
    STATUS     current
    DESCRIPTION
        "The number of licenses pooled in use"
    ::= { citrixGTLicensePoolEntry 7 }

ctxGTLicensePoolLicenseType OBJECT-TYPE
    SYNTAX     DisplayString
    MAX-ACCESS read-only
    STATUS     current
    DESCRIPTION
        "License type - NFR(Not For Resale), Retail,
        Eval(Evaluation), and TP(Technology Preview)"
    ::= { citrixGTLicensePoolEntry 8 }

ctxGTLicensePoolOverdraft OBJECT-TYPE
    SYNTAX     Gauge32
    MAX-ACCESS read-only
    STATUS     current
    DESCRIPTION
        "The number of Overdraft for a a license pool"
    ::= { citrixGTLicensePoolEntry 9 }

ctxGTLicensePoolPLATFORMS OBJECT-TYPE
    SYNTAX     DisplayString
    MAX-ACCESS read-only
    STATUS     current
    DESCRIPTION
        "Platforms a license is restricted to be used on"
    ::= { citrixGTLicensePoolEntry 10 }

ctxGTLicensePoolPLD OBJECT-TYPE
    SYNTAX     DisplayString
    MAX-ACCESS read-only
    STATUS     current
    DESCRIPTION
        "Product License Descriptor (The Globetrotter
        Feature Name). Every PLD consists of the three
        fields, Product Name, Product Feature and the
        License Model, e.g., MPS_ENT_CCU"
    ::= { citrixGTLicensePoolEntry 11 }

ctxGTLicensePoolPLDFullName OBJECT-TYPE
    SYNTAX     DisplayString
    MAX-ACCESS read-only
    STATUS     current
    DESCRIPTION
        "The full name of the PLD - <Product Name>|<License
        Model>"
    ::= { citrixGTLicensePoolEntry 12 }

ctxGTLicensePoolPooledAvailable OBJECT-TYPE
    SYNTAX     Gauge32
    MAX-ACCESS read-only
    STATUS     current
    DESCRIPTION
        "The number of licenses pooled available"
    ::= { citrixGTLicensePoolEntry 13 }

ctxGTLicensePoolSubscriptionDate OBJECT-TYPE
    SYNTAX     DateAndTime
    MAX-ACCESS read-only
    STATUS     current
    DESCRIPTION
        "Used as Citrix Subscription Advantage Date in the
        format of yyyy.mmdd"
    ::= { citrixGTLicensePoolEntry 14 }

ctxGTLicensePoolUSERBASED OBJECT-TYPE
    SYNTAX     Gauge32
    MAX-ACCESS read-only
    STATUS     current
    DESCRIPTION
        "FLEXlm user based license"
    ::= { citrixGTLicensePoolEntry 15 }

ctxGTLicensePoolVendorString OBJECT-TYPE
    SYNTAX     DisplayString
    MAX-ACCESS read-only
    STATUS     current
    DESCRIPTION
        "Vendor string"
    ::= { citrixGTLicensePoolEntry 16 }

citrixGTLicensesInLicensePlTable OBJECT-TYPE
    SYNTAX     SEQUENCE OF CitrixGTLicensesInLicensePool
    MAX-ACCESS not-accessible
    STATUS     current
    DESCRIPTION
        "The set of licenses that make up a license pool"
    ::= { ciitrixWmiCitrixLicensing 3 }

citrixGTLicensesInLicensePlEntry OBJECT-TYPE
    SYNTAX     CitrixGTLicensesInLicensePool
    MAX-ACCESS not-accessible
    STATUS     current
    DESCRIPTION
        "None"
    INDEX      { ctxgtllpIndex }
    ::= { citrixGTLicensesInLicensePlTable 1 }

CitrixGTLicensesInLicensePool ::= SEQUENCE {
    ctxgtllpIndex Integer32,
    ctxgtllpLicense DisplayString,
    ctxgtllpPool DisplayString
}

ctxgtllpIndex OBJECT-TYPE
    SYNTAX     Integer32 (1..2147483647)
    MAX-ACCESS read-only
    STATUS     current
    DESCRIPTION
        "The value of this object uniquely identifies the
        instance entry for this class."
    ::= { citrixGTLicensesInLicensePlEntry 1 }

ctxgtllpLicense OBJECT-TYPE
    SYNTAX     DisplayString
    MAX-ACCESS read-only
    STATUS     current
    DESCRIPTION
        "Return the license number"
    ::= { citrixGTLicensesInLicensePlEntry 2 }

ctxgtllpPool OBJECT-TYPE
    SYNTAX     DisplayString
    MAX-ACCESS read-only
    STATUS     current
    DESCRIPTION
        "Return the vendor string"
    ::= { citrixGTLicensesInLicensePlEntry 3 }

citrixLicenseSchemaVersionTable OBJECT-TYPE
    SYNTAX     SEQUENCE OF CitrixLicensingSchemaVersion
    MAX-ACCESS not-accessible
    STATUS     current
    DESCRIPTION
        "Schema Version. Used to verify that MOF & Dynamic
        provider are in step"
    ::= { ciitrixWmiCitrixLicensing 4 }

citrixLicenseSchemaVersionEntry OBJECT-TYPE
    SYNTAX     CitrixLicensingSchemaVersion
    MAX-ACCESS not-accessible
    STATUS     current
    DESCRIPTION
        "None"
    INDEX      { ctxLicensingSchemaVersionIndex }
    ::= { citrixLicenseSchemaVersionTable 1 }

CitrixLicensingSchemaVersion ::= SEQUENCE {
    ctxLicensingSchemaVersionIndex Integer32,
    ctxLicensingSchemaVersionVersion DisplayString
}

ctxLicensingSchemaVersionIndex OBJECT-TYPE
    SYNTAX     Integer32 (1..2147483647)
    MAX-ACCESS read-only
    STATUS     current
    DESCRIPTION
        "The value of this object uniquely identifies the
        instance entry for this class."
    ::= { citrixLicenseSchemaVersionEntry 1 }

ctxLicensingSchemaVersionVersion OBJECT-TYPE
    SYNTAX     DisplayString
    MAX-ACCESS read-only
    STATUS     current
    DESCRIPTION
        "Return the license schema version"
    ::= { citrixLicenseSchemaVersionEntry 2 }

END
