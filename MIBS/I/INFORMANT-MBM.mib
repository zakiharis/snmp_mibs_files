INFORMANT-MBM DEFINITIONS ::= BEGIN

IMPORTS
    MODULE-IDENTITY, OBJECT-IDENTITY, OBJECT-TYPE, Gauge32, Integer32
        FROM SNMPv2-SMI
    DateAndTime, DisplayString, TruthValue
        FROM SNMPv2-TC
    informant,WtcsDisplayString
        FROM WTCS;

motherBoardMonitor MODULE-IDENTITY
    LAST-UPDATED "200406232039Z"
    ORGANIZATION "Informant Systems, Inc."
    CONTACT-INFO
            "        Garth Williams
                Tel: +1 780 433 7973
             E-mail: garth.williams@wtcs.org"
    DESCRIPTION
            "The MIB module for informant standard entities."
    REVISION      "200406232039Z"
    DESCRIPTION
            "The initial revision of this MIB module."
    ::= { informant 10 }

mbmBusType OBJECT-TYPE
    SYNTAX     DisplayString
    MAX-ACCESS read-only
    STATUS     current
    DESCRIPTION
        "None"
    ::= { motherBoardMonitor 1 }

mbmPath OBJECT-TYPE
    SYNTAX     DisplayString (SIZE (0..255))
    MAX-ACCESS read-only
    STATUS     current
    DESCRIPTION
        "MBM path"
    ::= { motherBoardMonitor 2 }

mbmSmbName OBJECT-TYPE
    SYNTAX     DisplayString (SIZE (0..40))
    MAX-ACCESS read-only
    STATUS     current
    DESCRIPTION
        "Nice name for SMBus"
    ::= { motherBoardMonitor 3 }

mbmSmbType OBJECT-TYPE
    SYNTAX     DisplayString
    MAX-ACCESS read-only
    STATUS     current
    DESCRIPTION
        "None"
    ::= { motherBoardMonitor 4 }

mbmVersion OBJECT-TYPE
    SYNTAX     DisplayString
    MAX-ACCESS read-only
    STATUS     current
    DESCRIPTION
        "MBM Version number"
    ::= { motherBoardMonitor 5 }

mbmSensorTable OBJECT-TYPE
    SYNTAX     SEQUENCE OF MbmSensorEntry
    MAX-ACCESS not-accessible
    STATUS     current
    DESCRIPTION
        "The (conceptual) table listing all the MBM sensors."
    ::= { motherBoardMonitor 6 }

mbmSensorEntry OBJECT-TYPE
    SYNTAX     MbmSensorEntry
    MAX-ACCESS not-accessible
    STATUS     current
    DESCRIPTION
        "An entry (conceptual row) in the mbmSensorTable."
    INDEX      { mbmSensorIndex }
    ::= { mbmSensorTable 1 }

MbmSensorEntry ::= SEQUENCE {
    mbmSensorIndex Integer32,
    mbmSensorName DisplayString,
    mbmSensorType INTEGER,
    mbmSensorReadout Integer32,
    mbmSensorCurrentI Integer32,
    mbmSensorCurrentS DisplayString,
    mbmSensorLowI Integer32,
    mbmSensorLowS DisplayString,
    mbmSensorHighI Integer32,
    mbmSensorHighS DisplayString,
    mbmSensorAlarm1I Integer32,
    mbmSensorAlarm1S DisplayString,
    mbmSensorAlarm2I Integer32,
    mbmSensorAlarm2S DisplayString
}

mbmSensorIndex OBJECT-TYPE
    SYNTAX     Integer32 (1..99)
    MAX-ACCESS read-only
    STATUS     current
    DESCRIPTION
        "Index for this sensor"
    ::= { mbmSensorEntry 1 }

mbmSensorName OBJECT-TYPE
    SYNTAX     DisplayString (SIZE (0..11))
    MAX-ACCESS read-only
    STATUS     current
    DESCRIPTION
        "Name of sensor"
    ::= { mbmSensorEntry 2 }

mbmSensorType OBJECT-TYPE
    SYNTAX     INTEGER {
        stUnknown(0),
        stTemperature(1),
        stVoltage(2),
        stFan(3),
        stMhz(4),
        stPercentage(5)
    }
    MAX-ACCESS read-only
    STATUS     current
    DESCRIPTION
        "Type of sensor"
    ::= { mbmSensorEntry 3 }

mbmSensorReadout OBJECT-TYPE
    SYNTAX     Integer32
    MAX-ACCESS read-only
    STATUS     current
    DESCRIPTION
        "Total number of readout"
    ::= { mbmSensorEntry 4 }

mbmSensorCurrentI OBJECT-TYPE
    SYNTAX     Integer32
    MAX-ACCESS read-only
    STATUS     current
    DESCRIPTION
        "Current value in integer form"
    ::= { mbmSensorEntry 5 }

mbmSensorCurrentS OBJECT-TYPE
    SYNTAX     DisplayString (SIZE (0..50))
    MAX-ACCESS read-only
    STATUS     current
    DESCRIPTION
        "Current value in string form"
    ::= { mbmSensorEntry 6 }

mbmSensorLowI OBJECT-TYPE
    SYNTAX     Integer32
    MAX-ACCESS read-only
    STATUS     current
    DESCRIPTION
        "Lowest readout value in integer form"
    ::= { mbmSensorEntry 7 }

mbmSensorLowS OBJECT-TYPE
    SYNTAX     DisplayString (SIZE (0..50))
    MAX-ACCESS read-only
    STATUS     current
    DESCRIPTION
        "Lowest readout value in string form"
    ::= { mbmSensorEntry 8 }

mbmSensorHighI OBJECT-TYPE
    SYNTAX     Integer32
    MAX-ACCESS read-only
    STATUS     current
    DESCRIPTION
        "Highest readout value in integer form"
    ::= { mbmSensorEntry 9 }

mbmSensorHighS OBJECT-TYPE
    SYNTAX     DisplayString (SIZE (0..50))
    MAX-ACCESS read-only
    STATUS     current
    DESCRIPTION
        "Highest readout value in string form"
    ::= { mbmSensorEntry 10 }

mbmSensorAlarm1I OBJECT-TYPE
    SYNTAX     Integer32
    MAX-ACCESS read-only
    STATUS     current
    DESCRIPTION
        "temp & fan: low alarm; voltage: % off (integer
        form)"
    ::= { mbmSensorEntry 11 }

mbmSensorAlarm1S OBJECT-TYPE
    SYNTAX     DisplayString (SIZE (0..50))
    MAX-ACCESS read-only
    STATUS     current
    DESCRIPTION
        "temp & fan: low alarm; voltage: % off string
        form)"
    ::= { mbmSensorEntry 12 }

mbmSensorAlarm2I OBJECT-TYPE
    SYNTAX     Integer32
    MAX-ACCESS read-only
    STATUS     current
    DESCRIPTION
        "temp: high alarm (integer form)"
    ::= { mbmSensorEntry 13 }

mbmSensorAlarm2S OBJECT-TYPE
    SYNTAX     DisplayString (SIZE (0..50))
    MAX-ACCESS read-only
    STATUS     current
    DESCRIPTION
        "temp: high alarm (string form)"
    ::= { mbmSensorEntry 14 }

END
