IBM-SYSTEM-TRAP-MIB DEFINITIONS ::= BEGIN

IMPORTS
   OBJECT-TYPE
      FROM RFC-1212

   TRAP-TYPE
      FROM RFC-1215

   ibmSystemTrap, ibmSystemMIB,
   Boolean, Uint8, Sint8, Uint16, Sint16, Uint32,
   Sint32, Uint64, Sint64, Real32, Real64, String, Datetime
      FROM IBM-SYSTEM-MIB
   SnmpAdminString
      FROM SNMP-FRAMEWORK-MIB;

ibmSystemTrapTemperature TRAP-TYPE
   ENTERPRISE     ibmSystemMIB
   VARIABLES    {
      ibmSystemTrapTemperatureProviderName,
      ibmSystemTrapTemperatureEventID,
      ibmSystemTrapTemperatureAlertingManagedElement,
      ibmSystemTrapTemperatureSeverity,
      ibmSystemTrapTemperatureDescription,
      ibmSystemTrapTemperatureTimeStamp
   }
   DESCRIPTION    "This event is sent when the state of a system's temperature sensor changes
                   with respect to a manufacturer-defined and/or user-defined threshold."
   REFERENCE      "IBMPSG_Temperature"
::= 2

ibmSystemTrapTemperatureBindings OBJECT IDENTIFIER ::= { ibmSystemTrap 2 }

ibmSystemTrapTemperatureProviderName OBJECT-TYPE
   SYNTAX         String
   ACCESS         read-only
   STATUS         mandatory
   DESCRIPTION    "The name of the CIM Provider that monitors this device"
   REFERENCE      "IBMPSG_Temperature.ProviderName"
::= { ibmSystemTrapTemperatureBindings 1 }

ibmSystemTrapTemperatureEventID OBJECT-TYPE
   SYNTAX         String
   ACCESS         read-only
   STATUS         mandatory
   DESCRIPTION    "A unique EventID that identifies this trap" 
   REFERENCE      "IBMPSG_Temperature.EventID"
::= { ibmSystemTrapTemperatureBindings 2 }

ibmSystemTrapTemperatureAlertingManagedElement OBJECT-TYPE
   SYNTAX         String
   ACCESS         read-only
   STATUS         mandatory
   DESCRIPTION    "A unique string that identifies the monitored device"
   REFERENCE      "IBMPSG_Temperature.AlertingManagedElement"
::= { ibmSystemTrapTemperatureBindings 3 }

ibmSystemTrapTemperatureSeverity OBJECT-TYPE
   SYNTAX         Uint16
   ACCESS         read-only
   STATUS         mandatory
   DESCRIPTION    "0=Normall -- The temperatureis within normal thresholds
                   1=Warning -- The temperature has exceeded a user-defined or manufacturer-defined warning level thresold
                   2=Critical -- The temperature has exceeded a user-defined or manufacturer-defined critical threshold"
   REFERENCE      "IBMPSG_Temperature.Severity"
::= { ibmSystemTrapTemperatureBindings 4 }

ibmSystemTrapTemperatureDescription OBJECT-TYPE
   SYNTAX         SnmpAdminString
   ACCESS         read-only
   STATUS         mandatory
   DESCRIPTION    "The Event text of the trap"
   REFERENCE      "IBMPSG_Temperature.Description"
::= { ibmSystemTrapTemperatureBindings 5 }

ibmSystemTrapTemperatureTimeStamp OBJECT-TYPE
   SYNTAX         Datetime
   ACCESS         read-only
   STATUS         mandatory
   DESCRIPTION    "The time that the trap occurred"
   REFERENCE      "IBMPSG_Temperature.TimeStamp"
::= { ibmSystemTrapTemperatureBindings 6 }

ibmSystemTrapVoltage TRAP-TYPE
   ENTERPRISE     ibmSystemMIB
   VARIABLES    {
      ibmSystemTrapVoltageProviderName,
      ibmSystemTrapVoltageEventID,
      ibmSystemTrapVoltageAlertingManagedElement,
      ibmSystemTrapVoltageSeverity,
      ibmSystemTrapVoltageDescription,
      ibmSystemTrapVoltageTimeStamp
   }
   DESCRIPTION    "This event is sent when the state of a system's voltage sensor changes
                   with respect to a manufacturer-defined threshold."
   REFERENCE      "IBMPSG_Voltage"
::= 3

ibmSystemTrapVoltageBindings OBJECT IDENTIFIER ::= { ibmSystemTrap 3 }

ibmSystemTrapVoltageProviderName OBJECT-TYPE
   SYNTAX         String
   ACCESS         read-only
   STATUS         mandatory
   DESCRIPTION    "The name of the CIM Provider that monitors this device"
   REFERENCE      "IBMPSG_Voltage.ProviderName"
::= { ibmSystemTrapVoltageBindings 1 }

ibmSystemTrapVoltageEventID OBJECT-TYPE
   SYNTAX         String
   ACCESS         read-only
   STATUS         mandatory
   DESCRIPTION    "A unique EventID that identifies this trap"
   REFERENCE      "IBMPSG_Voltage.EventID"
::= { ibmSystemTrapVoltageBindings 2 }

ibmSystemTrapVoltageAlertingManagedElement OBJECT-TYPE
   SYNTAX         String
   ACCESS         read-only
   STATUS         mandatory
   DESCRIPTION    "A unique string that identifies the monitored device"
   REFERENCE      "IBMPSG_Voltage.AlertingManagedElement"
::= { ibmSystemTrapVoltageBindings 3 }

ibmSystemTrapVoltageSeverity OBJECT-TYPE
   SYNTAX         Uint16
   ACCESS         read-only
   STATUS         mandatory
   DESCRIPTION    "0=Normal -- The voltages is within normal thresholds
                   1=Warning -- The voltage has exceeded a manufacturer-defined warning level thresold
                   2=Critical -- The voltage has exceeded a manufacturer-defined critical threshold"
   REFERENCE      "IBMPSG_Voltage.Severity"
::= { ibmSystemTrapVoltageBindings 4 }

ibmSystemTrapVoltageDescription OBJECT-TYPE
   SYNTAX         SnmpAdminString
   ACCESS         read-only
   STATUS         mandatory
   DESCRIPTION    "The Event text of the trap"
   REFERENCE      "IBMPSG_Voltage.Description"
::= { ibmSystemTrapVoltageBindings 5 }

ibmSystemTrapVoltageTimeStamp OBJECT-TYPE
   SYNTAX         Datetime
   ACCESS         read-only
   STATUS         mandatory
   DESCRIPTION    "The time that the trap occurred"
   REFERENCE      "IBMPSG_Voltage.TimeStamp"
::= { ibmSystemTrapVoltageBindings 6 }

ibmSystemTrapChassis TRAP-TYPE
   ENTERPRISE     ibmSystemMIB
   VARIABLES    {
      ibmSystemTrapChassisProviderName,
      ibmSystemTrapChassisEventID,
      ibmSystemTrapChassisAlertingManagedElement,
      ibmSystemTrapChassisSeverity,
      ibmSystemTrapChassisDescription,
      ibmSystemTrapChassisTimeStamp
   }
   DESCRIPTION    "This event is sent when the state of a system's chassis has changed."
   REFERENCE      "IBMPSG_Chassis"
::= 4

ibmSystemTrapChassisBindings OBJECT IDENTIFIER ::= { ibmSystemTrap 4 }

ibmSystemTrapChassisProviderName OBJECT-TYPE
   SYNTAX         String
   ACCESS         read-only
   STATUS         mandatory
   DESCRIPTION    "The name of the CIM Provider that monitors this device"
   REFERENCE      "IBMPSG_Chassis.ProviderName"
::= { ibmSystemTrapChassisBindings 1 }

ibmSystemTrapChassisEventID OBJECT-TYPE
   SYNTAX         String
   ACCESS         read-only
   STATUS         mandatory
   DESCRIPTION    "A unique EventID that identifies this trap"
   REFERENCE      "IBMPSG_Chassis.EventID"
::= { ibmSystemTrapChassisBindings 2 }

ibmSystemTrapChassisAlertingManagedElement OBJECT-TYPE
   SYNTAX         String
   ACCESS         read-only
   STATUS         mandatory
   DESCRIPTION    "A unique string that identifies the monitored device"
   REFERENCE      "IBMPSG_Chassis.AlertingManagedElement"
::= { ibmSystemTrapChassisBindings 3 }

ibmSystemTrapChassisSeverity OBJECT-TYPE
   SYNTAX         Uint16
   ACCESS         read-only
   STATUS         mandatory
   DESCRIPTION    "0=Normal -- The systems's cover is closed
                   2=Critical -- The system's cover has been removed"
   REFERENCE      "IBMPSG_Chassis.Severity"
::= { ibmSystemTrapChassisBindings 4 }

ibmSystemTrapChassisDescription OBJECT-TYPE
   SYNTAX         SnmpAdminString
   ACCESS         read-only
   STATUS         mandatory
   DESCRIPTION    "The Event text of the trap"
   REFERENCE      "IBMPSG_Chassis.Description"
::= { ibmSystemTrapChassisBindings 5 }

ibmSystemTrapChassisTimeStamp OBJECT-TYPE
   SYNTAX         Datetime
   ACCESS         read-only
   STATUS         mandatory
   DESCRIPTION    "The time that the trap occurred"
   REFERENCE      "IBMPSG_Chassis.TimeStamp"
::= { ibmSystemTrapChassisBindings 6 }

ibmSystemTrapFan TRAP-TYPE
   ENTERPRISE     ibmSystemMIB
   VARIABLES    {
      ibmSystemTrapFanProviderName,
      ibmSystemTrapFanEventID,
      ibmSystemTrapFanAlertingManagedElement,
      ibmSystemTrapFanSeverity,
      ibmSystemTrapFanDescription,
      ibmSystemTrapFanTimeStamp
   }
   DESCRIPTION    "This event is sent when state of a system's fan has changed with respect to
                   manufacturer-defined rpm values."
   REFERENCE      "IBMPSG_Fan"
::=  5

ibmSystemTrapFanBindings OBJECT IDENTIFIER ::= { ibmSystemTrap 5 }

ibmSystemTrapFanProviderName OBJECT-TYPE
   SYNTAX         String
   ACCESS         read-only
   STATUS         mandatory
   DESCRIPTION    "The name of the CIM Provider that monitors this device"
   REFERENCE      "IBMPSG_Fan.ProviderName"
::= { ibmSystemTrapFanBindings 1 }

ibmSystemTrapFanEventID OBJECT-TYPE
   SYNTAX         String
   ACCESS         read-only
   STATUS         mandatory
   DESCRIPTION    "A unique EventID that identifies this trap"
   REFERENCE      "IBMPSG_Fan.EventID"
::= { ibmSystemTrapFanBindings 2 }

ibmSystemTrapFanAlertingManagedElement OBJECT-TYPE
   SYNTAX         String
   ACCESS         read-only
   STATUS         mandatory
   DESCRIPTION    "A unique string that identifies the monitored device"
   REFERENCE      "IBMPSG_Fan.AlertingManagedElement"
::= { ibmSystemTrapFanBindings 3 }

ibmSystemTrapFanSeverity OBJECT-TYPE
   SYNTAX         Uint16
   ACCESS         read-only
   STATUS         mandatory
   DESCRIPTION    "0=Normal -- The fan is functioning
                   1=Warning -- The fan is operating in a degraded state
                   2=Critical -- The fan has stopped."
   REFERENCE      "IBMPSG_Fan.Severity"
::= { ibmSystemTrapFanBindings 4 }

ibmSystemTrapFanDescription OBJECT-TYPE
   SYNTAX         SnmpAdminString
   ACCESS         read-only
   STATUS         mandatory
   DESCRIPTION    "The Event text of the trap"
   REFERENCE      "IBMPSG_Fan.Description"
::= { ibmSystemTrapFanBindings 5 }

ibmSystemTrapFanTimeStamp OBJECT-TYPE
   SYNTAX         Datetime
   ACCESS         read-only
   STATUS         mandatory
   DESCRIPTION    "The time that the trap occurred"
   REFERENCE      "IBMPSG_Fan.TimeStamp"
::= { ibmSystemTrapFanBindings 6 }

ibmSystemTrapStorage TRAP-TYPE
   ENTERPRISE     ibmSystemMIB
   VARIABLES    {
      ibmSystemTrapStorageProviderName,
      ibmSystemTrapStorageEventID,
      ibmSystemTrapStorageAlertingManagedElement,
      ibmSystemTrapStorageSeverity,
      ibmSystemTrapStorageDescription,
      ibmSystemTrapStorageTimeStamp
   }
   DESCRIPTION    "On systems with no Remote Supervisor Adapter, this event is sent when the 
                   state of a system's hard drive space has changed with respect to user-defined 
                   levels of percentage hard drive space remaining.
                   On systems with a Remote Supervisor Adapter, this event is sent when the
                   system has experienced a DASD controller failure."
   REFERENCE      "IBMPSG_Storage"
::= 7

ibmSystemTrapStorageBindings OBJECT IDENTIFIER ::= { ibmSystemTrap 7 }

ibmSystemTrapStorageProviderName OBJECT-TYPE
   SYNTAX         String
   ACCESS         read-only
   STATUS         mandatory
   DESCRIPTION    "The name of the CIM Provider that monitors this device"
   REFERENCE      "IBMPSG_Storage.ProviderName"
::= { ibmSystemTrapStorageBindings 1 }

ibmSystemTrapStorageEventID OBJECT-TYPE
   SYNTAX         String
   ACCESS         read-only
   STATUS         mandatory
   DESCRIPTION    "A unique EventID that identifies this trap"
   REFERENCE      "IBMPSG_Storage.EventID"
::= { ibmSystemTrapStorageBindings 2 }

ibmSystemTrapStorageAlertingManagedElement OBJECT-TYPE
   SYNTAX         String
   ACCESS         read-only
   STATUS         mandatory
   DESCRIPTION    "A unique string that identifies the monitored device"
   REFERENCE      "IBMPSG_Storage.AlertingManagedElement"
::= { ibmSystemTrapStorageBindings 3 }

ibmSystemTrapStorageSeverity OBJECT-TYPE
   SYNTAX         Uint16
   ACCESS         read-only
   STATUS         mandatory
   DESCRIPTION    "0=Normal --Percentage hard drive space remaining is above thresholds
                   1=Warning -- Percentage hard drive space remaining has fallen below user-defined Warning level threshold.
                   2=Critical -- Percentage hard drive space remaining has fallen below user-defined Critical level threshold.
                   2=Critical -- On systems with Remote Supervisor Adapter, DASD Controller failure."
   REFERENCE      "IBMPSG_Storage.Severity"
::= { ibmSystemTrapStorageBindings 4 }

ibmSystemTrapStorageDescription OBJECT-TYPE
   SYNTAX         SnmpAdminString
   ACCESS         read-only
   STATUS         mandatory
   DESCRIPTION    "The Event text of the trap"
   REFERENCE      "IBMPSG_Storage.Description"
::= { ibmSystemTrapStorageBindings 5 }

ibmSystemTrapStorageTimeStamp OBJECT-TYPE
   SYNTAX         Datetime
   ACCESS         read-only
   STATUS         mandatory
   DESCRIPTION    "The time that the trap occurred"
   REFERENCE      "IBMPSG_Storage.TimeStamp"
::= { ibmSystemTrapStorageBindings 6 }

ibmSystemTrapSMART TRAP-TYPE
   ENTERPRISE     ibmSystemMIB
   VARIABLES    {
      ibmSystemTrapSMARTProviderName,
      ibmSystemTrapSMARTEventID,
      ibmSystemTrapSMARTAlertingManagedElement,
      ibmSystemTrapSMARTSeverity,
      ibmSystemTrapSMARTDescription,
      ibmSystemTrapSMARTTimeStamp
   }
   DESCRIPTION    "This event is sent when the state of an IDE or SCSI hard drive that complies with the
                  Self-Monitoring, Analysis, and Reporting Technology changes with respect to
                  its availability."
   REFERENCE      "IBMPSG_SMART"
::= 9

ibmSystemTrapSMARTBindings OBJECT IDENTIFIER ::= { ibmSystemTrap 9 }

ibmSystemTrapSMARTProviderName OBJECT-TYPE
   SYNTAX         String
   ACCESS         read-only
   STATUS         mandatory
   DESCRIPTION    "The name of the CIM Provider that monitors this device"
   REFERENCE      "IBMPSG_SMART.ProviderName"
::= { ibmSystemTrapSMARTBindings 1 }

ibmSystemTrapSMARTEventID OBJECT-TYPE
   SYNTAX         String
   ACCESS         read-only
   STATUS         mandatory
   DESCRIPTION    "A unique EventID that identifies this trap"
   REFERENCE      "IBMPSG_SMART.EventID"
::= { ibmSystemTrapSMARTBindings 2 }

ibmSystemTrapSMARTAlertingManagedElement OBJECT-TYPE
   SYNTAX         String
   ACCESS         read-only
   STATUS         mandatory
   DESCRIPTION    "A unique string that identifies the monitored device"
   REFERENCE      "IBMPSG_SMART.AlertingManagedElement"
::= { ibmSystemTrapSMARTBindings 3 }

ibmSystemTrapSMARTSeverity OBJECT-TYPE
   SYNTAX         Uint16
   ACCESS         read-only
   STATUS         mandatory
   DESCRIPTION    "0=Normal -- The hard drive is not predicting a failure
                   2=Critical - The hard drive is experiencing an imminent failure."
   REFERENCE      "IBMPSG_SMART.Severity"
::= { ibmSystemTrapSMARTBindings 4 }

ibmSystemTrapSMARTDescription OBJECT-TYPE
   SYNTAX         SnmpAdminString
   ACCESS         read-only
   STATUS         mandatory
   DESCRIPTION    "The Event text of the trap"
   REFERENCE      "IBMPSG_SMART.Description"
::= { ibmSystemTrapSMARTBindings 5 }

ibmSystemTrapSMARTTimeStamp OBJECT-TYPE
   SYNTAX         Datetime
   ACCESS         read-only
   STATUS         mandatory
   DESCRIPTION    "The time that the trap occurred"
   REFERENCE      "IBMPSG_SMART.TimeStamp"
::= { ibmSystemTrapSMARTBindings 6 }

ibmSystemTrapLeaseExpiration TRAP-TYPE
   ENTERPRISE     ibmSystemMIB
   VARIABLES    {
      ibmSystemTrapLeaseExpirationProviderName,
      ibmSystemTrapLeaseExpirationEventID,
      ibmSystemTrapLeaseExpirationAlertingManagedElement,
      ibmSystemTrapLeaseExpirationSeverity,
      ibmSystemTrapLeaseExpirationDescription,
      ibmSystemTrapLeaseExpirationTimeStamp
   }
   DESCRIPTION    "This event is sent when a system's Lease Expiration date has been reached
                   with respect to the value configured for the date in the Asset ID tool."
   REFERENCE      "IBMPSG_LeaseExpiration"
::= 13

ibmSystemTrapLeaseExpirationBindings OBJECT IDENTIFIER ::= { ibmSystemTrap 13 }

ibmSystemTrapLeaseExpirationProviderName OBJECT-TYPE
   SYNTAX         String
   ACCESS         read-only
   STATUS         mandatory
   DESCRIPTION    "The name of the CIM Provider that monitors this device"
   REFERENCE      "IBMPSG_LeaseExpiration.ProviderName"
::= { ibmSystemTrapLeaseExpirationBindings 1 }

ibmSystemTrapLeaseExpirationEventID OBJECT-TYPE
   SYNTAX         String
   ACCESS         read-only
   STATUS         mandatory
   DESCRIPTION    "A unique EventID that identifies this trap"
   REFERENCE      "IBMPSG_LeaseExpiration.EventID"
::= { ibmSystemTrapLeaseExpirationBindings 2 }

ibmSystemTrapLeaseExpirationAlertingManagedElement OBJECT-TYPE
   SYNTAX         String
   ACCESS         read-only
   STATUS         mandatory
   DESCRIPTION    "A unique string that identifies the monitored device"
   REFERENCE      "IBMPSG_LeaseExpiration.AlertingManagedElement"
::= { ibmSystemTrapLeaseExpirationBindings 3 }

ibmSystemTrapLeaseExpirationSeverity OBJECT-TYPE
   SYNTAX         Uint16
   ACCESS         read-only
   STATUS         mandatory
   DESCRIPTION    "0=Normal -- The systems's lease has not expired
                   1=Warning -- The system's lease has expired."
   REFERENCE      "IBMPSG_LeaseExpiration.Severity"
::= { ibmSystemTrapLeaseExpirationBindings 4 }

ibmSystemTrapLeaseExpirationDescription OBJECT-TYPE
   SYNTAX         SnmpAdminString
   ACCESS         read-only
   STATUS         mandatory
   DESCRIPTION    "The Event text of the trap"
   REFERENCE      "IBMPSG_LeaseExpiration.Description"
::= { ibmSystemTrapLeaseExpirationBindings 5 }

ibmSystemTrapLeaseExpirationTimeStamp OBJECT-TYPE
   SYNTAX         Datetime
   ACCESS         read-only
   STATUS         mandatory
   DESCRIPTION    "The time that the trap occurred"
   REFERENCE      "IBMPSG_LeaseExpiration.TimeStamp"
::= { ibmSystemTrapLeaseExpirationBindings 6 }

ibmSystemTrapWarrantyExpiration TRAP-TYPE
   ENTERPRISE     ibmSystemMIB
   VARIABLES    {
      ibmSystemTrapWarrantyExpirationProviderName,
      ibmSystemTrapWarrantyExpirationEventID,
      ibmSystemTrapWarrantyExpirationAlertingManagedElement,
      ibmSystemTrapWarrantyExpirationSeverity,
      ibmSystemTrapWarrantyExpirationDescription,
      ibmSystemTrapWarrantyExpirationTimeStamp
   }
   DESCRIPTION    "This event is sent when a system's Warranty Expiration date has been reached
                   with respect to the value configured for the date in the Asset ID tool."
   REFERENCE      "IBMPSG_WarrantyExpiration"
::= 14

ibmSystemTrapWarrantyExpirationBindings OBJECT IDENTIFIER ::= { ibmSystemTrap 14 }

ibmSystemTrapWarrantyExpirationProviderName OBJECT-TYPE
   SYNTAX         String
   ACCESS         read-only
   STATUS         mandatory
   DESCRIPTION    "The name of the CIM Provider that monitors this device"
   REFERENCE      "IBMPSG_WarrantyExpiration.ProviderName"
::= { ibmSystemTrapWarrantyExpirationBindings 1 }

ibmSystemTrapWarrantyExpirationEventID OBJECT-TYPE
   SYNTAX         String
   ACCESS         read-only
   STATUS         mandatory
   DESCRIPTION    "A unique EventID that identifies this trap"
   REFERENCE      "IBMPSG_WarrantyExpiration.EventID"
::= { ibmSystemTrapWarrantyExpirationBindings 2 }

ibmSystemTrapWarrantyExpirationAlertingManagedElement OBJECT-TYPE
   SYNTAX         String
   ACCESS         read-only
   STATUS         mandatory
   DESCRIPTION    "A unique string that identifies the monitored device"
   REFERENCE      "IBMPSG_WarrantyExpiration.AlertingManagedElement"
::= { ibmSystemTrapWarrantyExpirationBindings 3 }

ibmSystemTrapWarrantyExpirationSeverity OBJECT-TYPE
   SYNTAX         Uint16
   ACCESS         read-only
   STATUS         mandatory
   DESCRIPTION    "0=Normal -- The system's warranty has not expired
                   1=Warning -- The system's warranty has expired."
   REFERENCE      "IBMPSG_WarrantyExpiration.Severity"
::= { ibmSystemTrapWarrantyExpirationBindings 4 }

ibmSystemTrapWarrantyExpirationDescription OBJECT-TYPE
   SYNTAX         SnmpAdminString
   ACCESS         read-only
   STATUS         mandatory
   DESCRIPTION    "The Event text of the trap"
   REFERENCE      "IBMPSG_WarrantyExpiration.Description"
::= { ibmSystemTrapWarrantyExpirationBindings 5 }

ibmSystemTrapWarrantyExpirationTimeStamp OBJECT-TYPE
   SYNTAX         Datetime
   ACCESS         read-only
   STATUS         mandatory
   DESCRIPTION    "The time that the trap occurred"
   REFERENCE      "IBMPSG_WarrantyExpiration.TimeStamp"
::= { ibmSystemTrapWarrantyExpirationBindings 6 }

ibmSystemTrapRedundantNIC TRAP-TYPE
   ENTERPRISE     ibmSystemMIB
   VARIABLES    {
      ibmSystemTrapRedundantNICProviderName,
      ibmSystemTrapRedundantNICEventID,
      ibmSystemTrapRedundantNICAlertingManagedElement,
      ibmSystemTrapRedundantNICSeverity,
      ibmSystemTrapRedundantNICDescription,
      ibmSystemTrapRedundantNICTimeStamp
   }
   DESCRIPTION	"This event is sent when the state of a system's NIC changes state with
                   respect to redundancy, but due to a limitation of the capabilities of
                   the NIC, a determination could not be made between a switchover and
                   a switchback."
   REFERENCE	"IBMPSG_RedundantNIC"
::= 15

ibmSystemTrapRedundantNICBindings OBJECT IDENTIFIER ::= { ibmSystemTrap 15 }

ibmSystemTrapRedundantNICProviderName OBJECT-TYPE
   SYNTAX         String
   ACCESS         read-only
   STATUS         mandatory
   DESCRIPTION    "The name of the CIM Provider that monitors this device"
   REFERENCE	  "IBMPSG_RedundantNIC.ProviderName"
::= { ibmSystemTrapRedundantNICBindings 1 }

ibmSystemTrapRedundantNICEventID OBJECT-TYPE
   SYNTAX         String
   ACCESS         read-only
   STATUS         mandatory
   DESCRIPTION    "A unique EventID that identifies this trap"
   REFERENCE	  "IBMPSG_RedundantNIC.EventID"
::= { ibmSystemTrapRedundantNICBindings 2 }

ibmSystemTrapRedundantNICAlertingManagedElement OBJECT-TYPE
   SYNTAX         String
   ACCESS         read-only
   STATUS         mandatory
   DESCRIPTION    "A unique string that identifies the monitored device"
   REFERENCE	  "IBMPSG_RedundantNIC.AlertingManagedElement"
::= { ibmSystemTrapRedundantNICBindings 3 }

ibmSystemTrapRedundantNICSeverity OBJECT-TYPE
   SYNTAX         Uint16
   ACCESS         read-only
   STATUS         mandatory
   DESCRIPTION    "0=Normal -- Redundant NICs are operating.
                   1=Warning -- A redundant NIC event occurred."
   REFERENCE	  "IBMPSG_RedundantNIC.Severity"
::= { ibmSystemTrapRedundantNICBindings 4 }

ibmSystemTrapRedundantNICDescription OBJECT-TYPE
   SYNTAX         SnmpAdminString
   ACCESS         read-only
   STATUS         mandatory
   DESCRIPTION    "The Event text of the trap"
   REFERENCE	  "IBMPSG_RedundantNIC.Description"
::= { ibmSystemTrapRedundantNICBindings 5 }

ibmSystemTrapRedundantNICTimeStamp OBJECT-TYPE
   SYNTAX         Datetime
   ACCESS         read-only
   STATUS         mandatory
   DESCRIPTION    "The time that the trap occurred"
   REFERENCE	  "IBMPSG_RedundantNIC.TimeStamp"
::= { ibmSystemTrapRedundantNICBindings 6 }

ibmSystemTrapRedundantNICSwitchover TRAP-TYPE
   ENTERPRISE     ibmSystemMIB
   VARIABLES    {
      ibmSystemTrapRedundantNICSwitchoverProviderName,
      ibmSystemTrapRedundantNICSwitchoverEventID,
      ibmSystemTrapRedundantNICSwitchoverAlertingManagedElement,
      ibmSystemTrapRedundantNICSwitchoverSeverity,
      ibmSystemTrapRedundantNICSwitchoverDescription,
      ibmSystemTrapRedundantNICSwitchoverTimeStamp
   }
   DESCRIPTION	"This event is sent when the active NIC in a system changes by failing over
                   to a redundant NIC."
   REFERENCE	"IBMPSG_RedundantNICSwitchover"
::= 16

ibmSystemTrapRedundantNICSwitchoverBindings OBJECT IDENTIFIER ::= { ibmSystemTrap 16 }

ibmSystemTrapRedundantNICSwitchoverProviderName OBJECT-TYPE
   SYNTAX         String
   ACCESS         read-only
   STATUS         mandatory
   DESCRIPTION    "The name of the CIM Provider that monitors this device"
   REFERENCE	  "IBMPSG_RedundantNIC.ProviderName"
::= { ibmSystemTrapRedundantNICSwitchoverBindings 1 }

ibmSystemTrapRedundantNICSwitchoverEventID OBJECT-TYPE
   SYNTAX         String
   ACCESS         read-only
   STATUS         mandatory
   DESCRIPTION    "A unique EventID that identifies this trap"
   REFERENCE	  "IBMPSG_RedundantNICSwitchover.EventID"
::= { ibmSystemTrapRedundantNICSwitchoverBindings 2 }

ibmSystemTrapRedundantNICSwitchoverAlertingManagedElement OBJECT-TYPE
   SYNTAX         String
   ACCESS         read-only
   STATUS         mandatory
   DESCRIPTION    "A unique string that identifies the monitored device"
   REFERENCE	  "IBMPSG_RedundantNICSwitchover.AlertingManagedElement"
::= { ibmSystemTrapRedundantNICSwitchoverBindings 3 }

ibmSystemTrapRedundantNICSwitchoverSeverity OBJECT-TYPE
   SYNTAX         Uint16
   ACCESS         read-only
   STATUS         mandatory
   DESCRIPTION    "1=Warning -- A failing NIC switched over to a redundant NIC."
   REFERENCE	  "IBMPSG_RedundantNICSwitchover.Severity"
::= { ibmSystemTrapRedundantNICSwitchoverBindings 4 }

ibmSystemTrapRedundantNICSwitchoverDescription OBJECT-TYPE
   SYNTAX         SnmpAdminString
   ACCESS         read-only
   STATUS         mandatory
   DESCRIPTION    "The Event text of the trap"
   REFERENCE	  "IBMPSG_RedundantNICSwitchover.Description"
::= { ibmSystemTrapRedundantNICSwitchoverBindings 5 }

ibmSystemTrapRedundantNICSwitchoverTimeStamp OBJECT-TYPE
   SYNTAX         Datetime
   ACCESS         read-only
   STATUS         mandatory
   DESCRIPTION    "The time that the trap occurred"
   REFERENCE	  "IBMPSG_RedundantNICSwitchover.TimeStamp"
::= { ibmSystemTrapRedundantNICSwitchoverBindings 6 }

ibmSystemTrapRedundantNICSwitchback TRAP-TYPE
   ENTERPRISE     ibmSystemMIB
   VARIABLES    {
      ibmSystemTrapRedundantNICSwitchbackProviderName,
      ibmSystemTrapRedundantNICSwitchbackEventID,
      ibmSystemTrapRedundantNICSwitchbackAlertingManagedElement,
      ibmSystemTrapRedundantNICSwitchbackSeverity,
      ibmSystemTrapRedundantNICSwitchbackDescription,
      ibmSystemTrapRedundantNICSwitchbackTimeStamp
   }
   DESCRIPTION	"This event is sent when the active NIC in a system changes due
                   to a recovery from a redundant NIC."
   REFERENCE	"IBMPSG_RedundantNICSwitchback"
::= 17

ibmSystemTrapRedundantNICSwitchbackBindings OBJECT IDENTIFIER ::= { ibmSystemTrap 17 }

ibmSystemTrapRedundantNICSwitchbackProviderName OBJECT-TYPE
   SYNTAX         String
   ACCESS         read-only
   STATUS         mandatory
   DESCRIPTION    "The name of the CIM Provider that monitors this device"
   REFERENCE	  "IBMPSG_RedundantNICSwitchback.ProviderName"
::= { ibmSystemTrapRedundantNICSwitchbackBindings 1 }

ibmSystemTrapRedundantNICSwitchbackEventID OBJECT-TYPE
   SYNTAX         String
   ACCESS         read-only
   STATUS         mandatory
   DESCRIPTION    "A unique EventID that identifies this trap"
   REFERENCE	  "IBMPSG_RedundantNICSwitchback.EventID"
::= { ibmSystemTrapRedundantNICSwitchbackBindings 2 }

ibmSystemTrapRedundantNICSwitchbackAlertingManagedElement OBJECT-TYPE
   SYNTAX         String
   ACCESS         read-only
   STATUS         mandatory
   DESCRIPTION    "A unique string that identifies the monitored device"
   REFERENCE	  "IBMPSG_RedundantNICSwitchback.AlertingManagedElement"
::= { ibmSystemTrapRedundantNICSwitchbackBindings 3 }

ibmSystemTrapRedundantNICSwitchbackSeverity OBJECT-TYPE
   SYNTAX         Uint16
   ACCESS         read-only
   STATUS         mandatory
   DESCRIPTION    "1=Warning -- The system's NIC has recovered and switched back, re-instating redundancy."
   REFERENCE	  "IBMPSG_RedundantNICSwitchback.Severity"
::= { ibmSystemTrapRedundantNICSwitchbackBindings 4 }

ibmSystemTrapRedundantNICSwitchbackDescription OBJECT-TYPE
   SYNTAX         SnmpAdminString
   ACCESS         read-only
   STATUS         mandatory
   DESCRIPTION    "The Event text of the trap"
   REFERENCE	  "IBMPSG_RedundantNICSwitchback.Description"
::= { ibmSystemTrapRedundantNICSwitchbackBindings 5 }

ibmSystemTrapRedundantNICSwitchbackTimeStamp OBJECT-TYPE
   SYNTAX         Datetime
   ACCESS         read-only
   STATUS         mandatory
   DESCRIPTION    "The time that the trap occurred"
   REFERENCE	  "IBMPSG_RedundantNICSwitchback.TimeStamp"
::= { ibmSystemTrapRedundantNICSwitchbackBindings 6 }

ibmSystemTrapProcessorPF TRAP-TYPE
   ENTERPRISE     ibmSystemMIB
   VARIABLES    {
      ibmSystemTrapProcessorPFProviderName,
      ibmSystemTrapProcessorPFEventID,
      ibmSystemTrapProcessorPFAlertingManagedElement,      
      ibmSystemTrapProcessorPFSeverity,
      ibmSystemTrapProcessorPFDescription,
      ibmSystemTrapProcessorPFTimeStamp
   }
   DESCRIPTION	"This event is sent when a system's processor changes state with respect to availability."
   REFERENCE	"IBMPSG_ProcessorPF"
::= 18

ibmSystemTrapProcessorPFBindings OBJECT IDENTIFIER ::= { ibmSystemTrap 18 }

ibmSystemTrapProcessorPFProviderName OBJECT-TYPE
   SYNTAX         String
   ACCESS         read-only
   STATUS         mandatory
   DESCRIPTION    "The name of the CIM Provider that monitors this device"
   REFERENCE	  "IBMPSG_ProcessorPF.ProviderName"
::= { ibmSystemTrapProcessorPFBindings 1 }

ibmSystemTrapProcessorPFEventID OBJECT-TYPE
   SYNTAX         String
   ACCESS         read-only
   STATUS         mandatory
   DESCRIPTION    "A unique EventID that identifies this trap"
   REFERENCE	  "IBMPSG_ProcessorPF.EventID"
::= { ibmSystemTrapProcessorPFBindings 2 }

ibmSystemTrapProcessorPFAlertingManagedElement OBJECT-TYPE
   SYNTAX         String
   ACCESS         read-only
   STATUS         mandatory
   DESCRIPTION    "A unique string that identifies the monitored device"
   REFERENCE	  "IBMPSG_ProcessorPF.AlertingManagedElement"
::= { ibmSystemTrapProcessorPFBindings 3 }

ibmSystemTrapProcessorPFSeverity OBJECT-TYPE
   SYNTAX         Uint16
   ACCESS         read-only
   STATUS         mandatory
   DESCRIPTION    "0=Normal -- The systems's processsor is not predicting a failure
                   2=Critical -- The system's processor is experiencing an imminent failure."
   REFERENCE	  "IBMPSG_ProcessorPF.Severity"
::= { ibmSystemTrapProcessorPFBindings 4 }

ibmSystemTrapProcessorPFDescription OBJECT-TYPE
   SYNTAX         SnmpAdminString
   ACCESS         read-only
   STATUS         mandatory
   DESCRIPTION    "The Event text of the trap"
   REFERENCE	  "IBMPSG_ProcessorPF.Description"
::= { ibmSystemTrapProcessorPFBindings 5 }

ibmSystemTrapProcessorPFTimeStamp OBJECT-TYPE
   SYNTAX         Datetime
   ACCESS         read-only
   STATUS         mandatory
   DESCRIPTION    "The time that the trap occurred"
   REFERENCE	  "IBMPSG_ProcessorPF.TimeStamp"
::= { ibmSystemTrapProcessorPFBindings 6 }

ibmSystemTrapMemoryPF TRAP-TYPE
   ENTERPRISE     ibmSystemMIB
   VARIABLES    {
      ibmSystemTrapMemoryPFProviderName,
      ibmSystemTrapMemoryPFEventID,
      ibmSystemTrapMemoryPFAlertingManagedElement,
      ibmSystemTrapMemoryPFSeverity,
      ibmSystemTrapMemoryPFDescription,
      ibmSystemTrapMemoryPFTimeStamp
   }
   DESCRIPTION	"This event is sent when a system's DIMM changes state with respect to availability."
   REFERENCE	"IBMPSG_MemoryPF"
::= 19

ibmSystemTrapMemoryPFBindings OBJECT IDENTIFIER ::= { ibmSystemTrap 19 }

ibmSystemTrapMemoryPFProviderName OBJECT-TYPE
   SYNTAX         String
   ACCESS         read-only
   STATUS         mandatory
   DESCRIPTION    "The name of the CIM Provider that monitors this device"
   REFERENCE	  "IBMPSG_MemoryPF.ProviderName"
::= { ibmSystemTrapMemoryPFBindings 1 }

ibmSystemTrapMemoryPFEventID OBJECT-TYPE
   SYNTAX         String
   ACCESS         read-only
   STATUS         mandatory
   DESCRIPTION    "A unique EventID that identifies this trap"
   REFERENCE	  "IBMPSG_MemoryPF.EventID"
::= { ibmSystemTrapMemoryPFBindings 2 }

ibmSystemTrapMemoryPFAlertingManagedElement OBJECT-TYPE
   SYNTAX         String
   ACCESS         read-only
   STATUS         mandatory
   DESCRIPTION    "A unique string that identifies the monitored device"
   REFERENCE	  "IBMPSG_MemoryPF.AlertingManagedElement"
::= { ibmSystemTrapMemoryPFBindings 3 }

ibmSystemTrapMemoryPFSeverity OBJECT-TYPE
   SYNTAX         Uint16
   ACCESS         read-only
   STATUS         mandatory
   DESCRIPTION    "0=Normal -- The DIMM is not predicting a failure
                   2=Critical -- A DIMM in the system is experiencing an imminent failure."
   REFERENCE	  "IBMPSG_MemoryPF.Severity"
::= { ibmSystemTrapMemoryPFBindings 4 }

ibmSystemTrapMemoryPFDescription OBJECT-TYPE
   SYNTAX         SnmpAdminString
   ACCESS         read-only
   STATUS         mandatory
   DESCRIPTION    "The Event text of the trap"
   REFERENCE	  "IBMPSG_MemoryPF.Description"
::= { ibmSystemTrapMemoryPFBindings 5 }

ibmSystemTrapMemoryPFTimeStamp OBJECT-TYPE
   SYNTAX         Datetime
   ACCESS         read-only
   STATUS         mandatory
   DESCRIPTION    "The time that the trap occurred"
   REFERENCE	  "IBMPSG_MemoryPF.TimeStamp"
::= { ibmSystemTrapMemoryPFBindings 6 }

ibmSystemTrapPFA TRAP-TYPE
   ENTERPRISE     ibmSystemMIB
   VARIABLES    {
      ibmSystemTrapPFAProviderName,
      ibmSystemTrapPFAEventID,
      ibmSystemTrapPFAAlertingManagedElement,
      ibmSystemTrapPFASeverity,
      ibmSystemTrapPFADescription,
      ibmSystemTrapPFATimeStamp
   }
   DESCRIPTION	"This event is sent when the Remote Supervisor Adapter detects that
                   a system is about to fail."
   REFERENCE	"IBMPSG_PFA"
::= 22

ibmSystemTrapPFABindings OBJECT IDENTIFIER ::= { ibmSystemTrap 22 }

ibmSystemTrapPFAProviderName OBJECT-TYPE
   SYNTAX         String
   ACCESS         read-only
   STATUS         mandatory
   DESCRIPTION    "The name of the CIM Provider that monitors this device"
   REFERENCE	  "IBMPSG_PFA.ProviderName"
::= { ibmSystemTrapPFABindings 1 }

ibmSystemTrapPFAEventID OBJECT-TYPE
   SYNTAX         String
   ACCESS         read-only
   STATUS         mandatory
   DESCRIPTION    "A unique EventID that identifies this trap"
   REFERENCE	  "IBMPSG_PFA.EventID"
::= { ibmSystemTrapPFABindings 2 }

ibmSystemTrapPFAAlertingManagedElement OBJECT-TYPE
   SYNTAX         String
   ACCESS         read-only
   STATUS         mandatory
   DESCRIPTION    "A unique string that identifies the monitored device"
   REFERENCE	  "IBMPSG_PFA.AlertingManagedElement"
::= { ibmSystemTrapPFABindings 3 }

ibmSystemTrapPFASeverity OBJECT-TYPE
   SYNTAX         Uint16
   ACCESS         read-only
   STATUS         mandatory
   DESCRIPTION    "2=Critical -- The system is experiencing an imminent failure."
   REFERENCE	  "IBMPSG_PFA.Severity"
::= { ibmSystemTrapPFABindings 4 }

ibmSystemTrapPFADescription OBJECT-TYPE
   SYNTAX         SnmpAdminString
   ACCESS         read-only
   STATUS         mandatory
   DESCRIPTION    "The Event text of the trap"
   REFERENCE	  "IBMPSG_PFA.Description"
::= { ibmSystemTrapPFABindings 5 }

ibmSystemTrapPFATimeStamp OBJECT-TYPE
   SYNTAX         Datetime
   ACCESS         read-only
   STATUS         mandatory
   DESCRIPTION    "The time that the trap occurred"
   REFERENCE	  "IBMPSG_PFA.TimeStamp"
::= { ibmSystemTrapPFABindings 6 }

ibmSystemTrapPowerSupply TRAP-TYPE
   ENTERPRISE     ibmSystemMIB
   VARIABLES    {
      ibmSystemTrapPowerSupplyProviderName,
      ibmSystemTrapPowerSupplyEventID,
      ibmSystemTrapPowerSupplyAlertingManagedElement,
      ibmSystemTrapPowerSupplySeverity,
      ibmSystemTrapPowerSupplyDescription,
      ibmSystemTrapPowerSupplyTimeStamp
   }
   DESCRIPTION	"This event is sent when the Remote Supervisor Adapter detects that the
                   state of a system's power supply changes with respect to availability."
   REFERENCE	"IBMPSG_PowerSupply"
::= 23

ibmSystemTrapPowerSupplyBindings OBJECT IDENTIFIER ::= { ibmSystemTrap 23 }

ibmSystemTrapPowerSupplyProviderName OBJECT-TYPE
   SYNTAX         String
   ACCESS         read-only
   STATUS         mandatory
   DESCRIPTION    "The name of the CIM Provider that monitors this device"
   REFERENCE	  "IBMPSG_PowerSupply.ProviderName"
::= { ibmSystemTrapPowerSupplyBindings 1 }

ibmSystemTrapPowerSupplyEventID OBJECT-TYPE
   SYNTAX         String
   ACCESS         read-only
   STATUS         mandatory
   DESCRIPTION    "A unique EventID that identifies this trap"
   REFERENCE	  "IBMPSG_PowerSupply.EventID"
::= { ibmSystemTrapPowerSupplyBindings 2 }

ibmSystemTrapPowerSupplyAlertingManagedElement OBJECT-TYPE
   SYNTAX         String
   ACCESS         read-only
   STATUS         mandatory
   DESCRIPTION    "A unique string that identifies the monitored device"
   REFERENCE	  "IBMPSG_PowerSupply.AlertingManagedElement"
::= { ibmSystemTrapPowerSupplyBindings 3 }

ibmSystemTrapPowerSupplySeverity OBJECT-TYPE
   SYNTAX         Uint16
   ACCESS         read-only
   STATUS         mandatory
   DESCRIPTION    "0=Normal -- A failed power supply has been recovered.
                   2=Critical -- A power supply in a system has failed and there's been a possible loss of redundancy."
   REFERENCE	  "IBMPSG_PowerSupply.Severity"
::= { ibmSystemTrapPowerSupplyBindings 4 }

ibmSystemTrapPowerSupplyDescription OBJECT-TYPE
   SYNTAX         SnmpAdminString
   ACCESS         read-only
   STATUS         mandatory
   DESCRIPTION    "The Event text of the trap"
   REFERENCE	  "IBMPSG_PowerSupply.Description"
::= { ibmSystemTrapPowerSupplyBindings 5 }

ibmSystemTrapPowerSupplyTimeStamp OBJECT-TYPE
   SYNTAX         Datetime
   ACCESS         read-only
   STATUS         mandatory
   DESCRIPTION    "The time that the trap occurred"
   REFERENCE	  "IBMPSG_PowerSupply.TimeStamp"
::= { ibmSystemTrapPowerSupplyBindings 6 }

ibmSystemTrapErrorLog TRAP-TYPE
   ENTERPRISE     ibmSystemMIB
   VARIABLES    {
      ibmSystemTrapErrorLogProviderName,
      ibmSystemTrapErrorLogEventID,
      ibmSystemTrapErrorLogAlertingManagedElement,
      ibmSystemTrapErrorLogSeverity,
      ibmSystemTrapErrorLogDescription,
      ibmSystemTrapErrorLogTimeStamp
   }
   DESCRIPTION	"This event is sent when the Remote Supervisor Adapter detects that its error
                   log is 75% full and/or 100% full."
   REFERENCE	"IBMPSG_ErrorLog"
::= 24

ibmSystemTrapErrorLogBindings OBJECT IDENTIFIER ::= { ibmSystemTrap 24 }

ibmSystemTrapErrorLogProviderName OBJECT-TYPE
   SYNTAX         String
   ACCESS         read-only
   STATUS         mandatory
   DESCRIPTION    "The name of the CIM Provider that monitors this device"
   REFERENCE	  "IBMPSG_ErrorLog.ProviderName"
::= { ibmSystemTrapErrorLogBindings 1 }

ibmSystemTrapErrorLogEventID OBJECT-TYPE
   SYNTAX         String
   ACCESS         read-only
   STATUS         mandatory
   DESCRIPTION    "A unique EventID that identifies this trap"
   REFERENCE	  "IBMPSG_ErrorLog.EventID"
::= { ibmSystemTrapErrorLogBindings 2 }

ibmSystemTrapErrorLogAlertingManagedElement OBJECT-TYPE
   SYNTAX         String
   ACCESS         read-only
   STATUS         mandatory
   DESCRIPTION    "A unique string that identifies the monitored device"
   REFERENCE	  "IBMPSG_ErrorLog.AlertingManagedElement"
::= { ibmSystemTrapErrorLogBindings 3 }

ibmSystemTrapErrorLogSeverity OBJECT-TYPE
   SYNTAX         Uint16
   ACCESS         read-only
   STATUS         mandatory
   DESCRIPTION    "1=Warning -- The Remote Supervisor Adapter's error log is 75% full.
                   2=Critical -- The Remote Supervisor Adapter's error log is 100% full."
   REFERENCE	  "IBMPSG_ErrorLog.Severity"
::= { ibmSystemTrapErrorLogBindings 4 }

ibmSystemTrapErrorLogDescription OBJECT-TYPE
   SYNTAX         SnmpAdminString
   ACCESS         read-only
   STATUS         mandatory
   DESCRIPTION    "The Event text of the trap"
   REFERENCE	  "IBMPSG_ErrorLog.Description"
::= { ibmSystemTrapErrorLogBindings 5 }

ibmSystemTrapErrorLogTimeStamp OBJECT-TYPE
   SYNTAX         Datetime
   ACCESS         read-only
   STATUS         mandatory
   DESCRIPTION    "The time that the trap occurred"
   REFERENCE	  "IBMPSG_ErrorLog.TimeStamp"
::= { ibmSystemTrapErrorLogBindings 6 }

ibmSystemTrapRemoteLogin TRAP-TYPE
   ENTERPRISE     ibmSystemMIB
   VARIABLES    {
      ibmSystemTrapRemoteLoginProviderName,
      ibmSystemTrapRemoteLoginEventID,
      ibmSystemTrapRemoteLoginAlertingManagedElement,
      ibmSystemTrapRemoteLoginSeverity,
      ibmSystemTrapRemoteLoginDescription,
      ibmSystemTrapRemoteLoginTimeStamp
   }
   DESCRIPTION	"This event is sent when the state of the Remote Supervisor Adapter changes
                   with respect to security because a user has logged into it."
   REFERENCE	"IBMPSG_RemoteLogin"
::= 25

ibmSystemTrapRemoteLoginBindings OBJECT IDENTIFIER ::= { ibmSystemTrap 25 }

ibmSystemTrapRemoteLoginProviderName OBJECT-TYPE
   SYNTAX         String
   ACCESS         read-only
   STATUS         mandatory
   DESCRIPTION    "The name of the CIM Provider that monitors this device"
   REFERENCE	  "IBMPSG_RemoteLogin.ProviderName"
::= { ibmSystemTrapRemoteLoginBindings 1 }

ibmSystemTrapRemoteLoginEventID OBJECT-TYPE
   SYNTAX         String
   ACCESS         read-only
   STATUS         mandatory
   DESCRIPTION    "A unique EventID that identifies this trap"
   REFERENCE	  "IBMPSG_RemoteLogin.EventID"
::= { ibmSystemTrapRemoteLoginBindings 2 }

ibmSystemTrapRemoteLoginAlertingManagedElement OBJECT-TYPE
   SYNTAX         String
   ACCESS         read-only
   STATUS         mandatory
   DESCRIPTION    "A unique string that identifies the monitored device"
   REFERENCE	  "IBMPSG_RemoteLogin.AlertingManagedElement"
::= { ibmSystemTrapRemoteLoginBindings 3 }

ibmSystemTrapRemoteLoginSeverity OBJECT-TYPE
   SYNTAX         Uint16
   ACCESS         read-only
   STATUS         mandatory
   DESCRIPTION    "1=Warning -- Someone has logged in remotely to the Remote Supervisor Adapter."
   REFERENCE	  "IBMPSG_RemoteLogin.Severity"
::= { ibmSystemTrapRemoteLoginBindings 4 }

ibmSystemTrapRemoteLoginDescription OBJECT-TYPE
   SYNTAX         SnmpAdminString
   ACCESS         read-only
   STATUS         mandatory
   DESCRIPTION    "The Event text of the trap"
   REFERENCE	  "IBMPSG_RemoteLogin.Description"
::= { ibmSystemTrapRemoteLoginBindings 5 }

ibmSystemTrapRemoteLoginTimeStamp OBJECT-TYPE
   SYNTAX         Datetime
   ACCESS         read-only
   STATUS         mandatory
   DESCRIPTION    "The time that the trap occurred"
   REFERENCE	  "IBMPSG_RemoteLogin.TimeStamp"
::= { ibmSystemTrapRemoteLoginBindings 6 }

ibmSystemTrapNetworkAdapterFailed TRAP-TYPE
   ENTERPRISE     ibmSystemMIB
   VARIABLES    {
      ibmSystemTrapNetworkAdapterFailedProviderName,
      ibmSystemTrapNetworkAdapterFailedEventID,
      ibmSystemTrapNetworkAdapterFailedAlertingManagedElement,
      ibmSystemTrapNetworkAdapterFailedSeverity,
      ibmSystemTrapNetworkAdapterFailedDescription,
      ibmSystemTrapNetworkAdapterFailedTimeStamp,
      ibmSystemTrapNetworkAdapterFailedComponentID
   }
   DESCRIPTION	"This event is sent when the state of a system's NIC fails."
   REFERENCE	"IBMPSG_NetworkAdapterFailed"
::= 26

ibmSystemTrapNetworkAdapterFailedBindings OBJECT IDENTIFIER ::= { ibmSystemTrap 26 }

ibmSystemTrapNetworkAdapterFailedProviderName OBJECT-TYPE
   SYNTAX         String
   ACCESS         read-only
   STATUS         mandatory
   DESCRIPTION    "The name of the CIM Provider that monitors this device"
   REFERENCE	  "IBMPSG_NetworkAdapterFailed.ProviderName"
::= { ibmSystemTrapNetworkAdapterFailedBindings 1 }

ibmSystemTrapNetworkAdapterFailedEventID OBJECT-TYPE
   SYNTAX         String
   ACCESS         read-only
   STATUS         mandatory
   DESCRIPTION    "A unique EventID that identifies this trap"
   REFERENCE	  "IBMPSG_NetworkAdapterFailed.EventID"
::= { ibmSystemTrapNetworkAdapterFailedBindings 2 }

ibmSystemTrapNetworkAdapterFailedAlertingManagedElement OBJECT-TYPE
   SYNTAX         String
   ACCESS         read-only
   STATUS         mandatory
   DESCRIPTION    "The CIM ObjectPath of the physical network adapter instance that has experienced
		   a change in state."
   REFERENCE	  "IBMPSG_NetworkAdapterFailed.AlertingManagedElement"
::= { ibmSystemTrapNetworkAdapterFailedBindings 3 }

ibmSystemTrapNetworkAdapterFailedSeverity OBJECT-TYPE
   SYNTAX         Uint16
   ACCESS         read-only
   STATUS         mandatory
   DESCRIPTION    "2=Critical -- The network adapter referenced in the target object path has failed.
		   0=Normal -- The network adapter referenced in the target object path has been recovered."
   REFERENCE	  "IBMPSG_NetworkAdapterFailed.Severity"
::= { ibmSystemTrapNetworkAdapterFailedBindings 4 }

ibmSystemTrapNetworkAdapterFailedDescription OBJECT-TYPE
   SYNTAX         SnmpAdminString
   ACCESS         read-only
   STATUS         mandatory
   DESCRIPTION    "The Event text of the trap"
   REFERENCE	  "IBMPSG_NetworkAdapterFailed.Description"
::= { ibmSystemTrapNetworkAdapterFailedBindings 5 }

ibmSystemTrapNetworkAdapterFailedTimeStamp OBJECT-TYPE
   SYNTAX         Datetime
   ACCESS         read-only
   STATUS         mandatory
   DESCRIPTION    "The date and time of the adapter failure on the managed system."
   REFERENCE	  "IBMPSG_NetworkAdapterFailed.TimeStamp"
::= { ibmSystemTrapNetworkAdapterFailedBindings 6 }

ibmSystemTrapNetworkAdapterFailedComponentID OBJECT-TYPE
   SYNTAX	Uint16
   ACCESS	read-only
   STATUS	mandatory
   DESCRIPTION  "The physical PCI Slot number or the onboard Port number of the NIC."
   REFERENCE	"IBMPSG_NetworkAdapterFailed.ComponentID"
::= { ibmSystemTrapNetworkAdapterFailedBindings 7 }

ibmSystemTrapNetworkAdapterOffline TRAP-TYPE
   ENTERPRISE     ibmSystemMIB
   VARIABLES    {
      ibmSystemTrapNetworkAdapterOfflineProviderName,
      ibmSystemTrapNetworkAdapterOfflineEventID,
      ibmSystemTrapNetworkAdapterOfflineAlertingManagedElement,
      ibmSystemTrapNetworkAdapterOfflineSeverity,
      ibmSystemTrapNetworkAdapterOfflineDescription,
      ibmSystemTrapNetworkAdapterOfflineTimeStamp,
      ibmSystemTrapNetworkAdapterOfflineComponentID
   }
   DESCRIPTION	"This event is sent when the state of a system's NIC goes offline."
   REFERENCE	"IBMPSG_NetworkAdapterOffline"
::= 27

ibmSystemTrapNetworkAdapterOfflineBindings OBJECT IDENTIFIER ::= { ibmSystemTrap 27 }

ibmSystemTrapNetworkAdapterOfflineProviderName OBJECT-TYPE
   SYNTAX         String
   ACCESS         read-only
   STATUS         mandatory
   DESCRIPTION    "The name of the CIM Provider that monitors this device"
   REFERENCE	  "IBMPSG_NetworkAdapterOffline.ProviderName"
::= { ibmSystemTrapNetworkAdapterOfflineBindings 1 }

ibmSystemTrapNetworkAdapterOfflineEventID OBJECT-TYPE
   SYNTAX         String
   ACCESS         read-only
   STATUS         mandatory
   DESCRIPTION    "A unique EventID that identifies this trap"
   REFERENCE	  "IBMPSG_NetworkAdapterOffline.EventID"
::= { ibmSystemTrapNetworkAdapterOfflineBindings 2 }

ibmSystemTrapNetworkAdapterOfflineAlertingManagedElement OBJECT-TYPE
   SYNTAX         String
   ACCESS         read-only
   STATUS         mandatory
   DESCRIPTION    "The CIM ObjectPath of the physical network adapter instance that has experienced
		   a change in state."
   REFERENCE	  "IBMPSG_NetworkAdapterOffline.AlertingManagedElement"
::= { ibmSystemTrapNetworkAdapterOfflineBindings 3 }

ibmSystemTrapNetworkAdapterOfflineSeverity OBJECT-TYPE
   SYNTAX         Uint16
   ACCESS         read-only
   STATUS         mandatory
   DESCRIPTION    "1=Warning -- The network adapter referenced in the target object path has gone offline."
   REFERENCE	  "IBMPSG_NetworkAdapterOffline.Severity"
::= { ibmSystemTrapNetworkAdapterOfflineBindings 4 }

ibmSystemTrapNetworkAdapterOfflineDescription OBJECT-TYPE
   SYNTAX         SnmpAdminString
   ACCESS         read-only
   STATUS         mandatory
   DESCRIPTION    "The Event text of the trap"
   REFERENCE	  "IBMPSG_NetworkAdapterOffline.Description"
::= { ibmSystemTrapNetworkAdapterOfflineBindings 5 }

ibmSystemTrapNetworkAdapterOfflineTimeStamp OBJECT-TYPE
   SYNTAX         Datetime
   ACCESS         read-only
   STATUS         mandatory
   DESCRIPTION    "The date and time that the network adapter went offline on the managed system."
   REFERENCE	  "IBMPSG_NetworkAdapterOffline.TimeStamp"
::= { ibmSystemTrapNetworkAdapterOfflineBindings 6 }

ibmSystemTrapNetworkAdapterOfflineComponentID OBJECT-TYPE
   SYNTAX	Uint16
   ACCESS	read-only
   STATUS	mandatory
   DESCRIPTION  "The physical PCI Slot number or the onboard Port number of the NIC."
   REFERENCE	"IBMPSG_NetworkAdapterOffline.ComponentID"
::= { ibmSystemTrapNetworkAdapterOfflineBindings 7 }

ibmSystemTrapNetworkAdapterOnline TRAP-TYPE
   ENTERPRISE     ibmSystemMIB
   VARIABLES    {
      ibmSystemTrapNetworkAdapterOnlineProviderName,
      ibmSystemTrapNetworkAdapterOnlineEventID,
      ibmSystemTrapNetworkAdapterOnlineAlertingManagedElement,
      ibmSystemTrapNetworkAdapterOnlineSeverity,
      ibmSystemTrapNetworkAdapterOnlineDescription,
      ibmSystemTrapNetworkAdapterOnlineTimeStamp,
      ibmSystemTrapNetworkAdapterOnlineComponentID
   }
   DESCRIPTION	"This event is sent when the state of a system's NIC goes online."
   REFERENCE	"IBMPSG_NetworkAdapterOnline"
::= 28

ibmSystemTrapNetworkAdapterOnlineBindings OBJECT IDENTIFIER ::= { ibmSystemTrap 28 }

ibmSystemTrapNetworkAdapterOnlineProviderName OBJECT-TYPE
   SYNTAX         String
   ACCESS         read-only
   STATUS         mandatory
   DESCRIPTION    "The name of the CIM Provider that monitors this device"
   REFERENCE	  "IBMPSG_NetworkAdapterOnline.ProviderName"
::= { ibmSystemTrapNetworkAdapterOnlineBindings 1 }

ibmSystemTrapNetworkAdapterOnlineEventID OBJECT-TYPE
   SYNTAX         String
   ACCESS         read-only
   STATUS         mandatory
   DESCRIPTION    "A unique EventID that identifies this trap"
   REFERENCE	  "IBMPSG_NetworkAdapterOnline.EventID"
::= { ibmSystemTrapNetworkAdapterOnlineBindings 2 }

ibmSystemTrapNetworkAdapterOnlineAlertingManagedElement OBJECT-TYPE
   SYNTAX         String
   ACCESS         read-only
   STATUS         mandatory
   DESCRIPTION    "The CIM ObjectPath of the physical network adapter instance that has experienced
		   a change in state."
   REFERENCE	  "IBMPSG_NetworkAdapterOnline.AlertingManagedElement"
::= { ibmSystemTrapNetworkAdapterOnlineBindings 3 }

ibmSystemTrapNetworkAdapterOnlineSeverity OBJECT-TYPE
   SYNTAX         Uint16
   ACCESS         read-only
   STATUS         mandatory
   DESCRIPTION    "0=Normal -- The network adapter referenced in the target object path has come online."
   REFERENCE	  "IBMPSG_NetworkAdapterOnline.Severity"
::= { ibmSystemTrapNetworkAdapterOnlineBindings 4 }

ibmSystemTrapNetworkAdapterOnlineDescription OBJECT-TYPE
   SYNTAX         SnmpAdminString
   ACCESS         read-only
   STATUS         mandatory
   DESCRIPTION    "The Event text of the trap"
   REFERENCE	  "IBMPSG_NetworkAdapterOnline.Description"
::= { ibmSystemTrapNetworkAdapterOnlineBindings 5 }

ibmSystemTrapNetworkAdapterOnlineTimeStamp OBJECT-TYPE
   SYNTAX         Datetime
   ACCESS         read-only
   STATUS         mandatory
   DESCRIPTION    "The date and time that the network adapter came online on the managed system."
   REFERENCE	  "IBMPSG_NetworkAdapterOnline.TimeStamp"
::= { ibmSystemTrapNetworkAdapterOnlineBindings 6 }

ibmSystemTrapNetworkAdapterOnlineComponentID OBJECT-TYPE
   SYNTAX	Uint16
   ACCESS	read-only
   STATUS	mandatory
   DESCRIPTION  "The physical PCI Slot number or the onboard Port number of the NIC."
   REFERENCE	"IBMPSG_NetworkAdapterFailed.ComponentID"
::= { ibmSystemTrapNetworkAdapterOnlineBindings 7 }

ibmSystemTrapSPPowerSupply TRAP-TYPE
   ENTERPRISE     ibmSystemMIB
   VARIABLES    {
      ibmSystemTrapSPPowerSupplyProviderName,
      ibmSystemTrapSPPowerSupplyEventID,
      ibmSystemTrapSPPowerSupplyAlertingManagedElement,
      ibmSystemTrapSPPowerSupplySeverity,
      ibmSystemTrapSPPowerSupplyDescription,
      ibmSystemTrapSPPowerSupplyTimeStamp
   }
   DESCRIPTION	"This event is sent when the Remote Supervisor Adapter detects that the
                   state of a system's power supply changes with respect to availability."
   REFERENCE	"IBMPSG_SP_PowerSupply"
::= 29

ibmSystemTrapSPPowerSupplyBindings OBJECT IDENTIFIER ::= { ibmSystemTrap 29 }

ibmSystemTrapSPPowerSupplyProviderName OBJECT-TYPE
   SYNTAX         String
   ACCESS         read-only
   STATUS         mandatory
   DESCRIPTION    "The name of the CIM Provider that monitors this device"
   REFERENCE	  "IBMPSG_SP_PowerSupply.ProviderName"
::= { ibmSystemTrapSPPowerSupplyBindings 1 }

ibmSystemTrapSPPowerSupplyEventID OBJECT-TYPE
   SYNTAX         String
   ACCESS         read-only
   STATUS         mandatory
   DESCRIPTION    "A unique EventID that identifies this trap"
   REFERENCE	  "IBMPSG_SP_PowerSupply.EventID"
::= { ibmSystemTrapSPPowerSupplyBindings 2 }

ibmSystemTrapSPPowerSupplyAlertingManagedElement OBJECT-TYPE
   SYNTAX         String
   ACCESS         read-only
   STATUS         mandatory
   DESCRIPTION    "A unique string that identifies the monitored device"
   REFERENCE	  "IBMPSG_SP_PowerSupply.AlertingManagedElement"
::= { ibmSystemTrapSPPowerSupplyBindings 3 }

ibmSystemTrapSPPowerSupplySeverity OBJECT-TYPE
   SYNTAX         Uint16
   ACCESS         read-only
   STATUS         mandatory
   DESCRIPTION    "0=Normal -- A power supply has recovered and redundancy may have been restored
                   2=Critical -- A power supply in a system has failed and there has been a possible loss of redundancy."
   REFERENCE	  "IBMPSG_SP_PowerSupply.Severity"
::= { ibmSystemTrapSPPowerSupplyBindings 4 }

ibmSystemTrapSPPowerSupplyDescription OBJECT-TYPE
   SYNTAX         SnmpAdminString
   ACCESS         read-only
   STATUS         mandatory
   DESCRIPTION    "The Event text of the trap"
   REFERENCE	  "IBMPSG_SP_PowerSupply.Description"
::= { ibmSystemTrapSPPowerSupplyBindings 5 }

ibmSystemTrapSPPowerSupplyTimeStamp OBJECT-TYPE
   SYNTAX         Datetime
   ACCESS         read-only
   STATUS         mandatory
   DESCRIPTION    "The time that the trap occurred"
   REFERENCE	  "IBMPSG_SP_PowerSupply.TimeStamp"
::= { ibmSystemTrapSPPowerSupplyBindings 6 }

ibmSystemTrapDASDBackplane TRAP-TYPE
   ENTERPRISE     ibmSystemMIB
   VARIABLES    {
      ibmSystemTrapDASDBackplaneProviderName,
      ibmSystemTrapDASDBackplaneEventID,
      ibmSystemTrapDASDBackplaneAlertingManagedElement,
      ibmSystemTrapDASDBackplaneSeverity,
      ibmSystemTrapDASDBackplaneDescription,
      ibmSystemTrapDASDBackplaneTimeStamp
   }
   DESCRIPTION	"This event is sent when the Remote Supervisor Adapter detects that the
                   drive backplane experiences a critical error."
   REFERENCE	"IBMPSG_DASDBackplane"
::= 30

ibmSystemTrapDASDBackplaneBindings OBJECT IDENTIFIER ::= { ibmSystemTrap 30 }

ibmSystemTrapDASDBackplaneProviderName OBJECT-TYPE
   SYNTAX         String
   ACCESS         read-only
   STATUS         mandatory
   DESCRIPTION    "The name of the CIM Provider that monitors this device"
   REFERENCE	  "IBMPSG_DASDBackplane.ProviderName"
::= { ibmSystemTrapDASDBackplaneBindings 1 }

ibmSystemTrapDASDBackplaneEventID OBJECT-TYPE
   SYNTAX         String
   ACCESS         read-only
   STATUS         mandatory
   DESCRIPTION    "A unique EventID that identifies this trap"
   REFERENCE	  "IBMPSG_DASDBackplane.EventID"
::= { ibmSystemTrapDASDBackplaneBindings 2 }

ibmSystemTrapDASDBackplaneAlertingManagedElement OBJECT-TYPE
   SYNTAX         String
   ACCESS         read-only
   STATUS         mandatory
   DESCRIPTION    "A unique string that identifies the monitored device"
   REFERENCE	  "IBMPSG_DASDBackplane.AlertingManagedElement"
::= { ibmSystemTrapDASDBackplaneBindings 3 }

ibmSystemTrapDASDBackplaneSeverity OBJECT-TYPE
   SYNTAX         Uint16
   ACCESS         read-only
   STATUS         mandatory
   DESCRIPTION    "2=Critical -- A hard drive failure has occured."
   REFERENCE	  "IBMPSG_DASDBackplane.Severity"
::= { ibmSystemTrapDASDBackplaneBindings 4 }

ibmSystemTrapDASDBackplaneDescription OBJECT-TYPE
   SYNTAX         SnmpAdminString
   ACCESS         read-only
   STATUS         mandatory
   DESCRIPTION    "The Event text of the trap"
   REFERENCE	  "IBMPSG_DASDBackplane.Description"
::= { ibmSystemTrapDASDBackplaneBindings 5 }

ibmSystemTrapDASDBackplaneTimeStamp OBJECT-TYPE
   SYNTAX         Datetime
   ACCESS         read-only
   STATUS         mandatory
   DESCRIPTION    "The time that the trap occurred"
   REFERENCE	  "IBMPSG_DASDBackplane.TimeStamp"
::= { ibmSystemTrapDASDBackplaneBindings 6 }

ibmSystemTrapGenericFan TRAP-TYPE
   ENTERPRISE     ibmSystemMIB
   VARIABLES    {
      ibmSystemTrapGenericFanProviderName,
      ibmSystemTrapGenericFanEventID,
      ibmSystemTrapGenericFanAlertingManagedElement,
      ibmSystemTrapGenericFanSeverity,
      ibmSystemTrapGenericFanDescription,
      ibmSystemTrapGenericFanTimeStamp
   }
   DESCRIPTION	"This event is sent when the Remote Supervisor Adapter detects that the
                   state of a system's fan has changed with respect to
                   manufacturer-defined rpm values"
   REFERENCE	"IBMPSG_GenericFan"
::= 31

ibmSystemTrapGenericFanBindings OBJECT IDENTIFIER ::= { ibmSystemTrap 31 }

ibmSystemTrapGenericFanProviderName OBJECT-TYPE
   SYNTAX         String
   ACCESS         read-only
   STATUS         mandatory
   DESCRIPTION    "The name of the CIM Provider that monitors this device"
   REFERENCE	  "IBMPSG_GenericFan.ProviderName"
::= { ibmSystemTrapGenericFanBindings 1 }

ibmSystemTrapGenericFanEventID OBJECT-TYPE
   SYNTAX         String
   ACCESS         read-only
   STATUS         mandatory
   DESCRIPTION    ""
   REFERENCE	  "IBMPSG_GenericFan.EventID"
::= { ibmSystemTrapGenericFanBindings 2 }

ibmSystemTrapGenericFanAlertingManagedElement OBJECT-TYPE
   SYNTAX         String
   ACCESS         read-only
   STATUS         mandatory
   DESCRIPTION    "A unique string that identifies the monitored device"
   REFERENCE	  "IBMPSG_GenericFan.AlertingManagedElement"
::= { ibmSystemTrapGenericFanBindings 3 }

ibmSystemTrapGenericFanSeverity OBJECT-TYPE
   SYNTAX         Uint16
   ACCESS         read-only
   STATUS         mandatory
   DESCRIPTION    "2=Critical -- The fan has stopped."
   REFERENCE	  "IBMPSG_GenericFan.Severity"
::= { ibmSystemTrapGenericFanBindings 4 }

ibmSystemTrapGenericFanDescription OBJECT-TYPE
   SYNTAX         SnmpAdminString
   ACCESS         read-only
   STATUS         mandatory
   DESCRIPTION    "The Event text of the trap"
   REFERENCE	  "IBMPSG_GenericFan.Description"
::= { ibmSystemTrapGenericFanBindings 5 }

ibmSystemTrapGenericFanTimeStamp OBJECT-TYPE
   SYNTAX         Datetime
   ACCESS         read-only
   STATUS         mandatory
   DESCRIPTION    "The time that the trap occurred"
   REFERENCE	  "IBMPSG_GenericFan.TimeStamp"
::= { ibmSystemTrapGenericFanBindings 6 }

ibmSystemTrapGenericVoltage TRAP-TYPE
   ENTERPRISE     ibmSystemMIB
   VARIABLES    {
      ibmSystemTrapGenericVoltageProviderName,
      ibmSystemTrapGenericVoltageEventID,
      ibmSystemTrapGenericVoltageAlertingManagedElement,
      ibmSystemTrapGenericVoltageSeverity,
      ibmSystemTrapGenericVoltageDescription,
      ibmSystemTrapGenericVoltageTimeStamp
   }
   DESCRIPTION	"This event is sent when the Remote Supervisor Adapter detects that the
                   state of a system's voltage sensor changes with respect to a 
                   manufacturer-defined threshold."
   REFERENCE	"IBMPSG_GenericVoltage"
::= 32

ibmSystemTrapGenericVoltageBindings OBJECT IDENTIFIER ::= { ibmSystemTrap 32 }

ibmSystemTrapGenericVoltageProviderName OBJECT-TYPE
   SYNTAX         String
   ACCESS         read-only
   STATUS         mandatory
   DESCRIPTION    "The name of the CIM Provider that monitors this device"
   REFERENCE	  "IBMPSG_GenericVoltage.ProviderName"
::= { ibmSystemTrapGenericVoltageBindings 1 }

ibmSystemTrapGenericVoltageEventID OBJECT-TYPE
   SYNTAX         String
   ACCESS         read-only
   STATUS         mandatory
   DESCRIPTION    "A unique EventID that identifies this trap"
   REFERENCE	  "IBMPSG_GenericVoltage.EventID"
::= { ibmSystemTrapGenericVoltageBindings 2 }

ibmSystemTrapGenericVoltageAlertingManagedElement OBJECT-TYPE
   SYNTAX         String
   ACCESS         read-only
   STATUS         mandatory
   DESCRIPTION    "A unique string that identifies the monitored device"
   REFERENCE	  "IBMPSG_GenericVoltage.AlertingManagedElement"
::= { ibmSystemTrapGenericVoltageBindings 3 }

ibmSystemTrapGenericVoltageSeverity OBJECT-TYPE
   SYNTAX         Uint16
   ACCESS         read-only
   STATUS         mandatory
   DESCRIPTION    "0=Normal -- The voltage is within normal thresholds
                   1=Warning -- The voltage has exceeded a manufacturer-defined warning level thresold
                   2=Critical -- The voltage has exceeded a manufacturer-defined critical threshold"
   REFERENCE	  "IBMPSG_GenericVoltage.Severity"
::= { ibmSystemTrapGenericVoltageBindings 4 }

ibmSystemTrapGenericVoltageDescription OBJECT-TYPE
   SYNTAX         SnmpAdminString
   ACCESS         read-only
   STATUS         mandatory
   DESCRIPTION    "The Event text of the trap"
   REFERENCE	  "IBMPSG_GenericVoltage.Description"
::= { ibmSystemTrapGenericVoltageBindings 5 }

ibmSystemTrapGenericVoltageTimeStamp OBJECT-TYPE
   SYNTAX         Datetime
   ACCESS         read-only
   STATUS         mandatory
   DESCRIPTION    "The time that the trap occurred"
   REFERENCE	  "IBMPSG_GenericVoltage.TimeStamp"
::= { ibmSystemTrapGenericVoltageBindings 6 }


ibmSystemTrapMgmtHwLogStatus TRAP-TYPE
   ENTERPRISE     ibmSystemMIB
   VARIABLES    {
      ibmSystemTrapMgmtHwLogStatusProviderName,
      ibmSystemTrapMgmtHwLogStatusEventID,
      ibmSystemTrapMgmtHwLogStatusAlertingManagedElement,
      ibmSystemTrapMgmtHwLogStatusSeverity,
      ibmSystemTrapMgmtHwLogStatusDescription,
      ibmSystemTrapMgmtHwLogStatusTimeStamp
   }
   DESCRIPTION	"This event is sent when the IPMI Status Log is full."
   REFERENCE	"IBM_MgmtHwLogStatus"
::= 33

ibmSystemTrapMgmtHwLogStatusBindings OBJECT IDENTIFIER ::= { ibmSystemTrap 33 }

ibmSystemTrapMgmtHwLogStatusProviderName OBJECT-TYPE
   SYNTAX         String
   ACCESS         read-only
   STATUS         mandatory
   DESCRIPTION    "The name of the CIM Provider that monitors this device"
   REFERENCE	  "IBM_MgmtHwLogStatus.ProviderName"
::= { ibmSystemTrapMgmtHwLogStatusBindings 1 }

ibmSystemTrapMgmtHwLogStatusEventID OBJECT-TYPE
   SYNTAX         String
   ACCESS         read-only
   STATUS         mandatory
   DESCRIPTION    "A unique EventID that identifies this trap"
   REFERENCE	  "IBM_MgmtHwLogStatus.EventID"
::= { ibmSystemTrapMgmtHwLogStatusBindings 2 }

ibmSystemTrapMgmtHwLogStatusAlertingManagedElement OBJECT-TYPE
   SYNTAX         String
   ACCESS         read-only
   STATUS         mandatory
   DESCRIPTION    "A unique string that identifies the monitored device"
   REFERENCE	  "IBM_MgmtHwLogStatus.AlertingManagedElement"
::= { ibmSystemTrapMgmtHwLogStatusBindings 3 }

ibmSystemTrapMgmtHwLogStatusSeverity OBJECT-TYPE
   SYNTAX         Uint16
   ACCESS         read-only
   STATUS         mandatory
   DESCRIPTION    "0=Normal -- An event has been logged in the Management Processor Log
                   1=Warning -- A warning event has been logged in the Management Processor Log
                   2=Critical -- A critical event has been logged in the Management Processor Log"
   REFERENCE	  "IBM_MgmtHwLogStatus.Severity"
::= { ibmSystemTrapMgmtHwLogStatusBindings 4 }

ibmSystemTrapMgmtHwLogStatusDescription OBJECT-TYPE
   SYNTAX         SnmpAdminString
   ACCESS         read-only
   STATUS         mandatory
   DESCRIPTION    "The Event text of the trap"
   REFERENCE	  "IBM_MgmtHwLogStatus.Description"
::= { ibmSystemTrapMgmtHwLogStatusBindings 5 }

ibmSystemTrapMgmtHwLogStatusTimeStamp OBJECT-TYPE
   SYNTAX         Datetime
   ACCESS         read-only
   STATUS         mandatory
   DESCRIPTION    "The time that the trap occurred"
   REFERENCE	  "IBM_MgmtHwLogStatus.TimeStamp"
::= { ibmSystemTrapMgmtHwLogStatusBindings 6 }


ibmSystemTrapxProcessor TRAP-TYPE
   ENTERPRISE     ibmSystemMIB
   VARIABLES    {
      ibmSystemTrapxProcessorProviderName,
      ibmSystemTrapxProcessorEventID,
      ibmSystemTrapxProcessorAlertingManagedElement,
      ibmSystemTrapxProcessorSeverity,
      ibmSystemTrapxProcessorDescription,
      ibmSystemTrapxProcessorTimeStamp
   }
   DESCRIPTION	""
   REFERENCE	"IBMPSG_xProcessor"
::= 34

ibmSystemTrapxProcessorBindings OBJECT IDENTIFIER ::= { ibmSystemTrap 34 }

ibmSystemTrapxProcessorProviderName OBJECT-TYPE
   SYNTAX         String
   ACCESS         read-only
   STATUS         mandatory
   DESCRIPTION    "The name of the CIM Provider that monitors this device"
   REFERENCE	  "IBMx_ProcessorEvent.ProviderName"
::= { ibmSystemTrapxProcessorBindings 1 }

ibmSystemTrapxProcessorEventID OBJECT-TYPE
   SYNTAX         String
   ACCESS         read-only
   STATUS         mandatory
   DESCRIPTION    "A unique EventID that identifies this trap"
   REFERENCE	  "IBMx_ProcessorEvent.EventID"
::= { ibmSystemTrapxProcessorBindings 2 }

ibmSystemTrapxProcessorAlertingManagedElement OBJECT-TYPE
   SYNTAX         String
   ACCESS         read-only
   STATUS         mandatory
   DESCRIPTION    "A unique string that identifies the monitored device"
   REFERENCE	  "IBMx_ProcessorEvent.AlertingManagedElement"
::= { ibmSystemTrapxProcessorBindings 3 }

ibmSystemTrapxProcessorSeverity OBJECT-TYPE
   SYNTAX         Uint16
   ACCESS         read-only
   STATUS         mandatory
   DESCRIPTION    "0=Normal -- A processor is reporting normal opertating status
                   1=Warning -- A processor is reporting a warning operational status
                   2=Critical -- A processor is reporting a critical operational status"
   REFERENCE	  "IBMx_ProcessorEvent.Severity"
::= { ibmSystemTrapxProcessorBindings 4 }

ibmSystemTrapxProcessorDescription OBJECT-TYPE
   SYNTAX         SnmpAdminString
   ACCESS         read-only
   STATUS         mandatory
   DESCRIPTION    "The Event text of the trap"
   REFERENCE	  "IBMx_ProcessorEvent.Description"
::= { ibmSystemTrapxProcessorBindings 5 }

ibmSystemTrapxProcessorTimeStamp OBJECT-TYPE
   SYNTAX         Datetime
   ACCESS         read-only
   STATUS         mandatory
   DESCRIPTION    "The time that the trap occurred"
   REFERENCE	  "IBMx_ProcessorEvent.TimeStamp"
::= { ibmSystemTrapxProcessorBindings 6 }


ibmSystemTrapxPhysicalMemory TRAP-TYPE
   ENTERPRISE     ibmSystemMIB
   VARIABLES    {
      ibmSystemTrapxPhysicalMemoryProviderName,
      ibmSystemTrapxPhysicalMemoryEventID,
      ibmSystemTrapxPhysicalMemoryAlertingManagedElement,
      ibmSystemTrapxPhysicalMemorySeverity,
      ibmSystemTrapxPhysicalMemoryDescription,
      ibmSystemTrapxPhysicalMemoryTimeStamp
   }
   DESCRIPTION	""
   REFERENCE	"IBMx_PhysicalMemoryEvent"
::= 35

ibmSystemTrapxPhysicalMemoryBindings OBJECT IDENTIFIER ::= { ibmSystemTrap 35 }

ibmSystemTrapxPhysicalMemoryProviderName OBJECT-TYPE
   SYNTAX         String
   ACCESS         read-only
   STATUS         mandatory
   DESCRIPTION    "The name of the CIM Provider that monitors this device"
   REFERENCE	  "IBMx_PhysicalMemoryEvent.ProviderName"
::= { ibmSystemTrapxPhysicalMemoryBindings 1 }

ibmSystemTrapxPhysicalMemoryEventID OBJECT-TYPE
   SYNTAX         String
   ACCESS         read-only
   STATUS         mandatory
   DESCRIPTION    "A unique EventID that identifies this trap"
   REFERENCE	  "IBMx_PhysicalMemoryEvent.EventID"
::= { ibmSystemTrapxPhysicalMemoryBindings 2 }

ibmSystemTrapxPhysicalMemoryAlertingManagedElement OBJECT-TYPE
   SYNTAX         String
   ACCESS         read-only
   STATUS         mandatory
   DESCRIPTION    "A unique string that identifies the monitored device"
   REFERENCE	  "IBMx_PhysicalMemoryEvent.AlertingManagedElement"
::= { ibmSystemTrapxPhysicalMemoryBindings 3 }

ibmSystemTrapxPhysicalMemorySeverity OBJECT-TYPE
   SYNTAX         Uint16
   ACCESS         read-only
   STATUS         mandatory
   DESCRIPTION    "0=Normal -- The memory device is operating normally
                   1=Warning -- The memory device is reporting a warning condition
                   2=Critical -- The memory device is reporting a critical condition"
   REFERENCE	  "IBMx_PhysicalMemoryEvent.Severity"
::= { ibmSystemTrapxPhysicalMemoryBindings 4 }

ibmSystemTrapxPhysicalMemoryDescription OBJECT-TYPE
   SYNTAX         SnmpAdminString
   ACCESS         read-only
   STATUS         mandatory
   DESCRIPTION    "The Event text of the trap"
   REFERENCE	  "IBMx_PhysicalMemoryEvent.Description"
::= { ibmSystemTrapxPhysicalMemoryBindings 5 }

ibmSystemTrapxPhysicalMemoryTimeStamp OBJECT-TYPE
   SYNTAX         Datetime
   ACCESS         read-only
   STATUS         mandatory
   DESCRIPTION    "The time that the trap occurred"
   REFERENCE	  "IBMx_PhysicalMemoryEvent.TimeStamp"
::= { ibmSystemTrapxPhysicalMemoryBindings 6 }


ibmSystemTrapxAutomaticServerRestart TRAP-TYPE
   ENTERPRISE     ibmSystemMIB
   VARIABLES    {
      ibmSystemTrapxAutomaticServerRestartProviderName,
      ibmSystemTrapxAutomaticServerRestartEventID,
      ibmSystemTrapxAutomaticServerRestartAlertingManagedElement,
      ibmSystemTrapxAutomaticServerRestartSeverity,
      ibmSystemTrapxAutomaticServerRestartDescription,
      ibmSystemTrapxAutomaticServerRestartTimeStamp
   }
   DESCRIPTION	"This event is sent when the Remote Supervisor Adapter detects that the
                   state of a system's voltage sensor changes with respect to a 
                   manufacturer-defined threshold."
   REFERENCE	"IBMx_AutomaticServerRestartEvent"
::= 36

ibmSystemTrapxAutomaticServerRestartBindings OBJECT IDENTIFIER ::= { ibmSystemTrap 36 }

ibmSystemTrapxAutomaticServerRestartProviderName OBJECT-TYPE
   SYNTAX         String
   ACCESS         read-only
   STATUS         mandatory
   DESCRIPTION    "The name of the CIM Provider that monitors this device"
   REFERENCE	  "IBMx_AutomaticServerRestartEvent.ProviderName"
::= { ibmSystemTrapxAutomaticServerRestartBindings 1 }

ibmSystemTrapxAutomaticServerRestartEventID OBJECT-TYPE
   SYNTAX         String
   ACCESS         read-only
   STATUS         mandatory
   DESCRIPTION    "A unique EventID that identifies this trap"
   REFERENCE	  "IBMx_AutomaticServerRestartEvent.EventID"
::= { ibmSystemTrapxAutomaticServerRestartBindings 2 }

ibmSystemTrapxAutomaticServerRestartAlertingManagedElement OBJECT-TYPE
   SYNTAX         String
   ACCESS         read-only
   STATUS         mandatory
   DESCRIPTION    "A unique string that identifies the monitored device"
   REFERENCE	  "IBMx_AutomaticServerRestartEvent.AlertingManagedElement"
::= { ibmSystemTrapxAutomaticServerRestartBindings 3 }

ibmSystemTrapxAutomaticServerRestartSeverity OBJECT-TYPE
   SYNTAX         Uint16
   ACCESS         read-only
   STATUS         mandatory
   DESCRIPTION    "1=Warning -- The voltage has exceeded a manufacturer-defined warning level thresold
                   2=Critical -- The voltage has exceeded a manufacturer-defined critical threshold"
   REFERENCE	  "IBMx_AutomaticServerRestartEvent.Severity"
::= { ibmSystemTrapxAutomaticServerRestartBindings 4 }

ibmSystemTrapxAutomaticServerRestartDescription OBJECT-TYPE
   SYNTAX         SnmpAdminString
   ACCESS         read-only
   STATUS         mandatory
   DESCRIPTION    "The Event text of the trap"
   REFERENCE	  "IBMx_AutomaticServerRestartEvent.Description"
::= { ibmSystemTrapxAutomaticServerRestartBindings 5 }

ibmSystemTrapxAutomaticServerRestartTimeStamp OBJECT-TYPE
   SYNTAX         Datetime
   ACCESS         read-only
   STATUS         mandatory
   DESCRIPTION    "The time that the trap occurred"
   REFERENCE	  "IBMx_AutomaticServerRestartEvent.TimeStamp"
::= { ibmSystemTrapxAutomaticServerRestartBindings 6 }


ibmSystemTrapMgmtHwLogEntry TRAP-TYPE
   ENTERPRISE     ibmSystemMIB
   VARIABLES    {
      ibmSystemTrapMgmtHwLogEntryProviderName,
      ibmSystemTrapMgmtHwLogEntryEventID,
      ibmSystemTrapMgmtHwLogEntryAlertingManagedElement,
      ibmSystemTrapMgmtHwLogEntrySeverity,
      ibmSystemTrapMgmtHwLogEntryDescription,
      ibmSystemTrapMgmtHwLogEntryTimeStamp
   }
   DESCRIPTION	"This event is sent when an Event is logged in the
                 Management Hardware Log"
   REFERENCE	"IBM_MgmtHwLogEntryEvent"
::= 37

ibmSystemTrapMgmtHwLogEntryBindings OBJECT IDENTIFIER ::= { ibmSystemTrap 37 }

ibmSystemTrapMgmtHwLogEntryProviderName OBJECT-TYPE
   SYNTAX         String
   ACCESS         read-only
   STATUS         mandatory
   DESCRIPTION    "The name of the CIM Provider that monitors this device"
   REFERENCE	  "IBM_MgmtHwLogEntryEvent.ProviderName"
::= { ibmSystemTrapMgmtHwLogEntryBindings 1 }

ibmSystemTrapMgmtHwLogEntryEventID OBJECT-TYPE
   SYNTAX         String
   ACCESS         read-only
   STATUS         mandatory
   DESCRIPTION    "A unique EventID that identifies this trap"
   REFERENCE	  "IBM_MgmtHwLogEntryEvent.EventID"
::= { ibmSystemTrapMgmtHwLogEntryBindings 2 }

ibmSystemTrapMgmtHwLogEntryAlertingManagedElement OBJECT-TYPE
   SYNTAX         String
   ACCESS         read-only
   STATUS         mandatory
   DESCRIPTION    "A unique string that identifies the monitored device"
   REFERENCE	  "IBM_MgmtHwLogEntryEvent.AlertingManagedElement"
::= { ibmSystemTrapMgmtHwLogEntryBindings 3 }

ibmSystemTrapMgmtHwLogEntrySeverity OBJECT-TYPE
   SYNTAX         Uint16
   ACCESS         read-only
   STATUS         mandatory
   DESCRIPTION    "0=Normal 
                   1=Warning
                   2=Critical"
   REFERENCE	  "IBM_MgmtHwLogEntryEvent.Severity"
::= { ibmSystemTrapMgmtHwLogEntryBindings 4 }

ibmSystemTrapMgmtHwLogEntryDescription OBJECT-TYPE
   SYNTAX         SnmpAdminString
   ACCESS         read-only
   STATUS         mandatory
   DESCRIPTION    "The Event text of the trap"
   REFERENCE	  "IBM_MgmtHwLogEntryEvent.Description"
::= { ibmSystemTrapMgmtHwLogEntryBindings 5 }

ibmSystemTrapMgmtHwLogEntryTimeStamp OBJECT-TYPE
   SYNTAX         Datetime
   ACCESS         read-only
   STATUS         mandatory
   DESCRIPTION    "The time that the trap occurred"
   REFERENCE	  "IBM_MgmtHwLogEntryEvent.TimeStamp"
::= { ibmSystemTrapMgmtHwLogEntryBindings 6 }


ibmSystemTrapMgmtHwLogFull TRAP-TYPE
   ENTERPRISE     ibmSystemMIB
   VARIABLES    {
      ibmSystemTrapMgmtHwLogFullProviderName,
      ibmSystemTrapMgmtHwLogFullEventID,
      ibmSystemTrapMgmtHwLogFullAlertingManagedElement,
      ibmSystemTrapMgmtHwLogFullSeverity,
      ibmSystemTrapMgmtHwLogFullDescription,
      ibmSystemTrapMgmtHwLogFullTimeStamp
   }
   DESCRIPTION	"This event is sent when Management Hardware Log is Full or near Full"
   REFERENCE	"IBM_MgmtHwLogFullEvent"
::= 38

ibmSystemTrapMgmtHwLogFullBindings OBJECT IDENTIFIER ::= { ibmSystemTrap 38 }

ibmSystemTrapMgmtHwLogFullProviderName OBJECT-TYPE
   SYNTAX         String
   ACCESS         read-only
   STATUS         mandatory
   DESCRIPTION    "The name of the CIM Provider that monitors this device"
   REFERENCE	  "IBM_MgmtHwLogFullEvent.ProviderName"
::= { ibmSystemTrapMgmtHwLogFullBindings 1 }

ibmSystemTrapMgmtHwLogFullEventID OBJECT-TYPE
   SYNTAX         String
   ACCESS         read-only
   STATUS         mandatory
   DESCRIPTION    "A unique EventID that identifies this trap"
   REFERENCE	  "IBM_MgmtHwLogFullEvent.EventID"
::= { ibmSystemTrapMgmtHwLogFullBindings 2 }

ibmSystemTrapMgmtHwLogFullAlertingManagedElement OBJECT-TYPE
   SYNTAX         String
   ACCESS         read-only
   STATUS         mandatory
   DESCRIPTION    "A unique string that identifies the monitored device"
   REFERENCE	  "IBM_MgmtHwLogFullEvent.AlertingManagedElement"
::= { ibmSystemTrapMgmtHwLogFullBindings 3 }

ibmSystemTrapMgmtHwLogFullSeverity OBJECT-TYPE
   SYNTAX         Uint16
   ACCESS         read-only
   STATUS         mandatory
   DESCRIPTION    "0=Normal 
                   1=Warning
                   2=Critical"
   REFERENCE	  "IBM_MgmtHwLogFullEvent.Severity"
::= { ibmSystemTrapMgmtHwLogFullBindings 4 }

ibmSystemTrapMgmtHwLogFullDescription OBJECT-TYPE
   SYNTAX         SnmpAdminString
   ACCESS         read-only
   STATUS         mandatory
   DESCRIPTION    "The Event text of the trap"
   REFERENCE	  "IBM_MgmtHwLogFullEvent.Description"
::= { ibmSystemTrapMgmtHwLogFullBindings 5 }

ibmSystemTrapMgmtHwLogFullTimeStamp OBJECT-TYPE
   SYNTAX         Datetime
   ACCESS         read-only
   STATUS         mandatory
   DESCRIPTION    "The time that the trap occurred"
   REFERENCE	  "IBM_MgmtHwLogFullEvent.TimeStamp"
::= { ibmSystemTrapMgmtHwLogFullBindings 6 }


ibmSystemTrapMgmtHwLogClear TRAP-TYPE
   ENTERPRISE     ibmSystemMIB
   VARIABLES    {
      ibmSystemTrapMgmtHwLogClearProviderName,
      ibmSystemTrapMgmtHwLogClearEventID,
      ibmSystemTrapMgmtHwLogClearAlertingManagedElement,
      ibmSystemTrapMgmtHwLogClearSeverity,
      ibmSystemTrapMgmtHwLogClearDescription,
      ibmSystemTrapMgmtHwLogClearTimeStamp
   }
   DESCRIPTION	"This event is sent when Management Hardware Log has been cleared"
   REFERENCE	"IBM_MgmtHwLogClearEvent"
::= 39

ibmSystemTrapMgmtHwLogClearBindings OBJECT IDENTIFIER ::= { ibmSystemTrap 39 }

ibmSystemTrapMgmtHwLogClearProviderName OBJECT-TYPE
   SYNTAX         String
   ACCESS         read-only
   STATUS         mandatory
   DESCRIPTION    "The name of the CIM Provider that monitors this device"
   REFERENCE	  "IBM_MgmtHwLogClearEvent.ProviderName"
::= { ibmSystemTrapMgmtHwLogClearBindings 1 }

ibmSystemTrapMgmtHwLogClearEventID OBJECT-TYPE
   SYNTAX         String
   ACCESS         read-only
   STATUS         mandatory
   DESCRIPTION    "A unique EventID that identifies this trap"
   REFERENCE	  "IBM_MgmtHwLogClearEvent.EventID"
::= { ibmSystemTrapMgmtHwLogClearBindings 2 }

ibmSystemTrapMgmtHwLogClearAlertingManagedElement OBJECT-TYPE
   SYNTAX         String
   ACCESS         read-only
   STATUS         mandatory
   DESCRIPTION    "A unique string that identifies the monitored device"
   REFERENCE	  "IBM_MgmtHwLogClearEvent.AlertingManagedElement"
::= { ibmSystemTrapMgmtHwLogClearBindings 3 }

ibmSystemTrapMgmtHwLogClearSeverity OBJECT-TYPE
   SYNTAX         Uint16
   ACCESS         read-only
   STATUS         mandatory
   DESCRIPTION    "0=Normal 
                   1=Warning
                   2=Critical"
   REFERENCE	  "IBM_MgmtHwLogClearEvent.Severity"
::= { ibmSystemTrapMgmtHwLogClearBindings 4 }

ibmSystemTrapMgmtHwLogClearDescription OBJECT-TYPE
   SYNTAX         SnmpAdminString
   ACCESS         read-only
   STATUS         mandatory
   DESCRIPTION    "The Event text of the trap"
   REFERENCE	  "IBM_MgmtHwLogClearEvent.Description"
::= { ibmSystemTrapMgmtHwLogClearBindings 5 }

ibmSystemTrapMgmtHwLogClearTimeStamp OBJECT-TYPE
   SYNTAX         Datetime
   ACCESS         read-only
   STATUS         mandatory
   DESCRIPTION    "The time that the trap occurred"
   REFERENCE	  "IBM_MgmtHwLogClearEvent.TimeStamp"
::= { ibmSystemTrapMgmtHwLogClearBindings 6 }


ibmSystemTrapCSServiceEvent TRAP-TYPE
   ENTERPRISE     ibmSystemMIB
   VARIABLES    {
      ibmSystemTrapCSServiceEventProviderName,
      ibmSystemTrapCSServiceEventEventID,
      ibmSystemTrapCSServiceEventAlertingManagedElement,
      ibmSystemTrapCSServiceEventSeverity,
      ibmSystemTrapCSServiceEventDescription,
      ibmSystemTrapCSServiceEventTimeStamp
   }
   DESCRIPTION	"This event is sent when an Service event occurs on a 
                 System p machine"
   REFERENCE	"IBMP_CSServiceEventIndication"
::= 40

ibmSystemTrapCSServiceEventBindings OBJECT IDENTIFIER ::= { ibmSystemTrap 40 }

ibmSystemTrapCSServiceEventProviderName OBJECT-TYPE
   SYNTAX         String
   ACCESS         read-only
   STATUS         mandatory
   DESCRIPTION    "The name of the CIM Provider that monitors this device"
   REFERENCE	  "IBMP_CSServiceEventIndication.ProviderName"
::= { ibmSystemTrapCSServiceEventBindings 1 }

ibmSystemTrapCSServiceEventEventID OBJECT-TYPE
   SYNTAX         String
   ACCESS         read-only
   STATUS         mandatory
   DESCRIPTION    "A unique EventID that identifies this trap"
   REFERENCE	  "IBMP_CSServiceEventIndication.EventID"
::= { ibmSystemTrapCSServiceEventBindings 2 }

ibmSystemTrapCSServiceEventAlertingManagedElement OBJECT-TYPE
   SYNTAX         String
   ACCESS         read-only
   STATUS         mandatory
   DESCRIPTION    "A unique string that identifies the monitored device"
   REFERENCE	  "IBMP_CSServiceEventIndication.AlertingManagedElement"
::= { ibmSystemTrapCSServiceEventBindings 3 }

ibmSystemTrapCSServiceEventSeverity OBJECT-TYPE
   SYNTAX         Uint16
   ACCESS         read-only
   STATUS         mandatory
   DESCRIPTION    "0=Normal -- The Service Event is reporting a recovery event   
                   1=Warning -- The Service Event is reporting a warning condition 
                   2=Critical -- The Service Event is reporting a critical condition"
   REFERENCE	  "IBMP_CSServiceEventIndication.Severity"
::= { ibmSystemTrapCSServiceEventBindings 4 }

ibmSystemTrapCSServiceEventDescription OBJECT-TYPE
   SYNTAX         SnmpAdminString
   ACCESS         read-only
   STATUS         mandatory
   DESCRIPTION    "The Event text of the trap"
   REFERENCE	  "IBMP_CSServiceEventIndication.Description"
::= { ibmSystemTrapCSServiceEventBindings 5 }

ibmSystemTrapCSServiceEventTimeStamp OBJECT-TYPE
   SYNTAX         Datetime
   ACCESS         read-only
   STATUS         mandatory
   DESCRIPTION    "The time that the trap occurred"
   REFERENCE	  "IBMP_CSServiceEventIndication.TimeStamp"
::= { ibmSystemTrapCSServiceEventBindings 6 }


-- added System p traps in 5.20.3

ibmSystempTrapFirmwareReplacedFRU TRAP-TYPE
   ENTERPRISE     ibmSystemMIB
   VARIABLES    {
      ibmSystempTrapFirmwareReplacedFRUProviderName,
      ibmSystempTrapFirmwareReplacedFRUEventID,
      ibmSystempTrapFirmwareReplacedFRUAME,
      ibmSystempTrapFirmwareReplacedFRUSeverity,
      ibmSystempTrapFirmwareReplacedFRUDescription,
      ibmSystempTrapFirmwareReplacedFRUTimeStamp
   }
   DESCRIPTION    "A System p event has occurred"
-- REFERENCE      "POWER_FirmwareReplacedFRUEventIndication"
::= 400

ibmSystempTrapFirmwareReplacedFRUBindings OBJECT IDENTIFIER ::= { ibmSystemTrap 400 }

ibmSystempTrapFirmwareReplacedFRUProviderName OBJECT-TYPE
   SYNTAX         String
   ACCESS         read-only
   STATUS         mandatory
   DESCRIPTION    "The name of the CIM Provider that monitors this device"
-- REFERENCE      "POWER_FirmwareReplacedFRUEventIndication.ProviderName"
::= { ibmSystempTrapFirmwareReplacedFRUBindings 1 }

ibmSystempTrapFirmwareReplacedFRUEventID OBJECT-TYPE
   SYNTAX         String
   ACCESS         read-only
   STATUS         mandatory
   DESCRIPTION    "A unique EventID that identifies this trap" 
-- REFERENCE      "POWER_FirmwareReplacedFRUEventIndication.EventID"
::= { ibmSystempTrapFirmwareReplacedFRUBindings 2 }

ibmSystempTrapFirmwareReplacedFRUAME OBJECT-TYPE
   SYNTAX         String
   ACCESS         read-only
   STATUS         mandatory
   DESCRIPTION    "A unique string that identifies the monitored device"
-- REFERENCE      "POWER_FirmwareReplacedFRUEventIndication.AlertingManagedElement"
::= { ibmSystempTrapFirmwareReplacedFRUBindings 3 }

ibmSystempTrapFirmwareReplacedFRUSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FirmwareReplacedFRUEventIndication.Severity"
::= { ibmSystempTrapFirmwareReplacedFRUBindings 4 }

ibmSystempTrapFirmwareReplacedFRUDescription OBJECT-TYPE
   SYNTAX         SnmpAdminString
   ACCESS         read-only
   STATUS         mandatory
   DESCRIPTION    "The Event text of the trap"
-- REFERENCE      "POWER_FirmwareReplacedFRUEventIndication.Description"
::= { ibmSystempTrapFirmwareReplacedFRUBindings 5 }

ibmSystempTrapFirmwareReplacedFRUTimeStamp OBJECT-TYPE
   SYNTAX         Datetime
   ACCESS         read-only
   STATUS         mandatory
   DESCRIPTION    "The time that the trap occurred"
-- REFERENCE      "POWER_FirmwareReplacedFRUEventIndication.TimeStamp"
::= { ibmSystempTrapFirmwareReplacedFRUBindings 6 }


ibmSystempTrapDTProcessorDiagnostics TRAP-TYPE
   ENTERPRISE     ibmSystemMIB
   VARIABLES    {
      ibmSystempTrapDTProcessorDiagnosticsProviderName,
      ibmSystempTrapDTProcessorDiagnosticsEventID,
      ibmSystempTrapDTProcessorDiagnosticsAME,
      ibmSystempTrapDTProcessorDiagnosticsSeverity,
      ibmSystempTrapDTProcessorDiagnosticsDescription,
      ibmSystempTrapDTProcessorDiagnosticsTimeStamp
   }
   DESCRIPTION    "A System p event has occurred"
-- REFERENCE      "POWER_DTProcessorDiagnosticsEventIndication"
::= 401

ibmSystempTrapDTProcessorDiagnosticsBindings OBJECT IDENTIFIER ::= { ibmSystemTrap 401 }

ibmSystempTrapDTProcessorDiagnosticsProviderName OBJECT-TYPE
   SYNTAX         String
   ACCESS         read-only
   STATUS         mandatory
   DESCRIPTION    "The name of the CIM Provider that monitors this device"
-- REFERENCE      "POWER_DTProcessorDiagnosticsEventIndication.ProviderName"
::= { ibmSystempTrapDTProcessorDiagnosticsBindings 1 }

ibmSystempTrapDTProcessorDiagnosticsEventID OBJECT-TYPE
   SYNTAX         String
   ACCESS         read-only
   STATUS         mandatory
   DESCRIPTION    "A unique EventID that identifies this trap" 
-- REFERENCE      "POWER_DTProcessorDiagnosticsEventIndication.EventID"
::= { ibmSystempTrapDTProcessorDiagnosticsBindings 2 }

ibmSystempTrapDTProcessorDiagnosticsAME OBJECT-TYPE
   SYNTAX         String
   ACCESS         read-only
   STATUS         mandatory
   DESCRIPTION    "A unique string that identifies the monitored device"
-- REFERENCE      "POWER_DTProcessorDiagnosticsEventIndication.AlertingManagedElement"
::= { ibmSystempTrapDTProcessorDiagnosticsBindings 3 }

ibmSystempTrapDTProcessorDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTProcessorDiagnosticsEventIndication.Severity"
::= { ibmSystempTrapDTProcessorDiagnosticsBindings 4 }

ibmSystempTrapDTProcessorDiagnosticsDescription OBJECT-TYPE
   SYNTAX         SnmpAdminString
   ACCESS         read-only
   STATUS         mandatory
   DESCRIPTION    "The Event text of the trap"
-- REFERENCE      "POWER_DTProcessorDiagnosticsEventIndication.Description"
::= { ibmSystempTrapDTProcessorDiagnosticsBindings 5 }

ibmSystempTrapDTProcessorDiagnosticsTimeStamp OBJECT-TYPE
   SYNTAX         Datetime
   ACCESS         read-only
   STATUS         mandatory
   DESCRIPTION    "The time that the trap occurred"
-- REFERENCE      "POWER_DTProcessorDiagnosticsEventIndication.TimeStamp"
::= { ibmSystempTrapDTProcessorDiagnosticsBindings 6 }


ibmSystempTrapPFProcessorDegradPerf TRAP-TYPE
   ENTERPRISE     ibmSystemMIB
   VARIABLES    {
      ibmSystempTrapPFProcessorDegradPerfProviderName,
      ibmSystempTrapPFProcessorDegradPerfEventID,
      ibmSystempTrapPFProcessorDegradPerfAME,
      ibmSystempTrapPFProcessorDegradPerfSeverity,
      ibmSystempTrapPFProcessorDegradPerfDescription,
      ibmSystempTrapPFProcessorDegradPerfTimeStamp
   }
   DESCRIPTION    "A System p event has occurred"
-- REFERENCE      "POWER_PFProcessorDegradPerfEventIndication"
::= 402

ibmSystempTrapPFProcessorDegradPerfBindings OBJECT IDENTIFIER ::= { ibmSystemTrap 402 }

ibmSystempTrapPFProcessorDegradPerfProviderName OBJECT-TYPE
   SYNTAX         String
   ACCESS         read-only
   STATUS         mandatory
   DESCRIPTION    "The name of the CIM Provider that monitors this device"
-- REFERENCE      "POWER_PFProcessorDegradPerfEventIndication.ProviderName"
::= { ibmSystempTrapPFProcessorDegradPerfBindings 1 }

ibmSystempTrapPFProcessorDegradPerfEventID OBJECT-TYPE
   SYNTAX         String
   ACCESS         read-only
   STATUS         mandatory
   DESCRIPTION    "A unique EventID that identifies this trap" 
-- REFERENCE      "POWER_PFProcessorDegradPerfEventIndication.EventID"
::= { ibmSystempTrapPFProcessorDegradPerfBindings 2 }

ibmSystempTrapPFProcessorDegradPerfAME OBJECT-TYPE
   SYNTAX         String
   ACCESS         read-only
   STATUS         mandatory
   DESCRIPTION    "A unique string that identifies the monitored device"
-- REFERENCE      "POWER_PFProcessorDegradPerfEventIndication.AlertingManagedElement"
::= { ibmSystempTrapPFProcessorDegradPerfBindings 3 }

ibmSystempTrapPFProcessorDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFProcessorDegradPerfEventIndication.Severity"
::= { ibmSystempTrapPFProcessorDegradPerfBindings 4 }

ibmSystempTrapPFProcessorDegradPerfDescription OBJECT-TYPE
   SYNTAX         SnmpAdminString
   ACCESS         read-only
   STATUS         mandatory
   DESCRIPTION    "The Event text of the trap"
-- REFERENCE      "POWER_PFProcessorDegradPerfEventIndication.Description"
::= { ibmSystempTrapPFProcessorDegradPerfBindings 5 }

ibmSystempTrapPFProcessorDegradPerfTimeStamp OBJECT-TYPE
   SYNTAX         Datetime
   ACCESS         read-only
   STATUS         mandatory
   DESCRIPTION    "The time that the trap occurred"
-- REFERENCE      "POWER_PFProcessorDegradPerfEventIndication.TimeStamp"
::= { ibmSystempTrapPFProcessorDegradPerfBindings 6 }


ibmSystempTrapPFProcessorCorrectAftIPL TRAP-TYPE
   ENTERPRISE     ibmSystemMIB
   VARIABLES    {
      ibmSystempTrapPFProcessorCorrectAftIPLProviderName,
      ibmSystempTrapPFProcessorCorrectAftIPLEventID,
      ibmSystempTrapPFProcessorCorrectAftIPLAME,
      ibmSystempTrapPFProcessorCorrectAftIPLSeverity,
      ibmSystempTrapPFProcessorCorrectAftIPLDescription,
      ibmSystempTrapPFProcessorCorrectAftIPLTimeStamp
   }
   DESCRIPTION    "A System p event has occurred"
-- REFERENCE      "POWER_PFProcessorCorrectAftIPLEventIndication"
::= 403

ibmSystempTrapPFProcessorCorrectAftIPLBindings OBJECT IDENTIFIER ::= { ibmSystemTrap 403 }

ibmSystempTrapPFProcessorCorrectAftIPLProviderName OBJECT-TYPE
   SYNTAX         String
   ACCESS         read-only
   STATUS         mandatory
   DESCRIPTION    "The name of the CIM Provider that monitors this device"
-- REFERENCE      "POWER_PFProcessorCorrectAftIPLEventIndication.ProviderName"
::= { ibmSystempTrapPFProcessorCorrectAftIPLBindings 1 }

ibmSystempTrapPFProcessorCorrectAftIPLEventID OBJECT-TYPE
   SYNTAX         String
   ACCESS         read-only
   STATUS         mandatory
   DESCRIPTION    "A unique EventID that identifies this trap" 
-- REFERENCE      "POWER_PFProcessorCorrectAftIPLEventIndication.EventID"
::= { ibmSystempTrapPFProcessorCorrectAftIPLBindings 2 }

ibmSystempTrapPFProcessorCorrectAftIPLAME OBJECT-TYPE
   SYNTAX         String
   ACCESS         read-only
   STATUS         mandatory
   DESCRIPTION    "A unique string that identifies the monitored device"
-- REFERENCE      "POWER_PFProcessorCorrectAftIPLEventIndication.AlertingManagedElement"
::= { ibmSystempTrapPFProcessorCorrectAftIPLBindings 3 }

ibmSystempTrapPFProcessorCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFProcessorCorrectAftIPLEventIndication.Severity"
::= { ibmSystempTrapPFProcessorCorrectAftIPLBindings 4 }

ibmSystempTrapPFProcessorCorrectAftIPLDescription OBJECT-TYPE
   SYNTAX         SnmpAdminString
   ACCESS         read-only
   STATUS         mandatory
   DESCRIPTION    "The Event text of the trap"
-- REFERENCE      "POWER_PFProcessorCorrectAftIPLEventIndication.Description"
::= { ibmSystempTrapPFProcessorCorrectAftIPLBindings 5 }

ibmSystempTrapPFProcessorCorrectAftIPLTimeStamp OBJECT-TYPE
   SYNTAX         Datetime
   ACCESS         read-only
   STATUS         mandatory
   DESCRIPTION    "The time that the trap occurred"
-- REFERENCE      "POWER_PFProcessorCorrectAftIPLEventIndication.TimeStamp"
::= { ibmSystempTrapPFProcessorCorrectAftIPLBindings 6 }


ibmSystempTrapPFProcessorCorrectAftIPLPerf TRAP-TYPE
   ENTERPRISE     ibmSystemMIB
   VARIABLES    {
      ibmSystempTrapPFProcessorCorrectAftIPLPerfProviderName,
      ibmSystempTrapPFProcessorCorrectAftIPLPerfEventID,
      ibmSystempTrapPFProcessorCorrectAftIPLPerfAME,
      ibmSystempTrapPFProcessorCorrectAftIPLPerfSeverity,
      ibmSystempTrapPFProcessorCorrectAftIPLPerfDescription,
      ibmSystempTrapPFProcessorCorrectAftIPLPerfTimeStamp
   }
   DESCRIPTION    "A System p event has occurred"
-- REFERENCE      "POWER_PFProcessorCorrectAftIPLPerfEventIndication"
::= 404

ibmSystempTrapPFProcessorCorrectAftIPLPerfBindings OBJECT IDENTIFIER ::= { ibmSystemTrap 404 }

ibmSystempTrapPFProcessorCorrectAftIPLPerfProviderName OBJECT-TYPE
   SYNTAX         String
   ACCESS         read-only
   STATUS         mandatory
   DESCRIPTION    "The name of the CIM Provider that monitors this device"
-- REFERENCE      "POWER_PFProcessorCorrectAftIPLPerfEventIndication.ProviderName"
::= { ibmSystempTrapPFProcessorCorrectAftIPLPerfBindings 1 }

ibmSystempTrapPFProcessorCorrectAftIPLPerfEventID OBJECT-TYPE
   SYNTAX         String
   ACCESS         read-only
   STATUS         mandatory
   DESCRIPTION    "A unique EventID that identifies this trap" 
-- REFERENCE      "POWER_PFProcessorCorrectAftIPLPerfEventIndication.EventID"
::= { ibmSystempTrapPFProcessorCorrectAftIPLPerfBindings 2 }

ibmSystempTrapPFProcessorCorrectAftIPLPerfAME OBJECT-TYPE
   SYNTAX         String
   ACCESS         read-only
   STATUS         mandatory
   DESCRIPTION    "A unique string that identifies the monitored device"
-- REFERENCE      "POWER_PFProcessorCorrectAftIPLPerfEventIndication.AlertingManagedElement"
::= { ibmSystempTrapPFProcessorCorrectAftIPLPerfBindings 3 }

ibmSystempTrapPFProcessorCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFProcessorCorrectAftIPLPerfEventIndication.Severity"
::= { ibmSystempTrapPFProcessorCorrectAftIPLPerfBindings 4 }

ibmSystempTrapPFProcessorCorrectAftIPLPerfDescription OBJECT-TYPE
   SYNTAX         SnmpAdminString
   ACCESS         read-only
   STATUS         mandatory
   DESCRIPTION    "The Event text of the trap"
-- REFERENCE      "POWER_PFProcessorCorrectAftIPLPerfEventIndication.Description"
::= { ibmSystempTrapPFProcessorCorrectAftIPLPerfBindings 5 }

ibmSystempTrapPFProcessorCorrectAftIPLPerfTimeStamp OBJECT-TYPE
   SYNTAX         Datetime
   ACCESS         read-only
   STATUS         mandatory
   DESCRIPTION    "The time that the trap occurred"
-- REFERENCE      "POWER_PFProcessorCorrectAftIPLPerfEventIndication.TimeStamp"
::= { ibmSystempTrapPFProcessorCorrectAftIPLPerfBindings 6 }


ibmSystempTrapPFProcessorLossOfRedundancy TRAP-TYPE
   ENTERPRISE     ibmSystemMIB
   VARIABLES    {
      ibmSystempTrapPFProcessorLossOfRedundancyProviderName,
      ibmSystempTrapPFProcessorLossOfRedundancyEventID,
      ibmSystempTrapPFProcessorLossOfRedundancyAME,
      ibmSystempTrapPFProcessorLossOfRedundancySeverity,
      ibmSystempTrapPFProcessorLossOfRedundancyDescription,
      ibmSystempTrapPFProcessorLossOfRedundancyTimeStamp
   }
   DESCRIPTION    "A System p event has occurred"
-- REFERENCE      "POWER_PFProcessorLossOfRedundancyEventIndication"
::= 405

ibmSystempTrapPFProcessorLossOfRedundancyBindings OBJECT IDENTIFIER ::= { ibmSystemTrap 405 }

ibmSystempTrapPFProcessorLossOfRedundancyProviderName OBJECT-TYPE
   SYNTAX         String
   ACCESS         read-only
   STATUS         mandatory
   DESCRIPTION    "The name of the CIM Provider that monitors this device"
-- REFERENCE      "POWER_PFProcessorLossOfRedundancyEventIndication.ProviderName"
::= { ibmSystempTrapPFProcessorLossOfRedundancyBindings 1 }

ibmSystempTrapPFProcessorLossOfRedundancyEventID OBJECT-TYPE
   SYNTAX         String
   ACCESS         read-only
   STATUS         mandatory
   DESCRIPTION    "A unique EventID that identifies this trap" 
-- REFERENCE      "POWER_PFProcessorLossOfRedundancyEventIndication.EventID"
::= { ibmSystempTrapPFProcessorLossOfRedundancyBindings 2 }

ibmSystempTrapPFProcessorLossOfRedundancyAME OBJECT-TYPE
   SYNTAX         String
   ACCESS         read-only
   STATUS         mandatory
   DESCRIPTION    "A unique string that identifies the monitored device"
-- REFERENCE      "POWER_PFProcessorLossOfRedundancyEventIndication.AlertingManagedElement"
::= { ibmSystempTrapPFProcessorLossOfRedundancyBindings 3 }

ibmSystempTrapPFProcessorLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFProcessorLossOfRedundancyEventIndication.Severity"
::= { ibmSystempTrapPFProcessorLossOfRedundancyBindings 4 }

ibmSystempTrapPFProcessorLossOfRedundancyDescription OBJECT-TYPE
   SYNTAX         SnmpAdminString
   ACCESS         read-only
   STATUS         mandatory
   DESCRIPTION    "The Event text of the trap"
-- REFERENCE      "POWER_PFProcessorLossOfRedundancyEventIndication.Description"
::= { ibmSystempTrapPFProcessorLossOfRedundancyBindings 5 }

ibmSystempTrapPFProcessorLossOfRedundancyTimeStamp OBJECT-TYPE
   SYNTAX         Datetime
   ACCESS         read-only
   STATUS         mandatory
   DESCRIPTION    "The time that the trap occurred"
-- REFERENCE      "POWER_PFProcessorLossOfRedundancyEventIndication.TimeStamp"
::= { ibmSystempTrapPFProcessorLossOfRedundancyBindings 6 }


ibmSystempTrapPFProcessorPredictiveError TRAP-TYPE
   ENTERPRISE     ibmSystemMIB
   VARIABLES    {
      ibmSystempTrapPFProcessorPredictiveErrorProviderName,
      ibmSystempTrapPFProcessorPredictiveErrorEventID,
      ibmSystempTrapPFProcessorPredictiveErrorAME,
      ibmSystempTrapPFProcessorPredictiveErrorSeverity,
      ibmSystempTrapPFProcessorPredictiveErrorDescription,
      ibmSystempTrapPFProcessorPredictiveErrorTimeStamp
   }
   DESCRIPTION    "A System p event has occurred"
-- REFERENCE      "POWER_PFProcessorPredictiveErrorEventIndication"
::= 406

ibmSystempTrapPFProcessorPredictiveErrorBindings OBJECT IDENTIFIER ::= { ibmSystemTrap 406 }

ibmSystempTrapPFProcessorPredictiveErrorProviderName OBJECT-TYPE
   SYNTAX         String
   ACCESS         read-only
   STATUS         mandatory
   DESCRIPTION    "The name of the CIM Provider that monitors this device"
-- REFERENCE      "POWER_PFProcessorPredictiveErrorEventIndication.ProviderName"
::= { ibmSystempTrapPFProcessorPredictiveErrorBindings 1 }

ibmSystempTrapPFProcessorPredictiveErrorEventID OBJECT-TYPE
   SYNTAX         String
   ACCESS         read-only
   STATUS         mandatory
   DESCRIPTION    "A unique EventID that identifies this trap" 
-- REFERENCE      "POWER_PFProcessorPredictiveErrorEventIndication.EventID"
::= { ibmSystempTrapPFProcessorPredictiveErrorBindings 2 }

ibmSystempTrapPFProcessorPredictiveErrorAME OBJECT-TYPE
   SYNTAX         String
   ACCESS         read-only
   STATUS         mandatory
   DESCRIPTION    "A unique string that identifies the monitored device"
-- REFERENCE      "POWER_PFProcessorPredictiveErrorEventIndication.AlertingManagedElement"
::= { ibmSystempTrapPFProcessorPredictiveErrorBindings 3 }

ibmSystempTrapPFProcessorPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFProcessorPredictiveErrorEventIndication.Severity"
::= { ibmSystempTrapPFProcessorPredictiveErrorBindings 4 }

ibmSystempTrapPFProcessorPredictiveErrorDescription OBJECT-TYPE
   SYNTAX         SnmpAdminString
   ACCESS         read-only
   STATUS         mandatory
   DESCRIPTION    "The Event text of the trap"
-- REFERENCE      "POWER_PFProcessorPredictiveErrorEventIndication.Description"
::= { ibmSystempTrapPFProcessorPredictiveErrorBindings 5 }

ibmSystempTrapPFProcessorPredictiveErrorTimeStamp OBJECT-TYPE
   SYNTAX         Datetime
   ACCESS         read-only
   STATUS         mandatory
   DESCRIPTION    "The time that the trap occurred"
-- REFERENCE      "POWER_PFProcessorPredictiveErrorEventIndication.TimeStamp"
::= { ibmSystempTrapPFProcessorPredictiveErrorBindings 6 }


ibmSystempTrapUEProcessorDegradPerf TRAP-TYPE
   ENTERPRISE     ibmSystemMIB
   VARIABLES    {
      ibmSystempTrapUEProcessorDegradPerfProviderName,
      ibmSystempTrapUEProcessorDegradPerfEventID,
      ibmSystempTrapUEProcessorDegradPerfAME,
      ibmSystempTrapUEProcessorDegradPerfSeverity,
      ibmSystempTrapUEProcessorDegradPerfDescription,
      ibmSystempTrapUEProcessorDegradPerfTimeStamp
   }
   DESCRIPTION    "A System p event has occurred"
-- REFERENCE      "POWER_UEProcessorDegradPerfEventIndication"
::= 407

ibmSystempTrapUEProcessorDegradPerfBindings OBJECT IDENTIFIER ::= { ibmSystemTrap 407 }

ibmSystempTrapUEProcessorDegradPerfProviderName OBJECT-TYPE
   SYNTAX         String
   ACCESS         read-only
   STATUS         mandatory
   DESCRIPTION    "The name of the CIM Provider that monitors this device"
-- REFERENCE      "POWER_UEProcessorDegradPerfEventIndication.ProviderName"
::= { ibmSystempTrapUEProcessorDegradPerfBindings 1 }

ibmSystempTrapUEProcessorDegradPerfEventID OBJECT-TYPE
   SYNTAX         String
   ACCESS         read-only
   STATUS         mandatory
   DESCRIPTION    "A unique EventID that identifies this trap" 
-- REFERENCE      "POWER_UEProcessorDegradPerfEventIndication.EventID"
::= { ibmSystempTrapUEProcessorDegradPerfBindings 2 }

ibmSystempTrapUEProcessorDegradPerfAME OBJECT-TYPE
   SYNTAX         String
   ACCESS         read-only
   STATUS         mandatory
   DESCRIPTION    "A unique string that identifies the monitored device"
-- REFERENCE      "POWER_UEProcessorDegradPerfEventIndication.AlertingManagedElement"
::= { ibmSystempTrapUEProcessorDegradPerfBindings 3 }

ibmSystempTrapUEProcessorDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEProcessorDegradPerfEventIndication.Severity"
::= { ibmSystempTrapUEProcessorDegradPerfBindings 4 }

ibmSystempTrapUEProcessorDegradPerfDescription OBJECT-TYPE
   SYNTAX         SnmpAdminString
   ACCESS         read-only
   STATUS         mandatory
   DESCRIPTION    "The Event text of the trap"
-- REFERENCE      "POWER_UEProcessorDegradPerfEventIndication.Description"
::= { ibmSystempTrapUEProcessorDegradPerfBindings 5 }

ibmSystempTrapUEProcessorDegradPerfTimeStamp OBJECT-TYPE
   SYNTAX         Datetime
   ACCESS         read-only
   STATUS         mandatory
   DESCRIPTION    "The time that the trap occurred"
-- REFERENCE      "POWER_UEProcessorDegradPerfEventIndication.TimeStamp"
::= { ibmSystempTrapUEProcessorDegradPerfBindings 6 }


ibmSystempTrapUEProcessorLossOfRedundancy TRAP-TYPE
   ENTERPRISE     ibmSystemMIB
   VARIABLES    {
      ibmSystempTrapUEProcessorLossOfRedundancyProviderName,
      ibmSystempTrapUEProcessorLossOfRedundancyEventID,
      ibmSystempTrapUEProcessorLossOfRedundancyAME,
      ibmSystempTrapUEProcessorLossOfRedundancySeverity,
      ibmSystempTrapUEProcessorLossOfRedundancyDescription,
      ibmSystempTrapUEProcessorLossOfRedundancyTimeStamp
   }
   DESCRIPTION    "A System p event has occurred"
-- REFERENCE      "POWER_UEProcessorLossOfRedundancyEventIndication"
::= 408

ibmSystempTrapUEProcessorLossOfRedundancyBindings OBJECT IDENTIFIER ::= { ibmSystemTrap 408 }

ibmSystempTrapUEProcessorLossOfRedundancyProviderName OBJECT-TYPE
   SYNTAX         String
   ACCESS         read-only
   STATUS         mandatory
   DESCRIPTION    "The name of the CIM Provider that monitors this device"
-- REFERENCE      "POWER_UEProcessorLossOfRedundancyEventIndication.ProviderName"
::= { ibmSystempTrapUEProcessorLossOfRedundancyBindings 1 }

ibmSystempTrapUEProcessorLossOfRedundancyEventID OBJECT-TYPE
   SYNTAX         String
   ACCESS         read-only
   STATUS         mandatory
   DESCRIPTION    "A unique EventID that identifies this trap" 
-- REFERENCE      "POWER_UEProcessorLossOfRedundancyEventIndication.EventID"
::= { ibmSystempTrapUEProcessorLossOfRedundancyBindings 2 }

ibmSystempTrapUEProcessorLossOfRedundancyAME OBJECT-TYPE
   SYNTAX         String
   ACCESS         read-only
   STATUS         mandatory
   DESCRIPTION    "A unique string that identifies the monitored device"
-- REFERENCE      "POWER_UEProcessorLossOfRedundancyEventIndication.AlertingManagedElement"
::= { ibmSystempTrapUEProcessorLossOfRedundancyBindings 3 }

ibmSystempTrapUEProcessorLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEProcessorLossOfRedundancyEventIndication.Severity"
::= { ibmSystempTrapUEProcessorLossOfRedundancyBindings 4 }

ibmSystempTrapUEProcessorLossOfRedundancyDescription OBJECT-TYPE
   SYNTAX         SnmpAdminString
   ACCESS         read-only
   STATUS         mandatory
   DESCRIPTION    "The Event text of the trap"
-- REFERENCE      "POWER_UEProcessorLossOfRedundancyEventIndication.Description"
::= { ibmSystempTrapUEProcessorLossOfRedundancyBindings 5 }

ibmSystempTrapUEProcessorLossOfRedundancyTimeStamp OBJECT-TYPE
   SYNTAX         Datetime
   ACCESS         read-only
   STATUS         mandatory
   DESCRIPTION    "The time that the trap occurred"
-- REFERENCE      "POWER_UEProcessorLossOfRedundancyEventIndication.TimeStamp"
::= { ibmSystempTrapUEProcessorLossOfRedundancyBindings 6 }


ibmSystempTrapUEProcessorLossOfRedundAndPerf TRAP-TYPE
   ENTERPRISE     ibmSystemMIB
   VARIABLES    {
      ibmSystempTrapUEProcessorLossOfRedundAndPerfProviderName,
      ibmSystempTrapUEProcessorLossOfRedundAndPerfEventID,
      ibmSystempTrapUEProcessorLossOfRedundAndPerfAME,
      ibmSystempTrapUEProcessorLossOfRedundAndPerfSeverity,
      ibmSystempTrapUEProcessorLossOfRedundAndPerfDescription,
      ibmSystempTrapUEProcessorLossOfRedundAndPerfTimeStamp
   }
   DESCRIPTION    "A System p event has occurred"
-- REFERENCE      "POWER_UEProcessorLossOfRedundAndPerfEventIndication"
::= 409

ibmSystempTrapUEProcessorLossOfRedundAndPerfBindings OBJECT IDENTIFIER ::= { ibmSystemTrap 409 }

ibmSystempTrapUEProcessorLossOfRedundAndPerfProviderName OBJECT-TYPE
   SYNTAX         String
   ACCESS         read-only
   STATUS         mandatory
   DESCRIPTION    "The name of the CIM Provider that monitors this device"
-- REFERENCE      "POWER_UEProcessorLossOfRedundAndPerfEventIndication.ProviderName"
::= { ibmSystempTrapUEProcessorLossOfRedundAndPerfBindings 1 }

ibmSystempTrapUEProcessorLossOfRedundAndPerfEventID OBJECT-TYPE
   SYNTAX         String
   ACCESS         read-only
   STATUS         mandatory
   DESCRIPTION    "A unique EventID that identifies this trap" 
-- REFERENCE      "POWER_UEProcessorLossOfRedundAndPerfEventIndication.EventID"
::= { ibmSystempTrapUEProcessorLossOfRedundAndPerfBindings 2 }

ibmSystempTrapUEProcessorLossOfRedundAndPerfAME OBJECT-TYPE
   SYNTAX         String
   ACCESS         read-only
   STATUS         mandatory
   DESCRIPTION    "A unique string that identifies the monitored device"
-- REFERENCE      "POWER_UEProcessorLossOfRedundAndPerfEventIndication.AlertingManagedElement"
::= { ibmSystempTrapUEProcessorLossOfRedundAndPerfBindings 3 }

ibmSystempTrapUEProcessorLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEProcessorLossOfRedundAndPerfEventIndication.Severity"
::= { ibmSystempTrapUEProcessorLossOfRedundAndPerfBindings 4 }

ibmSystempTrapUEProcessorLossOfRedundAndPerfDescription OBJECT-TYPE
   SYNTAX         SnmpAdminString
   ACCESS         read-only
   STATUS         mandatory
   DESCRIPTION    "The Event text of the trap"
-- REFERENCE      "POWER_UEProcessorLossOfRedundAndPerfEventIndication.Description"
::= { ibmSystempTrapUEProcessorLossOfRedundAndPerfBindings 5 }

ibmSystempTrapUEProcessorLossOfRedundAndPerfTimeStamp OBJECT-TYPE
   SYNTAX         Datetime
   ACCESS         read-only
   STATUS         mandatory
   DESCRIPTION    "The time that the trap occurred"
-- REFERENCE      "POWER_UEProcessorLossOfRedundAndPerfEventIndication.TimeStamp"
::= { ibmSystempTrapUEProcessorLossOfRedundAndPerfBindings 6 }


ibmSystempTrapUEProcessorLossOfFunction TRAP-TYPE
   ENTERPRISE     ibmSystemMIB
   VARIABLES    {
      ibmSystempTrapUEProcessorLossOfFunctionProviderName,
      ibmSystempTrapUEProcessorLossOfFunctionEventID,
      ibmSystempTrapUEProcessorLossOfFunctionAME,
      ibmSystempTrapUEProcessorLossOfFunctionSeverity,
      ibmSystempTrapUEProcessorLossOfFunctionDescription,
      ibmSystempTrapUEProcessorLossOfFunctionTimeStamp
   }
   DESCRIPTION    "A System p event has occurred"
-- REFERENCE      "POWER_UEProcessorLossOfFunctionEventIndication"
::= 410

ibmSystempTrapUEProcessorLossOfFunctionBindings OBJECT IDENTIFIER ::= { ibmSystemTrap 410 }

ibmSystempTrapUEProcessorLossOfFunctionProviderName OBJECT-TYPE
   SYNTAX         String
   ACCESS         read-only
   STATUS         mandatory
   DESCRIPTION    "The name of the CIM Provider that monitors this device"
-- REFERENCE      "POWER_UEProcessorLossOfFunctionEventIndication.ProviderName"
::= { ibmSystempTrapUEProcessorLossOfFunctionBindings 1 }

ibmSystempTrapUEProcessorLossOfFunctionEventID OBJECT-TYPE
   SYNTAX         String
   ACCESS         read-only
   STATUS         mandatory
   DESCRIPTION    "A unique EventID that identifies this trap" 
-- REFERENCE      "POWER_UEProcessorLossOfFunctionEventIndication.EventID"
::= { ibmSystempTrapUEProcessorLossOfFunctionBindings 2 }

ibmSystempTrapUEProcessorLossOfFunctionAME OBJECT-TYPE
   SYNTAX         String
   ACCESS         read-only
   STATUS         mandatory
   DESCRIPTION    "A unique string that identifies the monitored device"
-- REFERENCE      "POWER_UEProcessorLossOfFunctionEventIndication.AlertingManagedElement"
::= { ibmSystempTrapUEProcessorLossOfFunctionBindings 3 }

ibmSystempTrapUEProcessorLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEProcessorLossOfFunctionEventIndication.Severity"
::= { ibmSystempTrapUEProcessorLossOfFunctionBindings 4 }

ibmSystempTrapUEProcessorLossOfFunctionDescription OBJECT-TYPE
   SYNTAX         SnmpAdminString
   ACCESS         read-only
   STATUS         mandatory
   DESCRIPTION    "The Event text of the trap"
-- REFERENCE      "POWER_UEProcessorLossOfFunctionEventIndication.Description"
::= { ibmSystempTrapUEProcessorLossOfFunctionBindings 5 }

ibmSystempTrapUEProcessorLossOfFunctionTimeStamp OBJECT-TYPE
   SYNTAX         Datetime
   ACCESS         read-only
   STATUS         mandatory
   DESCRIPTION    "The time that the trap occurred"
-- REFERENCE      "POWER_UEProcessorLossOfFunctionEventIndication.TimeStamp"
::= { ibmSystempTrapUEProcessorLossOfFunctionBindings 6 }


ibmSystempTrapUEProcessorUnrecoverableError TRAP-TYPE
   ENTERPRISE     ibmSystemMIB
   VARIABLES    {
      ibmSystempTrapUEProcessorUnrecoverableErrorProviderName,
      ibmSystempTrapUEProcessorUnrecoverableErrorEventID,
      ibmSystempTrapUEProcessorUnrecoverableErrorAME,
      ibmSystempTrapUEProcessorUnrecoverableErrorSeverity,
      ibmSystempTrapUEProcessorUnrecoverableErrorDescription,
      ibmSystempTrapUEProcessorUnrecoverableErrorTimeStamp
   }
   DESCRIPTION    "A System p event has occurred"
-- REFERENCE      "POWER_UEProcessorUnrecoverableErrorEventIndication"
::= 411

ibmSystempTrapUEProcessorUnrecoverableErrorBindings OBJECT IDENTIFIER ::= { ibmSystemTrap 411 }

ibmSystempTrapUEProcessorUnrecoverableErrorProviderName OBJECT-TYPE
   SYNTAX         String
   ACCESS         read-only
   STATUS         mandatory
   DESCRIPTION    "The name of the CIM Provider that monitors this device"
-- REFERENCE      "POWER_UEProcessorUnrecoverableErrorEventIndication.ProviderName"
::= { ibmSystempTrapUEProcessorUnrecoverableErrorBindings 1 }

ibmSystempTrapUEProcessorUnrecoverableErrorEventID OBJECT-TYPE
   SYNTAX         String
   ACCESS         read-only
   STATUS         mandatory
   DESCRIPTION    "A unique EventID that identifies this trap" 
-- REFERENCE      "POWER_UEProcessorUnrecoverableErrorEventIndication.EventID"
::= { ibmSystempTrapUEProcessorUnrecoverableErrorBindings 2 }

ibmSystempTrapUEProcessorUnrecoverableErrorAME OBJECT-TYPE
   SYNTAX         String
   ACCESS         read-only
   STATUS         mandatory
   DESCRIPTION    "A unique string that identifies the monitored device"
-- REFERENCE      "POWER_UEProcessorUnrecoverableErrorEventIndication.AlertingManagedElement"
::= { ibmSystempTrapUEProcessorUnrecoverableErrorBindings 3 }

ibmSystempTrapUEProcessorUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEProcessorUnrecoverableErrorEventIndication.Severity"
::= { ibmSystempTrapUEProcessorUnrecoverableErrorBindings 4 }

ibmSystempTrapUEProcessorUnrecoverableErrorDescription OBJECT-TYPE
   SYNTAX         SnmpAdminString
   ACCESS         read-only
   STATUS         mandatory
   DESCRIPTION    "The Event text of the trap"
-- REFERENCE      "POWER_UEProcessorUnrecoverableErrorEventIndication.Description"
::= { ibmSystempTrapUEProcessorUnrecoverableErrorBindings 5 }

ibmSystempTrapUEProcessorUnrecoverableErrorTimeStamp OBJECT-TYPE
   SYNTAX         Datetime
   ACCESS         read-only
   STATUS         mandatory
   DESCRIPTION    "The time that the trap occurred"
-- REFERENCE      "POWER_UEProcessorUnrecoverableErrorEventIndication.TimeStamp"
::= { ibmSystempTrapUEProcessorUnrecoverableErrorBindings 6 }


ibmSystempTrapDTMemoryDiagnostics TRAP-TYPE
   ENTERPRISE     ibmSystemMIB
   VARIABLES    {
      ibmSystempTrapDTMemoryDiagnosticsProviderName,
      ibmSystempTrapDTMemoryDiagnosticsEventID,
      ibmSystempTrapDTMemoryDiagnosticsAME,
      ibmSystempTrapDTMemoryDiagnosticsSeverity,
      ibmSystempTrapDTMemoryDiagnosticsDescription,
      ibmSystempTrapDTMemoryDiagnosticsTimeStamp
   }
   DESCRIPTION    "A System p event has occurred"
-- REFERENCE      "POWER_DTMemoryDiagnosticsEventIndication"
::= 412

ibmSystempTrapDTMemoryDiagnosticsBindings OBJECT IDENTIFIER ::= { ibmSystemTrap 412 }

ibmSystempTrapDTMemoryDiagnosticsProviderName OBJECT-TYPE
   SYNTAX         String
   ACCESS         read-only
   STATUS         mandatory
   DESCRIPTION    "The name of the CIM Provider that monitors this device"
-- REFERENCE      "POWER_DTMemoryDiagnosticsEventIndication.ProviderName"
::= { ibmSystempTrapDTMemoryDiagnosticsBindings 1 }

ibmSystempTrapDTMemoryDiagnosticsEventID OBJECT-TYPE
   SYNTAX         String
   ACCESS         read-only
   STATUS         mandatory
   DESCRIPTION    "A unique EventID that identifies this trap" 
-- REFERENCE      "POWER_DTMemoryDiagnosticsEventIndication.EventID"
::= { ibmSystempTrapDTMemoryDiagnosticsBindings 2 }

ibmSystempTrapDTMemoryDiagnosticsAME OBJECT-TYPE
   SYNTAX         String
   ACCESS         read-only
   STATUS         mandatory
   DESCRIPTION    "A unique string that identifies the monitored device"
-- REFERENCE      "POWER_DTMemoryDiagnosticsEventIndication.AlertingManagedElement"
::= { ibmSystempTrapDTMemoryDiagnosticsBindings 3 }

ibmSystempTrapDTMemoryDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTMemoryDiagnosticsEventIndication.Severity"
::= { ibmSystempTrapDTMemoryDiagnosticsBindings 4 }

ibmSystempTrapDTMemoryDiagnosticsDescription OBJECT-TYPE
   SYNTAX         SnmpAdminString
   ACCESS         read-only
   STATUS         mandatory
   DESCRIPTION    "The Event text of the trap"
-- REFERENCE      "POWER_DTMemoryDiagnosticsEventIndication.Description"
::= { ibmSystempTrapDTMemoryDiagnosticsBindings 5 }

ibmSystempTrapDTMemoryDiagnosticsTimeStamp OBJECT-TYPE
   SYNTAX         Datetime
   ACCESS         read-only
   STATUS         mandatory
   DESCRIPTION    "The time that the trap occurred"
-- REFERENCE      "POWER_DTMemoryDiagnosticsEventIndication.TimeStamp"
::= { ibmSystempTrapDTMemoryDiagnosticsBindings 6 }


ibmSystempTrapPFMemoryDegradPerf TRAP-TYPE
   ENTERPRISE     ibmSystemMIB
   VARIABLES    {
      ibmSystempTrapPFMemoryDegradPerfProviderName,
      ibmSystempTrapPFMemoryDegradPerfEventID,
      ibmSystempTrapPFMemoryDegradPerfAME,
      ibmSystempTrapPFMemoryDegradPerfSeverity,
      ibmSystempTrapPFMemoryDegradPerfDescription,
      ibmSystempTrapPFMemoryDegradPerfTimeStamp
   }
   DESCRIPTION    "A System p event has occurred"
-- REFERENCE      "POWER_PFMemoryDegradPerfEventIndication"
::= 413

ibmSystempTrapPFMemoryDegradPerfBindings OBJECT IDENTIFIER ::= { ibmSystemTrap 413 }

ibmSystempTrapPFMemoryDegradPerfProviderName OBJECT-TYPE
   SYNTAX         String
   ACCESS         read-only
   STATUS         mandatory
   DESCRIPTION    "The name of the CIM Provider that monitors this device"
-- REFERENCE      "POWER_PFMemoryDegradPerfEventIndication.ProviderName"
::= { ibmSystempTrapPFMemoryDegradPerfBindings 1 }

ibmSystempTrapPFMemoryDegradPerfEventID OBJECT-TYPE
   SYNTAX         String
   ACCESS         read-only
   STATUS         mandatory
   DESCRIPTION    "A unique EventID that identifies this trap" 
-- REFERENCE      "POWER_PFMemoryDegradPerfEventIndication.EventID"
::= { ibmSystempTrapPFMemoryDegradPerfBindings 2 }

ibmSystempTrapPFMemoryDegradPerfAME OBJECT-TYPE
   SYNTAX         String
   ACCESS         read-only
   STATUS         mandatory
   DESCRIPTION    "A unique string that identifies the monitored device"
-- REFERENCE      "POWER_PFMemoryDegradPerfEventIndication.AlertingManagedElement"
::= { ibmSystempTrapPFMemoryDegradPerfBindings 3 }

ibmSystempTrapPFMemoryDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFMemoryDegradPerfEventIndication.Severity"
::= { ibmSystempTrapPFMemoryDegradPerfBindings 4 }

ibmSystempTrapPFMemoryDegradPerfDescription OBJECT-TYPE
   SYNTAX         SnmpAdminString
   ACCESS         read-only
   STATUS         mandatory
   DESCRIPTION    "The Event text of the trap"
-- REFERENCE      "POWER_PFMemoryDegradPerfEventIndication.Description"
::= { ibmSystempTrapPFMemoryDegradPerfBindings 5 }

ibmSystempTrapPFMemoryDegradPerfTimeStamp OBJECT-TYPE
   SYNTAX         Datetime
   ACCESS         read-only
   STATUS         mandatory
   DESCRIPTION    "The time that the trap occurred"
-- REFERENCE      "POWER_PFMemoryDegradPerfEventIndication.TimeStamp"
::= { ibmSystempTrapPFMemoryDegradPerfBindings 6 }


ibmSystempTrapPFMemoryCorrectAftIPL TRAP-TYPE
   ENTERPRISE     ibmSystemMIB
   VARIABLES    {
      ibmSystempTrapPFMemoryCorrectAftIPLProviderName,
      ibmSystempTrapPFMemoryCorrectAftIPLEventID,
      ibmSystempTrapPFMemoryCorrectAftIPLAME,
      ibmSystempTrapPFMemoryCorrectAftIPLSeverity,
      ibmSystempTrapPFMemoryCorrectAftIPLDescription,
      ibmSystempTrapPFMemoryCorrectAftIPLTimeStamp
   }
   DESCRIPTION    "A System p event has occurred"
-- REFERENCE      "POWER_PFMemoryCorrectAftIPLEventIndication"
::= 414

ibmSystempTrapPFMemoryCorrectAftIPLBindings OBJECT IDENTIFIER ::= { ibmSystemTrap 414 }

ibmSystempTrapPFMemoryCorrectAftIPLProviderName OBJECT-TYPE
   SYNTAX         String
   ACCESS         read-only
   STATUS         mandatory
   DESCRIPTION    "The name of the CIM Provider that monitors this device"
-- REFERENCE      "POWER_PFMemoryCorrectAftIPLEventIndication.ProviderName"
::= { ibmSystempTrapPFMemoryCorrectAftIPLBindings 1 }

ibmSystempTrapPFMemoryCorrectAftIPLEventID OBJECT-TYPE
   SYNTAX         String
   ACCESS         read-only
   STATUS         mandatory
   DESCRIPTION    "A unique EventID that identifies this trap" 
-- REFERENCE      "POWER_PFMemoryCorrectAftIPLEventIndication.EventID"
::= { ibmSystempTrapPFMemoryCorrectAftIPLBindings 2 }

ibmSystempTrapPFMemoryCorrectAftIPLAME OBJECT-TYPE
   SYNTAX         String
   ACCESS         read-only
   STATUS         mandatory
   DESCRIPTION    "A unique string that identifies the monitored device"
-- REFERENCE      "POWER_PFMemoryCorrectAftIPLEventIndication.AlertingManagedElement"
::= { ibmSystempTrapPFMemoryCorrectAftIPLBindings 3 }

ibmSystempTrapPFMemoryCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFMemoryCorrectAftIPLEventIndication.Severity"
::= { ibmSystempTrapPFMemoryCorrectAftIPLBindings 4 }

ibmSystempTrapPFMemoryCorrectAftIPLDescription OBJECT-TYPE
   SYNTAX         SnmpAdminString
   ACCESS         read-only
   STATUS         mandatory
   DESCRIPTION    "The Event text of the trap"
-- REFERENCE      "POWER_PFMemoryCorrectAftIPLEventIndication.Description"
::= { ibmSystempTrapPFMemoryCorrectAftIPLBindings 5 }

ibmSystempTrapPFMemoryCorrectAftIPLTimeStamp OBJECT-TYPE
   SYNTAX         Datetime
   ACCESS         read-only
   STATUS         mandatory
   DESCRIPTION    "The time that the trap occurred"
-- REFERENCE      "POWER_PFMemoryCorrectAftIPLEventIndication.TimeStamp"
::= { ibmSystempTrapPFMemoryCorrectAftIPLBindings 6 }


ibmSystempTrapPFMemoryCorrectAftIPLPerf TRAP-TYPE
   ENTERPRISE     ibmSystemMIB
   VARIABLES    {
      ibmSystempTrapPFMemoryCorrectAftIPLPerfProviderName,
      ibmSystempTrapPFMemoryCorrectAftIPLPerfEventID,
      ibmSystempTrapPFMemoryCorrectAftIPLPerfAME,
      ibmSystempTrapPFMemoryCorrectAftIPLPerfSeverity,
      ibmSystempTrapPFMemoryCorrectAftIPLPerfDescription,
      ibmSystempTrapPFMemoryCorrectAftIPLPerfTimeStamp
   }
   DESCRIPTION    "A System p event has occurred"
-- REFERENCE      "POWER_PFMemoryCorrectAftIPLPerfEventIndication"
::= 415

ibmSystempTrapPFMemoryCorrectAftIPLPerfBindings OBJECT IDENTIFIER ::= { ibmSystemTrap 415 }

ibmSystempTrapPFMemoryCorrectAftIPLPerfProviderName OBJECT-TYPE
   SYNTAX         String
   ACCESS         read-only
   STATUS         mandatory
   DESCRIPTION    "The name of the CIM Provider that monitors this device"
-- REFERENCE      "POWER_PFMemoryCorrectAftIPLPerfEventIndication.ProviderName"
::= { ibmSystempTrapPFMemoryCorrectAftIPLPerfBindings 1 }

ibmSystempTrapPFMemoryCorrectAftIPLPerfEventID OBJECT-TYPE
   SYNTAX         String
   ACCESS         read-only
   STATUS         mandatory
   DESCRIPTION    "A unique EventID that identifies this trap" 
-- REFERENCE      "POWER_PFMemoryCorrectAftIPLPerfEventIndication.EventID"
::= { ibmSystempTrapPFMemoryCorrectAftIPLPerfBindings 2 }

ibmSystempTrapPFMemoryCorrectAftIPLPerfAME OBJECT-TYPE
   SYNTAX         String
   ACCESS         read-only
   STATUS         mandatory
   DESCRIPTION    "A unique string that identifies the monitored device"
-- REFERENCE      "POWER_PFMemoryCorrectAftIPLPerfEventIndication.AlertingManagedElement"
::= { ibmSystempTrapPFMemoryCorrectAftIPLPerfBindings 3 }

ibmSystempTrapPFMemoryCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFMemoryCorrectAftIPLPerfEventIndication.Severity"
::= { ibmSystempTrapPFMemoryCorrectAftIPLPerfBindings 4 }

ibmSystempTrapPFMemoryCorrectAftIPLPerfDescription OBJECT-TYPE
   SYNTAX         SnmpAdminString
   ACCESS         read-only
   STATUS         mandatory
   DESCRIPTION    "The Event text of the trap"
-- REFERENCE      "POWER_PFMemoryCorrectAftIPLPerfEventIndication.Description"
::= { ibmSystempTrapPFMemoryCorrectAftIPLPerfBindings 5 }

ibmSystempTrapPFMemoryCorrectAftIPLPerfTimeStamp OBJECT-TYPE
   SYNTAX         Datetime
   ACCESS         read-only
   STATUS         mandatory
   DESCRIPTION    "The time that the trap occurred"
-- REFERENCE      "POWER_PFMemoryCorrectAftIPLPerfEventIndication.TimeStamp"
::= { ibmSystempTrapPFMemoryCorrectAftIPLPerfBindings 6 }


ibmSystempTrapPFMemoryLossOfRedundancy TRAP-TYPE
   ENTERPRISE     ibmSystemMIB
   VARIABLES    {
      ibmSystempTrapPFMemoryLossOfRedundancyProviderName,
      ibmSystempTrapPFMemoryLossOfRedundancyEventID,
      ibmSystempTrapPFMemoryLossOfRedundancyAME,
      ibmSystempTrapPFMemoryLossOfRedundancySeverity,
      ibmSystempTrapPFMemoryLossOfRedundancyDescription,
      ibmSystempTrapPFMemoryLossOfRedundancyTimeStamp
   }
   DESCRIPTION    "A System p event has occurred"
-- REFERENCE      "POWER_PFMemoryLossOfRedundancyEventIndication"
::= 416

ibmSystempTrapPFMemoryLossOfRedundancyBindings OBJECT IDENTIFIER ::= { ibmSystemTrap 416 }

ibmSystempTrapPFMemoryLossOfRedundancyProviderName OBJECT-TYPE
   SYNTAX         String
   ACCESS         read-only
   STATUS         mandatory
   DESCRIPTION    "The name of the CIM Provider that monitors this device"
-- REFERENCE      "POWER_PFMemoryLossOfRedundancyEventIndication.ProviderName"
::= { ibmSystempTrapPFMemoryLossOfRedundancyBindings 1 }

ibmSystempTrapPFMemoryLossOfRedundancyEventID OBJECT-TYPE
   SYNTAX         String
   ACCESS         read-only
   STATUS         mandatory
   DESCRIPTION    "A unique EventID that identifies this trap" 
-- REFERENCE      "POWER_PFMemoryLossOfRedundancyEventIndication.EventID"
::= { ibmSystempTrapPFMemoryLossOfRedundancyBindings 2 }

ibmSystempTrapPFMemoryLossOfRedundancyAME OBJECT-TYPE
   SYNTAX         String
   ACCESS         read-only
   STATUS         mandatory
   DESCRIPTION    "A unique string that identifies the monitored device"
-- REFERENCE      "POWER_PFMemoryLossOfRedundancyEventIndication.AlertingManagedElement"
::= { ibmSystempTrapPFMemoryLossOfRedundancyBindings 3 }

ibmSystempTrapPFMemoryLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFMemoryLossOfRedundancyEventIndication.Severity"
::= { ibmSystempTrapPFMemoryLossOfRedundancyBindings 4 }

ibmSystempTrapPFMemoryLossOfRedundancyDescription OBJECT-TYPE
   SYNTAX         SnmpAdminString
   ACCESS         read-only
   STATUS         mandatory
   DESCRIPTION    "The Event text of the trap"
-- REFERENCE      "POWER_PFMemoryLossOfRedundancyEventIndication.Description"
::= { ibmSystempTrapPFMemoryLossOfRedundancyBindings 5 }

ibmSystempTrapPFMemoryLossOfRedundancyTimeStamp OBJECT-TYPE
   SYNTAX         Datetime
   ACCESS         read-only
   STATUS         mandatory
   DESCRIPTION    "The time that the trap occurred"
-- REFERENCE      "POWER_PFMemoryLossOfRedundancyEventIndication.TimeStamp"
::= { ibmSystempTrapPFMemoryLossOfRedundancyBindings 6 }


ibmSystempTrapPFMemoryPredictiveError TRAP-TYPE
   ENTERPRISE     ibmSystemMIB
   VARIABLES    {
      ibmSystempTrapPFMemoryPredictiveErrorProviderName,
      ibmSystempTrapPFMemoryPredictiveErrorEventID,
      ibmSystempTrapPFMemoryPredictiveErrorAME,
      ibmSystempTrapPFMemoryPredictiveErrorSeverity,
      ibmSystempTrapPFMemoryPredictiveErrorDescription,
      ibmSystempTrapPFMemoryPredictiveErrorTimeStamp
   }
   DESCRIPTION    "A System p event has occurred"
-- REFERENCE      "POWER_PFMemoryPredictiveErrorEventIndication"
::= 417

ibmSystempTrapPFMemoryPredictiveErrorBindings OBJECT IDENTIFIER ::= { ibmSystemTrap 417 }

ibmSystempTrapPFMemoryPredictiveErrorProviderName OBJECT-TYPE
   SYNTAX         String
   ACCESS         read-only
   STATUS         mandatory
   DESCRIPTION    "The name of the CIM Provider that monitors this device"
-- REFERENCE      "POWER_PFMemoryPredictiveErrorEventIndication.ProviderName"
::= { ibmSystempTrapPFMemoryPredictiveErrorBindings 1 }

ibmSystempTrapPFMemoryPredictiveErrorEventID OBJECT-TYPE
   SYNTAX         String
   ACCESS         read-only
   STATUS         mandatory
   DESCRIPTION    "A unique EventID that identifies this trap" 
-- REFERENCE      "POWER_PFMemoryPredictiveErrorEventIndication.EventID"
::= { ibmSystempTrapPFMemoryPredictiveErrorBindings 2 }

ibmSystempTrapPFMemoryPredictiveErrorAME OBJECT-TYPE
   SYNTAX         String
   ACCESS         read-only
   STATUS         mandatory
   DESCRIPTION    "A unique string that identifies the monitored device"
-- REFERENCE      "POWER_PFMemoryPredictiveErrorEventIndication.AlertingManagedElement"
::= { ibmSystempTrapPFMemoryPredictiveErrorBindings 3 }

ibmSystempTrapPFMemoryPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFMemoryPredictiveErrorEventIndication.Severity"
::= { ibmSystempTrapPFMemoryPredictiveErrorBindings 4 }

ibmSystempTrapPFMemoryPredictiveErrorDescription OBJECT-TYPE
   SYNTAX         SnmpAdminString
   ACCESS         read-only
   STATUS         mandatory
   DESCRIPTION    "The Event text of the trap"
-- REFERENCE      "POWER_PFMemoryPredictiveErrorEventIndication.Description"
::= { ibmSystempTrapPFMemoryPredictiveErrorBindings 5 }

ibmSystempTrapPFMemoryPredictiveErrorTimeStamp OBJECT-TYPE
   SYNTAX         Datetime
   ACCESS         read-only
   STATUS         mandatory
   DESCRIPTION    "The time that the trap occurred"
-- REFERENCE      "POWER_PFMemoryPredictiveErrorEventIndication.TimeStamp"
::= { ibmSystempTrapPFMemoryPredictiveErrorBindings 6 }


ibmSystempTrapUEMemoryDegradPerf TRAP-TYPE
   ENTERPRISE     ibmSystemMIB
   VARIABLES    {
      ibmSystempTrapUEMemoryDegradPerfProviderName,
      ibmSystempTrapUEMemoryDegradPerfEventID,
      ibmSystempTrapUEMemoryDegradPerfAME,
      ibmSystempTrapUEMemoryDegradPerfSeverity,
      ibmSystempTrapUEMemoryDegradPerfDescription,
      ibmSystempTrapUEMemoryDegradPerfTimeStamp
   }
   DESCRIPTION    "A System p event has occurred"
-- REFERENCE      "POWER_UEMemoryDegradPerfEventIndication"
::= 418

ibmSystempTrapUEMemoryDegradPerfBindings OBJECT IDENTIFIER ::= { ibmSystemTrap 418 }

ibmSystempTrapUEMemoryDegradPerfProviderName OBJECT-TYPE
   SYNTAX         String
   ACCESS         read-only
   STATUS         mandatory
   DESCRIPTION    "The name of the CIM Provider that monitors this device"
-- REFERENCE      "POWER_UEMemoryDegradPerfEventIndication.ProviderName"
::= { ibmSystempTrapUEMemoryDegradPerfBindings 1 }

ibmSystempTrapUEMemoryDegradPerfEventID OBJECT-TYPE
   SYNTAX         String
   ACCESS         read-only
   STATUS         mandatory
   DESCRIPTION    "A unique EventID that identifies this trap" 
-- REFERENCE      "POWER_UEMemoryDegradPerfEventIndication.EventID"
::= { ibmSystempTrapUEMemoryDegradPerfBindings 2 }

ibmSystempTrapUEMemoryDegradPerfAME OBJECT-TYPE
   SYNTAX         String
   ACCESS         read-only
   STATUS         mandatory
   DESCRIPTION    "A unique string that identifies the monitored device"
-- REFERENCE      "POWER_UEMemoryDegradPerfEventIndication.AlertingManagedElement"
::= { ibmSystempTrapUEMemoryDegradPerfBindings 3 }

ibmSystempTrapUEMemoryDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEMemoryDegradPerfEventIndication.Severity"
::= { ibmSystempTrapUEMemoryDegradPerfBindings 4 }

ibmSystempTrapUEMemoryDegradPerfDescription OBJECT-TYPE
   SYNTAX         SnmpAdminString
   ACCESS         read-only
   STATUS         mandatory
   DESCRIPTION    "The Event text of the trap"
-- REFERENCE      "POWER_UEMemoryDegradPerfEventIndication.Description"
::= { ibmSystempTrapUEMemoryDegradPerfBindings 5 }

ibmSystempTrapUEMemoryDegradPerfTimeStamp OBJECT-TYPE
   SYNTAX         Datetime
   ACCESS         read-only
   STATUS         mandatory
   DESCRIPTION    "The time that the trap occurred"
-- REFERENCE      "POWER_UEMemoryDegradPerfEventIndication.TimeStamp"
::= { ibmSystempTrapUEMemoryDegradPerfBindings 6 }


ibmSystempTrapUEMemoryLossOfRedundancy TRAP-TYPE
   ENTERPRISE     ibmSystemMIB
   VARIABLES    {
      ibmSystempTrapUEMemoryLossOfRedundancyProviderName,
      ibmSystempTrapUEMemoryLossOfRedundancyEventID,
      ibmSystempTrapUEMemoryLossOfRedundancyAME,
      ibmSystempTrapUEMemoryLossOfRedundancySeverity,
      ibmSystempTrapUEMemoryLossOfRedundancyDescription,
      ibmSystempTrapUEMemoryLossOfRedundancyTimeStamp
   }
   DESCRIPTION    "A System p event has occurred"
-- REFERENCE      "POWER_UEMemoryLossOfRedundancyEventIndication"
::= 419

ibmSystempTrapUEMemoryLossOfRedundancyBindings OBJECT IDENTIFIER ::= { ibmSystemTrap 419 }

ibmSystempTrapUEMemoryLossOfRedundancyProviderName OBJECT-TYPE
   SYNTAX         String
   ACCESS         read-only
   STATUS         mandatory
   DESCRIPTION    "The name of the CIM Provider that monitors this device"
-- REFERENCE      "POWER_UEMemoryLossOfRedundancyEventIndication.ProviderName"
::= { ibmSystempTrapUEMemoryLossOfRedundancyBindings 1 }

ibmSystempTrapUEMemoryLossOfRedundancyEventID OBJECT-TYPE
   SYNTAX         String
   ACCESS         read-only
   STATUS         mandatory
   DESCRIPTION    "A unique EventID that identifies this trap" 
-- REFERENCE      "POWER_UEMemoryLossOfRedundancyEventIndication.EventID"
::= { ibmSystempTrapUEMemoryLossOfRedundancyBindings 2 }

ibmSystempTrapUEMemoryLossOfRedundancyAME OBJECT-TYPE
   SYNTAX         String
   ACCESS         read-only
   STATUS         mandatory
   DESCRIPTION    "A unique string that identifies the monitored device"
-- REFERENCE      "POWER_UEMemoryLossOfRedundancyEventIndication.AlertingManagedElement"
::= { ibmSystempTrapUEMemoryLossOfRedundancyBindings 3 }

ibmSystempTrapUEMemoryLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEMemoryLossOfRedundancyEventIndication.Severity"
::= { ibmSystempTrapUEMemoryLossOfRedundancyBindings 4 }

ibmSystempTrapUEMemoryLossOfRedundancyDescription OBJECT-TYPE
   SYNTAX         SnmpAdminString
   ACCESS         read-only
   STATUS         mandatory
   DESCRIPTION    "The Event text of the trap"
-- REFERENCE      "POWER_UEMemoryLossOfRedundancyEventIndication.Description"
::= { ibmSystempTrapUEMemoryLossOfRedundancyBindings 5 }

ibmSystempTrapUEMemoryLossOfRedundancyTimeStamp OBJECT-TYPE
   SYNTAX         Datetime
   ACCESS         read-only
   STATUS         mandatory
   DESCRIPTION    "The time that the trap occurred"
-- REFERENCE      "POWER_UEMemoryLossOfRedundancyEventIndication.TimeStamp"
::= { ibmSystempTrapUEMemoryLossOfRedundancyBindings 6 }


ibmSystempTrapUEMemoryLossOfRedundAndPerf TRAP-TYPE
   ENTERPRISE     ibmSystemMIB
   VARIABLES    {
      ibmSystempTrapUEMemoryLossOfRedundAndPerfProviderName,
      ibmSystempTrapUEMemoryLossOfRedundAndPerfEventID,
      ibmSystempTrapUEMemoryLossOfRedundAndPerfAME,
      ibmSystempTrapUEMemoryLossOfRedundAndPerfSeverity,
      ibmSystempTrapUEMemoryLossOfRedundAndPerfDescription,
      ibmSystempTrapUEMemoryLossOfRedundAndPerfTimeStamp
   }
   DESCRIPTION    "A System p event has occurred"
-- REFERENCE      "POWER_UEMemoryLossOfRedundAndPerfEventIndication"
::= 420

ibmSystempTrapUEMemoryLossOfRedundAndPerfBindings OBJECT IDENTIFIER ::= { ibmSystemTrap 420 }

ibmSystempTrapUEMemoryLossOfRedundAndPerfProviderName OBJECT-TYPE
   SYNTAX         String
   ACCESS         read-only
   STATUS         mandatory
   DESCRIPTION    "The name of the CIM Provider that monitors this device"
-- REFERENCE      "POWER_UEMemoryLossOfRedundAndPerfEventIndication.ProviderName"
::= { ibmSystempTrapUEMemoryLossOfRedundAndPerfBindings 1 }

ibmSystempTrapUEMemoryLossOfRedundAndPerfEventID OBJECT-TYPE
   SYNTAX         String
   ACCESS         read-only
   STATUS         mandatory
   DESCRIPTION    "A unique EventID that identifies this trap" 
-- REFERENCE      "POWER_UEMemoryLossOfRedundAndPerfEventIndication.EventID"
::= { ibmSystempTrapUEMemoryLossOfRedundAndPerfBindings 2 }

ibmSystempTrapUEMemoryLossOfRedundAndPerfAME OBJECT-TYPE
   SYNTAX         String
   ACCESS         read-only
   STATUS         mandatory
   DESCRIPTION    "A unique string that identifies the monitored device"
-- REFERENCE      "POWER_UEMemoryLossOfRedundAndPerfEventIndication.AlertingManagedElement"
::= { ibmSystempTrapUEMemoryLossOfRedundAndPerfBindings 3 }

ibmSystempTrapUEMemoryLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEMemoryLossOfRedundAndPerfEventIndication.Severity"
::= { ibmSystempTrapUEMemoryLossOfRedundAndPerfBindings 4 }

ibmSystempTrapUEMemoryLossOfRedundAndPerfDescription OBJECT-TYPE
   SYNTAX         SnmpAdminString
   ACCESS         read-only
   STATUS         mandatory
   DESCRIPTION    "The Event text of the trap"
-- REFERENCE      "POWER_UEMemoryLossOfRedundAndPerfEventIndication.Description"
::= { ibmSystempTrapUEMemoryLossOfRedundAndPerfBindings 5 }

ibmSystempTrapUEMemoryLossOfRedundAndPerfTimeStamp OBJECT-TYPE
   SYNTAX         Datetime
   ACCESS         read-only
   STATUS         mandatory
   DESCRIPTION    "The time that the trap occurred"
-- REFERENCE      "POWER_UEMemoryLossOfRedundAndPerfEventIndication.TimeStamp"
::= { ibmSystempTrapUEMemoryLossOfRedundAndPerfBindings 6 }


ibmSystempTrapUEMemoryLossOfFunction TRAP-TYPE
   ENTERPRISE     ibmSystemMIB
   VARIABLES    {
      ibmSystempTrapUEMemoryLossOfFunctionProviderName,
      ibmSystempTrapUEMemoryLossOfFunctionEventID,
      ibmSystempTrapUEMemoryLossOfFunctionAME,
      ibmSystempTrapUEMemoryLossOfFunctionSeverity,
      ibmSystempTrapUEMemoryLossOfFunctionDescription,
      ibmSystempTrapUEMemoryLossOfFunctionTimeStamp
   }
   DESCRIPTION    "A System p event has occurred"
-- REFERENCE      "POWER_UEMemoryLossOfFunctionEventIndication"
::= 421

ibmSystempTrapUEMemoryLossOfFunctionBindings OBJECT IDENTIFIER ::= { ibmSystemTrap 421 }

ibmSystempTrapUEMemoryLossOfFunctionProviderName OBJECT-TYPE
   SYNTAX         String
   ACCESS         read-only
   STATUS         mandatory
   DESCRIPTION    "The name of the CIM Provider that monitors this device"
-- REFERENCE      "POWER_UEMemoryLossOfFunctionEventIndication.ProviderName"
::= { ibmSystempTrapUEMemoryLossOfFunctionBindings 1 }

ibmSystempTrapUEMemoryLossOfFunctionEventID OBJECT-TYPE
   SYNTAX         String
   ACCESS         read-only
   STATUS         mandatory
   DESCRIPTION    "A unique EventID that identifies this trap" 
-- REFERENCE      "POWER_UEMemoryLossOfFunctionEventIndication.EventID"
::= { ibmSystempTrapUEMemoryLossOfFunctionBindings 2 }

ibmSystempTrapUEMemoryLossOfFunctionAME OBJECT-TYPE
   SYNTAX         String
   ACCESS         read-only
   STATUS         mandatory
   DESCRIPTION    "A unique string that identifies the monitored device"
-- REFERENCE      "POWER_UEMemoryLossOfFunctionEventIndication.AlertingManagedElement"
::= { ibmSystempTrapUEMemoryLossOfFunctionBindings 3 }

ibmSystempTrapUEMemoryLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEMemoryLossOfFunctionEventIndication.Severity"
::= { ibmSystempTrapUEMemoryLossOfFunctionBindings 4 }

ibmSystempTrapUEMemoryLossOfFunctionDescription OBJECT-TYPE
   SYNTAX         SnmpAdminString
   ACCESS         read-only
   STATUS         mandatory
   DESCRIPTION    "The Event text of the trap"
-- REFERENCE      "POWER_UEMemoryLossOfFunctionEventIndication.Description"
::= { ibmSystempTrapUEMemoryLossOfFunctionBindings 5 }

ibmSystempTrapUEMemoryLossOfFunctionTimeStamp OBJECT-TYPE
   SYNTAX         Datetime
   ACCESS         read-only
   STATUS         mandatory
   DESCRIPTION    "The time that the trap occurred"
-- REFERENCE      "POWER_UEMemoryLossOfFunctionEventIndication.TimeStamp"
::= { ibmSystempTrapUEMemoryLossOfFunctionBindings 6 }


ibmSystempTrapUEMemoryUnrecoverableError TRAP-TYPE
   ENTERPRISE     ibmSystemMIB
   VARIABLES    {
      ibmSystempTrapUEMemoryUnrecoverableErrorProviderName,
      ibmSystempTrapUEMemoryUnrecoverableErrorEventID,
      ibmSystempTrapUEMemoryUnrecoverableErrorAME,
      ibmSystempTrapUEMemoryUnrecoverableErrorSeverity,
      ibmSystempTrapUEMemoryUnrecoverableErrorDescription,
      ibmSystempTrapUEMemoryUnrecoverableErrorTimeStamp
   }
   DESCRIPTION    "A System p event has occurred"
-- REFERENCE      "POWER_UEMemoryUnrecoverableErrorEventIndication"
::= 422

ibmSystempTrapUEMemoryUnrecoverableErrorBindings OBJECT IDENTIFIER ::= { ibmSystemTrap 422 }

ibmSystempTrapUEMemoryUnrecoverableErrorProviderName OBJECT-TYPE
   SYNTAX         String
   ACCESS         read-only
   STATUS         mandatory
   DESCRIPTION    "The name of the CIM Provider that monitors this device"
-- REFERENCE      "POWER_UEMemoryUnrecoverableErrorEventIndication.ProviderName"
::= { ibmSystempTrapUEMemoryUnrecoverableErrorBindings 1 }

ibmSystempTrapUEMemoryUnrecoverableErrorEventID OBJECT-TYPE
   SYNTAX         String
   ACCESS         read-only
   STATUS         mandatory
   DESCRIPTION    "A unique EventID that identifies this trap" 
-- REFERENCE      "POWER_UEMemoryUnrecoverableErrorEventIndication.EventID"
::= { ibmSystempTrapUEMemoryUnrecoverableErrorBindings 2 }

ibmSystempTrapUEMemoryUnrecoverableErrorAME OBJECT-TYPE
   SYNTAX         String
   ACCESS         read-only
   STATUS         mandatory
   DESCRIPTION    "A unique string that identifies the monitored device"
-- REFERENCE      "POWER_UEMemoryUnrecoverableErrorEventIndication.AlertingManagedElement"
::= { ibmSystempTrapUEMemoryUnrecoverableErrorBindings 3 }

ibmSystempTrapUEMemoryUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEMemoryUnrecoverableErrorEventIndication.Severity"
::= { ibmSystempTrapUEMemoryUnrecoverableErrorBindings 4 }

ibmSystempTrapUEMemoryUnrecoverableErrorDescription OBJECT-TYPE
   SYNTAX         SnmpAdminString
   ACCESS         read-only
   STATUS         mandatory
   DESCRIPTION    "The Event text of the trap"
-- REFERENCE      "POWER_UEMemoryUnrecoverableErrorEventIndication.Description"
::= { ibmSystempTrapUEMemoryUnrecoverableErrorBindings 5 }

ibmSystempTrapUEMemoryUnrecoverableErrorTimeStamp OBJECT-TYPE
   SYNTAX         Datetime
   ACCESS         read-only
   STATUS         mandatory
   DESCRIPTION    "The time that the trap occurred"
-- REFERENCE      "POWER_UEMemoryUnrecoverableErrorEventIndication.TimeStamp"
::= { ibmSystempTrapUEMemoryUnrecoverableErrorBindings 6 }


ibmSystempTrapDTIOSubsystemDiagnostics TRAP-TYPE
   ENTERPRISE     ibmSystemMIB
   VARIABLES    {
      ibmSystempTrapDTIOSubsystemDiagnosticsProviderName,
      ibmSystempTrapDTIOSubsystemDiagnosticsEventID,
      ibmSystempTrapDTIOSubsystemDiagnosticsAME,
      ibmSystempTrapDTIOSubsystemDiagnosticsSeverity,
      ibmSystempTrapDTIOSubsystemDiagnosticsDescription,
      ibmSystempTrapDTIOSubsystemDiagnosticsTimeStamp
   }
   DESCRIPTION    "A System p event has occurred"
-- REFERENCE      "POWER_DTIOSubsystemDiagnosticsEventIndication"
::= 423

ibmSystempTrapDTIOSubsystemDiagnosticsBindings OBJECT IDENTIFIER ::= { ibmSystemTrap 423 }

ibmSystempTrapDTIOSubsystemDiagnosticsProviderName OBJECT-TYPE
   SYNTAX         String
   ACCESS         read-only
   STATUS         mandatory
   DESCRIPTION    "The name of the CIM Provider that monitors this device"
-- REFERENCE      "POWER_DTIOSubsystemDiagnosticsEventIndication.ProviderName"
::= { ibmSystempTrapDTIOSubsystemDiagnosticsBindings 1 }

ibmSystempTrapDTIOSubsystemDiagnosticsEventID OBJECT-TYPE
   SYNTAX         String
   ACCESS         read-only
   STATUS         mandatory
   DESCRIPTION    "A unique EventID that identifies this trap" 
-- REFERENCE      "POWER_DTIOSubsystemDiagnosticsEventIndication.EventID"
::= { ibmSystempTrapDTIOSubsystemDiagnosticsBindings 2 }

ibmSystempTrapDTIOSubsystemDiagnosticsAME OBJECT-TYPE
   SYNTAX         String
   ACCESS         read-only
   STATUS         mandatory
   DESCRIPTION    "A unique string that identifies the monitored device"
-- REFERENCE      "POWER_DTIOSubsystemDiagnosticsEventIndication.AlertingManagedElement"
::= { ibmSystempTrapDTIOSubsystemDiagnosticsBindings 3 }

ibmSystempTrapDTIOSubsystemDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTIOSubsystemDiagnosticsEventIndication.Severity"
::= { ibmSystempTrapDTIOSubsystemDiagnosticsBindings 4 }

ibmSystempTrapDTIOSubsystemDiagnosticsDescription OBJECT-TYPE
   SYNTAX         SnmpAdminString
   ACCESS         read-only
   STATUS         mandatory
   DESCRIPTION    "The Event text of the trap"
-- REFERENCE      "POWER_DTIOSubsystemDiagnosticsEventIndication.Description"
::= { ibmSystempTrapDTIOSubsystemDiagnosticsBindings 5 }

ibmSystempTrapDTIOSubsystemDiagnosticsTimeStamp OBJECT-TYPE
   SYNTAX         Datetime
   ACCESS         read-only
   STATUS         mandatory
   DESCRIPTION    "The time that the trap occurred"
-- REFERENCE      "POWER_DTIOSubsystemDiagnosticsEventIndication.TimeStamp"
::= { ibmSystempTrapDTIOSubsystemDiagnosticsBindings 6 }


ibmSystempTrapPFIOSubsystemDegradPerf TRAP-TYPE
   ENTERPRISE     ibmSystemMIB
   VARIABLES    {
      ibmSystempTrapPFIOSubsystemDegradPerfProviderName,
      ibmSystempTrapPFIOSubsystemDegradPerfEventID,
      ibmSystempTrapPFIOSubsystemDegradPerfAME,
      ibmSystempTrapPFIOSubsystemDegradPerfSeverity,
      ibmSystempTrapPFIOSubsystemDegradPerfDescription,
      ibmSystempTrapPFIOSubsystemDegradPerfTimeStamp
   }
   DESCRIPTION    "A System p event has occurred"
-- REFERENCE      "POWER_PFIOSubsystemDegradPerfEventIndication"
::= 424

ibmSystempTrapPFIOSubsystemDegradPerfBindings OBJECT IDENTIFIER ::= { ibmSystemTrap 424 }

ibmSystempTrapPFIOSubsystemDegradPerfProviderName OBJECT-TYPE
   SYNTAX         String
   ACCESS         read-only
   STATUS         mandatory
   DESCRIPTION    "The name of the CIM Provider that monitors this device"
-- REFERENCE      "POWER_PFIOSubsystemDegradPerfEventIndication.ProviderName"
::= { ibmSystempTrapPFIOSubsystemDegradPerfBindings 1 }

ibmSystempTrapPFIOSubsystemDegradPerfEventID OBJECT-TYPE
   SYNTAX         String
   ACCESS         read-only
   STATUS         mandatory
   DESCRIPTION    "A unique EventID that identifies this trap" 
-- REFERENCE      "POWER_PFIOSubsystemDegradPerfEventIndication.EventID"
::= { ibmSystempTrapPFIOSubsystemDegradPerfBindings 2 }

ibmSystempTrapPFIOSubsystemDegradPerfAME OBJECT-TYPE
   SYNTAX         String
   ACCESS         read-only
   STATUS         mandatory
   DESCRIPTION    "A unique string that identifies the monitored device"
-- REFERENCE      "POWER_PFIOSubsystemDegradPerfEventIndication.AlertingManagedElement"
::= { ibmSystempTrapPFIOSubsystemDegradPerfBindings 3 }

ibmSystempTrapPFIOSubsystemDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOSubsystemDegradPerfEventIndication.Severity"
::= { ibmSystempTrapPFIOSubsystemDegradPerfBindings 4 }

ibmSystempTrapPFIOSubsystemDegradPerfDescription OBJECT-TYPE
   SYNTAX         SnmpAdminString
   ACCESS         read-only
   STATUS         mandatory
   DESCRIPTION    "The Event text of the trap"
-- REFERENCE      "POWER_PFIOSubsystemDegradPerfEventIndication.Description"
::= { ibmSystempTrapPFIOSubsystemDegradPerfBindings 5 }

ibmSystempTrapPFIOSubsystemDegradPerfTimeStamp OBJECT-TYPE
   SYNTAX         Datetime
   ACCESS         read-only
   STATUS         mandatory
   DESCRIPTION    "The time that the trap occurred"
-- REFERENCE      "POWER_PFIOSubsystemDegradPerfEventIndication.TimeStamp"
::= { ibmSystempTrapPFIOSubsystemDegradPerfBindings 6 }


ibmSystempTrapPFIOSubsystemCorrectAftIPL TRAP-TYPE
   ENTERPRISE     ibmSystemMIB
   VARIABLES    {
      ibmSystempTrapPFIOSubsystemCorrectAftIPLProviderName,
      ibmSystempTrapPFIOSubsystemCorrectAftIPLEventID,
      ibmSystempTrapPFIOSubsystemCorrectAftIPLAME,
      ibmSystempTrapPFIOSubsystemCorrectAftIPLSeverity,
      ibmSystempTrapPFIOSubsystemCorrectAftIPLDescription,
      ibmSystempTrapPFIOSubsystemCorrectAftIPLTimeStamp
   }
   DESCRIPTION    "A System p event has occurred"
-- REFERENCE      "POWER_PFIOSubsystemCorrectAftIPLEventIndication"
::= 425

ibmSystempTrapPFIOSubsystemCorrectAftIPLBindings OBJECT IDENTIFIER ::= { ibmSystemTrap 425 }

ibmSystempTrapPFIOSubsystemCorrectAftIPLProviderName OBJECT-TYPE
   SYNTAX         String
   ACCESS         read-only
   STATUS         mandatory
   DESCRIPTION    "The name of the CIM Provider that monitors this device"
-- REFERENCE      "POWER_PFIOSubsystemCorrectAftIPLEventIndication.ProviderName"
::= { ibmSystempTrapPFIOSubsystemCorrectAftIPLBindings 1 }

ibmSystempTrapPFIOSubsystemCorrectAftIPLEventID OBJECT-TYPE
   SYNTAX         String
   ACCESS         read-only
   STATUS         mandatory
   DESCRIPTION    "A unique EventID that identifies this trap" 
-- REFERENCE      "POWER_PFIOSubsystemCorrectAftIPLEventIndication.EventID"
::= { ibmSystempTrapPFIOSubsystemCorrectAftIPLBindings 2 }

ibmSystempTrapPFIOSubsystemCorrectAftIPLAME OBJECT-TYPE
   SYNTAX         String
   ACCESS         read-only
   STATUS         mandatory
   DESCRIPTION    "A unique string that identifies the monitored device"
-- REFERENCE      "POWER_PFIOSubsystemCorrectAftIPLEventIndication.AlertingManagedElement"
::= { ibmSystempTrapPFIOSubsystemCorrectAftIPLBindings 3 }

ibmSystempTrapPFIOSubsystemCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOSubsystemCorrectAftIPLEventIndication.Severity"
::= { ibmSystempTrapPFIOSubsystemCorrectAftIPLBindings 4 }

ibmSystempTrapPFIOSubsystemCorrectAftIPLDescription OBJECT-TYPE
   SYNTAX         SnmpAdminString
   ACCESS         read-only
   STATUS         mandatory
   DESCRIPTION    "The Event text of the trap"
-- REFERENCE      "POWER_PFIOSubsystemCorrectAftIPLEventIndication.Description"
::= { ibmSystempTrapPFIOSubsystemCorrectAftIPLBindings 5 }

ibmSystempTrapPFIOSubsystemCorrectAftIPLTimeStamp OBJECT-TYPE
   SYNTAX         Datetime
   ACCESS         read-only
   STATUS         mandatory
   DESCRIPTION    "The time that the trap occurred"
-- REFERENCE      "POWER_PFIOSubsystemCorrectAftIPLEventIndication.TimeStamp"
::= { ibmSystempTrapPFIOSubsystemCorrectAftIPLBindings 6 }


ibmSystempTrapPFIOSubsystemCorrectAftIPLPerf TRAP-TYPE
   ENTERPRISE     ibmSystemMIB
   VARIABLES    {
      ibmSystempTrapPFIOSubsystemCorrectAftIPLPerfProviderName,
      ibmSystempTrapPFIOSubsystemCorrectAftIPLPerfEventID,
      ibmSystempTrapPFIOSubsystemCorrectAftIPLPerfAME,
      ibmSystempTrapPFIOSubsystemCorrectAftIPLPerfSeverity,
      ibmSystempTrapPFIOSubsystemCorrectAftIPLPerfDescription,
      ibmSystempTrapPFIOSubsystemCorrectAftIPLPerfTimeStamp
   }
   DESCRIPTION    "A System p event has occurred"
-- REFERENCE      "POWER_PFIOSubsystemCorrectAftIPLPerfEventIndication"
::= 426

ibmSystempTrapPFIOSubsystemCorrectAftIPLPerfBindings OBJECT IDENTIFIER ::= { ibmSystemTrap 426 }

ibmSystempTrapPFIOSubsystemCorrectAftIPLPerfProviderName OBJECT-TYPE
   SYNTAX         String
   ACCESS         read-only
   STATUS         mandatory
   DESCRIPTION    "The name of the CIM Provider that monitors this device"
-- REFERENCE      "POWER_PFIOSubsystemCorrectAftIPLPerfEventIndication.ProviderName"
::= { ibmSystempTrapPFIOSubsystemCorrectAftIPLPerfBindings 1 }

ibmSystempTrapPFIOSubsystemCorrectAftIPLPerfEventID OBJECT-TYPE
   SYNTAX         String
   ACCESS         read-only
   STATUS         mandatory
   DESCRIPTION    "A unique EventID that identifies this trap" 
-- REFERENCE      "POWER_PFIOSubsystemCorrectAftIPLPerfEventIndication.EventID"
::= { ibmSystempTrapPFIOSubsystemCorrectAftIPLPerfBindings 2 }

ibmSystempTrapPFIOSubsystemCorrectAftIPLPerfAME OBJECT-TYPE
   SYNTAX         String
   ACCESS         read-only
   STATUS         mandatory
   DESCRIPTION    "A unique string that identifies the monitored device"
-- REFERENCE      "POWER_PFIOSubsystemCorrectAftIPLPerfEventIndication.AlertingManagedElement"
::= { ibmSystempTrapPFIOSubsystemCorrectAftIPLPerfBindings 3 }

ibmSystempTrapPFIOSubsystemCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOSubsystemCorrectAftIPLPerfEventIndication.Severity"
::= { ibmSystempTrapPFIOSubsystemCorrectAftIPLPerfBindings 4 }

ibmSystempTrapPFIOSubsystemCorrectAftIPLPerfDescription OBJECT-TYPE
   SYNTAX         SnmpAdminString
   ACCESS         read-only
   STATUS         mandatory
   DESCRIPTION    "The Event text of the trap"
-- REFERENCE      "POWER_PFIOSubsystemCorrectAftIPLPerfEventIndication.Description"
::= { ibmSystempTrapPFIOSubsystemCorrectAftIPLPerfBindings 5 }

ibmSystempTrapPFIOSubsystemCorrectAftIPLPerfTimeStamp OBJECT-TYPE
   SYNTAX         Datetime
   ACCESS         read-only
   STATUS         mandatory
   DESCRIPTION    "The time that the trap occurred"
-- REFERENCE      "POWER_PFIOSubsystemCorrectAftIPLPerfEventIndication.TimeStamp"
::= { ibmSystempTrapPFIOSubsystemCorrectAftIPLPerfBindings 6 }


ibmSystempTrapPFIOSubsystemLossOfRedundancy TRAP-TYPE
   ENTERPRISE     ibmSystemMIB
   VARIABLES    {
      ibmSystempTrapPFIOSubsystemLossOfRedundancyProviderName,
      ibmSystempTrapPFIOSubsystemLossOfRedundancyEventID,
      ibmSystempTrapPFIOSubsystemLossOfRedundancyAME,
      ibmSystempTrapPFIOSubsystemLossOfRedundancySeverity,
      ibmSystempTrapPFIOSubsystemLossOfRedundancyDescription,
      ibmSystempTrapPFIOSubsystemLossOfRedundancyTimeStamp
   }
   DESCRIPTION    "A System p event has occurred"
-- REFERENCE      "POWER_PFIOSubsystemLossOfRedundancyEventIndication"
::= 427

ibmSystempTrapPFIOSubsystemLossOfRedundancyBindings OBJECT IDENTIFIER ::= { ibmSystemTrap 427 }

ibmSystempTrapPFIOSubsystemLossOfRedundancyProviderName OBJECT-TYPE
   SYNTAX         String
   ACCESS         read-only
   STATUS         mandatory
   DESCRIPTION    "The name of the CIM Provider that monitors this device"
-- REFERENCE      "POWER_PFIOSubsystemLossOfRedundancyEventIndication.ProviderName"
::= { ibmSystempTrapPFIOSubsystemLossOfRedundancyBindings 1 }

ibmSystempTrapPFIOSubsystemLossOfRedundancyEventID OBJECT-TYPE
   SYNTAX         String
   ACCESS         read-only
   STATUS         mandatory
   DESCRIPTION    "A unique EventID that identifies this trap" 
-- REFERENCE      "POWER_PFIOSubsystemLossOfRedundancyEventIndication.EventID"
::= { ibmSystempTrapPFIOSubsystemLossOfRedundancyBindings 2 }

ibmSystempTrapPFIOSubsystemLossOfRedundancyAME OBJECT-TYPE
   SYNTAX         String
   ACCESS         read-only
   STATUS         mandatory
   DESCRIPTION    "A unique string that identifies the monitored device"
-- REFERENCE      "POWER_PFIOSubsystemLossOfRedundancyEventIndication.AlertingManagedElement"
::= { ibmSystempTrapPFIOSubsystemLossOfRedundancyBindings 3 }

ibmSystempTrapPFIOSubsystemLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOSubsystemLossOfRedundancyEventIndication.Severity"
::= { ibmSystempTrapPFIOSubsystemLossOfRedundancyBindings 4 }

ibmSystempTrapPFIOSubsystemLossOfRedundancyDescription OBJECT-TYPE
   SYNTAX         SnmpAdminString
   ACCESS         read-only
   STATUS         mandatory
   DESCRIPTION    "The Event text of the trap"
-- REFERENCE      "POWER_PFIOSubsystemLossOfRedundancyEventIndication.Description"
::= { ibmSystempTrapPFIOSubsystemLossOfRedundancyBindings 5 }

ibmSystempTrapPFIOSubsystemLossOfRedundancyTimeStamp OBJECT-TYPE
   SYNTAX         Datetime
   ACCESS         read-only
   STATUS         mandatory
   DESCRIPTION    "The time that the trap occurred"
-- REFERENCE      "POWER_PFIOSubsystemLossOfRedundancyEventIndication.TimeStamp"
::= { ibmSystempTrapPFIOSubsystemLossOfRedundancyBindings 6 }


ibmSystempTrapPFIOSubsystemPredictiveError TRAP-TYPE
   ENTERPRISE     ibmSystemMIB
   VARIABLES    {
      ibmSystempTrapPFIOSubsystemPredictiveErrorProviderName,
      ibmSystempTrapPFIOSubsystemPredictiveErrorEventID,
      ibmSystempTrapPFIOSubsystemPredictiveErrorAME,
      ibmSystempTrapPFIOSubsystemPredictiveErrorSeverity,
      ibmSystempTrapPFIOSubsystemPredictiveErrorDescription,
      ibmSystempTrapPFIOSubsystemPredictiveErrorTimeStamp
   }
   DESCRIPTION    "A System p event has occurred"
-- REFERENCE      "POWER_PFIOSubsystemPredictiveErrorEventIndication"
::= 428

ibmSystempTrapPFIOSubsystemPredictiveErrorBindings OBJECT IDENTIFIER ::= { ibmSystemTrap 428 }

ibmSystempTrapPFIOSubsystemPredictiveErrorProviderName OBJECT-TYPE
   SYNTAX         String
   ACCESS         read-only
   STATUS         mandatory
   DESCRIPTION    "The name of the CIM Provider that monitors this device"
-- REFERENCE      "POWER_PFIOSubsystemPredictiveErrorEventIndication.ProviderName"
::= { ibmSystempTrapPFIOSubsystemPredictiveErrorBindings 1 }

ibmSystempTrapPFIOSubsystemPredictiveErrorEventID OBJECT-TYPE
   SYNTAX         String
   ACCESS         read-only
   STATUS         mandatory
   DESCRIPTION    "A unique EventID that identifies this trap" 
-- REFERENCE      "POWER_PFIOSubsystemPredictiveErrorEventIndication.EventID"
::= { ibmSystempTrapPFIOSubsystemPredictiveErrorBindings 2 }

ibmSystempTrapPFIOSubsystemPredictiveErrorAME OBJECT-TYPE
   SYNTAX         String
   ACCESS         read-only
   STATUS         mandatory
   DESCRIPTION    "A unique string that identifies the monitored device"
-- REFERENCE      "POWER_PFIOSubsystemPredictiveErrorEventIndication.AlertingManagedElement"
::= { ibmSystempTrapPFIOSubsystemPredictiveErrorBindings 3 }

ibmSystempTrapPFIOSubsystemPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOSubsystemPredictiveErrorEventIndication.Severity"
::= { ibmSystempTrapPFIOSubsystemPredictiveErrorBindings 4 }

ibmSystempTrapPFIOSubsystemPredictiveErrorDescription OBJECT-TYPE
   SYNTAX         SnmpAdminString
   ACCESS         read-only
   STATUS         mandatory
   DESCRIPTION    "The Event text of the trap"
-- REFERENCE      "POWER_PFIOSubsystemPredictiveErrorEventIndication.Description"
::= { ibmSystempTrapPFIOSubsystemPredictiveErrorBindings 5 }

ibmSystempTrapPFIOSubsystemPredictiveErrorTimeStamp OBJECT-TYPE
   SYNTAX         Datetime
   ACCESS         read-only
   STATUS         mandatory
   DESCRIPTION    "The time that the trap occurred"
-- REFERENCE      "POWER_PFIOSubsystemPredictiveErrorEventIndication.TimeStamp"
::= { ibmSystempTrapPFIOSubsystemPredictiveErrorBindings 6 }


ibmSystempTrapUEIOSubsystemDegradPerf TRAP-TYPE
   ENTERPRISE     ibmSystemMIB
   VARIABLES    {
      ibmSystempTrapUEIOSubsystemDegradPerfProviderName,
      ibmSystempTrapUEIOSubsystemDegradPerfEventID,
      ibmSystempTrapUEIOSubsystemDegradPerfAME,
      ibmSystempTrapUEIOSubsystemDegradPerfSeverity,
      ibmSystempTrapUEIOSubsystemDegradPerfDescription,
      ibmSystempTrapUEIOSubsystemDegradPerfTimeStamp
   }
   DESCRIPTION    "A System p event has occurred"
-- REFERENCE      "POWER_UEIOSubsystemDegradPerfEventIndication"
::= 429

ibmSystempTrapUEIOSubsystemDegradPerfBindings OBJECT IDENTIFIER ::= { ibmSystemTrap 429 }

ibmSystempTrapUEIOSubsystemDegradPerfProviderName OBJECT-TYPE
   SYNTAX         String
   ACCESS         read-only
   STATUS         mandatory
   DESCRIPTION    "The name of the CIM Provider that monitors this device"
-- REFERENCE      "POWER_UEIOSubsystemDegradPerfEventIndication.ProviderName"
::= { ibmSystempTrapUEIOSubsystemDegradPerfBindings 1 }

ibmSystempTrapUEIOSubsystemDegradPerfEventID OBJECT-TYPE
   SYNTAX         String
   ACCESS         read-only
   STATUS         mandatory
   DESCRIPTION    "A unique EventID that identifies this trap" 
-- REFERENCE      "POWER_UEIOSubsystemDegradPerfEventIndication.EventID"
::= { ibmSystempTrapUEIOSubsystemDegradPerfBindings 2 }

ibmSystempTrapUEIOSubsystemDegradPerfAME OBJECT-TYPE
   SYNTAX         String
   ACCESS         read-only
   STATUS         mandatory
   DESCRIPTION    "A unique string that identifies the monitored device"
-- REFERENCE      "POWER_UEIOSubsystemDegradPerfEventIndication.AlertingManagedElement"
::= { ibmSystempTrapUEIOSubsystemDegradPerfBindings 3 }

ibmSystempTrapUEIOSubsystemDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOSubsystemDegradPerfEventIndication.Severity"
::= { ibmSystempTrapUEIOSubsystemDegradPerfBindings 4 }

ibmSystempTrapUEIOSubsystemDegradPerfDescription OBJECT-TYPE
   SYNTAX         SnmpAdminString
   ACCESS         read-only
   STATUS         mandatory
   DESCRIPTION    "The Event text of the trap"
-- REFERENCE      "POWER_UEIOSubsystemDegradPerfEventIndication.Description"
::= { ibmSystempTrapUEIOSubsystemDegradPerfBindings 5 }

ibmSystempTrapUEIOSubsystemDegradPerfTimeStamp OBJECT-TYPE
   SYNTAX         Datetime
   ACCESS         read-only
   STATUS         mandatory
   DESCRIPTION    "The time that the trap occurred"
-- REFERENCE      "POWER_UEIOSubsystemDegradPerfEventIndication.TimeStamp"
::= { ibmSystempTrapUEIOSubsystemDegradPerfBindings 6 }


ibmSystempTrapUEIOSubsystemLossOfRedundancy TRAP-TYPE
   ENTERPRISE     ibmSystemMIB
   VARIABLES    {
      ibmSystempTrapUEIOSubsystemLossOfRedundancyProviderName,
      ibmSystempTrapUEIOSubsystemLossOfRedundancyEventID,
      ibmSystempTrapUEIOSubsystemLossOfRedundancyAME,
      ibmSystempTrapUEIOSubsystemLossOfRedundancySeverity,
      ibmSystempTrapUEIOSubsystemLossOfRedundancyDescription,
      ibmSystempTrapUEIOSubsystemLossOfRedundancyTimeStamp
   }
   DESCRIPTION    "A System p event has occurred"
-- REFERENCE      "POWER_UEIOSubsystemLossOfRedundancyEventIndication"
::= 430

ibmSystempTrapUEIOSubsystemLossOfRedundancyBindings OBJECT IDENTIFIER ::= { ibmSystemTrap 430 }

ibmSystempTrapUEIOSubsystemLossOfRedundancyProviderName OBJECT-TYPE
   SYNTAX         String
   ACCESS         read-only
   STATUS         mandatory
   DESCRIPTION    "The name of the CIM Provider that monitors this device"
-- REFERENCE      "POWER_UEIOSubsystemLossOfRedundancyEventIndication.ProviderName"
::= { ibmSystempTrapUEIOSubsystemLossOfRedundancyBindings 1 }

ibmSystempTrapUEIOSubsystemLossOfRedundancyEventID OBJECT-TYPE
   SYNTAX         String
   ACCESS         read-only
   STATUS         mandatory
   DESCRIPTION    "A unique EventID that identifies this trap" 
-- REFERENCE      "POWER_UEIOSubsystemLossOfRedundancyEventIndication.EventID"
::= { ibmSystempTrapUEIOSubsystemLossOfRedundancyBindings 2 }

ibmSystempTrapUEIOSubsystemLossOfRedundancyAME OBJECT-TYPE
   SYNTAX         String
   ACCESS         read-only
   STATUS         mandatory
   DESCRIPTION    "A unique string that identifies the monitored device"
-- REFERENCE      "POWER_UEIOSubsystemLossOfRedundancyEventIndication.AlertingManagedElement"
::= { ibmSystempTrapUEIOSubsystemLossOfRedundancyBindings 3 }

ibmSystempTrapUEIOSubsystemLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOSubsystemLossOfRedundancyEventIndication.Severity"
::= { ibmSystempTrapUEIOSubsystemLossOfRedundancyBindings 4 }

ibmSystempTrapUEIOSubsystemLossOfRedundancyDescription OBJECT-TYPE
   SYNTAX         SnmpAdminString
   ACCESS         read-only
   STATUS         mandatory
   DESCRIPTION    "The Event text of the trap"
-- REFERENCE      "POWER_UEIOSubsystemLossOfRedundancyEventIndication.Description"
::= { ibmSystempTrapUEIOSubsystemLossOfRedundancyBindings 5 }

ibmSystempTrapUEIOSubsystemLossOfRedundancyTimeStamp OBJECT-TYPE
   SYNTAX         Datetime
   ACCESS         read-only
   STATUS         mandatory
   DESCRIPTION    "The time that the trap occurred"
-- REFERENCE      "POWER_UEIOSubsystemLossOfRedundancyEventIndication.TimeStamp"
::= { ibmSystempTrapUEIOSubsystemLossOfRedundancyBindings 6 }


ibmSystempTrapUEIOSubsystemLossOfRedundAndPerf TRAP-TYPE
   ENTERPRISE     ibmSystemMIB
   VARIABLES    {
      ibmSystempTrapUEIOSubsystemLossOfRedundAndPerfProviderName,
      ibmSystempTrapUEIOSubsystemLossOfRedundAndPerfEventID,
      ibmSystempTrapUEIOSubsystemLossOfRedundAndPerfAME,
      ibmSystempTrapUEIOSubsystemLossOfRedundAndPerfSeverity,
      ibmSystempTrapUEIOSubsystemLossOfRedundAndPerfDescription,
      ibmSystempTrapUEIOSubsystemLossOfRedundAndPerfTimeStamp
   }
   DESCRIPTION    "A System p event has occurred"
-- REFERENCE      "POWER_UEIOSubsystemLossOfRedundAndPerfEventIndication"
::= 431

ibmSystempTrapUEIOSubsystemLossOfRedundAndPerfBindings OBJECT IDENTIFIER ::= { ibmSystemTrap 431 }

ibmSystempTrapUEIOSubsystemLossOfRedundAndPerfProviderName OBJECT-TYPE
   SYNTAX         String
   ACCESS         read-only
   STATUS         mandatory
   DESCRIPTION    "The name of the CIM Provider that monitors this device"
-- REFERENCE      "POWER_UEIOSubsystemLossOfRedundAndPerfEventIndication.ProviderName"
::= { ibmSystempTrapUEIOSubsystemLossOfRedundAndPerfBindings 1 }

ibmSystempTrapUEIOSubsystemLossOfRedundAndPerfEventID OBJECT-TYPE
   SYNTAX         String
   ACCESS         read-only
   STATUS         mandatory
   DESCRIPTION    "A unique EventID that identifies this trap" 
-- REFERENCE      "POWER_UEIOSubsystemLossOfRedundAndPerfEventIndication.EventID"
::= { ibmSystempTrapUEIOSubsystemLossOfRedundAndPerfBindings 2 }

ibmSystempTrapUEIOSubsystemLossOfRedundAndPerfAME OBJECT-TYPE
   SYNTAX         String
   ACCESS         read-only
   STATUS         mandatory
   DESCRIPTION    "A unique string that identifies the monitored device"
-- REFERENCE      "POWER_UEIOSubsystemLossOfRedundAndPerfEventIndication.AlertingManagedElement"
::= { ibmSystempTrapUEIOSubsystemLossOfRedundAndPerfBindings 3 }

ibmSystempTrapUEIOSubsystemLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOSubsystemLossOfRedundAndPerfEventIndication.Severity"
::= { ibmSystempTrapUEIOSubsystemLossOfRedundAndPerfBindings 4 }

ibmSystempTrapUEIOSubsystemLossOfRedundAndPerfDescription OBJECT-TYPE
   SYNTAX         SnmpAdminString
   ACCESS         read-only
   STATUS         mandatory
   DESCRIPTION    "The Event text of the trap"
-- REFERENCE      "POWER_UEIOSubsystemLossOfRedundAndPerfEventIndication.Description"
::= { ibmSystempTrapUEIOSubsystemLossOfRedundAndPerfBindings 5 }

ibmSystempTrapUEIOSubsystemLossOfRedundAndPerfTimeStamp OBJECT-TYPE
   SYNTAX         Datetime
   ACCESS         read-only
   STATUS         mandatory
   DESCRIPTION    "The time that the trap occurred"
-- REFERENCE      "POWER_UEIOSubsystemLossOfRedundAndPerfEventIndication.TimeStamp"
::= { ibmSystempTrapUEIOSubsystemLossOfRedundAndPerfBindings 6 }


ibmSystempTrapUEIOSubsystemLossOfFunction TRAP-TYPE
   ENTERPRISE     ibmSystemMIB
   VARIABLES    {
      ibmSystempTrapUEIOSubsystemLossOfFunctionProviderName,
      ibmSystempTrapUEIOSubsystemLossOfFunctionEventID,
      ibmSystempTrapUEIOSubsystemLossOfFunctionAME,
      ibmSystempTrapUEIOSubsystemLossOfFunctionSeverity,
      ibmSystempTrapUEIOSubsystemLossOfFunctionDescription,
      ibmSystempTrapUEIOSubsystemLossOfFunctionTimeStamp
   }
   DESCRIPTION    "A System p event has occurred"
-- REFERENCE      "POWER_UEIOSubsystemLossOfFunctionEventIndication"
::= 432

ibmSystempTrapUEIOSubsystemLossOfFunctionBindings OBJECT IDENTIFIER ::= { ibmSystemTrap 432 }

ibmSystempTrapUEIOSubsystemLossOfFunctionProviderName OBJECT-TYPE
   SYNTAX         String
   ACCESS         read-only
   STATUS         mandatory
   DESCRIPTION    "The name of the CIM Provider that monitors this device"
-- REFERENCE      "POWER_UEIOSubsystemLossOfFunctionEventIndication.ProviderName"
::= { ibmSystempTrapUEIOSubsystemLossOfFunctionBindings 1 }

ibmSystempTrapUEIOSubsystemLossOfFunctionEventID OBJECT-TYPE
   SYNTAX         String
   ACCESS         read-only
   STATUS         mandatory
   DESCRIPTION    "A unique EventID that identifies this trap" 
-- REFERENCE      "POWER_UEIOSubsystemLossOfFunctionEventIndication.EventID"
::= { ibmSystempTrapUEIOSubsystemLossOfFunctionBindings 2 }

ibmSystempTrapUEIOSubsystemLossOfFunctionAME OBJECT-TYPE
   SYNTAX         String
   ACCESS         read-only
   STATUS         mandatory
   DESCRIPTION    "A unique string that identifies the monitored device"
-- REFERENCE      "POWER_UEIOSubsystemLossOfFunctionEventIndication.AlertingManagedElement"
::= { ibmSystempTrapUEIOSubsystemLossOfFunctionBindings 3 }

ibmSystempTrapUEIOSubsystemLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOSubsystemLossOfFunctionEventIndication.Severity"
::= { ibmSystempTrapUEIOSubsystemLossOfFunctionBindings 4 }

ibmSystempTrapUEIOSubsystemLossOfFunctionDescription OBJECT-TYPE
   SYNTAX         SnmpAdminString
   ACCESS         read-only
   STATUS         mandatory
   DESCRIPTION    "The Event text of the trap"
-- REFERENCE      "POWER_UEIOSubsystemLossOfFunctionEventIndication.Description"
::= { ibmSystempTrapUEIOSubsystemLossOfFunctionBindings 5 }

ibmSystempTrapUEIOSubsystemLossOfFunctionTimeStamp OBJECT-TYPE
   SYNTAX         Datetime
   ACCESS         read-only
   STATUS         mandatory
   DESCRIPTION    "The time that the trap occurred"
-- REFERENCE      "POWER_UEIOSubsystemLossOfFunctionEventIndication.TimeStamp"
::= { ibmSystempTrapUEIOSubsystemLossOfFunctionBindings 6 }


ibmSystempTrapUEIOSubsystemUnrecoverableError TRAP-TYPE
   ENTERPRISE     ibmSystemMIB
   VARIABLES    {
      ibmSystempTrapUEIOSubsystemUnrecoverableErrorProviderName,
      ibmSystempTrapUEIOSubsystemUnrecoverableErrorEventID,
      ibmSystempTrapUEIOSubsystemUnrecoverableErrorAME,
      ibmSystempTrapUEIOSubsystemUnrecoverableErrorSeverity,
      ibmSystempTrapUEIOSubsystemUnrecoverableErrorDescription,
      ibmSystempTrapUEIOSubsystemUnrecoverableErrorTimeStamp
   }
   DESCRIPTION    "A System p event has occurred"
-- REFERENCE      "POWER_UEIOSubsystemUnrecoverableErrorEventIndication"
::= 433

ibmSystempTrapUEIOSubsystemUnrecoverableErrorBindings OBJECT IDENTIFIER ::= { ibmSystemTrap 433 }

ibmSystempTrapUEIOSubsystemUnrecoverableErrorProviderName OBJECT-TYPE
   SYNTAX         String
   ACCESS         read-only
   STATUS         mandatory
   DESCRIPTION    "The name of the CIM Provider that monitors this device"
-- REFERENCE      "POWER_UEIOSubsystemUnrecoverableErrorEventIndication.ProviderName"
::= { ibmSystempTrapUEIOSubsystemUnrecoverableErrorBindings 1 }

ibmSystempTrapUEIOSubsystemUnrecoverableErrorEventID OBJECT-TYPE
   SYNTAX         String
   ACCESS         read-only
   STATUS         mandatory
   DESCRIPTION    "A unique EventID that identifies this trap" 
-- REFERENCE      "POWER_UEIOSubsystemUnrecoverableErrorEventIndication.EventID"
::= { ibmSystempTrapUEIOSubsystemUnrecoverableErrorBindings 2 }

ibmSystempTrapUEIOSubsystemUnrecoverableErrorAME OBJECT-TYPE
   SYNTAX         String
   ACCESS         read-only
   STATUS         mandatory
   DESCRIPTION    "A unique string that identifies the monitored device"
-- REFERENCE      "POWER_UEIOSubsystemUnrecoverableErrorEventIndication.AlertingManagedElement"
::= { ibmSystempTrapUEIOSubsystemUnrecoverableErrorBindings 3 }

ibmSystempTrapUEIOSubsystemUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOSubsystemUnrecoverableErrorEventIndication.Severity"
::= { ibmSystempTrapUEIOSubsystemUnrecoverableErrorBindings 4 }

ibmSystempTrapUEIOSubsystemUnrecoverableErrorDescription OBJECT-TYPE
   SYNTAX         SnmpAdminString
   ACCESS         read-only
   STATUS         mandatory
   DESCRIPTION    "The Event text of the trap"
-- REFERENCE      "POWER_UEIOSubsystemUnrecoverableErrorEventIndication.Description"
::= { ibmSystempTrapUEIOSubsystemUnrecoverableErrorBindings 5 }

ibmSystempTrapUEIOSubsystemUnrecoverableErrorTimeStamp OBJECT-TYPE
   SYNTAX         Datetime
   ACCESS         read-only
   STATUS         mandatory
   DESCRIPTION    "The time that the trap occurred"
-- REFERENCE      "POWER_UEIOSubsystemUnrecoverableErrorEventIndication.TimeStamp"
::= { ibmSystempTrapUEIOSubsystemUnrecoverableErrorBindings 6 }


ibmSystempTrapDTIOAdapterDiagnostics TRAP-TYPE
   ENTERPRISE     ibmSystemMIB
   VARIABLES    {
      ibmSystempTrapDTIOAdapterDiagnosticsProviderName,
      ibmSystempTrapDTIOAdapterDiagnosticsEventID,
      ibmSystempTrapDTIOAdapterDiagnosticsAME,
      ibmSystempTrapDTIOAdapterDiagnosticsSeverity,
      ibmSystempTrapDTIOAdapterDiagnosticsDescription,
      ibmSystempTrapDTIOAdapterDiagnosticsTimeStamp
   }
   DESCRIPTION    "A System p event has occurred"
-- REFERENCE      "POWER_DTIOAdapterDiagnosticsEventIndication"
::= 434

ibmSystempTrapDTIOAdapterDiagnosticsBindings OBJECT IDENTIFIER ::= { ibmSystemTrap 434 }

ibmSystempTrapDTIOAdapterDiagnosticsProviderName OBJECT-TYPE
   SYNTAX         String
   ACCESS         read-only
   STATUS         mandatory
   DESCRIPTION    "The name of the CIM Provider that monitors this device"
-- REFERENCE      "POWER_DTIOAdapterDiagnosticsEventIndication.ProviderName"
::= { ibmSystempTrapDTIOAdapterDiagnosticsBindings 1 }

ibmSystempTrapDTIOAdapterDiagnosticsEventID OBJECT-TYPE
   SYNTAX         String
   ACCESS         read-only
   STATUS         mandatory
   DESCRIPTION    "A unique EventID that identifies this trap" 
-- REFERENCE      "POWER_DTIOAdapterDiagnosticsEventIndication.EventID"
::= { ibmSystempTrapDTIOAdapterDiagnosticsBindings 2 }

ibmSystempTrapDTIOAdapterDiagnosticsAME OBJECT-TYPE
   SYNTAX         String
   ACCESS         read-only
   STATUS         mandatory
   DESCRIPTION    "A unique string that identifies the monitored device"
-- REFERENCE      "POWER_DTIOAdapterDiagnosticsEventIndication.AlertingManagedElement"
::= { ibmSystempTrapDTIOAdapterDiagnosticsBindings 3 }

ibmSystempTrapDTIOAdapterDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTIOAdapterDiagnosticsEventIndication.Severity"
::= { ibmSystempTrapDTIOAdapterDiagnosticsBindings 4 }

ibmSystempTrapDTIOAdapterDiagnosticsDescription OBJECT-TYPE
   SYNTAX         SnmpAdminString
   ACCESS         read-only
   STATUS         mandatory
   DESCRIPTION    "The Event text of the trap"
-- REFERENCE      "POWER_DTIOAdapterDiagnosticsEventIndication.Description"
::= { ibmSystempTrapDTIOAdapterDiagnosticsBindings 5 }

ibmSystempTrapDTIOAdapterDiagnosticsTimeStamp OBJECT-TYPE
   SYNTAX         Datetime
   ACCESS         read-only
   STATUS         mandatory
   DESCRIPTION    "The time that the trap occurred"
-- REFERENCE      "POWER_DTIOAdapterDiagnosticsEventIndication.TimeStamp"
::= { ibmSystempTrapDTIOAdapterDiagnosticsBindings 6 }


ibmSystempTrapPFIOAdapterDegradPerf TRAP-TYPE
   ENTERPRISE     ibmSystemMIB
   VARIABLES    {
      ibmSystempTrapPFIOAdapterDegradPerfProviderName,
      ibmSystempTrapPFIOAdapterDegradPerfEventID,
      ibmSystempTrapPFIOAdapterDegradPerfAME,
      ibmSystempTrapPFIOAdapterDegradPerfSeverity,
      ibmSystempTrapPFIOAdapterDegradPerfDescription,
      ibmSystempTrapPFIOAdapterDegradPerfTimeStamp
   }
   DESCRIPTION    "A System p event has occurred"
-- REFERENCE      "POWER_PFIOAdapterDegradPerfEventIndication"
::= 435

ibmSystempTrapPFIOAdapterDegradPerfBindings OBJECT IDENTIFIER ::= { ibmSystemTrap 435 }

ibmSystempTrapPFIOAdapterDegradPerfProviderName OBJECT-TYPE
   SYNTAX         String
   ACCESS         read-only
   STATUS         mandatory
   DESCRIPTION    "The name of the CIM Provider that monitors this device"
-- REFERENCE      "POWER_PFIOAdapterDegradPerfEventIndication.ProviderName"
::= { ibmSystempTrapPFIOAdapterDegradPerfBindings 1 }

ibmSystempTrapPFIOAdapterDegradPerfEventID OBJECT-TYPE
   SYNTAX         String
   ACCESS         read-only
   STATUS         mandatory
   DESCRIPTION    "A unique EventID that identifies this trap" 
-- REFERENCE      "POWER_PFIOAdapterDegradPerfEventIndication.EventID"
::= { ibmSystempTrapPFIOAdapterDegradPerfBindings 2 }

ibmSystempTrapPFIOAdapterDegradPerfAME OBJECT-TYPE
   SYNTAX         String
   ACCESS         read-only
   STATUS         mandatory
   DESCRIPTION    "A unique string that identifies the monitored device"
-- REFERENCE      "POWER_PFIOAdapterDegradPerfEventIndication.AlertingManagedElement"
::= { ibmSystempTrapPFIOAdapterDegradPerfBindings 3 }

ibmSystempTrapPFIOAdapterDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOAdapterDegradPerfEventIndication.Severity"
::= { ibmSystempTrapPFIOAdapterDegradPerfBindings 4 }

ibmSystempTrapPFIOAdapterDegradPerfDescription OBJECT-TYPE
   SYNTAX         SnmpAdminString
   ACCESS         read-only
   STATUS         mandatory
   DESCRIPTION    "The Event text of the trap"
-- REFERENCE      "POWER_PFIOAdapterDegradPerfEventIndication.Description"
::= { ibmSystempTrapPFIOAdapterDegradPerfBindings 5 }

ibmSystempTrapPFIOAdapterDegradPerfTimeStamp OBJECT-TYPE
   SYNTAX         Datetime
   ACCESS         read-only
   STATUS         mandatory
   DESCRIPTION    "The time that the trap occurred"
-- REFERENCE      "POWER_PFIOAdapterDegradPerfEventIndication.TimeStamp"
::= { ibmSystempTrapPFIOAdapterDegradPerfBindings 6 }


ibmSystempTrapPFIOAdapterCorrectAftIPL TRAP-TYPE
   ENTERPRISE     ibmSystemMIB
   VARIABLES    {
      ibmSystempTrapPFIOAdapterCorrectAftIPLProviderName,
      ibmSystempTrapPFIOAdapterCorrectAftIPLEventID,
      ibmSystempTrapPFIOAdapterCorrectAftIPLAME,
      ibmSystempTrapPFIOAdapterCorrectAftIPLSeverity,
      ibmSystempTrapPFIOAdapterCorrectAftIPLDescription,
      ibmSystempTrapPFIOAdapterCorrectAftIPLTimeStamp
   }
   DESCRIPTION    "A System p event has occurred"
-- REFERENCE      "POWER_PFIOAdapterCorrectAftIPLEventIndication"
::= 436

ibmSystempTrapPFIOAdapterCorrectAftIPLBindings OBJECT IDENTIFIER ::= { ibmSystemTrap 436 }

ibmSystempTrapPFIOAdapterCorrectAftIPLProviderName OBJECT-TYPE
   SYNTAX         String
   ACCESS         read-only
   STATUS         mandatory
   DESCRIPTION    "The name of the CIM Provider that monitors this device"
-- REFERENCE      "POWER_PFIOAdapterCorrectAftIPLEventIndication.ProviderName"
::= { ibmSystempTrapPFIOAdapterCorrectAftIPLBindings 1 }

ibmSystempTrapPFIOAdapterCorrectAftIPLEventID OBJECT-TYPE
   SYNTAX         String
   ACCESS         read-only
   STATUS         mandatory
   DESCRIPTION    "A unique EventID that identifies this trap" 
-- REFERENCE      "POWER_PFIOAdapterCorrectAftIPLEventIndication.EventID"
::= { ibmSystempTrapPFIOAdapterCorrectAftIPLBindings 2 }

ibmSystempTrapPFIOAdapterCorrectAftIPLAME OBJECT-TYPE
   SYNTAX         String
   ACCESS         read-only
   STATUS         mandatory
   DESCRIPTION    "A unique string that identifies the monitored device"
-- REFERENCE      "POWER_PFIOAdapterCorrectAftIPLEventIndication.AlertingManagedElement"
::= { ibmSystempTrapPFIOAdapterCorrectAftIPLBindings 3 }

ibmSystempTrapPFIOAdapterCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOAdapterCorrectAftIPLEventIndication.Severity"
::= { ibmSystempTrapPFIOAdapterCorrectAftIPLBindings 4 }

ibmSystempTrapPFIOAdapterCorrectAftIPLDescription OBJECT-TYPE
   SYNTAX         SnmpAdminString
   ACCESS         read-only
   STATUS         mandatory
   DESCRIPTION    "The Event text of the trap"
-- REFERENCE      "POWER_PFIOAdapterCorrectAftIPLEventIndication.Description"
::= { ibmSystempTrapPFIOAdapterCorrectAftIPLBindings 5 }

ibmSystempTrapPFIOAdapterCorrectAftIPLTimeStamp OBJECT-TYPE
   SYNTAX         Datetime
   ACCESS         read-only
   STATUS         mandatory
   DESCRIPTION    "The time that the trap occurred"
-- REFERENCE      "POWER_PFIOAdapterCorrectAftIPLEventIndication.TimeStamp"
::= { ibmSystempTrapPFIOAdapterCorrectAftIPLBindings 6 }


ibmSystempTrapPFIOAdapterCorrectAftIPLPerf TRAP-TYPE
   ENTERPRISE     ibmSystemMIB
   VARIABLES    {
      ibmSystempTrapPFIOAdapterCorrectAftIPLPerfProviderName,
      ibmSystempTrapPFIOAdapterCorrectAftIPLPerfEventID,
      ibmSystempTrapPFIOAdapterCorrectAftIPLPerfAME,
      ibmSystempTrapPFIOAdapterCorrectAftIPLPerfSeverity,
      ibmSystempTrapPFIOAdapterCorrectAftIPLPerfDescription,
      ibmSystempTrapPFIOAdapterCorrectAftIPLPerfTimeStamp
   }
   DESCRIPTION    "A System p event has occurred"
-- REFERENCE      "POWER_PFIOAdapterCorrectAftIPLPerfEventIndication"
::= 437

ibmSystempTrapPFIOAdapterCorrectAftIPLPerfBindings OBJECT IDENTIFIER ::= { ibmSystemTrap 437 }

ibmSystempTrapPFIOAdapterCorrectAftIPLPerfProviderName OBJECT-TYPE
   SYNTAX         String
   ACCESS         read-only
   STATUS         mandatory
   DESCRIPTION    "The name of the CIM Provider that monitors this device"
-- REFERENCE      "POWER_PFIOAdapterCorrectAftIPLPerfEventIndication.ProviderName"
::= { ibmSystempTrapPFIOAdapterCorrectAftIPLPerfBindings 1 }

ibmSystempTrapPFIOAdapterCorrectAftIPLPerfEventID OBJECT-TYPE
   SYNTAX         String
   ACCESS         read-only
   STATUS         mandatory
   DESCRIPTION    "A unique EventID that identifies this trap" 
-- REFERENCE      "POWER_PFIOAdapterCorrectAftIPLPerfEventIndication.EventID"
::= { ibmSystempTrapPFIOAdapterCorrectAftIPLPerfBindings 2 }

ibmSystempTrapPFIOAdapterCorrectAftIPLPerfAME OBJECT-TYPE
   SYNTAX         String
   ACCESS         read-only
   STATUS         mandatory
   DESCRIPTION    "A unique string that identifies the monitored device"
-- REFERENCE      "POWER_PFIOAdapterCorrectAftIPLPerfEventIndication.AlertingManagedElement"
::= { ibmSystempTrapPFIOAdapterCorrectAftIPLPerfBindings 3 }

ibmSystempTrapPFIOAdapterCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOAdapterCorrectAftIPLPerfEventIndication.Severity"
::= { ibmSystempTrapPFIOAdapterCorrectAftIPLPerfBindings 4 }

ibmSystempTrapPFIOAdapterCorrectAftIPLPerfDescription OBJECT-TYPE
   SYNTAX         SnmpAdminString
   ACCESS         read-only
   STATUS         mandatory
   DESCRIPTION    "The Event text of the trap"
-- REFERENCE      "POWER_PFIOAdapterCorrectAftIPLPerfEventIndication.Description"
::= { ibmSystempTrapPFIOAdapterCorrectAftIPLPerfBindings 5 }

ibmSystempTrapPFIOAdapterCorrectAftIPLPerfTimeStamp OBJECT-TYPE
   SYNTAX         Datetime
   ACCESS         read-only
   STATUS         mandatory
   DESCRIPTION    "The time that the trap occurred"
-- REFERENCE      "POWER_PFIOAdapterCorrectAftIPLPerfEventIndication.TimeStamp"
::= { ibmSystempTrapPFIOAdapterCorrectAftIPLPerfBindings 6 }


ibmSystempTrapPFIOAdapterLossOfRedundancy TRAP-TYPE
   ENTERPRISE     ibmSystemMIB
   VARIABLES    {
      ibmSystempTrapPFIOAdapterLossOfRedundancyProviderName,
      ibmSystempTrapPFIOAdapterLossOfRedundancyEventID,
      ibmSystempTrapPFIOAdapterLossOfRedundancyAME,
      ibmSystempTrapPFIOAdapterLossOfRedundancySeverity,
      ibmSystempTrapPFIOAdapterLossOfRedundancyDescription,
      ibmSystempTrapPFIOAdapterLossOfRedundancyTimeStamp
   }
   DESCRIPTION    "A System p event has occurred"
-- REFERENCE      "POWER_PFIOAdapterLossOfRedundancyEventIndication"
::= 438

ibmSystempTrapPFIOAdapterLossOfRedundancyBindings OBJECT IDENTIFIER ::= { ibmSystemTrap 438 }

ibmSystempTrapPFIOAdapterLossOfRedundancyProviderName OBJECT-TYPE
   SYNTAX         String
   ACCESS         read-only
   STATUS         mandatory
   DESCRIPTION    "The name of the CIM Provider that monitors this device"
-- REFERENCE      "POWER_PFIOAdapterLossOfRedundancyEventIndication.ProviderName"
::= { ibmSystempTrapPFIOAdapterLossOfRedundancyBindings 1 }

ibmSystempTrapPFIOAdapterLossOfRedundancyEventID OBJECT-TYPE
   SYNTAX         String
   ACCESS         read-only
   STATUS         mandatory
   DESCRIPTION    "A unique EventID that identifies this trap" 
-- REFERENCE      "POWER_PFIOAdapterLossOfRedundancyEventIndication.EventID"
::= { ibmSystempTrapPFIOAdapterLossOfRedundancyBindings 2 }

ibmSystempTrapPFIOAdapterLossOfRedundancyAME OBJECT-TYPE
   SYNTAX         String
   ACCESS         read-only
   STATUS         mandatory
   DESCRIPTION    "A unique string that identifies the monitored device"
-- REFERENCE      "POWER_PFIOAdapterLossOfRedundancyEventIndication.AlertingManagedElement"
::= { ibmSystempTrapPFIOAdapterLossOfRedundancyBindings 3 }

ibmSystempTrapPFIOAdapterLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOAdapterLossOfRedundancyEventIndication.Severity"
::= { ibmSystempTrapPFIOAdapterLossOfRedundancyBindings 4 }

ibmSystempTrapPFIOAdapterLossOfRedundancyDescription OBJECT-TYPE
   SYNTAX         SnmpAdminString
   ACCESS         read-only
   STATUS         mandatory
   DESCRIPTION    "The Event text of the trap"
-- REFERENCE      "POWER_PFIOAdapterLossOfRedundancyEventIndication.Description"
::= { ibmSystempTrapPFIOAdapterLossOfRedundancyBindings 5 }

ibmSystempTrapPFIOAdapterLossOfRedundancyTimeStamp OBJECT-TYPE
   SYNTAX         Datetime
   ACCESS         read-only
   STATUS         mandatory
   DESCRIPTION    "The time that the trap occurred"
-- REFERENCE      "POWER_PFIOAdapterLossOfRedundancyEventIndication.TimeStamp"
::= { ibmSystempTrapPFIOAdapterLossOfRedundancyBindings 6 }


ibmSystempTrapPFIOAdapterPredictiveError TRAP-TYPE
   ENTERPRISE     ibmSystemMIB
   VARIABLES    {
      ibmSystempTrapPFIOAdapterPredictiveErrorProviderName,
      ibmSystempTrapPFIOAdapterPredictiveErrorEventID,
      ibmSystempTrapPFIOAdapterPredictiveErrorAME,
      ibmSystempTrapPFIOAdapterPredictiveErrorSeverity,
      ibmSystempTrapPFIOAdapterPredictiveErrorDescription,
      ibmSystempTrapPFIOAdapterPredictiveErrorTimeStamp
   }
   DESCRIPTION    "A System p event has occurred"
-- REFERENCE      "POWER_PFIOAdapterPredictiveErrorEventIndication"
::= 439

ibmSystempTrapPFIOAdapterPredictiveErrorBindings OBJECT IDENTIFIER ::= { ibmSystemTrap 439 }

ibmSystempTrapPFIOAdapterPredictiveErrorProviderName OBJECT-TYPE
   SYNTAX         String
   ACCESS         read-only
   STATUS         mandatory
   DESCRIPTION    "The name of the CIM Provider that monitors this device"
-- REFERENCE      "POWER_PFIOAdapterPredictiveErrorEventIndication.ProviderName"
::= { ibmSystempTrapPFIOAdapterPredictiveErrorBindings 1 }

ibmSystempTrapPFIOAdapterPredictiveErrorEventID OBJECT-TYPE
   SYNTAX         String
   ACCESS         read-only
   STATUS         mandatory
   DESCRIPTION    "A unique EventID that identifies this trap" 
-- REFERENCE      "POWER_PFIOAdapterPredictiveErrorEventIndication.EventID"
::= { ibmSystempTrapPFIOAdapterPredictiveErrorBindings 2 }

ibmSystempTrapPFIOAdapterPredictiveErrorAME OBJECT-TYPE
   SYNTAX         String
   ACCESS         read-only
   STATUS         mandatory
   DESCRIPTION    "A unique string that identifies the monitored device"
-- REFERENCE      "POWER_PFIOAdapterPredictiveErrorEventIndication.AlertingManagedElement"
::= { ibmSystempTrapPFIOAdapterPredictiveErrorBindings 3 }

ibmSystempTrapPFIOAdapterPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFIOAdapterPredictiveErrorEventIndication.Severity"
::= { ibmSystempTrapPFIOAdapterPredictiveErrorBindings 4 }

ibmSystempTrapPFIOAdapterPredictiveErrorDescription OBJECT-TYPE
   SYNTAX         SnmpAdminString
   ACCESS         read-only
   STATUS         mandatory
   DESCRIPTION    "The Event text of the trap"
-- REFERENCE      "POWER_PFIOAdapterPredictiveErrorEventIndication.Description"
::= { ibmSystempTrapPFIOAdapterPredictiveErrorBindings 5 }

ibmSystempTrapPFIOAdapterPredictiveErrorTimeStamp OBJECT-TYPE
   SYNTAX         Datetime
   ACCESS         read-only
   STATUS         mandatory
   DESCRIPTION    "The time that the trap occurred"
-- REFERENCE      "POWER_PFIOAdapterPredictiveErrorEventIndication.TimeStamp"
::= { ibmSystempTrapPFIOAdapterPredictiveErrorBindings 6 }


ibmSystempTrapUEIOAdapterDegradPerf TRAP-TYPE
   ENTERPRISE     ibmSystemMIB
   VARIABLES    {
      ibmSystempTrapUEIOAdapterDegradPerfProviderName,
      ibmSystempTrapUEIOAdapterDegradPerfEventID,
      ibmSystempTrapUEIOAdapterDegradPerfAME,
      ibmSystempTrapUEIOAdapterDegradPerfSeverity,
      ibmSystempTrapUEIOAdapterDegradPerfDescription,
      ibmSystempTrapUEIOAdapterDegradPerfTimeStamp
   }
   DESCRIPTION    "A System p event has occurred"
-- REFERENCE      "POWER_UEIOAdapterDegradPerfEventIndication"
::= 440

ibmSystempTrapUEIOAdapterDegradPerfBindings OBJECT IDENTIFIER ::= { ibmSystemTrap 440 }

ibmSystempTrapUEIOAdapterDegradPerfProviderName OBJECT-TYPE
   SYNTAX         String
   ACCESS         read-only
   STATUS         mandatory
   DESCRIPTION    "The name of the CIM Provider that monitors this device"
-- REFERENCE      "POWER_UEIOAdapterDegradPerfEventIndication.ProviderName"
::= { ibmSystempTrapUEIOAdapterDegradPerfBindings 1 }

ibmSystempTrapUEIOAdapterDegradPerfEventID OBJECT-TYPE
   SYNTAX         String
   ACCESS         read-only
   STATUS         mandatory
   DESCRIPTION    "A unique EventID that identifies this trap" 
-- REFERENCE      "POWER_UEIOAdapterDegradPerfEventIndication.EventID"
::= { ibmSystempTrapUEIOAdapterDegradPerfBindings 2 }

ibmSystempTrapUEIOAdapterDegradPerfAME OBJECT-TYPE
   SYNTAX         String
   ACCESS         read-only
   STATUS         mandatory
   DESCRIPTION    "A unique string that identifies the monitored device"
-- REFERENCE      "POWER_UEIOAdapterDegradPerfEventIndication.AlertingManagedElement"
::= { ibmSystempTrapUEIOAdapterDegradPerfBindings 3 }

ibmSystempTrapUEIOAdapterDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOAdapterDegradPerfEventIndication.Severity"
::= { ibmSystempTrapUEIOAdapterDegradPerfBindings 4 }

ibmSystempTrapUEIOAdapterDegradPerfDescription OBJECT-TYPE
   SYNTAX         SnmpAdminString
   ACCESS         read-only
   STATUS         mandatory
   DESCRIPTION    "The Event text of the trap"
-- REFERENCE      "POWER_UEIOAdapterDegradPerfEventIndication.Description"
::= { ibmSystempTrapUEIOAdapterDegradPerfBindings 5 }

ibmSystempTrapUEIOAdapterDegradPerfTimeStamp OBJECT-TYPE
   SYNTAX         Datetime
   ACCESS         read-only
   STATUS         mandatory
   DESCRIPTION    "The time that the trap occurred"
-- REFERENCE      "POWER_UEIOAdapterDegradPerfEventIndication.TimeStamp"
::= { ibmSystempTrapUEIOAdapterDegradPerfBindings 6 }


ibmSystempTrapUEIOAdapterLossOfRedundancy TRAP-TYPE
   ENTERPRISE     ibmSystemMIB
   VARIABLES    {
      ibmSystempTrapUEIOAdapterLossOfRedundancyProviderName,
      ibmSystempTrapUEIOAdapterLossOfRedundancyEventID,
      ibmSystempTrapUEIOAdapterLossOfRedundancyAME,
      ibmSystempTrapUEIOAdapterLossOfRedundancySeverity,
      ibmSystempTrapUEIOAdapterLossOfRedundancyDescription,
      ibmSystempTrapUEIOAdapterLossOfRedundancyTimeStamp
   }
   DESCRIPTION    "A System p event has occurred"
-- REFERENCE      "POWER_UEIOAdapterLossOfRedundancyEventIndication"
::= 441

ibmSystempTrapUEIOAdapterLossOfRedundancyBindings OBJECT IDENTIFIER ::= { ibmSystemTrap 441 }

ibmSystempTrapUEIOAdapterLossOfRedundancyProviderName OBJECT-TYPE
   SYNTAX         String
   ACCESS         read-only
   STATUS         mandatory
   DESCRIPTION    "The name of the CIM Provider that monitors this device"
-- REFERENCE      "POWER_UEIOAdapterLossOfRedundancyEventIndication.ProviderName"
::= { ibmSystempTrapUEIOAdapterLossOfRedundancyBindings 1 }

ibmSystempTrapUEIOAdapterLossOfRedundancyEventID OBJECT-TYPE
   SYNTAX         String
   ACCESS         read-only
   STATUS         mandatory
   DESCRIPTION    "A unique EventID that identifies this trap" 
-- REFERENCE      "POWER_UEIOAdapterLossOfRedundancyEventIndication.EventID"
::= { ibmSystempTrapUEIOAdapterLossOfRedundancyBindings 2 }

ibmSystempTrapUEIOAdapterLossOfRedundancyAME OBJECT-TYPE
   SYNTAX         String
   ACCESS         read-only
   STATUS         mandatory
   DESCRIPTION    "A unique string that identifies the monitored device"
-- REFERENCE      "POWER_UEIOAdapterLossOfRedundancyEventIndication.AlertingManagedElement"
::= { ibmSystempTrapUEIOAdapterLossOfRedundancyBindings 3 }

ibmSystempTrapUEIOAdapterLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOAdapterLossOfRedundancyEventIndication.Severity"
::= { ibmSystempTrapUEIOAdapterLossOfRedundancyBindings 4 }

ibmSystempTrapUEIOAdapterLossOfRedundancyDescription OBJECT-TYPE
   SYNTAX         SnmpAdminString
   ACCESS         read-only
   STATUS         mandatory
   DESCRIPTION    "The Event text of the trap"
-- REFERENCE      "POWER_UEIOAdapterLossOfRedundancyEventIndication.Description"
::= { ibmSystempTrapUEIOAdapterLossOfRedundancyBindings 5 }

ibmSystempTrapUEIOAdapterLossOfRedundancyTimeStamp OBJECT-TYPE
   SYNTAX         Datetime
   ACCESS         read-only
   STATUS         mandatory
   DESCRIPTION    "The time that the trap occurred"
-- REFERENCE      "POWER_UEIOAdapterLossOfRedundancyEventIndication.TimeStamp"
::= { ibmSystempTrapUEIOAdapterLossOfRedundancyBindings 6 }


ibmSystempTrapUEIOAdapterLossOfRedundAndPerf TRAP-TYPE
   ENTERPRISE     ibmSystemMIB
   VARIABLES    {
      ibmSystempTrapUEIOAdapterLossOfRedundAndPerfProviderName,
      ibmSystempTrapUEIOAdapterLossOfRedundAndPerfEventID,
      ibmSystempTrapUEIOAdapterLossOfRedundAndPerfAME,
      ibmSystempTrapUEIOAdapterLossOfRedundAndPerfSeverity,
      ibmSystempTrapUEIOAdapterLossOfRedundAndPerfDescription,
      ibmSystempTrapUEIOAdapterLossOfRedundAndPerfTimeStamp
   }
   DESCRIPTION    "A System p event has occurred"
-- REFERENCE      "POWER_UEIOAdapterLossOfRedundAndPerfEventIndication"
::= 442

ibmSystempTrapUEIOAdapterLossOfRedundAndPerfBindings OBJECT IDENTIFIER ::= { ibmSystemTrap 442 }

ibmSystempTrapUEIOAdapterLossOfRedundAndPerfProviderName OBJECT-TYPE
   SYNTAX         String
   ACCESS         read-only
   STATUS         mandatory
   DESCRIPTION    "The name of the CIM Provider that monitors this device"
-- REFERENCE      "POWER_UEIOAdapterLossOfRedundAndPerfEventIndication.ProviderName"
::= { ibmSystempTrapUEIOAdapterLossOfRedundAndPerfBindings 1 }

ibmSystempTrapUEIOAdapterLossOfRedundAndPerfEventID OBJECT-TYPE
   SYNTAX         String
   ACCESS         read-only
   STATUS         mandatory
   DESCRIPTION    "A unique EventID that identifies this trap" 
-- REFERENCE      "POWER_UEIOAdapterLossOfRedundAndPerfEventIndication.EventID"
::= { ibmSystempTrapUEIOAdapterLossOfRedundAndPerfBindings 2 }

ibmSystempTrapUEIOAdapterLossOfRedundAndPerfAME OBJECT-TYPE
   SYNTAX         String
   ACCESS         read-only
   STATUS         mandatory
   DESCRIPTION    "A unique string that identifies the monitored device"
-- REFERENCE      "POWER_UEIOAdapterLossOfRedundAndPerfEventIndication.AlertingManagedElement"
::= { ibmSystempTrapUEIOAdapterLossOfRedundAndPerfBindings 3 }

ibmSystempTrapUEIOAdapterLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOAdapterLossOfRedundAndPerfEventIndication.Severity"
::= { ibmSystempTrapUEIOAdapterLossOfRedundAndPerfBindings 4 }

ibmSystempTrapUEIOAdapterLossOfRedundAndPerfDescription OBJECT-TYPE
   SYNTAX         SnmpAdminString
   ACCESS         read-only
   STATUS         mandatory
   DESCRIPTION    "The Event text of the trap"
-- REFERENCE      "POWER_UEIOAdapterLossOfRedundAndPerfEventIndication.Description"
::= { ibmSystempTrapUEIOAdapterLossOfRedundAndPerfBindings 5 }

ibmSystempTrapUEIOAdapterLossOfRedundAndPerfTimeStamp OBJECT-TYPE
   SYNTAX         Datetime
   ACCESS         read-only
   STATUS         mandatory
   DESCRIPTION    "The time that the trap occurred"
-- REFERENCE      "POWER_UEIOAdapterLossOfRedundAndPerfEventIndication.TimeStamp"
::= { ibmSystempTrapUEIOAdapterLossOfRedundAndPerfBindings 6 }


ibmSystempTrapUEIOAdapterLossOfFunction TRAP-TYPE
   ENTERPRISE     ibmSystemMIB
   VARIABLES    {
      ibmSystempTrapUEIOAdapterLossOfFunctionProviderName,
      ibmSystempTrapUEIOAdapterLossOfFunctionEventID,
      ibmSystempTrapUEIOAdapterLossOfFunctionAME,
      ibmSystempTrapUEIOAdapterLossOfFunctionSeverity,
      ibmSystempTrapUEIOAdapterLossOfFunctionDescription,
      ibmSystempTrapUEIOAdapterLossOfFunctionTimeStamp
   }
   DESCRIPTION    "A System p event has occurred"
-- REFERENCE      "POWER_UEIOAdapterLossOfFunctionEventIndication"
::= 443

ibmSystempTrapUEIOAdapterLossOfFunctionBindings OBJECT IDENTIFIER ::= { ibmSystemTrap 443 }

ibmSystempTrapUEIOAdapterLossOfFunctionProviderName OBJECT-TYPE
   SYNTAX         String
   ACCESS         read-only
   STATUS         mandatory
   DESCRIPTION    "The name of the CIM Provider that monitors this device"
-- REFERENCE      "POWER_UEIOAdapterLossOfFunctionEventIndication.ProviderName"
::= { ibmSystempTrapUEIOAdapterLossOfFunctionBindings 1 }

ibmSystempTrapUEIOAdapterLossOfFunctionEventID OBJECT-TYPE
   SYNTAX         String
   ACCESS         read-only
   STATUS         mandatory
   DESCRIPTION    "A unique EventID that identifies this trap" 
-- REFERENCE      "POWER_UEIOAdapterLossOfFunctionEventIndication.EventID"
::= { ibmSystempTrapUEIOAdapterLossOfFunctionBindings 2 }

ibmSystempTrapUEIOAdapterLossOfFunctionAME OBJECT-TYPE
   SYNTAX         String
   ACCESS         read-only
   STATUS         mandatory
   DESCRIPTION    "A unique string that identifies the monitored device"
-- REFERENCE      "POWER_UEIOAdapterLossOfFunctionEventIndication.AlertingManagedElement"
::= { ibmSystempTrapUEIOAdapterLossOfFunctionBindings 3 }

ibmSystempTrapUEIOAdapterLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOAdapterLossOfFunctionEventIndication.Severity"
::= { ibmSystempTrapUEIOAdapterLossOfFunctionBindings 4 }

ibmSystempTrapUEIOAdapterLossOfFunctionDescription OBJECT-TYPE
   SYNTAX         SnmpAdminString
   ACCESS         read-only
   STATUS         mandatory
   DESCRIPTION    "The Event text of the trap"
-- REFERENCE      "POWER_UEIOAdapterLossOfFunctionEventIndication.Description"
::= { ibmSystempTrapUEIOAdapterLossOfFunctionBindings 5 }

ibmSystempTrapUEIOAdapterLossOfFunctionTimeStamp OBJECT-TYPE
   SYNTAX         Datetime
   ACCESS         read-only
   STATUS         mandatory
   DESCRIPTION    "The time that the trap occurred"
-- REFERENCE      "POWER_UEIOAdapterLossOfFunctionEventIndication.TimeStamp"
::= { ibmSystempTrapUEIOAdapterLossOfFunctionBindings 6 }


ibmSystempTrapUEIOAdapterUnrecoverableError TRAP-TYPE
   ENTERPRISE     ibmSystemMIB
   VARIABLES    {
      ibmSystempTrapUEIOAdapterUnrecoverableErrorProviderName,
      ibmSystempTrapUEIOAdapterUnrecoverableErrorEventID,
      ibmSystempTrapUEIOAdapterUnrecoverableErrorAME,
      ibmSystempTrapUEIOAdapterUnrecoverableErrorSeverity,
      ibmSystempTrapUEIOAdapterUnrecoverableErrorDescription,
      ibmSystempTrapUEIOAdapterUnrecoverableErrorTimeStamp
   }
   DESCRIPTION    "A System p event has occurred"
-- REFERENCE      "POWER_UEIOAdapterUnrecoverableErrorEventIndication"
::= 444

ibmSystempTrapUEIOAdapterUnrecoverableErrorBindings OBJECT IDENTIFIER ::= { ibmSystemTrap 444 }

ibmSystempTrapUEIOAdapterUnrecoverableErrorProviderName OBJECT-TYPE
   SYNTAX         String
   ACCESS         read-only
   STATUS         mandatory
   DESCRIPTION    "The name of the CIM Provider that monitors this device"
-- REFERENCE      "POWER_UEIOAdapterUnrecoverableErrorEventIndication.ProviderName"
::= { ibmSystempTrapUEIOAdapterUnrecoverableErrorBindings 1 }

ibmSystempTrapUEIOAdapterUnrecoverableErrorEventID OBJECT-TYPE
   SYNTAX         String
   ACCESS         read-only
   STATUS         mandatory
   DESCRIPTION    "A unique EventID that identifies this trap" 
-- REFERENCE      "POWER_UEIOAdapterUnrecoverableErrorEventIndication.EventID"
::= { ibmSystempTrapUEIOAdapterUnrecoverableErrorBindings 2 }

ibmSystempTrapUEIOAdapterUnrecoverableErrorAME OBJECT-TYPE
   SYNTAX         String
   ACCESS         read-only
   STATUS         mandatory
   DESCRIPTION    "A unique string that identifies the monitored device"
-- REFERENCE      "POWER_UEIOAdapterUnrecoverableErrorEventIndication.AlertingManagedElement"
::= { ibmSystempTrapUEIOAdapterUnrecoverableErrorBindings 3 }

ibmSystempTrapUEIOAdapterUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEIOAdapterUnrecoverableErrorEventIndication.Severity"
::= { ibmSystempTrapUEIOAdapterUnrecoverableErrorBindings 4 }

ibmSystempTrapUEIOAdapterUnrecoverableErrorDescription OBJECT-TYPE
   SYNTAX         SnmpAdminString
   ACCESS         read-only
   STATUS         mandatory
   DESCRIPTION    "The Event text of the trap"
-- REFERENCE      "POWER_UEIOAdapterUnrecoverableErrorEventIndication.Description"
::= { ibmSystempTrapUEIOAdapterUnrecoverableErrorBindings 5 }

ibmSystempTrapUEIOAdapterUnrecoverableErrorTimeStamp OBJECT-TYPE
   SYNTAX         Datetime
   ACCESS         read-only
   STATUS         mandatory
   DESCRIPTION    "The time that the trap occurred"
-- REFERENCE      "POWER_UEIOAdapterUnrecoverableErrorEventIndication.TimeStamp"
::= { ibmSystempTrapUEIOAdapterUnrecoverableErrorBindings 6 }


ibmSystempTrapDTCECHWDiagnostics TRAP-TYPE
   ENTERPRISE     ibmSystemMIB
   VARIABLES    {
      ibmSystempTrapDTCECHWDiagnosticsProviderName,
      ibmSystempTrapDTCECHWDiagnosticsEventID,
      ibmSystempTrapDTCECHWDiagnosticsAME,
      ibmSystempTrapDTCECHWDiagnosticsSeverity,
      ibmSystempTrapDTCECHWDiagnosticsDescription,
      ibmSystempTrapDTCECHWDiagnosticsTimeStamp
   }
   DESCRIPTION    "A System p event has occurred"
-- REFERENCE      "POWER_DTCECHWDiagnosticsEventIndication"
::= 445

ibmSystempTrapDTCECHWDiagnosticsBindings OBJECT IDENTIFIER ::= { ibmSystemTrap 445 }

ibmSystempTrapDTCECHWDiagnosticsProviderName OBJECT-TYPE
   SYNTAX         String
   ACCESS         read-only
   STATUS         mandatory
   DESCRIPTION    "The name of the CIM Provider that monitors this device"
-- REFERENCE      "POWER_DTCECHWDiagnosticsEventIndication.ProviderName"
::= { ibmSystempTrapDTCECHWDiagnosticsBindings 1 }

ibmSystempTrapDTCECHWDiagnosticsEventID OBJECT-TYPE
   SYNTAX         String
   ACCESS         read-only
   STATUS         mandatory
   DESCRIPTION    "A unique EventID that identifies this trap" 
-- REFERENCE      "POWER_DTCECHWDiagnosticsEventIndication.EventID"
::= { ibmSystempTrapDTCECHWDiagnosticsBindings 2 }

ibmSystempTrapDTCECHWDiagnosticsAME OBJECT-TYPE
   SYNTAX         String
   ACCESS         read-only
   STATUS         mandatory
   DESCRIPTION    "A unique string that identifies the monitored device"
-- REFERENCE      "POWER_DTCECHWDiagnosticsEventIndication.AlertingManagedElement"
::= { ibmSystempTrapDTCECHWDiagnosticsBindings 3 }

ibmSystempTrapDTCECHWDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTCECHWDiagnosticsEventIndication.Severity"
::= { ibmSystempTrapDTCECHWDiagnosticsBindings 4 }

ibmSystempTrapDTCECHWDiagnosticsDescription OBJECT-TYPE
   SYNTAX         SnmpAdminString
   ACCESS         read-only
   STATUS         mandatory
   DESCRIPTION    "The Event text of the trap"
-- REFERENCE      "POWER_DTCECHWDiagnosticsEventIndication.Description"
::= { ibmSystempTrapDTCECHWDiagnosticsBindings 5 }

ibmSystempTrapDTCECHWDiagnosticsTimeStamp OBJECT-TYPE
   SYNTAX         Datetime
   ACCESS         read-only
   STATUS         mandatory
   DESCRIPTION    "The time that the trap occurred"
-- REFERENCE      "POWER_DTCECHWDiagnosticsEventIndication.TimeStamp"
::= { ibmSystempTrapDTCECHWDiagnosticsBindings 6 }


ibmSystempTrapPFCECHWDegradPerf TRAP-TYPE
   ENTERPRISE     ibmSystemMIB
   VARIABLES    {
      ibmSystempTrapPFCECHWDegradPerfProviderName,
      ibmSystempTrapPFCECHWDegradPerfEventID,
      ibmSystempTrapPFCECHWDegradPerfAME,
      ibmSystempTrapPFCECHWDegradPerfSeverity,
      ibmSystempTrapPFCECHWDegradPerfDescription,
      ibmSystempTrapPFCECHWDegradPerfTimeStamp
   }
   DESCRIPTION    "A System p event has occurred"
-- REFERENCE      "POWER_PFCECHWDegradPerfEventIndication"
::= 446

ibmSystempTrapPFCECHWDegradPerfBindings OBJECT IDENTIFIER ::= { ibmSystemTrap 446 }

ibmSystempTrapPFCECHWDegradPerfProviderName OBJECT-TYPE
   SYNTAX         String
   ACCESS         read-only
   STATUS         mandatory
   DESCRIPTION    "The name of the CIM Provider that monitors this device"
-- REFERENCE      "POWER_PFCECHWDegradPerfEventIndication.ProviderName"
::= { ibmSystempTrapPFCECHWDegradPerfBindings 1 }

ibmSystempTrapPFCECHWDegradPerfEventID OBJECT-TYPE
   SYNTAX         String
   ACCESS         read-only
   STATUS         mandatory
   DESCRIPTION    "A unique EventID that identifies this trap" 
-- REFERENCE      "POWER_PFCECHWDegradPerfEventIndication.EventID"
::= { ibmSystempTrapPFCECHWDegradPerfBindings 2 }

ibmSystempTrapPFCECHWDegradPerfAME OBJECT-TYPE
   SYNTAX         String
   ACCESS         read-only
   STATUS         mandatory
   DESCRIPTION    "A unique string that identifies the monitored device"
-- REFERENCE      "POWER_PFCECHWDegradPerfEventIndication.AlertingManagedElement"
::= { ibmSystempTrapPFCECHWDegradPerfBindings 3 }

ibmSystempTrapPFCECHWDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFCECHWDegradPerfEventIndication.Severity"
::= { ibmSystempTrapPFCECHWDegradPerfBindings 4 }

ibmSystempTrapPFCECHWDegradPerfDescription OBJECT-TYPE
   SYNTAX         SnmpAdminString
   ACCESS         read-only
   STATUS         mandatory
   DESCRIPTION    "The Event text of the trap"
-- REFERENCE      "POWER_PFCECHWDegradPerfEventIndication.Description"
::= { ibmSystempTrapPFCECHWDegradPerfBindings 5 }

ibmSystempTrapPFCECHWDegradPerfTimeStamp OBJECT-TYPE
   SYNTAX         Datetime
   ACCESS         read-only
   STATUS         mandatory
   DESCRIPTION    "The time that the trap occurred"
-- REFERENCE      "POWER_PFCECHWDegradPerfEventIndication.TimeStamp"
::= { ibmSystempTrapPFCECHWDegradPerfBindings 6 }


ibmSystempTrapPFCECHWCorrectAftIPL TRAP-TYPE
   ENTERPRISE     ibmSystemMIB
   VARIABLES    {
      ibmSystempTrapPFCECHWCorrectAftIPLProviderName,
      ibmSystempTrapPFCECHWCorrectAftIPLEventID,
      ibmSystempTrapPFCECHWCorrectAftIPLAME,
      ibmSystempTrapPFCECHWCorrectAftIPLSeverity,
      ibmSystempTrapPFCECHWCorrectAftIPLDescription,
      ibmSystempTrapPFCECHWCorrectAftIPLTimeStamp
   }
   DESCRIPTION    "A System p event has occurred"
-- REFERENCE      "POWER_PFCECHWCorrectAftIPLEventIndication"
::= 447

ibmSystempTrapPFCECHWCorrectAftIPLBindings OBJECT IDENTIFIER ::= { ibmSystemTrap 447 }

ibmSystempTrapPFCECHWCorrectAftIPLProviderName OBJECT-TYPE
   SYNTAX         String
   ACCESS         read-only
   STATUS         mandatory
   DESCRIPTION    "The name of the CIM Provider that monitors this device"
-- REFERENCE      "POWER_PFCECHWCorrectAftIPLEventIndication.ProviderName"
::= { ibmSystempTrapPFCECHWCorrectAftIPLBindings 1 }

ibmSystempTrapPFCECHWCorrectAftIPLEventID OBJECT-TYPE
   SYNTAX         String
   ACCESS         read-only
   STATUS         mandatory
   DESCRIPTION    "A unique EventID that identifies this trap" 
-- REFERENCE      "POWER_PFCECHWCorrectAftIPLEventIndication.EventID"
::= { ibmSystempTrapPFCECHWCorrectAftIPLBindings 2 }

ibmSystempTrapPFCECHWCorrectAftIPLAME OBJECT-TYPE
   SYNTAX         String
   ACCESS         read-only
   STATUS         mandatory
   DESCRIPTION    "A unique string that identifies the monitored device"
-- REFERENCE      "POWER_PFCECHWCorrectAftIPLEventIndication.AlertingManagedElement"
::= { ibmSystempTrapPFCECHWCorrectAftIPLBindings 3 }

ibmSystempTrapPFCECHWCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFCECHWCorrectAftIPLEventIndication.Severity"
::= { ibmSystempTrapPFCECHWCorrectAftIPLBindings 4 }

ibmSystempTrapPFCECHWCorrectAftIPLDescription OBJECT-TYPE
   SYNTAX         SnmpAdminString
   ACCESS         read-only
   STATUS         mandatory
   DESCRIPTION    "The Event text of the trap"
-- REFERENCE      "POWER_PFCECHWCorrectAftIPLEventIndication.Description"
::= { ibmSystempTrapPFCECHWCorrectAftIPLBindings 5 }

ibmSystempTrapPFCECHWCorrectAftIPLTimeStamp OBJECT-TYPE
   SYNTAX         Datetime
   ACCESS         read-only
   STATUS         mandatory
   DESCRIPTION    "The time that the trap occurred"
-- REFERENCE      "POWER_PFCECHWCorrectAftIPLEventIndication.TimeStamp"
::= { ibmSystempTrapPFCECHWCorrectAftIPLBindings 6 }


ibmSystempTrapPFCECHWCorrectAftIPLPerf TRAP-TYPE
   ENTERPRISE     ibmSystemMIB
   VARIABLES    {
      ibmSystempTrapPFCECHWCorrectAftIPLPerfProviderName,
      ibmSystempTrapPFCECHWCorrectAftIPLPerfEventID,
      ibmSystempTrapPFCECHWCorrectAftIPLPerfAME,
      ibmSystempTrapPFCECHWCorrectAftIPLPerfSeverity,
      ibmSystempTrapPFCECHWCorrectAftIPLPerfDescription,
      ibmSystempTrapPFCECHWCorrectAftIPLPerfTimeStamp
   }
   DESCRIPTION    "A System p event has occurred"
-- REFERENCE      "POWER_PFCECHWCorrectAftIPLPerfEventIndication"
::= 448

ibmSystempTrapPFCECHWCorrectAftIPLPerfBindings OBJECT IDENTIFIER ::= { ibmSystemTrap 448 }

ibmSystempTrapPFCECHWCorrectAftIPLPerfProviderName OBJECT-TYPE
   SYNTAX         String
   ACCESS         read-only
   STATUS         mandatory
   DESCRIPTION    "The name of the CIM Provider that monitors this device"
-- REFERENCE      "POWER_PFCECHWCorrectAftIPLPerfEventIndication.ProviderName"
::= { ibmSystempTrapPFCECHWCorrectAftIPLPerfBindings 1 }

ibmSystempTrapPFCECHWCorrectAftIPLPerfEventID OBJECT-TYPE
   SYNTAX         String
   ACCESS         read-only
   STATUS         mandatory
   DESCRIPTION    "A unique EventID that identifies this trap" 
-- REFERENCE      "POWER_PFCECHWCorrectAftIPLPerfEventIndication.EventID"
::= { ibmSystempTrapPFCECHWCorrectAftIPLPerfBindings 2 }

ibmSystempTrapPFCECHWCorrectAftIPLPerfAME OBJECT-TYPE
   SYNTAX         String
   ACCESS         read-only
   STATUS         mandatory
   DESCRIPTION    "A unique string that identifies the monitored device"
-- REFERENCE      "POWER_PFCECHWCorrectAftIPLPerfEventIndication.AlertingManagedElement"
::= { ibmSystempTrapPFCECHWCorrectAftIPLPerfBindings 3 }

ibmSystempTrapPFCECHWCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFCECHWCorrectAftIPLPerfEventIndication.Severity"
::= { ibmSystempTrapPFCECHWCorrectAftIPLPerfBindings 4 }

ibmSystempTrapPFCECHWCorrectAftIPLPerfDescription OBJECT-TYPE
   SYNTAX         SnmpAdminString
   ACCESS         read-only
   STATUS         mandatory
   DESCRIPTION    "The Event text of the trap"
-- REFERENCE      "POWER_PFCECHWCorrectAftIPLPerfEventIndication.Description"
::= { ibmSystempTrapPFCECHWCorrectAftIPLPerfBindings 5 }

ibmSystempTrapPFCECHWCorrectAftIPLPerfTimeStamp OBJECT-TYPE
   SYNTAX         Datetime
   ACCESS         read-only
   STATUS         mandatory
   DESCRIPTION    "The time that the trap occurred"
-- REFERENCE      "POWER_PFCECHWCorrectAftIPLPerfEventIndication.TimeStamp"
::= { ibmSystempTrapPFCECHWCorrectAftIPLPerfBindings 6 }


ibmSystempTrapPFCECHWLossOfRedundancy TRAP-TYPE
   ENTERPRISE     ibmSystemMIB
   VARIABLES    {
      ibmSystempTrapPFCECHWLossOfRedundancyProviderName,
      ibmSystempTrapPFCECHWLossOfRedundancyEventID,
      ibmSystempTrapPFCECHWLossOfRedundancyAME,
      ibmSystempTrapPFCECHWLossOfRedundancySeverity,
      ibmSystempTrapPFCECHWLossOfRedundancyDescription,
      ibmSystempTrapPFCECHWLossOfRedundancyTimeStamp
   }
   DESCRIPTION    "A System p event has occurred"
-- REFERENCE      "POWER_PFCECHWLossOfRedundancyEventIndication"
::= 449

ibmSystempTrapPFCECHWLossOfRedundancyBindings OBJECT IDENTIFIER ::= { ibmSystemTrap 449 }

ibmSystempTrapPFCECHWLossOfRedundancyProviderName OBJECT-TYPE
   SYNTAX         String
   ACCESS         read-only
   STATUS         mandatory
   DESCRIPTION    "The name of the CIM Provider that monitors this device"
-- REFERENCE      "POWER_PFCECHWLossOfRedundancyEventIndication.ProviderName"
::= { ibmSystempTrapPFCECHWLossOfRedundancyBindings 1 }

ibmSystempTrapPFCECHWLossOfRedundancyEventID OBJECT-TYPE
   SYNTAX         String
   ACCESS         read-only
   STATUS         mandatory
   DESCRIPTION    "A unique EventID that identifies this trap" 
-- REFERENCE      "POWER_PFCECHWLossOfRedundancyEventIndication.EventID"
::= { ibmSystempTrapPFCECHWLossOfRedundancyBindings 2 }

ibmSystempTrapPFCECHWLossOfRedundancyAME OBJECT-TYPE
   SYNTAX         String
   ACCESS         read-only
   STATUS         mandatory
   DESCRIPTION    "A unique string that identifies the monitored device"
-- REFERENCE      "POWER_PFCECHWLossOfRedundancyEventIndication.AlertingManagedElement"
::= { ibmSystempTrapPFCECHWLossOfRedundancyBindings 3 }

ibmSystempTrapPFCECHWLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFCECHWLossOfRedundancyEventIndication.Severity"
::= { ibmSystempTrapPFCECHWLossOfRedundancyBindings 4 }

ibmSystempTrapPFCECHWLossOfRedundancyDescription OBJECT-TYPE
   SYNTAX         SnmpAdminString
   ACCESS         read-only
   STATUS         mandatory
   DESCRIPTION    "The Event text of the trap"
-- REFERENCE      "POWER_PFCECHWLossOfRedundancyEventIndication.Description"
::= { ibmSystempTrapPFCECHWLossOfRedundancyBindings 5 }

ibmSystempTrapPFCECHWLossOfRedundancyTimeStamp OBJECT-TYPE
   SYNTAX         Datetime
   ACCESS         read-only
   STATUS         mandatory
   DESCRIPTION    "The time that the trap occurred"
-- REFERENCE      "POWER_PFCECHWLossOfRedundancyEventIndication.TimeStamp"
::= { ibmSystempTrapPFCECHWLossOfRedundancyBindings 6 }


ibmSystempTrapPFCECHWPredictiveError TRAP-TYPE
   ENTERPRISE     ibmSystemMIB
   VARIABLES    {
      ibmSystempTrapPFCECHWPredictiveErrorProviderName,
      ibmSystempTrapPFCECHWPredictiveErrorEventID,
      ibmSystempTrapPFCECHWPredictiveErrorAME,
      ibmSystempTrapPFCECHWPredictiveErrorSeverity,
      ibmSystempTrapPFCECHWPredictiveErrorDescription,
      ibmSystempTrapPFCECHWPredictiveErrorTimeStamp
   }
   DESCRIPTION    "A System p event has occurred"
-- REFERENCE      "POWER_PFCECHWPredictiveErrorEventIndication"
::= 450

ibmSystempTrapPFCECHWPredictiveErrorBindings OBJECT IDENTIFIER ::= { ibmSystemTrap 450 }

ibmSystempTrapPFCECHWPredictiveErrorProviderName OBJECT-TYPE
   SYNTAX         String
   ACCESS         read-only
   STATUS         mandatory
   DESCRIPTION    "The name of the CIM Provider that monitors this device"
-- REFERENCE      "POWER_PFCECHWPredictiveErrorEventIndication.ProviderName"
::= { ibmSystempTrapPFCECHWPredictiveErrorBindings 1 }

ibmSystempTrapPFCECHWPredictiveErrorEventID OBJECT-TYPE
   SYNTAX         String
   ACCESS         read-only
   STATUS         mandatory
   DESCRIPTION    "A unique EventID that identifies this trap" 
-- REFERENCE      "POWER_PFCECHWPredictiveErrorEventIndication.EventID"
::= { ibmSystempTrapPFCECHWPredictiveErrorBindings 2 }

ibmSystempTrapPFCECHWPredictiveErrorAME OBJECT-TYPE
   SYNTAX         String
   ACCESS         read-only
   STATUS         mandatory
   DESCRIPTION    "A unique string that identifies the monitored device"
-- REFERENCE      "POWER_PFCECHWPredictiveErrorEventIndication.AlertingManagedElement"
::= { ibmSystempTrapPFCECHWPredictiveErrorBindings 3 }

ibmSystempTrapPFCECHWPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFCECHWPredictiveErrorEventIndication.Severity"
::= { ibmSystempTrapPFCECHWPredictiveErrorBindings 4 }

ibmSystempTrapPFCECHWPredictiveErrorDescription OBJECT-TYPE
   SYNTAX         SnmpAdminString
   ACCESS         read-only
   STATUS         mandatory
   DESCRIPTION    "The Event text of the trap"
-- REFERENCE      "POWER_PFCECHWPredictiveErrorEventIndication.Description"
::= { ibmSystempTrapPFCECHWPredictiveErrorBindings 5 }

ibmSystempTrapPFCECHWPredictiveErrorTimeStamp OBJECT-TYPE
   SYNTAX         Datetime
   ACCESS         read-only
   STATUS         mandatory
   DESCRIPTION    "The time that the trap occurred"
-- REFERENCE      "POWER_PFCECHWPredictiveErrorEventIndication.TimeStamp"
::= { ibmSystempTrapPFCECHWPredictiveErrorBindings 6 }


ibmSystempTrapUECECHWDegradPerf TRAP-TYPE
   ENTERPRISE     ibmSystemMIB
   VARIABLES    {
      ibmSystempTrapUECECHWDegradPerfProviderName,
      ibmSystempTrapUECECHWDegradPerfEventID,
      ibmSystempTrapUECECHWDegradPerfAME,
      ibmSystempTrapUECECHWDegradPerfSeverity,
      ibmSystempTrapUECECHWDegradPerfDescription,
      ibmSystempTrapUECECHWDegradPerfTimeStamp
   }
   DESCRIPTION    "A System p event has occurred"
-- REFERENCE      "POWER_UECECHWDegradPerfEventIndication"
::= 451

ibmSystempTrapUECECHWDegradPerfBindings OBJECT IDENTIFIER ::= { ibmSystemTrap 451 }

ibmSystempTrapUECECHWDegradPerfProviderName OBJECT-TYPE
   SYNTAX         String
   ACCESS         read-only
   STATUS         mandatory
   DESCRIPTION    "The name of the CIM Provider that monitors this device"
-- REFERENCE      "POWER_UECECHWDegradPerfEventIndication.ProviderName"
::= { ibmSystempTrapUECECHWDegradPerfBindings 1 }

ibmSystempTrapUECECHWDegradPerfEventID OBJECT-TYPE
   SYNTAX         String
   ACCESS         read-only
   STATUS         mandatory
   DESCRIPTION    "A unique EventID that identifies this trap" 
-- REFERENCE      "POWER_UECECHWDegradPerfEventIndication.EventID"
::= { ibmSystempTrapUECECHWDegradPerfBindings 2 }

ibmSystempTrapUECECHWDegradPerfAME OBJECT-TYPE
   SYNTAX         String
   ACCESS         read-only
   STATUS         mandatory
   DESCRIPTION    "A unique string that identifies the monitored device"
-- REFERENCE      "POWER_UECECHWDegradPerfEventIndication.AlertingManagedElement"
::= { ibmSystempTrapUECECHWDegradPerfBindings 3 }

ibmSystempTrapUECECHWDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UECECHWDegradPerfEventIndication.Severity"
::= { ibmSystempTrapUECECHWDegradPerfBindings 4 }

ibmSystempTrapUECECHWDegradPerfDescription OBJECT-TYPE
   SYNTAX         SnmpAdminString
   ACCESS         read-only
   STATUS         mandatory
   DESCRIPTION    "The Event text of the trap"
-- REFERENCE      "POWER_UECECHWDegradPerfEventIndication.Description"
::= { ibmSystempTrapUECECHWDegradPerfBindings 5 }

ibmSystempTrapUECECHWDegradPerfTimeStamp OBJECT-TYPE
   SYNTAX         Datetime
   ACCESS         read-only
   STATUS         mandatory
   DESCRIPTION    "The time that the trap occurred"
-- REFERENCE      "POWER_UECECHWDegradPerfEventIndication.TimeStamp"
::= { ibmSystempTrapUECECHWDegradPerfBindings 6 }


ibmSystempTrapUECECHWLossOfRedundancy TRAP-TYPE
   ENTERPRISE     ibmSystemMIB
   VARIABLES    {
      ibmSystempTrapUECECHWLossOfRedundancyProviderName,
      ibmSystempTrapUECECHWLossOfRedundancyEventID,
      ibmSystempTrapUECECHWLossOfRedundancyAME,
      ibmSystempTrapUECECHWLossOfRedundancySeverity,
      ibmSystempTrapUECECHWLossOfRedundancyDescription,
      ibmSystempTrapUECECHWLossOfRedundancyTimeStamp
   }
   DESCRIPTION    "A System p event has occurred"
-- REFERENCE      "POWER_UECECHWLossOfRedundancyEventIndication"
::= 452

ibmSystempTrapUECECHWLossOfRedundancyBindings OBJECT IDENTIFIER ::= { ibmSystemTrap 452 }

ibmSystempTrapUECECHWLossOfRedundancyProviderName OBJECT-TYPE
   SYNTAX         String
   ACCESS         read-only
   STATUS         mandatory
   DESCRIPTION    "The name of the CIM Provider that monitors this device"
-- REFERENCE      "POWER_UECECHWLossOfRedundancyEventIndication.ProviderName"
::= { ibmSystempTrapUECECHWLossOfRedundancyBindings 1 }

ibmSystempTrapUECECHWLossOfRedundancyEventID OBJECT-TYPE
   SYNTAX         String
   ACCESS         read-only
   STATUS         mandatory
   DESCRIPTION    "A unique EventID that identifies this trap" 
-- REFERENCE      "POWER_UECECHWLossOfRedundancyEventIndication.EventID"
::= { ibmSystempTrapUECECHWLossOfRedundancyBindings 2 }

ibmSystempTrapUECECHWLossOfRedundancyAME OBJECT-TYPE
   SYNTAX         String
   ACCESS         read-only
   STATUS         mandatory
   DESCRIPTION    "A unique string that identifies the monitored device"
-- REFERENCE      "POWER_UECECHWLossOfRedundancyEventIndication.AlertingManagedElement"
::= { ibmSystempTrapUECECHWLossOfRedundancyBindings 3 }

ibmSystempTrapUECECHWLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UECECHWLossOfRedundancyEventIndication.Severity"
::= { ibmSystempTrapUECECHWLossOfRedundancyBindings 4 }

ibmSystempTrapUECECHWLossOfRedundancyDescription OBJECT-TYPE
   SYNTAX         SnmpAdminString
   ACCESS         read-only
   STATUS         mandatory
   DESCRIPTION    "The Event text of the trap"
-- REFERENCE      "POWER_UECECHWLossOfRedundancyEventIndication.Description"
::= { ibmSystempTrapUECECHWLossOfRedundancyBindings 5 }

ibmSystempTrapUECECHWLossOfRedundancyTimeStamp OBJECT-TYPE
   SYNTAX         Datetime
   ACCESS         read-only
   STATUS         mandatory
   DESCRIPTION    "The time that the trap occurred"
-- REFERENCE      "POWER_UECECHWLossOfRedundancyEventIndication.TimeStamp"
::= { ibmSystempTrapUECECHWLossOfRedundancyBindings 6 }


ibmSystempTrapUECECHWLossOfRedundAndPerf TRAP-TYPE
   ENTERPRISE     ibmSystemMIB
   VARIABLES    {
      ibmSystempTrapUECECHWLossOfRedundAndPerfProviderName,
      ibmSystempTrapUECECHWLossOfRedundAndPerfEventID,
      ibmSystempTrapUECECHWLossOfRedundAndPerfAME,
      ibmSystempTrapUECECHWLossOfRedundAndPerfSeverity,
      ibmSystempTrapUECECHWLossOfRedundAndPerfDescription,
      ibmSystempTrapUECECHWLossOfRedundAndPerfTimeStamp
   }
   DESCRIPTION    "A System p event has occurred"
-- REFERENCE      "POWER_UECECHWLossOfRedundAndPerfEventIndication"
::= 453

ibmSystempTrapUECECHWLossOfRedundAndPerfBindings OBJECT IDENTIFIER ::= { ibmSystemTrap 453 }

ibmSystempTrapUECECHWLossOfRedundAndPerfProviderName OBJECT-TYPE
   SYNTAX         String
   ACCESS         read-only
   STATUS         mandatory
   DESCRIPTION    "The name of the CIM Provider that monitors this device"
-- REFERENCE      "POWER_UECECHWLossOfRedundAndPerfEventIndication.ProviderName"
::= { ibmSystempTrapUECECHWLossOfRedundAndPerfBindings 1 }

ibmSystempTrapUECECHWLossOfRedundAndPerfEventID OBJECT-TYPE
   SYNTAX         String
   ACCESS         read-only
   STATUS         mandatory
   DESCRIPTION    "A unique EventID that identifies this trap" 
-- REFERENCE      "POWER_UECECHWLossOfRedundAndPerfEventIndication.EventID"
::= { ibmSystempTrapUECECHWLossOfRedundAndPerfBindings 2 }

ibmSystempTrapUECECHWLossOfRedundAndPerfAME OBJECT-TYPE
   SYNTAX         String
   ACCESS         read-only
   STATUS         mandatory
   DESCRIPTION    "A unique string that identifies the monitored device"
-- REFERENCE      "POWER_UECECHWLossOfRedundAndPerfEventIndication.AlertingManagedElement"
::= { ibmSystempTrapUECECHWLossOfRedundAndPerfBindings 3 }

ibmSystempTrapUECECHWLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UECECHWLossOfRedundAndPerfEventIndication.Severity"
::= { ibmSystempTrapUECECHWLossOfRedundAndPerfBindings 4 }

ibmSystempTrapUECECHWLossOfRedundAndPerfDescription OBJECT-TYPE
   SYNTAX         SnmpAdminString
   ACCESS         read-only
   STATUS         mandatory
   DESCRIPTION    "The Event text of the trap"
-- REFERENCE      "POWER_UECECHWLossOfRedundAndPerfEventIndication.Description"
::= { ibmSystempTrapUECECHWLossOfRedundAndPerfBindings 5 }

ibmSystempTrapUECECHWLossOfRedundAndPerfTimeStamp OBJECT-TYPE
   SYNTAX         Datetime
   ACCESS         read-only
   STATUS         mandatory
   DESCRIPTION    "The time that the trap occurred"
-- REFERENCE      "POWER_UECECHWLossOfRedundAndPerfEventIndication.TimeStamp"
::= { ibmSystempTrapUECECHWLossOfRedundAndPerfBindings 6 }


ibmSystempTrapUECECHWLossOfFunction TRAP-TYPE
   ENTERPRISE     ibmSystemMIB
   VARIABLES    {
      ibmSystempTrapUECECHWLossOfFunctionProviderName,
      ibmSystempTrapUECECHWLossOfFunctionEventID,
      ibmSystempTrapUECECHWLossOfFunctionAME,
      ibmSystempTrapUECECHWLossOfFunctionSeverity,
      ibmSystempTrapUECECHWLossOfFunctionDescription,
      ibmSystempTrapUECECHWLossOfFunctionTimeStamp
   }
   DESCRIPTION    "A System p event has occurred"
-- REFERENCE      "POWER_UECECHWLossOfFunctionEventIndication"
::= 454

ibmSystempTrapUECECHWLossOfFunctionBindings OBJECT IDENTIFIER ::= { ibmSystemTrap 454 }

ibmSystempTrapUECECHWLossOfFunctionProviderName OBJECT-TYPE
   SYNTAX         String
   ACCESS         read-only
   STATUS         mandatory
   DESCRIPTION    "The name of the CIM Provider that monitors this device"
-- REFERENCE      "POWER_UECECHWLossOfFunctionEventIndication.ProviderName"
::= { ibmSystempTrapUECECHWLossOfFunctionBindings 1 }

ibmSystempTrapUECECHWLossOfFunctionEventID OBJECT-TYPE
   SYNTAX         String
   ACCESS         read-only
   STATUS         mandatory
   DESCRIPTION    "A unique EventID that identifies this trap" 
-- REFERENCE      "POWER_UECECHWLossOfFunctionEventIndication.EventID"
::= { ibmSystempTrapUECECHWLossOfFunctionBindings 2 }

ibmSystempTrapUECECHWLossOfFunctionAME OBJECT-TYPE
   SYNTAX         String
   ACCESS         read-only
   STATUS         mandatory
   DESCRIPTION    "A unique string that identifies the monitored device"
-- REFERENCE      "POWER_UECECHWLossOfFunctionEventIndication.AlertingManagedElement"
::= { ibmSystempTrapUECECHWLossOfFunctionBindings 3 }

ibmSystempTrapUECECHWLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UECECHWLossOfFunctionEventIndication.Severity"
::= { ibmSystempTrapUECECHWLossOfFunctionBindings 4 }

ibmSystempTrapUECECHWLossOfFunctionDescription OBJECT-TYPE
   SYNTAX         SnmpAdminString
   ACCESS         read-only
   STATUS         mandatory
   DESCRIPTION    "The Event text of the trap"
-- REFERENCE      "POWER_UECECHWLossOfFunctionEventIndication.Description"
::= { ibmSystempTrapUECECHWLossOfFunctionBindings 5 }

ibmSystempTrapUECECHWLossOfFunctionTimeStamp OBJECT-TYPE
   SYNTAX         Datetime
   ACCESS         read-only
   STATUS         mandatory
   DESCRIPTION    "The time that the trap occurred"
-- REFERENCE      "POWER_UECECHWLossOfFunctionEventIndication.TimeStamp"
::= { ibmSystempTrapUECECHWLossOfFunctionBindings 6 }


ibmSystempTrapUECECHWUnrecoverableError TRAP-TYPE
   ENTERPRISE     ibmSystemMIB
   VARIABLES    {
      ibmSystempTrapUECECHWUnrecoverableErrorProviderName,
      ibmSystempTrapUECECHWUnrecoverableErrorEventID,
      ibmSystempTrapUECECHWUnrecoverableErrorAME,
      ibmSystempTrapUECECHWUnrecoverableErrorSeverity,
      ibmSystempTrapUECECHWUnrecoverableErrorDescription,
      ibmSystempTrapUECECHWUnrecoverableErrorTimeStamp
   }
   DESCRIPTION    "A System p event has occurred"
-- REFERENCE      "POWER_UECECHWUnrecoverableErrorEventIndication"
::= 455

ibmSystempTrapUECECHWUnrecoverableErrorBindings OBJECT IDENTIFIER ::= { ibmSystemTrap 455 }

ibmSystempTrapUECECHWUnrecoverableErrorProviderName OBJECT-TYPE
   SYNTAX         String
   ACCESS         read-only
   STATUS         mandatory
   DESCRIPTION    "The name of the CIM Provider that monitors this device"
-- REFERENCE      "POWER_UECECHWUnrecoverableErrorEventIndication.ProviderName"
::= { ibmSystempTrapUECECHWUnrecoverableErrorBindings 1 }

ibmSystempTrapUECECHWUnrecoverableErrorEventID OBJECT-TYPE
   SYNTAX         String
   ACCESS         read-only
   STATUS         mandatory
   DESCRIPTION    "A unique EventID that identifies this trap" 
-- REFERENCE      "POWER_UECECHWUnrecoverableErrorEventIndication.EventID"
::= { ibmSystempTrapUECECHWUnrecoverableErrorBindings 2 }

ibmSystempTrapUECECHWUnrecoverableErrorAME OBJECT-TYPE
   SYNTAX         String
   ACCESS         read-only
   STATUS         mandatory
   DESCRIPTION    "A unique string that identifies the monitored device"
-- REFERENCE      "POWER_UECECHWUnrecoverableErrorEventIndication.AlertingManagedElement"
::= { ibmSystempTrapUECECHWUnrecoverableErrorBindings 3 }

ibmSystempTrapUECECHWUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UECECHWUnrecoverableErrorEventIndication.Severity"
::= { ibmSystempTrapUECECHWUnrecoverableErrorBindings 4 }

ibmSystempTrapUECECHWUnrecoverableErrorDescription OBJECT-TYPE
   SYNTAX         SnmpAdminString
   ACCESS         read-only
   STATUS         mandatory
   DESCRIPTION    "The Event text of the trap"
-- REFERENCE      "POWER_UECECHWUnrecoverableErrorEventIndication.Description"
::= { ibmSystempTrapUECECHWUnrecoverableErrorBindings 5 }

ibmSystempTrapUECECHWUnrecoverableErrorTimeStamp OBJECT-TYPE
   SYNTAX         Datetime
   ACCESS         read-only
   STATUS         mandatory
   DESCRIPTION    "The time that the trap occurred"
-- REFERENCE      "POWER_UECECHWUnrecoverableErrorEventIndication.TimeStamp"
::= { ibmSystempTrapUECECHWUnrecoverableErrorBindings 6 }


ibmSystempTrapDTPowerCoolingDiagnostics TRAP-TYPE
   ENTERPRISE     ibmSystemMIB
   VARIABLES    {
      ibmSystempTrapDTPowerCoolingDiagnosticsProviderName,
      ibmSystempTrapDTPowerCoolingDiagnosticsEventID,
      ibmSystempTrapDTPowerCoolingDiagnosticsAME,
      ibmSystempTrapDTPowerCoolingDiagnosticsSeverity,
      ibmSystempTrapDTPowerCoolingDiagnosticsDescription,
      ibmSystempTrapDTPowerCoolingDiagnosticsTimeStamp
   }
   DESCRIPTION    "A System p event has occurred"
-- REFERENCE      "POWER_DTPowerCoolingDiagnosticsEventIndication"
::= 456

ibmSystempTrapDTPowerCoolingDiagnosticsBindings OBJECT IDENTIFIER ::= { ibmSystemTrap 456 }

ibmSystempTrapDTPowerCoolingDiagnosticsProviderName OBJECT-TYPE
   SYNTAX         String
   ACCESS         read-only
   STATUS         mandatory
   DESCRIPTION    "The name of the CIM Provider that monitors this device"
-- REFERENCE      "POWER_DTPowerCoolingDiagnosticsEventIndication.ProviderName"
::= { ibmSystempTrapDTPowerCoolingDiagnosticsBindings 1 }

ibmSystempTrapDTPowerCoolingDiagnosticsEventID OBJECT-TYPE
   SYNTAX         String
   ACCESS         read-only
   STATUS         mandatory
   DESCRIPTION    "A unique EventID that identifies this trap" 
-- REFERENCE      "POWER_DTPowerCoolingDiagnosticsEventIndication.EventID"
::= { ibmSystempTrapDTPowerCoolingDiagnosticsBindings 2 }

ibmSystempTrapDTPowerCoolingDiagnosticsAME OBJECT-TYPE
   SYNTAX         String
   ACCESS         read-only
   STATUS         mandatory
   DESCRIPTION    "A unique string that identifies the monitored device"
-- REFERENCE      "POWER_DTPowerCoolingDiagnosticsEventIndication.AlertingManagedElement"
::= { ibmSystempTrapDTPowerCoolingDiagnosticsBindings 3 }

ibmSystempTrapDTPowerCoolingDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTPowerCoolingDiagnosticsEventIndication.Severity"
::= { ibmSystempTrapDTPowerCoolingDiagnosticsBindings 4 }

ibmSystempTrapDTPowerCoolingDiagnosticsDescription OBJECT-TYPE
   SYNTAX         SnmpAdminString
   ACCESS         read-only
   STATUS         mandatory
   DESCRIPTION    "The Event text of the trap"
-- REFERENCE      "POWER_DTPowerCoolingDiagnosticsEventIndication.Description"
::= { ibmSystempTrapDTPowerCoolingDiagnosticsBindings 5 }

ibmSystempTrapDTPowerCoolingDiagnosticsTimeStamp OBJECT-TYPE
   SYNTAX         Datetime
   ACCESS         read-only
   STATUS         mandatory
   DESCRIPTION    "The time that the trap occurred"
-- REFERENCE      "POWER_DTPowerCoolingDiagnosticsEventIndication.TimeStamp"
::= { ibmSystempTrapDTPowerCoolingDiagnosticsBindings 6 }


ibmSystempTrapPFPowerCoolingDegradPerf TRAP-TYPE
   ENTERPRISE     ibmSystemMIB
   VARIABLES    {
      ibmSystempTrapPFPowerCoolingDegradPerfProviderName,
      ibmSystempTrapPFPowerCoolingDegradPerfEventID,
      ibmSystempTrapPFPowerCoolingDegradPerfAME,
      ibmSystempTrapPFPowerCoolingDegradPerfSeverity,
      ibmSystempTrapPFPowerCoolingDegradPerfDescription,
      ibmSystempTrapPFPowerCoolingDegradPerfTimeStamp
   }
   DESCRIPTION    "A System p event has occurred"
-- REFERENCE      "POWER_PFPowerCoolingDegradPerfEventIndication"
::= 457

ibmSystempTrapPFPowerCoolingDegradPerfBindings OBJECT IDENTIFIER ::= { ibmSystemTrap 457 }

ibmSystempTrapPFPowerCoolingDegradPerfProviderName OBJECT-TYPE
   SYNTAX         String
   ACCESS         read-only
   STATUS         mandatory
   DESCRIPTION    "The name of the CIM Provider that monitors this device"
-- REFERENCE      "POWER_PFPowerCoolingDegradPerfEventIndication.ProviderName"
::= { ibmSystempTrapPFPowerCoolingDegradPerfBindings 1 }

ibmSystempTrapPFPowerCoolingDegradPerfEventID OBJECT-TYPE
   SYNTAX         String
   ACCESS         read-only
   STATUS         mandatory
   DESCRIPTION    "A unique EventID that identifies this trap" 
-- REFERENCE      "POWER_PFPowerCoolingDegradPerfEventIndication.EventID"
::= { ibmSystempTrapPFPowerCoolingDegradPerfBindings 2 }

ibmSystempTrapPFPowerCoolingDegradPerfAME OBJECT-TYPE
   SYNTAX         String
   ACCESS         read-only
   STATUS         mandatory
   DESCRIPTION    "A unique string that identifies the monitored device"
-- REFERENCE      "POWER_PFPowerCoolingDegradPerfEventIndication.AlertingManagedElement"
::= { ibmSystempTrapPFPowerCoolingDegradPerfBindings 3 }

ibmSystempTrapPFPowerCoolingDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerCoolingDegradPerfEventIndication.Severity"
::= { ibmSystempTrapPFPowerCoolingDegradPerfBindings 4 }

ibmSystempTrapPFPowerCoolingDegradPerfDescription OBJECT-TYPE
   SYNTAX         SnmpAdminString
   ACCESS         read-only
   STATUS         mandatory
   DESCRIPTION    "The Event text of the trap"
-- REFERENCE      "POWER_PFPowerCoolingDegradPerfEventIndication.Description"
::= { ibmSystempTrapPFPowerCoolingDegradPerfBindings 5 }

ibmSystempTrapPFPowerCoolingDegradPerfTimeStamp OBJECT-TYPE
   SYNTAX         Datetime
   ACCESS         read-only
   STATUS         mandatory
   DESCRIPTION    "The time that the trap occurred"
-- REFERENCE      "POWER_PFPowerCoolingDegradPerfEventIndication.TimeStamp"
::= { ibmSystempTrapPFPowerCoolingDegradPerfBindings 6 }


ibmSystempTrapPFPowerCoolingCorrectAftIPL TRAP-TYPE
   ENTERPRISE     ibmSystemMIB
   VARIABLES    {
      ibmSystempTrapPFPowerCoolingCorrectAftIPLProviderName,
      ibmSystempTrapPFPowerCoolingCorrectAftIPLEventID,
      ibmSystempTrapPFPowerCoolingCorrectAftIPLAME,
      ibmSystempTrapPFPowerCoolingCorrectAftIPLSeverity,
      ibmSystempTrapPFPowerCoolingCorrectAftIPLDescription,
      ibmSystempTrapPFPowerCoolingCorrectAftIPLTimeStamp
   }
   DESCRIPTION    "A System p event has occurred"
-- REFERENCE      "POWER_PFPowerCoolingCorrectAftIPLEventIndication"
::= 458

ibmSystempTrapPFPowerCoolingCorrectAftIPLBindings OBJECT IDENTIFIER ::= { ibmSystemTrap 458 }

ibmSystempTrapPFPowerCoolingCorrectAftIPLProviderName OBJECT-TYPE
   SYNTAX         String
   ACCESS         read-only
   STATUS         mandatory
   DESCRIPTION    "The name of the CIM Provider that monitors this device"
-- REFERENCE      "POWER_PFPowerCoolingCorrectAftIPLEventIndication.ProviderName"
::= { ibmSystempTrapPFPowerCoolingCorrectAftIPLBindings 1 }

ibmSystempTrapPFPowerCoolingCorrectAftIPLEventID OBJECT-TYPE
   SYNTAX         String
   ACCESS         read-only
   STATUS         mandatory
   DESCRIPTION    "A unique EventID that identifies this trap" 
-- REFERENCE      "POWER_PFPowerCoolingCorrectAftIPLEventIndication.EventID"
::= { ibmSystempTrapPFPowerCoolingCorrectAftIPLBindings 2 }

ibmSystempTrapPFPowerCoolingCorrectAftIPLAME OBJECT-TYPE
   SYNTAX         String
   ACCESS         read-only
   STATUS         mandatory
   DESCRIPTION    "A unique string that identifies the monitored device"
-- REFERENCE      "POWER_PFPowerCoolingCorrectAftIPLEventIndication.AlertingManagedElement"
::= { ibmSystempTrapPFPowerCoolingCorrectAftIPLBindings 3 }

ibmSystempTrapPFPowerCoolingCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerCoolingCorrectAftIPLEventIndication.Severity"
::= { ibmSystempTrapPFPowerCoolingCorrectAftIPLBindings 4 }

ibmSystempTrapPFPowerCoolingCorrectAftIPLDescription OBJECT-TYPE
   SYNTAX         SnmpAdminString
   ACCESS         read-only
   STATUS         mandatory
   DESCRIPTION    "The Event text of the trap"
-- REFERENCE      "POWER_PFPowerCoolingCorrectAftIPLEventIndication.Description"
::= { ibmSystempTrapPFPowerCoolingCorrectAftIPLBindings 5 }

ibmSystempTrapPFPowerCoolingCorrectAftIPLTimeStamp OBJECT-TYPE
   SYNTAX         Datetime
   ACCESS         read-only
   STATUS         mandatory
   DESCRIPTION    "The time that the trap occurred"
-- REFERENCE      "POWER_PFPowerCoolingCorrectAftIPLEventIndication.TimeStamp"
::= { ibmSystempTrapPFPowerCoolingCorrectAftIPLBindings 6 }


ibmSystempTrapPFPowerCoolingCorrectAftIPLPerf TRAP-TYPE
   ENTERPRISE     ibmSystemMIB
   VARIABLES    {
      ibmSystempTrapPFPowerCoolingCorrectAftIPLPerfProviderName,
      ibmSystempTrapPFPowerCoolingCorrectAftIPLPerfEventID,
      ibmSystempTrapPFPowerCoolingCorrectAftIPLPerfAME,
      ibmSystempTrapPFPowerCoolingCorrectAftIPLPerfSeverity,
      ibmSystempTrapPFPowerCoolingCorrectAftIPLPerfDescription,
      ibmSystempTrapPFPowerCoolingCorrectAftIPLPerfTimeStamp
   }
   DESCRIPTION    "A System p event has occurred"
-- REFERENCE      "POWER_PFPowerCoolingCorrectAftIPLPerfEventIndication"
::= 459

ibmSystempTrapPFPowerCoolingCorrectAftIPLPerfBindings OBJECT IDENTIFIER ::= { ibmSystemTrap 459 }

ibmSystempTrapPFPowerCoolingCorrectAftIPLPerfProviderName OBJECT-TYPE
   SYNTAX         String
   ACCESS         read-only
   STATUS         mandatory
   DESCRIPTION    "The name of the CIM Provider that monitors this device"
-- REFERENCE      "POWER_PFPowerCoolingCorrectAftIPLPerfEventIndication.ProviderName"
::= { ibmSystempTrapPFPowerCoolingCorrectAftIPLPerfBindings 1 }

ibmSystempTrapPFPowerCoolingCorrectAftIPLPerfEventID OBJECT-TYPE
   SYNTAX         String
   ACCESS         read-only
   STATUS         mandatory
   DESCRIPTION    "A unique EventID that identifies this trap" 
-- REFERENCE      "POWER_PFPowerCoolingCorrectAftIPLPerfEventIndication.EventID"
::= { ibmSystempTrapPFPowerCoolingCorrectAftIPLPerfBindings 2 }

ibmSystempTrapPFPowerCoolingCorrectAftIPLPerfAME OBJECT-TYPE
   SYNTAX         String
   ACCESS         read-only
   STATUS         mandatory
   DESCRIPTION    "A unique string that identifies the monitored device"
-- REFERENCE      "POWER_PFPowerCoolingCorrectAftIPLPerfEventIndication.AlertingManagedElement"
::= { ibmSystempTrapPFPowerCoolingCorrectAftIPLPerfBindings 3 }

ibmSystempTrapPFPowerCoolingCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerCoolingCorrectAftIPLPerfEventIndication.Severity"
::= { ibmSystempTrapPFPowerCoolingCorrectAftIPLPerfBindings 4 }

ibmSystempTrapPFPowerCoolingCorrectAftIPLPerfDescription OBJECT-TYPE
   SYNTAX         SnmpAdminString
   ACCESS         read-only
   STATUS         mandatory
   DESCRIPTION    "The Event text of the trap"
-- REFERENCE      "POWER_PFPowerCoolingCorrectAftIPLPerfEventIndication.Description"
::= { ibmSystempTrapPFPowerCoolingCorrectAftIPLPerfBindings 5 }

ibmSystempTrapPFPowerCoolingCorrectAftIPLPerfTimeStamp OBJECT-TYPE
   SYNTAX         Datetime
   ACCESS         read-only
   STATUS         mandatory
   DESCRIPTION    "The time that the trap occurred"
-- REFERENCE      "POWER_PFPowerCoolingCorrectAftIPLPerfEventIndication.TimeStamp"
::= { ibmSystempTrapPFPowerCoolingCorrectAftIPLPerfBindings 6 }


ibmSystempTrapPFPowerCoolingLossOfRedundancy TRAP-TYPE
   ENTERPRISE     ibmSystemMIB
   VARIABLES    {
      ibmSystempTrapPFPowerCoolingLossOfRedundancyProviderName,
      ibmSystempTrapPFPowerCoolingLossOfRedundancyEventID,
      ibmSystempTrapPFPowerCoolingLossOfRedundancyAME,
      ibmSystempTrapPFPowerCoolingLossOfRedundancySeverity,
      ibmSystempTrapPFPowerCoolingLossOfRedundancyDescription,
      ibmSystempTrapPFPowerCoolingLossOfRedundancyTimeStamp
   }
   DESCRIPTION    "A System p event has occurred"
-- REFERENCE      "POWER_PFPowerCoolingLossOfRedundancyEventIndication"
::= 460

ibmSystempTrapPFPowerCoolingLossOfRedundancyBindings OBJECT IDENTIFIER ::= { ibmSystemTrap 460 }

ibmSystempTrapPFPowerCoolingLossOfRedundancyProviderName OBJECT-TYPE
   SYNTAX         String
   ACCESS         read-only
   STATUS         mandatory
   DESCRIPTION    "The name of the CIM Provider that monitors this device"
-- REFERENCE      "POWER_PFPowerCoolingLossOfRedundancyEventIndication.ProviderName"
::= { ibmSystempTrapPFPowerCoolingLossOfRedundancyBindings 1 }

ibmSystempTrapPFPowerCoolingLossOfRedundancyEventID OBJECT-TYPE
   SYNTAX         String
   ACCESS         read-only
   STATUS         mandatory
   DESCRIPTION    "A unique EventID that identifies this trap" 
-- REFERENCE      "POWER_PFPowerCoolingLossOfRedundancyEventIndication.EventID"
::= { ibmSystempTrapPFPowerCoolingLossOfRedundancyBindings 2 }

ibmSystempTrapPFPowerCoolingLossOfRedundancyAME OBJECT-TYPE
   SYNTAX         String
   ACCESS         read-only
   STATUS         mandatory
   DESCRIPTION    "A unique string that identifies the monitored device"
-- REFERENCE      "POWER_PFPowerCoolingLossOfRedundancyEventIndication.AlertingManagedElement"
::= { ibmSystempTrapPFPowerCoolingLossOfRedundancyBindings 3 }

ibmSystempTrapPFPowerCoolingLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerCoolingLossOfRedundancyEventIndication.Severity"
::= { ibmSystempTrapPFPowerCoolingLossOfRedundancyBindings 4 }

ibmSystempTrapPFPowerCoolingLossOfRedundancyDescription OBJECT-TYPE
   SYNTAX         SnmpAdminString
   ACCESS         read-only
   STATUS         mandatory
   DESCRIPTION    "The Event text of the trap"
-- REFERENCE      "POWER_PFPowerCoolingLossOfRedundancyEventIndication.Description"
::= { ibmSystempTrapPFPowerCoolingLossOfRedundancyBindings 5 }

ibmSystempTrapPFPowerCoolingLossOfRedundancyTimeStamp OBJECT-TYPE
   SYNTAX         Datetime
   ACCESS         read-only
   STATUS         mandatory
   DESCRIPTION    "The time that the trap occurred"
-- REFERENCE      "POWER_PFPowerCoolingLossOfRedundancyEventIndication.TimeStamp"
::= { ibmSystempTrapPFPowerCoolingLossOfRedundancyBindings 6 }


ibmSystempTrapPFPowerCoolingPredictiveError TRAP-TYPE
   ENTERPRISE     ibmSystemMIB
   VARIABLES    {
      ibmSystempTrapPFPowerCoolingPredictiveErrorProviderName,
      ibmSystempTrapPFPowerCoolingPredictiveErrorEventID,
      ibmSystempTrapPFPowerCoolingPredictiveErrorAME,
      ibmSystempTrapPFPowerCoolingPredictiveErrorSeverity,
      ibmSystempTrapPFPowerCoolingPredictiveErrorDescription,
      ibmSystempTrapPFPowerCoolingPredictiveErrorTimeStamp
   }
   DESCRIPTION    "A System p event has occurred"
-- REFERENCE      "POWER_PFPowerCoolingPredictiveErrorEventIndication"
::= 461

ibmSystempTrapPFPowerCoolingPredictiveErrorBindings OBJECT IDENTIFIER ::= { ibmSystemTrap 461 }

ibmSystempTrapPFPowerCoolingPredictiveErrorProviderName OBJECT-TYPE
   SYNTAX         String
   ACCESS         read-only
   STATUS         mandatory
   DESCRIPTION    "The name of the CIM Provider that monitors this device"
-- REFERENCE      "POWER_PFPowerCoolingPredictiveErrorEventIndication.ProviderName"
::= { ibmSystempTrapPFPowerCoolingPredictiveErrorBindings 1 }

ibmSystempTrapPFPowerCoolingPredictiveErrorEventID OBJECT-TYPE
   SYNTAX         String
   ACCESS         read-only
   STATUS         mandatory
   DESCRIPTION    "A unique EventID that identifies this trap" 
-- REFERENCE      "POWER_PFPowerCoolingPredictiveErrorEventIndication.EventID"
::= { ibmSystempTrapPFPowerCoolingPredictiveErrorBindings 2 }

ibmSystempTrapPFPowerCoolingPredictiveErrorAME OBJECT-TYPE
   SYNTAX         String
   ACCESS         read-only
   STATUS         mandatory
   DESCRIPTION    "A unique string that identifies the monitored device"
-- REFERENCE      "POWER_PFPowerCoolingPredictiveErrorEventIndication.AlertingManagedElement"
::= { ibmSystempTrapPFPowerCoolingPredictiveErrorBindings 3 }

ibmSystempTrapPFPowerCoolingPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerCoolingPredictiveErrorEventIndication.Severity"
::= { ibmSystempTrapPFPowerCoolingPredictiveErrorBindings 4 }

ibmSystempTrapPFPowerCoolingPredictiveErrorDescription OBJECT-TYPE
   SYNTAX         SnmpAdminString
   ACCESS         read-only
   STATUS         mandatory
   DESCRIPTION    "The Event text of the trap"
-- REFERENCE      "POWER_PFPowerCoolingPredictiveErrorEventIndication.Description"
::= { ibmSystempTrapPFPowerCoolingPredictiveErrorBindings 5 }

ibmSystempTrapPFPowerCoolingPredictiveErrorTimeStamp OBJECT-TYPE
   SYNTAX         Datetime
   ACCESS         read-only
   STATUS         mandatory
   DESCRIPTION    "The time that the trap occurred"
-- REFERENCE      "POWER_PFPowerCoolingPredictiveErrorEventIndication.TimeStamp"
::= { ibmSystempTrapPFPowerCoolingPredictiveErrorBindings 6 }


ibmSystempTrapUEPowerCoolingDegradPerf TRAP-TYPE
   ENTERPRISE     ibmSystemMIB
   VARIABLES    {
      ibmSystempTrapUEPowerCoolingDegradPerfProviderName,
      ibmSystempTrapUEPowerCoolingDegradPerfEventID,
      ibmSystempTrapUEPowerCoolingDegradPerfAME,
      ibmSystempTrapUEPowerCoolingDegradPerfSeverity,
      ibmSystempTrapUEPowerCoolingDegradPerfDescription,
      ibmSystempTrapUEPowerCoolingDegradPerfTimeStamp
   }
   DESCRIPTION    "A System p event has occurred"
-- REFERENCE      "POWER_UEPowerCoolingDegradPerfEventIndication"
::= 462

ibmSystempTrapUEPowerCoolingDegradPerfBindings OBJECT IDENTIFIER ::= { ibmSystemTrap 462 }

ibmSystempTrapUEPowerCoolingDegradPerfProviderName OBJECT-TYPE
   SYNTAX         String
   ACCESS         read-only
   STATUS         mandatory
   DESCRIPTION    "The name of the CIM Provider that monitors this device"
-- REFERENCE      "POWER_UEPowerCoolingDegradPerfEventIndication.ProviderName"
::= { ibmSystempTrapUEPowerCoolingDegradPerfBindings 1 }

ibmSystempTrapUEPowerCoolingDegradPerfEventID OBJECT-TYPE
   SYNTAX         String
   ACCESS         read-only
   STATUS         mandatory
   DESCRIPTION    "A unique EventID that identifies this trap" 
-- REFERENCE      "POWER_UEPowerCoolingDegradPerfEventIndication.EventID"
::= { ibmSystempTrapUEPowerCoolingDegradPerfBindings 2 }

ibmSystempTrapUEPowerCoolingDegradPerfAME OBJECT-TYPE
   SYNTAX         String
   ACCESS         read-only
   STATUS         mandatory
   DESCRIPTION    "A unique string that identifies the monitored device"
-- REFERENCE      "POWER_UEPowerCoolingDegradPerfEventIndication.AlertingManagedElement"
::= { ibmSystempTrapUEPowerCoolingDegradPerfBindings 3 }

ibmSystempTrapUEPowerCoolingDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerCoolingDegradPerfEventIndication.Severity"
::= { ibmSystempTrapUEPowerCoolingDegradPerfBindings 4 }

ibmSystempTrapUEPowerCoolingDegradPerfDescription OBJECT-TYPE
   SYNTAX         SnmpAdminString
   ACCESS         read-only
   STATUS         mandatory
   DESCRIPTION    "The Event text of the trap"
-- REFERENCE      "POWER_UEPowerCoolingDegradPerfEventIndication.Description"
::= { ibmSystempTrapUEPowerCoolingDegradPerfBindings 5 }

ibmSystempTrapUEPowerCoolingDegradPerfTimeStamp OBJECT-TYPE
   SYNTAX         Datetime
   ACCESS         read-only
   STATUS         mandatory
   DESCRIPTION    "The time that the trap occurred"
-- REFERENCE      "POWER_UEPowerCoolingDegradPerfEventIndication.TimeStamp"
::= { ibmSystempTrapUEPowerCoolingDegradPerfBindings 6 }


ibmSystempTrapUEPowerCoolingLossOfRedundancy TRAP-TYPE
   ENTERPRISE     ibmSystemMIB
   VARIABLES    {
      ibmSystempTrapUEPowerCoolingLossOfRedundancyProviderName,
      ibmSystempTrapUEPowerCoolingLossOfRedundancyEventID,
      ibmSystempTrapUEPowerCoolingLossOfRedundancyAME,
      ibmSystempTrapUEPowerCoolingLossOfRedundancySeverity,
      ibmSystempTrapUEPowerCoolingLossOfRedundancyDescription,
      ibmSystempTrapUEPowerCoolingLossOfRedundancyTimeStamp
   }
   DESCRIPTION    "A System p event has occurred"
-- REFERENCE      "POWER_UEPowerCoolingLossOfRedundancyEventIndication"
::= 463

ibmSystempTrapUEPowerCoolingLossOfRedundancyBindings OBJECT IDENTIFIER ::= { ibmSystemTrap 463 }

ibmSystempTrapUEPowerCoolingLossOfRedundancyProviderName OBJECT-TYPE
   SYNTAX         String
   ACCESS         read-only
   STATUS         mandatory
   DESCRIPTION    "The name of the CIM Provider that monitors this device"
-- REFERENCE      "POWER_UEPowerCoolingLossOfRedundancyEventIndication.ProviderName"
::= { ibmSystempTrapUEPowerCoolingLossOfRedundancyBindings 1 }

ibmSystempTrapUEPowerCoolingLossOfRedundancyEventID OBJECT-TYPE
   SYNTAX         String
   ACCESS         read-only
   STATUS         mandatory
   DESCRIPTION    "A unique EventID that identifies this trap" 
-- REFERENCE      "POWER_UEPowerCoolingLossOfRedundancyEventIndication.EventID"
::= { ibmSystempTrapUEPowerCoolingLossOfRedundancyBindings 2 }

ibmSystempTrapUEPowerCoolingLossOfRedundancyAME OBJECT-TYPE
   SYNTAX         String
   ACCESS         read-only
   STATUS         mandatory
   DESCRIPTION    "A unique string that identifies the monitored device"
-- REFERENCE      "POWER_UEPowerCoolingLossOfRedundancyEventIndication.AlertingManagedElement"
::= { ibmSystempTrapUEPowerCoolingLossOfRedundancyBindings 3 }

ibmSystempTrapUEPowerCoolingLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerCoolingLossOfRedundancyEventIndication.Severity"
::= { ibmSystempTrapUEPowerCoolingLossOfRedundancyBindings 4 }

ibmSystempTrapUEPowerCoolingLossOfRedundancyDescription OBJECT-TYPE
   SYNTAX         SnmpAdminString
   ACCESS         read-only
   STATUS         mandatory
   DESCRIPTION    "The Event text of the trap"
-- REFERENCE      "POWER_UEPowerCoolingLossOfRedundancyEventIndication.Description"
::= { ibmSystempTrapUEPowerCoolingLossOfRedundancyBindings 5 }

ibmSystempTrapUEPowerCoolingLossOfRedundancyTimeStamp OBJECT-TYPE
   SYNTAX         Datetime
   ACCESS         read-only
   STATUS         mandatory
   DESCRIPTION    "The time that the trap occurred"
-- REFERENCE      "POWER_UEPowerCoolingLossOfRedundancyEventIndication.TimeStamp"
::= { ibmSystempTrapUEPowerCoolingLossOfRedundancyBindings 6 }


ibmSystempTrapUEPowerCoolingLossOfRedundAndPerf TRAP-TYPE
   ENTERPRISE     ibmSystemMIB
   VARIABLES    {
      ibmSystempTrapUEPowerCoolingLossOfRedundAndPerfProviderName,
      ibmSystempTrapUEPowerCoolingLossOfRedundAndPerfEventID,
      ibmSystempTrapUEPowerCoolingLossOfRedundAndPerfAME,
      ibmSystempTrapUEPowerCoolingLossOfRedundAndPerfSeverity,
      ibmSystempTrapUEPowerCoolingLossOfRedundAndPerfDescription,
      ibmSystempTrapUEPowerCoolingLossOfRedundAndPerfTimeStamp
   }
   DESCRIPTION    "A System p event has occurred"
-- REFERENCE      "POWER_UEPowerCoolingLossOfRedundAndPerfEventIndication"
::= 464

ibmSystempTrapUEPowerCoolingLossOfRedundAndPerfBindings OBJECT IDENTIFIER ::= { ibmSystemTrap 464 }

ibmSystempTrapUEPowerCoolingLossOfRedundAndPerfProviderName OBJECT-TYPE
   SYNTAX         String
   ACCESS         read-only
   STATUS         mandatory
   DESCRIPTION    "The name of the CIM Provider that monitors this device"
-- REFERENCE      "POWER_UEPowerCoolingLossOfRedundAndPerfEventIndication.ProviderName"
::= { ibmSystempTrapUEPowerCoolingLossOfRedundAndPerfBindings 1 }

ibmSystempTrapUEPowerCoolingLossOfRedundAndPerfEventID OBJECT-TYPE
   SYNTAX         String
   ACCESS         read-only
   STATUS         mandatory
   DESCRIPTION    "A unique EventID that identifies this trap" 
-- REFERENCE      "POWER_UEPowerCoolingLossOfRedundAndPerfEventIndication.EventID"
::= { ibmSystempTrapUEPowerCoolingLossOfRedundAndPerfBindings 2 }

ibmSystempTrapUEPowerCoolingLossOfRedundAndPerfAME OBJECT-TYPE
   SYNTAX         String
   ACCESS         read-only
   STATUS         mandatory
   DESCRIPTION    "A unique string that identifies the monitored device"
-- REFERENCE      "POWER_UEPowerCoolingLossOfRedundAndPerfEventIndication.AlertingManagedElement"
::= { ibmSystempTrapUEPowerCoolingLossOfRedundAndPerfBindings 3 }

ibmSystempTrapUEPowerCoolingLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerCoolingLossOfRedundAndPerfEventIndication.Severity"
::= { ibmSystempTrapUEPowerCoolingLossOfRedundAndPerfBindings 4 }

ibmSystempTrapUEPowerCoolingLossOfRedundAndPerfDescription OBJECT-TYPE
   SYNTAX         SnmpAdminString
   ACCESS         read-only
   STATUS         mandatory
   DESCRIPTION    "The Event text of the trap"
-- REFERENCE      "POWER_UEPowerCoolingLossOfRedundAndPerfEventIndication.Description"
::= { ibmSystempTrapUEPowerCoolingLossOfRedundAndPerfBindings 5 }

ibmSystempTrapUEPowerCoolingLossOfRedundAndPerfTimeStamp OBJECT-TYPE
   SYNTAX         Datetime
   ACCESS         read-only
   STATUS         mandatory
   DESCRIPTION    "The time that the trap occurred"
-- REFERENCE      "POWER_UEPowerCoolingLossOfRedundAndPerfEventIndication.TimeStamp"
::= { ibmSystempTrapUEPowerCoolingLossOfRedundAndPerfBindings 6 }


ibmSystempTrapUEPowerCoolingLossOfFunction TRAP-TYPE
   ENTERPRISE     ibmSystemMIB
   VARIABLES    {
      ibmSystempTrapUEPowerCoolingLossOfFunctionProviderName,
      ibmSystempTrapUEPowerCoolingLossOfFunctionEventID,
      ibmSystempTrapUEPowerCoolingLossOfFunctionAME,
      ibmSystempTrapUEPowerCoolingLossOfFunctionSeverity,
      ibmSystempTrapUEPowerCoolingLossOfFunctionDescription,
      ibmSystempTrapUEPowerCoolingLossOfFunctionTimeStamp
   }
   DESCRIPTION    "A System p event has occurred"
-- REFERENCE      "POWER_UEPowerCoolingLossOfFunctionEventIndication"
::= 465

ibmSystempTrapUEPowerCoolingLossOfFunctionBindings OBJECT IDENTIFIER ::= { ibmSystemTrap 465 }

ibmSystempTrapUEPowerCoolingLossOfFunctionProviderName OBJECT-TYPE
   SYNTAX         String
   ACCESS         read-only
   STATUS         mandatory
   DESCRIPTION    "The name of the CIM Provider that monitors this device"
-- REFERENCE      "POWER_UEPowerCoolingLossOfFunctionEventIndication.ProviderName"
::= { ibmSystempTrapUEPowerCoolingLossOfFunctionBindings 1 }

ibmSystempTrapUEPowerCoolingLossOfFunctionEventID OBJECT-TYPE
   SYNTAX         String
   ACCESS         read-only
   STATUS         mandatory
   DESCRIPTION    "A unique EventID that identifies this trap" 
-- REFERENCE      "POWER_UEPowerCoolingLossOfFunctionEventIndication.EventID"
::= { ibmSystempTrapUEPowerCoolingLossOfFunctionBindings 2 }

ibmSystempTrapUEPowerCoolingLossOfFunctionAME OBJECT-TYPE
   SYNTAX         String
   ACCESS         read-only
   STATUS         mandatory
   DESCRIPTION    "A unique string that identifies the monitored device"
-- REFERENCE      "POWER_UEPowerCoolingLossOfFunctionEventIndication.AlertingManagedElement"
::= { ibmSystempTrapUEPowerCoolingLossOfFunctionBindings 3 }

ibmSystempTrapUEPowerCoolingLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerCoolingLossOfFunctionEventIndication.Severity"
::= { ibmSystempTrapUEPowerCoolingLossOfFunctionBindings 4 }

ibmSystempTrapUEPowerCoolingLossOfFunctionDescription OBJECT-TYPE
   SYNTAX         SnmpAdminString
   ACCESS         read-only
   STATUS         mandatory
   DESCRIPTION    "The Event text of the trap"
-- REFERENCE      "POWER_UEPowerCoolingLossOfFunctionEventIndication.Description"
::= { ibmSystempTrapUEPowerCoolingLossOfFunctionBindings 5 }

ibmSystempTrapUEPowerCoolingLossOfFunctionTimeStamp OBJECT-TYPE
   SYNTAX         Datetime
   ACCESS         read-only
   STATUS         mandatory
   DESCRIPTION    "The time that the trap occurred"
-- REFERENCE      "POWER_UEPowerCoolingLossOfFunctionEventIndication.TimeStamp"
::= { ibmSystempTrapUEPowerCoolingLossOfFunctionBindings 6 }


ibmSystempTrapUEPowerCoolingUnrecoverableError TRAP-TYPE
   ENTERPRISE     ibmSystemMIB
   VARIABLES    {
      ibmSystempTrapUEPowerCoolingUnrecoverableErrorProviderName,
      ibmSystempTrapUEPowerCoolingUnrecoverableErrorEventID,
      ibmSystempTrapUEPowerCoolingUnrecoverableErrorAME,
      ibmSystempTrapUEPowerCoolingUnrecoverableErrorSeverity,
      ibmSystempTrapUEPowerCoolingUnrecoverableErrorDescription,
      ibmSystempTrapUEPowerCoolingUnrecoverableErrorTimeStamp
   }
   DESCRIPTION    "A System p event has occurred"
-- REFERENCE      "POWER_UEPowerCoolingUnrecoverableErrorEventIndication"
::= 466

ibmSystempTrapUEPowerCoolingUnrecoverableErrorBindings OBJECT IDENTIFIER ::= { ibmSystemTrap 466 }

ibmSystempTrapUEPowerCoolingUnrecoverableErrorProviderName OBJECT-TYPE
   SYNTAX         String
   ACCESS         read-only
   STATUS         mandatory
   DESCRIPTION    "The name of the CIM Provider that monitors this device"
-- REFERENCE      "POWER_UEPowerCoolingUnrecoverableErrorEventIndication.ProviderName"
::= { ibmSystempTrapUEPowerCoolingUnrecoverableErrorBindings 1 }

ibmSystempTrapUEPowerCoolingUnrecoverableErrorEventID OBJECT-TYPE
   SYNTAX         String
   ACCESS         read-only
   STATUS         mandatory
   DESCRIPTION    "A unique EventID that identifies this trap" 
-- REFERENCE      "POWER_UEPowerCoolingUnrecoverableErrorEventIndication.EventID"
::= { ibmSystempTrapUEPowerCoolingUnrecoverableErrorBindings 2 }

ibmSystempTrapUEPowerCoolingUnrecoverableErrorAME OBJECT-TYPE
   SYNTAX         String
   ACCESS         read-only
   STATUS         mandatory
   DESCRIPTION    "A unique string that identifies the monitored device"
-- REFERENCE      "POWER_UEPowerCoolingUnrecoverableErrorEventIndication.AlertingManagedElement"
::= { ibmSystempTrapUEPowerCoolingUnrecoverableErrorBindings 3 }

ibmSystempTrapUEPowerCoolingUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerCoolingUnrecoverableErrorEventIndication.Severity"
::= { ibmSystempTrapUEPowerCoolingUnrecoverableErrorBindings 4 }

ibmSystempTrapUEPowerCoolingUnrecoverableErrorDescription OBJECT-TYPE
   SYNTAX         SnmpAdminString
   ACCESS         read-only
   STATUS         mandatory
   DESCRIPTION    "The Event text of the trap"
-- REFERENCE      "POWER_UEPowerCoolingUnrecoverableErrorEventIndication.Description"
::= { ibmSystempTrapUEPowerCoolingUnrecoverableErrorBindings 5 }

ibmSystempTrapUEPowerCoolingUnrecoverableErrorTimeStamp OBJECT-TYPE
   SYNTAX         Datetime
   ACCESS         read-only
   STATUS         mandatory
   DESCRIPTION    "The time that the trap occurred"
-- REFERENCE      "POWER_UEPowerCoolingUnrecoverableErrorEventIndication.TimeStamp"
::= { ibmSystempTrapUEPowerCoolingUnrecoverableErrorBindings 6 }


ibmSystempTrapDTPowerSupplyDiagnostics TRAP-TYPE
   ENTERPRISE     ibmSystemMIB
   VARIABLES    {
      ibmSystempTrapDTPowerSupplyDiagnosticsProviderName,
      ibmSystempTrapDTPowerSupplyDiagnosticsEventID,
      ibmSystempTrapDTPowerSupplyDiagnosticsAME,
      ibmSystempTrapDTPowerSupplyDiagnosticsSeverity,
      ibmSystempTrapDTPowerSupplyDiagnosticsDescription,
      ibmSystempTrapDTPowerSupplyDiagnosticsTimeStamp
   }
   DESCRIPTION    "A System p event has occurred"
-- REFERENCE      "POWER_DTPowerSupplyDiagnosticsEventIndication"
::= 467

ibmSystempTrapDTPowerSupplyDiagnosticsBindings OBJECT IDENTIFIER ::= { ibmSystemTrap 467 }

ibmSystempTrapDTPowerSupplyDiagnosticsProviderName OBJECT-TYPE
   SYNTAX         String
   ACCESS         read-only
   STATUS         mandatory
   DESCRIPTION    "The name of the CIM Provider that monitors this device"
-- REFERENCE      "POWER_DTPowerSupplyDiagnosticsEventIndication.ProviderName"
::= { ibmSystempTrapDTPowerSupplyDiagnosticsBindings 1 }

ibmSystempTrapDTPowerSupplyDiagnosticsEventID OBJECT-TYPE
   SYNTAX         String
   ACCESS         read-only
   STATUS         mandatory
   DESCRIPTION    "A unique EventID that identifies this trap" 
-- REFERENCE      "POWER_DTPowerSupplyDiagnosticsEventIndication.EventID"
::= { ibmSystempTrapDTPowerSupplyDiagnosticsBindings 2 }

ibmSystempTrapDTPowerSupplyDiagnosticsAME OBJECT-TYPE
   SYNTAX         String
   ACCESS         read-only
   STATUS         mandatory
   DESCRIPTION    "A unique string that identifies the monitored device"
-- REFERENCE      "POWER_DTPowerSupplyDiagnosticsEventIndication.AlertingManagedElement"
::= { ibmSystempTrapDTPowerSupplyDiagnosticsBindings 3 }

ibmSystempTrapDTPowerSupplyDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTPowerSupplyDiagnosticsEventIndication.Severity"
::= { ibmSystempTrapDTPowerSupplyDiagnosticsBindings 4 }

ibmSystempTrapDTPowerSupplyDiagnosticsDescription OBJECT-TYPE
   SYNTAX         SnmpAdminString
   ACCESS         read-only
   STATUS         mandatory
   DESCRIPTION    "The Event text of the trap"
-- REFERENCE      "POWER_DTPowerSupplyDiagnosticsEventIndication.Description"
::= { ibmSystempTrapDTPowerSupplyDiagnosticsBindings 5 }

ibmSystempTrapDTPowerSupplyDiagnosticsTimeStamp OBJECT-TYPE
   SYNTAX         Datetime
   ACCESS         read-only
   STATUS         mandatory
   DESCRIPTION    "The time that the trap occurred"
-- REFERENCE      "POWER_DTPowerSupplyDiagnosticsEventIndication.TimeStamp"
::= { ibmSystempTrapDTPowerSupplyDiagnosticsBindings 6 }


ibmSystempTrapPFPowerSupplyDegradPerf TRAP-TYPE
   ENTERPRISE     ibmSystemMIB
   VARIABLES    {
      ibmSystempTrapPFPowerSupplyDegradPerfProviderName,
      ibmSystempTrapPFPowerSupplyDegradPerfEventID,
      ibmSystempTrapPFPowerSupplyDegradPerfAME,
      ibmSystempTrapPFPowerSupplyDegradPerfSeverity,
      ibmSystempTrapPFPowerSupplyDegradPerfDescription,
      ibmSystempTrapPFPowerSupplyDegradPerfTimeStamp
   }
   DESCRIPTION    "A System p event has occurred"
-- REFERENCE      "POWER_PFPowerSupplyDegradPerfEventIndication"
::= 468

ibmSystempTrapPFPowerSupplyDegradPerfBindings OBJECT IDENTIFIER ::= { ibmSystemTrap 468 }

ibmSystempTrapPFPowerSupplyDegradPerfProviderName OBJECT-TYPE
   SYNTAX         String
   ACCESS         read-only
   STATUS         mandatory
   DESCRIPTION    "The name of the CIM Provider that monitors this device"
-- REFERENCE      "POWER_PFPowerSupplyDegradPerfEventIndication.ProviderName"
::= { ibmSystempTrapPFPowerSupplyDegradPerfBindings 1 }

ibmSystempTrapPFPowerSupplyDegradPerfEventID OBJECT-TYPE
   SYNTAX         String
   ACCESS         read-only
   STATUS         mandatory
   DESCRIPTION    "A unique EventID that identifies this trap" 
-- REFERENCE      "POWER_PFPowerSupplyDegradPerfEventIndication.EventID"
::= { ibmSystempTrapPFPowerSupplyDegradPerfBindings 2 }

ibmSystempTrapPFPowerSupplyDegradPerfAME OBJECT-TYPE
   SYNTAX         String
   ACCESS         read-only
   STATUS         mandatory
   DESCRIPTION    "A unique string that identifies the monitored device"
-- REFERENCE      "POWER_PFPowerSupplyDegradPerfEventIndication.AlertingManagedElement"
::= { ibmSystempTrapPFPowerSupplyDegradPerfBindings 3 }

ibmSystempTrapPFPowerSupplyDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerSupplyDegradPerfEventIndication.Severity"
::= { ibmSystempTrapPFPowerSupplyDegradPerfBindings 4 }

ibmSystempTrapPFPowerSupplyDegradPerfDescription OBJECT-TYPE
   SYNTAX         SnmpAdminString
   ACCESS         read-only
   STATUS         mandatory
   DESCRIPTION    "The Event text of the trap"
-- REFERENCE      "POWER_PFPowerSupplyDegradPerfEventIndication.Description"
::= { ibmSystempTrapPFPowerSupplyDegradPerfBindings 5 }

ibmSystempTrapPFPowerSupplyDegradPerfTimeStamp OBJECT-TYPE
   SYNTAX         Datetime
   ACCESS         read-only
   STATUS         mandatory
   DESCRIPTION    "The time that the trap occurred"
-- REFERENCE      "POWER_PFPowerSupplyDegradPerfEventIndication.TimeStamp"
::= { ibmSystempTrapPFPowerSupplyDegradPerfBindings 6 }


ibmSystempTrapPFPowerSupplyCorrectAftIPL TRAP-TYPE
   ENTERPRISE     ibmSystemMIB
   VARIABLES    {
      ibmSystempTrapPFPowerSupplyCorrectAftIPLProviderName,
      ibmSystempTrapPFPowerSupplyCorrectAftIPLEventID,
      ibmSystempTrapPFPowerSupplyCorrectAftIPLAME,
      ibmSystempTrapPFPowerSupplyCorrectAftIPLSeverity,
      ibmSystempTrapPFPowerSupplyCorrectAftIPLDescription,
      ibmSystempTrapPFPowerSupplyCorrectAftIPLTimeStamp
   }
   DESCRIPTION    "A System p event has occurred"
-- REFERENCE      "POWER_PFPowerSupplyCorrectAftIPLEventIndication"
::= 469

ibmSystempTrapPFPowerSupplyCorrectAftIPLBindings OBJECT IDENTIFIER ::= { ibmSystemTrap 469 }

ibmSystempTrapPFPowerSupplyCorrectAftIPLProviderName OBJECT-TYPE
   SYNTAX         String
   ACCESS         read-only
   STATUS         mandatory
   DESCRIPTION    "The name of the CIM Provider that monitors this device"
-- REFERENCE      "POWER_PFPowerSupplyCorrectAftIPLEventIndication.ProviderName"
::= { ibmSystempTrapPFPowerSupplyCorrectAftIPLBindings 1 }

ibmSystempTrapPFPowerSupplyCorrectAftIPLEventID OBJECT-TYPE
   SYNTAX         String
   ACCESS         read-only
   STATUS         mandatory
   DESCRIPTION    "A unique EventID that identifies this trap" 
-- REFERENCE      "POWER_PFPowerSupplyCorrectAftIPLEventIndication.EventID"
::= { ibmSystempTrapPFPowerSupplyCorrectAftIPLBindings 2 }

ibmSystempTrapPFPowerSupplyCorrectAftIPLAME OBJECT-TYPE
   SYNTAX         String
   ACCESS         read-only
   STATUS         mandatory
   DESCRIPTION    "A unique string that identifies the monitored device"
-- REFERENCE      "POWER_PFPowerSupplyCorrectAftIPLEventIndication.AlertingManagedElement"
::= { ibmSystempTrapPFPowerSupplyCorrectAftIPLBindings 3 }

ibmSystempTrapPFPowerSupplyCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerSupplyCorrectAftIPLEventIndication.Severity"
::= { ibmSystempTrapPFPowerSupplyCorrectAftIPLBindings 4 }

ibmSystempTrapPFPowerSupplyCorrectAftIPLDescription OBJECT-TYPE
   SYNTAX         SnmpAdminString
   ACCESS         read-only
   STATUS         mandatory
   DESCRIPTION    "The Event text of the trap"
-- REFERENCE      "POWER_PFPowerSupplyCorrectAftIPLEventIndication.Description"
::= { ibmSystempTrapPFPowerSupplyCorrectAftIPLBindings 5 }

ibmSystempTrapPFPowerSupplyCorrectAftIPLTimeStamp OBJECT-TYPE
   SYNTAX         Datetime
   ACCESS         read-only
   STATUS         mandatory
   DESCRIPTION    "The time that the trap occurred"
-- REFERENCE      "POWER_PFPowerSupplyCorrectAftIPLEventIndication.TimeStamp"
::= { ibmSystempTrapPFPowerSupplyCorrectAftIPLBindings 6 }


ibmSystempTrapPFPowerSupplyCorrectAftIPLPerf TRAP-TYPE
   ENTERPRISE     ibmSystemMIB
   VARIABLES    {
      ibmSystempTrapPFPowerSupplyCorrectAftIPLPerfProviderName,
      ibmSystempTrapPFPowerSupplyCorrectAftIPLPerfEventID,
      ibmSystempTrapPFPowerSupplyCorrectAftIPLPerfAME,
      ibmSystempTrapPFPowerSupplyCorrectAftIPLPerfSeverity,
      ibmSystempTrapPFPowerSupplyCorrectAftIPLPerfDescription,
      ibmSystempTrapPFPowerSupplyCorrectAftIPLPerfTimeStamp
   }
   DESCRIPTION    "A System p event has occurred"
-- REFERENCE      "POWER_PFPowerSupplyCorrectAftIPLPerfEventIndication"
::= 470

ibmSystempTrapPFPowerSupplyCorrectAftIPLPerfBindings OBJECT IDENTIFIER ::= { ibmSystemTrap 470 }

ibmSystempTrapPFPowerSupplyCorrectAftIPLPerfProviderName OBJECT-TYPE
   SYNTAX         String
   ACCESS         read-only
   STATUS         mandatory
   DESCRIPTION    "The name of the CIM Provider that monitors this device"
-- REFERENCE      "POWER_PFPowerSupplyCorrectAftIPLPerfEventIndication.ProviderName"
::= { ibmSystempTrapPFPowerSupplyCorrectAftIPLPerfBindings 1 }

ibmSystempTrapPFPowerSupplyCorrectAftIPLPerfEventID OBJECT-TYPE
   SYNTAX         String
   ACCESS         read-only
   STATUS         mandatory
   DESCRIPTION    "A unique EventID that identifies this trap" 
-- REFERENCE      "POWER_PFPowerSupplyCorrectAftIPLPerfEventIndication.EventID"
::= { ibmSystempTrapPFPowerSupplyCorrectAftIPLPerfBindings 2 }

ibmSystempTrapPFPowerSupplyCorrectAftIPLPerfAME OBJECT-TYPE
   SYNTAX         String
   ACCESS         read-only
   STATUS         mandatory
   DESCRIPTION    "A unique string that identifies the monitored device"
-- REFERENCE      "POWER_PFPowerSupplyCorrectAftIPLPerfEventIndication.AlertingManagedElement"
::= { ibmSystempTrapPFPowerSupplyCorrectAftIPLPerfBindings 3 }

ibmSystempTrapPFPowerSupplyCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerSupplyCorrectAftIPLPerfEventIndication.Severity"
::= { ibmSystempTrapPFPowerSupplyCorrectAftIPLPerfBindings 4 }

ibmSystempTrapPFPowerSupplyCorrectAftIPLPerfDescription OBJECT-TYPE
   SYNTAX         SnmpAdminString
   ACCESS         read-only
   STATUS         mandatory
   DESCRIPTION    "The Event text of the trap"
-- REFERENCE      "POWER_PFPowerSupplyCorrectAftIPLPerfEventIndication.Description"
::= { ibmSystempTrapPFPowerSupplyCorrectAftIPLPerfBindings 5 }

ibmSystempTrapPFPowerSupplyCorrectAftIPLPerfTimeStamp OBJECT-TYPE
   SYNTAX         Datetime
   ACCESS         read-only
   STATUS         mandatory
   DESCRIPTION    "The time that the trap occurred"
-- REFERENCE      "POWER_PFPowerSupplyCorrectAftIPLPerfEventIndication.TimeStamp"
::= { ibmSystempTrapPFPowerSupplyCorrectAftIPLPerfBindings 6 }


ibmSystempTrapPFPowerSupplyLossOfRedundancy TRAP-TYPE
   ENTERPRISE     ibmSystemMIB
   VARIABLES    {
      ibmSystempTrapPFPowerSupplyLossOfRedundancyProviderName,
      ibmSystempTrapPFPowerSupplyLossOfRedundancyEventID,
      ibmSystempTrapPFPowerSupplyLossOfRedundancyAME,
      ibmSystempTrapPFPowerSupplyLossOfRedundancySeverity,
      ibmSystempTrapPFPowerSupplyLossOfRedundancyDescription,
      ibmSystempTrapPFPowerSupplyLossOfRedundancyTimeStamp
   }
   DESCRIPTION    "A System p event has occurred"
-- REFERENCE      "POWER_PFPowerSupplyLossOfRedundancyEventIndication"
::= 471

ibmSystempTrapPFPowerSupplyLossOfRedundancyBindings OBJECT IDENTIFIER ::= { ibmSystemTrap 471 }

ibmSystempTrapPFPowerSupplyLossOfRedundancyProviderName OBJECT-TYPE
   SYNTAX         String
   ACCESS         read-only
   STATUS         mandatory
   DESCRIPTION    "The name of the CIM Provider that monitors this device"
-- REFERENCE      "POWER_PFPowerSupplyLossOfRedundancyEventIndication.ProviderName"
::= { ibmSystempTrapPFPowerSupplyLossOfRedundancyBindings 1 }

ibmSystempTrapPFPowerSupplyLossOfRedundancyEventID OBJECT-TYPE
   SYNTAX         String
   ACCESS         read-only
   STATUS         mandatory
   DESCRIPTION    "A unique EventID that identifies this trap" 
-- REFERENCE      "POWER_PFPowerSupplyLossOfRedundancyEventIndication.EventID"
::= { ibmSystempTrapPFPowerSupplyLossOfRedundancyBindings 2 }

ibmSystempTrapPFPowerSupplyLossOfRedundancyAME OBJECT-TYPE
   SYNTAX         String
   ACCESS         read-only
   STATUS         mandatory
   DESCRIPTION    "A unique string that identifies the monitored device"
-- REFERENCE      "POWER_PFPowerSupplyLossOfRedundancyEventIndication.AlertingManagedElement"
::= { ibmSystempTrapPFPowerSupplyLossOfRedundancyBindings 3 }

ibmSystempTrapPFPowerSupplyLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerSupplyLossOfRedundancyEventIndication.Severity"
::= { ibmSystempTrapPFPowerSupplyLossOfRedundancyBindings 4 }

ibmSystempTrapPFPowerSupplyLossOfRedundancyDescription OBJECT-TYPE
   SYNTAX         SnmpAdminString
   ACCESS         read-only
   STATUS         mandatory
   DESCRIPTION    "The Event text of the trap"
-- REFERENCE      "POWER_PFPowerSupplyLossOfRedundancyEventIndication.Description"
::= { ibmSystempTrapPFPowerSupplyLossOfRedundancyBindings 5 }

ibmSystempTrapPFPowerSupplyLossOfRedundancyTimeStamp OBJECT-TYPE
   SYNTAX         Datetime
   ACCESS         read-only
   STATUS         mandatory
   DESCRIPTION    "The time that the trap occurred"
-- REFERENCE      "POWER_PFPowerSupplyLossOfRedundancyEventIndication.TimeStamp"
::= { ibmSystempTrapPFPowerSupplyLossOfRedundancyBindings 6 }


ibmSystempTrapPFPowerSupplyPredictiveError TRAP-TYPE
   ENTERPRISE     ibmSystemMIB
   VARIABLES    {
      ibmSystempTrapPFPowerSupplyPredictiveErrorProviderName,
      ibmSystempTrapPFPowerSupplyPredictiveErrorEventID,
      ibmSystempTrapPFPowerSupplyPredictiveErrorAME,
      ibmSystempTrapPFPowerSupplyPredictiveErrorSeverity,
      ibmSystempTrapPFPowerSupplyPredictiveErrorDescription,
      ibmSystempTrapPFPowerSupplyPredictiveErrorTimeStamp
   }
   DESCRIPTION    "A System p event has occurred"
-- REFERENCE      "POWER_PFPowerSupplyPredictiveErrorEventIndication"
::= 472

ibmSystempTrapPFPowerSupplyPredictiveErrorBindings OBJECT IDENTIFIER ::= { ibmSystemTrap 472 }

ibmSystempTrapPFPowerSupplyPredictiveErrorProviderName OBJECT-TYPE
   SYNTAX         String
   ACCESS         read-only
   STATUS         mandatory
   DESCRIPTION    "The name of the CIM Provider that monitors this device"
-- REFERENCE      "POWER_PFPowerSupplyPredictiveErrorEventIndication.ProviderName"
::= { ibmSystempTrapPFPowerSupplyPredictiveErrorBindings 1 }

ibmSystempTrapPFPowerSupplyPredictiveErrorEventID OBJECT-TYPE
   SYNTAX         String
   ACCESS         read-only
   STATUS         mandatory
   DESCRIPTION    "A unique EventID that identifies this trap" 
-- REFERENCE      "POWER_PFPowerSupplyPredictiveErrorEventIndication.EventID"
::= { ibmSystempTrapPFPowerSupplyPredictiveErrorBindings 2 }

ibmSystempTrapPFPowerSupplyPredictiveErrorAME OBJECT-TYPE
   SYNTAX         String
   ACCESS         read-only
   STATUS         mandatory
   DESCRIPTION    "A unique string that identifies the monitored device"
-- REFERENCE      "POWER_PFPowerSupplyPredictiveErrorEventIndication.AlertingManagedElement"
::= { ibmSystempTrapPFPowerSupplyPredictiveErrorBindings 3 }

ibmSystempTrapPFPowerSupplyPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPowerSupplyPredictiveErrorEventIndication.Severity"
::= { ibmSystempTrapPFPowerSupplyPredictiveErrorBindings 4 }

ibmSystempTrapPFPowerSupplyPredictiveErrorDescription OBJECT-TYPE
   SYNTAX         SnmpAdminString
   ACCESS         read-only
   STATUS         mandatory
   DESCRIPTION    "The Event text of the trap"
-- REFERENCE      "POWER_PFPowerSupplyPredictiveErrorEventIndication.Description"
::= { ibmSystempTrapPFPowerSupplyPredictiveErrorBindings 5 }

ibmSystempTrapPFPowerSupplyPredictiveErrorTimeStamp OBJECT-TYPE
   SYNTAX         Datetime
   ACCESS         read-only
   STATUS         mandatory
   DESCRIPTION    "The time that the trap occurred"
-- REFERENCE      "POWER_PFPowerSupplyPredictiveErrorEventIndication.TimeStamp"
::= { ibmSystempTrapPFPowerSupplyPredictiveErrorBindings 6 }


ibmSystempTrapUEPowerSupplyDegradPerf TRAP-TYPE
   ENTERPRISE     ibmSystemMIB
   VARIABLES    {
      ibmSystempTrapUEPowerSupplyDegradPerfProviderName,
      ibmSystempTrapUEPowerSupplyDegradPerfEventID,
      ibmSystempTrapUEPowerSupplyDegradPerfAME,
      ibmSystempTrapUEPowerSupplyDegradPerfSeverity,
      ibmSystempTrapUEPowerSupplyDegradPerfDescription,
      ibmSystempTrapUEPowerSupplyDegradPerfTimeStamp
   }
   DESCRIPTION    "A System p event has occurred"
-- REFERENCE      "POWER_UEPowerSupplyDegradPerfEventIndication"
::= 473

ibmSystempTrapUEPowerSupplyDegradPerfBindings OBJECT IDENTIFIER ::= { ibmSystemTrap 473 }

ibmSystempTrapUEPowerSupplyDegradPerfProviderName OBJECT-TYPE
   SYNTAX         String
   ACCESS         read-only
   STATUS         mandatory
   DESCRIPTION    "The name of the CIM Provider that monitors this device"
-- REFERENCE      "POWER_UEPowerSupplyDegradPerfEventIndication.ProviderName"
::= { ibmSystempTrapUEPowerSupplyDegradPerfBindings 1 }

ibmSystempTrapUEPowerSupplyDegradPerfEventID OBJECT-TYPE
   SYNTAX         String
   ACCESS         read-only
   STATUS         mandatory
   DESCRIPTION    "A unique EventID that identifies this trap" 
-- REFERENCE      "POWER_UEPowerSupplyDegradPerfEventIndication.EventID"
::= { ibmSystempTrapUEPowerSupplyDegradPerfBindings 2 }

ibmSystempTrapUEPowerSupplyDegradPerfAME OBJECT-TYPE
   SYNTAX         String
   ACCESS         read-only
   STATUS         mandatory
   DESCRIPTION    "A unique string that identifies the monitored device"
-- REFERENCE      "POWER_UEPowerSupplyDegradPerfEventIndication.AlertingManagedElement"
::= { ibmSystempTrapUEPowerSupplyDegradPerfBindings 3 }

ibmSystempTrapUEPowerSupplyDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerSupplyDegradPerfEventIndication.Severity"
::= { ibmSystempTrapUEPowerSupplyDegradPerfBindings 4 }

ibmSystempTrapUEPowerSupplyDegradPerfDescription OBJECT-TYPE
   SYNTAX         SnmpAdminString
   ACCESS         read-only
   STATUS         mandatory
   DESCRIPTION    "The Event text of the trap"
-- REFERENCE      "POWER_UEPowerSupplyDegradPerfEventIndication.Description"
::= { ibmSystempTrapUEPowerSupplyDegradPerfBindings 5 }

ibmSystempTrapUEPowerSupplyDegradPerfTimeStamp OBJECT-TYPE
   SYNTAX         Datetime
   ACCESS         read-only
   STATUS         mandatory
   DESCRIPTION    "The time that the trap occurred"
-- REFERENCE      "POWER_UEPowerSupplyDegradPerfEventIndication.TimeStamp"
::= { ibmSystempTrapUEPowerSupplyDegradPerfBindings 6 }


ibmSystempTrapUEPowerSupplyLossOfRedundancy TRAP-TYPE
   ENTERPRISE     ibmSystemMIB
   VARIABLES    {
      ibmSystempTrapUEPowerSupplyLossOfRedundancyProviderName,
      ibmSystempTrapUEPowerSupplyLossOfRedundancyEventID,
      ibmSystempTrapUEPowerSupplyLossOfRedundancyAME,
      ibmSystempTrapUEPowerSupplyLossOfRedundancySeverity,
      ibmSystempTrapUEPowerSupplyLossOfRedundancyDescription,
      ibmSystempTrapUEPowerSupplyLossOfRedundancyTimeStamp
   }
   DESCRIPTION    "A System p event has occurred"
-- REFERENCE      "POWER_UEPowerSupplyLossOfRedundancyEventIndication"
::= 474

ibmSystempTrapUEPowerSupplyLossOfRedundancyBindings OBJECT IDENTIFIER ::= { ibmSystemTrap 474 }

ibmSystempTrapUEPowerSupplyLossOfRedundancyProviderName OBJECT-TYPE
   SYNTAX         String
   ACCESS         read-only
   STATUS         mandatory
   DESCRIPTION    "The name of the CIM Provider that monitors this device"
-- REFERENCE      "POWER_UEPowerSupplyLossOfRedundancyEventIndication.ProviderName"
::= { ibmSystempTrapUEPowerSupplyLossOfRedundancyBindings 1 }

ibmSystempTrapUEPowerSupplyLossOfRedundancyEventID OBJECT-TYPE
   SYNTAX         String
   ACCESS         read-only
   STATUS         mandatory
   DESCRIPTION    "A unique EventID that identifies this trap" 
-- REFERENCE      "POWER_UEPowerSupplyLossOfRedundancyEventIndication.EventID"
::= { ibmSystempTrapUEPowerSupplyLossOfRedundancyBindings 2 }

ibmSystempTrapUEPowerSupplyLossOfRedundancyAME OBJECT-TYPE
   SYNTAX         String
   ACCESS         read-only
   STATUS         mandatory
   DESCRIPTION    "A unique string that identifies the monitored device"
-- REFERENCE      "POWER_UEPowerSupplyLossOfRedundancyEventIndication.AlertingManagedElement"
::= { ibmSystempTrapUEPowerSupplyLossOfRedundancyBindings 3 }

ibmSystempTrapUEPowerSupplyLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerSupplyLossOfRedundancyEventIndication.Severity"
::= { ibmSystempTrapUEPowerSupplyLossOfRedundancyBindings 4 }

ibmSystempTrapUEPowerSupplyLossOfRedundancyDescription OBJECT-TYPE
   SYNTAX         SnmpAdminString
   ACCESS         read-only
   STATUS         mandatory
   DESCRIPTION    "The Event text of the trap"
-- REFERENCE      "POWER_UEPowerSupplyLossOfRedundancyEventIndication.Description"
::= { ibmSystempTrapUEPowerSupplyLossOfRedundancyBindings 5 }

ibmSystempTrapUEPowerSupplyLossOfRedundancyTimeStamp OBJECT-TYPE
   SYNTAX         Datetime
   ACCESS         read-only
   STATUS         mandatory
   DESCRIPTION    "The time that the trap occurred"
-- REFERENCE      "POWER_UEPowerSupplyLossOfRedundancyEventIndication.TimeStamp"
::= { ibmSystempTrapUEPowerSupplyLossOfRedundancyBindings 6 }


ibmSystempTrapUEPowerSupplyLossOfRedundAndPerf TRAP-TYPE
   ENTERPRISE     ibmSystemMIB
   VARIABLES    {
      ibmSystempTrapUEPowerSupplyLossOfRedundAndPerfProviderName,
      ibmSystempTrapUEPowerSupplyLossOfRedundAndPerfEventID,
      ibmSystempTrapUEPowerSupplyLossOfRedundAndPerfAME,
      ibmSystempTrapUEPowerSupplyLossOfRedundAndPerfSeverity,
      ibmSystempTrapUEPowerSupplyLossOfRedundAndPerfDescription,
      ibmSystempTrapUEPowerSupplyLossOfRedundAndPerfTimeStamp
   }
   DESCRIPTION    "A System p event has occurred"
-- REFERENCE      "POWER_UEPowerSupplyLossOfRedundAndPerfEventIndication"
::= 475

ibmSystempTrapUEPowerSupplyLossOfRedundAndPerfBindings OBJECT IDENTIFIER ::= { ibmSystemTrap 475 }

ibmSystempTrapUEPowerSupplyLossOfRedundAndPerfProviderName OBJECT-TYPE
   SYNTAX         String
   ACCESS         read-only
   STATUS         mandatory
   DESCRIPTION    "The name of the CIM Provider that monitors this device"
-- REFERENCE      "POWER_UEPowerSupplyLossOfRedundAndPerfEventIndication.ProviderName"
::= { ibmSystempTrapUEPowerSupplyLossOfRedundAndPerfBindings 1 }

ibmSystempTrapUEPowerSupplyLossOfRedundAndPerfEventID OBJECT-TYPE
   SYNTAX         String
   ACCESS         read-only
   STATUS         mandatory
   DESCRIPTION    "A unique EventID that identifies this trap" 
-- REFERENCE      "POWER_UEPowerSupplyLossOfRedundAndPerfEventIndication.EventID"
::= { ibmSystempTrapUEPowerSupplyLossOfRedundAndPerfBindings 2 }

ibmSystempTrapUEPowerSupplyLossOfRedundAndPerfAME OBJECT-TYPE
   SYNTAX         String
   ACCESS         read-only
   STATUS         mandatory
   DESCRIPTION    "A unique string that identifies the monitored device"
-- REFERENCE      "POWER_UEPowerSupplyLossOfRedundAndPerfEventIndication.AlertingManagedElement"
::= { ibmSystempTrapUEPowerSupplyLossOfRedundAndPerfBindings 3 }

ibmSystempTrapUEPowerSupplyLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerSupplyLossOfRedundAndPerfEventIndication.Severity"
::= { ibmSystempTrapUEPowerSupplyLossOfRedundAndPerfBindings 4 }

ibmSystempTrapUEPowerSupplyLossOfRedundAndPerfDescription OBJECT-TYPE
   SYNTAX         SnmpAdminString
   ACCESS         read-only
   STATUS         mandatory
   DESCRIPTION    "The Event text of the trap"
-- REFERENCE      "POWER_UEPowerSupplyLossOfRedundAndPerfEventIndication.Description"
::= { ibmSystempTrapUEPowerSupplyLossOfRedundAndPerfBindings 5 }

ibmSystempTrapUEPowerSupplyLossOfRedundAndPerfTimeStamp OBJECT-TYPE
   SYNTAX         Datetime
   ACCESS         read-only
   STATUS         mandatory
   DESCRIPTION    "The time that the trap occurred"
-- REFERENCE      "POWER_UEPowerSupplyLossOfRedundAndPerfEventIndication.TimeStamp"
::= { ibmSystempTrapUEPowerSupplyLossOfRedundAndPerfBindings 6 }


ibmSystempTrapUEPowerSupplyLossOfFunction TRAP-TYPE
   ENTERPRISE     ibmSystemMIB
   VARIABLES    {
      ibmSystempTrapUEPowerSupplyLossOfFunctionProviderName,
      ibmSystempTrapUEPowerSupplyLossOfFunctionEventID,
      ibmSystempTrapUEPowerSupplyLossOfFunctionAME,
      ibmSystempTrapUEPowerSupplyLossOfFunctionSeverity,
      ibmSystempTrapUEPowerSupplyLossOfFunctionDescription,
      ibmSystempTrapUEPowerSupplyLossOfFunctionTimeStamp
   }
   DESCRIPTION    "A System p event has occurred"
-- REFERENCE      "POWER_UEPowerSupplyLossOfFunctionEventIndication"
::= 476

ibmSystempTrapUEPowerSupplyLossOfFunctionBindings OBJECT IDENTIFIER ::= { ibmSystemTrap 476 }

ibmSystempTrapUEPowerSupplyLossOfFunctionProviderName OBJECT-TYPE
   SYNTAX         String
   ACCESS         read-only
   STATUS         mandatory
   DESCRIPTION    "The name of the CIM Provider that monitors this device"
-- REFERENCE      "POWER_UEPowerSupplyLossOfFunctionEventIndication.ProviderName"
::= { ibmSystempTrapUEPowerSupplyLossOfFunctionBindings 1 }

ibmSystempTrapUEPowerSupplyLossOfFunctionEventID OBJECT-TYPE
   SYNTAX         String
   ACCESS         read-only
   STATUS         mandatory
   DESCRIPTION    "A unique EventID that identifies this trap" 
-- REFERENCE      "POWER_UEPowerSupplyLossOfFunctionEventIndication.EventID"
::= { ibmSystempTrapUEPowerSupplyLossOfFunctionBindings 2 }

ibmSystempTrapUEPowerSupplyLossOfFunctionAME OBJECT-TYPE
   SYNTAX         String
   ACCESS         read-only
   STATUS         mandatory
   DESCRIPTION    "A unique string that identifies the monitored device"
-- REFERENCE      "POWER_UEPowerSupplyLossOfFunctionEventIndication.AlertingManagedElement"
::= { ibmSystempTrapUEPowerSupplyLossOfFunctionBindings 3 }

ibmSystempTrapUEPowerSupplyLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerSupplyLossOfFunctionEventIndication.Severity"
::= { ibmSystempTrapUEPowerSupplyLossOfFunctionBindings 4 }

ibmSystempTrapUEPowerSupplyLossOfFunctionDescription OBJECT-TYPE
   SYNTAX         SnmpAdminString
   ACCESS         read-only
   STATUS         mandatory
   DESCRIPTION    "The Event text of the trap"
-- REFERENCE      "POWER_UEPowerSupplyLossOfFunctionEventIndication.Description"
::= { ibmSystempTrapUEPowerSupplyLossOfFunctionBindings 5 }

ibmSystempTrapUEPowerSupplyLossOfFunctionTimeStamp OBJECT-TYPE
   SYNTAX         Datetime
   ACCESS         read-only
   STATUS         mandatory
   DESCRIPTION    "The time that the trap occurred"
-- REFERENCE      "POWER_UEPowerSupplyLossOfFunctionEventIndication.TimeStamp"
::= { ibmSystempTrapUEPowerSupplyLossOfFunctionBindings 6 }


ibmSystempTrapUEPowerSupplyUnrecoverableError TRAP-TYPE
   ENTERPRISE     ibmSystemMIB
   VARIABLES    {
      ibmSystempTrapUEPowerSupplyUnrecoverableErrorProviderName,
      ibmSystempTrapUEPowerSupplyUnrecoverableErrorEventID,
      ibmSystempTrapUEPowerSupplyUnrecoverableErrorAME,
      ibmSystempTrapUEPowerSupplyUnrecoverableErrorSeverity,
      ibmSystempTrapUEPowerSupplyUnrecoverableErrorDescription,
      ibmSystempTrapUEPowerSupplyUnrecoverableErrorTimeStamp
   }
   DESCRIPTION    "A System p event has occurred"
-- REFERENCE      "POWER_UEPowerSupplyUnrecoverableErrorEventIndication"
::= 477

ibmSystempTrapUEPowerSupplyUnrecoverableErrorBindings OBJECT IDENTIFIER ::= { ibmSystemTrap 477 }

ibmSystempTrapUEPowerSupplyUnrecoverableErrorProviderName OBJECT-TYPE
   SYNTAX         String
   ACCESS         read-only
   STATUS         mandatory
   DESCRIPTION    "The name of the CIM Provider that monitors this device"
-- REFERENCE      "POWER_UEPowerSupplyUnrecoverableErrorEventIndication.ProviderName"
::= { ibmSystempTrapUEPowerSupplyUnrecoverableErrorBindings 1 }

ibmSystempTrapUEPowerSupplyUnrecoverableErrorEventID OBJECT-TYPE
   SYNTAX         String
   ACCESS         read-only
   STATUS         mandatory
   DESCRIPTION    "A unique EventID that identifies this trap" 
-- REFERENCE      "POWER_UEPowerSupplyUnrecoverableErrorEventIndication.EventID"
::= { ibmSystempTrapUEPowerSupplyUnrecoverableErrorBindings 2 }

ibmSystempTrapUEPowerSupplyUnrecoverableErrorAME OBJECT-TYPE
   SYNTAX         String
   ACCESS         read-only
   STATUS         mandatory
   DESCRIPTION    "A unique string that identifies the monitored device"
-- REFERENCE      "POWER_UEPowerSupplyUnrecoverableErrorEventIndication.AlertingManagedElement"
::= { ibmSystempTrapUEPowerSupplyUnrecoverableErrorBindings 3 }

ibmSystempTrapUEPowerSupplyUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPowerSupplyUnrecoverableErrorEventIndication.Severity"
::= { ibmSystempTrapUEPowerSupplyUnrecoverableErrorBindings 4 }

ibmSystempTrapUEPowerSupplyUnrecoverableErrorDescription OBJECT-TYPE
   SYNTAX         SnmpAdminString
   ACCESS         read-only
   STATUS         mandatory
   DESCRIPTION    "The Event text of the trap"
-- REFERENCE      "POWER_UEPowerSupplyUnrecoverableErrorEventIndication.Description"
::= { ibmSystempTrapUEPowerSupplyUnrecoverableErrorBindings 5 }

ibmSystempTrapUEPowerSupplyUnrecoverableErrorTimeStamp OBJECT-TYPE
   SYNTAX         Datetime
   ACCESS         read-only
   STATUS         mandatory
   DESCRIPTION    "The time that the trap occurred"
-- REFERENCE      "POWER_UEPowerSupplyUnrecoverableErrorEventIndication.TimeStamp"
::= { ibmSystempTrapUEPowerSupplyUnrecoverableErrorBindings 6 }


ibmSystempTrapDTFanDiagnostics TRAP-TYPE
   ENTERPRISE     ibmSystemMIB
   VARIABLES    {
      ibmSystempTrapDTFanDiagnosticsProviderName,
      ibmSystempTrapDTFanDiagnosticsEventID,
      ibmSystempTrapDTFanDiagnosticsAME,
      ibmSystempTrapDTFanDiagnosticsSeverity,
      ibmSystempTrapDTFanDiagnosticsDescription,
      ibmSystempTrapDTFanDiagnosticsTimeStamp
   }
   DESCRIPTION    "A System p event has occurred"
-- REFERENCE      "POWER_DTFanDiagnosticsEventIndication"
::= 478

ibmSystempTrapDTFanDiagnosticsBindings OBJECT IDENTIFIER ::= { ibmSystemTrap 478 }

ibmSystempTrapDTFanDiagnosticsProviderName OBJECT-TYPE
   SYNTAX         String
   ACCESS         read-only
   STATUS         mandatory
   DESCRIPTION    "The name of the CIM Provider that monitors this device"
-- REFERENCE      "POWER_DTFanDiagnosticsEventIndication.ProviderName"
::= { ibmSystempTrapDTFanDiagnosticsBindings 1 }

ibmSystempTrapDTFanDiagnosticsEventID OBJECT-TYPE
   SYNTAX         String
   ACCESS         read-only
   STATUS         mandatory
   DESCRIPTION    "A unique EventID that identifies this trap" 
-- REFERENCE      "POWER_DTFanDiagnosticsEventIndication.EventID"
::= { ibmSystempTrapDTFanDiagnosticsBindings 2 }

ibmSystempTrapDTFanDiagnosticsAME OBJECT-TYPE
   SYNTAX         String
   ACCESS         read-only
   STATUS         mandatory
   DESCRIPTION    "A unique string that identifies the monitored device"
-- REFERENCE      "POWER_DTFanDiagnosticsEventIndication.AlertingManagedElement"
::= { ibmSystempTrapDTFanDiagnosticsBindings 3 }

ibmSystempTrapDTFanDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTFanDiagnosticsEventIndication.Severity"
::= { ibmSystempTrapDTFanDiagnosticsBindings 4 }

ibmSystempTrapDTFanDiagnosticsDescription OBJECT-TYPE
   SYNTAX         SnmpAdminString
   ACCESS         read-only
   STATUS         mandatory
   DESCRIPTION    "The Event text of the trap"
-- REFERENCE      "POWER_DTFanDiagnosticsEventIndication.Description"
::= { ibmSystempTrapDTFanDiagnosticsBindings 5 }

ibmSystempTrapDTFanDiagnosticsTimeStamp OBJECT-TYPE
   SYNTAX         Datetime
   ACCESS         read-only
   STATUS         mandatory
   DESCRIPTION    "The time that the trap occurred"
-- REFERENCE      "POWER_DTFanDiagnosticsEventIndication.TimeStamp"
::= { ibmSystempTrapDTFanDiagnosticsBindings 6 }


ibmSystempTrapPFFanDegradPerf TRAP-TYPE
   ENTERPRISE     ibmSystemMIB
   VARIABLES    {
      ibmSystempTrapPFFanDegradPerfProviderName,
      ibmSystempTrapPFFanDegradPerfEventID,
      ibmSystempTrapPFFanDegradPerfAME,
      ibmSystempTrapPFFanDegradPerfSeverity,
      ibmSystempTrapPFFanDegradPerfDescription,
      ibmSystempTrapPFFanDegradPerfTimeStamp
   }
   DESCRIPTION    "A System p event has occurred"
-- REFERENCE      "POWER_PFFanDegradPerfEventIndication"
::= 479

ibmSystempTrapPFFanDegradPerfBindings OBJECT IDENTIFIER ::= { ibmSystemTrap 479 }

ibmSystempTrapPFFanDegradPerfProviderName OBJECT-TYPE
   SYNTAX         String
   ACCESS         read-only
   STATUS         mandatory
   DESCRIPTION    "The name of the CIM Provider that monitors this device"
-- REFERENCE      "POWER_PFFanDegradPerfEventIndication.ProviderName"
::= { ibmSystempTrapPFFanDegradPerfBindings 1 }

ibmSystempTrapPFFanDegradPerfEventID OBJECT-TYPE
   SYNTAX         String
   ACCESS         read-only
   STATUS         mandatory
   DESCRIPTION    "A unique EventID that identifies this trap" 
-- REFERENCE      "POWER_PFFanDegradPerfEventIndication.EventID"
::= { ibmSystempTrapPFFanDegradPerfBindings 2 }

ibmSystempTrapPFFanDegradPerfAME OBJECT-TYPE
   SYNTAX         String
   ACCESS         read-only
   STATUS         mandatory
   DESCRIPTION    "A unique string that identifies the monitored device"
-- REFERENCE      "POWER_PFFanDegradPerfEventIndication.AlertingManagedElement"
::= { ibmSystempTrapPFFanDegradPerfBindings 3 }

ibmSystempTrapPFFanDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFFanDegradPerfEventIndication.Severity"
::= { ibmSystempTrapPFFanDegradPerfBindings 4 }

ibmSystempTrapPFFanDegradPerfDescription OBJECT-TYPE
   SYNTAX         SnmpAdminString
   ACCESS         read-only
   STATUS         mandatory
   DESCRIPTION    "The Event text of the trap"
-- REFERENCE      "POWER_PFFanDegradPerfEventIndication.Description"
::= { ibmSystempTrapPFFanDegradPerfBindings 5 }

ibmSystempTrapPFFanDegradPerfTimeStamp OBJECT-TYPE
   SYNTAX         Datetime
   ACCESS         read-only
   STATUS         mandatory
   DESCRIPTION    "The time that the trap occurred"
-- REFERENCE      "POWER_PFFanDegradPerfEventIndication.TimeStamp"
::= { ibmSystempTrapPFFanDegradPerfBindings 6 }


ibmSystempTrapPFFanCorrectAftIPL TRAP-TYPE
   ENTERPRISE     ibmSystemMIB
   VARIABLES    {
      ibmSystempTrapPFFanCorrectAftIPLProviderName,
      ibmSystempTrapPFFanCorrectAftIPLEventID,
      ibmSystempTrapPFFanCorrectAftIPLAME,
      ibmSystempTrapPFFanCorrectAftIPLSeverity,
      ibmSystempTrapPFFanCorrectAftIPLDescription,
      ibmSystempTrapPFFanCorrectAftIPLTimeStamp
   }
   DESCRIPTION    "A System p event has occurred"
-- REFERENCE      "POWER_PFFanCorrectAftIPLEventIndication"
::= 480

ibmSystempTrapPFFanCorrectAftIPLBindings OBJECT IDENTIFIER ::= { ibmSystemTrap 480 }

ibmSystempTrapPFFanCorrectAftIPLProviderName OBJECT-TYPE
   SYNTAX         String
   ACCESS         read-only
   STATUS         mandatory
   DESCRIPTION    "The name of the CIM Provider that monitors this device"
-- REFERENCE      "POWER_PFFanCorrectAftIPLEventIndication.ProviderName"
::= { ibmSystempTrapPFFanCorrectAftIPLBindings 1 }

ibmSystempTrapPFFanCorrectAftIPLEventID OBJECT-TYPE
   SYNTAX         String
   ACCESS         read-only
   STATUS         mandatory
   DESCRIPTION    "A unique EventID that identifies this trap" 
-- REFERENCE      "POWER_PFFanCorrectAftIPLEventIndication.EventID"
::= { ibmSystempTrapPFFanCorrectAftIPLBindings 2 }

ibmSystempTrapPFFanCorrectAftIPLAME OBJECT-TYPE
   SYNTAX         String
   ACCESS         read-only
   STATUS         mandatory
   DESCRIPTION    "A unique string that identifies the monitored device"
-- REFERENCE      "POWER_PFFanCorrectAftIPLEventIndication.AlertingManagedElement"
::= { ibmSystempTrapPFFanCorrectAftIPLBindings 3 }

ibmSystempTrapPFFanCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFFanCorrectAftIPLEventIndication.Severity"
::= { ibmSystempTrapPFFanCorrectAftIPLBindings 4 }

ibmSystempTrapPFFanCorrectAftIPLDescription OBJECT-TYPE
   SYNTAX         SnmpAdminString
   ACCESS         read-only
   STATUS         mandatory
   DESCRIPTION    "The Event text of the trap"
-- REFERENCE      "POWER_PFFanCorrectAftIPLEventIndication.Description"
::= { ibmSystempTrapPFFanCorrectAftIPLBindings 5 }

ibmSystempTrapPFFanCorrectAftIPLTimeStamp OBJECT-TYPE
   SYNTAX         Datetime
   ACCESS         read-only
   STATUS         mandatory
   DESCRIPTION    "The time that the trap occurred"
-- REFERENCE      "POWER_PFFanCorrectAftIPLEventIndication.TimeStamp"
::= { ibmSystempTrapPFFanCorrectAftIPLBindings 6 }


ibmSystempTrapPFFanCorrectAftIPLPerf TRAP-TYPE
   ENTERPRISE     ibmSystemMIB
   VARIABLES    {
      ibmSystempTrapPFFanCorrectAftIPLPerfProviderName,
      ibmSystempTrapPFFanCorrectAftIPLPerfEventID,
      ibmSystempTrapPFFanCorrectAftIPLPerfAME,
      ibmSystempTrapPFFanCorrectAftIPLPerfSeverity,
      ibmSystempTrapPFFanCorrectAftIPLPerfDescription,
      ibmSystempTrapPFFanCorrectAftIPLPerfTimeStamp
   }
   DESCRIPTION    "A System p event has occurred"
-- REFERENCE      "POWER_PFFanCorrectAftIPLPerfEventIndication"
::= 481

ibmSystempTrapPFFanCorrectAftIPLPerfBindings OBJECT IDENTIFIER ::= { ibmSystemTrap 481 }

ibmSystempTrapPFFanCorrectAftIPLPerfProviderName OBJECT-TYPE
   SYNTAX         String
   ACCESS         read-only
   STATUS         mandatory
   DESCRIPTION    "The name of the CIM Provider that monitors this device"
-- REFERENCE      "POWER_PFFanCorrectAftIPLPerfEventIndication.ProviderName"
::= { ibmSystempTrapPFFanCorrectAftIPLPerfBindings 1 }

ibmSystempTrapPFFanCorrectAftIPLPerfEventID OBJECT-TYPE
   SYNTAX         String
   ACCESS         read-only
   STATUS         mandatory
   DESCRIPTION    "A unique EventID that identifies this trap" 
-- REFERENCE      "POWER_PFFanCorrectAftIPLPerfEventIndication.EventID"
::= { ibmSystempTrapPFFanCorrectAftIPLPerfBindings 2 }

ibmSystempTrapPFFanCorrectAftIPLPerfAME OBJECT-TYPE
   SYNTAX         String
   ACCESS         read-only
   STATUS         mandatory
   DESCRIPTION    "A unique string that identifies the monitored device"
-- REFERENCE      "POWER_PFFanCorrectAftIPLPerfEventIndication.AlertingManagedElement"
::= { ibmSystempTrapPFFanCorrectAftIPLPerfBindings 3 }

ibmSystempTrapPFFanCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFFanCorrectAftIPLPerfEventIndication.Severity"
::= { ibmSystempTrapPFFanCorrectAftIPLPerfBindings 4 }

ibmSystempTrapPFFanCorrectAftIPLPerfDescription OBJECT-TYPE
   SYNTAX         SnmpAdminString
   ACCESS         read-only
   STATUS         mandatory
   DESCRIPTION    "The Event text of the trap"
-- REFERENCE      "POWER_PFFanCorrectAftIPLPerfEventIndication.Description"
::= { ibmSystempTrapPFFanCorrectAftIPLPerfBindings 5 }

ibmSystempTrapPFFanCorrectAftIPLPerfTimeStamp OBJECT-TYPE
   SYNTAX         Datetime
   ACCESS         read-only
   STATUS         mandatory
   DESCRIPTION    "The time that the trap occurred"
-- REFERENCE      "POWER_PFFanCorrectAftIPLPerfEventIndication.TimeStamp"
::= { ibmSystempTrapPFFanCorrectAftIPLPerfBindings 6 }


ibmSystempTrapPFFanLossOfRedundancy TRAP-TYPE
   ENTERPRISE     ibmSystemMIB
   VARIABLES    {
      ibmSystempTrapPFFanLossOfRedundancyProviderName,
      ibmSystempTrapPFFanLossOfRedundancyEventID,
      ibmSystempTrapPFFanLossOfRedundancyAME,
      ibmSystempTrapPFFanLossOfRedundancySeverity,
      ibmSystempTrapPFFanLossOfRedundancyDescription,
      ibmSystempTrapPFFanLossOfRedundancyTimeStamp
   }
   DESCRIPTION    "A System p event has occurred"
-- REFERENCE      "POWER_PFFanLossOfRedundancyEventIndication"
::= 482

ibmSystempTrapPFFanLossOfRedundancyBindings OBJECT IDENTIFIER ::= { ibmSystemTrap 482 }

ibmSystempTrapPFFanLossOfRedundancyProviderName OBJECT-TYPE
   SYNTAX         String
   ACCESS         read-only
   STATUS         mandatory
   DESCRIPTION    "The name of the CIM Provider that monitors this device"
-- REFERENCE      "POWER_PFFanLossOfRedundancyEventIndication.ProviderName"
::= { ibmSystempTrapPFFanLossOfRedundancyBindings 1 }

ibmSystempTrapPFFanLossOfRedundancyEventID OBJECT-TYPE
   SYNTAX         String
   ACCESS         read-only
   STATUS         mandatory
   DESCRIPTION    "A unique EventID that identifies this trap" 
-- REFERENCE      "POWER_PFFanLossOfRedundancyEventIndication.EventID"
::= { ibmSystempTrapPFFanLossOfRedundancyBindings 2 }

ibmSystempTrapPFFanLossOfRedundancyAME OBJECT-TYPE
   SYNTAX         String
   ACCESS         read-only
   STATUS         mandatory
   DESCRIPTION    "A unique string that identifies the monitored device"
-- REFERENCE      "POWER_PFFanLossOfRedundancyEventIndication.AlertingManagedElement"
::= { ibmSystempTrapPFFanLossOfRedundancyBindings 3 }

ibmSystempTrapPFFanLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFFanLossOfRedundancyEventIndication.Severity"
::= { ibmSystempTrapPFFanLossOfRedundancyBindings 4 }

ibmSystempTrapPFFanLossOfRedundancyDescription OBJECT-TYPE
   SYNTAX         SnmpAdminString
   ACCESS         read-only
   STATUS         mandatory
   DESCRIPTION    "The Event text of the trap"
-- REFERENCE      "POWER_PFFanLossOfRedundancyEventIndication.Description"
::= { ibmSystempTrapPFFanLossOfRedundancyBindings 5 }

ibmSystempTrapPFFanLossOfRedundancyTimeStamp OBJECT-TYPE
   SYNTAX         Datetime
   ACCESS         read-only
   STATUS         mandatory
   DESCRIPTION    "The time that the trap occurred"
-- REFERENCE      "POWER_PFFanLossOfRedundancyEventIndication.TimeStamp"
::= { ibmSystempTrapPFFanLossOfRedundancyBindings 6 }


ibmSystempTrapPFFanPredictiveError TRAP-TYPE
   ENTERPRISE     ibmSystemMIB
   VARIABLES    {
      ibmSystempTrapPFFanPredictiveErrorProviderName,
      ibmSystempTrapPFFanPredictiveErrorEventID,
      ibmSystempTrapPFFanPredictiveErrorAME,
      ibmSystempTrapPFFanPredictiveErrorSeverity,
      ibmSystempTrapPFFanPredictiveErrorDescription,
      ibmSystempTrapPFFanPredictiveErrorTimeStamp
   }
   DESCRIPTION    "A System p event has occurred"
-- REFERENCE      "POWER_PFFanPredictiveErrorEventIndication"
::= 483

ibmSystempTrapPFFanPredictiveErrorBindings OBJECT IDENTIFIER ::= { ibmSystemTrap 483 }

ibmSystempTrapPFFanPredictiveErrorProviderName OBJECT-TYPE
   SYNTAX         String
   ACCESS         read-only
   STATUS         mandatory
   DESCRIPTION    "The name of the CIM Provider that monitors this device"
-- REFERENCE      "POWER_PFFanPredictiveErrorEventIndication.ProviderName"
::= { ibmSystempTrapPFFanPredictiveErrorBindings 1 }

ibmSystempTrapPFFanPredictiveErrorEventID OBJECT-TYPE
   SYNTAX         String
   ACCESS         read-only
   STATUS         mandatory
   DESCRIPTION    "A unique EventID that identifies this trap" 
-- REFERENCE      "POWER_PFFanPredictiveErrorEventIndication.EventID"
::= { ibmSystempTrapPFFanPredictiveErrorBindings 2 }

ibmSystempTrapPFFanPredictiveErrorAME OBJECT-TYPE
   SYNTAX         String
   ACCESS         read-only
   STATUS         mandatory
   DESCRIPTION    "A unique string that identifies the monitored device"
-- REFERENCE      "POWER_PFFanPredictiveErrorEventIndication.AlertingManagedElement"
::= { ibmSystempTrapPFFanPredictiveErrorBindings 3 }

ibmSystempTrapPFFanPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFFanPredictiveErrorEventIndication.Severity"
::= { ibmSystempTrapPFFanPredictiveErrorBindings 4 }

ibmSystempTrapPFFanPredictiveErrorDescription OBJECT-TYPE
   SYNTAX         SnmpAdminString
   ACCESS         read-only
   STATUS         mandatory
   DESCRIPTION    "The Event text of the trap"
-- REFERENCE      "POWER_PFFanPredictiveErrorEventIndication.Description"
::= { ibmSystempTrapPFFanPredictiveErrorBindings 5 }

ibmSystempTrapPFFanPredictiveErrorTimeStamp OBJECT-TYPE
   SYNTAX         Datetime
   ACCESS         read-only
   STATUS         mandatory
   DESCRIPTION    "The time that the trap occurred"
-- REFERENCE      "POWER_PFFanPredictiveErrorEventIndication.TimeStamp"
::= { ibmSystempTrapPFFanPredictiveErrorBindings 6 }


ibmSystempTrapUEFanDegradPerf TRAP-TYPE
   ENTERPRISE     ibmSystemMIB
   VARIABLES    {
      ibmSystempTrapUEFanDegradPerfProviderName,
      ibmSystempTrapUEFanDegradPerfEventID,
      ibmSystempTrapUEFanDegradPerfAME,
      ibmSystempTrapUEFanDegradPerfSeverity,
      ibmSystempTrapUEFanDegradPerfDescription,
      ibmSystempTrapUEFanDegradPerfTimeStamp
   }
   DESCRIPTION    "A System p event has occurred"
-- REFERENCE      "POWER_UEFanDegradPerfEventIndication"
::= 484

ibmSystempTrapUEFanDegradPerfBindings OBJECT IDENTIFIER ::= { ibmSystemTrap 484 }

ibmSystempTrapUEFanDegradPerfProviderName OBJECT-TYPE
   SYNTAX         String
   ACCESS         read-only
   STATUS         mandatory
   DESCRIPTION    "The name of the CIM Provider that monitors this device"
-- REFERENCE      "POWER_UEFanDegradPerfEventIndication.ProviderName"
::= { ibmSystempTrapUEFanDegradPerfBindings 1 }

ibmSystempTrapUEFanDegradPerfEventID OBJECT-TYPE
   SYNTAX         String
   ACCESS         read-only
   STATUS         mandatory
   DESCRIPTION    "A unique EventID that identifies this trap" 
-- REFERENCE      "POWER_UEFanDegradPerfEventIndication.EventID"
::= { ibmSystempTrapUEFanDegradPerfBindings 2 }

ibmSystempTrapUEFanDegradPerfAME OBJECT-TYPE
   SYNTAX         String
   ACCESS         read-only
   STATUS         mandatory
   DESCRIPTION    "A unique string that identifies the monitored device"
-- REFERENCE      "POWER_UEFanDegradPerfEventIndication.AlertingManagedElement"
::= { ibmSystempTrapUEFanDegradPerfBindings 3 }

ibmSystempTrapUEFanDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEFanDegradPerfEventIndication.Severity"
::= { ibmSystempTrapUEFanDegradPerfBindings 4 }

ibmSystempTrapUEFanDegradPerfDescription OBJECT-TYPE
   SYNTAX         SnmpAdminString
   ACCESS         read-only
   STATUS         mandatory
   DESCRIPTION    "The Event text of the trap"
-- REFERENCE      "POWER_UEFanDegradPerfEventIndication.Description"
::= { ibmSystempTrapUEFanDegradPerfBindings 5 }

ibmSystempTrapUEFanDegradPerfTimeStamp OBJECT-TYPE
   SYNTAX         Datetime
   ACCESS         read-only
   STATUS         mandatory
   DESCRIPTION    "The time that the trap occurred"
-- REFERENCE      "POWER_UEFanDegradPerfEventIndication.TimeStamp"
::= { ibmSystempTrapUEFanDegradPerfBindings 6 }


ibmSystempTrapUEFanLossOfRedundancy TRAP-TYPE
   ENTERPRISE     ibmSystemMIB
   VARIABLES    {
      ibmSystempTrapUEFanLossOfRedundancyProviderName,
      ibmSystempTrapUEFanLossOfRedundancyEventID,
      ibmSystempTrapUEFanLossOfRedundancyAME,
      ibmSystempTrapUEFanLossOfRedundancySeverity,
      ibmSystempTrapUEFanLossOfRedundancyDescription,
      ibmSystempTrapUEFanLossOfRedundancyTimeStamp
   }
   DESCRIPTION    "A System p event has occurred"
-- REFERENCE      "POWER_UEFanLossOfRedundancyEventIndication"
::= 485

ibmSystempTrapUEFanLossOfRedundancyBindings OBJECT IDENTIFIER ::= { ibmSystemTrap 485 }

ibmSystempTrapUEFanLossOfRedundancyProviderName OBJECT-TYPE
   SYNTAX         String
   ACCESS         read-only
   STATUS         mandatory
   DESCRIPTION    "The name of the CIM Provider that monitors this device"
-- REFERENCE      "POWER_UEFanLossOfRedundancyEventIndication.ProviderName"
::= { ibmSystempTrapUEFanLossOfRedundancyBindings 1 }

ibmSystempTrapUEFanLossOfRedundancyEventID OBJECT-TYPE
   SYNTAX         String
   ACCESS         read-only
   STATUS         mandatory
   DESCRIPTION    "A unique EventID that identifies this trap" 
-- REFERENCE      "POWER_UEFanLossOfRedundancyEventIndication.EventID"
::= { ibmSystempTrapUEFanLossOfRedundancyBindings 2 }

ibmSystempTrapUEFanLossOfRedundancyAME OBJECT-TYPE
   SYNTAX         String
   ACCESS         read-only
   STATUS         mandatory
   DESCRIPTION    "A unique string that identifies the monitored device"
-- REFERENCE      "POWER_UEFanLossOfRedundancyEventIndication.AlertingManagedElement"
::= { ibmSystempTrapUEFanLossOfRedundancyBindings 3 }

ibmSystempTrapUEFanLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEFanLossOfRedundancyEventIndication.Severity"
::= { ibmSystempTrapUEFanLossOfRedundancyBindings 4 }

ibmSystempTrapUEFanLossOfRedundancyDescription OBJECT-TYPE
   SYNTAX         SnmpAdminString
   ACCESS         read-only
   STATUS         mandatory
   DESCRIPTION    "The Event text of the trap"
-- REFERENCE      "POWER_UEFanLossOfRedundancyEventIndication.Description"
::= { ibmSystempTrapUEFanLossOfRedundancyBindings 5 }

ibmSystempTrapUEFanLossOfRedundancyTimeStamp OBJECT-TYPE
   SYNTAX         Datetime
   ACCESS         read-only
   STATUS         mandatory
   DESCRIPTION    "The time that the trap occurred"
-- REFERENCE      "POWER_UEFanLossOfRedundancyEventIndication.TimeStamp"
::= { ibmSystempTrapUEFanLossOfRedundancyBindings 6 }


ibmSystempTrapUEFanLossOfRedundAndPerf TRAP-TYPE
   ENTERPRISE     ibmSystemMIB
   VARIABLES    {
      ibmSystempTrapUEFanLossOfRedundAndPerfProviderName,
      ibmSystempTrapUEFanLossOfRedundAndPerfEventID,
      ibmSystempTrapUEFanLossOfRedundAndPerfAME,
      ibmSystempTrapUEFanLossOfRedundAndPerfSeverity,
      ibmSystempTrapUEFanLossOfRedundAndPerfDescription,
      ibmSystempTrapUEFanLossOfRedundAndPerfTimeStamp
   }
   DESCRIPTION    "A System p event has occurred"
-- REFERENCE      "POWER_UEFanLossOfRedundAndPerfEventIndication"
::= 486

ibmSystempTrapUEFanLossOfRedundAndPerfBindings OBJECT IDENTIFIER ::= { ibmSystemTrap 486 }

ibmSystempTrapUEFanLossOfRedundAndPerfProviderName OBJECT-TYPE
   SYNTAX         String
   ACCESS         read-only
   STATUS         mandatory
   DESCRIPTION    "The name of the CIM Provider that monitors this device"
-- REFERENCE      "POWER_UEFanLossOfRedundAndPerfEventIndication.ProviderName"
::= { ibmSystempTrapUEFanLossOfRedundAndPerfBindings 1 }

ibmSystempTrapUEFanLossOfRedundAndPerfEventID OBJECT-TYPE
   SYNTAX         String
   ACCESS         read-only
   STATUS         mandatory
   DESCRIPTION    "A unique EventID that identifies this trap" 
-- REFERENCE      "POWER_UEFanLossOfRedundAndPerfEventIndication.EventID"
::= { ibmSystempTrapUEFanLossOfRedundAndPerfBindings 2 }

ibmSystempTrapUEFanLossOfRedundAndPerfAME OBJECT-TYPE
   SYNTAX         String
   ACCESS         read-only
   STATUS         mandatory
   DESCRIPTION    "A unique string that identifies the monitored device"
-- REFERENCE      "POWER_UEFanLossOfRedundAndPerfEventIndication.AlertingManagedElement"
::= { ibmSystempTrapUEFanLossOfRedundAndPerfBindings 3 }

ibmSystempTrapUEFanLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEFanLossOfRedundAndPerfEventIndication.Severity"
::= { ibmSystempTrapUEFanLossOfRedundAndPerfBindings 4 }

ibmSystempTrapUEFanLossOfRedundAndPerfDescription OBJECT-TYPE
   SYNTAX         SnmpAdminString
   ACCESS         read-only
   STATUS         mandatory
   DESCRIPTION    "The Event text of the trap"
-- REFERENCE      "POWER_UEFanLossOfRedundAndPerfEventIndication.Description"
::= { ibmSystempTrapUEFanLossOfRedundAndPerfBindings 5 }

ibmSystempTrapUEFanLossOfRedundAndPerfTimeStamp OBJECT-TYPE
   SYNTAX         Datetime
   ACCESS         read-only
   STATUS         mandatory
   DESCRIPTION    "The time that the trap occurred"
-- REFERENCE      "POWER_UEFanLossOfRedundAndPerfEventIndication.TimeStamp"
::= { ibmSystempTrapUEFanLossOfRedundAndPerfBindings 6 }


ibmSystempTrapUEFanLossOfFunction TRAP-TYPE
   ENTERPRISE     ibmSystemMIB
   VARIABLES    {
      ibmSystempTrapUEFanLossOfFunctionProviderName,
      ibmSystempTrapUEFanLossOfFunctionEventID,
      ibmSystempTrapUEFanLossOfFunctionAME,
      ibmSystempTrapUEFanLossOfFunctionSeverity,
      ibmSystempTrapUEFanLossOfFunctionDescription,
      ibmSystempTrapUEFanLossOfFunctionTimeStamp
   }
   DESCRIPTION    "A System p event has occurred"
-- REFERENCE      "POWER_UEFanLossOfFunctionEventIndication"
::= 487

ibmSystempTrapUEFanLossOfFunctionBindings OBJECT IDENTIFIER ::= { ibmSystemTrap 487 }

ibmSystempTrapUEFanLossOfFunctionProviderName OBJECT-TYPE
   SYNTAX         String
   ACCESS         read-only
   STATUS         mandatory
   DESCRIPTION    "The name of the CIM Provider that monitors this device"
-- REFERENCE      "POWER_UEFanLossOfFunctionEventIndication.ProviderName"
::= { ibmSystempTrapUEFanLossOfFunctionBindings 1 }

ibmSystempTrapUEFanLossOfFunctionEventID OBJECT-TYPE
   SYNTAX         String
   ACCESS         read-only
   STATUS         mandatory
   DESCRIPTION    "A unique EventID that identifies this trap" 
-- REFERENCE      "POWER_UEFanLossOfFunctionEventIndication.EventID"
::= { ibmSystempTrapUEFanLossOfFunctionBindings 2 }

ibmSystempTrapUEFanLossOfFunctionAME OBJECT-TYPE
   SYNTAX         String
   ACCESS         read-only
   STATUS         mandatory
   DESCRIPTION    "A unique string that identifies the monitored device"
-- REFERENCE      "POWER_UEFanLossOfFunctionEventIndication.AlertingManagedElement"
::= { ibmSystempTrapUEFanLossOfFunctionBindings 3 }

ibmSystempTrapUEFanLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEFanLossOfFunctionEventIndication.Severity"
::= { ibmSystempTrapUEFanLossOfFunctionBindings 4 }

ibmSystempTrapUEFanLossOfFunctionDescription OBJECT-TYPE
   SYNTAX         SnmpAdminString
   ACCESS         read-only
   STATUS         mandatory
   DESCRIPTION    "The Event text of the trap"
-- REFERENCE      "POWER_UEFanLossOfFunctionEventIndication.Description"
::= { ibmSystempTrapUEFanLossOfFunctionBindings 5 }

ibmSystempTrapUEFanLossOfFunctionTimeStamp OBJECT-TYPE
   SYNTAX         Datetime
   ACCESS         read-only
   STATUS         mandatory
   DESCRIPTION    "The time that the trap occurred"
-- REFERENCE      "POWER_UEFanLossOfFunctionEventIndication.TimeStamp"
::= { ibmSystempTrapUEFanLossOfFunctionBindings 6 }


ibmSystempTrapUEFanUnrecoverableError TRAP-TYPE
   ENTERPRISE     ibmSystemMIB
   VARIABLES    {
      ibmSystempTrapUEFanUnrecoverableErrorProviderName,
      ibmSystempTrapUEFanUnrecoverableErrorEventID,
      ibmSystempTrapUEFanUnrecoverableErrorAME,
      ibmSystempTrapUEFanUnrecoverableErrorSeverity,
      ibmSystempTrapUEFanUnrecoverableErrorDescription,
      ibmSystempTrapUEFanUnrecoverableErrorTimeStamp
   }
   DESCRIPTION    "A System p event has occurred"
-- REFERENCE      "POWER_UEFanUnrecoverableErrorEventIndication"
::= 488

ibmSystempTrapUEFanUnrecoverableErrorBindings OBJECT IDENTIFIER ::= { ibmSystemTrap 488 }

ibmSystempTrapUEFanUnrecoverableErrorProviderName OBJECT-TYPE
   SYNTAX         String
   ACCESS         read-only
   STATUS         mandatory
   DESCRIPTION    "The name of the CIM Provider that monitors this device"
-- REFERENCE      "POWER_UEFanUnrecoverableErrorEventIndication.ProviderName"
::= { ibmSystempTrapUEFanUnrecoverableErrorBindings 1 }

ibmSystempTrapUEFanUnrecoverableErrorEventID OBJECT-TYPE
   SYNTAX         String
   ACCESS         read-only
   STATUS         mandatory
   DESCRIPTION    "A unique EventID that identifies this trap" 
-- REFERENCE      "POWER_UEFanUnrecoverableErrorEventIndication.EventID"
::= { ibmSystempTrapUEFanUnrecoverableErrorBindings 2 }

ibmSystempTrapUEFanUnrecoverableErrorAME OBJECT-TYPE
   SYNTAX         String
   ACCESS         read-only
   STATUS         mandatory
   DESCRIPTION    "A unique string that identifies the monitored device"
-- REFERENCE      "POWER_UEFanUnrecoverableErrorEventIndication.AlertingManagedElement"
::= { ibmSystempTrapUEFanUnrecoverableErrorBindings 3 }

ibmSystempTrapUEFanUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEFanUnrecoverableErrorEventIndication.Severity"
::= { ibmSystempTrapUEFanUnrecoverableErrorBindings 4 }

ibmSystempTrapUEFanUnrecoverableErrorDescription OBJECT-TYPE
   SYNTAX         SnmpAdminString
   ACCESS         read-only
   STATUS         mandatory
   DESCRIPTION    "The Event text of the trap"
-- REFERENCE      "POWER_UEFanUnrecoverableErrorEventIndication.Description"
::= { ibmSystempTrapUEFanUnrecoverableErrorBindings 5 }

ibmSystempTrapUEFanUnrecoverableErrorTimeStamp OBJECT-TYPE
   SYNTAX         Datetime
   ACCESS         read-only
   STATUS         mandatory
   DESCRIPTION    "The time that the trap occurred"
-- REFERENCE      "POWER_UEFanUnrecoverableErrorEventIndication.TimeStamp"
::= { ibmSystempTrapUEFanUnrecoverableErrorBindings 6 }


ibmSystempTrapDTOtherSubsystemDiagnostics TRAP-TYPE
   ENTERPRISE     ibmSystemMIB
   VARIABLES    {
      ibmSystempTrapDTOtherSubsystemDiagnosticsProviderName,
      ibmSystempTrapDTOtherSubsystemDiagnosticsEventID,
      ibmSystempTrapDTOtherSubsystemDiagnosticsAME,
      ibmSystempTrapDTOtherSubsystemDiagnosticsSeverity,
      ibmSystempTrapDTOtherSubsystemDiagnosticsDescription,
      ibmSystempTrapDTOtherSubsystemDiagnosticsTimeStamp
   }
   DESCRIPTION    "A System p event has occurred"
-- REFERENCE      "POWER_DTOtherSubsystemDiagnosticsEventIndication"
::= 489

ibmSystempTrapDTOtherSubsystemDiagnosticsBindings OBJECT IDENTIFIER ::= { ibmSystemTrap 489 }

ibmSystempTrapDTOtherSubsystemDiagnosticsProviderName OBJECT-TYPE
   SYNTAX         String
   ACCESS         read-only
   STATUS         mandatory
   DESCRIPTION    "The name of the CIM Provider that monitors this device"
-- REFERENCE      "POWER_DTOtherSubsystemDiagnosticsEventIndication.ProviderName"
::= { ibmSystempTrapDTOtherSubsystemDiagnosticsBindings 1 }

ibmSystempTrapDTOtherSubsystemDiagnosticsEventID OBJECT-TYPE
   SYNTAX         String
   ACCESS         read-only
   STATUS         mandatory
   DESCRIPTION    "A unique EventID that identifies this trap" 
-- REFERENCE      "POWER_DTOtherSubsystemDiagnosticsEventIndication.EventID"
::= { ibmSystempTrapDTOtherSubsystemDiagnosticsBindings 2 }

ibmSystempTrapDTOtherSubsystemDiagnosticsAME OBJECT-TYPE
   SYNTAX         String
   ACCESS         read-only
   STATUS         mandatory
   DESCRIPTION    "A unique string that identifies the monitored device"
-- REFERENCE      "POWER_DTOtherSubsystemDiagnosticsEventIndication.AlertingManagedElement"
::= { ibmSystempTrapDTOtherSubsystemDiagnosticsBindings 3 }

ibmSystempTrapDTOtherSubsystemDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTOtherSubsystemDiagnosticsEventIndication.Severity"
::= { ibmSystempTrapDTOtherSubsystemDiagnosticsBindings 4 }

ibmSystempTrapDTOtherSubsystemDiagnosticsDescription OBJECT-TYPE
   SYNTAX         SnmpAdminString
   ACCESS         read-only
   STATUS         mandatory
   DESCRIPTION    "The Event text of the trap"
-- REFERENCE      "POWER_DTOtherSubsystemDiagnosticsEventIndication.Description"
::= { ibmSystempTrapDTOtherSubsystemDiagnosticsBindings 5 }

ibmSystempTrapDTOtherSubsystemDiagnosticsTimeStamp OBJECT-TYPE
   SYNTAX         Datetime
   ACCESS         read-only
   STATUS         mandatory
   DESCRIPTION    "The time that the trap occurred"
-- REFERENCE      "POWER_DTOtherSubsystemDiagnosticsEventIndication.TimeStamp"
::= { ibmSystempTrapDTOtherSubsystemDiagnosticsBindings 6 }


ibmSystempTrapPFOtherSubsystemDegradPerf TRAP-TYPE
   ENTERPRISE     ibmSystemMIB
   VARIABLES    {
      ibmSystempTrapPFOtherSubsystemDegradPerfProviderName,
      ibmSystempTrapPFOtherSubsystemDegradPerfEventID,
      ibmSystempTrapPFOtherSubsystemDegradPerfAME,
      ibmSystempTrapPFOtherSubsystemDegradPerfSeverity,
      ibmSystempTrapPFOtherSubsystemDegradPerfDescription,
      ibmSystempTrapPFOtherSubsystemDegradPerfTimeStamp
   }
   DESCRIPTION    "A System p event has occurred"
-- REFERENCE      "POWER_PFOtherSubsystemDegradPerfEventIndication"
::= 490

ibmSystempTrapPFOtherSubsystemDegradPerfBindings OBJECT IDENTIFIER ::= { ibmSystemTrap 490 }

ibmSystempTrapPFOtherSubsystemDegradPerfProviderName OBJECT-TYPE
   SYNTAX         String
   ACCESS         read-only
   STATUS         mandatory
   DESCRIPTION    "The name of the CIM Provider that monitors this device"
-- REFERENCE      "POWER_PFOtherSubsystemDegradPerfEventIndication.ProviderName"
::= { ibmSystempTrapPFOtherSubsystemDegradPerfBindings 1 }

ibmSystempTrapPFOtherSubsystemDegradPerfEventID OBJECT-TYPE
   SYNTAX         String
   ACCESS         read-only
   STATUS         mandatory
   DESCRIPTION    "A unique EventID that identifies this trap" 
-- REFERENCE      "POWER_PFOtherSubsystemDegradPerfEventIndication.EventID"
::= { ibmSystempTrapPFOtherSubsystemDegradPerfBindings 2 }

ibmSystempTrapPFOtherSubsystemDegradPerfAME OBJECT-TYPE
   SYNTAX         String
   ACCESS         read-only
   STATUS         mandatory
   DESCRIPTION    "A unique string that identifies the monitored device"
-- REFERENCE      "POWER_PFOtherSubsystemDegradPerfEventIndication.AlertingManagedElement"
::= { ibmSystempTrapPFOtherSubsystemDegradPerfBindings 3 }

ibmSystempTrapPFOtherSubsystemDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFOtherSubsystemDegradPerfEventIndication.Severity"
::= { ibmSystempTrapPFOtherSubsystemDegradPerfBindings 4 }

ibmSystempTrapPFOtherSubsystemDegradPerfDescription OBJECT-TYPE
   SYNTAX         SnmpAdminString
   ACCESS         read-only
   STATUS         mandatory
   DESCRIPTION    "The Event text of the trap"
-- REFERENCE      "POWER_PFOtherSubsystemDegradPerfEventIndication.Description"
::= { ibmSystempTrapPFOtherSubsystemDegradPerfBindings 5 }

ibmSystempTrapPFOtherSubsystemDegradPerfTimeStamp OBJECT-TYPE
   SYNTAX         Datetime
   ACCESS         read-only
   STATUS         mandatory
   DESCRIPTION    "The time that the trap occurred"
-- REFERENCE      "POWER_PFOtherSubsystemDegradPerfEventIndication.TimeStamp"
::= { ibmSystempTrapPFOtherSubsystemDegradPerfBindings 6 }


ibmSystempTrapPFOtherSubsystemCorrectAftIPL TRAP-TYPE
   ENTERPRISE     ibmSystemMIB
   VARIABLES    {
      ibmSystempTrapPFOtherSubsystemCorrectAftIPLProviderName,
      ibmSystempTrapPFOtherSubsystemCorrectAftIPLEventID,
      ibmSystempTrapPFOtherSubsystemCorrectAftIPLAME,
      ibmSystempTrapPFOtherSubsystemCorrectAftIPLSeverity,
      ibmSystempTrapPFOtherSubsystemCorrectAftIPLDescription,
      ibmSystempTrapPFOtherSubsystemCorrectAftIPLTimeStamp
   }
   DESCRIPTION    "A System p event has occurred"
-- REFERENCE      "POWER_PFOtherSubsystemCorrectAftIPLEventIndication"
::= 491

ibmSystempTrapPFOtherSubsystemCorrectAftIPLBindings OBJECT IDENTIFIER ::= { ibmSystemTrap 491 }

ibmSystempTrapPFOtherSubsystemCorrectAftIPLProviderName OBJECT-TYPE
   SYNTAX         String
   ACCESS         read-only
   STATUS         mandatory
   DESCRIPTION    "The name of the CIM Provider that monitors this device"
-- REFERENCE      "POWER_PFOtherSubsystemCorrectAftIPLEventIndication.ProviderName"
::= { ibmSystempTrapPFOtherSubsystemCorrectAftIPLBindings 1 }

ibmSystempTrapPFOtherSubsystemCorrectAftIPLEventID OBJECT-TYPE
   SYNTAX         String
   ACCESS         read-only
   STATUS         mandatory
   DESCRIPTION    "A unique EventID that identifies this trap" 
-- REFERENCE      "POWER_PFOtherSubsystemCorrectAftIPLEventIndication.EventID"
::= { ibmSystempTrapPFOtherSubsystemCorrectAftIPLBindings 2 }

ibmSystempTrapPFOtherSubsystemCorrectAftIPLAME OBJECT-TYPE
   SYNTAX         String
   ACCESS         read-only
   STATUS         mandatory
   DESCRIPTION    "A unique string that identifies the monitored device"
-- REFERENCE      "POWER_PFOtherSubsystemCorrectAftIPLEventIndication.AlertingManagedElement"
::= { ibmSystempTrapPFOtherSubsystemCorrectAftIPLBindings 3 }

ibmSystempTrapPFOtherSubsystemCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFOtherSubsystemCorrectAftIPLEventIndication.Severity"
::= { ibmSystempTrapPFOtherSubsystemCorrectAftIPLBindings 4 }

ibmSystempTrapPFOtherSubsystemCorrectAftIPLDescription OBJECT-TYPE
   SYNTAX         SnmpAdminString
   ACCESS         read-only
   STATUS         mandatory
   DESCRIPTION    "The Event text of the trap"
-- REFERENCE      "POWER_PFOtherSubsystemCorrectAftIPLEventIndication.Description"
::= { ibmSystempTrapPFOtherSubsystemCorrectAftIPLBindings 5 }

ibmSystempTrapPFOtherSubsystemCorrectAftIPLTimeStamp OBJECT-TYPE
   SYNTAX         Datetime
   ACCESS         read-only
   STATUS         mandatory
   DESCRIPTION    "The time that the trap occurred"
-- REFERENCE      "POWER_PFOtherSubsystemCorrectAftIPLEventIndication.TimeStamp"
::= { ibmSystempTrapPFOtherSubsystemCorrectAftIPLBindings 6 }


ibmSystempTrapPFOtherSubsystemCorrectAftIPLPerf TRAP-TYPE
   ENTERPRISE     ibmSystemMIB
   VARIABLES    {
      ibmSystempTrapPFOtherSubsystemCorrectAftIPLPerfProviderName,
      ibmSystempTrapPFOtherSubsystemCorrectAftIPLPerfEventID,
      ibmSystempTrapPFOtherSubsystemCorrectAftIPLPerfAME,
      ibmSystempTrapPFOtherSubsystemCorrectAftIPLPerfSeverity,
      ibmSystempTrapPFOtherSubsystemCorrectAftIPLPerfDescription,
      ibmSystempTrapPFOtherSubsystemCorrectAftIPLPerfTimeStamp
   }
   DESCRIPTION    "A System p event has occurred"
-- REFERENCE      "POWER_PFOtherSubsystemCorrectAftIPLPerfEventIndication"
::= 492

ibmSystempTrapPFOtherSubsystemCorrectAftIPLPerfBindings OBJECT IDENTIFIER ::= { ibmSystemTrap 492 }

ibmSystempTrapPFOtherSubsystemCorrectAftIPLPerfProviderName OBJECT-TYPE
   SYNTAX         String
   ACCESS         read-only
   STATUS         mandatory
   DESCRIPTION    "The name of the CIM Provider that monitors this device"
-- REFERENCE      "POWER_PFOtherSubsystemCorrectAftIPLPerfEventIndication.ProviderName"
::= { ibmSystempTrapPFOtherSubsystemCorrectAftIPLPerfBindings 1 }

ibmSystempTrapPFOtherSubsystemCorrectAftIPLPerfEventID OBJECT-TYPE
   SYNTAX         String
   ACCESS         read-only
   STATUS         mandatory
   DESCRIPTION    "A unique EventID that identifies this trap" 
-- REFERENCE      "POWER_PFOtherSubsystemCorrectAftIPLPerfEventIndication.EventID"
::= { ibmSystempTrapPFOtherSubsystemCorrectAftIPLPerfBindings 2 }

ibmSystempTrapPFOtherSubsystemCorrectAftIPLPerfAME OBJECT-TYPE
   SYNTAX         String
   ACCESS         read-only
   STATUS         mandatory
   DESCRIPTION    "A unique string that identifies the monitored device"
-- REFERENCE      "POWER_PFOtherSubsystemCorrectAftIPLPerfEventIndication.AlertingManagedElement"
::= { ibmSystempTrapPFOtherSubsystemCorrectAftIPLPerfBindings 3 }

ibmSystempTrapPFOtherSubsystemCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFOtherSubsystemCorrectAftIPLPerfEventIndication.Severity"
::= { ibmSystempTrapPFOtherSubsystemCorrectAftIPLPerfBindings 4 }

ibmSystempTrapPFOtherSubsystemCorrectAftIPLPerfDescription OBJECT-TYPE
   SYNTAX         SnmpAdminString
   ACCESS         read-only
   STATUS         mandatory
   DESCRIPTION    "The Event text of the trap"
-- REFERENCE      "POWER_PFOtherSubsystemCorrectAftIPLPerfEventIndication.Description"
::= { ibmSystempTrapPFOtherSubsystemCorrectAftIPLPerfBindings 5 }

ibmSystempTrapPFOtherSubsystemCorrectAftIPLPerfTimeStamp OBJECT-TYPE
   SYNTAX         Datetime
   ACCESS         read-only
   STATUS         mandatory
   DESCRIPTION    "The time that the trap occurred"
-- REFERENCE      "POWER_PFOtherSubsystemCorrectAftIPLPerfEventIndication.TimeStamp"
::= { ibmSystempTrapPFOtherSubsystemCorrectAftIPLPerfBindings 6 }


ibmSystempTrapPFOtherSubsystemLossOfRedundancy TRAP-TYPE
   ENTERPRISE     ibmSystemMIB
   VARIABLES    {
      ibmSystempTrapPFOtherSubsystemLossOfRedundancyProviderName,
      ibmSystempTrapPFOtherSubsystemLossOfRedundancyEventID,
      ibmSystempTrapPFOtherSubsystemLossOfRedundancyAME,
      ibmSystempTrapPFOtherSubsystemLossOfRedundancySeverity,
      ibmSystempTrapPFOtherSubsystemLossOfRedundancyDescription,
      ibmSystempTrapPFOtherSubsystemLossOfRedundancyTimeStamp
   }
   DESCRIPTION    "A System p event has occurred"
-- REFERENCE      "POWER_PFOtherSubsystemLossOfRedundancyEventIndication"
::= 493

ibmSystempTrapPFOtherSubsystemLossOfRedundancyBindings OBJECT IDENTIFIER ::= { ibmSystemTrap 493 }

ibmSystempTrapPFOtherSubsystemLossOfRedundancyProviderName OBJECT-TYPE
   SYNTAX         String
   ACCESS         read-only
   STATUS         mandatory
   DESCRIPTION    "The name of the CIM Provider that monitors this device"
-- REFERENCE      "POWER_PFOtherSubsystemLossOfRedundancyEventIndication.ProviderName"
::= { ibmSystempTrapPFOtherSubsystemLossOfRedundancyBindings 1 }

ibmSystempTrapPFOtherSubsystemLossOfRedundancyEventID OBJECT-TYPE
   SYNTAX         String
   ACCESS         read-only
   STATUS         mandatory
   DESCRIPTION    "A unique EventID that identifies this trap" 
-- REFERENCE      "POWER_PFOtherSubsystemLossOfRedundancyEventIndication.EventID"
::= { ibmSystempTrapPFOtherSubsystemLossOfRedundancyBindings 2 }

ibmSystempTrapPFOtherSubsystemLossOfRedundancyAME OBJECT-TYPE
   SYNTAX         String
   ACCESS         read-only
   STATUS         mandatory
   DESCRIPTION    "A unique string that identifies the monitored device"
-- REFERENCE      "POWER_PFOtherSubsystemLossOfRedundancyEventIndication.AlertingManagedElement"
::= { ibmSystempTrapPFOtherSubsystemLossOfRedundancyBindings 3 }

ibmSystempTrapPFOtherSubsystemLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFOtherSubsystemLossOfRedundancyEventIndication.Severity"
::= { ibmSystempTrapPFOtherSubsystemLossOfRedundancyBindings 4 }

ibmSystempTrapPFOtherSubsystemLossOfRedundancyDescription OBJECT-TYPE
   SYNTAX         SnmpAdminString
   ACCESS         read-only
   STATUS         mandatory
   DESCRIPTION    "The Event text of the trap"
-- REFERENCE      "POWER_PFOtherSubsystemLossOfRedundancyEventIndication.Description"
::= { ibmSystempTrapPFOtherSubsystemLossOfRedundancyBindings 5 }

ibmSystempTrapPFOtherSubsystemLossOfRedundancyTimeStamp OBJECT-TYPE
   SYNTAX         Datetime
   ACCESS         read-only
   STATUS         mandatory
   DESCRIPTION    "The time that the trap occurred"
-- REFERENCE      "POWER_PFOtherSubsystemLossOfRedundancyEventIndication.TimeStamp"
::= { ibmSystempTrapPFOtherSubsystemLossOfRedundancyBindings 6 }


ibmSystempTrapPFOtherSubsystemPredictiveError TRAP-TYPE
   ENTERPRISE     ibmSystemMIB
   VARIABLES    {
      ibmSystempTrapPFOtherSubsystemPredictiveErrorProviderName,
      ibmSystempTrapPFOtherSubsystemPredictiveErrorEventID,
      ibmSystempTrapPFOtherSubsystemPredictiveErrorAME,
      ibmSystempTrapPFOtherSubsystemPredictiveErrorSeverity,
      ibmSystempTrapPFOtherSubsystemPredictiveErrorDescription,
      ibmSystempTrapPFOtherSubsystemPredictiveErrorTimeStamp
   }
   DESCRIPTION    "A System p event has occurred"
-- REFERENCE      "POWER_PFOtherSubsystemPredictiveErrorEventIndication"
::= 494

ibmSystempTrapPFOtherSubsystemPredictiveErrorBindings OBJECT IDENTIFIER ::= { ibmSystemTrap 494 }

ibmSystempTrapPFOtherSubsystemPredictiveErrorProviderName OBJECT-TYPE
   SYNTAX         String
   ACCESS         read-only
   STATUS         mandatory
   DESCRIPTION    "The name of the CIM Provider that monitors this device"
-- REFERENCE      "POWER_PFOtherSubsystemPredictiveErrorEventIndication.ProviderName"
::= { ibmSystempTrapPFOtherSubsystemPredictiveErrorBindings 1 }

ibmSystempTrapPFOtherSubsystemPredictiveErrorEventID OBJECT-TYPE
   SYNTAX         String
   ACCESS         read-only
   STATUS         mandatory
   DESCRIPTION    "A unique EventID that identifies this trap" 
-- REFERENCE      "POWER_PFOtherSubsystemPredictiveErrorEventIndication.EventID"
::= { ibmSystempTrapPFOtherSubsystemPredictiveErrorBindings 2 }

ibmSystempTrapPFOtherSubsystemPredictiveErrorAME OBJECT-TYPE
   SYNTAX         String
   ACCESS         read-only
   STATUS         mandatory
   DESCRIPTION    "A unique string that identifies the monitored device"
-- REFERENCE      "POWER_PFOtherSubsystemPredictiveErrorEventIndication.AlertingManagedElement"
::= { ibmSystempTrapPFOtherSubsystemPredictiveErrorBindings 3 }

ibmSystempTrapPFOtherSubsystemPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFOtherSubsystemPredictiveErrorEventIndication.Severity"
::= { ibmSystempTrapPFOtherSubsystemPredictiveErrorBindings 4 }

ibmSystempTrapPFOtherSubsystemPredictiveErrorDescription OBJECT-TYPE
   SYNTAX         SnmpAdminString
   ACCESS         read-only
   STATUS         mandatory
   DESCRIPTION    "The Event text of the trap"
-- REFERENCE      "POWER_PFOtherSubsystemPredictiveErrorEventIndication.Description"
::= { ibmSystempTrapPFOtherSubsystemPredictiveErrorBindings 5 }

ibmSystempTrapPFOtherSubsystemPredictiveErrorTimeStamp OBJECT-TYPE
   SYNTAX         Datetime
   ACCESS         read-only
   STATUS         mandatory
   DESCRIPTION    "The time that the trap occurred"
-- REFERENCE      "POWER_PFOtherSubsystemPredictiveErrorEventIndication.TimeStamp"
::= { ibmSystempTrapPFOtherSubsystemPredictiveErrorBindings 6 }


ibmSystempTrapUEOtherSubsystemDegradPerf TRAP-TYPE
   ENTERPRISE     ibmSystemMIB
   VARIABLES    {
      ibmSystempTrapUEOtherSubsystemDegradPerfProviderName,
      ibmSystempTrapUEOtherSubsystemDegradPerfEventID,
      ibmSystempTrapUEOtherSubsystemDegradPerfAME,
      ibmSystempTrapUEOtherSubsystemDegradPerfSeverity,
      ibmSystempTrapUEOtherSubsystemDegradPerfDescription,
      ibmSystempTrapUEOtherSubsystemDegradPerfTimeStamp
   }
   DESCRIPTION    "A System p event has occurred"
-- REFERENCE      "POWER_UEOtherSubsystemDegradPerfEventIndication"
::= 495

ibmSystempTrapUEOtherSubsystemDegradPerfBindings OBJECT IDENTIFIER ::= { ibmSystemTrap 495 }

ibmSystempTrapUEOtherSubsystemDegradPerfProviderName OBJECT-TYPE
   SYNTAX         String
   ACCESS         read-only
   STATUS         mandatory
   DESCRIPTION    "The name of the CIM Provider that monitors this device"
-- REFERENCE      "POWER_UEOtherSubsystemDegradPerfEventIndication.ProviderName"
::= { ibmSystempTrapUEOtherSubsystemDegradPerfBindings 1 }

ibmSystempTrapUEOtherSubsystemDegradPerfEventID OBJECT-TYPE
   SYNTAX         String
   ACCESS         read-only
   STATUS         mandatory
   DESCRIPTION    "A unique EventID that identifies this trap" 
-- REFERENCE      "POWER_UEOtherSubsystemDegradPerfEventIndication.EventID"
::= { ibmSystempTrapUEOtherSubsystemDegradPerfBindings 2 }

ibmSystempTrapUEOtherSubsystemDegradPerfAME OBJECT-TYPE
   SYNTAX         String
   ACCESS         read-only
   STATUS         mandatory
   DESCRIPTION    "A unique string that identifies the monitored device"
-- REFERENCE      "POWER_UEOtherSubsystemDegradPerfEventIndication.AlertingManagedElement"
::= { ibmSystempTrapUEOtherSubsystemDegradPerfBindings 3 }

ibmSystempTrapUEOtherSubsystemDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEOtherSubsystemDegradPerfEventIndication.Severity"
::= { ibmSystempTrapUEOtherSubsystemDegradPerfBindings 4 }

ibmSystempTrapUEOtherSubsystemDegradPerfDescription OBJECT-TYPE
   SYNTAX         SnmpAdminString
   ACCESS         read-only
   STATUS         mandatory
   DESCRIPTION    "The Event text of the trap"
-- REFERENCE      "POWER_UEOtherSubsystemDegradPerfEventIndication.Description"
::= { ibmSystempTrapUEOtherSubsystemDegradPerfBindings 5 }

ibmSystempTrapUEOtherSubsystemDegradPerfTimeStamp OBJECT-TYPE
   SYNTAX         Datetime
   ACCESS         read-only
   STATUS         mandatory
   DESCRIPTION    "The time that the trap occurred"
-- REFERENCE      "POWER_UEOtherSubsystemDegradPerfEventIndication.TimeStamp"
::= { ibmSystempTrapUEOtherSubsystemDegradPerfBindings 6 }


ibmSystempTrapUEOtherSubsystemLossOfRedundancy TRAP-TYPE
   ENTERPRISE     ibmSystemMIB
   VARIABLES    {
      ibmSystempTrapUEOtherSubsystemLossOfRedundancyProviderName,
      ibmSystempTrapUEOtherSubsystemLossOfRedundancyEventID,
      ibmSystempTrapUEOtherSubsystemLossOfRedundancyAME,
      ibmSystempTrapUEOtherSubsystemLossOfRedundancySeverity,
      ibmSystempTrapUEOtherSubsystemLossOfRedundancyDescription,
      ibmSystempTrapUEOtherSubsystemLossOfRedundancyTimeStamp
   }
   DESCRIPTION    "A System p event has occurred"
-- REFERENCE      "POWER_UEOtherSubsystemLossOfRedundancyEventIndication"
::= 496

ibmSystempTrapUEOtherSubsystemLossOfRedundancyBindings OBJECT IDENTIFIER ::= { ibmSystemTrap 496 }

ibmSystempTrapUEOtherSubsystemLossOfRedundancyProviderName OBJECT-TYPE
   SYNTAX         String
   ACCESS         read-only
   STATUS         mandatory
   DESCRIPTION    "The name of the CIM Provider that monitors this device"
-- REFERENCE      "POWER_UEOtherSubsystemLossOfRedundancyEventIndication.ProviderName"
::= { ibmSystempTrapUEOtherSubsystemLossOfRedundancyBindings 1 }

ibmSystempTrapUEOtherSubsystemLossOfRedundancyEventID OBJECT-TYPE
   SYNTAX         String
   ACCESS         read-only
   STATUS         mandatory
   DESCRIPTION    "A unique EventID that identifies this trap" 
-- REFERENCE      "POWER_UEOtherSubsystemLossOfRedundancyEventIndication.EventID"
::= { ibmSystempTrapUEOtherSubsystemLossOfRedundancyBindings 2 }

ibmSystempTrapUEOtherSubsystemLossOfRedundancyAME OBJECT-TYPE
   SYNTAX         String
   ACCESS         read-only
   STATUS         mandatory
   DESCRIPTION    "A unique string that identifies the monitored device"
-- REFERENCE      "POWER_UEOtherSubsystemLossOfRedundancyEventIndication.AlertingManagedElement"
::= { ibmSystempTrapUEOtherSubsystemLossOfRedundancyBindings 3 }

ibmSystempTrapUEOtherSubsystemLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEOtherSubsystemLossOfRedundancyEventIndication.Severity"
::= { ibmSystempTrapUEOtherSubsystemLossOfRedundancyBindings 4 }

ibmSystempTrapUEOtherSubsystemLossOfRedundancyDescription OBJECT-TYPE
   SYNTAX         SnmpAdminString
   ACCESS         read-only
   STATUS         mandatory
   DESCRIPTION    "The Event text of the trap"
-- REFERENCE      "POWER_UEOtherSubsystemLossOfRedundancyEventIndication.Description"
::= { ibmSystempTrapUEOtherSubsystemLossOfRedundancyBindings 5 }

ibmSystempTrapUEOtherSubsystemLossOfRedundancyTimeStamp OBJECT-TYPE
   SYNTAX         Datetime
   ACCESS         read-only
   STATUS         mandatory
   DESCRIPTION    "The time that the trap occurred"
-- REFERENCE      "POWER_UEOtherSubsystemLossOfRedundancyEventIndication.TimeStamp"
::= { ibmSystempTrapUEOtherSubsystemLossOfRedundancyBindings 6 }


ibmSystempTrapUEOtherSubsystemLossOfRedundAndPerf TRAP-TYPE
   ENTERPRISE     ibmSystemMIB
   VARIABLES    {
      ibmSystempTrapUEOtherSubsystemLossOfRedundAndPerfProviderName,
      ibmSystempTrapUEOtherSubsystemLossOfRedundAndPerfEventID,
      ibmSystempTrapUEOtherSubsystemLossOfRedundAndPerfAME,
      ibmSystempTrapUEOtherSubsystemLossOfRedundAndPerfSeverity,
      ibmSystempTrapUEOtherSubsystemLossOfRedundAndPerfDescription,
      ibmSystempTrapUEOtherSubsystemLossOfRedundAndPerfTimeStamp
   }
   DESCRIPTION    "A System p event has occurred"
-- REFERENCE      "POWER_UEOtherSubsystemLossOfRedundAndPerfEventIndication"
::= 497

ibmSystempTrapUEOtherSubsystemLossOfRedundAndPerfBindings OBJECT IDENTIFIER ::= { ibmSystemTrap 497 }

ibmSystempTrapUEOtherSubsystemLossOfRedundAndPerfProviderName OBJECT-TYPE
   SYNTAX         String
   ACCESS         read-only
   STATUS         mandatory
   DESCRIPTION    "The name of the CIM Provider that monitors this device"
-- REFERENCE      "POWER_UEOtherSubsystemLossOfRedundAndPerfEventIndication.ProviderName"
::= { ibmSystempTrapUEOtherSubsystemLossOfRedundAndPerfBindings 1 }

ibmSystempTrapUEOtherSubsystemLossOfRedundAndPerfEventID OBJECT-TYPE
   SYNTAX         String
   ACCESS         read-only
   STATUS         mandatory
   DESCRIPTION    "A unique EventID that identifies this trap" 
-- REFERENCE      "POWER_UEOtherSubsystemLossOfRedundAndPerfEventIndication.EventID"
::= { ibmSystempTrapUEOtherSubsystemLossOfRedundAndPerfBindings 2 }

ibmSystempTrapUEOtherSubsystemLossOfRedundAndPerfAME OBJECT-TYPE
   SYNTAX         String
   ACCESS         read-only
   STATUS         mandatory
   DESCRIPTION    "A unique string that identifies the monitored device"
-- REFERENCE      "POWER_UEOtherSubsystemLossOfRedundAndPerfEventIndication.AlertingManagedElement"
::= { ibmSystempTrapUEOtherSubsystemLossOfRedundAndPerfBindings 3 }

ibmSystempTrapUEOtherSubsystemLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEOtherSubsystemLossOfRedundAndPerfEventIndication.Severity"
::= { ibmSystempTrapUEOtherSubsystemLossOfRedundAndPerfBindings 4 }

ibmSystempTrapUEOtherSubsystemLossOfRedundAndPerfDescription OBJECT-TYPE
   SYNTAX         SnmpAdminString
   ACCESS         read-only
   STATUS         mandatory
   DESCRIPTION    "The Event text of the trap"
-- REFERENCE      "POWER_UEOtherSubsystemLossOfRedundAndPerfEventIndication.Description"
::= { ibmSystempTrapUEOtherSubsystemLossOfRedundAndPerfBindings 5 }

ibmSystempTrapUEOtherSubsystemLossOfRedundAndPerfTimeStamp OBJECT-TYPE
   SYNTAX         Datetime
   ACCESS         read-only
   STATUS         mandatory
   DESCRIPTION    "The time that the trap occurred"
-- REFERENCE      "POWER_UEOtherSubsystemLossOfRedundAndPerfEventIndication.TimeStamp"
::= { ibmSystempTrapUEOtherSubsystemLossOfRedundAndPerfBindings 6 }


ibmSystempTrapUEOtherSubsystemLossOfFunction TRAP-TYPE
   ENTERPRISE     ibmSystemMIB
   VARIABLES    {
      ibmSystempTrapUEOtherSubsystemLossOfFunctionProviderName,
      ibmSystempTrapUEOtherSubsystemLossOfFunctionEventID,
      ibmSystempTrapUEOtherSubsystemLossOfFunctionAME,
      ibmSystempTrapUEOtherSubsystemLossOfFunctionSeverity,
      ibmSystempTrapUEOtherSubsystemLossOfFunctionDescription,
      ibmSystempTrapUEOtherSubsystemLossOfFunctionTimeStamp
   }
   DESCRIPTION    "A System p event has occurred"
-- REFERENCE      "POWER_UEOtherSubsystemLossOfFunctionEventIndication"
::= 498

ibmSystempTrapUEOtherSubsystemLossOfFunctionBindings OBJECT IDENTIFIER ::= { ibmSystemTrap 498 }

ibmSystempTrapUEOtherSubsystemLossOfFunctionProviderName OBJECT-TYPE
   SYNTAX         String
   ACCESS         read-only
   STATUS         mandatory
   DESCRIPTION    "The name of the CIM Provider that monitors this device"
-- REFERENCE      "POWER_UEOtherSubsystemLossOfFunctionEventIndication.ProviderName"
::= { ibmSystempTrapUEOtherSubsystemLossOfFunctionBindings 1 }

ibmSystempTrapUEOtherSubsystemLossOfFunctionEventID OBJECT-TYPE
   SYNTAX         String
   ACCESS         read-only
   STATUS         mandatory
   DESCRIPTION    "A unique EventID that identifies this trap" 
-- REFERENCE      "POWER_UEOtherSubsystemLossOfFunctionEventIndication.EventID"
::= { ibmSystempTrapUEOtherSubsystemLossOfFunctionBindings 2 }

ibmSystempTrapUEOtherSubsystemLossOfFunctionAME OBJECT-TYPE
   SYNTAX         String
   ACCESS         read-only
   STATUS         mandatory
   DESCRIPTION    "A unique string that identifies the monitored device"
-- REFERENCE      "POWER_UEOtherSubsystemLossOfFunctionEventIndication.AlertingManagedElement"
::= { ibmSystempTrapUEOtherSubsystemLossOfFunctionBindings 3 }

ibmSystempTrapUEOtherSubsystemLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEOtherSubsystemLossOfFunctionEventIndication.Severity"
::= { ibmSystempTrapUEOtherSubsystemLossOfFunctionBindings 4 }

ibmSystempTrapUEOtherSubsystemLossOfFunctionDescription OBJECT-TYPE
   SYNTAX         SnmpAdminString
   ACCESS         read-only
   STATUS         mandatory
   DESCRIPTION    "The Event text of the trap"
-- REFERENCE      "POWER_UEOtherSubsystemLossOfFunctionEventIndication.Description"
::= { ibmSystempTrapUEOtherSubsystemLossOfFunctionBindings 5 }

ibmSystempTrapUEOtherSubsystemLossOfFunctionTimeStamp OBJECT-TYPE
   SYNTAX         Datetime
   ACCESS         read-only
   STATUS         mandatory
   DESCRIPTION    "The time that the trap occurred"
-- REFERENCE      "POWER_UEOtherSubsystemLossOfFunctionEventIndication.TimeStamp"
::= { ibmSystempTrapUEOtherSubsystemLossOfFunctionBindings 6 }


ibmSystempTrapUEOtherSubsystemUnrecoverableError TRAP-TYPE
   ENTERPRISE     ibmSystemMIB
   VARIABLES    {
      ibmSystempTrapUEOtherSubsystemUnrecoverableErrorProviderName,
      ibmSystempTrapUEOtherSubsystemUnrecoverableErrorEventID,
      ibmSystempTrapUEOtherSubsystemUnrecoverableErrorAME,
      ibmSystempTrapUEOtherSubsystemUnrecoverableErrorSeverity,
      ibmSystempTrapUEOtherSubsystemUnrecoverableErrorDescription,
      ibmSystempTrapUEOtherSubsystemUnrecoverableErrorTimeStamp
   }
   DESCRIPTION    "A System p event has occurred"
-- REFERENCE      "POWER_UEOtherSubsystemUnrecoverableErrorEventIndication"
::= 499

ibmSystempTrapUEOtherSubsystemUnrecoverableErrorBindings OBJECT IDENTIFIER ::= { ibmSystemTrap 499 }

ibmSystempTrapUEOtherSubsystemUnrecoverableErrorProviderName OBJECT-TYPE
   SYNTAX         String
   ACCESS         read-only
   STATUS         mandatory
   DESCRIPTION    "The name of the CIM Provider that monitors this device"
-- REFERENCE      "POWER_UEOtherSubsystemUnrecoverableErrorEventIndication.ProviderName"
::= { ibmSystempTrapUEOtherSubsystemUnrecoverableErrorBindings 1 }

ibmSystempTrapUEOtherSubsystemUnrecoverableErrorEventID OBJECT-TYPE
   SYNTAX         String
   ACCESS         read-only
   STATUS         mandatory
   DESCRIPTION    "A unique EventID that identifies this trap" 
-- REFERENCE      "POWER_UEOtherSubsystemUnrecoverableErrorEventIndication.EventID"
::= { ibmSystempTrapUEOtherSubsystemUnrecoverableErrorBindings 2 }

ibmSystempTrapUEOtherSubsystemUnrecoverableErrorAME OBJECT-TYPE
   SYNTAX         String
   ACCESS         read-only
   STATUS         mandatory
   DESCRIPTION    "A unique string that identifies the monitored device"
-- REFERENCE      "POWER_UEOtherSubsystemUnrecoverableErrorEventIndication.AlertingManagedElement"
::= { ibmSystempTrapUEOtherSubsystemUnrecoverableErrorBindings 3 }

ibmSystempTrapUEOtherSubsystemUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEOtherSubsystemUnrecoverableErrorEventIndication.Severity"
::= { ibmSystempTrapUEOtherSubsystemUnrecoverableErrorBindings 4 }

ibmSystempTrapUEOtherSubsystemUnrecoverableErrorDescription OBJECT-TYPE
   SYNTAX         SnmpAdminString
   ACCESS         read-only
   STATUS         mandatory
   DESCRIPTION    "The Event text of the trap"
-- REFERENCE      "POWER_UEOtherSubsystemUnrecoverableErrorEventIndication.Description"
::= { ibmSystempTrapUEOtherSubsystemUnrecoverableErrorBindings 5 }

ibmSystempTrapUEOtherSubsystemUnrecoverableErrorTimeStamp OBJECT-TYPE
   SYNTAX         Datetime
   ACCESS         read-only
   STATUS         mandatory
   DESCRIPTION    "The time that the trap occurred"
-- REFERENCE      "POWER_UEOtherSubsystemUnrecoverableErrorEventIndication.TimeStamp"
::= { ibmSystempTrapUEOtherSubsystemUnrecoverableErrorBindings 6 }


ibmSystempTrapDTSurveilErrorDiagnostics TRAP-TYPE
   ENTERPRISE     ibmSystemMIB
   VARIABLES    {
      ibmSystempTrapDTSurveilErrorDiagnosticsProviderName,
      ibmSystempTrapDTSurveilErrorDiagnosticsEventID,
      ibmSystempTrapDTSurveilErrorDiagnosticsAME,
      ibmSystempTrapDTSurveilErrorDiagnosticsSeverity,
      ibmSystempTrapDTSurveilErrorDiagnosticsDescription,
      ibmSystempTrapDTSurveilErrorDiagnosticsTimeStamp
   }
   DESCRIPTION    "A System p event has occurred"
-- REFERENCE      "POWER_DTSurveilErrorDiagnosticsEventIndication"
::= 500

ibmSystempTrapDTSurveilErrorDiagnosticsBindings OBJECT IDENTIFIER ::= { ibmSystemTrap 500 }

ibmSystempTrapDTSurveilErrorDiagnosticsProviderName OBJECT-TYPE
   SYNTAX         String
   ACCESS         read-only
   STATUS         mandatory
   DESCRIPTION    "The name of the CIM Provider that monitors this device"
-- REFERENCE      "POWER_DTSurveilErrorDiagnosticsEventIndication.ProviderName"
::= { ibmSystempTrapDTSurveilErrorDiagnosticsBindings 1 }

ibmSystempTrapDTSurveilErrorDiagnosticsEventID OBJECT-TYPE
   SYNTAX         String
   ACCESS         read-only
   STATUS         mandatory
   DESCRIPTION    "A unique EventID that identifies this trap" 
-- REFERENCE      "POWER_DTSurveilErrorDiagnosticsEventIndication.EventID"
::= { ibmSystempTrapDTSurveilErrorDiagnosticsBindings 2 }

ibmSystempTrapDTSurveilErrorDiagnosticsAME OBJECT-TYPE
   SYNTAX         String
   ACCESS         read-only
   STATUS         mandatory
   DESCRIPTION    "A unique string that identifies the monitored device"
-- REFERENCE      "POWER_DTSurveilErrorDiagnosticsEventIndication.AlertingManagedElement"
::= { ibmSystempTrapDTSurveilErrorDiagnosticsBindings 3 }

ibmSystempTrapDTSurveilErrorDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTSurveilErrorDiagnosticsEventIndication.Severity"
::= { ibmSystempTrapDTSurveilErrorDiagnosticsBindings 4 }

ibmSystempTrapDTSurveilErrorDiagnosticsDescription OBJECT-TYPE
   SYNTAX         SnmpAdminString
   ACCESS         read-only
   STATUS         mandatory
   DESCRIPTION    "The Event text of the trap"
-- REFERENCE      "POWER_DTSurveilErrorDiagnosticsEventIndication.Description"
::= { ibmSystempTrapDTSurveilErrorDiagnosticsBindings 5 }

ibmSystempTrapDTSurveilErrorDiagnosticsTimeStamp OBJECT-TYPE
   SYNTAX         Datetime
   ACCESS         read-only
   STATUS         mandatory
   DESCRIPTION    "The time that the trap occurred"
-- REFERENCE      "POWER_DTSurveilErrorDiagnosticsEventIndication.TimeStamp"
::= { ibmSystempTrapDTSurveilErrorDiagnosticsBindings 6 }


ibmSystempTrapPFSurveilErrorDegradPerf TRAP-TYPE
   ENTERPRISE     ibmSystemMIB
   VARIABLES    {
      ibmSystempTrapPFSurveilErrorDegradPerfProviderName,
      ibmSystempTrapPFSurveilErrorDegradPerfEventID,
      ibmSystempTrapPFSurveilErrorDegradPerfAME,
      ibmSystempTrapPFSurveilErrorDegradPerfSeverity,
      ibmSystempTrapPFSurveilErrorDegradPerfDescription,
      ibmSystempTrapPFSurveilErrorDegradPerfTimeStamp
   }
   DESCRIPTION    "A System p event has occurred"
-- REFERENCE      "POWER_PFSurveilErrorDegradPerfEventIndication"
::= 501

ibmSystempTrapPFSurveilErrorDegradPerfBindings OBJECT IDENTIFIER ::= { ibmSystemTrap 501 }

ibmSystempTrapPFSurveilErrorDegradPerfProviderName OBJECT-TYPE
   SYNTAX         String
   ACCESS         read-only
   STATUS         mandatory
   DESCRIPTION    "The name of the CIM Provider that monitors this device"
-- REFERENCE      "POWER_PFSurveilErrorDegradPerfEventIndication.ProviderName"
::= { ibmSystempTrapPFSurveilErrorDegradPerfBindings 1 }

ibmSystempTrapPFSurveilErrorDegradPerfEventID OBJECT-TYPE
   SYNTAX         String
   ACCESS         read-only
   STATUS         mandatory
   DESCRIPTION    "A unique EventID that identifies this trap" 
-- REFERENCE      "POWER_PFSurveilErrorDegradPerfEventIndication.EventID"
::= { ibmSystempTrapPFSurveilErrorDegradPerfBindings 2 }

ibmSystempTrapPFSurveilErrorDegradPerfAME OBJECT-TYPE
   SYNTAX         String
   ACCESS         read-only
   STATUS         mandatory
   DESCRIPTION    "A unique string that identifies the monitored device"
-- REFERENCE      "POWER_PFSurveilErrorDegradPerfEventIndication.AlertingManagedElement"
::= { ibmSystempTrapPFSurveilErrorDegradPerfBindings 3 }

ibmSystempTrapPFSurveilErrorDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFSurveilErrorDegradPerfEventIndication.Severity"
::= { ibmSystempTrapPFSurveilErrorDegradPerfBindings 4 }

ibmSystempTrapPFSurveilErrorDegradPerfDescription OBJECT-TYPE
   SYNTAX         SnmpAdminString
   ACCESS         read-only
   STATUS         mandatory
   DESCRIPTION    "The Event text of the trap"
-- REFERENCE      "POWER_PFSurveilErrorDegradPerfEventIndication.Description"
::= { ibmSystempTrapPFSurveilErrorDegradPerfBindings 5 }

ibmSystempTrapPFSurveilErrorDegradPerfTimeStamp OBJECT-TYPE
   SYNTAX         Datetime
   ACCESS         read-only
   STATUS         mandatory
   DESCRIPTION    "The time that the trap occurred"
-- REFERENCE      "POWER_PFSurveilErrorDegradPerfEventIndication.TimeStamp"
::= { ibmSystempTrapPFSurveilErrorDegradPerfBindings 6 }


ibmSystempTrapPFSurveilErrorCorrectAftIPL TRAP-TYPE
   ENTERPRISE     ibmSystemMIB
   VARIABLES    {
      ibmSystempTrapPFSurveilErrorCorrectAftIPLProviderName,
      ibmSystempTrapPFSurveilErrorCorrectAftIPLEventID,
      ibmSystempTrapPFSurveilErrorCorrectAftIPLAME,
      ibmSystempTrapPFSurveilErrorCorrectAftIPLSeverity,
      ibmSystempTrapPFSurveilErrorCorrectAftIPLDescription,
      ibmSystempTrapPFSurveilErrorCorrectAftIPLTimeStamp
   }
   DESCRIPTION    "A System p event has occurred"
-- REFERENCE      "POWER_PFSurveilErrorCorrectAftIPLEventIndication"
::= 502

ibmSystempTrapPFSurveilErrorCorrectAftIPLBindings OBJECT IDENTIFIER ::= { ibmSystemTrap 502 }

ibmSystempTrapPFSurveilErrorCorrectAftIPLProviderName OBJECT-TYPE
   SYNTAX         String
   ACCESS         read-only
   STATUS         mandatory
   DESCRIPTION    "The name of the CIM Provider that monitors this device"
-- REFERENCE      "POWER_PFSurveilErrorCorrectAftIPLEventIndication.ProviderName"
::= { ibmSystempTrapPFSurveilErrorCorrectAftIPLBindings 1 }

ibmSystempTrapPFSurveilErrorCorrectAftIPLEventID OBJECT-TYPE
   SYNTAX         String
   ACCESS         read-only
   STATUS         mandatory
   DESCRIPTION    "A unique EventID that identifies this trap" 
-- REFERENCE      "POWER_PFSurveilErrorCorrectAftIPLEventIndication.EventID"
::= { ibmSystempTrapPFSurveilErrorCorrectAftIPLBindings 2 }

ibmSystempTrapPFSurveilErrorCorrectAftIPLAME OBJECT-TYPE
   SYNTAX         String
   ACCESS         read-only
   STATUS         mandatory
   DESCRIPTION    "A unique string that identifies the monitored device"
-- REFERENCE      "POWER_PFSurveilErrorCorrectAftIPLEventIndication.AlertingManagedElement"
::= { ibmSystempTrapPFSurveilErrorCorrectAftIPLBindings 3 }

ibmSystempTrapPFSurveilErrorCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFSurveilErrorCorrectAftIPLEventIndication.Severity"
::= { ibmSystempTrapPFSurveilErrorCorrectAftIPLBindings 4 }

ibmSystempTrapPFSurveilErrorCorrectAftIPLDescription OBJECT-TYPE
   SYNTAX         SnmpAdminString
   ACCESS         read-only
   STATUS         mandatory
   DESCRIPTION    "The Event text of the trap"
-- REFERENCE      "POWER_PFSurveilErrorCorrectAftIPLEventIndication.Description"
::= { ibmSystempTrapPFSurveilErrorCorrectAftIPLBindings 5 }

ibmSystempTrapPFSurveilErrorCorrectAftIPLTimeStamp OBJECT-TYPE
   SYNTAX         Datetime
   ACCESS         read-only
   STATUS         mandatory
   DESCRIPTION    "The time that the trap occurred"
-- REFERENCE      "POWER_PFSurveilErrorCorrectAftIPLEventIndication.TimeStamp"
::= { ibmSystempTrapPFSurveilErrorCorrectAftIPLBindings 6 }


ibmSystempTrapPFSurveilErrorCorrectAftIPLPerf TRAP-TYPE
   ENTERPRISE     ibmSystemMIB
   VARIABLES    {
      ibmSystempTrapPFSurveilErrorCorrectAftIPLPerfProviderName,
      ibmSystempTrapPFSurveilErrorCorrectAftIPLPerfEventID,
      ibmSystempTrapPFSurveilErrorCorrectAftIPLPerfAME,
      ibmSystempTrapPFSurveilErrorCorrectAftIPLPerfSeverity,
      ibmSystempTrapPFSurveilErrorCorrectAftIPLPerfDescription,
      ibmSystempTrapPFSurveilErrorCorrectAftIPLPerfTimeStamp
   }
   DESCRIPTION    "A System p event has occurred"
-- REFERENCE      "POWER_PFSurveilErrorCorrectAftIPLPerfEventIndication"
::= 503

ibmSystempTrapPFSurveilErrorCorrectAftIPLPerfBindings OBJECT IDENTIFIER ::= { ibmSystemTrap 503 }

ibmSystempTrapPFSurveilErrorCorrectAftIPLPerfProviderName OBJECT-TYPE
   SYNTAX         String
   ACCESS         read-only
   STATUS         mandatory
   DESCRIPTION    "The name of the CIM Provider that monitors this device"
-- REFERENCE      "POWER_PFSurveilErrorCorrectAftIPLPerfEventIndication.ProviderName"
::= { ibmSystempTrapPFSurveilErrorCorrectAftIPLPerfBindings 1 }

ibmSystempTrapPFSurveilErrorCorrectAftIPLPerfEventID OBJECT-TYPE
   SYNTAX         String
   ACCESS         read-only
   STATUS         mandatory
   DESCRIPTION    "A unique EventID that identifies this trap" 
-- REFERENCE      "POWER_PFSurveilErrorCorrectAftIPLPerfEventIndication.EventID"
::= { ibmSystempTrapPFSurveilErrorCorrectAftIPLPerfBindings 2 }

ibmSystempTrapPFSurveilErrorCorrectAftIPLPerfAME OBJECT-TYPE
   SYNTAX         String
   ACCESS         read-only
   STATUS         mandatory
   DESCRIPTION    "A unique string that identifies the monitored device"
-- REFERENCE      "POWER_PFSurveilErrorCorrectAftIPLPerfEventIndication.AlertingManagedElement"
::= { ibmSystempTrapPFSurveilErrorCorrectAftIPLPerfBindings 3 }

ibmSystempTrapPFSurveilErrorCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFSurveilErrorCorrectAftIPLPerfEventIndication.Severity"
::= { ibmSystempTrapPFSurveilErrorCorrectAftIPLPerfBindings 4 }

ibmSystempTrapPFSurveilErrorCorrectAftIPLPerfDescription OBJECT-TYPE
   SYNTAX         SnmpAdminString
   ACCESS         read-only
   STATUS         mandatory
   DESCRIPTION    "The Event text of the trap"
-- REFERENCE      "POWER_PFSurveilErrorCorrectAftIPLPerfEventIndication.Description"
::= { ibmSystempTrapPFSurveilErrorCorrectAftIPLPerfBindings 5 }

ibmSystempTrapPFSurveilErrorCorrectAftIPLPerfTimeStamp OBJECT-TYPE
   SYNTAX         Datetime
   ACCESS         read-only
   STATUS         mandatory
   DESCRIPTION    "The time that the trap occurred"
-- REFERENCE      "POWER_PFSurveilErrorCorrectAftIPLPerfEventIndication.TimeStamp"
::= { ibmSystempTrapPFSurveilErrorCorrectAftIPLPerfBindings 6 }


ibmSystempTrapPFSurveilErrorLossOfRedundancy TRAP-TYPE
   ENTERPRISE     ibmSystemMIB
   VARIABLES    {
      ibmSystempTrapPFSurveilErrorLossOfRedundancyProviderName,
      ibmSystempTrapPFSurveilErrorLossOfRedundancyEventID,
      ibmSystempTrapPFSurveilErrorLossOfRedundancyAME,
      ibmSystempTrapPFSurveilErrorLossOfRedundancySeverity,
      ibmSystempTrapPFSurveilErrorLossOfRedundancyDescription,
      ibmSystempTrapPFSurveilErrorLossOfRedundancyTimeStamp
   }
   DESCRIPTION    "A System p event has occurred"
-- REFERENCE      "POWER_PFSurveilErrorLossOfRedundancyEventIndication"
::= 504

ibmSystempTrapPFSurveilErrorLossOfRedundancyBindings OBJECT IDENTIFIER ::= { ibmSystemTrap 504 }

ibmSystempTrapPFSurveilErrorLossOfRedundancyProviderName OBJECT-TYPE
   SYNTAX         String
   ACCESS         read-only
   STATUS         mandatory
   DESCRIPTION    "The name of the CIM Provider that monitors this device"
-- REFERENCE      "POWER_PFSurveilErrorLossOfRedundancyEventIndication.ProviderName"
::= { ibmSystempTrapPFSurveilErrorLossOfRedundancyBindings 1 }

ibmSystempTrapPFSurveilErrorLossOfRedundancyEventID OBJECT-TYPE
   SYNTAX         String
   ACCESS         read-only
   STATUS         mandatory
   DESCRIPTION    "A unique EventID that identifies this trap" 
-- REFERENCE      "POWER_PFSurveilErrorLossOfRedundancyEventIndication.EventID"
::= { ibmSystempTrapPFSurveilErrorLossOfRedundancyBindings 2 }

ibmSystempTrapPFSurveilErrorLossOfRedundancyAME OBJECT-TYPE
   SYNTAX         String
   ACCESS         read-only
   STATUS         mandatory
   DESCRIPTION    "A unique string that identifies the monitored device"
-- REFERENCE      "POWER_PFSurveilErrorLossOfRedundancyEventIndication.AlertingManagedElement"
::= { ibmSystempTrapPFSurveilErrorLossOfRedundancyBindings 3 }

ibmSystempTrapPFSurveilErrorLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFSurveilErrorLossOfRedundancyEventIndication.Severity"
::= { ibmSystempTrapPFSurveilErrorLossOfRedundancyBindings 4 }

ibmSystempTrapPFSurveilErrorLossOfRedundancyDescription OBJECT-TYPE
   SYNTAX         SnmpAdminString
   ACCESS         read-only
   STATUS         mandatory
   DESCRIPTION    "The Event text of the trap"
-- REFERENCE      "POWER_PFSurveilErrorLossOfRedundancyEventIndication.Description"
::= { ibmSystempTrapPFSurveilErrorLossOfRedundancyBindings 5 }

ibmSystempTrapPFSurveilErrorLossOfRedundancyTimeStamp OBJECT-TYPE
   SYNTAX         Datetime
   ACCESS         read-only
   STATUS         mandatory
   DESCRIPTION    "The time that the trap occurred"
-- REFERENCE      "POWER_PFSurveilErrorLossOfRedundancyEventIndication.TimeStamp"
::= { ibmSystempTrapPFSurveilErrorLossOfRedundancyBindings 6 }


ibmSystempTrapPFSurveilErrorPredictiveError TRAP-TYPE
   ENTERPRISE     ibmSystemMIB
   VARIABLES    {
      ibmSystempTrapPFSurveilErrorPredictiveErrorProviderName,
      ibmSystempTrapPFSurveilErrorPredictiveErrorEventID,
      ibmSystempTrapPFSurveilErrorPredictiveErrorAME,
      ibmSystempTrapPFSurveilErrorPredictiveErrorSeverity,
      ibmSystempTrapPFSurveilErrorPredictiveErrorDescription,
      ibmSystempTrapPFSurveilErrorPredictiveErrorTimeStamp
   }
   DESCRIPTION    "A System p event has occurred"
-- REFERENCE      "POWER_PFSurveilErrorPredictiveErrorEventIndication"
::= 505

ibmSystempTrapPFSurveilErrorPredictiveErrorBindings OBJECT IDENTIFIER ::= { ibmSystemTrap 505 }

ibmSystempTrapPFSurveilErrorPredictiveErrorProviderName OBJECT-TYPE
   SYNTAX         String
   ACCESS         read-only
   STATUS         mandatory
   DESCRIPTION    "The name of the CIM Provider that monitors this device"
-- REFERENCE      "POWER_PFSurveilErrorPredictiveErrorEventIndication.ProviderName"
::= { ibmSystempTrapPFSurveilErrorPredictiveErrorBindings 1 }

ibmSystempTrapPFSurveilErrorPredictiveErrorEventID OBJECT-TYPE
   SYNTAX         String
   ACCESS         read-only
   STATUS         mandatory
   DESCRIPTION    "A unique EventID that identifies this trap" 
-- REFERENCE      "POWER_PFSurveilErrorPredictiveErrorEventIndication.EventID"
::= { ibmSystempTrapPFSurveilErrorPredictiveErrorBindings 2 }

ibmSystempTrapPFSurveilErrorPredictiveErrorAME OBJECT-TYPE
   SYNTAX         String
   ACCESS         read-only
   STATUS         mandatory
   DESCRIPTION    "A unique string that identifies the monitored device"
-- REFERENCE      "POWER_PFSurveilErrorPredictiveErrorEventIndication.AlertingManagedElement"
::= { ibmSystempTrapPFSurveilErrorPredictiveErrorBindings 3 }

ibmSystempTrapPFSurveilErrorPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFSurveilErrorPredictiveErrorEventIndication.Severity"
::= { ibmSystempTrapPFSurveilErrorPredictiveErrorBindings 4 }

ibmSystempTrapPFSurveilErrorPredictiveErrorDescription OBJECT-TYPE
   SYNTAX         SnmpAdminString
   ACCESS         read-only
   STATUS         mandatory
   DESCRIPTION    "The Event text of the trap"
-- REFERENCE      "POWER_PFSurveilErrorPredictiveErrorEventIndication.Description"
::= { ibmSystempTrapPFSurveilErrorPredictiveErrorBindings 5 }

ibmSystempTrapPFSurveilErrorPredictiveErrorTimeStamp OBJECT-TYPE
   SYNTAX         Datetime
   ACCESS         read-only
   STATUS         mandatory
   DESCRIPTION    "The time that the trap occurred"
-- REFERENCE      "POWER_PFSurveilErrorPredictiveErrorEventIndication.TimeStamp"
::= { ibmSystempTrapPFSurveilErrorPredictiveErrorBindings 6 }


ibmSystempTrapUESurveilErrorDegradPerf TRAP-TYPE
   ENTERPRISE     ibmSystemMIB
   VARIABLES    {
      ibmSystempTrapUESurveilErrorDegradPerfProviderName,
      ibmSystempTrapUESurveilErrorDegradPerfEventID,
      ibmSystempTrapUESurveilErrorDegradPerfAME,
      ibmSystempTrapUESurveilErrorDegradPerfSeverity,
      ibmSystempTrapUESurveilErrorDegradPerfDescription,
      ibmSystempTrapUESurveilErrorDegradPerfTimeStamp
   }
   DESCRIPTION    "A System p event has occurred"
-- REFERENCE      "POWER_UESurveilErrorDegradPerfEventIndication"
::= 506

ibmSystempTrapUESurveilErrorDegradPerfBindings OBJECT IDENTIFIER ::= { ibmSystemTrap 506 }

ibmSystempTrapUESurveilErrorDegradPerfProviderName OBJECT-TYPE
   SYNTAX         String
   ACCESS         read-only
   STATUS         mandatory
   DESCRIPTION    "The name of the CIM Provider that monitors this device"
-- REFERENCE      "POWER_UESurveilErrorDegradPerfEventIndication.ProviderName"
::= { ibmSystempTrapUESurveilErrorDegradPerfBindings 1 }

ibmSystempTrapUESurveilErrorDegradPerfEventID OBJECT-TYPE
   SYNTAX         String
   ACCESS         read-only
   STATUS         mandatory
   DESCRIPTION    "A unique EventID that identifies this trap" 
-- REFERENCE      "POWER_UESurveilErrorDegradPerfEventIndication.EventID"
::= { ibmSystempTrapUESurveilErrorDegradPerfBindings 2 }

ibmSystempTrapUESurveilErrorDegradPerfAME OBJECT-TYPE
   SYNTAX         String
   ACCESS         read-only
   STATUS         mandatory
   DESCRIPTION    "A unique string that identifies the monitored device"
-- REFERENCE      "POWER_UESurveilErrorDegradPerfEventIndication.AlertingManagedElement"
::= { ibmSystempTrapUESurveilErrorDegradPerfBindings 3 }

ibmSystempTrapUESurveilErrorDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UESurveilErrorDegradPerfEventIndication.Severity"
::= { ibmSystempTrapUESurveilErrorDegradPerfBindings 4 }

ibmSystempTrapUESurveilErrorDegradPerfDescription OBJECT-TYPE
   SYNTAX         SnmpAdminString
   ACCESS         read-only
   STATUS         mandatory
   DESCRIPTION    "The Event text of the trap"
-- REFERENCE      "POWER_UESurveilErrorDegradPerfEventIndication.Description"
::= { ibmSystempTrapUESurveilErrorDegradPerfBindings 5 }

ibmSystempTrapUESurveilErrorDegradPerfTimeStamp OBJECT-TYPE
   SYNTAX         Datetime
   ACCESS         read-only
   STATUS         mandatory
   DESCRIPTION    "The time that the trap occurred"
-- REFERENCE      "POWER_UESurveilErrorDegradPerfEventIndication.TimeStamp"
::= { ibmSystempTrapUESurveilErrorDegradPerfBindings 6 }


ibmSystempTrapUESurveilErrorLossOfRedundancy TRAP-TYPE
   ENTERPRISE     ibmSystemMIB
   VARIABLES    {
      ibmSystempTrapUESurveilErrorLossOfRedundancyProviderName,
      ibmSystempTrapUESurveilErrorLossOfRedundancyEventID,
      ibmSystempTrapUESurveilErrorLossOfRedundancyAME,
      ibmSystempTrapUESurveilErrorLossOfRedundancySeverity,
      ibmSystempTrapUESurveilErrorLossOfRedundancyDescription,
      ibmSystempTrapUESurveilErrorLossOfRedundancyTimeStamp
   }
   DESCRIPTION    "A System p event has occurred"
-- REFERENCE      "POWER_UESurveilErrorLossOfRedundancyEventIndication"
::= 507

ibmSystempTrapUESurveilErrorLossOfRedundancyBindings OBJECT IDENTIFIER ::= { ibmSystemTrap 507 }

ibmSystempTrapUESurveilErrorLossOfRedundancyProviderName OBJECT-TYPE
   SYNTAX         String
   ACCESS         read-only
   STATUS         mandatory
   DESCRIPTION    "The name of the CIM Provider that monitors this device"
-- REFERENCE      "POWER_UESurveilErrorLossOfRedundancyEventIndication.ProviderName"
::= { ibmSystempTrapUESurveilErrorLossOfRedundancyBindings 1 }

ibmSystempTrapUESurveilErrorLossOfRedundancyEventID OBJECT-TYPE
   SYNTAX         String
   ACCESS         read-only
   STATUS         mandatory
   DESCRIPTION    "A unique EventID that identifies this trap" 
-- REFERENCE      "POWER_UESurveilErrorLossOfRedundancyEventIndication.EventID"
::= { ibmSystempTrapUESurveilErrorLossOfRedundancyBindings 2 }

ibmSystempTrapUESurveilErrorLossOfRedundancyAME OBJECT-TYPE
   SYNTAX         String
   ACCESS         read-only
   STATUS         mandatory
   DESCRIPTION    "A unique string that identifies the monitored device"
-- REFERENCE      "POWER_UESurveilErrorLossOfRedundancyEventIndication.AlertingManagedElement"
::= { ibmSystempTrapUESurveilErrorLossOfRedundancyBindings 3 }

ibmSystempTrapUESurveilErrorLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UESurveilErrorLossOfRedundancyEventIndication.Severity"
::= { ibmSystempTrapUESurveilErrorLossOfRedundancyBindings 4 }

ibmSystempTrapUESurveilErrorLossOfRedundancyDescription OBJECT-TYPE
   SYNTAX         SnmpAdminString
   ACCESS         read-only
   STATUS         mandatory
   DESCRIPTION    "The Event text of the trap"
-- REFERENCE      "POWER_UESurveilErrorLossOfRedundancyEventIndication.Description"
::= { ibmSystempTrapUESurveilErrorLossOfRedundancyBindings 5 }

ibmSystempTrapUESurveilErrorLossOfRedundancyTimeStamp OBJECT-TYPE
   SYNTAX         Datetime
   ACCESS         read-only
   STATUS         mandatory
   DESCRIPTION    "The time that the trap occurred"
-- REFERENCE      "POWER_UESurveilErrorLossOfRedundancyEventIndication.TimeStamp"
::= { ibmSystempTrapUESurveilErrorLossOfRedundancyBindings 6 }


ibmSystempTrapUESurveilErrorLossOfRedundAndPerf TRAP-TYPE
   ENTERPRISE     ibmSystemMIB
   VARIABLES    {
      ibmSystempTrapUESurveilErrorLossOfRedundAndPerfProviderName,
      ibmSystempTrapUESurveilErrorLossOfRedundAndPerfEventID,
      ibmSystempTrapUESurveilErrorLossOfRedundAndPerfAME,
      ibmSystempTrapUESurveilErrorLossOfRedundAndPerfSeverity,
      ibmSystempTrapUESurveilErrorLossOfRedundAndPerfDescription,
      ibmSystempTrapUESurveilErrorLossOfRedundAndPerfTimeStamp
   }
   DESCRIPTION    "A System p event has occurred"
-- REFERENCE      "POWER_UESurveilErrorLossOfRedundAndPerfEventIndication"
::= 508

ibmSystempTrapUESurveilErrorLossOfRedundAndPerfBindings OBJECT IDENTIFIER ::= { ibmSystemTrap 508 }

ibmSystempTrapUESurveilErrorLossOfRedundAndPerfProviderName OBJECT-TYPE
   SYNTAX         String
   ACCESS         read-only
   STATUS         mandatory
   DESCRIPTION    "The name of the CIM Provider that monitors this device"
-- REFERENCE      "POWER_UESurveilErrorLossOfRedundAndPerfEventIndication.ProviderName"
::= { ibmSystempTrapUESurveilErrorLossOfRedundAndPerfBindings 1 }

ibmSystempTrapUESurveilErrorLossOfRedundAndPerfEventID OBJECT-TYPE
   SYNTAX         String
   ACCESS         read-only
   STATUS         mandatory
   DESCRIPTION    "A unique EventID that identifies this trap" 
-- REFERENCE      "POWER_UESurveilErrorLossOfRedundAndPerfEventIndication.EventID"
::= { ibmSystempTrapUESurveilErrorLossOfRedundAndPerfBindings 2 }

ibmSystempTrapUESurveilErrorLossOfRedundAndPerfAME OBJECT-TYPE
   SYNTAX         String
   ACCESS         read-only
   STATUS         mandatory
   DESCRIPTION    "A unique string that identifies the monitored device"
-- REFERENCE      "POWER_UESurveilErrorLossOfRedundAndPerfEventIndication.AlertingManagedElement"
::= { ibmSystempTrapUESurveilErrorLossOfRedundAndPerfBindings 3 }

ibmSystempTrapUESurveilErrorLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UESurveilErrorLossOfRedundAndPerfEventIndication.Severity"
::= { ibmSystempTrapUESurveilErrorLossOfRedundAndPerfBindings 4 }

ibmSystempTrapUESurveilErrorLossOfRedundAndPerfDescription OBJECT-TYPE
   SYNTAX         SnmpAdminString
   ACCESS         read-only
   STATUS         mandatory
   DESCRIPTION    "The Event text of the trap"
-- REFERENCE      "POWER_UESurveilErrorLossOfRedundAndPerfEventIndication.Description"
::= { ibmSystempTrapUESurveilErrorLossOfRedundAndPerfBindings 5 }

ibmSystempTrapUESurveilErrorLossOfRedundAndPerfTimeStamp OBJECT-TYPE
   SYNTAX         Datetime
   ACCESS         read-only
   STATUS         mandatory
   DESCRIPTION    "The time that the trap occurred"
-- REFERENCE      "POWER_UESurveilErrorLossOfRedundAndPerfEventIndication.TimeStamp"
::= { ibmSystempTrapUESurveilErrorLossOfRedundAndPerfBindings 6 }


ibmSystempTrapUESurveilErrorLossOfFunction TRAP-TYPE
   ENTERPRISE     ibmSystemMIB
   VARIABLES    {
      ibmSystempTrapUESurveilErrorLossOfFunctionProviderName,
      ibmSystempTrapUESurveilErrorLossOfFunctionEventID,
      ibmSystempTrapUESurveilErrorLossOfFunctionAME,
      ibmSystempTrapUESurveilErrorLossOfFunctionSeverity,
      ibmSystempTrapUESurveilErrorLossOfFunctionDescription,
      ibmSystempTrapUESurveilErrorLossOfFunctionTimeStamp
   }
   DESCRIPTION    "A System p event has occurred"
-- REFERENCE      "POWER_UESurveilErrorLossOfFunctionEventIndication"
::= 509

ibmSystempTrapUESurveilErrorLossOfFunctionBindings OBJECT IDENTIFIER ::= { ibmSystemTrap 509 }

ibmSystempTrapUESurveilErrorLossOfFunctionProviderName OBJECT-TYPE
   SYNTAX         String
   ACCESS         read-only
   STATUS         mandatory
   DESCRIPTION    "The name of the CIM Provider that monitors this device"
-- REFERENCE      "POWER_UESurveilErrorLossOfFunctionEventIndication.ProviderName"
::= { ibmSystempTrapUESurveilErrorLossOfFunctionBindings 1 }

ibmSystempTrapUESurveilErrorLossOfFunctionEventID OBJECT-TYPE
   SYNTAX         String
   ACCESS         read-only
   STATUS         mandatory
   DESCRIPTION    "A unique EventID that identifies this trap" 
-- REFERENCE      "POWER_UESurveilErrorLossOfFunctionEventIndication.EventID"
::= { ibmSystempTrapUESurveilErrorLossOfFunctionBindings 2 }

ibmSystempTrapUESurveilErrorLossOfFunctionAME OBJECT-TYPE
   SYNTAX         String
   ACCESS         read-only
   STATUS         mandatory
   DESCRIPTION    "A unique string that identifies the monitored device"
-- REFERENCE      "POWER_UESurveilErrorLossOfFunctionEventIndication.AlertingManagedElement"
::= { ibmSystempTrapUESurveilErrorLossOfFunctionBindings 3 }

ibmSystempTrapUESurveilErrorLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UESurveilErrorLossOfFunctionEventIndication.Severity"
::= { ibmSystempTrapUESurveilErrorLossOfFunctionBindings 4 }

ibmSystempTrapUESurveilErrorLossOfFunctionDescription OBJECT-TYPE
   SYNTAX         SnmpAdminString
   ACCESS         read-only
   STATUS         mandatory
   DESCRIPTION    "The Event text of the trap"
-- REFERENCE      "POWER_UESurveilErrorLossOfFunctionEventIndication.Description"
::= { ibmSystempTrapUESurveilErrorLossOfFunctionBindings 5 }

ibmSystempTrapUESurveilErrorLossOfFunctionTimeStamp OBJECT-TYPE
   SYNTAX         Datetime
   ACCESS         read-only
   STATUS         mandatory
   DESCRIPTION    "The time that the trap occurred"
-- REFERENCE      "POWER_UESurveilErrorLossOfFunctionEventIndication.TimeStamp"
::= { ibmSystempTrapUESurveilErrorLossOfFunctionBindings 6 }


ibmSystempTrapUESurveilErrorUnrecoverableError TRAP-TYPE
   ENTERPRISE     ibmSystemMIB
   VARIABLES    {
      ibmSystempTrapUESurveilErrorUnrecoverableErrorProviderName,
      ibmSystempTrapUESurveilErrorUnrecoverableErrorEventID,
      ibmSystempTrapUESurveilErrorUnrecoverableErrorAME,
      ibmSystempTrapUESurveilErrorUnrecoverableErrorSeverity,
      ibmSystempTrapUESurveilErrorUnrecoverableErrorDescription,
      ibmSystempTrapUESurveilErrorUnrecoverableErrorTimeStamp
   }
   DESCRIPTION    "A System p event has occurred"
-- REFERENCE      "POWER_UESurveilErrorUnrecoverableErrorEventIndication"
::= 510

ibmSystempTrapUESurveilErrorUnrecoverableErrorBindings OBJECT IDENTIFIER ::= { ibmSystemTrap 510 }

ibmSystempTrapUESurveilErrorUnrecoverableErrorProviderName OBJECT-TYPE
   SYNTAX         String
   ACCESS         read-only
   STATUS         mandatory
   DESCRIPTION    "The name of the CIM Provider that monitors this device"
-- REFERENCE      "POWER_UESurveilErrorUnrecoverableErrorEventIndication.ProviderName"
::= { ibmSystempTrapUESurveilErrorUnrecoverableErrorBindings 1 }

ibmSystempTrapUESurveilErrorUnrecoverableErrorEventID OBJECT-TYPE
   SYNTAX         String
   ACCESS         read-only
   STATUS         mandatory
   DESCRIPTION    "A unique EventID that identifies this trap" 
-- REFERENCE      "POWER_UESurveilErrorUnrecoverableErrorEventIndication.EventID"
::= { ibmSystempTrapUESurveilErrorUnrecoverableErrorBindings 2 }

ibmSystempTrapUESurveilErrorUnrecoverableErrorAME OBJECT-TYPE
   SYNTAX         String
   ACCESS         read-only
   STATUS         mandatory
   DESCRIPTION    "A unique string that identifies the monitored device"
-- REFERENCE      "POWER_UESurveilErrorUnrecoverableErrorEventIndication.AlertingManagedElement"
::= { ibmSystempTrapUESurveilErrorUnrecoverableErrorBindings 3 }

ibmSystempTrapUESurveilErrorUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UESurveilErrorUnrecoverableErrorEventIndication.Severity"
::= { ibmSystempTrapUESurveilErrorUnrecoverableErrorBindings 4 }

ibmSystempTrapUESurveilErrorUnrecoverableErrorDescription OBJECT-TYPE
   SYNTAX         SnmpAdminString
   ACCESS         read-only
   STATUS         mandatory
   DESCRIPTION    "The Event text of the trap"
-- REFERENCE      "POWER_UESurveilErrorUnrecoverableErrorEventIndication.Description"
::= { ibmSystempTrapUESurveilErrorUnrecoverableErrorBindings 5 }

ibmSystempTrapUESurveilErrorUnrecoverableErrorTimeStamp OBJECT-TYPE
   SYNTAX         Datetime
   ACCESS         read-only
   STATUS         mandatory
   DESCRIPTION    "The time that the trap occurred"
-- REFERENCE      "POWER_UESurveilErrorUnrecoverableErrorEventIndication.TimeStamp"
::= { ibmSystempTrapUESurveilErrorUnrecoverableErrorBindings 6 }


ibmSystempTrapDTPlatformFirmwareDiagnostics TRAP-TYPE
   ENTERPRISE     ibmSystemMIB
   VARIABLES    {
      ibmSystempTrapDTPlatformFirmwareDiagnosticsProviderName,
      ibmSystempTrapDTPlatformFirmwareDiagnosticsEventID,
      ibmSystempTrapDTPlatformFirmwareDiagnosticsAME,
      ibmSystempTrapDTPlatformFirmwareDiagnosticsSeverity,
      ibmSystempTrapDTPlatformFirmwareDiagnosticsDescription,
      ibmSystempTrapDTPlatformFirmwareDiagnosticsTimeStamp
   }
   DESCRIPTION    "A System p event has occurred"
-- REFERENCE      "POWER_DTPlatformFirmwareDiagnosticsEventIndication"
::= 511

ibmSystempTrapDTPlatformFirmwareDiagnosticsBindings OBJECT IDENTIFIER ::= { ibmSystemTrap 511 }

ibmSystempTrapDTPlatformFirmwareDiagnosticsProviderName OBJECT-TYPE
   SYNTAX         String
   ACCESS         read-only
   STATUS         mandatory
   DESCRIPTION    "The name of the CIM Provider that monitors this device"
-- REFERENCE      "POWER_DTPlatformFirmwareDiagnosticsEventIndication.ProviderName"
::= { ibmSystempTrapDTPlatformFirmwareDiagnosticsBindings 1 }

ibmSystempTrapDTPlatformFirmwareDiagnosticsEventID OBJECT-TYPE
   SYNTAX         String
   ACCESS         read-only
   STATUS         mandatory
   DESCRIPTION    "A unique EventID that identifies this trap" 
-- REFERENCE      "POWER_DTPlatformFirmwareDiagnosticsEventIndication.EventID"
::= { ibmSystempTrapDTPlatformFirmwareDiagnosticsBindings 2 }

ibmSystempTrapDTPlatformFirmwareDiagnosticsAME OBJECT-TYPE
   SYNTAX         String
   ACCESS         read-only
   STATUS         mandatory
   DESCRIPTION    "A unique string that identifies the monitored device"
-- REFERENCE      "POWER_DTPlatformFirmwareDiagnosticsEventIndication.AlertingManagedElement"
::= { ibmSystempTrapDTPlatformFirmwareDiagnosticsBindings 3 }

ibmSystempTrapDTPlatformFirmwareDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTPlatformFirmwareDiagnosticsEventIndication.Severity"
::= { ibmSystempTrapDTPlatformFirmwareDiagnosticsBindings 4 }

ibmSystempTrapDTPlatformFirmwareDiagnosticsDescription OBJECT-TYPE
   SYNTAX         SnmpAdminString
   ACCESS         read-only
   STATUS         mandatory
   DESCRIPTION    "The Event text of the trap"
-- REFERENCE      "POWER_DTPlatformFirmwareDiagnosticsEventIndication.Description"
::= { ibmSystempTrapDTPlatformFirmwareDiagnosticsBindings 5 }

ibmSystempTrapDTPlatformFirmwareDiagnosticsTimeStamp OBJECT-TYPE
   SYNTAX         Datetime
   ACCESS         read-only
   STATUS         mandatory
   DESCRIPTION    "The time that the trap occurred"
-- REFERENCE      "POWER_DTPlatformFirmwareDiagnosticsEventIndication.TimeStamp"
::= { ibmSystempTrapDTPlatformFirmwareDiagnosticsBindings 6 }


ibmSystempTrapPFPlatformFirmwareDegradPerf TRAP-TYPE
   ENTERPRISE     ibmSystemMIB
   VARIABLES    {
      ibmSystempTrapPFPlatformFirmwareDegradPerfProviderName,
      ibmSystempTrapPFPlatformFirmwareDegradPerfEventID,
      ibmSystempTrapPFPlatformFirmwareDegradPerfAME,
      ibmSystempTrapPFPlatformFirmwareDegradPerfSeverity,
      ibmSystempTrapPFPlatformFirmwareDegradPerfDescription,
      ibmSystempTrapPFPlatformFirmwareDegradPerfTimeStamp
   }
   DESCRIPTION    "A System p event has occurred"
-- REFERENCE      "POWER_PFPlatformFirmwareDegradPerfEventIndication"
::= 512

ibmSystempTrapPFPlatformFirmwareDegradPerfBindings OBJECT IDENTIFIER ::= { ibmSystemTrap 512 }

ibmSystempTrapPFPlatformFirmwareDegradPerfProviderName OBJECT-TYPE
   SYNTAX         String
   ACCESS         read-only
   STATUS         mandatory
   DESCRIPTION    "The name of the CIM Provider that monitors this device"
-- REFERENCE      "POWER_PFPlatformFirmwareDegradPerfEventIndication.ProviderName"
::= { ibmSystempTrapPFPlatformFirmwareDegradPerfBindings 1 }

ibmSystempTrapPFPlatformFirmwareDegradPerfEventID OBJECT-TYPE
   SYNTAX         String
   ACCESS         read-only
   STATUS         mandatory
   DESCRIPTION    "A unique EventID that identifies this trap" 
-- REFERENCE      "POWER_PFPlatformFirmwareDegradPerfEventIndication.EventID"
::= { ibmSystempTrapPFPlatformFirmwareDegradPerfBindings 2 }

ibmSystempTrapPFPlatformFirmwareDegradPerfAME OBJECT-TYPE
   SYNTAX         String
   ACCESS         read-only
   STATUS         mandatory
   DESCRIPTION    "A unique string that identifies the monitored device"
-- REFERENCE      "POWER_PFPlatformFirmwareDegradPerfEventIndication.AlertingManagedElement"
::= { ibmSystempTrapPFPlatformFirmwareDegradPerfBindings 3 }

ibmSystempTrapPFPlatformFirmwareDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPlatformFirmwareDegradPerfEventIndication.Severity"
::= { ibmSystempTrapPFPlatformFirmwareDegradPerfBindings 4 }

ibmSystempTrapPFPlatformFirmwareDegradPerfDescription OBJECT-TYPE
   SYNTAX         SnmpAdminString
   ACCESS         read-only
   STATUS         mandatory
   DESCRIPTION    "The Event text of the trap"
-- REFERENCE      "POWER_PFPlatformFirmwareDegradPerfEventIndication.Description"
::= { ibmSystempTrapPFPlatformFirmwareDegradPerfBindings 5 }

ibmSystempTrapPFPlatformFirmwareDegradPerfTimeStamp OBJECT-TYPE
   SYNTAX         Datetime
   ACCESS         read-only
   STATUS         mandatory
   DESCRIPTION    "The time that the trap occurred"
-- REFERENCE      "POWER_PFPlatformFirmwareDegradPerfEventIndication.TimeStamp"
::= { ibmSystempTrapPFPlatformFirmwareDegradPerfBindings 6 }


ibmSystempTrapPFPlatformFirmwareCorrectAftIPL TRAP-TYPE
   ENTERPRISE     ibmSystemMIB
   VARIABLES    {
      ibmSystempTrapPFPlatformFirmwareCorrectAftIPLProviderName,
      ibmSystempTrapPFPlatformFirmwareCorrectAftIPLEventID,
      ibmSystempTrapPFPlatformFirmwareCorrectAftIPLAME,
      ibmSystempTrapPFPlatformFirmwareCorrectAftIPLSeverity,
      ibmSystempTrapPFPlatformFirmwareCorrectAftIPLDescription,
      ibmSystempTrapPFPlatformFirmwareCorrectAftIPLTimeStamp
   }
   DESCRIPTION    "A System p event has occurred"
-- REFERENCE      "POWER_PFPlatformFirmwareCorrectAftIPLEventIndication"
::= 513

ibmSystempTrapPFPlatformFirmwareCorrectAftIPLBindings OBJECT IDENTIFIER ::= { ibmSystemTrap 513 }

ibmSystempTrapPFPlatformFirmwareCorrectAftIPLProviderName OBJECT-TYPE
   SYNTAX         String
   ACCESS         read-only
   STATUS         mandatory
   DESCRIPTION    "The name of the CIM Provider that monitors this device"
-- REFERENCE      "POWER_PFPlatformFirmwareCorrectAftIPLEventIndication.ProviderName"
::= { ibmSystempTrapPFPlatformFirmwareCorrectAftIPLBindings 1 }

ibmSystempTrapPFPlatformFirmwareCorrectAftIPLEventID OBJECT-TYPE
   SYNTAX         String
   ACCESS         read-only
   STATUS         mandatory
   DESCRIPTION    "A unique EventID that identifies this trap" 
-- REFERENCE      "POWER_PFPlatformFirmwareCorrectAftIPLEventIndication.EventID"
::= { ibmSystempTrapPFPlatformFirmwareCorrectAftIPLBindings 2 }

ibmSystempTrapPFPlatformFirmwareCorrectAftIPLAME OBJECT-TYPE
   SYNTAX         String
   ACCESS         read-only
   STATUS         mandatory
   DESCRIPTION    "A unique string that identifies the monitored device"
-- REFERENCE      "POWER_PFPlatformFirmwareCorrectAftIPLEventIndication.AlertingManagedElement"
::= { ibmSystempTrapPFPlatformFirmwareCorrectAftIPLBindings 3 }

ibmSystempTrapPFPlatformFirmwareCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPlatformFirmwareCorrectAftIPLEventIndication.Severity"
::= { ibmSystempTrapPFPlatformFirmwareCorrectAftIPLBindings 4 }

ibmSystempTrapPFPlatformFirmwareCorrectAftIPLDescription OBJECT-TYPE
   SYNTAX         SnmpAdminString
   ACCESS         read-only
   STATUS         mandatory
   DESCRIPTION    "The Event text of the trap"
-- REFERENCE      "POWER_PFPlatformFirmwareCorrectAftIPLEventIndication.Description"
::= { ibmSystempTrapPFPlatformFirmwareCorrectAftIPLBindings 5 }

ibmSystempTrapPFPlatformFirmwareCorrectAftIPLTimeStamp OBJECT-TYPE
   SYNTAX         Datetime
   ACCESS         read-only
   STATUS         mandatory
   DESCRIPTION    "The time that the trap occurred"
-- REFERENCE      "POWER_PFPlatformFirmwareCorrectAftIPLEventIndication.TimeStamp"
::= { ibmSystempTrapPFPlatformFirmwareCorrectAftIPLBindings 6 }


ibmSystempTrapPFPlatformFirmwareCorrectAftIPLPerf TRAP-TYPE
   ENTERPRISE     ibmSystemMIB
   VARIABLES    {
      ibmSystempTrapPFPlatformFirmwareCorrectAftIPLPerfProviderName,
      ibmSystempTrapPFPlatformFirmwareCorrectAftIPLPerfEventID,
      ibmSystempTrapPFPlatformFirmwareCorrectAftIPLPerfAME,
      ibmSystempTrapPFPlatformFirmwareCorrectAftIPLPerfSeverity,
      ibmSystempTrapPFPlatformFirmwareCorrectAftIPLPerfDescription,
      ibmSystempTrapPFPlatformFirmwareCorrectAftIPLPerfTimeStamp
   }
   DESCRIPTION    "A System p event has occurred"
-- REFERENCE      "POWER_PFPlatformFirmwareCorrectAftIPLPerfEventIndication"
::= 514

ibmSystempTrapPFPlatformFirmwareCorrectAftIPLPerfBindings OBJECT IDENTIFIER ::= { ibmSystemTrap 514 }

ibmSystempTrapPFPlatformFirmwareCorrectAftIPLPerfProviderName OBJECT-TYPE
   SYNTAX         String
   ACCESS         read-only
   STATUS         mandatory
   DESCRIPTION    "The name of the CIM Provider that monitors this device"
-- REFERENCE      "POWER_PFPlatformFirmwareCorrectAftIPLPerfEventIndication.ProviderName"
::= { ibmSystempTrapPFPlatformFirmwareCorrectAftIPLPerfBindings 1 }

ibmSystempTrapPFPlatformFirmwareCorrectAftIPLPerfEventID OBJECT-TYPE
   SYNTAX         String
   ACCESS         read-only
   STATUS         mandatory
   DESCRIPTION    "A unique EventID that identifies this trap" 
-- REFERENCE      "POWER_PFPlatformFirmwareCorrectAftIPLPerfEventIndication.EventID"
::= { ibmSystempTrapPFPlatformFirmwareCorrectAftIPLPerfBindings 2 }

ibmSystempTrapPFPlatformFirmwareCorrectAftIPLPerfAME OBJECT-TYPE
   SYNTAX         String
   ACCESS         read-only
   STATUS         mandatory
   DESCRIPTION    "A unique string that identifies the monitored device"
-- REFERENCE      "POWER_PFPlatformFirmwareCorrectAftIPLPerfEventIndication.AlertingManagedElement"
::= { ibmSystempTrapPFPlatformFirmwareCorrectAftIPLPerfBindings 3 }

ibmSystempTrapPFPlatformFirmwareCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPlatformFirmwareCorrectAftIPLPerfEventIndication.Severity"
::= { ibmSystempTrapPFPlatformFirmwareCorrectAftIPLPerfBindings 4 }

ibmSystempTrapPFPlatformFirmwareCorrectAftIPLPerfDescription OBJECT-TYPE
   SYNTAX         SnmpAdminString
   ACCESS         read-only
   STATUS         mandatory
   DESCRIPTION    "The Event text of the trap"
-- REFERENCE      "POWER_PFPlatformFirmwareCorrectAftIPLPerfEventIndication.Description"
::= { ibmSystempTrapPFPlatformFirmwareCorrectAftIPLPerfBindings 5 }

ibmSystempTrapPFPlatformFirmwareCorrectAftIPLPerfTimeStamp OBJECT-TYPE
   SYNTAX         Datetime
   ACCESS         read-only
   STATUS         mandatory
   DESCRIPTION    "The time that the trap occurred"
-- REFERENCE      "POWER_PFPlatformFirmwareCorrectAftIPLPerfEventIndication.TimeStamp"
::= { ibmSystempTrapPFPlatformFirmwareCorrectAftIPLPerfBindings 6 }


ibmSystempTrapPFPlatformFirmwareLossOfRedundancy TRAP-TYPE
   ENTERPRISE     ibmSystemMIB
   VARIABLES    {
      ibmSystempTrapPFPlatformFirmwareLossOfRedundancyProviderName,
      ibmSystempTrapPFPlatformFirmwareLossOfRedundancyEventID,
      ibmSystempTrapPFPlatformFirmwareLossOfRedundancyAME,
      ibmSystempTrapPFPlatformFirmwareLossOfRedundancySeverity,
      ibmSystempTrapPFPlatformFirmwareLossOfRedundancyDescription,
      ibmSystempTrapPFPlatformFirmwareLossOfRedundancyTimeStamp
   }
   DESCRIPTION    "A System p event has occurred"
-- REFERENCE      "POWER_PFPlatformFirmwareLossOfRedundancyEventIndication"
::= 515

ibmSystempTrapPFPlatformFirmwareLossOfRedundancyBindings OBJECT IDENTIFIER ::= { ibmSystemTrap 515 }

ibmSystempTrapPFPlatformFirmwareLossOfRedundancyProviderName OBJECT-TYPE
   SYNTAX         String
   ACCESS         read-only
   STATUS         mandatory
   DESCRIPTION    "The name of the CIM Provider that monitors this device"
-- REFERENCE      "POWER_PFPlatformFirmwareLossOfRedundancyEventIndication.ProviderName"
::= { ibmSystempTrapPFPlatformFirmwareLossOfRedundancyBindings 1 }

ibmSystempTrapPFPlatformFirmwareLossOfRedundancyEventID OBJECT-TYPE
   SYNTAX         String
   ACCESS         read-only
   STATUS         mandatory
   DESCRIPTION    "A unique EventID that identifies this trap" 
-- REFERENCE      "POWER_PFPlatformFirmwareLossOfRedundancyEventIndication.EventID"
::= { ibmSystempTrapPFPlatformFirmwareLossOfRedundancyBindings 2 }

ibmSystempTrapPFPlatformFirmwareLossOfRedundancyAME OBJECT-TYPE
   SYNTAX         String
   ACCESS         read-only
   STATUS         mandatory
   DESCRIPTION    "A unique string that identifies the monitored device"
-- REFERENCE      "POWER_PFPlatformFirmwareLossOfRedundancyEventIndication.AlertingManagedElement"
::= { ibmSystempTrapPFPlatformFirmwareLossOfRedundancyBindings 3 }

ibmSystempTrapPFPlatformFirmwareLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPlatformFirmwareLossOfRedundancyEventIndication.Severity"
::= { ibmSystempTrapPFPlatformFirmwareLossOfRedundancyBindings 4 }

ibmSystempTrapPFPlatformFirmwareLossOfRedundancyDescription OBJECT-TYPE
   SYNTAX         SnmpAdminString
   ACCESS         read-only
   STATUS         mandatory
   DESCRIPTION    "The Event text of the trap"
-- REFERENCE      "POWER_PFPlatformFirmwareLossOfRedundancyEventIndication.Description"
::= { ibmSystempTrapPFPlatformFirmwareLossOfRedundancyBindings 5 }

ibmSystempTrapPFPlatformFirmwareLossOfRedundancyTimeStamp OBJECT-TYPE
   SYNTAX         Datetime
   ACCESS         read-only
   STATUS         mandatory
   DESCRIPTION    "The time that the trap occurred"
-- REFERENCE      "POWER_PFPlatformFirmwareLossOfRedundancyEventIndication.TimeStamp"
::= { ibmSystempTrapPFPlatformFirmwareLossOfRedundancyBindings 6 }


ibmSystempTrapPFPlatformFirmwarePredictiveError TRAP-TYPE
   ENTERPRISE     ibmSystemMIB
   VARIABLES    {
      ibmSystempTrapPFPlatformFirmwarePredictiveErrorProviderName,
      ibmSystempTrapPFPlatformFirmwarePredictiveErrorEventID,
      ibmSystempTrapPFPlatformFirmwarePredictiveErrorAME,
      ibmSystempTrapPFPlatformFirmwarePredictiveErrorSeverity,
      ibmSystempTrapPFPlatformFirmwarePredictiveErrorDescription,
      ibmSystempTrapPFPlatformFirmwarePredictiveErrorTimeStamp
   }
   DESCRIPTION    "A System p event has occurred"
-- REFERENCE      "POWER_PFPlatformFirmwarePredictiveErrorEventIndication"
::= 516

ibmSystempTrapPFPlatformFirmwarePredictiveErrorBindings OBJECT IDENTIFIER ::= { ibmSystemTrap 516 }

ibmSystempTrapPFPlatformFirmwarePredictiveErrorProviderName OBJECT-TYPE
   SYNTAX         String
   ACCESS         read-only
   STATUS         mandatory
   DESCRIPTION    "The name of the CIM Provider that monitors this device"
-- REFERENCE      "POWER_PFPlatformFirmwarePredictiveErrorEventIndication.ProviderName"
::= { ibmSystempTrapPFPlatformFirmwarePredictiveErrorBindings 1 }

ibmSystempTrapPFPlatformFirmwarePredictiveErrorEventID OBJECT-TYPE
   SYNTAX         String
   ACCESS         read-only
   STATUS         mandatory
   DESCRIPTION    "A unique EventID that identifies this trap" 
-- REFERENCE      "POWER_PFPlatformFirmwarePredictiveErrorEventIndication.EventID"
::= { ibmSystempTrapPFPlatformFirmwarePredictiveErrorBindings 2 }

ibmSystempTrapPFPlatformFirmwarePredictiveErrorAME OBJECT-TYPE
   SYNTAX         String
   ACCESS         read-only
   STATUS         mandatory
   DESCRIPTION    "A unique string that identifies the monitored device"
-- REFERENCE      "POWER_PFPlatformFirmwarePredictiveErrorEventIndication.AlertingManagedElement"
::= { ibmSystempTrapPFPlatformFirmwarePredictiveErrorBindings 3 }

ibmSystempTrapPFPlatformFirmwarePredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFPlatformFirmwarePredictiveErrorEventIndication.Severity"
::= { ibmSystempTrapPFPlatformFirmwarePredictiveErrorBindings 4 }

ibmSystempTrapPFPlatformFirmwarePredictiveErrorDescription OBJECT-TYPE
   SYNTAX         SnmpAdminString
   ACCESS         read-only
   STATUS         mandatory
   DESCRIPTION    "The Event text of the trap"
-- REFERENCE      "POWER_PFPlatformFirmwarePredictiveErrorEventIndication.Description"
::= { ibmSystempTrapPFPlatformFirmwarePredictiveErrorBindings 5 }

ibmSystempTrapPFPlatformFirmwarePredictiveErrorTimeStamp OBJECT-TYPE
   SYNTAX         Datetime
   ACCESS         read-only
   STATUS         mandatory
   DESCRIPTION    "The time that the trap occurred"
-- REFERENCE      "POWER_PFPlatformFirmwarePredictiveErrorEventIndication.TimeStamp"
::= { ibmSystempTrapPFPlatformFirmwarePredictiveErrorBindings 6 }


ibmSystempTrapUEPlatformFirmwareDegradPerf TRAP-TYPE
   ENTERPRISE     ibmSystemMIB
   VARIABLES    {
      ibmSystempTrapUEPlatformFirmwareDegradPerfProviderName,
      ibmSystempTrapUEPlatformFirmwareDegradPerfEventID,
      ibmSystempTrapUEPlatformFirmwareDegradPerfAME,
      ibmSystempTrapUEPlatformFirmwareDegradPerfSeverity,
      ibmSystempTrapUEPlatformFirmwareDegradPerfDescription,
      ibmSystempTrapUEPlatformFirmwareDegradPerfTimeStamp
   }
   DESCRIPTION    "A System p event has occurred"
-- REFERENCE      "POWER_UEPlatformFirmwareDegradPerfEventIndication"
::= 517

ibmSystempTrapUEPlatformFirmwareDegradPerfBindings OBJECT IDENTIFIER ::= { ibmSystemTrap 517 }

ibmSystempTrapUEPlatformFirmwareDegradPerfProviderName OBJECT-TYPE
   SYNTAX         String
   ACCESS         read-only
   STATUS         mandatory
   DESCRIPTION    "The name of the CIM Provider that monitors this device"
-- REFERENCE      "POWER_UEPlatformFirmwareDegradPerfEventIndication.ProviderName"
::= { ibmSystempTrapUEPlatformFirmwareDegradPerfBindings 1 }

ibmSystempTrapUEPlatformFirmwareDegradPerfEventID OBJECT-TYPE
   SYNTAX         String
   ACCESS         read-only
   STATUS         mandatory
   DESCRIPTION    "A unique EventID that identifies this trap" 
-- REFERENCE      "POWER_UEPlatformFirmwareDegradPerfEventIndication.EventID"
::= { ibmSystempTrapUEPlatformFirmwareDegradPerfBindings 2 }

ibmSystempTrapUEPlatformFirmwareDegradPerfAME OBJECT-TYPE
   SYNTAX         String
   ACCESS         read-only
   STATUS         mandatory
   DESCRIPTION    "A unique string that identifies the monitored device"
-- REFERENCE      "POWER_UEPlatformFirmwareDegradPerfEventIndication.AlertingManagedElement"
::= { ibmSystempTrapUEPlatformFirmwareDegradPerfBindings 3 }

ibmSystempTrapUEPlatformFirmwareDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPlatformFirmwareDegradPerfEventIndication.Severity"
::= { ibmSystempTrapUEPlatformFirmwareDegradPerfBindings 4 }

ibmSystempTrapUEPlatformFirmwareDegradPerfDescription OBJECT-TYPE
   SYNTAX         SnmpAdminString
   ACCESS         read-only
   STATUS         mandatory
   DESCRIPTION    "The Event text of the trap"
-- REFERENCE      "POWER_UEPlatformFirmwareDegradPerfEventIndication.Description"
::= { ibmSystempTrapUEPlatformFirmwareDegradPerfBindings 5 }

ibmSystempTrapUEPlatformFirmwareDegradPerfTimeStamp OBJECT-TYPE
   SYNTAX         Datetime
   ACCESS         read-only
   STATUS         mandatory
   DESCRIPTION    "The time that the trap occurred"
-- REFERENCE      "POWER_UEPlatformFirmwareDegradPerfEventIndication.TimeStamp"
::= { ibmSystempTrapUEPlatformFirmwareDegradPerfBindings 6 }


ibmSystempTrapUEPlatformFirmwareLossOfRedundancy TRAP-TYPE
   ENTERPRISE     ibmSystemMIB
   VARIABLES    {
      ibmSystempTrapUEPlatformFirmwareLossOfRedundancyProviderName,
      ibmSystempTrapUEPlatformFirmwareLossOfRedundancyEventID,
      ibmSystempTrapUEPlatformFirmwareLossOfRedundancyAME,
      ibmSystempTrapUEPlatformFirmwareLossOfRedundancySeverity,
      ibmSystempTrapUEPlatformFirmwareLossOfRedundancyDescription,
      ibmSystempTrapUEPlatformFirmwareLossOfRedundancyTimeStamp
   }
   DESCRIPTION    "A System p event has occurred"
-- REFERENCE      "POWER_UEPlatformFirmwareLossOfRedundancyEventIndication"
::= 518

ibmSystempTrapUEPlatformFirmwareLossOfRedundancyBindings OBJECT IDENTIFIER ::= { ibmSystemTrap 518 }

ibmSystempTrapUEPlatformFirmwareLossOfRedundancyProviderName OBJECT-TYPE
   SYNTAX         String
   ACCESS         read-only
   STATUS         mandatory
   DESCRIPTION    "The name of the CIM Provider that monitors this device"
-- REFERENCE      "POWER_UEPlatformFirmwareLossOfRedundancyEventIndication.ProviderName"
::= { ibmSystempTrapUEPlatformFirmwareLossOfRedundancyBindings 1 }

ibmSystempTrapUEPlatformFirmwareLossOfRedundancyEventID OBJECT-TYPE
   SYNTAX         String
   ACCESS         read-only
   STATUS         mandatory
   DESCRIPTION    "A unique EventID that identifies this trap" 
-- REFERENCE      "POWER_UEPlatformFirmwareLossOfRedundancyEventIndication.EventID"
::= { ibmSystempTrapUEPlatformFirmwareLossOfRedundancyBindings 2 }

ibmSystempTrapUEPlatformFirmwareLossOfRedundancyAME OBJECT-TYPE
   SYNTAX         String
   ACCESS         read-only
   STATUS         mandatory
   DESCRIPTION    "A unique string that identifies the monitored device"
-- REFERENCE      "POWER_UEPlatformFirmwareLossOfRedundancyEventIndication.AlertingManagedElement"
::= { ibmSystempTrapUEPlatformFirmwareLossOfRedundancyBindings 3 }

ibmSystempTrapUEPlatformFirmwareLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPlatformFirmwareLossOfRedundancyEventIndication.Severity"
::= { ibmSystempTrapUEPlatformFirmwareLossOfRedundancyBindings 4 }

ibmSystempTrapUEPlatformFirmwareLossOfRedundancyDescription OBJECT-TYPE
   SYNTAX         SnmpAdminString
   ACCESS         read-only
   STATUS         mandatory
   DESCRIPTION    "The Event text of the trap"
-- REFERENCE      "POWER_UEPlatformFirmwareLossOfRedundancyEventIndication.Description"
::= { ibmSystempTrapUEPlatformFirmwareLossOfRedundancyBindings 5 }

ibmSystempTrapUEPlatformFirmwareLossOfRedundancyTimeStamp OBJECT-TYPE
   SYNTAX         Datetime
   ACCESS         read-only
   STATUS         mandatory
   DESCRIPTION    "The time that the trap occurred"
-- REFERENCE      "POWER_UEPlatformFirmwareLossOfRedundancyEventIndication.TimeStamp"
::= { ibmSystempTrapUEPlatformFirmwareLossOfRedundancyBindings 6 }


ibmSystempTrapUEPlatformFirmwareLossOfRedundAndPerf TRAP-TYPE
   ENTERPRISE     ibmSystemMIB
   VARIABLES    {
      ibmSystempTrapUEPlatformFirmwareLossOfRedundAndPerfProviderName,
      ibmSystempTrapUEPlatformFirmwareLossOfRedundAndPerfEventID,
      ibmSystempTrapUEPlatformFirmwareLossOfRedundAndPerfAME,
      ibmSystempTrapUEPlatformFirmwareLossOfRedundAndPerfSeverity,
      ibmSystempTrapUEPlatformFirmwareLossOfRedundAndPerfDescription,
      ibmSystempTrapUEPlatformFirmwareLossOfRedundAndPerfTimeStamp
   }
   DESCRIPTION    "A System p event has occurred"
-- REFERENCE      "POWER_UEPlatformFirmwareLossOfRedundAndPerfEventIndication"
::= 519

ibmSystempTrapUEPlatformFirmwareLossOfRedundAndPerfBindings OBJECT IDENTIFIER ::= { ibmSystemTrap 519 }

ibmSystempTrapUEPlatformFirmwareLossOfRedundAndPerfProviderName OBJECT-TYPE
   SYNTAX         String
   ACCESS         read-only
   STATUS         mandatory
   DESCRIPTION    "The name of the CIM Provider that monitors this device"
-- REFERENCE      "POWER_UEPlatformFirmwareLossOfRedundAndPerfEventIndication.ProviderName"
::= { ibmSystempTrapUEPlatformFirmwareLossOfRedundAndPerfBindings 1 }

ibmSystempTrapUEPlatformFirmwareLossOfRedundAndPerfEventID OBJECT-TYPE
   SYNTAX         String
   ACCESS         read-only
   STATUS         mandatory
   DESCRIPTION    "A unique EventID that identifies this trap" 
-- REFERENCE      "POWER_UEPlatformFirmwareLossOfRedundAndPerfEventIndication.EventID"
::= { ibmSystempTrapUEPlatformFirmwareLossOfRedundAndPerfBindings 2 }

ibmSystempTrapUEPlatformFirmwareLossOfRedundAndPerfAME OBJECT-TYPE
   SYNTAX         String
   ACCESS         read-only
   STATUS         mandatory
   DESCRIPTION    "A unique string that identifies the monitored device"
-- REFERENCE      "POWER_UEPlatformFirmwareLossOfRedundAndPerfEventIndication.AlertingManagedElement"
::= { ibmSystempTrapUEPlatformFirmwareLossOfRedundAndPerfBindings 3 }

ibmSystempTrapUEPlatformFirmwareLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPlatformFirmwareLossOfRedundAndPerfEventIndication.Severity"
::= { ibmSystempTrapUEPlatformFirmwareLossOfRedundAndPerfBindings 4 }

ibmSystempTrapUEPlatformFirmwareLossOfRedundAndPerfDescription OBJECT-TYPE
   SYNTAX         SnmpAdminString
   ACCESS         read-only
   STATUS         mandatory
   DESCRIPTION    "The Event text of the trap"
-- REFERENCE      "POWER_UEPlatformFirmwareLossOfRedundAndPerfEventIndication.Description"
::= { ibmSystempTrapUEPlatformFirmwareLossOfRedundAndPerfBindings 5 }

ibmSystempTrapUEPlatformFirmwareLossOfRedundAndPerfTimeStamp OBJECT-TYPE
   SYNTAX         Datetime
   ACCESS         read-only
   STATUS         mandatory
   DESCRIPTION    "The time that the trap occurred"
-- REFERENCE      "POWER_UEPlatformFirmwareLossOfRedundAndPerfEventIndication.TimeStamp"
::= { ibmSystempTrapUEPlatformFirmwareLossOfRedundAndPerfBindings 6 }


ibmSystempTrapUEPlatformFirmwareLossOfFunction TRAP-TYPE
   ENTERPRISE     ibmSystemMIB
   VARIABLES    {
      ibmSystempTrapUEPlatformFirmwareLossOfFunctionProviderName,
      ibmSystempTrapUEPlatformFirmwareLossOfFunctionEventID,
      ibmSystempTrapUEPlatformFirmwareLossOfFunctionAME,
      ibmSystempTrapUEPlatformFirmwareLossOfFunctionSeverity,
      ibmSystempTrapUEPlatformFirmwareLossOfFunctionDescription,
      ibmSystempTrapUEPlatformFirmwareLossOfFunctionTimeStamp
   }
   DESCRIPTION    "A System p event has occurred"
-- REFERENCE      "POWER_UEPlatformFirmwareLossOfFunctionEventIndication"
::= 520

ibmSystempTrapUEPlatformFirmwareLossOfFunctionBindings OBJECT IDENTIFIER ::= { ibmSystemTrap 520 }

ibmSystempTrapUEPlatformFirmwareLossOfFunctionProviderName OBJECT-TYPE
   SYNTAX         String
   ACCESS         read-only
   STATUS         mandatory
   DESCRIPTION    "The name of the CIM Provider that monitors this device"
-- REFERENCE      "POWER_UEPlatformFirmwareLossOfFunctionEventIndication.ProviderName"
::= { ibmSystempTrapUEPlatformFirmwareLossOfFunctionBindings 1 }

ibmSystempTrapUEPlatformFirmwareLossOfFunctionEventID OBJECT-TYPE
   SYNTAX         String
   ACCESS         read-only
   STATUS         mandatory
   DESCRIPTION    "A unique EventID that identifies this trap" 
-- REFERENCE      "POWER_UEPlatformFirmwareLossOfFunctionEventIndication.EventID"
::= { ibmSystempTrapUEPlatformFirmwareLossOfFunctionBindings 2 }

ibmSystempTrapUEPlatformFirmwareLossOfFunctionAME OBJECT-TYPE
   SYNTAX         String
   ACCESS         read-only
   STATUS         mandatory
   DESCRIPTION    "A unique string that identifies the monitored device"
-- REFERENCE      "POWER_UEPlatformFirmwareLossOfFunctionEventIndication.AlertingManagedElement"
::= { ibmSystempTrapUEPlatformFirmwareLossOfFunctionBindings 3 }

ibmSystempTrapUEPlatformFirmwareLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPlatformFirmwareLossOfFunctionEventIndication.Severity"
::= { ibmSystempTrapUEPlatformFirmwareLossOfFunctionBindings 4 }

ibmSystempTrapUEPlatformFirmwareLossOfFunctionDescription OBJECT-TYPE
   SYNTAX         SnmpAdminString
   ACCESS         read-only
   STATUS         mandatory
   DESCRIPTION    "The Event text of the trap"
-- REFERENCE      "POWER_UEPlatformFirmwareLossOfFunctionEventIndication.Description"
::= { ibmSystempTrapUEPlatformFirmwareLossOfFunctionBindings 5 }

ibmSystempTrapUEPlatformFirmwareLossOfFunctionTimeStamp OBJECT-TYPE
   SYNTAX         Datetime
   ACCESS         read-only
   STATUS         mandatory
   DESCRIPTION    "The time that the trap occurred"
-- REFERENCE      "POWER_UEPlatformFirmwareLossOfFunctionEventIndication.TimeStamp"
::= { ibmSystempTrapUEPlatformFirmwareLossOfFunctionBindings 6 }


ibmSystempTrapUEPlatformFirmwareUnrecoverableError TRAP-TYPE
   ENTERPRISE     ibmSystemMIB
   VARIABLES    {
      ibmSystempTrapUEPlatformFirmwareUnrecoverableErrorProviderName,
      ibmSystempTrapUEPlatformFirmwareUnrecoverableErrorEventID,
      ibmSystempTrapUEPlatformFirmwareUnrecoverableErrorAME,
      ibmSystempTrapUEPlatformFirmwareUnrecoverableErrorSeverity,
      ibmSystempTrapUEPlatformFirmwareUnrecoverableErrorDescription,
      ibmSystempTrapUEPlatformFirmwareUnrecoverableErrorTimeStamp
   }
   DESCRIPTION    "A System p event has occurred"
-- REFERENCE      "POWER_UEPlatformFirmwareUnrecoverableErrorEventIndication"
::= 521

ibmSystempTrapUEPlatformFirmwareUnrecoverableErrorBindings OBJECT IDENTIFIER ::= { ibmSystemTrap 521 }

ibmSystempTrapUEPlatformFirmwareUnrecoverableErrorProviderName OBJECT-TYPE
   SYNTAX         String
   ACCESS         read-only
   STATUS         mandatory
   DESCRIPTION    "The name of the CIM Provider that monitors this device"
-- REFERENCE      "POWER_UEPlatformFirmwareUnrecoverableErrorEventIndication.ProviderName"
::= { ibmSystempTrapUEPlatformFirmwareUnrecoverableErrorBindings 1 }

ibmSystempTrapUEPlatformFirmwareUnrecoverableErrorEventID OBJECT-TYPE
   SYNTAX         String
   ACCESS         read-only
   STATUS         mandatory
   DESCRIPTION    "A unique EventID that identifies this trap" 
-- REFERENCE      "POWER_UEPlatformFirmwareUnrecoverableErrorEventIndication.EventID"
::= { ibmSystempTrapUEPlatformFirmwareUnrecoverableErrorBindings 2 }

ibmSystempTrapUEPlatformFirmwareUnrecoverableErrorAME OBJECT-TYPE
   SYNTAX         String
   ACCESS         read-only
   STATUS         mandatory
   DESCRIPTION    "A unique string that identifies the monitored device"
-- REFERENCE      "POWER_UEPlatformFirmwareUnrecoverableErrorEventIndication.AlertingManagedElement"
::= { ibmSystempTrapUEPlatformFirmwareUnrecoverableErrorBindings 3 }

ibmSystempTrapUEPlatformFirmwareUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEPlatformFirmwareUnrecoverableErrorEventIndication.Severity"
::= { ibmSystempTrapUEPlatformFirmwareUnrecoverableErrorBindings 4 }

ibmSystempTrapUEPlatformFirmwareUnrecoverableErrorDescription OBJECT-TYPE
   SYNTAX         SnmpAdminString
   ACCESS         read-only
   STATUS         mandatory
   DESCRIPTION    "The Event text of the trap"
-- REFERENCE      "POWER_UEPlatformFirmwareUnrecoverableErrorEventIndication.Description"
::= { ibmSystempTrapUEPlatformFirmwareUnrecoverableErrorBindings 5 }

ibmSystempTrapUEPlatformFirmwareUnrecoverableErrorTimeStamp OBJECT-TYPE
   SYNTAX         Datetime
   ACCESS         read-only
   STATUS         mandatory
   DESCRIPTION    "The time that the trap occurred"
-- REFERENCE      "POWER_UEPlatformFirmwareUnrecoverableErrorEventIndication.TimeStamp"
::= { ibmSystempTrapUEPlatformFirmwareUnrecoverableErrorBindings 6 }


ibmSystempTrapDTExtEnvironmentDiagnostics TRAP-TYPE
   ENTERPRISE     ibmSystemMIB
   VARIABLES    {
      ibmSystempTrapDTExtEnvironmentDiagnosticsProviderName,
      ibmSystempTrapDTExtEnvironmentDiagnosticsEventID,
      ibmSystempTrapDTExtEnvironmentDiagnosticsAME,
      ibmSystempTrapDTExtEnvironmentDiagnosticsSeverity,
      ibmSystempTrapDTExtEnvironmentDiagnosticsDescription,
      ibmSystempTrapDTExtEnvironmentDiagnosticsTimeStamp
   }
   DESCRIPTION    "A System p event has occurred"
-- REFERENCE      "POWER_DTExtEnvironmentDiagnosticsEventIndication"
::= 522

ibmSystempTrapDTExtEnvironmentDiagnosticsBindings OBJECT IDENTIFIER ::= { ibmSystemTrap 522 }

ibmSystempTrapDTExtEnvironmentDiagnosticsProviderName OBJECT-TYPE
   SYNTAX         String
   ACCESS         read-only
   STATUS         mandatory
   DESCRIPTION    "The name of the CIM Provider that monitors this device"
-- REFERENCE      "POWER_DTExtEnvironmentDiagnosticsEventIndication.ProviderName"
::= { ibmSystempTrapDTExtEnvironmentDiagnosticsBindings 1 }

ibmSystempTrapDTExtEnvironmentDiagnosticsEventID OBJECT-TYPE
   SYNTAX         String
   ACCESS         read-only
   STATUS         mandatory
   DESCRIPTION    "A unique EventID that identifies this trap" 
-- REFERENCE      "POWER_DTExtEnvironmentDiagnosticsEventIndication.EventID"
::= { ibmSystempTrapDTExtEnvironmentDiagnosticsBindings 2 }

ibmSystempTrapDTExtEnvironmentDiagnosticsAME OBJECT-TYPE
   SYNTAX         String
   ACCESS         read-only
   STATUS         mandatory
   DESCRIPTION    "A unique string that identifies the monitored device"
-- REFERENCE      "POWER_DTExtEnvironmentDiagnosticsEventIndication.AlertingManagedElement"
::= { ibmSystempTrapDTExtEnvironmentDiagnosticsBindings 3 }

ibmSystempTrapDTExtEnvironmentDiagnosticsSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_DTExtEnvironmentDiagnosticsEventIndication.Severity"
::= { ibmSystempTrapDTExtEnvironmentDiagnosticsBindings 4 }

ibmSystempTrapDTExtEnvironmentDiagnosticsDescription OBJECT-TYPE
   SYNTAX         SnmpAdminString
   ACCESS         read-only
   STATUS         mandatory
   DESCRIPTION    "The Event text of the trap"
-- REFERENCE      "POWER_DTExtEnvironmentDiagnosticsEventIndication.Description"
::= { ibmSystempTrapDTExtEnvironmentDiagnosticsBindings 5 }

ibmSystempTrapDTExtEnvironmentDiagnosticsTimeStamp OBJECT-TYPE
   SYNTAX         Datetime
   ACCESS         read-only
   STATUS         mandatory
   DESCRIPTION    "The time that the trap occurred"
-- REFERENCE      "POWER_DTExtEnvironmentDiagnosticsEventIndication.TimeStamp"
::= { ibmSystempTrapDTExtEnvironmentDiagnosticsBindings 6 }


ibmSystempTrapPFExtEnvironmentDegradPerf TRAP-TYPE
   ENTERPRISE     ibmSystemMIB
   VARIABLES    {
      ibmSystempTrapPFExtEnvironmentDegradPerfProviderName,
      ibmSystempTrapPFExtEnvironmentDegradPerfEventID,
      ibmSystempTrapPFExtEnvironmentDegradPerfAME,
      ibmSystempTrapPFExtEnvironmentDegradPerfSeverity,
      ibmSystempTrapPFExtEnvironmentDegradPerfDescription,
      ibmSystempTrapPFExtEnvironmentDegradPerfTimeStamp
   }
   DESCRIPTION    "A System p event has occurred"
-- REFERENCE      "POWER_PFExtEnvironmentDegradPerfEventIndication"
::= 523

ibmSystempTrapPFExtEnvironmentDegradPerfBindings OBJECT IDENTIFIER ::= { ibmSystemTrap 523 }

ibmSystempTrapPFExtEnvironmentDegradPerfProviderName OBJECT-TYPE
   SYNTAX         String
   ACCESS         read-only
   STATUS         mandatory
   DESCRIPTION    "The name of the CIM Provider that monitors this device"
-- REFERENCE      "POWER_PFExtEnvironmentDegradPerfEventIndication.ProviderName"
::= { ibmSystempTrapPFExtEnvironmentDegradPerfBindings 1 }

ibmSystempTrapPFExtEnvironmentDegradPerfEventID OBJECT-TYPE
   SYNTAX         String
   ACCESS         read-only
   STATUS         mandatory
   DESCRIPTION    "A unique EventID that identifies this trap" 
-- REFERENCE      "POWER_PFExtEnvironmentDegradPerfEventIndication.EventID"
::= { ibmSystempTrapPFExtEnvironmentDegradPerfBindings 2 }

ibmSystempTrapPFExtEnvironmentDegradPerfAME OBJECT-TYPE
   SYNTAX         String
   ACCESS         read-only
   STATUS         mandatory
   DESCRIPTION    "A unique string that identifies the monitored device"
-- REFERENCE      "POWER_PFExtEnvironmentDegradPerfEventIndication.AlertingManagedElement"
::= { ibmSystempTrapPFExtEnvironmentDegradPerfBindings 3 }

ibmSystempTrapPFExtEnvironmentDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFExtEnvironmentDegradPerfEventIndication.Severity"
::= { ibmSystempTrapPFExtEnvironmentDegradPerfBindings 4 }

ibmSystempTrapPFExtEnvironmentDegradPerfDescription OBJECT-TYPE
   SYNTAX         SnmpAdminString
   ACCESS         read-only
   STATUS         mandatory
   DESCRIPTION    "The Event text of the trap"
-- REFERENCE      "POWER_PFExtEnvironmentDegradPerfEventIndication.Description"
::= { ibmSystempTrapPFExtEnvironmentDegradPerfBindings 5 }

ibmSystempTrapPFExtEnvironmentDegradPerfTimeStamp OBJECT-TYPE
   SYNTAX         Datetime
   ACCESS         read-only
   STATUS         mandatory
   DESCRIPTION    "The time that the trap occurred"
-- REFERENCE      "POWER_PFExtEnvironmentDegradPerfEventIndication.TimeStamp"
::= { ibmSystempTrapPFExtEnvironmentDegradPerfBindings 6 }


ibmSystempTrapPFExtEnvironmentCorrectAftIPL TRAP-TYPE
   ENTERPRISE     ibmSystemMIB
   VARIABLES    {
      ibmSystempTrapPFExtEnvironmentCorrectAftIPLProviderName,
      ibmSystempTrapPFExtEnvironmentCorrectAftIPLEventID,
      ibmSystempTrapPFExtEnvironmentCorrectAftIPLAME,
      ibmSystempTrapPFExtEnvironmentCorrectAftIPLSeverity,
      ibmSystempTrapPFExtEnvironmentCorrectAftIPLDescription,
      ibmSystempTrapPFExtEnvironmentCorrectAftIPLTimeStamp
   }
   DESCRIPTION    "A System p event has occurred"
-- REFERENCE      "POWER_PFExtEnvironmentCorrectAftIPLEventIndication"
::= 524

ibmSystempTrapPFExtEnvironmentCorrectAftIPLBindings OBJECT IDENTIFIER ::= { ibmSystemTrap 524 }

ibmSystempTrapPFExtEnvironmentCorrectAftIPLProviderName OBJECT-TYPE
   SYNTAX         String
   ACCESS         read-only
   STATUS         mandatory
   DESCRIPTION    "The name of the CIM Provider that monitors this device"
-- REFERENCE      "POWER_PFExtEnvironmentCorrectAftIPLEventIndication.ProviderName"
::= { ibmSystempTrapPFExtEnvironmentCorrectAftIPLBindings 1 }

ibmSystempTrapPFExtEnvironmentCorrectAftIPLEventID OBJECT-TYPE
   SYNTAX         String
   ACCESS         read-only
   STATUS         mandatory
   DESCRIPTION    "A unique EventID that identifies this trap" 
-- REFERENCE      "POWER_PFExtEnvironmentCorrectAftIPLEventIndication.EventID"
::= { ibmSystempTrapPFExtEnvironmentCorrectAftIPLBindings 2 }

ibmSystempTrapPFExtEnvironmentCorrectAftIPLAME OBJECT-TYPE
   SYNTAX         String
   ACCESS         read-only
   STATUS         mandatory
   DESCRIPTION    "A unique string that identifies the monitored device"
-- REFERENCE      "POWER_PFExtEnvironmentCorrectAftIPLEventIndication.AlertingManagedElement"
::= { ibmSystempTrapPFExtEnvironmentCorrectAftIPLBindings 3 }

ibmSystempTrapPFExtEnvironmentCorrectAftIPLSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFExtEnvironmentCorrectAftIPLEventIndication.Severity"
::= { ibmSystempTrapPFExtEnvironmentCorrectAftIPLBindings 4 }

ibmSystempTrapPFExtEnvironmentCorrectAftIPLDescription OBJECT-TYPE
   SYNTAX         SnmpAdminString
   ACCESS         read-only
   STATUS         mandatory
   DESCRIPTION    "The Event text of the trap"
-- REFERENCE      "POWER_PFExtEnvironmentCorrectAftIPLEventIndication.Description"
::= { ibmSystempTrapPFExtEnvironmentCorrectAftIPLBindings 5 }

ibmSystempTrapPFExtEnvironmentCorrectAftIPLTimeStamp OBJECT-TYPE
   SYNTAX         Datetime
   ACCESS         read-only
   STATUS         mandatory
   DESCRIPTION    "The time that the trap occurred"
-- REFERENCE      "POWER_PFExtEnvironmentCorrectAftIPLEventIndication.TimeStamp"
::= { ibmSystempTrapPFExtEnvironmentCorrectAftIPLBindings 6 }


ibmSystempTrapPFExtEnvironmentCorrectAftIPLPerf TRAP-TYPE
   ENTERPRISE     ibmSystemMIB
   VARIABLES    {
      ibmSystempTrapPFExtEnvironmentCorrectAftIPLPerfProviderName,
      ibmSystempTrapPFExtEnvironmentCorrectAftIPLPerfEventID,
      ibmSystempTrapPFExtEnvironmentCorrectAftIPLPerfAME,
      ibmSystempTrapPFExtEnvironmentCorrectAftIPLPerfSeverity,
      ibmSystempTrapPFExtEnvironmentCorrectAftIPLPerfDescription,
      ibmSystempTrapPFExtEnvironmentCorrectAftIPLPerfTimeStamp
   }
   DESCRIPTION    "A System p event has occurred"
-- REFERENCE      "POWER_PFExtEnvironmentCorrectAftIPLPerfEventIndication"
::= 525

ibmSystempTrapPFExtEnvironmentCorrectAftIPLPerfBindings OBJECT IDENTIFIER ::= { ibmSystemTrap 525 }

ibmSystempTrapPFExtEnvironmentCorrectAftIPLPerfProviderName OBJECT-TYPE
   SYNTAX         String
   ACCESS         read-only
   STATUS         mandatory
   DESCRIPTION    "The name of the CIM Provider that monitors this device"
-- REFERENCE      "POWER_PFExtEnvironmentCorrectAftIPLPerfEventIndication.ProviderName"
::= { ibmSystempTrapPFExtEnvironmentCorrectAftIPLPerfBindings 1 }

ibmSystempTrapPFExtEnvironmentCorrectAftIPLPerfEventID OBJECT-TYPE
   SYNTAX         String
   ACCESS         read-only
   STATUS         mandatory
   DESCRIPTION    "A unique EventID that identifies this trap" 
-- REFERENCE      "POWER_PFExtEnvironmentCorrectAftIPLPerfEventIndication.EventID"
::= { ibmSystempTrapPFExtEnvironmentCorrectAftIPLPerfBindings 2 }

ibmSystempTrapPFExtEnvironmentCorrectAftIPLPerfAME OBJECT-TYPE
   SYNTAX         String
   ACCESS         read-only
   STATUS         mandatory
   DESCRIPTION    "A unique string that identifies the monitored device"
-- REFERENCE      "POWER_PFExtEnvironmentCorrectAftIPLPerfEventIndication.AlertingManagedElement"
::= { ibmSystempTrapPFExtEnvironmentCorrectAftIPLPerfBindings 3 }

ibmSystempTrapPFExtEnvironmentCorrectAftIPLPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFExtEnvironmentCorrectAftIPLPerfEventIndication.Severity"
::= { ibmSystempTrapPFExtEnvironmentCorrectAftIPLPerfBindings 4 }

ibmSystempTrapPFExtEnvironmentCorrectAftIPLPerfDescription OBJECT-TYPE
   SYNTAX         SnmpAdminString
   ACCESS         read-only
   STATUS         mandatory
   DESCRIPTION    "The Event text of the trap"
-- REFERENCE      "POWER_PFExtEnvironmentCorrectAftIPLPerfEventIndication.Description"
::= { ibmSystempTrapPFExtEnvironmentCorrectAftIPLPerfBindings 5 }

ibmSystempTrapPFExtEnvironmentCorrectAftIPLPerfTimeStamp OBJECT-TYPE
   SYNTAX         Datetime
   ACCESS         read-only
   STATUS         mandatory
   DESCRIPTION    "The time that the trap occurred"
-- REFERENCE      "POWER_PFExtEnvironmentCorrectAftIPLPerfEventIndication.TimeStamp"
::= { ibmSystempTrapPFExtEnvironmentCorrectAftIPLPerfBindings 6 }


ibmSystempTrapPFExtEnvironmentLossOfRedundancy TRAP-TYPE
   ENTERPRISE     ibmSystemMIB
   VARIABLES    {
      ibmSystempTrapPFExtEnvironmentLossOfRedundancyProviderName,
      ibmSystempTrapPFExtEnvironmentLossOfRedundancyEventID,
      ibmSystempTrapPFExtEnvironmentLossOfRedundancyAME,
      ibmSystempTrapPFExtEnvironmentLossOfRedundancySeverity,
      ibmSystempTrapPFExtEnvironmentLossOfRedundancyDescription,
      ibmSystempTrapPFExtEnvironmentLossOfRedundancyTimeStamp
   }
   DESCRIPTION    "A System p event has occurred"
-- REFERENCE      "POWER_PFExtEnvironmentLossOfRedundancyEventIndication"
::= 526

ibmSystempTrapPFExtEnvironmentLossOfRedundancyBindings OBJECT IDENTIFIER ::= { ibmSystemTrap 526 }

ibmSystempTrapPFExtEnvironmentLossOfRedundancyProviderName OBJECT-TYPE
   SYNTAX         String
   ACCESS         read-only
   STATUS         mandatory
   DESCRIPTION    "The name of the CIM Provider that monitors this device"
-- REFERENCE      "POWER_PFExtEnvironmentLossOfRedundancyEventIndication.ProviderName"
::= { ibmSystempTrapPFExtEnvironmentLossOfRedundancyBindings 1 }

ibmSystempTrapPFExtEnvironmentLossOfRedundancyEventID OBJECT-TYPE
   SYNTAX         String
   ACCESS         read-only
   STATUS         mandatory
   DESCRIPTION    "A unique EventID that identifies this trap" 
-- REFERENCE      "POWER_PFExtEnvironmentLossOfRedundancyEventIndication.EventID"
::= { ibmSystempTrapPFExtEnvironmentLossOfRedundancyBindings 2 }

ibmSystempTrapPFExtEnvironmentLossOfRedundancyAME OBJECT-TYPE
   SYNTAX         String
   ACCESS         read-only
   STATUS         mandatory
   DESCRIPTION    "A unique string that identifies the monitored device"
-- REFERENCE      "POWER_PFExtEnvironmentLossOfRedundancyEventIndication.AlertingManagedElement"
::= { ibmSystempTrapPFExtEnvironmentLossOfRedundancyBindings 3 }

ibmSystempTrapPFExtEnvironmentLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFExtEnvironmentLossOfRedundancyEventIndication.Severity"
::= { ibmSystempTrapPFExtEnvironmentLossOfRedundancyBindings 4 }

ibmSystempTrapPFExtEnvironmentLossOfRedundancyDescription OBJECT-TYPE
   SYNTAX         SnmpAdminString
   ACCESS         read-only
   STATUS         mandatory
   DESCRIPTION    "The Event text of the trap"
-- REFERENCE      "POWER_PFExtEnvironmentLossOfRedundancyEventIndication.Description"
::= { ibmSystempTrapPFExtEnvironmentLossOfRedundancyBindings 5 }

ibmSystempTrapPFExtEnvironmentLossOfRedundancyTimeStamp OBJECT-TYPE
   SYNTAX         Datetime
   ACCESS         read-only
   STATUS         mandatory
   DESCRIPTION    "The time that the trap occurred"
-- REFERENCE      "POWER_PFExtEnvironmentLossOfRedundancyEventIndication.TimeStamp"
::= { ibmSystempTrapPFExtEnvironmentLossOfRedundancyBindings 6 }


ibmSystempTrapPFExtEnvironmentPredictiveError TRAP-TYPE
   ENTERPRISE     ibmSystemMIB
   VARIABLES    {
      ibmSystempTrapPFExtEnvironmentPredictiveErrorProviderName,
      ibmSystempTrapPFExtEnvironmentPredictiveErrorEventID,
      ibmSystempTrapPFExtEnvironmentPredictiveErrorAME,
      ibmSystempTrapPFExtEnvironmentPredictiveErrorSeverity,
      ibmSystempTrapPFExtEnvironmentPredictiveErrorDescription,
      ibmSystempTrapPFExtEnvironmentPredictiveErrorTimeStamp
   }
   DESCRIPTION    "A System p event has occurred"
-- REFERENCE      "POWER_PFExtEnvironmentPredictiveErrorEventIndication"
::= 527

ibmSystempTrapPFExtEnvironmentPredictiveErrorBindings OBJECT IDENTIFIER ::= { ibmSystemTrap 527 }

ibmSystempTrapPFExtEnvironmentPredictiveErrorProviderName OBJECT-TYPE
   SYNTAX         String
   ACCESS         read-only
   STATUS         mandatory
   DESCRIPTION    "The name of the CIM Provider that monitors this device"
-- REFERENCE      "POWER_PFExtEnvironmentPredictiveErrorEventIndication.ProviderName"
::= { ibmSystempTrapPFExtEnvironmentPredictiveErrorBindings 1 }

ibmSystempTrapPFExtEnvironmentPredictiveErrorEventID OBJECT-TYPE
   SYNTAX         String
   ACCESS         read-only
   STATUS         mandatory
   DESCRIPTION    "A unique EventID that identifies this trap" 
-- REFERENCE      "POWER_PFExtEnvironmentPredictiveErrorEventIndication.EventID"
::= { ibmSystempTrapPFExtEnvironmentPredictiveErrorBindings 2 }

ibmSystempTrapPFExtEnvironmentPredictiveErrorAME OBJECT-TYPE
   SYNTAX         String
   ACCESS         read-only
   STATUS         mandatory
   DESCRIPTION    "A unique string that identifies the monitored device"
-- REFERENCE      "POWER_PFExtEnvironmentPredictiveErrorEventIndication.AlertingManagedElement"
::= { ibmSystempTrapPFExtEnvironmentPredictiveErrorBindings 3 }

ibmSystempTrapPFExtEnvironmentPredictiveErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_PFExtEnvironmentPredictiveErrorEventIndication.Severity"
::= { ibmSystempTrapPFExtEnvironmentPredictiveErrorBindings 4 }

ibmSystempTrapPFExtEnvironmentPredictiveErrorDescription OBJECT-TYPE
   SYNTAX         SnmpAdminString
   ACCESS         read-only
   STATUS         mandatory
   DESCRIPTION    "The Event text of the trap"
-- REFERENCE      "POWER_PFExtEnvironmentPredictiveErrorEventIndication.Description"
::= { ibmSystempTrapPFExtEnvironmentPredictiveErrorBindings 5 }

ibmSystempTrapPFExtEnvironmentPredictiveErrorTimeStamp OBJECT-TYPE
   SYNTAX         Datetime
   ACCESS         read-only
   STATUS         mandatory
   DESCRIPTION    "The time that the trap occurred"
-- REFERENCE      "POWER_PFExtEnvironmentPredictiveErrorEventIndication.TimeStamp"
::= { ibmSystempTrapPFExtEnvironmentPredictiveErrorBindings 6 }


ibmSystempTrapUEExtEnvironmentDegradPerf TRAP-TYPE
   ENTERPRISE     ibmSystemMIB
   VARIABLES    {
      ibmSystempTrapUEExtEnvironmentDegradPerfProviderName,
      ibmSystempTrapUEExtEnvironmentDegradPerfEventID,
      ibmSystempTrapUEExtEnvironmentDegradPerfAME,
      ibmSystempTrapUEExtEnvironmentDegradPerfSeverity,
      ibmSystempTrapUEExtEnvironmentDegradPerfDescription,
      ibmSystempTrapUEExtEnvironmentDegradPerfTimeStamp
   }
   DESCRIPTION    "A System p event has occurred"
-- REFERENCE      "POWER_UEExtEnvironmentDegradPerfEventIndication"
::= 528

ibmSystempTrapUEExtEnvironmentDegradPerfBindings OBJECT IDENTIFIER ::= { ibmSystemTrap 528 }

ibmSystempTrapUEExtEnvironmentDegradPerfProviderName OBJECT-TYPE
   SYNTAX         String
   ACCESS         read-only
   STATUS         mandatory
   DESCRIPTION    "The name of the CIM Provider that monitors this device"
-- REFERENCE      "POWER_UEExtEnvironmentDegradPerfEventIndication.ProviderName"
::= { ibmSystempTrapUEExtEnvironmentDegradPerfBindings 1 }

ibmSystempTrapUEExtEnvironmentDegradPerfEventID OBJECT-TYPE
   SYNTAX         String
   ACCESS         read-only
   STATUS         mandatory
   DESCRIPTION    "A unique EventID that identifies this trap" 
-- REFERENCE      "POWER_UEExtEnvironmentDegradPerfEventIndication.EventID"
::= { ibmSystempTrapUEExtEnvironmentDegradPerfBindings 2 }

ibmSystempTrapUEExtEnvironmentDegradPerfAME OBJECT-TYPE
   SYNTAX         String
   ACCESS         read-only
   STATUS         mandatory
   DESCRIPTION    "A unique string that identifies the monitored device"
-- REFERENCE      "POWER_UEExtEnvironmentDegradPerfEventIndication.AlertingManagedElement"
::= { ibmSystempTrapUEExtEnvironmentDegradPerfBindings 3 }

ibmSystempTrapUEExtEnvironmentDegradPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEExtEnvironmentDegradPerfEventIndication.Severity"
::= { ibmSystempTrapUEExtEnvironmentDegradPerfBindings 4 }

ibmSystempTrapUEExtEnvironmentDegradPerfDescription OBJECT-TYPE
   SYNTAX         SnmpAdminString
   ACCESS         read-only
   STATUS         mandatory
   DESCRIPTION    "The Event text of the trap"
-- REFERENCE      "POWER_UEExtEnvironmentDegradPerfEventIndication.Description"
::= { ibmSystempTrapUEExtEnvironmentDegradPerfBindings 5 }

ibmSystempTrapUEExtEnvironmentDegradPerfTimeStamp OBJECT-TYPE
   SYNTAX         Datetime
   ACCESS         read-only
   STATUS         mandatory
   DESCRIPTION    "The time that the trap occurred"
-- REFERENCE      "POWER_UEExtEnvironmentDegradPerfEventIndication.TimeStamp"
::= { ibmSystempTrapUEExtEnvironmentDegradPerfBindings 6 }


ibmSystempTrapUEExtEnvironmentLossOfRedundancy TRAP-TYPE
   ENTERPRISE     ibmSystemMIB
   VARIABLES    {
      ibmSystempTrapUEExtEnvironmentLossOfRedundancyProviderName,
      ibmSystempTrapUEExtEnvironmentLossOfRedundancyEventID,
      ibmSystempTrapUEExtEnvironmentLossOfRedundancyAME,
      ibmSystempTrapUEExtEnvironmentLossOfRedundancySeverity,
      ibmSystempTrapUEExtEnvironmentLossOfRedundancyDescription,
      ibmSystempTrapUEExtEnvironmentLossOfRedundancyTimeStamp
   }
   DESCRIPTION    "A System p event has occurred"
-- REFERENCE      "POWER_UEExtEnvironmentLossOfRedundancyEventIndication"
::= 529

ibmSystempTrapUEExtEnvironmentLossOfRedundancyBindings OBJECT IDENTIFIER ::= { ibmSystemTrap 529 }

ibmSystempTrapUEExtEnvironmentLossOfRedundancyProviderName OBJECT-TYPE
   SYNTAX         String
   ACCESS         read-only
   STATUS         mandatory
   DESCRIPTION    "The name of the CIM Provider that monitors this device"
-- REFERENCE      "POWER_UEExtEnvironmentLossOfRedundancyEventIndication.ProviderName"
::= { ibmSystempTrapUEExtEnvironmentLossOfRedundancyBindings 1 }

ibmSystempTrapUEExtEnvironmentLossOfRedundancyEventID OBJECT-TYPE
   SYNTAX         String
   ACCESS         read-only
   STATUS         mandatory
   DESCRIPTION    "A unique EventID that identifies this trap" 
-- REFERENCE      "POWER_UEExtEnvironmentLossOfRedundancyEventIndication.EventID"
::= { ibmSystempTrapUEExtEnvironmentLossOfRedundancyBindings 2 }

ibmSystempTrapUEExtEnvironmentLossOfRedundancyAME OBJECT-TYPE
   SYNTAX         String
   ACCESS         read-only
   STATUS         mandatory
   DESCRIPTION    "A unique string that identifies the monitored device"
-- REFERENCE      "POWER_UEExtEnvironmentLossOfRedundancyEventIndication.AlertingManagedElement"
::= { ibmSystempTrapUEExtEnvironmentLossOfRedundancyBindings 3 }

ibmSystempTrapUEExtEnvironmentLossOfRedundancySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEExtEnvironmentLossOfRedundancyEventIndication.Severity"
::= { ibmSystempTrapUEExtEnvironmentLossOfRedundancyBindings 4 }

ibmSystempTrapUEExtEnvironmentLossOfRedundancyDescription OBJECT-TYPE
   SYNTAX         SnmpAdminString
   ACCESS         read-only
   STATUS         mandatory
   DESCRIPTION    "The Event text of the trap"
-- REFERENCE      "POWER_UEExtEnvironmentLossOfRedundancyEventIndication.Description"
::= { ibmSystempTrapUEExtEnvironmentLossOfRedundancyBindings 5 }

ibmSystempTrapUEExtEnvironmentLossOfRedundancyTimeStamp OBJECT-TYPE
   SYNTAX         Datetime
   ACCESS         read-only
   STATUS         mandatory
   DESCRIPTION    "The time that the trap occurred"
-- REFERENCE      "POWER_UEExtEnvironmentLossOfRedundancyEventIndication.TimeStamp"
::= { ibmSystempTrapUEExtEnvironmentLossOfRedundancyBindings 6 }


ibmSystempTrapUEExtEnvironmentLossOfRedundAndPerf TRAP-TYPE
   ENTERPRISE     ibmSystemMIB
   VARIABLES    {
      ibmSystempTrapUEExtEnvironmentLossOfRedundAndPerfProviderName,
      ibmSystempTrapUEExtEnvironmentLossOfRedundAndPerfEventID,
      ibmSystempTrapUEExtEnvironmentLossOfRedundAndPerfAME,
      ibmSystempTrapUEExtEnvironmentLossOfRedundAndPerfSeverity,
      ibmSystempTrapUEExtEnvironmentLossOfRedundAndPerfDescription,
      ibmSystempTrapUEExtEnvironmentLossOfRedundAndPerfTimeStamp
   }
   DESCRIPTION    "A System p event has occurred"
-- REFERENCE      "POWER_UEExtEnvironmentLossOfRedundAndPerfEventIndication"
::= 530

ibmSystempTrapUEExtEnvironmentLossOfRedundAndPerfBindings OBJECT IDENTIFIER ::= { ibmSystemTrap 530 }

ibmSystempTrapUEExtEnvironmentLossOfRedundAndPerfProviderName OBJECT-TYPE
   SYNTAX         String
   ACCESS         read-only
   STATUS         mandatory
   DESCRIPTION    "The name of the CIM Provider that monitors this device"
-- REFERENCE      "POWER_UEExtEnvironmentLossOfRedundAndPerfEventIndication.ProviderName"
::= { ibmSystempTrapUEExtEnvironmentLossOfRedundAndPerfBindings 1 }

ibmSystempTrapUEExtEnvironmentLossOfRedundAndPerfEventID OBJECT-TYPE
   SYNTAX         String
   ACCESS         read-only
   STATUS         mandatory
   DESCRIPTION    "A unique EventID that identifies this trap" 
-- REFERENCE      "POWER_UEExtEnvironmentLossOfRedundAndPerfEventIndication.EventID"
::= { ibmSystempTrapUEExtEnvironmentLossOfRedundAndPerfBindings 2 }

ibmSystempTrapUEExtEnvironmentLossOfRedundAndPerfAME OBJECT-TYPE
   SYNTAX         String
   ACCESS         read-only
   STATUS         mandatory
   DESCRIPTION    "A unique string that identifies the monitored device"
-- REFERENCE      "POWER_UEExtEnvironmentLossOfRedundAndPerfEventIndication.AlertingManagedElement"
::= { ibmSystempTrapUEExtEnvironmentLossOfRedundAndPerfBindings 3 }

ibmSystempTrapUEExtEnvironmentLossOfRedundAndPerfSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEExtEnvironmentLossOfRedundAndPerfEventIndication.Severity"
::= { ibmSystempTrapUEExtEnvironmentLossOfRedundAndPerfBindings 4 }

ibmSystempTrapUEExtEnvironmentLossOfRedundAndPerfDescription OBJECT-TYPE
   SYNTAX         SnmpAdminString
   ACCESS         read-only
   STATUS         mandatory
   DESCRIPTION    "The Event text of the trap"
-- REFERENCE      "POWER_UEExtEnvironmentLossOfRedundAndPerfEventIndication.Description"
::= { ibmSystempTrapUEExtEnvironmentLossOfRedundAndPerfBindings 5 }

ibmSystempTrapUEExtEnvironmentLossOfRedundAndPerfTimeStamp OBJECT-TYPE
   SYNTAX         Datetime
   ACCESS         read-only
   STATUS         mandatory
   DESCRIPTION    "The time that the trap occurred"
-- REFERENCE      "POWER_UEExtEnvironmentLossOfRedundAndPerfEventIndication.TimeStamp"
::= { ibmSystempTrapUEExtEnvironmentLossOfRedundAndPerfBindings 6 }


ibmSystempTrapUEExtEnvironmentLossOfFunction TRAP-TYPE
   ENTERPRISE     ibmSystemMIB
   VARIABLES    {
      ibmSystempTrapUEExtEnvironmentLossOfFunctionProviderName,
      ibmSystempTrapUEExtEnvironmentLossOfFunctionEventID,
      ibmSystempTrapUEExtEnvironmentLossOfFunctionAME,
      ibmSystempTrapUEExtEnvironmentLossOfFunctionSeverity,
      ibmSystempTrapUEExtEnvironmentLossOfFunctionDescription,
      ibmSystempTrapUEExtEnvironmentLossOfFunctionTimeStamp
   }
   DESCRIPTION    "A System p event has occurred"
-- REFERENCE      "POWER_UEExtEnvironmentLossOfFunctionEventIndication"
::= 531

ibmSystempTrapUEExtEnvironmentLossOfFunctionBindings OBJECT IDENTIFIER ::= { ibmSystemTrap 531 }

ibmSystempTrapUEExtEnvironmentLossOfFunctionProviderName OBJECT-TYPE
   SYNTAX         String
   ACCESS         read-only
   STATUS         mandatory
   DESCRIPTION    "The name of the CIM Provider that monitors this device"
-- REFERENCE      "POWER_UEExtEnvironmentLossOfFunctionEventIndication.ProviderName"
::= { ibmSystempTrapUEExtEnvironmentLossOfFunctionBindings 1 }

ibmSystempTrapUEExtEnvironmentLossOfFunctionEventID OBJECT-TYPE
   SYNTAX         String
   ACCESS         read-only
   STATUS         mandatory
   DESCRIPTION    "A unique EventID that identifies this trap" 
-- REFERENCE      "POWER_UEExtEnvironmentLossOfFunctionEventIndication.EventID"
::= { ibmSystempTrapUEExtEnvironmentLossOfFunctionBindings 2 }

ibmSystempTrapUEExtEnvironmentLossOfFunctionAME OBJECT-TYPE
   SYNTAX         String
   ACCESS         read-only
   STATUS         mandatory
   DESCRIPTION    "A unique string that identifies the monitored device"
-- REFERENCE      "POWER_UEExtEnvironmentLossOfFunctionEventIndication.AlertingManagedElement"
::= { ibmSystempTrapUEExtEnvironmentLossOfFunctionBindings 3 }

ibmSystempTrapUEExtEnvironmentLossOfFunctionSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEExtEnvironmentLossOfFunctionEventIndication.Severity"
::= { ibmSystempTrapUEExtEnvironmentLossOfFunctionBindings 4 }

ibmSystempTrapUEExtEnvironmentLossOfFunctionDescription OBJECT-TYPE
   SYNTAX         SnmpAdminString
   ACCESS         read-only
   STATUS         mandatory
   DESCRIPTION    "The Event text of the trap"
-- REFERENCE      "POWER_UEExtEnvironmentLossOfFunctionEventIndication.Description"
::= { ibmSystempTrapUEExtEnvironmentLossOfFunctionBindings 5 }

ibmSystempTrapUEExtEnvironmentLossOfFunctionTimeStamp OBJECT-TYPE
   SYNTAX         Datetime
   ACCESS         read-only
   STATUS         mandatory
   DESCRIPTION    "The time that the trap occurred"
-- REFERENCE      "POWER_UEExtEnvironmentLossOfFunctionEventIndication.TimeStamp"
::= { ibmSystempTrapUEExtEnvironmentLossOfFunctionBindings 6 }


ibmSystempTrapUEExtEnvironmentUnrecoverableError TRAP-TYPE
   ENTERPRISE     ibmSystemMIB
   VARIABLES    {
      ibmSystempTrapUEExtEnvironmentUnrecoverableErrorProviderName,
      ibmSystempTrapUEExtEnvironmentUnrecoverableErrorEventID,
      ibmSystempTrapUEExtEnvironmentUnrecoverableErrorAME,
      ibmSystempTrapUEExtEnvironmentUnrecoverableErrorSeverity,
      ibmSystempTrapUEExtEnvironmentUnrecoverableErrorDescription,
      ibmSystempTrapUEExtEnvironmentUnrecoverableErrorTimeStamp
   }
   DESCRIPTION    "A System p event has occurred"
-- REFERENCE      "POWER_UEExtEnvironmentUnrecoverableErrorEventIndication"
::= 532

ibmSystempTrapUEExtEnvironmentUnrecoverableErrorBindings OBJECT IDENTIFIER ::= { ibmSystemTrap 532 }

ibmSystempTrapUEExtEnvironmentUnrecoverableErrorProviderName OBJECT-TYPE
   SYNTAX         String
   ACCESS         read-only
   STATUS         mandatory
   DESCRIPTION    "The name of the CIM Provider that monitors this device"
-- REFERENCE      "POWER_UEExtEnvironmentUnrecoverableErrorEventIndication.ProviderName"
::= { ibmSystempTrapUEExtEnvironmentUnrecoverableErrorBindings 1 }

ibmSystempTrapUEExtEnvironmentUnrecoverableErrorEventID OBJECT-TYPE
   SYNTAX         String
   ACCESS         read-only
   STATUS         mandatory
   DESCRIPTION    "A unique EventID that identifies this trap" 
-- REFERENCE      "POWER_UEExtEnvironmentUnrecoverableErrorEventIndication.EventID"
::= { ibmSystempTrapUEExtEnvironmentUnrecoverableErrorBindings 2 }

ibmSystempTrapUEExtEnvironmentUnrecoverableErrorAME OBJECT-TYPE
   SYNTAX         String
   ACCESS         read-only
   STATUS         mandatory
   DESCRIPTION    "A unique string that identifies the monitored device"
-- REFERENCE      "POWER_UEExtEnvironmentUnrecoverableErrorEventIndication.AlertingManagedElement"
::= { ibmSystempTrapUEExtEnvironmentUnrecoverableErrorBindings 3 }

ibmSystempTrapUEExtEnvironmentUnrecoverableErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_UEExtEnvironmentUnrecoverableErrorEventIndication.Severity"
::= { ibmSystempTrapUEExtEnvironmentUnrecoverableErrorBindings 4 }

ibmSystempTrapUEExtEnvironmentUnrecoverableErrorDescription OBJECT-TYPE
   SYNTAX         SnmpAdminString
   ACCESS         read-only
   STATUS         mandatory
   DESCRIPTION    "The Event text of the trap"
-- REFERENCE      "POWER_UEExtEnvironmentUnrecoverableErrorEventIndication.Description"
::= { ibmSystempTrapUEExtEnvironmentUnrecoverableErrorBindings 5 }

ibmSystempTrapUEExtEnvironmentUnrecoverableErrorTimeStamp OBJECT-TYPE
   SYNTAX         Datetime
   ACCESS         read-only
   STATUS         mandatory
   DESCRIPTION    "The time that the trap occurred"
-- REFERENCE      "POWER_UEExtEnvironmentUnrecoverableErrorEventIndication.TimeStamp"
::= { ibmSystempTrapUEExtEnvironmentUnrecoverableErrorBindings 6 }


ibmSystempTrapCryptoAdapterINFO TRAP-TYPE
   ENTERPRISE     ibmSystemMIB
   VARIABLES    {
      ibmSystempTrapCryptoAdapterINFOProviderName,
      ibmSystempTrapCryptoAdapterINFOEventID,
      ibmSystempTrapCryptoAdapterINFOAME,
      ibmSystempTrapCryptoAdapterINFOSeverity,
      ibmSystempTrapCryptoAdapterINFODescription,
      ibmSystempTrapCryptoAdapterINFOTimeStamp
   }
   DESCRIPTION    "A System p event has occurred"
-- REFERENCE      "POWER_CryptoAdapterINFOEventIndication"
::= 533

ibmSystempTrapCryptoAdapterINFOBindings OBJECT IDENTIFIER ::= { ibmSystemTrap 533 }

ibmSystempTrapCryptoAdapterINFOProviderName OBJECT-TYPE
   SYNTAX         String
   ACCESS         read-only
   STATUS         mandatory
   DESCRIPTION    "The name of the CIM Provider that monitors this device"
-- REFERENCE      "POWER_CryptoAdapterINFOEventIndication.ProviderName"
::= { ibmSystempTrapCryptoAdapterINFOBindings 1 }

ibmSystempTrapCryptoAdapterINFOEventID OBJECT-TYPE
   SYNTAX         String
   ACCESS         read-only
   STATUS         mandatory
   DESCRIPTION    "A unique EventID that identifies this trap" 
-- REFERENCE      "POWER_CryptoAdapterINFOEventIndication.EventID"
::= { ibmSystempTrapCryptoAdapterINFOBindings 2 }

ibmSystempTrapCryptoAdapterINFOAME OBJECT-TYPE
   SYNTAX         String
   ACCESS         read-only
   STATUS         mandatory
   DESCRIPTION    "A unique string that identifies the monitored device"
-- REFERENCE      "POWER_CryptoAdapterINFOEventIndication.AlertingManagedElement"
::= { ibmSystempTrapCryptoAdapterINFOBindings 3 }

ibmSystempTrapCryptoAdapterINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_CryptoAdapterINFOEventIndication.Severity"
::= { ibmSystempTrapCryptoAdapterINFOBindings 4 }

ibmSystempTrapCryptoAdapterINFODescription OBJECT-TYPE
   SYNTAX         SnmpAdminString
   ACCESS         read-only
   STATUS         mandatory
   DESCRIPTION    "The Event text of the trap"
-- REFERENCE      "POWER_CryptoAdapterINFOEventIndication.Description"
::= { ibmSystempTrapCryptoAdapterINFOBindings 5 }

ibmSystempTrapCryptoAdapterINFOTimeStamp OBJECT-TYPE
   SYNTAX         Datetime
   ACCESS         read-only
   STATUS         mandatory
   DESCRIPTION    "The time that the trap occurred"
-- REFERENCE      "POWER_CryptoAdapterINFOEventIndication.TimeStamp"
::= { ibmSystempTrapCryptoAdapterINFOBindings 6 }


ibmSystempTrapCryptoAdapterTEMP TRAP-TYPE
   ENTERPRISE     ibmSystemMIB
   VARIABLES    {
      ibmSystempTrapCryptoAdapterTEMPProviderName,
      ibmSystempTrapCryptoAdapterTEMPEventID,
      ibmSystempTrapCryptoAdapterTEMPAME,
      ibmSystempTrapCryptoAdapterTEMPSeverity,
      ibmSystempTrapCryptoAdapterTEMPDescription,
      ibmSystempTrapCryptoAdapterTEMPTimeStamp
   }
   DESCRIPTION    "A System p event has occurred"
-- REFERENCE      "POWER_CryptoAdapterTEMPEventIndication"
::= 534

ibmSystempTrapCryptoAdapterTEMPBindings OBJECT IDENTIFIER ::= { ibmSystemTrap 534 }

ibmSystempTrapCryptoAdapterTEMPProviderName OBJECT-TYPE
   SYNTAX         String
   ACCESS         read-only
   STATUS         mandatory
   DESCRIPTION    "The name of the CIM Provider that monitors this device"
-- REFERENCE      "POWER_CryptoAdapterTEMPEventIndication.ProviderName"
::= { ibmSystempTrapCryptoAdapterTEMPBindings 1 }

ibmSystempTrapCryptoAdapterTEMPEventID OBJECT-TYPE
   SYNTAX         String
   ACCESS         read-only
   STATUS         mandatory
   DESCRIPTION    "A unique EventID that identifies this trap" 
-- REFERENCE      "POWER_CryptoAdapterTEMPEventIndication.EventID"
::= { ibmSystempTrapCryptoAdapterTEMPBindings 2 }

ibmSystempTrapCryptoAdapterTEMPAME OBJECT-TYPE
   SYNTAX         String
   ACCESS         read-only
   STATUS         mandatory
   DESCRIPTION    "A unique string that identifies the monitored device"
-- REFERENCE      "POWER_CryptoAdapterTEMPEventIndication.AlertingManagedElement"
::= { ibmSystempTrapCryptoAdapterTEMPBindings 3 }

ibmSystempTrapCryptoAdapterTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_CryptoAdapterTEMPEventIndication.Severity"
::= { ibmSystempTrapCryptoAdapterTEMPBindings 4 }

ibmSystempTrapCryptoAdapterTEMPDescription OBJECT-TYPE
   SYNTAX         SnmpAdminString
   ACCESS         read-only
   STATUS         mandatory
   DESCRIPTION    "The Event text of the trap"
-- REFERENCE      "POWER_CryptoAdapterTEMPEventIndication.Description"
::= { ibmSystempTrapCryptoAdapterTEMPBindings 5 }

ibmSystempTrapCryptoAdapterTEMPTimeStamp OBJECT-TYPE
   SYNTAX         Datetime
   ACCESS         read-only
   STATUS         mandatory
   DESCRIPTION    "The time that the trap occurred"
-- REFERENCE      "POWER_CryptoAdapterTEMPEventIndication.TimeStamp"
::= { ibmSystempTrapCryptoAdapterTEMPBindings 6 }


ibmSystempTrapCryptoAdapterPEND TRAP-TYPE
   ENTERPRISE     ibmSystemMIB
   VARIABLES    {
      ibmSystempTrapCryptoAdapterPENDProviderName,
      ibmSystempTrapCryptoAdapterPENDEventID,
      ibmSystempTrapCryptoAdapterPENDAME,
      ibmSystempTrapCryptoAdapterPENDSeverity,
      ibmSystempTrapCryptoAdapterPENDDescription,
      ibmSystempTrapCryptoAdapterPENDTimeStamp
   }
   DESCRIPTION    "A System p event has occurred"
-- REFERENCE      "POWER_CryptoAdapterPENDEventIndication"
::= 535

ibmSystempTrapCryptoAdapterPENDBindings OBJECT IDENTIFIER ::= { ibmSystemTrap 535 }

ibmSystempTrapCryptoAdapterPENDProviderName OBJECT-TYPE
   SYNTAX         String
   ACCESS         read-only
   STATUS         mandatory
   DESCRIPTION    "The name of the CIM Provider that monitors this device"
-- REFERENCE      "POWER_CryptoAdapterPENDEventIndication.ProviderName"
::= { ibmSystempTrapCryptoAdapterPENDBindings 1 }

ibmSystempTrapCryptoAdapterPENDEventID OBJECT-TYPE
   SYNTAX         String
   ACCESS         read-only
   STATUS         mandatory
   DESCRIPTION    "A unique EventID that identifies this trap" 
-- REFERENCE      "POWER_CryptoAdapterPENDEventIndication.EventID"
::= { ibmSystempTrapCryptoAdapterPENDBindings 2 }

ibmSystempTrapCryptoAdapterPENDAME OBJECT-TYPE
   SYNTAX         String
   ACCESS         read-only
   STATUS         mandatory
   DESCRIPTION    "A unique string that identifies the monitored device"
-- REFERENCE      "POWER_CryptoAdapterPENDEventIndication.AlertingManagedElement"
::= { ibmSystempTrapCryptoAdapterPENDBindings 3 }

ibmSystempTrapCryptoAdapterPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_CryptoAdapterPENDEventIndication.Severity"
::= { ibmSystempTrapCryptoAdapterPENDBindings 4 }

ibmSystempTrapCryptoAdapterPENDDescription OBJECT-TYPE
   SYNTAX         SnmpAdminString
   ACCESS         read-only
   STATUS         mandatory
   DESCRIPTION    "The Event text of the trap"
-- REFERENCE      "POWER_CryptoAdapterPENDEventIndication.Description"
::= { ibmSystempTrapCryptoAdapterPENDBindings 5 }

ibmSystempTrapCryptoAdapterPENDTimeStamp OBJECT-TYPE
   SYNTAX         Datetime
   ACCESS         read-only
   STATUS         mandatory
   DESCRIPTION    "The time that the trap occurred"
-- REFERENCE      "POWER_CryptoAdapterPENDEventIndication.TimeStamp"
::= { ibmSystempTrapCryptoAdapterPENDBindings 6 }


ibmSystempTrapCryptoAdapterPERF TRAP-TYPE
   ENTERPRISE     ibmSystemMIB
   VARIABLES    {
      ibmSystempTrapCryptoAdapterPERFProviderName,
      ibmSystempTrapCryptoAdapterPERFEventID,
      ibmSystempTrapCryptoAdapterPERFAME,
      ibmSystempTrapCryptoAdapterPERFSeverity,
      ibmSystempTrapCryptoAdapterPERFDescription,
      ibmSystempTrapCryptoAdapterPERFTimeStamp
   }
   DESCRIPTION    "A System p event has occurred"
-- REFERENCE      "POWER_CryptoAdapterPERFEventIndication"
::= 536

ibmSystempTrapCryptoAdapterPERFBindings OBJECT IDENTIFIER ::= { ibmSystemTrap 536 }

ibmSystempTrapCryptoAdapterPERFProviderName OBJECT-TYPE
   SYNTAX         String
   ACCESS         read-only
   STATUS         mandatory
   DESCRIPTION    "The name of the CIM Provider that monitors this device"
-- REFERENCE      "POWER_CryptoAdapterPERFEventIndication.ProviderName"
::= { ibmSystempTrapCryptoAdapterPERFBindings 1 }

ibmSystempTrapCryptoAdapterPERFEventID OBJECT-TYPE
   SYNTAX         String
   ACCESS         read-only
   STATUS         mandatory
   DESCRIPTION    "A unique EventID that identifies this trap" 
-- REFERENCE      "POWER_CryptoAdapterPERFEventIndication.EventID"
::= { ibmSystempTrapCryptoAdapterPERFBindings 2 }

ibmSystempTrapCryptoAdapterPERFAME OBJECT-TYPE
   SYNTAX         String
   ACCESS         read-only
   STATUS         mandatory
   DESCRIPTION    "A unique string that identifies the monitored device"
-- REFERENCE      "POWER_CryptoAdapterPERFEventIndication.AlertingManagedElement"
::= { ibmSystempTrapCryptoAdapterPERFBindings 3 }

ibmSystempTrapCryptoAdapterPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_CryptoAdapterPERFEventIndication.Severity"
::= { ibmSystempTrapCryptoAdapterPERFBindings 4 }

ibmSystempTrapCryptoAdapterPERFDescription OBJECT-TYPE
   SYNTAX         SnmpAdminString
   ACCESS         read-only
   STATUS         mandatory
   DESCRIPTION    "The Event text of the trap"
-- REFERENCE      "POWER_CryptoAdapterPERFEventIndication.Description"
::= { ibmSystempTrapCryptoAdapterPERFBindings 5 }

ibmSystempTrapCryptoAdapterPERFTimeStamp OBJECT-TYPE
   SYNTAX         Datetime
   ACCESS         read-only
   STATUS         mandatory
   DESCRIPTION    "The time that the trap occurred"
-- REFERENCE      "POWER_CryptoAdapterPERFEventIndication.TimeStamp"
::= { ibmSystempTrapCryptoAdapterPERFBindings 6 }


ibmSystempTrapCryptoAdapterUNKNOWN TRAP-TYPE
   ENTERPRISE     ibmSystemMIB
   VARIABLES    {
      ibmSystempTrapCryptoAdapterUNKNOWNProviderName,
      ibmSystempTrapCryptoAdapterUNKNOWNEventID,
      ibmSystempTrapCryptoAdapterUNKNOWNAME,
      ibmSystempTrapCryptoAdapterUNKNOWNSeverity,
      ibmSystempTrapCryptoAdapterUNKNOWNDescription,
      ibmSystempTrapCryptoAdapterUNKNOWNTimeStamp
   }
   DESCRIPTION    "A System p event has occurred"
-- REFERENCE      "POWER_CryptoAdapterUNKNOWNEventIndication"
::= 537

ibmSystempTrapCryptoAdapterUNKNOWNBindings OBJECT IDENTIFIER ::= { ibmSystemTrap 537 }

ibmSystempTrapCryptoAdapterUNKNOWNProviderName OBJECT-TYPE
   SYNTAX         String
   ACCESS         read-only
   STATUS         mandatory
   DESCRIPTION    "The name of the CIM Provider that monitors this device"
-- REFERENCE      "POWER_CryptoAdapterUNKNOWNEventIndication.ProviderName"
::= { ibmSystempTrapCryptoAdapterUNKNOWNBindings 1 }

ibmSystempTrapCryptoAdapterUNKNOWNEventID OBJECT-TYPE
   SYNTAX         String
   ACCESS         read-only
   STATUS         mandatory
   DESCRIPTION    "A unique EventID that identifies this trap" 
-- REFERENCE      "POWER_CryptoAdapterUNKNOWNEventIndication.EventID"
::= { ibmSystempTrapCryptoAdapterUNKNOWNBindings 2 }

ibmSystempTrapCryptoAdapterUNKNOWNAME OBJECT-TYPE
   SYNTAX         String
   ACCESS         read-only
   STATUS         mandatory
   DESCRIPTION    "A unique string that identifies the monitored device"
-- REFERENCE      "POWER_CryptoAdapterUNKNOWNEventIndication.AlertingManagedElement"
::= { ibmSystempTrapCryptoAdapterUNKNOWNBindings 3 }

ibmSystempTrapCryptoAdapterUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_CryptoAdapterUNKNOWNEventIndication.Severity"
::= { ibmSystempTrapCryptoAdapterUNKNOWNBindings 4 }

ibmSystempTrapCryptoAdapterUNKNOWNDescription OBJECT-TYPE
   SYNTAX         SnmpAdminString
   ACCESS         read-only
   STATUS         mandatory
   DESCRIPTION    "The Event text of the trap"
-- REFERENCE      "POWER_CryptoAdapterUNKNOWNEventIndication.Description"
::= { ibmSystempTrapCryptoAdapterUNKNOWNBindings 5 }

ibmSystempTrapCryptoAdapterUNKNOWNTimeStamp OBJECT-TYPE
   SYNTAX         Datetime
   ACCESS         read-only
   STATUS         mandatory
   DESCRIPTION    "The time that the trap occurred"
-- REFERENCE      "POWER_CryptoAdapterUNKNOWNEventIndication.TimeStamp"
::= { ibmSystempTrapCryptoAdapterUNKNOWNBindings 6 }


ibmSystempTrapCryptoAdapterPERM TRAP-TYPE
   ENTERPRISE     ibmSystemMIB
   VARIABLES    {
      ibmSystempTrapCryptoAdapterPERMProviderName,
      ibmSystempTrapCryptoAdapterPERMEventID,
      ibmSystempTrapCryptoAdapterPERMAME,
      ibmSystempTrapCryptoAdapterPERMSeverity,
      ibmSystempTrapCryptoAdapterPERMDescription,
      ibmSystempTrapCryptoAdapterPERMTimeStamp
   }
   DESCRIPTION    "A System p event has occurred"
-- REFERENCE      "POWER_CryptoAdapterPERMEventIndication"
::= 538

ibmSystempTrapCryptoAdapterPERMBindings OBJECT IDENTIFIER ::= { ibmSystemTrap 538 }

ibmSystempTrapCryptoAdapterPERMProviderName OBJECT-TYPE
   SYNTAX         String
   ACCESS         read-only
   STATUS         mandatory
   DESCRIPTION    "The name of the CIM Provider that monitors this device"
-- REFERENCE      "POWER_CryptoAdapterPERMEventIndication.ProviderName"
::= { ibmSystempTrapCryptoAdapterPERMBindings 1 }

ibmSystempTrapCryptoAdapterPERMEventID OBJECT-TYPE
   SYNTAX         String
   ACCESS         read-only
   STATUS         mandatory
   DESCRIPTION    "A unique EventID that identifies this trap" 
-- REFERENCE      "POWER_CryptoAdapterPERMEventIndication.EventID"
::= { ibmSystempTrapCryptoAdapterPERMBindings 2 }

ibmSystempTrapCryptoAdapterPERMAME OBJECT-TYPE
   SYNTAX         String
   ACCESS         read-only
   STATUS         mandatory
   DESCRIPTION    "A unique string that identifies the monitored device"
-- REFERENCE      "POWER_CryptoAdapterPERMEventIndication.AlertingManagedElement"
::= { ibmSystempTrapCryptoAdapterPERMBindings 3 }

ibmSystempTrapCryptoAdapterPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_CryptoAdapterPERMEventIndication.Severity"
::= { ibmSystempTrapCryptoAdapterPERMBindings 4 }

ibmSystempTrapCryptoAdapterPERMDescription OBJECT-TYPE
   SYNTAX         SnmpAdminString
   ACCESS         read-only
   STATUS         mandatory
   DESCRIPTION    "The Event text of the trap"
-- REFERENCE      "POWER_CryptoAdapterPERMEventIndication.Description"
::= { ibmSystempTrapCryptoAdapterPERMBindings 5 }

ibmSystempTrapCryptoAdapterPERMTimeStamp OBJECT-TYPE
   SYNTAX         Datetime
   ACCESS         read-only
   STATUS         mandatory
   DESCRIPTION    "The time that the trap occurred"
-- REFERENCE      "POWER_CryptoAdapterPERMEventIndication.TimeStamp"
::= { ibmSystempTrapCryptoAdapterPERMBindings 6 }


ibmSystempTrapEthernetAdapterINFO TRAP-TYPE
   ENTERPRISE     ibmSystemMIB
   VARIABLES    {
      ibmSystempTrapEthernetAdapterINFOProviderName,
      ibmSystempTrapEthernetAdapterINFOEventID,
      ibmSystempTrapEthernetAdapterINFOAME,
      ibmSystempTrapEthernetAdapterINFOSeverity,
      ibmSystempTrapEthernetAdapterINFODescription,
      ibmSystempTrapEthernetAdapterINFOTimeStamp
   }
   DESCRIPTION    "A System p event has occurred"
-- REFERENCE      "POWER_EthernetAdapterINFOEventIndication"
::= 539

ibmSystempTrapEthernetAdapterINFOBindings OBJECT IDENTIFIER ::= { ibmSystemTrap 539 }

ibmSystempTrapEthernetAdapterINFOProviderName OBJECT-TYPE
   SYNTAX         String
   ACCESS         read-only
   STATUS         mandatory
   DESCRIPTION    "The name of the CIM Provider that monitors this device"
-- REFERENCE      "POWER_EthernetAdapterINFOEventIndication.ProviderName"
::= { ibmSystempTrapEthernetAdapterINFOBindings 1 }

ibmSystempTrapEthernetAdapterINFOEventID OBJECT-TYPE
   SYNTAX         String
   ACCESS         read-only
   STATUS         mandatory
   DESCRIPTION    "A unique EventID that identifies this trap" 
-- REFERENCE      "POWER_EthernetAdapterINFOEventIndication.EventID"
::= { ibmSystempTrapEthernetAdapterINFOBindings 2 }

ibmSystempTrapEthernetAdapterINFOAME OBJECT-TYPE
   SYNTAX         String
   ACCESS         read-only
   STATUS         mandatory
   DESCRIPTION    "A unique string that identifies the monitored device"
-- REFERENCE      "POWER_EthernetAdapterINFOEventIndication.AlertingManagedElement"
::= { ibmSystempTrapEthernetAdapterINFOBindings 3 }

ibmSystempTrapEthernetAdapterINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_EthernetAdapterINFOEventIndication.Severity"
::= { ibmSystempTrapEthernetAdapterINFOBindings 4 }

ibmSystempTrapEthernetAdapterINFODescription OBJECT-TYPE
   SYNTAX         SnmpAdminString
   ACCESS         read-only
   STATUS         mandatory
   DESCRIPTION    "The Event text of the trap"
-- REFERENCE      "POWER_EthernetAdapterINFOEventIndication.Description"
::= { ibmSystempTrapEthernetAdapterINFOBindings 5 }

ibmSystempTrapEthernetAdapterINFOTimeStamp OBJECT-TYPE
   SYNTAX         Datetime
   ACCESS         read-only
   STATUS         mandatory
   DESCRIPTION    "The time that the trap occurred"
-- REFERENCE      "POWER_EthernetAdapterINFOEventIndication.TimeStamp"
::= { ibmSystempTrapEthernetAdapterINFOBindings 6 }


ibmSystempTrapEthernetAdapterTEMP TRAP-TYPE
   ENTERPRISE     ibmSystemMIB
   VARIABLES    {
      ibmSystempTrapEthernetAdapterTEMPProviderName,
      ibmSystempTrapEthernetAdapterTEMPEventID,
      ibmSystempTrapEthernetAdapterTEMPAME,
      ibmSystempTrapEthernetAdapterTEMPSeverity,
      ibmSystempTrapEthernetAdapterTEMPDescription,
      ibmSystempTrapEthernetAdapterTEMPTimeStamp
   }
   DESCRIPTION    "A System p event has occurred"
-- REFERENCE      "POWER_EthernetAdapterTEMPEventIndication"
::= 540

ibmSystempTrapEthernetAdapterTEMPBindings OBJECT IDENTIFIER ::= { ibmSystemTrap 540 }

ibmSystempTrapEthernetAdapterTEMPProviderName OBJECT-TYPE
   SYNTAX         String
   ACCESS         read-only
   STATUS         mandatory
   DESCRIPTION    "The name of the CIM Provider that monitors this device"
-- REFERENCE      "POWER_EthernetAdapterTEMPEventIndication.ProviderName"
::= { ibmSystempTrapEthernetAdapterTEMPBindings 1 }

ibmSystempTrapEthernetAdapterTEMPEventID OBJECT-TYPE
   SYNTAX         String
   ACCESS         read-only
   STATUS         mandatory
   DESCRIPTION    "A unique EventID that identifies this trap" 
-- REFERENCE      "POWER_EthernetAdapterTEMPEventIndication.EventID"
::= { ibmSystempTrapEthernetAdapterTEMPBindings 2 }

ibmSystempTrapEthernetAdapterTEMPAME OBJECT-TYPE
   SYNTAX         String
   ACCESS         read-only
   STATUS         mandatory
   DESCRIPTION    "A unique string that identifies the monitored device"
-- REFERENCE      "POWER_EthernetAdapterTEMPEventIndication.AlertingManagedElement"
::= { ibmSystempTrapEthernetAdapterTEMPBindings 3 }

ibmSystempTrapEthernetAdapterTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_EthernetAdapterTEMPEventIndication.Severity"
::= { ibmSystempTrapEthernetAdapterTEMPBindings 4 }

ibmSystempTrapEthernetAdapterTEMPDescription OBJECT-TYPE
   SYNTAX         SnmpAdminString
   ACCESS         read-only
   STATUS         mandatory
   DESCRIPTION    "The Event text of the trap"
-- REFERENCE      "POWER_EthernetAdapterTEMPEventIndication.Description"
::= { ibmSystempTrapEthernetAdapterTEMPBindings 5 }

ibmSystempTrapEthernetAdapterTEMPTimeStamp OBJECT-TYPE
   SYNTAX         Datetime
   ACCESS         read-only
   STATUS         mandatory
   DESCRIPTION    "The time that the trap occurred"
-- REFERENCE      "POWER_EthernetAdapterTEMPEventIndication.TimeStamp"
::= { ibmSystempTrapEthernetAdapterTEMPBindings 6 }


ibmSystempTrapEthernetAdapterPEND TRAP-TYPE
   ENTERPRISE     ibmSystemMIB
   VARIABLES    {
      ibmSystempTrapEthernetAdapterPENDProviderName,
      ibmSystempTrapEthernetAdapterPENDEventID,
      ibmSystempTrapEthernetAdapterPENDAME,
      ibmSystempTrapEthernetAdapterPENDSeverity,
      ibmSystempTrapEthernetAdapterPENDDescription,
      ibmSystempTrapEthernetAdapterPENDTimeStamp
   }
   DESCRIPTION    "A System p event has occurred"
-- REFERENCE      "POWER_EthernetAdapterPENDEventIndication"
::= 541

ibmSystempTrapEthernetAdapterPENDBindings OBJECT IDENTIFIER ::= { ibmSystemTrap 541 }

ibmSystempTrapEthernetAdapterPENDProviderName OBJECT-TYPE
   SYNTAX         String
   ACCESS         read-only
   STATUS         mandatory
   DESCRIPTION    "The name of the CIM Provider that monitors this device"
-- REFERENCE      "POWER_EthernetAdapterPENDEventIndication.ProviderName"
::= { ibmSystempTrapEthernetAdapterPENDBindings 1 }

ibmSystempTrapEthernetAdapterPENDEventID OBJECT-TYPE
   SYNTAX         String
   ACCESS         read-only
   STATUS         mandatory
   DESCRIPTION    "A unique EventID that identifies this trap" 
-- REFERENCE      "POWER_EthernetAdapterPENDEventIndication.EventID"
::= { ibmSystempTrapEthernetAdapterPENDBindings 2 }

ibmSystempTrapEthernetAdapterPENDAME OBJECT-TYPE
   SYNTAX         String
   ACCESS         read-only
   STATUS         mandatory
   DESCRIPTION    "A unique string that identifies the monitored device"
-- REFERENCE      "POWER_EthernetAdapterPENDEventIndication.AlertingManagedElement"
::= { ibmSystempTrapEthernetAdapterPENDBindings 3 }

ibmSystempTrapEthernetAdapterPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_EthernetAdapterPENDEventIndication.Severity"
::= { ibmSystempTrapEthernetAdapterPENDBindings 4 }

ibmSystempTrapEthernetAdapterPENDDescription OBJECT-TYPE
   SYNTAX         SnmpAdminString
   ACCESS         read-only
   STATUS         mandatory
   DESCRIPTION    "The Event text of the trap"
-- REFERENCE      "POWER_EthernetAdapterPENDEventIndication.Description"
::= { ibmSystempTrapEthernetAdapterPENDBindings 5 }

ibmSystempTrapEthernetAdapterPENDTimeStamp OBJECT-TYPE
   SYNTAX         Datetime
   ACCESS         read-only
   STATUS         mandatory
   DESCRIPTION    "The time that the trap occurred"
-- REFERENCE      "POWER_EthernetAdapterPENDEventIndication.TimeStamp"
::= { ibmSystempTrapEthernetAdapterPENDBindings 6 }


ibmSystempTrapEthernetAdapterPERF TRAP-TYPE
   ENTERPRISE     ibmSystemMIB
   VARIABLES    {
      ibmSystempTrapEthernetAdapterPERFProviderName,
      ibmSystempTrapEthernetAdapterPERFEventID,
      ibmSystempTrapEthernetAdapterPERFAME,
      ibmSystempTrapEthernetAdapterPERFSeverity,
      ibmSystempTrapEthernetAdapterPERFDescription,
      ibmSystempTrapEthernetAdapterPERFTimeStamp
   }
   DESCRIPTION    "A System p event has occurred"
-- REFERENCE      "POWER_EthernetAdapterPERFEventIndication"
::= 542

ibmSystempTrapEthernetAdapterPERFBindings OBJECT IDENTIFIER ::= { ibmSystemTrap 542 }

ibmSystempTrapEthernetAdapterPERFProviderName OBJECT-TYPE
   SYNTAX         String
   ACCESS         read-only
   STATUS         mandatory
   DESCRIPTION    "The name of the CIM Provider that monitors this device"
-- REFERENCE      "POWER_EthernetAdapterPERFEventIndication.ProviderName"
::= { ibmSystempTrapEthernetAdapterPERFBindings 1 }

ibmSystempTrapEthernetAdapterPERFEventID OBJECT-TYPE
   SYNTAX         String
   ACCESS         read-only
   STATUS         mandatory
   DESCRIPTION    "A unique EventID that identifies this trap" 
-- REFERENCE      "POWER_EthernetAdapterPERFEventIndication.EventID"
::= { ibmSystempTrapEthernetAdapterPERFBindings 2 }

ibmSystempTrapEthernetAdapterPERFAME OBJECT-TYPE
   SYNTAX         String
   ACCESS         read-only
   STATUS         mandatory
   DESCRIPTION    "A unique string that identifies the monitored device"
-- REFERENCE      "POWER_EthernetAdapterPERFEventIndication.AlertingManagedElement"
::= { ibmSystempTrapEthernetAdapterPERFBindings 3 }

ibmSystempTrapEthernetAdapterPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_EthernetAdapterPERFEventIndication.Severity"
::= { ibmSystempTrapEthernetAdapterPERFBindings 4 }

ibmSystempTrapEthernetAdapterPERFDescription OBJECT-TYPE
   SYNTAX         SnmpAdminString
   ACCESS         read-only
   STATUS         mandatory
   DESCRIPTION    "The Event text of the trap"
-- REFERENCE      "POWER_EthernetAdapterPERFEventIndication.Description"
::= { ibmSystempTrapEthernetAdapterPERFBindings 5 }

ibmSystempTrapEthernetAdapterPERFTimeStamp OBJECT-TYPE
   SYNTAX         Datetime
   ACCESS         read-only
   STATUS         mandatory
   DESCRIPTION    "The time that the trap occurred"
-- REFERENCE      "POWER_EthernetAdapterPERFEventIndication.TimeStamp"
::= { ibmSystempTrapEthernetAdapterPERFBindings 6 }


ibmSystempTrapEthernetAdapterUNKNOWN TRAP-TYPE
   ENTERPRISE     ibmSystemMIB
   VARIABLES    {
      ibmSystempTrapEthernetAdapterUNKNOWNProviderName,
      ibmSystempTrapEthernetAdapterUNKNOWNEventID,
      ibmSystempTrapEthernetAdapterUNKNOWNAME,
      ibmSystempTrapEthernetAdapterUNKNOWNSeverity,
      ibmSystempTrapEthernetAdapterUNKNOWNDescription,
      ibmSystempTrapEthernetAdapterUNKNOWNTimeStamp
   }
   DESCRIPTION    "A System p event has occurred"
-- REFERENCE      "POWER_EthernetAdapterUNKNOWNEventIndication"
::= 543

ibmSystempTrapEthernetAdapterUNKNOWNBindings OBJECT IDENTIFIER ::= { ibmSystemTrap 543 }

ibmSystempTrapEthernetAdapterUNKNOWNProviderName OBJECT-TYPE
   SYNTAX         String
   ACCESS         read-only
   STATUS         mandatory
   DESCRIPTION    "The name of the CIM Provider that monitors this device"
-- REFERENCE      "POWER_EthernetAdapterUNKNOWNEventIndication.ProviderName"
::= { ibmSystempTrapEthernetAdapterUNKNOWNBindings 1 }

ibmSystempTrapEthernetAdapterUNKNOWNEventID OBJECT-TYPE
   SYNTAX         String
   ACCESS         read-only
   STATUS         mandatory
   DESCRIPTION    "A unique EventID that identifies this trap" 
-- REFERENCE      "POWER_EthernetAdapterUNKNOWNEventIndication.EventID"
::= { ibmSystempTrapEthernetAdapterUNKNOWNBindings 2 }

ibmSystempTrapEthernetAdapterUNKNOWNAME OBJECT-TYPE
   SYNTAX         String
   ACCESS         read-only
   STATUS         mandatory
   DESCRIPTION    "A unique string that identifies the monitored device"
-- REFERENCE      "POWER_EthernetAdapterUNKNOWNEventIndication.AlertingManagedElement"
::= { ibmSystempTrapEthernetAdapterUNKNOWNBindings 3 }

ibmSystempTrapEthernetAdapterUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_EthernetAdapterUNKNOWNEventIndication.Severity"
::= { ibmSystempTrapEthernetAdapterUNKNOWNBindings 4 }

ibmSystempTrapEthernetAdapterUNKNOWNDescription OBJECT-TYPE
   SYNTAX         SnmpAdminString
   ACCESS         read-only
   STATUS         mandatory
   DESCRIPTION    "The Event text of the trap"
-- REFERENCE      "POWER_EthernetAdapterUNKNOWNEventIndication.Description"
::= { ibmSystempTrapEthernetAdapterUNKNOWNBindings 5 }

ibmSystempTrapEthernetAdapterUNKNOWNTimeStamp OBJECT-TYPE
   SYNTAX         Datetime
   ACCESS         read-only
   STATUS         mandatory
   DESCRIPTION    "The time that the trap occurred"
-- REFERENCE      "POWER_EthernetAdapterUNKNOWNEventIndication.TimeStamp"
::= { ibmSystempTrapEthernetAdapterUNKNOWNBindings 6 }


ibmSystempTrapEthernetAdapterPERM TRAP-TYPE
   ENTERPRISE     ibmSystemMIB
   VARIABLES    {
      ibmSystempTrapEthernetAdapterPERMProviderName,
      ibmSystempTrapEthernetAdapterPERMEventID,
      ibmSystempTrapEthernetAdapterPERMAME,
      ibmSystempTrapEthernetAdapterPERMSeverity,
      ibmSystempTrapEthernetAdapterPERMDescription,
      ibmSystempTrapEthernetAdapterPERMTimeStamp
   }
   DESCRIPTION    "A System p event has occurred"
-- REFERENCE      "POWER_EthernetAdapterPERMEventIndication"
::= 544

ibmSystempTrapEthernetAdapterPERMBindings OBJECT IDENTIFIER ::= { ibmSystemTrap 544 }

ibmSystempTrapEthernetAdapterPERMProviderName OBJECT-TYPE
   SYNTAX         String
   ACCESS         read-only
   STATUS         mandatory
   DESCRIPTION    "The name of the CIM Provider that monitors this device"
-- REFERENCE      "POWER_EthernetAdapterPERMEventIndication.ProviderName"
::= { ibmSystempTrapEthernetAdapterPERMBindings 1 }

ibmSystempTrapEthernetAdapterPERMEventID OBJECT-TYPE
   SYNTAX         String
   ACCESS         read-only
   STATUS         mandatory
   DESCRIPTION    "A unique EventID that identifies this trap" 
-- REFERENCE      "POWER_EthernetAdapterPERMEventIndication.EventID"
::= { ibmSystempTrapEthernetAdapterPERMBindings 2 }

ibmSystempTrapEthernetAdapterPERMAME OBJECT-TYPE
   SYNTAX         String
   ACCESS         read-only
   STATUS         mandatory
   DESCRIPTION    "A unique string that identifies the monitored device"
-- REFERENCE      "POWER_EthernetAdapterPERMEventIndication.AlertingManagedElement"
::= { ibmSystempTrapEthernetAdapterPERMBindings 3 }

ibmSystempTrapEthernetAdapterPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_EthernetAdapterPERMEventIndication.Severity"
::= { ibmSystempTrapEthernetAdapterPERMBindings 4 }

ibmSystempTrapEthernetAdapterPERMDescription OBJECT-TYPE
   SYNTAX         SnmpAdminString
   ACCESS         read-only
   STATUS         mandatory
   DESCRIPTION    "The Event text of the trap"
-- REFERENCE      "POWER_EthernetAdapterPERMEventIndication.Description"
::= { ibmSystempTrapEthernetAdapterPERMBindings 5 }

ibmSystempTrapEthernetAdapterPERMTimeStamp OBJECT-TYPE
   SYNTAX         Datetime
   ACCESS         read-only
   STATUS         mandatory
   DESCRIPTION    "The time that the trap occurred"
-- REFERENCE      "POWER_EthernetAdapterPERMEventIndication.TimeStamp"
::= { ibmSystempTrapEthernetAdapterPERMBindings 6 }


ibmSystempTrapFCAdapterINFO TRAP-TYPE
   ENTERPRISE     ibmSystemMIB
   VARIABLES    {
      ibmSystempTrapFCAdapterINFOProviderName,
      ibmSystempTrapFCAdapterINFOEventID,
      ibmSystempTrapFCAdapterINFOAME,
      ibmSystempTrapFCAdapterINFOSeverity,
      ibmSystempTrapFCAdapterINFODescription,
      ibmSystempTrapFCAdapterINFOTimeStamp
   }
   DESCRIPTION    "A System p event has occurred"
-- REFERENCE      "POWER_FCAdapterINFOEventIndication"
::= 545

ibmSystempTrapFCAdapterINFOBindings OBJECT IDENTIFIER ::= { ibmSystemTrap 545 }

ibmSystempTrapFCAdapterINFOProviderName OBJECT-TYPE
   SYNTAX         String
   ACCESS         read-only
   STATUS         mandatory
   DESCRIPTION    "The name of the CIM Provider that monitors this device"
-- REFERENCE      "POWER_FCAdapterINFOEventIndication.ProviderName"
::= { ibmSystempTrapFCAdapterINFOBindings 1 }

ibmSystempTrapFCAdapterINFOEventID OBJECT-TYPE
   SYNTAX         String
   ACCESS         read-only
   STATUS         mandatory
   DESCRIPTION    "A unique EventID that identifies this trap" 
-- REFERENCE      "POWER_FCAdapterINFOEventIndication.EventID"
::= { ibmSystempTrapFCAdapterINFOBindings 2 }

ibmSystempTrapFCAdapterINFOAME OBJECT-TYPE
   SYNTAX         String
   ACCESS         read-only
   STATUS         mandatory
   DESCRIPTION    "A unique string that identifies the monitored device"
-- REFERENCE      "POWER_FCAdapterINFOEventIndication.AlertingManagedElement"
::= { ibmSystempTrapFCAdapterINFOBindings 3 }

ibmSystempTrapFCAdapterINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FCAdapterINFOEventIndication.Severity"
::= { ibmSystempTrapFCAdapterINFOBindings 4 }

ibmSystempTrapFCAdapterINFODescription OBJECT-TYPE
   SYNTAX         SnmpAdminString
   ACCESS         read-only
   STATUS         mandatory
   DESCRIPTION    "The Event text of the trap"
-- REFERENCE      "POWER_FCAdapterINFOEventIndication.Description"
::= { ibmSystempTrapFCAdapterINFOBindings 5 }

ibmSystempTrapFCAdapterINFOTimeStamp OBJECT-TYPE
   SYNTAX         Datetime
   ACCESS         read-only
   STATUS         mandatory
   DESCRIPTION    "The time that the trap occurred"
-- REFERENCE      "POWER_FCAdapterINFOEventIndication.TimeStamp"
::= { ibmSystempTrapFCAdapterINFOBindings 6 }


ibmSystempTrapFCAdapterTEMP TRAP-TYPE
   ENTERPRISE     ibmSystemMIB
   VARIABLES    {
      ibmSystempTrapFCAdapterTEMPProviderName,
      ibmSystempTrapFCAdapterTEMPEventID,
      ibmSystempTrapFCAdapterTEMPAME,
      ibmSystempTrapFCAdapterTEMPSeverity,
      ibmSystempTrapFCAdapterTEMPDescription,
      ibmSystempTrapFCAdapterTEMPTimeStamp
   }
   DESCRIPTION    "A System p event has occurred"
-- REFERENCE      "POWER_FCAdapterTEMPEventIndication"
::= 546

ibmSystempTrapFCAdapterTEMPBindings OBJECT IDENTIFIER ::= { ibmSystemTrap 546 }

ibmSystempTrapFCAdapterTEMPProviderName OBJECT-TYPE
   SYNTAX         String
   ACCESS         read-only
   STATUS         mandatory
   DESCRIPTION    "The name of the CIM Provider that monitors this device"
-- REFERENCE      "POWER_FCAdapterTEMPEventIndication.ProviderName"
::= { ibmSystempTrapFCAdapterTEMPBindings 1 }

ibmSystempTrapFCAdapterTEMPEventID OBJECT-TYPE
   SYNTAX         String
   ACCESS         read-only
   STATUS         mandatory
   DESCRIPTION    "A unique EventID that identifies this trap" 
-- REFERENCE      "POWER_FCAdapterTEMPEventIndication.EventID"
::= { ibmSystempTrapFCAdapterTEMPBindings 2 }

ibmSystempTrapFCAdapterTEMPAME OBJECT-TYPE
   SYNTAX         String
   ACCESS         read-only
   STATUS         mandatory
   DESCRIPTION    "A unique string that identifies the monitored device"
-- REFERENCE      "POWER_FCAdapterTEMPEventIndication.AlertingManagedElement"
::= { ibmSystempTrapFCAdapterTEMPBindings 3 }

ibmSystempTrapFCAdapterTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FCAdapterTEMPEventIndication.Severity"
::= { ibmSystempTrapFCAdapterTEMPBindings 4 }

ibmSystempTrapFCAdapterTEMPDescription OBJECT-TYPE
   SYNTAX         SnmpAdminString
   ACCESS         read-only
   STATUS         mandatory
   DESCRIPTION    "The Event text of the trap"
-- REFERENCE      "POWER_FCAdapterTEMPEventIndication.Description"
::= { ibmSystempTrapFCAdapterTEMPBindings 5 }

ibmSystempTrapFCAdapterTEMPTimeStamp OBJECT-TYPE
   SYNTAX         Datetime
   ACCESS         read-only
   STATUS         mandatory
   DESCRIPTION    "The time that the trap occurred"
-- REFERENCE      "POWER_FCAdapterTEMPEventIndication.TimeStamp"
::= { ibmSystempTrapFCAdapterTEMPBindings 6 }


ibmSystempTrapFCAdapterPEND TRAP-TYPE
   ENTERPRISE     ibmSystemMIB
   VARIABLES    {
      ibmSystempTrapFCAdapterPENDProviderName,
      ibmSystempTrapFCAdapterPENDEventID,
      ibmSystempTrapFCAdapterPENDAME,
      ibmSystempTrapFCAdapterPENDSeverity,
      ibmSystempTrapFCAdapterPENDDescription,
      ibmSystempTrapFCAdapterPENDTimeStamp
   }
   DESCRIPTION    "A System p event has occurred"
-- REFERENCE      "POWER_FCAdapterPENDEventIndication"
::= 547

ibmSystempTrapFCAdapterPENDBindings OBJECT IDENTIFIER ::= { ibmSystemTrap 547 }

ibmSystempTrapFCAdapterPENDProviderName OBJECT-TYPE
   SYNTAX         String
   ACCESS         read-only
   STATUS         mandatory
   DESCRIPTION    "The name of the CIM Provider that monitors this device"
-- REFERENCE      "POWER_FCAdapterPENDEventIndication.ProviderName"
::= { ibmSystempTrapFCAdapterPENDBindings 1 }

ibmSystempTrapFCAdapterPENDEventID OBJECT-TYPE
   SYNTAX         String
   ACCESS         read-only
   STATUS         mandatory
   DESCRIPTION    "A unique EventID that identifies this trap" 
-- REFERENCE      "POWER_FCAdapterPENDEventIndication.EventID"
::= { ibmSystempTrapFCAdapterPENDBindings 2 }

ibmSystempTrapFCAdapterPENDAME OBJECT-TYPE
   SYNTAX         String
   ACCESS         read-only
   STATUS         mandatory
   DESCRIPTION    "A unique string that identifies the monitored device"
-- REFERENCE      "POWER_FCAdapterPENDEventIndication.AlertingManagedElement"
::= { ibmSystempTrapFCAdapterPENDBindings 3 }

ibmSystempTrapFCAdapterPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FCAdapterPENDEventIndication.Severity"
::= { ibmSystempTrapFCAdapterPENDBindings 4 }

ibmSystempTrapFCAdapterPENDDescription OBJECT-TYPE
   SYNTAX         SnmpAdminString
   ACCESS         read-only
   STATUS         mandatory
   DESCRIPTION    "The Event text of the trap"
-- REFERENCE      "POWER_FCAdapterPENDEventIndication.Description"
::= { ibmSystempTrapFCAdapterPENDBindings 5 }

ibmSystempTrapFCAdapterPENDTimeStamp OBJECT-TYPE
   SYNTAX         Datetime
   ACCESS         read-only
   STATUS         mandatory
   DESCRIPTION    "The time that the trap occurred"
-- REFERENCE      "POWER_FCAdapterPENDEventIndication.TimeStamp"
::= { ibmSystempTrapFCAdapterPENDBindings 6 }


ibmSystempTrapFCAdapterPERF TRAP-TYPE
   ENTERPRISE     ibmSystemMIB
   VARIABLES    {
      ibmSystempTrapFCAdapterPERFProviderName,
      ibmSystempTrapFCAdapterPERFEventID,
      ibmSystempTrapFCAdapterPERFAME,
      ibmSystempTrapFCAdapterPERFSeverity,
      ibmSystempTrapFCAdapterPERFDescription,
      ibmSystempTrapFCAdapterPERFTimeStamp
   }
   DESCRIPTION    "A System p event has occurred"
-- REFERENCE      "POWER_FCAdapterPERFEventIndication"
::= 548

ibmSystempTrapFCAdapterPERFBindings OBJECT IDENTIFIER ::= { ibmSystemTrap 548 }

ibmSystempTrapFCAdapterPERFProviderName OBJECT-TYPE
   SYNTAX         String
   ACCESS         read-only
   STATUS         mandatory
   DESCRIPTION    "The name of the CIM Provider that monitors this device"
-- REFERENCE      "POWER_FCAdapterPERFEventIndication.ProviderName"
::= { ibmSystempTrapFCAdapterPERFBindings 1 }

ibmSystempTrapFCAdapterPERFEventID OBJECT-TYPE
   SYNTAX         String
   ACCESS         read-only
   STATUS         mandatory
   DESCRIPTION    "A unique EventID that identifies this trap" 
-- REFERENCE      "POWER_FCAdapterPERFEventIndication.EventID"
::= { ibmSystempTrapFCAdapterPERFBindings 2 }

ibmSystempTrapFCAdapterPERFAME OBJECT-TYPE
   SYNTAX         String
   ACCESS         read-only
   STATUS         mandatory
   DESCRIPTION    "A unique string that identifies the monitored device"
-- REFERENCE      "POWER_FCAdapterPERFEventIndication.AlertingManagedElement"
::= { ibmSystempTrapFCAdapterPERFBindings 3 }

ibmSystempTrapFCAdapterPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FCAdapterPERFEventIndication.Severity"
::= { ibmSystempTrapFCAdapterPERFBindings 4 }

ibmSystempTrapFCAdapterPERFDescription OBJECT-TYPE
   SYNTAX         SnmpAdminString
   ACCESS         read-only
   STATUS         mandatory
   DESCRIPTION    "The Event text of the trap"
-- REFERENCE      "POWER_FCAdapterPERFEventIndication.Description"
::= { ibmSystempTrapFCAdapterPERFBindings 5 }

ibmSystempTrapFCAdapterPERFTimeStamp OBJECT-TYPE
   SYNTAX         Datetime
   ACCESS         read-only
   STATUS         mandatory
   DESCRIPTION    "The time that the trap occurred"
-- REFERENCE      "POWER_FCAdapterPERFEventIndication.TimeStamp"
::= { ibmSystempTrapFCAdapterPERFBindings 6 }


ibmSystempTrapFCAdapterUNKNOWN TRAP-TYPE
   ENTERPRISE     ibmSystemMIB
   VARIABLES    {
      ibmSystempTrapFCAdapterUNKNOWNProviderName,
      ibmSystempTrapFCAdapterUNKNOWNEventID,
      ibmSystempTrapFCAdapterUNKNOWNAME,
      ibmSystempTrapFCAdapterUNKNOWNSeverity,
      ibmSystempTrapFCAdapterUNKNOWNDescription,
      ibmSystempTrapFCAdapterUNKNOWNTimeStamp
   }
   DESCRIPTION    "A System p event has occurred"
-- REFERENCE      "POWER_FCAdapterUNKNOWNEventIndication"
::= 549

ibmSystempTrapFCAdapterUNKNOWNBindings OBJECT IDENTIFIER ::= { ibmSystemTrap 549 }

ibmSystempTrapFCAdapterUNKNOWNProviderName OBJECT-TYPE
   SYNTAX         String
   ACCESS         read-only
   STATUS         mandatory
   DESCRIPTION    "The name of the CIM Provider that monitors this device"
-- REFERENCE      "POWER_FCAdapterUNKNOWNEventIndication.ProviderName"
::= { ibmSystempTrapFCAdapterUNKNOWNBindings 1 }

ibmSystempTrapFCAdapterUNKNOWNEventID OBJECT-TYPE
   SYNTAX         String
   ACCESS         read-only
   STATUS         mandatory
   DESCRIPTION    "A unique EventID that identifies this trap" 
-- REFERENCE      "POWER_FCAdapterUNKNOWNEventIndication.EventID"
::= { ibmSystempTrapFCAdapterUNKNOWNBindings 2 }

ibmSystempTrapFCAdapterUNKNOWNAME OBJECT-TYPE
   SYNTAX         String
   ACCESS         read-only
   STATUS         mandatory
   DESCRIPTION    "A unique string that identifies the monitored device"
-- REFERENCE      "POWER_FCAdapterUNKNOWNEventIndication.AlertingManagedElement"
::= { ibmSystempTrapFCAdapterUNKNOWNBindings 3 }

ibmSystempTrapFCAdapterUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FCAdapterUNKNOWNEventIndication.Severity"
::= { ibmSystempTrapFCAdapterUNKNOWNBindings 4 }

ibmSystempTrapFCAdapterUNKNOWNDescription OBJECT-TYPE
   SYNTAX         SnmpAdminString
   ACCESS         read-only
   STATUS         mandatory
   DESCRIPTION    "The Event text of the trap"
-- REFERENCE      "POWER_FCAdapterUNKNOWNEventIndication.Description"
::= { ibmSystempTrapFCAdapterUNKNOWNBindings 5 }

ibmSystempTrapFCAdapterUNKNOWNTimeStamp OBJECT-TYPE
   SYNTAX         Datetime
   ACCESS         read-only
   STATUS         mandatory
   DESCRIPTION    "The time that the trap occurred"
-- REFERENCE      "POWER_FCAdapterUNKNOWNEventIndication.TimeStamp"
::= { ibmSystempTrapFCAdapterUNKNOWNBindings 6 }


ibmSystempTrapFCAdapterPERM TRAP-TYPE
   ENTERPRISE     ibmSystemMIB
   VARIABLES    {
      ibmSystempTrapFCAdapterPERMProviderName,
      ibmSystempTrapFCAdapterPERMEventID,
      ibmSystempTrapFCAdapterPERMAME,
      ibmSystempTrapFCAdapterPERMSeverity,
      ibmSystempTrapFCAdapterPERMDescription,
      ibmSystempTrapFCAdapterPERMTimeStamp
   }
   DESCRIPTION    "A System p event has occurred"
-- REFERENCE      "POWER_FCAdapterPERMEventIndication"
::= 550

ibmSystempTrapFCAdapterPERMBindings OBJECT IDENTIFIER ::= { ibmSystemTrap 550 }

ibmSystempTrapFCAdapterPERMProviderName OBJECT-TYPE
   SYNTAX         String
   ACCESS         read-only
   STATUS         mandatory
   DESCRIPTION    "The name of the CIM Provider that monitors this device"
-- REFERENCE      "POWER_FCAdapterPERMEventIndication.ProviderName"
::= { ibmSystempTrapFCAdapterPERMBindings 1 }

ibmSystempTrapFCAdapterPERMEventID OBJECT-TYPE
   SYNTAX         String
   ACCESS         read-only
   STATUS         mandatory
   DESCRIPTION    "A unique EventID that identifies this trap" 
-- REFERENCE      "POWER_FCAdapterPERMEventIndication.EventID"
::= { ibmSystempTrapFCAdapterPERMBindings 2 }

ibmSystempTrapFCAdapterPERMAME OBJECT-TYPE
   SYNTAX         String
   ACCESS         read-only
   STATUS         mandatory
   DESCRIPTION    "A unique string that identifies the monitored device"
-- REFERENCE      "POWER_FCAdapterPERMEventIndication.AlertingManagedElement"
::= { ibmSystempTrapFCAdapterPERMBindings 3 }

ibmSystempTrapFCAdapterPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_FCAdapterPERMEventIndication.Severity"
::= { ibmSystempTrapFCAdapterPERMBindings 4 }

ibmSystempTrapFCAdapterPERMDescription OBJECT-TYPE
   SYNTAX         SnmpAdminString
   ACCESS         read-only
   STATUS         mandatory
   DESCRIPTION    "The Event text of the trap"
-- REFERENCE      "POWER_FCAdapterPERMEventIndication.Description"
::= { ibmSystempTrapFCAdapterPERMBindings 5 }

ibmSystempTrapFCAdapterPERMTimeStamp OBJECT-TYPE
   SYNTAX         Datetime
   ACCESS         read-only
   STATUS         mandatory
   DESCRIPTION    "The time that the trap occurred"
-- REFERENCE      "POWER_FCAdapterPERMEventIndication.TimeStamp"
::= { ibmSystempTrapFCAdapterPERMBindings 6 }


ibmSystempTrapSASAdapterINFO TRAP-TYPE
   ENTERPRISE     ibmSystemMIB
   VARIABLES    {
      ibmSystempTrapSASAdapterINFOProviderName,
      ibmSystempTrapSASAdapterINFOEventID,
      ibmSystempTrapSASAdapterINFOAME,
      ibmSystempTrapSASAdapterINFOSeverity,
      ibmSystempTrapSASAdapterINFODescription,
      ibmSystempTrapSASAdapterINFOTimeStamp
   }
   DESCRIPTION    "A System p event has occurred"
-- REFERENCE      "POWER_SASAdapterINFOEventIndication"
::= 551

ibmSystempTrapSASAdapterINFOBindings OBJECT IDENTIFIER ::= { ibmSystemTrap 551 }

ibmSystempTrapSASAdapterINFOProviderName OBJECT-TYPE
   SYNTAX         String
   ACCESS         read-only
   STATUS         mandatory
   DESCRIPTION    "The name of the CIM Provider that monitors this device"
-- REFERENCE      "POWER_SASAdapterINFOEventIndication.ProviderName"
::= { ibmSystempTrapSASAdapterINFOBindings 1 }

ibmSystempTrapSASAdapterINFOEventID OBJECT-TYPE
   SYNTAX         String
   ACCESS         read-only
   STATUS         mandatory
   DESCRIPTION    "A unique EventID that identifies this trap" 
-- REFERENCE      "POWER_SASAdapterINFOEventIndication.EventID"
::= { ibmSystempTrapSASAdapterINFOBindings 2 }

ibmSystempTrapSASAdapterINFOAME OBJECT-TYPE
   SYNTAX         String
   ACCESS         read-only
   STATUS         mandatory
   DESCRIPTION    "A unique string that identifies the monitored device"
-- REFERENCE      "POWER_SASAdapterINFOEventIndication.AlertingManagedElement"
::= { ibmSystempTrapSASAdapterINFOBindings 3 }

ibmSystempTrapSASAdapterINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SASAdapterINFOEventIndication.Severity"
::= { ibmSystempTrapSASAdapterINFOBindings 4 }

ibmSystempTrapSASAdapterINFODescription OBJECT-TYPE
   SYNTAX         SnmpAdminString
   ACCESS         read-only
   STATUS         mandatory
   DESCRIPTION    "The Event text of the trap"
-- REFERENCE      "POWER_SASAdapterINFOEventIndication.Description"
::= { ibmSystempTrapSASAdapterINFOBindings 5 }

ibmSystempTrapSASAdapterINFOTimeStamp OBJECT-TYPE
   SYNTAX         Datetime
   ACCESS         read-only
   STATUS         mandatory
   DESCRIPTION    "The time that the trap occurred"
-- REFERENCE      "POWER_SASAdapterINFOEventIndication.TimeStamp"
::= { ibmSystempTrapSASAdapterINFOBindings 6 }


ibmSystempTrapSASAdapterTEMP TRAP-TYPE
   ENTERPRISE     ibmSystemMIB
   VARIABLES    {
      ibmSystempTrapSASAdapterTEMPProviderName,
      ibmSystempTrapSASAdapterTEMPEventID,
      ibmSystempTrapSASAdapterTEMPAME,
      ibmSystempTrapSASAdapterTEMPSeverity,
      ibmSystempTrapSASAdapterTEMPDescription,
      ibmSystempTrapSASAdapterTEMPTimeStamp
   }
   DESCRIPTION    "A System p event has occurred"
-- REFERENCE      "POWER_SASAdapterTEMPEventIndication"
::= 552

ibmSystempTrapSASAdapterTEMPBindings OBJECT IDENTIFIER ::= { ibmSystemTrap 552 }

ibmSystempTrapSASAdapterTEMPProviderName OBJECT-TYPE
   SYNTAX         String
   ACCESS         read-only
   STATUS         mandatory
   DESCRIPTION    "The name of the CIM Provider that monitors this device"
-- REFERENCE      "POWER_SASAdapterTEMPEventIndication.ProviderName"
::= { ibmSystempTrapSASAdapterTEMPBindings 1 }

ibmSystempTrapSASAdapterTEMPEventID OBJECT-TYPE
   SYNTAX         String
   ACCESS         read-only
   STATUS         mandatory
   DESCRIPTION    "A unique EventID that identifies this trap" 
-- REFERENCE      "POWER_SASAdapterTEMPEventIndication.EventID"
::= { ibmSystempTrapSASAdapterTEMPBindings 2 }

ibmSystempTrapSASAdapterTEMPAME OBJECT-TYPE
   SYNTAX         String
   ACCESS         read-only
   STATUS         mandatory
   DESCRIPTION    "A unique string that identifies the monitored device"
-- REFERENCE      "POWER_SASAdapterTEMPEventIndication.AlertingManagedElement"
::= { ibmSystempTrapSASAdapterTEMPBindings 3 }

ibmSystempTrapSASAdapterTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SASAdapterTEMPEventIndication.Severity"
::= { ibmSystempTrapSASAdapterTEMPBindings 4 }

ibmSystempTrapSASAdapterTEMPDescription OBJECT-TYPE
   SYNTAX         SnmpAdminString
   ACCESS         read-only
   STATUS         mandatory
   DESCRIPTION    "The Event text of the trap"
-- REFERENCE      "POWER_SASAdapterTEMPEventIndication.Description"
::= { ibmSystempTrapSASAdapterTEMPBindings 5 }

ibmSystempTrapSASAdapterTEMPTimeStamp OBJECT-TYPE
   SYNTAX         Datetime
   ACCESS         read-only
   STATUS         mandatory
   DESCRIPTION    "The time that the trap occurred"
-- REFERENCE      "POWER_SASAdapterTEMPEventIndication.TimeStamp"
::= { ibmSystempTrapSASAdapterTEMPBindings 6 }


ibmSystempTrapSASAdapterPEND TRAP-TYPE
   ENTERPRISE     ibmSystemMIB
   VARIABLES    {
      ibmSystempTrapSASAdapterPENDProviderName,
      ibmSystempTrapSASAdapterPENDEventID,
      ibmSystempTrapSASAdapterPENDAME,
      ibmSystempTrapSASAdapterPENDSeverity,
      ibmSystempTrapSASAdapterPENDDescription,
      ibmSystempTrapSASAdapterPENDTimeStamp
   }
   DESCRIPTION    "A System p event has occurred"
-- REFERENCE      "POWER_SASAdapterPENDEventIndication"
::= 553

ibmSystempTrapSASAdapterPENDBindings OBJECT IDENTIFIER ::= { ibmSystemTrap 553 }

ibmSystempTrapSASAdapterPENDProviderName OBJECT-TYPE
   SYNTAX         String
   ACCESS         read-only
   STATUS         mandatory
   DESCRIPTION    "The name of the CIM Provider that monitors this device"
-- REFERENCE      "POWER_SASAdapterPENDEventIndication.ProviderName"
::= { ibmSystempTrapSASAdapterPENDBindings 1 }

ibmSystempTrapSASAdapterPENDEventID OBJECT-TYPE
   SYNTAX         String
   ACCESS         read-only
   STATUS         mandatory
   DESCRIPTION    "A unique EventID that identifies this trap" 
-- REFERENCE      "POWER_SASAdapterPENDEventIndication.EventID"
::= { ibmSystempTrapSASAdapterPENDBindings 2 }

ibmSystempTrapSASAdapterPENDAME OBJECT-TYPE
   SYNTAX         String
   ACCESS         read-only
   STATUS         mandatory
   DESCRIPTION    "A unique string that identifies the monitored device"
-- REFERENCE      "POWER_SASAdapterPENDEventIndication.AlertingManagedElement"
::= { ibmSystempTrapSASAdapterPENDBindings 3 }

ibmSystempTrapSASAdapterPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SASAdapterPENDEventIndication.Severity"
::= { ibmSystempTrapSASAdapterPENDBindings 4 }

ibmSystempTrapSASAdapterPENDDescription OBJECT-TYPE
   SYNTAX         SnmpAdminString
   ACCESS         read-only
   STATUS         mandatory
   DESCRIPTION    "The Event text of the trap"
-- REFERENCE      "POWER_SASAdapterPENDEventIndication.Description"
::= { ibmSystempTrapSASAdapterPENDBindings 5 }

ibmSystempTrapSASAdapterPENDTimeStamp OBJECT-TYPE
   SYNTAX         Datetime
   ACCESS         read-only
   STATUS         mandatory
   DESCRIPTION    "The time that the trap occurred"
-- REFERENCE      "POWER_SASAdapterPENDEventIndication.TimeStamp"
::= { ibmSystempTrapSASAdapterPENDBindings 6 }


ibmSystempTrapSASAdapterPERF TRAP-TYPE
   ENTERPRISE     ibmSystemMIB
   VARIABLES    {
      ibmSystempTrapSASAdapterPERFProviderName,
      ibmSystempTrapSASAdapterPERFEventID,
      ibmSystempTrapSASAdapterPERFAME,
      ibmSystempTrapSASAdapterPERFSeverity,
      ibmSystempTrapSASAdapterPERFDescription,
      ibmSystempTrapSASAdapterPERFTimeStamp
   }
   DESCRIPTION    "A System p event has occurred"
-- REFERENCE      "POWER_SASAdapterPERFEventIndication"
::= 554

ibmSystempTrapSASAdapterPERFBindings OBJECT IDENTIFIER ::= { ibmSystemTrap 554 }

ibmSystempTrapSASAdapterPERFProviderName OBJECT-TYPE
   SYNTAX         String
   ACCESS         read-only
   STATUS         mandatory
   DESCRIPTION    "The name of the CIM Provider that monitors this device"
-- REFERENCE      "POWER_SASAdapterPERFEventIndication.ProviderName"
::= { ibmSystempTrapSASAdapterPERFBindings 1 }

ibmSystempTrapSASAdapterPERFEventID OBJECT-TYPE
   SYNTAX         String
   ACCESS         read-only
   STATUS         mandatory
   DESCRIPTION    "A unique EventID that identifies this trap" 
-- REFERENCE      "POWER_SASAdapterPERFEventIndication.EventID"
::= { ibmSystempTrapSASAdapterPERFBindings 2 }

ibmSystempTrapSASAdapterPERFAME OBJECT-TYPE
   SYNTAX         String
   ACCESS         read-only
   STATUS         mandatory
   DESCRIPTION    "A unique string that identifies the monitored device"
-- REFERENCE      "POWER_SASAdapterPERFEventIndication.AlertingManagedElement"
::= { ibmSystempTrapSASAdapterPERFBindings 3 }

ibmSystempTrapSASAdapterPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SASAdapterPERFEventIndication.Severity"
::= { ibmSystempTrapSASAdapterPERFBindings 4 }

ibmSystempTrapSASAdapterPERFDescription OBJECT-TYPE
   SYNTAX         SnmpAdminString
   ACCESS         read-only
   STATUS         mandatory
   DESCRIPTION    "The Event text of the trap"
-- REFERENCE      "POWER_SASAdapterPERFEventIndication.Description"
::= { ibmSystempTrapSASAdapterPERFBindings 5 }

ibmSystempTrapSASAdapterPERFTimeStamp OBJECT-TYPE
   SYNTAX         Datetime
   ACCESS         read-only
   STATUS         mandatory
   DESCRIPTION    "The time that the trap occurred"
-- REFERENCE      "POWER_SASAdapterPERFEventIndication.TimeStamp"
::= { ibmSystempTrapSASAdapterPERFBindings 6 }


ibmSystempTrapSASAdapterUNKNOWN TRAP-TYPE
   ENTERPRISE     ibmSystemMIB
   VARIABLES    {
      ibmSystempTrapSASAdapterUNKNOWNProviderName,
      ibmSystempTrapSASAdapterUNKNOWNEventID,
      ibmSystempTrapSASAdapterUNKNOWNAME,
      ibmSystempTrapSASAdapterUNKNOWNSeverity,
      ibmSystempTrapSASAdapterUNKNOWNDescription,
      ibmSystempTrapSASAdapterUNKNOWNTimeStamp
   }
   DESCRIPTION    "A System p event has occurred"
-- REFERENCE      "POWER_SASAdapterUNKNOWNEventIndication"
::= 555

ibmSystempTrapSASAdapterUNKNOWNBindings OBJECT IDENTIFIER ::= { ibmSystemTrap 555 }

ibmSystempTrapSASAdapterUNKNOWNProviderName OBJECT-TYPE
   SYNTAX         String
   ACCESS         read-only
   STATUS         mandatory
   DESCRIPTION    "The name of the CIM Provider that monitors this device"
-- REFERENCE      "POWER_SASAdapterUNKNOWNEventIndication.ProviderName"
::= { ibmSystempTrapSASAdapterUNKNOWNBindings 1 }

ibmSystempTrapSASAdapterUNKNOWNEventID OBJECT-TYPE
   SYNTAX         String
   ACCESS         read-only
   STATUS         mandatory
   DESCRIPTION    "A unique EventID that identifies this trap" 
-- REFERENCE      "POWER_SASAdapterUNKNOWNEventIndication.EventID"
::= { ibmSystempTrapSASAdapterUNKNOWNBindings 2 }

ibmSystempTrapSASAdapterUNKNOWNAME OBJECT-TYPE
   SYNTAX         String
   ACCESS         read-only
   STATUS         mandatory
   DESCRIPTION    "A unique string that identifies the monitored device"
-- REFERENCE      "POWER_SASAdapterUNKNOWNEventIndication.AlertingManagedElement"
::= { ibmSystempTrapSASAdapterUNKNOWNBindings 3 }

ibmSystempTrapSASAdapterUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SASAdapterUNKNOWNEventIndication.Severity"
::= { ibmSystempTrapSASAdapterUNKNOWNBindings 4 }

ibmSystempTrapSASAdapterUNKNOWNDescription OBJECT-TYPE
   SYNTAX         SnmpAdminString
   ACCESS         read-only
   STATUS         mandatory
   DESCRIPTION    "The Event text of the trap"
-- REFERENCE      "POWER_SASAdapterUNKNOWNEventIndication.Description"
::= { ibmSystempTrapSASAdapterUNKNOWNBindings 5 }

ibmSystempTrapSASAdapterUNKNOWNTimeStamp OBJECT-TYPE
   SYNTAX         Datetime
   ACCESS         read-only
   STATUS         mandatory
   DESCRIPTION    "The time that the trap occurred"
-- REFERENCE      "POWER_SASAdapterUNKNOWNEventIndication.TimeStamp"
::= { ibmSystempTrapSASAdapterUNKNOWNBindings 6 }


ibmSystempTrapSASAdapterPERM TRAP-TYPE
   ENTERPRISE     ibmSystemMIB
   VARIABLES    {
      ibmSystempTrapSASAdapterPERMProviderName,
      ibmSystempTrapSASAdapterPERMEventID,
      ibmSystempTrapSASAdapterPERMAME,
      ibmSystempTrapSASAdapterPERMSeverity,
      ibmSystempTrapSASAdapterPERMDescription,
      ibmSystempTrapSASAdapterPERMTimeStamp
   }
   DESCRIPTION    "A System p event has occurred"
-- REFERENCE      "POWER_SASAdapterPERMEventIndication"
::= 556

ibmSystempTrapSASAdapterPERMBindings OBJECT IDENTIFIER ::= { ibmSystemTrap 556 }

ibmSystempTrapSASAdapterPERMProviderName OBJECT-TYPE
   SYNTAX         String
   ACCESS         read-only
   STATUS         mandatory
   DESCRIPTION    "The name of the CIM Provider that monitors this device"
-- REFERENCE      "POWER_SASAdapterPERMEventIndication.ProviderName"
::= { ibmSystempTrapSASAdapterPERMBindings 1 }

ibmSystempTrapSASAdapterPERMEventID OBJECT-TYPE
   SYNTAX         String
   ACCESS         read-only
   STATUS         mandatory
   DESCRIPTION    "A unique EventID that identifies this trap" 
-- REFERENCE      "POWER_SASAdapterPERMEventIndication.EventID"
::= { ibmSystempTrapSASAdapterPERMBindings 2 }

ibmSystempTrapSASAdapterPERMAME OBJECT-TYPE
   SYNTAX         String
   ACCESS         read-only
   STATUS         mandatory
   DESCRIPTION    "A unique string that identifies the monitored device"
-- REFERENCE      "POWER_SASAdapterPERMEventIndication.AlertingManagedElement"
::= { ibmSystempTrapSASAdapterPERMBindings 3 }

ibmSystempTrapSASAdapterPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SASAdapterPERMEventIndication.Severity"
::= { ibmSystempTrapSASAdapterPERMBindings 4 }

ibmSystempTrapSASAdapterPERMDescription OBJECT-TYPE
   SYNTAX         SnmpAdminString
   ACCESS         read-only
   STATUS         mandatory
   DESCRIPTION    "The Event text of the trap"
-- REFERENCE      "POWER_SASAdapterPERMEventIndication.Description"
::= { ibmSystempTrapSASAdapterPERMBindings 5 }

ibmSystempTrapSASAdapterPERMTimeStamp OBJECT-TYPE
   SYNTAX         Datetime
   ACCESS         read-only
   STATUS         mandatory
   DESCRIPTION    "The time that the trap occurred"
-- REFERENCE      "POWER_SASAdapterPERMEventIndication.TimeStamp"
::= { ibmSystempTrapSASAdapterPERMBindings 6 }


ibmSystempTrapSerialAdapterINFO TRAP-TYPE
   ENTERPRISE     ibmSystemMIB
   VARIABLES    {
      ibmSystempTrapSerialAdapterINFOProviderName,
      ibmSystempTrapSerialAdapterINFOEventID,
      ibmSystempTrapSerialAdapterINFOAME,
      ibmSystempTrapSerialAdapterINFOSeverity,
      ibmSystempTrapSerialAdapterINFODescription,
      ibmSystempTrapSerialAdapterINFOTimeStamp
   }
   DESCRIPTION    "A System p event has occurred"
-- REFERENCE      "POWER_SerialAdapterINFOEventIndication"
::= 557

ibmSystempTrapSerialAdapterINFOBindings OBJECT IDENTIFIER ::= { ibmSystemTrap 557 }

ibmSystempTrapSerialAdapterINFOProviderName OBJECT-TYPE
   SYNTAX         String
   ACCESS         read-only
   STATUS         mandatory
   DESCRIPTION    "The name of the CIM Provider that monitors this device"
-- REFERENCE      "POWER_SerialAdapterINFOEventIndication.ProviderName"
::= { ibmSystempTrapSerialAdapterINFOBindings 1 }

ibmSystempTrapSerialAdapterINFOEventID OBJECT-TYPE
   SYNTAX         String
   ACCESS         read-only
   STATUS         mandatory
   DESCRIPTION    "A unique EventID that identifies this trap" 
-- REFERENCE      "POWER_SerialAdapterINFOEventIndication.EventID"
::= { ibmSystempTrapSerialAdapterINFOBindings 2 }

ibmSystempTrapSerialAdapterINFOAME OBJECT-TYPE
   SYNTAX         String
   ACCESS         read-only
   STATUS         mandatory
   DESCRIPTION    "A unique string that identifies the monitored device"
-- REFERENCE      "POWER_SerialAdapterINFOEventIndication.AlertingManagedElement"
::= { ibmSystempTrapSerialAdapterINFOBindings 3 }

ibmSystempTrapSerialAdapterINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SerialAdapterINFOEventIndication.Severity"
::= { ibmSystempTrapSerialAdapterINFOBindings 4 }

ibmSystempTrapSerialAdapterINFODescription OBJECT-TYPE
   SYNTAX         SnmpAdminString
   ACCESS         read-only
   STATUS         mandatory
   DESCRIPTION    "The Event text of the trap"
-- REFERENCE      "POWER_SerialAdapterINFOEventIndication.Description"
::= { ibmSystempTrapSerialAdapterINFOBindings 5 }

ibmSystempTrapSerialAdapterINFOTimeStamp OBJECT-TYPE
   SYNTAX         Datetime
   ACCESS         read-only
   STATUS         mandatory
   DESCRIPTION    "The time that the trap occurred"
-- REFERENCE      "POWER_SerialAdapterINFOEventIndication.TimeStamp"
::= { ibmSystempTrapSerialAdapterINFOBindings 6 }


ibmSystempTrapSerialAdapterTEMP TRAP-TYPE
   ENTERPRISE     ibmSystemMIB
   VARIABLES    {
      ibmSystempTrapSerialAdapterTEMPProviderName,
      ibmSystempTrapSerialAdapterTEMPEventID,
      ibmSystempTrapSerialAdapterTEMPAME,
      ibmSystempTrapSerialAdapterTEMPSeverity,
      ibmSystempTrapSerialAdapterTEMPDescription,
      ibmSystempTrapSerialAdapterTEMPTimeStamp
   }
   DESCRIPTION    "A System p event has occurred"
-- REFERENCE      "POWER_SerialAdapterTEMPEventIndication"
::= 558

ibmSystempTrapSerialAdapterTEMPBindings OBJECT IDENTIFIER ::= { ibmSystemTrap 558 }

ibmSystempTrapSerialAdapterTEMPProviderName OBJECT-TYPE
   SYNTAX         String
   ACCESS         read-only
   STATUS         mandatory
   DESCRIPTION    "The name of the CIM Provider that monitors this device"
-- REFERENCE      "POWER_SerialAdapterTEMPEventIndication.ProviderName"
::= { ibmSystempTrapSerialAdapterTEMPBindings 1 }

ibmSystempTrapSerialAdapterTEMPEventID OBJECT-TYPE
   SYNTAX         String
   ACCESS         read-only
   STATUS         mandatory
   DESCRIPTION    "A unique EventID that identifies this trap" 
-- REFERENCE      "POWER_SerialAdapterTEMPEventIndication.EventID"
::= { ibmSystempTrapSerialAdapterTEMPBindings 2 }

ibmSystempTrapSerialAdapterTEMPAME OBJECT-TYPE
   SYNTAX         String
   ACCESS         read-only
   STATUS         mandatory
   DESCRIPTION    "A unique string that identifies the monitored device"
-- REFERENCE      "POWER_SerialAdapterTEMPEventIndication.AlertingManagedElement"
::= { ibmSystempTrapSerialAdapterTEMPBindings 3 }

ibmSystempTrapSerialAdapterTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SerialAdapterTEMPEventIndication.Severity"
::= { ibmSystempTrapSerialAdapterTEMPBindings 4 }

ibmSystempTrapSerialAdapterTEMPDescription OBJECT-TYPE
   SYNTAX         SnmpAdminString
   ACCESS         read-only
   STATUS         mandatory
   DESCRIPTION    "The Event text of the trap"
-- REFERENCE      "POWER_SerialAdapterTEMPEventIndication.Description"
::= { ibmSystempTrapSerialAdapterTEMPBindings 5 }

ibmSystempTrapSerialAdapterTEMPTimeStamp OBJECT-TYPE
   SYNTAX         Datetime
   ACCESS         read-only
   STATUS         mandatory
   DESCRIPTION    "The time that the trap occurred"
-- REFERENCE      "POWER_SerialAdapterTEMPEventIndication.TimeStamp"
::= { ibmSystempTrapSerialAdapterTEMPBindings 6 }


ibmSystempTrapSerialAdapterPEND TRAP-TYPE
   ENTERPRISE     ibmSystemMIB
   VARIABLES    {
      ibmSystempTrapSerialAdapterPENDProviderName,
      ibmSystempTrapSerialAdapterPENDEventID,
      ibmSystempTrapSerialAdapterPENDAME,
      ibmSystempTrapSerialAdapterPENDSeverity,
      ibmSystempTrapSerialAdapterPENDDescription,
      ibmSystempTrapSerialAdapterPENDTimeStamp
   }
   DESCRIPTION    "A System p event has occurred"
-- REFERENCE      "POWER_SerialAdapterPENDEventIndication"
::= 559

ibmSystempTrapSerialAdapterPENDBindings OBJECT IDENTIFIER ::= { ibmSystemTrap 559 }

ibmSystempTrapSerialAdapterPENDProviderName OBJECT-TYPE
   SYNTAX         String
   ACCESS         read-only
   STATUS         mandatory
   DESCRIPTION    "The name of the CIM Provider that monitors this device"
-- REFERENCE      "POWER_SerialAdapterPENDEventIndication.ProviderName"
::= { ibmSystempTrapSerialAdapterPENDBindings 1 }

ibmSystempTrapSerialAdapterPENDEventID OBJECT-TYPE
   SYNTAX         String
   ACCESS         read-only
   STATUS         mandatory
   DESCRIPTION    "A unique EventID that identifies this trap" 
-- REFERENCE      "POWER_SerialAdapterPENDEventIndication.EventID"
::= { ibmSystempTrapSerialAdapterPENDBindings 2 }

ibmSystempTrapSerialAdapterPENDAME OBJECT-TYPE
   SYNTAX         String
   ACCESS         read-only
   STATUS         mandatory
   DESCRIPTION    "A unique string that identifies the monitored device"
-- REFERENCE      "POWER_SerialAdapterPENDEventIndication.AlertingManagedElement"
::= { ibmSystempTrapSerialAdapterPENDBindings 3 }

ibmSystempTrapSerialAdapterPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SerialAdapterPENDEventIndication.Severity"
::= { ibmSystempTrapSerialAdapterPENDBindings 4 }

ibmSystempTrapSerialAdapterPENDDescription OBJECT-TYPE
   SYNTAX         SnmpAdminString
   ACCESS         read-only
   STATUS         mandatory
   DESCRIPTION    "The Event text of the trap"
-- REFERENCE      "POWER_SerialAdapterPENDEventIndication.Description"
::= { ibmSystempTrapSerialAdapterPENDBindings 5 }

ibmSystempTrapSerialAdapterPENDTimeStamp OBJECT-TYPE
   SYNTAX         Datetime
   ACCESS         read-only
   STATUS         mandatory
   DESCRIPTION    "The time that the trap occurred"
-- REFERENCE      "POWER_SerialAdapterPENDEventIndication.TimeStamp"
::= { ibmSystempTrapSerialAdapterPENDBindings 6 }


ibmSystempTrapSerialAdapterPERF TRAP-TYPE
   ENTERPRISE     ibmSystemMIB
   VARIABLES    {
      ibmSystempTrapSerialAdapterPERFProviderName,
      ibmSystempTrapSerialAdapterPERFEventID,
      ibmSystempTrapSerialAdapterPERFAME,
      ibmSystempTrapSerialAdapterPERFSeverity,
      ibmSystempTrapSerialAdapterPERFDescription,
      ibmSystempTrapSerialAdapterPERFTimeStamp
   }
   DESCRIPTION    "A System p event has occurred"
-- REFERENCE      "POWER_SerialAdapterPERFEventIndication"
::= 560

ibmSystempTrapSerialAdapterPERFBindings OBJECT IDENTIFIER ::= { ibmSystemTrap 560 }

ibmSystempTrapSerialAdapterPERFProviderName OBJECT-TYPE
   SYNTAX         String
   ACCESS         read-only
   STATUS         mandatory
   DESCRIPTION    "The name of the CIM Provider that monitors this device"
-- REFERENCE      "POWER_SerialAdapterPERFEventIndication.ProviderName"
::= { ibmSystempTrapSerialAdapterPERFBindings 1 }

ibmSystempTrapSerialAdapterPERFEventID OBJECT-TYPE
   SYNTAX         String
   ACCESS         read-only
   STATUS         mandatory
   DESCRIPTION    "A unique EventID that identifies this trap" 
-- REFERENCE      "POWER_SerialAdapterPERFEventIndication.EventID"
::= { ibmSystempTrapSerialAdapterPERFBindings 2 }

ibmSystempTrapSerialAdapterPERFAME OBJECT-TYPE
   SYNTAX         String
   ACCESS         read-only
   STATUS         mandatory
   DESCRIPTION    "A unique string that identifies the monitored device"
-- REFERENCE      "POWER_SerialAdapterPERFEventIndication.AlertingManagedElement"
::= { ibmSystempTrapSerialAdapterPERFBindings 3 }

ibmSystempTrapSerialAdapterPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SerialAdapterPERFEventIndication.Severity"
::= { ibmSystempTrapSerialAdapterPERFBindings 4 }

ibmSystempTrapSerialAdapterPERFDescription OBJECT-TYPE
   SYNTAX         SnmpAdminString
   ACCESS         read-only
   STATUS         mandatory
   DESCRIPTION    "The Event text of the trap"
-- REFERENCE      "POWER_SerialAdapterPERFEventIndication.Description"
::= { ibmSystempTrapSerialAdapterPERFBindings 5 }

ibmSystempTrapSerialAdapterPERFTimeStamp OBJECT-TYPE
   SYNTAX         Datetime
   ACCESS         read-only
   STATUS         mandatory
   DESCRIPTION    "The time that the trap occurred"
-- REFERENCE      "POWER_SerialAdapterPERFEventIndication.TimeStamp"
::= { ibmSystempTrapSerialAdapterPERFBindings 6 }


ibmSystempTrapSerialAdapterUNKNOWN TRAP-TYPE
   ENTERPRISE     ibmSystemMIB
   VARIABLES    {
      ibmSystempTrapSerialAdapterUNKNOWNProviderName,
      ibmSystempTrapSerialAdapterUNKNOWNEventID,
      ibmSystempTrapSerialAdapterUNKNOWNAME,
      ibmSystempTrapSerialAdapterUNKNOWNSeverity,
      ibmSystempTrapSerialAdapterUNKNOWNDescription,
      ibmSystempTrapSerialAdapterUNKNOWNTimeStamp
   }
   DESCRIPTION    "A System p event has occurred"
-- REFERENCE      "POWER_SerialAdapterUNKNOWNEventIndication"
::= 561

ibmSystempTrapSerialAdapterUNKNOWNBindings OBJECT IDENTIFIER ::= { ibmSystemTrap 561 }

ibmSystempTrapSerialAdapterUNKNOWNProviderName OBJECT-TYPE
   SYNTAX         String
   ACCESS         read-only
   STATUS         mandatory
   DESCRIPTION    "The name of the CIM Provider that monitors this device"
-- REFERENCE      "POWER_SerialAdapterUNKNOWNEventIndication.ProviderName"
::= { ibmSystempTrapSerialAdapterUNKNOWNBindings 1 }

ibmSystempTrapSerialAdapterUNKNOWNEventID OBJECT-TYPE
   SYNTAX         String
   ACCESS         read-only
   STATUS         mandatory
   DESCRIPTION    "A unique EventID that identifies this trap" 
-- REFERENCE      "POWER_SerialAdapterUNKNOWNEventIndication.EventID"
::= { ibmSystempTrapSerialAdapterUNKNOWNBindings 2 }

ibmSystempTrapSerialAdapterUNKNOWNAME OBJECT-TYPE
   SYNTAX         String
   ACCESS         read-only
   STATUS         mandatory
   DESCRIPTION    "A unique string that identifies the monitored device"
-- REFERENCE      "POWER_SerialAdapterUNKNOWNEventIndication.AlertingManagedElement"
::= { ibmSystempTrapSerialAdapterUNKNOWNBindings 3 }

ibmSystempTrapSerialAdapterUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SerialAdapterUNKNOWNEventIndication.Severity"
::= { ibmSystempTrapSerialAdapterUNKNOWNBindings 4 }

ibmSystempTrapSerialAdapterUNKNOWNDescription OBJECT-TYPE
   SYNTAX         SnmpAdminString
   ACCESS         read-only
   STATUS         mandatory
   DESCRIPTION    "The Event text of the trap"
-- REFERENCE      "POWER_SerialAdapterUNKNOWNEventIndication.Description"
::= { ibmSystempTrapSerialAdapterUNKNOWNBindings 5 }

ibmSystempTrapSerialAdapterUNKNOWNTimeStamp OBJECT-TYPE
   SYNTAX         Datetime
   ACCESS         read-only
   STATUS         mandatory
   DESCRIPTION    "The time that the trap occurred"
-- REFERENCE      "POWER_SerialAdapterUNKNOWNEventIndication.TimeStamp"
::= { ibmSystempTrapSerialAdapterUNKNOWNBindings 6 }


ibmSystempTrapSerialAdapterPERM TRAP-TYPE
   ENTERPRISE     ibmSystemMIB
   VARIABLES    {
      ibmSystempTrapSerialAdapterPERMProviderName,
      ibmSystempTrapSerialAdapterPERMEventID,
      ibmSystempTrapSerialAdapterPERMAME,
      ibmSystempTrapSerialAdapterPERMSeverity,
      ibmSystempTrapSerialAdapterPERMDescription,
      ibmSystempTrapSerialAdapterPERMTimeStamp
   }
   DESCRIPTION    "A System p event has occurred"
-- REFERENCE      "POWER_SerialAdapterPERMEventIndication"
::= 562

ibmSystempTrapSerialAdapterPERMBindings OBJECT IDENTIFIER ::= { ibmSystemTrap 562 }

ibmSystempTrapSerialAdapterPERMProviderName OBJECT-TYPE
   SYNTAX         String
   ACCESS         read-only
   STATUS         mandatory
   DESCRIPTION    "The name of the CIM Provider that monitors this device"
-- REFERENCE      "POWER_SerialAdapterPERMEventIndication.ProviderName"
::= { ibmSystempTrapSerialAdapterPERMBindings 1 }

ibmSystempTrapSerialAdapterPERMEventID OBJECT-TYPE
   SYNTAX         String
   ACCESS         read-only
   STATUS         mandatory
   DESCRIPTION    "A unique EventID that identifies this trap" 
-- REFERENCE      "POWER_SerialAdapterPERMEventIndication.EventID"
::= { ibmSystempTrapSerialAdapterPERMBindings 2 }

ibmSystempTrapSerialAdapterPERMAME OBJECT-TYPE
   SYNTAX         String
   ACCESS         read-only
   STATUS         mandatory
   DESCRIPTION    "A unique string that identifies the monitored device"
-- REFERENCE      "POWER_SerialAdapterPERMEventIndication.AlertingManagedElement"
::= { ibmSystempTrapSerialAdapterPERMBindings 3 }

ibmSystempTrapSerialAdapterPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SerialAdapterPERMEventIndication.Severity"
::= { ibmSystempTrapSerialAdapterPERMBindings 4 }

ibmSystempTrapSerialAdapterPERMDescription OBJECT-TYPE
   SYNTAX         SnmpAdminString
   ACCESS         read-only
   STATUS         mandatory
   DESCRIPTION    "The Event text of the trap"
-- REFERENCE      "POWER_SerialAdapterPERMEventIndication.Description"
::= { ibmSystempTrapSerialAdapterPERMBindings 5 }

ibmSystempTrapSerialAdapterPERMTimeStamp OBJECT-TYPE
   SYNTAX         Datetime
   ACCESS         read-only
   STATUS         mandatory
   DESCRIPTION    "The time that the trap occurred"
-- REFERENCE      "POWER_SerialAdapterPERMEventIndication.TimeStamp"
::= { ibmSystempTrapSerialAdapterPERMBindings 6 }


ibmSystempTrapUSBAdapterINFO TRAP-TYPE
   ENTERPRISE     ibmSystemMIB
   VARIABLES    {
      ibmSystempTrapUSBAdapterINFOProviderName,
      ibmSystempTrapUSBAdapterINFOEventID,
      ibmSystempTrapUSBAdapterINFOAME,
      ibmSystempTrapUSBAdapterINFOSeverity,
      ibmSystempTrapUSBAdapterINFODescription,
      ibmSystempTrapUSBAdapterINFOTimeStamp
   }
   DESCRIPTION    "A System p event has occurred"
-- REFERENCE      "POWER_USBAdapterINFOEventIndication"
::= 563

ibmSystempTrapUSBAdapterINFOBindings OBJECT IDENTIFIER ::= { ibmSystemTrap 563 }

ibmSystempTrapUSBAdapterINFOProviderName OBJECT-TYPE
   SYNTAX         String
   ACCESS         read-only
   STATUS         mandatory
   DESCRIPTION    "The name of the CIM Provider that monitors this device"
-- REFERENCE      "POWER_USBAdapterINFOEventIndication.ProviderName"
::= { ibmSystempTrapUSBAdapterINFOBindings 1 }

ibmSystempTrapUSBAdapterINFOEventID OBJECT-TYPE
   SYNTAX         String
   ACCESS         read-only
   STATUS         mandatory
   DESCRIPTION    "A unique EventID that identifies this trap" 
-- REFERENCE      "POWER_USBAdapterINFOEventIndication.EventID"
::= { ibmSystempTrapUSBAdapterINFOBindings 2 }

ibmSystempTrapUSBAdapterINFOAME OBJECT-TYPE
   SYNTAX         String
   ACCESS         read-only
   STATUS         mandatory
   DESCRIPTION    "A unique string that identifies the monitored device"
-- REFERENCE      "POWER_USBAdapterINFOEventIndication.AlertingManagedElement"
::= { ibmSystempTrapUSBAdapterINFOBindings 3 }

ibmSystempTrapUSBAdapterINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBAdapterINFOEventIndication.Severity"
::= { ibmSystempTrapUSBAdapterINFOBindings 4 }

ibmSystempTrapUSBAdapterINFODescription OBJECT-TYPE
   SYNTAX         SnmpAdminString
   ACCESS         read-only
   STATUS         mandatory
   DESCRIPTION    "The Event text of the trap"
-- REFERENCE      "POWER_USBAdapterINFOEventIndication.Description"
::= { ibmSystempTrapUSBAdapterINFOBindings 5 }

ibmSystempTrapUSBAdapterINFOTimeStamp OBJECT-TYPE
   SYNTAX         Datetime
   ACCESS         read-only
   STATUS         mandatory
   DESCRIPTION    "The time that the trap occurred"
-- REFERENCE      "POWER_USBAdapterINFOEventIndication.TimeStamp"
::= { ibmSystempTrapUSBAdapterINFOBindings 6 }


ibmSystempTrapUSBAdapterTEMP TRAP-TYPE
   ENTERPRISE     ibmSystemMIB
   VARIABLES    {
      ibmSystempTrapUSBAdapterTEMPProviderName,
      ibmSystempTrapUSBAdapterTEMPEventID,
      ibmSystempTrapUSBAdapterTEMPAME,
      ibmSystempTrapUSBAdapterTEMPSeverity,
      ibmSystempTrapUSBAdapterTEMPDescription,
      ibmSystempTrapUSBAdapterTEMPTimeStamp
   }
   DESCRIPTION    "A System p event has occurred"
-- REFERENCE      "POWER_USBAdapterTEMPEventIndication"
::= 564

ibmSystempTrapUSBAdapterTEMPBindings OBJECT IDENTIFIER ::= { ibmSystemTrap 564 }

ibmSystempTrapUSBAdapterTEMPProviderName OBJECT-TYPE
   SYNTAX         String
   ACCESS         read-only
   STATUS         mandatory
   DESCRIPTION    "The name of the CIM Provider that monitors this device"
-- REFERENCE      "POWER_USBAdapterTEMPEventIndication.ProviderName"
::= { ibmSystempTrapUSBAdapterTEMPBindings 1 }

ibmSystempTrapUSBAdapterTEMPEventID OBJECT-TYPE
   SYNTAX         String
   ACCESS         read-only
   STATUS         mandatory
   DESCRIPTION    "A unique EventID that identifies this trap" 
-- REFERENCE      "POWER_USBAdapterTEMPEventIndication.EventID"
::= { ibmSystempTrapUSBAdapterTEMPBindings 2 }

ibmSystempTrapUSBAdapterTEMPAME OBJECT-TYPE
   SYNTAX         String
   ACCESS         read-only
   STATUS         mandatory
   DESCRIPTION    "A unique string that identifies the monitored device"
-- REFERENCE      "POWER_USBAdapterTEMPEventIndication.AlertingManagedElement"
::= { ibmSystempTrapUSBAdapterTEMPBindings 3 }

ibmSystempTrapUSBAdapterTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBAdapterTEMPEventIndication.Severity"
::= { ibmSystempTrapUSBAdapterTEMPBindings 4 }

ibmSystempTrapUSBAdapterTEMPDescription OBJECT-TYPE
   SYNTAX         SnmpAdminString
   ACCESS         read-only
   STATUS         mandatory
   DESCRIPTION    "The Event text of the trap"
-- REFERENCE      "POWER_USBAdapterTEMPEventIndication.Description"
::= { ibmSystempTrapUSBAdapterTEMPBindings 5 }

ibmSystempTrapUSBAdapterTEMPTimeStamp OBJECT-TYPE
   SYNTAX         Datetime
   ACCESS         read-only
   STATUS         mandatory
   DESCRIPTION    "The time that the trap occurred"
-- REFERENCE      "POWER_USBAdapterTEMPEventIndication.TimeStamp"
::= { ibmSystempTrapUSBAdapterTEMPBindings 6 }


ibmSystempTrapUSBAdapterPEND TRAP-TYPE
   ENTERPRISE     ibmSystemMIB
   VARIABLES    {
      ibmSystempTrapUSBAdapterPENDProviderName,
      ibmSystempTrapUSBAdapterPENDEventID,
      ibmSystempTrapUSBAdapterPENDAME,
      ibmSystempTrapUSBAdapterPENDSeverity,
      ibmSystempTrapUSBAdapterPENDDescription,
      ibmSystempTrapUSBAdapterPENDTimeStamp
   }
   DESCRIPTION    "A System p event has occurred"
-- REFERENCE      "POWER_USBAdapterPENDEventIndication"
::= 565

ibmSystempTrapUSBAdapterPENDBindings OBJECT IDENTIFIER ::= { ibmSystemTrap 565 }

ibmSystempTrapUSBAdapterPENDProviderName OBJECT-TYPE
   SYNTAX         String
   ACCESS         read-only
   STATUS         mandatory
   DESCRIPTION    "The name of the CIM Provider that monitors this device"
-- REFERENCE      "POWER_USBAdapterPENDEventIndication.ProviderName"
::= { ibmSystempTrapUSBAdapterPENDBindings 1 }

ibmSystempTrapUSBAdapterPENDEventID OBJECT-TYPE
   SYNTAX         String
   ACCESS         read-only
   STATUS         mandatory
   DESCRIPTION    "A unique EventID that identifies this trap" 
-- REFERENCE      "POWER_USBAdapterPENDEventIndication.EventID"
::= { ibmSystempTrapUSBAdapterPENDBindings 2 }

ibmSystempTrapUSBAdapterPENDAME OBJECT-TYPE
   SYNTAX         String
   ACCESS         read-only
   STATUS         mandatory
   DESCRIPTION    "A unique string that identifies the monitored device"
-- REFERENCE      "POWER_USBAdapterPENDEventIndication.AlertingManagedElement"
::= { ibmSystempTrapUSBAdapterPENDBindings 3 }

ibmSystempTrapUSBAdapterPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBAdapterPENDEventIndication.Severity"
::= { ibmSystempTrapUSBAdapterPENDBindings 4 }

ibmSystempTrapUSBAdapterPENDDescription OBJECT-TYPE
   SYNTAX         SnmpAdminString
   ACCESS         read-only
   STATUS         mandatory
   DESCRIPTION    "The Event text of the trap"
-- REFERENCE      "POWER_USBAdapterPENDEventIndication.Description"
::= { ibmSystempTrapUSBAdapterPENDBindings 5 }

ibmSystempTrapUSBAdapterPENDTimeStamp OBJECT-TYPE
   SYNTAX         Datetime
   ACCESS         read-only
   STATUS         mandatory
   DESCRIPTION    "The time that the trap occurred"
-- REFERENCE      "POWER_USBAdapterPENDEventIndication.TimeStamp"
::= { ibmSystempTrapUSBAdapterPENDBindings 6 }


ibmSystempTrapUSBAdapterPERF TRAP-TYPE
   ENTERPRISE     ibmSystemMIB
   VARIABLES    {
      ibmSystempTrapUSBAdapterPERFProviderName,
      ibmSystempTrapUSBAdapterPERFEventID,
      ibmSystempTrapUSBAdapterPERFAME,
      ibmSystempTrapUSBAdapterPERFSeverity,
      ibmSystempTrapUSBAdapterPERFDescription,
      ibmSystempTrapUSBAdapterPERFTimeStamp
   }
   DESCRIPTION    "A System p event has occurred"
-- REFERENCE      "POWER_USBAdapterPERFEventIndication"
::= 566

ibmSystempTrapUSBAdapterPERFBindings OBJECT IDENTIFIER ::= { ibmSystemTrap 566 }

ibmSystempTrapUSBAdapterPERFProviderName OBJECT-TYPE
   SYNTAX         String
   ACCESS         read-only
   STATUS         mandatory
   DESCRIPTION    "The name of the CIM Provider that monitors this device"
-- REFERENCE      "POWER_USBAdapterPERFEventIndication.ProviderName"
::= { ibmSystempTrapUSBAdapterPERFBindings 1 }

ibmSystempTrapUSBAdapterPERFEventID OBJECT-TYPE
   SYNTAX         String
   ACCESS         read-only
   STATUS         mandatory
   DESCRIPTION    "A unique EventID that identifies this trap" 
-- REFERENCE      "POWER_USBAdapterPERFEventIndication.EventID"
::= { ibmSystempTrapUSBAdapterPERFBindings 2 }

ibmSystempTrapUSBAdapterPERFAME OBJECT-TYPE
   SYNTAX         String
   ACCESS         read-only
   STATUS         mandatory
   DESCRIPTION    "A unique string that identifies the monitored device"
-- REFERENCE      "POWER_USBAdapterPERFEventIndication.AlertingManagedElement"
::= { ibmSystempTrapUSBAdapterPERFBindings 3 }

ibmSystempTrapUSBAdapterPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBAdapterPERFEventIndication.Severity"
::= { ibmSystempTrapUSBAdapterPERFBindings 4 }

ibmSystempTrapUSBAdapterPERFDescription OBJECT-TYPE
   SYNTAX         SnmpAdminString
   ACCESS         read-only
   STATUS         mandatory
   DESCRIPTION    "The Event text of the trap"
-- REFERENCE      "POWER_USBAdapterPERFEventIndication.Description"
::= { ibmSystempTrapUSBAdapterPERFBindings 5 }

ibmSystempTrapUSBAdapterPERFTimeStamp OBJECT-TYPE
   SYNTAX         Datetime
   ACCESS         read-only
   STATUS         mandatory
   DESCRIPTION    "The time that the trap occurred"
-- REFERENCE      "POWER_USBAdapterPERFEventIndication.TimeStamp"
::= { ibmSystempTrapUSBAdapterPERFBindings 6 }


ibmSystempTrapUSBAdapterUNKNOWN TRAP-TYPE
   ENTERPRISE     ibmSystemMIB
   VARIABLES    {
      ibmSystempTrapUSBAdapterUNKNOWNProviderName,
      ibmSystempTrapUSBAdapterUNKNOWNEventID,
      ibmSystempTrapUSBAdapterUNKNOWNAME,
      ibmSystempTrapUSBAdapterUNKNOWNSeverity,
      ibmSystempTrapUSBAdapterUNKNOWNDescription,
      ibmSystempTrapUSBAdapterUNKNOWNTimeStamp
   }
   DESCRIPTION    "A System p event has occurred"
-- REFERENCE      "POWER_USBAdapterUNKNOWNEventIndication"
::= 567

ibmSystempTrapUSBAdapterUNKNOWNBindings OBJECT IDENTIFIER ::= { ibmSystemTrap 567 }

ibmSystempTrapUSBAdapterUNKNOWNProviderName OBJECT-TYPE
   SYNTAX         String
   ACCESS         read-only
   STATUS         mandatory
   DESCRIPTION    "The name of the CIM Provider that monitors this device"
-- REFERENCE      "POWER_USBAdapterUNKNOWNEventIndication.ProviderName"
::= { ibmSystempTrapUSBAdapterUNKNOWNBindings 1 }

ibmSystempTrapUSBAdapterUNKNOWNEventID OBJECT-TYPE
   SYNTAX         String
   ACCESS         read-only
   STATUS         mandatory
   DESCRIPTION    "A unique EventID that identifies this trap" 
-- REFERENCE      "POWER_USBAdapterUNKNOWNEventIndication.EventID"
::= { ibmSystempTrapUSBAdapterUNKNOWNBindings 2 }

ibmSystempTrapUSBAdapterUNKNOWNAME OBJECT-TYPE
   SYNTAX         String
   ACCESS         read-only
   STATUS         mandatory
   DESCRIPTION    "A unique string that identifies the monitored device"
-- REFERENCE      "POWER_USBAdapterUNKNOWNEventIndication.AlertingManagedElement"
::= { ibmSystempTrapUSBAdapterUNKNOWNBindings 3 }

ibmSystempTrapUSBAdapterUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBAdapterUNKNOWNEventIndication.Severity"
::= { ibmSystempTrapUSBAdapterUNKNOWNBindings 4 }

ibmSystempTrapUSBAdapterUNKNOWNDescription OBJECT-TYPE
   SYNTAX         SnmpAdminString
   ACCESS         read-only
   STATUS         mandatory
   DESCRIPTION    "The Event text of the trap"
-- REFERENCE      "POWER_USBAdapterUNKNOWNEventIndication.Description"
::= { ibmSystempTrapUSBAdapterUNKNOWNBindings 5 }

ibmSystempTrapUSBAdapterUNKNOWNTimeStamp OBJECT-TYPE
   SYNTAX         Datetime
   ACCESS         read-only
   STATUS         mandatory
   DESCRIPTION    "The time that the trap occurred"
-- REFERENCE      "POWER_USBAdapterUNKNOWNEventIndication.TimeStamp"
::= { ibmSystempTrapUSBAdapterUNKNOWNBindings 6 }


ibmSystempTrapUSBAdapterPERM TRAP-TYPE
   ENTERPRISE     ibmSystemMIB
   VARIABLES    {
      ibmSystempTrapUSBAdapterPERMProviderName,
      ibmSystempTrapUSBAdapterPERMEventID,
      ibmSystempTrapUSBAdapterPERMAME,
      ibmSystempTrapUSBAdapterPERMSeverity,
      ibmSystempTrapUSBAdapterPERMDescription,
      ibmSystempTrapUSBAdapterPERMTimeStamp
   }
   DESCRIPTION    "A System p event has occurred"
-- REFERENCE      "POWER_USBAdapterPERMEventIndication"
::= 568

ibmSystempTrapUSBAdapterPERMBindings OBJECT IDENTIFIER ::= { ibmSystemTrap 568 }

ibmSystempTrapUSBAdapterPERMProviderName OBJECT-TYPE
   SYNTAX         String
   ACCESS         read-only
   STATUS         mandatory
   DESCRIPTION    "The name of the CIM Provider that monitors this device"
-- REFERENCE      "POWER_USBAdapterPERMEventIndication.ProviderName"
::= { ibmSystempTrapUSBAdapterPERMBindings 1 }

ibmSystempTrapUSBAdapterPERMEventID OBJECT-TYPE
   SYNTAX         String
   ACCESS         read-only
   STATUS         mandatory
   DESCRIPTION    "A unique EventID that identifies this trap" 
-- REFERENCE      "POWER_USBAdapterPERMEventIndication.EventID"
::= { ibmSystempTrapUSBAdapterPERMBindings 2 }

ibmSystempTrapUSBAdapterPERMAME OBJECT-TYPE
   SYNTAX         String
   ACCESS         read-only
   STATUS         mandatory
   DESCRIPTION    "A unique string that identifies the monitored device"
-- REFERENCE      "POWER_USBAdapterPERMEventIndication.AlertingManagedElement"
::= { ibmSystempTrapUSBAdapterPERMBindings 3 }

ibmSystempTrapUSBAdapterPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBAdapterPERMEventIndication.Severity"
::= { ibmSystempTrapUSBAdapterPERMBindings 4 }

ibmSystempTrapUSBAdapterPERMDescription OBJECT-TYPE
   SYNTAX         SnmpAdminString
   ACCESS         read-only
   STATUS         mandatory
   DESCRIPTION    "The Event text of the trap"
-- REFERENCE      "POWER_USBAdapterPERMEventIndication.Description"
::= { ibmSystempTrapUSBAdapterPERMBindings 5 }

ibmSystempTrapUSBAdapterPERMTimeStamp OBJECT-TYPE
   SYNTAX         Datetime
   ACCESS         read-only
   STATUS         mandatory
   DESCRIPTION    "The time that the trap occurred"
-- REFERENCE      "POWER_USBAdapterPERMEventIndication.TimeStamp"
::= { ibmSystempTrapUSBAdapterPERMBindings 6 }


ibmSystempTrapInfiniBandINFO TRAP-TYPE
   ENTERPRISE     ibmSystemMIB
   VARIABLES    {
      ibmSystempTrapInfiniBandINFOProviderName,
      ibmSystempTrapInfiniBandINFOEventID,
      ibmSystempTrapInfiniBandINFOAME,
      ibmSystempTrapInfiniBandINFOSeverity,
      ibmSystempTrapInfiniBandINFODescription,
      ibmSystempTrapInfiniBandINFOTimeStamp
   }
   DESCRIPTION    "A System p event has occurred"
-- REFERENCE      "POWER_InfiniBandINFOEventIndication"
::= 569

ibmSystempTrapInfiniBandINFOBindings OBJECT IDENTIFIER ::= { ibmSystemTrap 569 }

ibmSystempTrapInfiniBandINFOProviderName OBJECT-TYPE
   SYNTAX         String
   ACCESS         read-only
   STATUS         mandatory
   DESCRIPTION    "The name of the CIM Provider that monitors this device"
-- REFERENCE      "POWER_InfiniBandINFOEventIndication.ProviderName"
::= { ibmSystempTrapInfiniBandINFOBindings 1 }

ibmSystempTrapInfiniBandINFOEventID OBJECT-TYPE
   SYNTAX         String
   ACCESS         read-only
   STATUS         mandatory
   DESCRIPTION    "A unique EventID that identifies this trap" 
-- REFERENCE      "POWER_InfiniBandINFOEventIndication.EventID"
::= { ibmSystempTrapInfiniBandINFOBindings 2 }

ibmSystempTrapInfiniBandINFOAME OBJECT-TYPE
   SYNTAX         String
   ACCESS         read-only
   STATUS         mandatory
   DESCRIPTION    "A unique string that identifies the monitored device"
-- REFERENCE      "POWER_InfiniBandINFOEventIndication.AlertingManagedElement"
::= { ibmSystempTrapInfiniBandINFOBindings 3 }

ibmSystempTrapInfiniBandINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_InfiniBandINFOEventIndication.Severity"
::= { ibmSystempTrapInfiniBandINFOBindings 4 }

ibmSystempTrapInfiniBandINFODescription OBJECT-TYPE
   SYNTAX         SnmpAdminString
   ACCESS         read-only
   STATUS         mandatory
   DESCRIPTION    "The Event text of the trap"
-- REFERENCE      "POWER_InfiniBandINFOEventIndication.Description"
::= { ibmSystempTrapInfiniBandINFOBindings 5 }

ibmSystempTrapInfiniBandINFOTimeStamp OBJECT-TYPE
   SYNTAX         Datetime
   ACCESS         read-only
   STATUS         mandatory
   DESCRIPTION    "The time that the trap occurred"
-- REFERENCE      "POWER_InfiniBandINFOEventIndication.TimeStamp"
::= { ibmSystempTrapInfiniBandINFOBindings 6 }


ibmSystempTrapInfiniBandTEMP TRAP-TYPE
   ENTERPRISE     ibmSystemMIB
   VARIABLES    {
      ibmSystempTrapInfiniBandTEMPProviderName,
      ibmSystempTrapInfiniBandTEMPEventID,
      ibmSystempTrapInfiniBandTEMPAME,
      ibmSystempTrapInfiniBandTEMPSeverity,
      ibmSystempTrapInfiniBandTEMPDescription,
      ibmSystempTrapInfiniBandTEMPTimeStamp
   }
   DESCRIPTION    "A System p event has occurred"
-- REFERENCE      "POWER_InfiniBandTEMPEventIndication"
::= 570

ibmSystempTrapInfiniBandTEMPBindings OBJECT IDENTIFIER ::= { ibmSystemTrap 570 }

ibmSystempTrapInfiniBandTEMPProviderName OBJECT-TYPE
   SYNTAX         String
   ACCESS         read-only
   STATUS         mandatory
   DESCRIPTION    "The name of the CIM Provider that monitors this device"
-- REFERENCE      "POWER_InfiniBandTEMPEventIndication.ProviderName"
::= { ibmSystempTrapInfiniBandTEMPBindings 1 }

ibmSystempTrapInfiniBandTEMPEventID OBJECT-TYPE
   SYNTAX         String
   ACCESS         read-only
   STATUS         mandatory
   DESCRIPTION    "A unique EventID that identifies this trap" 
-- REFERENCE      "POWER_InfiniBandTEMPEventIndication.EventID"
::= { ibmSystempTrapInfiniBandTEMPBindings 2 }

ibmSystempTrapInfiniBandTEMPAME OBJECT-TYPE
   SYNTAX         String
   ACCESS         read-only
   STATUS         mandatory
   DESCRIPTION    "A unique string that identifies the monitored device"
-- REFERENCE      "POWER_InfiniBandTEMPEventIndication.AlertingManagedElement"
::= { ibmSystempTrapInfiniBandTEMPBindings 3 }

ibmSystempTrapInfiniBandTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_InfiniBandTEMPEventIndication.Severity"
::= { ibmSystempTrapInfiniBandTEMPBindings 4 }

ibmSystempTrapInfiniBandTEMPDescription OBJECT-TYPE
   SYNTAX         SnmpAdminString
   ACCESS         read-only
   STATUS         mandatory
   DESCRIPTION    "The Event text of the trap"
-- REFERENCE      "POWER_InfiniBandTEMPEventIndication.Description"
::= { ibmSystempTrapInfiniBandTEMPBindings 5 }

ibmSystempTrapInfiniBandTEMPTimeStamp OBJECT-TYPE
   SYNTAX         Datetime
   ACCESS         read-only
   STATUS         mandatory
   DESCRIPTION    "The time that the trap occurred"
-- REFERENCE      "POWER_InfiniBandTEMPEventIndication.TimeStamp"
::= { ibmSystempTrapInfiniBandTEMPBindings 6 }


ibmSystempTrapInfiniBandPEND TRAP-TYPE
   ENTERPRISE     ibmSystemMIB
   VARIABLES    {
      ibmSystempTrapInfiniBandPENDProviderName,
      ibmSystempTrapInfiniBandPENDEventID,
      ibmSystempTrapInfiniBandPENDAME,
      ibmSystempTrapInfiniBandPENDSeverity,
      ibmSystempTrapInfiniBandPENDDescription,
      ibmSystempTrapInfiniBandPENDTimeStamp
   }
   DESCRIPTION    "A System p event has occurred"
-- REFERENCE      "POWER_InfiniBandPENDEventIndication"
::= 571

ibmSystempTrapInfiniBandPENDBindings OBJECT IDENTIFIER ::= { ibmSystemTrap 571 }

ibmSystempTrapInfiniBandPENDProviderName OBJECT-TYPE
   SYNTAX         String
   ACCESS         read-only
   STATUS         mandatory
   DESCRIPTION    "The name of the CIM Provider that monitors this device"
-- REFERENCE      "POWER_InfiniBandPENDEventIndication.ProviderName"
::= { ibmSystempTrapInfiniBandPENDBindings 1 }

ibmSystempTrapInfiniBandPENDEventID OBJECT-TYPE
   SYNTAX         String
   ACCESS         read-only
   STATUS         mandatory
   DESCRIPTION    "A unique EventID that identifies this trap" 
-- REFERENCE      "POWER_InfiniBandPENDEventIndication.EventID"
::= { ibmSystempTrapInfiniBandPENDBindings 2 }

ibmSystempTrapInfiniBandPENDAME OBJECT-TYPE
   SYNTAX         String
   ACCESS         read-only
   STATUS         mandatory
   DESCRIPTION    "A unique string that identifies the monitored device"
-- REFERENCE      "POWER_InfiniBandPENDEventIndication.AlertingManagedElement"
::= { ibmSystempTrapInfiniBandPENDBindings 3 }

ibmSystempTrapInfiniBandPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_InfiniBandPENDEventIndication.Severity"
::= { ibmSystempTrapInfiniBandPENDBindings 4 }

ibmSystempTrapInfiniBandPENDDescription OBJECT-TYPE
   SYNTAX         SnmpAdminString
   ACCESS         read-only
   STATUS         mandatory
   DESCRIPTION    "The Event text of the trap"
-- REFERENCE      "POWER_InfiniBandPENDEventIndication.Description"
::= { ibmSystempTrapInfiniBandPENDBindings 5 }

ibmSystempTrapInfiniBandPENDTimeStamp OBJECT-TYPE
   SYNTAX         Datetime
   ACCESS         read-only
   STATUS         mandatory
   DESCRIPTION    "The time that the trap occurred"
-- REFERENCE      "POWER_InfiniBandPENDEventIndication.TimeStamp"
::= { ibmSystempTrapInfiniBandPENDBindings 6 }


ibmSystempTrapInfiniBandPERF TRAP-TYPE
   ENTERPRISE     ibmSystemMIB
   VARIABLES    {
      ibmSystempTrapInfiniBandPERFProviderName,
      ibmSystempTrapInfiniBandPERFEventID,
      ibmSystempTrapInfiniBandPERFAME,
      ibmSystempTrapInfiniBandPERFSeverity,
      ibmSystempTrapInfiniBandPERFDescription,
      ibmSystempTrapInfiniBandPERFTimeStamp
   }
   DESCRIPTION    "A System p event has occurred"
-- REFERENCE      "POWER_InfiniBandPERFEventIndication"
::= 572

ibmSystempTrapInfiniBandPERFBindings OBJECT IDENTIFIER ::= { ibmSystemTrap 572 }

ibmSystempTrapInfiniBandPERFProviderName OBJECT-TYPE
   SYNTAX         String
   ACCESS         read-only
   STATUS         mandatory
   DESCRIPTION    "The name of the CIM Provider that monitors this device"
-- REFERENCE      "POWER_InfiniBandPERFEventIndication.ProviderName"
::= { ibmSystempTrapInfiniBandPERFBindings 1 }

ibmSystempTrapInfiniBandPERFEventID OBJECT-TYPE
   SYNTAX         String
   ACCESS         read-only
   STATUS         mandatory
   DESCRIPTION    "A unique EventID that identifies this trap" 
-- REFERENCE      "POWER_InfiniBandPERFEventIndication.EventID"
::= { ibmSystempTrapInfiniBandPERFBindings 2 }

ibmSystempTrapInfiniBandPERFAME OBJECT-TYPE
   SYNTAX         String
   ACCESS         read-only
   STATUS         mandatory
   DESCRIPTION    "A unique string that identifies the monitored device"
-- REFERENCE      "POWER_InfiniBandPERFEventIndication.AlertingManagedElement"
::= { ibmSystempTrapInfiniBandPERFBindings 3 }

ibmSystempTrapInfiniBandPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_InfiniBandPERFEventIndication.Severity"
::= { ibmSystempTrapInfiniBandPERFBindings 4 }

ibmSystempTrapInfiniBandPERFDescription OBJECT-TYPE
   SYNTAX         SnmpAdminString
   ACCESS         read-only
   STATUS         mandatory
   DESCRIPTION    "The Event text of the trap"
-- REFERENCE      "POWER_InfiniBandPERFEventIndication.Description"
::= { ibmSystempTrapInfiniBandPERFBindings 5 }

ibmSystempTrapInfiniBandPERFTimeStamp OBJECT-TYPE
   SYNTAX         Datetime
   ACCESS         read-only
   STATUS         mandatory
   DESCRIPTION    "The time that the trap occurred"
-- REFERENCE      "POWER_InfiniBandPERFEventIndication.TimeStamp"
::= { ibmSystempTrapInfiniBandPERFBindings 6 }


ibmSystempTrapInfiniBandUNKNOWN TRAP-TYPE
   ENTERPRISE     ibmSystemMIB
   VARIABLES    {
      ibmSystempTrapInfiniBandUNKNOWNProviderName,
      ibmSystempTrapInfiniBandUNKNOWNEventID,
      ibmSystempTrapInfiniBandUNKNOWNAME,
      ibmSystempTrapInfiniBandUNKNOWNSeverity,
      ibmSystempTrapInfiniBandUNKNOWNDescription,
      ibmSystempTrapInfiniBandUNKNOWNTimeStamp
   }
   DESCRIPTION    "A System p event has occurred"
-- REFERENCE      "POWER_InfiniBandUNKNOWNEventIndication"
::= 573

ibmSystempTrapInfiniBandUNKNOWNBindings OBJECT IDENTIFIER ::= { ibmSystemTrap 573 }

ibmSystempTrapInfiniBandUNKNOWNProviderName OBJECT-TYPE
   SYNTAX         String
   ACCESS         read-only
   STATUS         mandatory
   DESCRIPTION    "The name of the CIM Provider that monitors this device"
-- REFERENCE      "POWER_InfiniBandUNKNOWNEventIndication.ProviderName"
::= { ibmSystempTrapInfiniBandUNKNOWNBindings 1 }

ibmSystempTrapInfiniBandUNKNOWNEventID OBJECT-TYPE
   SYNTAX         String
   ACCESS         read-only
   STATUS         mandatory
   DESCRIPTION    "A unique EventID that identifies this trap" 
-- REFERENCE      "POWER_InfiniBandUNKNOWNEventIndication.EventID"
::= { ibmSystempTrapInfiniBandUNKNOWNBindings 2 }

ibmSystempTrapInfiniBandUNKNOWNAME OBJECT-TYPE
   SYNTAX         String
   ACCESS         read-only
   STATUS         mandatory
   DESCRIPTION    "A unique string that identifies the monitored device"
-- REFERENCE      "POWER_InfiniBandUNKNOWNEventIndication.AlertingManagedElement"
::= { ibmSystempTrapInfiniBandUNKNOWNBindings 3 }

ibmSystempTrapInfiniBandUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_InfiniBandUNKNOWNEventIndication.Severity"
::= { ibmSystempTrapInfiniBandUNKNOWNBindings 4 }

ibmSystempTrapInfiniBandUNKNOWNDescription OBJECT-TYPE
   SYNTAX         SnmpAdminString
   ACCESS         read-only
   STATUS         mandatory
   DESCRIPTION    "The Event text of the trap"
-- REFERENCE      "POWER_InfiniBandUNKNOWNEventIndication.Description"
::= { ibmSystempTrapInfiniBandUNKNOWNBindings 5 }

ibmSystempTrapInfiniBandUNKNOWNTimeStamp OBJECT-TYPE
   SYNTAX         Datetime
   ACCESS         read-only
   STATUS         mandatory
   DESCRIPTION    "The time that the trap occurred"
-- REFERENCE      "POWER_InfiniBandUNKNOWNEventIndication.TimeStamp"
::= { ibmSystempTrapInfiniBandUNKNOWNBindings 6 }


ibmSystempTrapInfiniBandPERM TRAP-TYPE
   ENTERPRISE     ibmSystemMIB
   VARIABLES    {
      ibmSystempTrapInfiniBandPERMProviderName,
      ibmSystempTrapInfiniBandPERMEventID,
      ibmSystempTrapInfiniBandPERMAME,
      ibmSystempTrapInfiniBandPERMSeverity,
      ibmSystempTrapInfiniBandPERMDescription,
      ibmSystempTrapInfiniBandPERMTimeStamp
   }
   DESCRIPTION    "A System p event has occurred"
-- REFERENCE      "POWER_InfiniBandPERMEventIndication"
::= 574

ibmSystempTrapInfiniBandPERMBindings OBJECT IDENTIFIER ::= { ibmSystemTrap 574 }

ibmSystempTrapInfiniBandPERMProviderName OBJECT-TYPE
   SYNTAX         String
   ACCESS         read-only
   STATUS         mandatory
   DESCRIPTION    "The name of the CIM Provider that monitors this device"
-- REFERENCE      "POWER_InfiniBandPERMEventIndication.ProviderName"
::= { ibmSystempTrapInfiniBandPERMBindings 1 }

ibmSystempTrapInfiniBandPERMEventID OBJECT-TYPE
   SYNTAX         String
   ACCESS         read-only
   STATUS         mandatory
   DESCRIPTION    "A unique EventID that identifies this trap" 
-- REFERENCE      "POWER_InfiniBandPERMEventIndication.EventID"
::= { ibmSystempTrapInfiniBandPERMBindings 2 }

ibmSystempTrapInfiniBandPERMAME OBJECT-TYPE
   SYNTAX         String
   ACCESS         read-only
   STATUS         mandatory
   DESCRIPTION    "A unique string that identifies the monitored device"
-- REFERENCE      "POWER_InfiniBandPERMEventIndication.AlertingManagedElement"
::= { ibmSystempTrapInfiniBandPERMBindings 3 }

ibmSystempTrapInfiniBandPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_InfiniBandPERMEventIndication.Severity"
::= { ibmSystempTrapInfiniBandPERMBindings 4 }

ibmSystempTrapInfiniBandPERMDescription OBJECT-TYPE
   SYNTAX         SnmpAdminString
   ACCESS         read-only
   STATUS         mandatory
   DESCRIPTION    "The Event text of the trap"
-- REFERENCE      "POWER_InfiniBandPERMEventIndication.Description"
::= { ibmSystempTrapInfiniBandPERMBindings 5 }

ibmSystempTrapInfiniBandPERMTimeStamp OBJECT-TYPE
   SYNTAX         Datetime
   ACCESS         read-only
   STATUS         mandatory
   DESCRIPTION    "The time that the trap occurred"
-- REFERENCE      "POWER_InfiniBandPERMEventIndication.TimeStamp"
::= { ibmSystempTrapInfiniBandPERMBindings 6 }


ibmSystempTrapIDEDiskINFO TRAP-TYPE
   ENTERPRISE     ibmSystemMIB
   VARIABLES    {
      ibmSystempTrapIDEDiskINFOProviderName,
      ibmSystempTrapIDEDiskINFOEventID,
      ibmSystempTrapIDEDiskINFOAME,
      ibmSystempTrapIDEDiskINFOSeverity,
      ibmSystempTrapIDEDiskINFODescription,
      ibmSystempTrapIDEDiskINFOTimeStamp
   }
   DESCRIPTION    "A System p event has occurred"
-- REFERENCE      "POWER_IDEDiskINFOEventIndication"
::= 575

ibmSystempTrapIDEDiskINFOBindings OBJECT IDENTIFIER ::= { ibmSystemTrap 575 }

ibmSystempTrapIDEDiskINFOProviderName OBJECT-TYPE
   SYNTAX         String
   ACCESS         read-only
   STATUS         mandatory
   DESCRIPTION    "The name of the CIM Provider that monitors this device"
-- REFERENCE      "POWER_IDEDiskINFOEventIndication.ProviderName"
::= { ibmSystempTrapIDEDiskINFOBindings 1 }

ibmSystempTrapIDEDiskINFOEventID OBJECT-TYPE
   SYNTAX         String
   ACCESS         read-only
   STATUS         mandatory
   DESCRIPTION    "A unique EventID that identifies this trap" 
-- REFERENCE      "POWER_IDEDiskINFOEventIndication.EventID"
::= { ibmSystempTrapIDEDiskINFOBindings 2 }

ibmSystempTrapIDEDiskINFOAME OBJECT-TYPE
   SYNTAX         String
   ACCESS         read-only
   STATUS         mandatory
   DESCRIPTION    "A unique string that identifies the monitored device"
-- REFERENCE      "POWER_IDEDiskINFOEventIndication.AlertingManagedElement"
::= { ibmSystempTrapIDEDiskINFOBindings 3 }

ibmSystempTrapIDEDiskINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_IDEDiskINFOEventIndication.Severity"
::= { ibmSystempTrapIDEDiskINFOBindings 4 }

ibmSystempTrapIDEDiskINFODescription OBJECT-TYPE
   SYNTAX         SnmpAdminString
   ACCESS         read-only
   STATUS         mandatory
   DESCRIPTION    "The Event text of the trap"
-- REFERENCE      "POWER_IDEDiskINFOEventIndication.Description"
::= { ibmSystempTrapIDEDiskINFOBindings 5 }

ibmSystempTrapIDEDiskINFOTimeStamp OBJECT-TYPE
   SYNTAX         Datetime
   ACCESS         read-only
   STATUS         mandatory
   DESCRIPTION    "The time that the trap occurred"
-- REFERENCE      "POWER_IDEDiskINFOEventIndication.TimeStamp"
::= { ibmSystempTrapIDEDiskINFOBindings 6 }


ibmSystempTrapIDEDiskTEMP TRAP-TYPE
   ENTERPRISE     ibmSystemMIB
   VARIABLES    {
      ibmSystempTrapIDEDiskTEMPProviderName,
      ibmSystempTrapIDEDiskTEMPEventID,
      ibmSystempTrapIDEDiskTEMPAME,
      ibmSystempTrapIDEDiskTEMPSeverity,
      ibmSystempTrapIDEDiskTEMPDescription,
      ibmSystempTrapIDEDiskTEMPTimeStamp
   }
   DESCRIPTION    "A System p event has occurred"
-- REFERENCE      "POWER_IDEDiskTEMPEventIndication"
::= 576

ibmSystempTrapIDEDiskTEMPBindings OBJECT IDENTIFIER ::= { ibmSystemTrap 576 }

ibmSystempTrapIDEDiskTEMPProviderName OBJECT-TYPE
   SYNTAX         String
   ACCESS         read-only
   STATUS         mandatory
   DESCRIPTION    "The name of the CIM Provider that monitors this device"
-- REFERENCE      "POWER_IDEDiskTEMPEventIndication.ProviderName"
::= { ibmSystempTrapIDEDiskTEMPBindings 1 }

ibmSystempTrapIDEDiskTEMPEventID OBJECT-TYPE
   SYNTAX         String
   ACCESS         read-only
   STATUS         mandatory
   DESCRIPTION    "A unique EventID that identifies this trap" 
-- REFERENCE      "POWER_IDEDiskTEMPEventIndication.EventID"
::= { ibmSystempTrapIDEDiskTEMPBindings 2 }

ibmSystempTrapIDEDiskTEMPAME OBJECT-TYPE
   SYNTAX         String
   ACCESS         read-only
   STATUS         mandatory
   DESCRIPTION    "A unique string that identifies the monitored device"
-- REFERENCE      "POWER_IDEDiskTEMPEventIndication.AlertingManagedElement"
::= { ibmSystempTrapIDEDiskTEMPBindings 3 }

ibmSystempTrapIDEDiskTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_IDEDiskTEMPEventIndication.Severity"
::= { ibmSystempTrapIDEDiskTEMPBindings 4 }

ibmSystempTrapIDEDiskTEMPDescription OBJECT-TYPE
   SYNTAX         SnmpAdminString
   ACCESS         read-only
   STATUS         mandatory
   DESCRIPTION    "The Event text of the trap"
-- REFERENCE      "POWER_IDEDiskTEMPEventIndication.Description"
::= { ibmSystempTrapIDEDiskTEMPBindings 5 }

ibmSystempTrapIDEDiskTEMPTimeStamp OBJECT-TYPE
   SYNTAX         Datetime
   ACCESS         read-only
   STATUS         mandatory
   DESCRIPTION    "The time that the trap occurred"
-- REFERENCE      "POWER_IDEDiskTEMPEventIndication.TimeStamp"
::= { ibmSystempTrapIDEDiskTEMPBindings 6 }


ibmSystempTrapIDEDiskPEND TRAP-TYPE
   ENTERPRISE     ibmSystemMIB
   VARIABLES    {
      ibmSystempTrapIDEDiskPENDProviderName,
      ibmSystempTrapIDEDiskPENDEventID,
      ibmSystempTrapIDEDiskPENDAME,
      ibmSystempTrapIDEDiskPENDSeverity,
      ibmSystempTrapIDEDiskPENDDescription,
      ibmSystempTrapIDEDiskPENDTimeStamp
   }
   DESCRIPTION    "A System p event has occurred"
-- REFERENCE      "POWER_IDEDiskPENDEventIndication"
::= 577

ibmSystempTrapIDEDiskPENDBindings OBJECT IDENTIFIER ::= { ibmSystemTrap 577 }

ibmSystempTrapIDEDiskPENDProviderName OBJECT-TYPE
   SYNTAX         String
   ACCESS         read-only
   STATUS         mandatory
   DESCRIPTION    "The name of the CIM Provider that monitors this device"
-- REFERENCE      "POWER_IDEDiskPENDEventIndication.ProviderName"
::= { ibmSystempTrapIDEDiskPENDBindings 1 }

ibmSystempTrapIDEDiskPENDEventID OBJECT-TYPE
   SYNTAX         String
   ACCESS         read-only
   STATUS         mandatory
   DESCRIPTION    "A unique EventID that identifies this trap" 
-- REFERENCE      "POWER_IDEDiskPENDEventIndication.EventID"
::= { ibmSystempTrapIDEDiskPENDBindings 2 }

ibmSystempTrapIDEDiskPENDAME OBJECT-TYPE
   SYNTAX         String
   ACCESS         read-only
   STATUS         mandatory
   DESCRIPTION    "A unique string that identifies the monitored device"
-- REFERENCE      "POWER_IDEDiskPENDEventIndication.AlertingManagedElement"
::= { ibmSystempTrapIDEDiskPENDBindings 3 }

ibmSystempTrapIDEDiskPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_IDEDiskPENDEventIndication.Severity"
::= { ibmSystempTrapIDEDiskPENDBindings 4 }

ibmSystempTrapIDEDiskPENDDescription OBJECT-TYPE
   SYNTAX         SnmpAdminString
   ACCESS         read-only
   STATUS         mandatory
   DESCRIPTION    "The Event text of the trap"
-- REFERENCE      "POWER_IDEDiskPENDEventIndication.Description"
::= { ibmSystempTrapIDEDiskPENDBindings 5 }

ibmSystempTrapIDEDiskPENDTimeStamp OBJECT-TYPE
   SYNTAX         Datetime
   ACCESS         read-only
   STATUS         mandatory
   DESCRIPTION    "The time that the trap occurred"
-- REFERENCE      "POWER_IDEDiskPENDEventIndication.TimeStamp"
::= { ibmSystempTrapIDEDiskPENDBindings 6 }


ibmSystempTrapIDEDiskPERF TRAP-TYPE
   ENTERPRISE     ibmSystemMIB
   VARIABLES    {
      ibmSystempTrapIDEDiskPERFProviderName,
      ibmSystempTrapIDEDiskPERFEventID,
      ibmSystempTrapIDEDiskPERFAME,
      ibmSystempTrapIDEDiskPERFSeverity,
      ibmSystempTrapIDEDiskPERFDescription,
      ibmSystempTrapIDEDiskPERFTimeStamp
   }
   DESCRIPTION    "A System p event has occurred"
-- REFERENCE      "POWER_IDEDiskPERFEventIndication"
::= 578

ibmSystempTrapIDEDiskPERFBindings OBJECT IDENTIFIER ::= { ibmSystemTrap 578 }

ibmSystempTrapIDEDiskPERFProviderName OBJECT-TYPE
   SYNTAX         String
   ACCESS         read-only
   STATUS         mandatory
   DESCRIPTION    "The name of the CIM Provider that monitors this device"
-- REFERENCE      "POWER_IDEDiskPERFEventIndication.ProviderName"
::= { ibmSystempTrapIDEDiskPERFBindings 1 }

ibmSystempTrapIDEDiskPERFEventID OBJECT-TYPE
   SYNTAX         String
   ACCESS         read-only
   STATUS         mandatory
   DESCRIPTION    "A unique EventID that identifies this trap" 
-- REFERENCE      "POWER_IDEDiskPERFEventIndication.EventID"
::= { ibmSystempTrapIDEDiskPERFBindings 2 }

ibmSystempTrapIDEDiskPERFAME OBJECT-TYPE
   SYNTAX         String
   ACCESS         read-only
   STATUS         mandatory
   DESCRIPTION    "A unique string that identifies the monitored device"
-- REFERENCE      "POWER_IDEDiskPERFEventIndication.AlertingManagedElement"
::= { ibmSystempTrapIDEDiskPERFBindings 3 }

ibmSystempTrapIDEDiskPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_IDEDiskPERFEventIndication.Severity"
::= { ibmSystempTrapIDEDiskPERFBindings 4 }

ibmSystempTrapIDEDiskPERFDescription OBJECT-TYPE
   SYNTAX         SnmpAdminString
   ACCESS         read-only
   STATUS         mandatory
   DESCRIPTION    "The Event text of the trap"
-- REFERENCE      "POWER_IDEDiskPERFEventIndication.Description"
::= { ibmSystempTrapIDEDiskPERFBindings 5 }

ibmSystempTrapIDEDiskPERFTimeStamp OBJECT-TYPE
   SYNTAX         Datetime
   ACCESS         read-only
   STATUS         mandatory
   DESCRIPTION    "The time that the trap occurred"
-- REFERENCE      "POWER_IDEDiskPERFEventIndication.TimeStamp"
::= { ibmSystempTrapIDEDiskPERFBindings 6 }


ibmSystempTrapIDEDiskUNKNOWN TRAP-TYPE
   ENTERPRISE     ibmSystemMIB
   VARIABLES    {
      ibmSystempTrapIDEDiskUNKNOWNProviderName,
      ibmSystempTrapIDEDiskUNKNOWNEventID,
      ibmSystempTrapIDEDiskUNKNOWNAME,
      ibmSystempTrapIDEDiskUNKNOWNSeverity,
      ibmSystempTrapIDEDiskUNKNOWNDescription,
      ibmSystempTrapIDEDiskUNKNOWNTimeStamp
   }
   DESCRIPTION    "A System p event has occurred"
-- REFERENCE      "POWER_IDEDiskUNKNOWNEventIndication"
::= 579

ibmSystempTrapIDEDiskUNKNOWNBindings OBJECT IDENTIFIER ::= { ibmSystemTrap 579 }

ibmSystempTrapIDEDiskUNKNOWNProviderName OBJECT-TYPE
   SYNTAX         String
   ACCESS         read-only
   STATUS         mandatory
   DESCRIPTION    "The name of the CIM Provider that monitors this device"
-- REFERENCE      "POWER_IDEDiskUNKNOWNEventIndication.ProviderName"
::= { ibmSystempTrapIDEDiskUNKNOWNBindings 1 }

ibmSystempTrapIDEDiskUNKNOWNEventID OBJECT-TYPE
   SYNTAX         String
   ACCESS         read-only
   STATUS         mandatory
   DESCRIPTION    "A unique EventID that identifies this trap" 
-- REFERENCE      "POWER_IDEDiskUNKNOWNEventIndication.EventID"
::= { ibmSystempTrapIDEDiskUNKNOWNBindings 2 }

ibmSystempTrapIDEDiskUNKNOWNAME OBJECT-TYPE
   SYNTAX         String
   ACCESS         read-only
   STATUS         mandatory
   DESCRIPTION    "A unique string that identifies the monitored device"
-- REFERENCE      "POWER_IDEDiskUNKNOWNEventIndication.AlertingManagedElement"
::= { ibmSystempTrapIDEDiskUNKNOWNBindings 3 }

ibmSystempTrapIDEDiskUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_IDEDiskUNKNOWNEventIndication.Severity"
::= { ibmSystempTrapIDEDiskUNKNOWNBindings 4 }

ibmSystempTrapIDEDiskUNKNOWNDescription OBJECT-TYPE
   SYNTAX         SnmpAdminString
   ACCESS         read-only
   STATUS         mandatory
   DESCRIPTION    "The Event text of the trap"
-- REFERENCE      "POWER_IDEDiskUNKNOWNEventIndication.Description"
::= { ibmSystempTrapIDEDiskUNKNOWNBindings 5 }

ibmSystempTrapIDEDiskUNKNOWNTimeStamp OBJECT-TYPE
   SYNTAX         Datetime
   ACCESS         read-only
   STATUS         mandatory
   DESCRIPTION    "The time that the trap occurred"
-- REFERENCE      "POWER_IDEDiskUNKNOWNEventIndication.TimeStamp"
::= { ibmSystempTrapIDEDiskUNKNOWNBindings 6 }


ibmSystempTrapIDEDiskPERM TRAP-TYPE
   ENTERPRISE     ibmSystemMIB
   VARIABLES    {
      ibmSystempTrapIDEDiskPERMProviderName,
      ibmSystempTrapIDEDiskPERMEventID,
      ibmSystempTrapIDEDiskPERMAME,
      ibmSystempTrapIDEDiskPERMSeverity,
      ibmSystempTrapIDEDiskPERMDescription,
      ibmSystempTrapIDEDiskPERMTimeStamp
   }
   DESCRIPTION    "A System p event has occurred"
-- REFERENCE      "POWER_IDEDiskPERMEventIndication"
::= 580

ibmSystempTrapIDEDiskPERMBindings OBJECT IDENTIFIER ::= { ibmSystemTrap 580 }

ibmSystempTrapIDEDiskPERMProviderName OBJECT-TYPE
   SYNTAX         String
   ACCESS         read-only
   STATUS         mandatory
   DESCRIPTION    "The name of the CIM Provider that monitors this device"
-- REFERENCE      "POWER_IDEDiskPERMEventIndication.ProviderName"
::= { ibmSystempTrapIDEDiskPERMBindings 1 }

ibmSystempTrapIDEDiskPERMEventID OBJECT-TYPE
   SYNTAX         String
   ACCESS         read-only
   STATUS         mandatory
   DESCRIPTION    "A unique EventID that identifies this trap" 
-- REFERENCE      "POWER_IDEDiskPERMEventIndication.EventID"
::= { ibmSystempTrapIDEDiskPERMBindings 2 }

ibmSystempTrapIDEDiskPERMAME OBJECT-TYPE
   SYNTAX         String
   ACCESS         read-only
   STATUS         mandatory
   DESCRIPTION    "A unique string that identifies the monitored device"
-- REFERENCE      "POWER_IDEDiskPERMEventIndication.AlertingManagedElement"
::= { ibmSystempTrapIDEDiskPERMBindings 3 }

ibmSystempTrapIDEDiskPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_IDEDiskPERMEventIndication.Severity"
::= { ibmSystempTrapIDEDiskPERMBindings 4 }

ibmSystempTrapIDEDiskPERMDescription OBJECT-TYPE
   SYNTAX         SnmpAdminString
   ACCESS         read-only
   STATUS         mandatory
   DESCRIPTION    "The Event text of the trap"
-- REFERENCE      "POWER_IDEDiskPERMEventIndication.Description"
::= { ibmSystempTrapIDEDiskPERMBindings 5 }

ibmSystempTrapIDEDiskPERMTimeStamp OBJECT-TYPE
   SYNTAX         Datetime
   ACCESS         read-only
   STATUS         mandatory
   DESCRIPTION    "The time that the trap occurred"
-- REFERENCE      "POWER_IDEDiskPERMEventIndication.TimeStamp"
::= { ibmSystempTrapIDEDiskPERMBindings 6 }


ibmSystempTrapSCSIDiskINFO TRAP-TYPE
   ENTERPRISE     ibmSystemMIB
   VARIABLES    {
      ibmSystempTrapSCSIDiskINFOProviderName,
      ibmSystempTrapSCSIDiskINFOEventID,
      ibmSystempTrapSCSIDiskINFOAME,
      ibmSystempTrapSCSIDiskINFOSeverity,
      ibmSystempTrapSCSIDiskINFODescription,
      ibmSystempTrapSCSIDiskINFOTimeStamp
   }
   DESCRIPTION    "A System p event has occurred"
-- REFERENCE      "POWER_SCSIDiskINFOEventIndication"
::= 581

ibmSystempTrapSCSIDiskINFOBindings OBJECT IDENTIFIER ::= { ibmSystemTrap 581 }

ibmSystempTrapSCSIDiskINFOProviderName OBJECT-TYPE
   SYNTAX         String
   ACCESS         read-only
   STATUS         mandatory
   DESCRIPTION    "The name of the CIM Provider that monitors this device"
-- REFERENCE      "POWER_SCSIDiskINFOEventIndication.ProviderName"
::= { ibmSystempTrapSCSIDiskINFOBindings 1 }

ibmSystempTrapSCSIDiskINFOEventID OBJECT-TYPE
   SYNTAX         String
   ACCESS         read-only
   STATUS         mandatory
   DESCRIPTION    "A unique EventID that identifies this trap" 
-- REFERENCE      "POWER_SCSIDiskINFOEventIndication.EventID"
::= { ibmSystempTrapSCSIDiskINFOBindings 2 }

ibmSystempTrapSCSIDiskINFOAME OBJECT-TYPE
   SYNTAX         String
   ACCESS         read-only
   STATUS         mandatory
   DESCRIPTION    "A unique string that identifies the monitored device"
-- REFERENCE      "POWER_SCSIDiskINFOEventIndication.AlertingManagedElement"
::= { ibmSystempTrapSCSIDiskINFOBindings 3 }

ibmSystempTrapSCSIDiskINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIDiskINFOEventIndication.Severity"
::= { ibmSystempTrapSCSIDiskINFOBindings 4 }

ibmSystempTrapSCSIDiskINFODescription OBJECT-TYPE
   SYNTAX         SnmpAdminString
   ACCESS         read-only
   STATUS         mandatory
   DESCRIPTION    "The Event text of the trap"
-- REFERENCE      "POWER_SCSIDiskINFOEventIndication.Description"
::= { ibmSystempTrapSCSIDiskINFOBindings 5 }

ibmSystempTrapSCSIDiskINFOTimeStamp OBJECT-TYPE
   SYNTAX         Datetime
   ACCESS         read-only
   STATUS         mandatory
   DESCRIPTION    "The time that the trap occurred"
-- REFERENCE      "POWER_SCSIDiskINFOEventIndication.TimeStamp"
::= { ibmSystempTrapSCSIDiskINFOBindings 6 }


ibmSystempTrapSCSIDiskTEMP TRAP-TYPE
   ENTERPRISE     ibmSystemMIB
   VARIABLES    {
      ibmSystempTrapSCSIDiskTEMPProviderName,
      ibmSystempTrapSCSIDiskTEMPEventID,
      ibmSystempTrapSCSIDiskTEMPAME,
      ibmSystempTrapSCSIDiskTEMPSeverity,
      ibmSystempTrapSCSIDiskTEMPDescription,
      ibmSystempTrapSCSIDiskTEMPTimeStamp
   }
   DESCRIPTION    "A System p event has occurred"
-- REFERENCE      "POWER_SCSIDiskTEMPEventIndication"
::= 582

ibmSystempTrapSCSIDiskTEMPBindings OBJECT IDENTIFIER ::= { ibmSystemTrap 582 }

ibmSystempTrapSCSIDiskTEMPProviderName OBJECT-TYPE
   SYNTAX         String
   ACCESS         read-only
   STATUS         mandatory
   DESCRIPTION    "The name of the CIM Provider that monitors this device"
-- REFERENCE      "POWER_SCSIDiskTEMPEventIndication.ProviderName"
::= { ibmSystempTrapSCSIDiskTEMPBindings 1 }

ibmSystempTrapSCSIDiskTEMPEventID OBJECT-TYPE
   SYNTAX         String
   ACCESS         read-only
   STATUS         mandatory
   DESCRIPTION    "A unique EventID that identifies this trap" 
-- REFERENCE      "POWER_SCSIDiskTEMPEventIndication.EventID"
::= { ibmSystempTrapSCSIDiskTEMPBindings 2 }

ibmSystempTrapSCSIDiskTEMPAME OBJECT-TYPE
   SYNTAX         String
   ACCESS         read-only
   STATUS         mandatory
   DESCRIPTION    "A unique string that identifies the monitored device"
-- REFERENCE      "POWER_SCSIDiskTEMPEventIndication.AlertingManagedElement"
::= { ibmSystempTrapSCSIDiskTEMPBindings 3 }

ibmSystempTrapSCSIDiskTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIDiskTEMPEventIndication.Severity"
::= { ibmSystempTrapSCSIDiskTEMPBindings 4 }

ibmSystempTrapSCSIDiskTEMPDescription OBJECT-TYPE
   SYNTAX         SnmpAdminString
   ACCESS         read-only
   STATUS         mandatory
   DESCRIPTION    "The Event text of the trap"
-- REFERENCE      "POWER_SCSIDiskTEMPEventIndication.Description"
::= { ibmSystempTrapSCSIDiskTEMPBindings 5 }

ibmSystempTrapSCSIDiskTEMPTimeStamp OBJECT-TYPE
   SYNTAX         Datetime
   ACCESS         read-only
   STATUS         mandatory
   DESCRIPTION    "The time that the trap occurred"
-- REFERENCE      "POWER_SCSIDiskTEMPEventIndication.TimeStamp"
::= { ibmSystempTrapSCSIDiskTEMPBindings 6 }


ibmSystempTrapSCSIDiskPEND TRAP-TYPE
   ENTERPRISE     ibmSystemMIB
   VARIABLES    {
      ibmSystempTrapSCSIDiskPENDProviderName,
      ibmSystempTrapSCSIDiskPENDEventID,
      ibmSystempTrapSCSIDiskPENDAME,
      ibmSystempTrapSCSIDiskPENDSeverity,
      ibmSystempTrapSCSIDiskPENDDescription,
      ibmSystempTrapSCSIDiskPENDTimeStamp
   }
   DESCRIPTION    "A System p event has occurred"
-- REFERENCE      "POWER_SCSIDiskPENDEventIndication"
::= 583

ibmSystempTrapSCSIDiskPENDBindings OBJECT IDENTIFIER ::= { ibmSystemTrap 583 }

ibmSystempTrapSCSIDiskPENDProviderName OBJECT-TYPE
   SYNTAX         String
   ACCESS         read-only
   STATUS         mandatory
   DESCRIPTION    "The name of the CIM Provider that monitors this device"
-- REFERENCE      "POWER_SCSIDiskPENDEventIndication.ProviderName"
::= { ibmSystempTrapSCSIDiskPENDBindings 1 }

ibmSystempTrapSCSIDiskPENDEventID OBJECT-TYPE
   SYNTAX         String
   ACCESS         read-only
   STATUS         mandatory
   DESCRIPTION    "A unique EventID that identifies this trap" 
-- REFERENCE      "POWER_SCSIDiskPENDEventIndication.EventID"
::= { ibmSystempTrapSCSIDiskPENDBindings 2 }

ibmSystempTrapSCSIDiskPENDAME OBJECT-TYPE
   SYNTAX         String
   ACCESS         read-only
   STATUS         mandatory
   DESCRIPTION    "A unique string that identifies the monitored device"
-- REFERENCE      "POWER_SCSIDiskPENDEventIndication.AlertingManagedElement"
::= { ibmSystempTrapSCSIDiskPENDBindings 3 }

ibmSystempTrapSCSIDiskPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIDiskPENDEventIndication.Severity"
::= { ibmSystempTrapSCSIDiskPENDBindings 4 }

ibmSystempTrapSCSIDiskPENDDescription OBJECT-TYPE
   SYNTAX         SnmpAdminString
   ACCESS         read-only
   STATUS         mandatory
   DESCRIPTION    "The Event text of the trap"
-- REFERENCE      "POWER_SCSIDiskPENDEventIndication.Description"
::= { ibmSystempTrapSCSIDiskPENDBindings 5 }

ibmSystempTrapSCSIDiskPENDTimeStamp OBJECT-TYPE
   SYNTAX         Datetime
   ACCESS         read-only
   STATUS         mandatory
   DESCRIPTION    "The time that the trap occurred"
-- REFERENCE      "POWER_SCSIDiskPENDEventIndication.TimeStamp"
::= { ibmSystempTrapSCSIDiskPENDBindings 6 }


ibmSystempTrapSCSIDiskPERF TRAP-TYPE
   ENTERPRISE     ibmSystemMIB
   VARIABLES    {
      ibmSystempTrapSCSIDiskPERFProviderName,
      ibmSystempTrapSCSIDiskPERFEventID,
      ibmSystempTrapSCSIDiskPERFAME,
      ibmSystempTrapSCSIDiskPERFSeverity,
      ibmSystempTrapSCSIDiskPERFDescription,
      ibmSystempTrapSCSIDiskPERFTimeStamp
   }
   DESCRIPTION    "A System p event has occurred"
-- REFERENCE      "POWER_SCSIDiskPERFEventIndication"
::= 584

ibmSystempTrapSCSIDiskPERFBindings OBJECT IDENTIFIER ::= { ibmSystemTrap 584 }

ibmSystempTrapSCSIDiskPERFProviderName OBJECT-TYPE
   SYNTAX         String
   ACCESS         read-only
   STATUS         mandatory
   DESCRIPTION    "The name of the CIM Provider that monitors this device"
-- REFERENCE      "POWER_SCSIDiskPERFEventIndication.ProviderName"
::= { ibmSystempTrapSCSIDiskPERFBindings 1 }

ibmSystempTrapSCSIDiskPERFEventID OBJECT-TYPE
   SYNTAX         String
   ACCESS         read-only
   STATUS         mandatory
   DESCRIPTION    "A unique EventID that identifies this trap" 
-- REFERENCE      "POWER_SCSIDiskPERFEventIndication.EventID"
::= { ibmSystempTrapSCSIDiskPERFBindings 2 }

ibmSystempTrapSCSIDiskPERFAME OBJECT-TYPE
   SYNTAX         String
   ACCESS         read-only
   STATUS         mandatory
   DESCRIPTION    "A unique string that identifies the monitored device"
-- REFERENCE      "POWER_SCSIDiskPERFEventIndication.AlertingManagedElement"
::= { ibmSystempTrapSCSIDiskPERFBindings 3 }

ibmSystempTrapSCSIDiskPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIDiskPERFEventIndication.Severity"
::= { ibmSystempTrapSCSIDiskPERFBindings 4 }

ibmSystempTrapSCSIDiskPERFDescription OBJECT-TYPE
   SYNTAX         SnmpAdminString
   ACCESS         read-only
   STATUS         mandatory
   DESCRIPTION    "The Event text of the trap"
-- REFERENCE      "POWER_SCSIDiskPERFEventIndication.Description"
::= { ibmSystempTrapSCSIDiskPERFBindings 5 }

ibmSystempTrapSCSIDiskPERFTimeStamp OBJECT-TYPE
   SYNTAX         Datetime
   ACCESS         read-only
   STATUS         mandatory
   DESCRIPTION    "The time that the trap occurred"
-- REFERENCE      "POWER_SCSIDiskPERFEventIndication.TimeStamp"
::= { ibmSystempTrapSCSIDiskPERFBindings 6 }


ibmSystempTrapSCSIDiskUNKNOWN TRAP-TYPE
   ENTERPRISE     ibmSystemMIB
   VARIABLES    {
      ibmSystempTrapSCSIDiskUNKNOWNProviderName,
      ibmSystempTrapSCSIDiskUNKNOWNEventID,
      ibmSystempTrapSCSIDiskUNKNOWNAME,
      ibmSystempTrapSCSIDiskUNKNOWNSeverity,
      ibmSystempTrapSCSIDiskUNKNOWNDescription,
      ibmSystempTrapSCSIDiskUNKNOWNTimeStamp
   }
   DESCRIPTION    "A System p event has occurred"
-- REFERENCE      "POWER_SCSIDiskUNKNOWNEventIndication"
::= 585

ibmSystempTrapSCSIDiskUNKNOWNBindings OBJECT IDENTIFIER ::= { ibmSystemTrap 585 }

ibmSystempTrapSCSIDiskUNKNOWNProviderName OBJECT-TYPE
   SYNTAX         String
   ACCESS         read-only
   STATUS         mandatory
   DESCRIPTION    "The name of the CIM Provider that monitors this device"
-- REFERENCE      "POWER_SCSIDiskUNKNOWNEventIndication.ProviderName"
::= { ibmSystempTrapSCSIDiskUNKNOWNBindings 1 }

ibmSystempTrapSCSIDiskUNKNOWNEventID OBJECT-TYPE
   SYNTAX         String
   ACCESS         read-only
   STATUS         mandatory
   DESCRIPTION    "A unique EventID that identifies this trap" 
-- REFERENCE      "POWER_SCSIDiskUNKNOWNEventIndication.EventID"
::= { ibmSystempTrapSCSIDiskUNKNOWNBindings 2 }

ibmSystempTrapSCSIDiskUNKNOWNAME OBJECT-TYPE
   SYNTAX         String
   ACCESS         read-only
   STATUS         mandatory
   DESCRIPTION    "A unique string that identifies the monitored device"
-- REFERENCE      "POWER_SCSIDiskUNKNOWNEventIndication.AlertingManagedElement"
::= { ibmSystempTrapSCSIDiskUNKNOWNBindings 3 }

ibmSystempTrapSCSIDiskUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIDiskUNKNOWNEventIndication.Severity"
::= { ibmSystempTrapSCSIDiskUNKNOWNBindings 4 }

ibmSystempTrapSCSIDiskUNKNOWNDescription OBJECT-TYPE
   SYNTAX         SnmpAdminString
   ACCESS         read-only
   STATUS         mandatory
   DESCRIPTION    "The Event text of the trap"
-- REFERENCE      "POWER_SCSIDiskUNKNOWNEventIndication.Description"
::= { ibmSystempTrapSCSIDiskUNKNOWNBindings 5 }

ibmSystempTrapSCSIDiskUNKNOWNTimeStamp OBJECT-TYPE
   SYNTAX         Datetime
   ACCESS         read-only
   STATUS         mandatory
   DESCRIPTION    "The time that the trap occurred"
-- REFERENCE      "POWER_SCSIDiskUNKNOWNEventIndication.TimeStamp"
::= { ibmSystempTrapSCSIDiskUNKNOWNBindings 6 }


ibmSystempTrapSCSIDiskPERM TRAP-TYPE
   ENTERPRISE     ibmSystemMIB
   VARIABLES    {
      ibmSystempTrapSCSIDiskPERMProviderName,
      ibmSystempTrapSCSIDiskPERMEventID,
      ibmSystempTrapSCSIDiskPERMAME,
      ibmSystempTrapSCSIDiskPERMSeverity,
      ibmSystempTrapSCSIDiskPERMDescription,
      ibmSystempTrapSCSIDiskPERMTimeStamp
   }
   DESCRIPTION    "A System p event has occurred"
-- REFERENCE      "POWER_SCSIDiskPERMEventIndication"
::= 586

ibmSystempTrapSCSIDiskPERMBindings OBJECT IDENTIFIER ::= { ibmSystemTrap 586 }

ibmSystempTrapSCSIDiskPERMProviderName OBJECT-TYPE
   SYNTAX         String
   ACCESS         read-only
   STATUS         mandatory
   DESCRIPTION    "The name of the CIM Provider that monitors this device"
-- REFERENCE      "POWER_SCSIDiskPERMEventIndication.ProviderName"
::= { ibmSystempTrapSCSIDiskPERMBindings 1 }

ibmSystempTrapSCSIDiskPERMEventID OBJECT-TYPE
   SYNTAX         String
   ACCESS         read-only
   STATUS         mandatory
   DESCRIPTION    "A unique EventID that identifies this trap" 
-- REFERENCE      "POWER_SCSIDiskPERMEventIndication.EventID"
::= { ibmSystempTrapSCSIDiskPERMBindings 2 }

ibmSystempTrapSCSIDiskPERMAME OBJECT-TYPE
   SYNTAX         String
   ACCESS         read-only
   STATUS         mandatory
   DESCRIPTION    "A unique string that identifies the monitored device"
-- REFERENCE      "POWER_SCSIDiskPERMEventIndication.AlertingManagedElement"
::= { ibmSystempTrapSCSIDiskPERMBindings 3 }

ibmSystempTrapSCSIDiskPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIDiskPERMEventIndication.Severity"
::= { ibmSystempTrapSCSIDiskPERMBindings 4 }

ibmSystempTrapSCSIDiskPERMDescription OBJECT-TYPE
   SYNTAX         SnmpAdminString
   ACCESS         read-only
   STATUS         mandatory
   DESCRIPTION    "The Event text of the trap"
-- REFERENCE      "POWER_SCSIDiskPERMEventIndication.Description"
::= { ibmSystempTrapSCSIDiskPERMBindings 5 }

ibmSystempTrapSCSIDiskPERMTimeStamp OBJECT-TYPE
   SYNTAX         Datetime
   ACCESS         read-only
   STATUS         mandatory
   DESCRIPTION    "The time that the trap occurred"
-- REFERENCE      "POWER_SCSIDiskPERMEventIndication.TimeStamp"
::= { ibmSystempTrapSCSIDiskPERMBindings 6 }


ibmSystempTrapOpticalDeviceINFO TRAP-TYPE
   ENTERPRISE     ibmSystemMIB
   VARIABLES    {
      ibmSystempTrapOpticalDeviceINFOProviderName,
      ibmSystempTrapOpticalDeviceINFOEventID,
      ibmSystempTrapOpticalDeviceINFOAME,
      ibmSystempTrapOpticalDeviceINFOSeverity,
      ibmSystempTrapOpticalDeviceINFODescription,
      ibmSystempTrapOpticalDeviceINFOTimeStamp
   }
   DESCRIPTION    "A System p event has occurred"
-- REFERENCE      "POWER_OpticalDeviceINFOEventIndication"
::= 587

ibmSystempTrapOpticalDeviceINFOBindings OBJECT IDENTIFIER ::= { ibmSystemTrap 587 }

ibmSystempTrapOpticalDeviceINFOProviderName OBJECT-TYPE
   SYNTAX         String
   ACCESS         read-only
   STATUS         mandatory
   DESCRIPTION    "The name of the CIM Provider that monitors this device"
-- REFERENCE      "POWER_OpticalDeviceINFOEventIndication.ProviderName"
::= { ibmSystempTrapOpticalDeviceINFOBindings 1 }

ibmSystempTrapOpticalDeviceINFOEventID OBJECT-TYPE
   SYNTAX         String
   ACCESS         read-only
   STATUS         mandatory
   DESCRIPTION    "A unique EventID that identifies this trap" 
-- REFERENCE      "POWER_OpticalDeviceINFOEventIndication.EventID"
::= { ibmSystempTrapOpticalDeviceINFOBindings 2 }

ibmSystempTrapOpticalDeviceINFOAME OBJECT-TYPE
   SYNTAX         String
   ACCESS         read-only
   STATUS         mandatory
   DESCRIPTION    "A unique string that identifies the monitored device"
-- REFERENCE      "POWER_OpticalDeviceINFOEventIndication.AlertingManagedElement"
::= { ibmSystempTrapOpticalDeviceINFOBindings 3 }

ibmSystempTrapOpticalDeviceINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_OpticalDeviceINFOEventIndication.Severity"
::= { ibmSystempTrapOpticalDeviceINFOBindings 4 }

ibmSystempTrapOpticalDeviceINFODescription OBJECT-TYPE
   SYNTAX         SnmpAdminString
   ACCESS         read-only
   STATUS         mandatory
   DESCRIPTION    "The Event text of the trap"
-- REFERENCE      "POWER_OpticalDeviceINFOEventIndication.Description"
::= { ibmSystempTrapOpticalDeviceINFOBindings 5 }

ibmSystempTrapOpticalDeviceINFOTimeStamp OBJECT-TYPE
   SYNTAX         Datetime
   ACCESS         read-only
   STATUS         mandatory
   DESCRIPTION    "The time that the trap occurred"
-- REFERENCE      "POWER_OpticalDeviceINFOEventIndication.TimeStamp"
::= { ibmSystempTrapOpticalDeviceINFOBindings 6 }


ibmSystempTrapOpticalDeviceTEMP TRAP-TYPE
   ENTERPRISE     ibmSystemMIB
   VARIABLES    {
      ibmSystempTrapOpticalDeviceTEMPProviderName,
      ibmSystempTrapOpticalDeviceTEMPEventID,
      ibmSystempTrapOpticalDeviceTEMPAME,
      ibmSystempTrapOpticalDeviceTEMPSeverity,
      ibmSystempTrapOpticalDeviceTEMPDescription,
      ibmSystempTrapOpticalDeviceTEMPTimeStamp
   }
   DESCRIPTION    "A System p event has occurred"
-- REFERENCE      "POWER_OpticalDeviceTEMPEventIndication"
::= 588

ibmSystempTrapOpticalDeviceTEMPBindings OBJECT IDENTIFIER ::= { ibmSystemTrap 588 }

ibmSystempTrapOpticalDeviceTEMPProviderName OBJECT-TYPE
   SYNTAX         String
   ACCESS         read-only
   STATUS         mandatory
   DESCRIPTION    "The name of the CIM Provider that monitors this device"
-- REFERENCE      "POWER_OpticalDeviceTEMPEventIndication.ProviderName"
::= { ibmSystempTrapOpticalDeviceTEMPBindings 1 }

ibmSystempTrapOpticalDeviceTEMPEventID OBJECT-TYPE
   SYNTAX         String
   ACCESS         read-only
   STATUS         mandatory
   DESCRIPTION    "A unique EventID that identifies this trap" 
-- REFERENCE      "POWER_OpticalDeviceTEMPEventIndication.EventID"
::= { ibmSystempTrapOpticalDeviceTEMPBindings 2 }

ibmSystempTrapOpticalDeviceTEMPAME OBJECT-TYPE
   SYNTAX         String
   ACCESS         read-only
   STATUS         mandatory
   DESCRIPTION    "A unique string that identifies the monitored device"
-- REFERENCE      "POWER_OpticalDeviceTEMPEventIndication.AlertingManagedElement"
::= { ibmSystempTrapOpticalDeviceTEMPBindings 3 }

ibmSystempTrapOpticalDeviceTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_OpticalDeviceTEMPEventIndication.Severity"
::= { ibmSystempTrapOpticalDeviceTEMPBindings 4 }

ibmSystempTrapOpticalDeviceTEMPDescription OBJECT-TYPE
   SYNTAX         SnmpAdminString
   ACCESS         read-only
   STATUS         mandatory
   DESCRIPTION    "The Event text of the trap"
-- REFERENCE      "POWER_OpticalDeviceTEMPEventIndication.Description"
::= { ibmSystempTrapOpticalDeviceTEMPBindings 5 }

ibmSystempTrapOpticalDeviceTEMPTimeStamp OBJECT-TYPE
   SYNTAX         Datetime
   ACCESS         read-only
   STATUS         mandatory
   DESCRIPTION    "The time that the trap occurred"
-- REFERENCE      "POWER_OpticalDeviceTEMPEventIndication.TimeStamp"
::= { ibmSystempTrapOpticalDeviceTEMPBindings 6 }


ibmSystempTrapOpticalDevicePEND TRAP-TYPE
   ENTERPRISE     ibmSystemMIB
   VARIABLES    {
      ibmSystempTrapOpticalDevicePENDProviderName,
      ibmSystempTrapOpticalDevicePENDEventID,
      ibmSystempTrapOpticalDevicePENDAME,
      ibmSystempTrapOpticalDevicePENDSeverity,
      ibmSystempTrapOpticalDevicePENDDescription,
      ibmSystempTrapOpticalDevicePENDTimeStamp
   }
   DESCRIPTION    "A System p event has occurred"
-- REFERENCE      "POWER_OpticalDevicePENDEventIndication"
::= 589

ibmSystempTrapOpticalDevicePENDBindings OBJECT IDENTIFIER ::= { ibmSystemTrap 589 }

ibmSystempTrapOpticalDevicePENDProviderName OBJECT-TYPE
   SYNTAX         String
   ACCESS         read-only
   STATUS         mandatory
   DESCRIPTION    "The name of the CIM Provider that monitors this device"
-- REFERENCE      "POWER_OpticalDevicePENDEventIndication.ProviderName"
::= { ibmSystempTrapOpticalDevicePENDBindings 1 }

ibmSystempTrapOpticalDevicePENDEventID OBJECT-TYPE
   SYNTAX         String
   ACCESS         read-only
   STATUS         mandatory
   DESCRIPTION    "A unique EventID that identifies this trap" 
-- REFERENCE      "POWER_OpticalDevicePENDEventIndication.EventID"
::= { ibmSystempTrapOpticalDevicePENDBindings 2 }

ibmSystempTrapOpticalDevicePENDAME OBJECT-TYPE
   SYNTAX         String
   ACCESS         read-only
   STATUS         mandatory
   DESCRIPTION    "A unique string that identifies the monitored device"
-- REFERENCE      "POWER_OpticalDevicePENDEventIndication.AlertingManagedElement"
::= { ibmSystempTrapOpticalDevicePENDBindings 3 }

ibmSystempTrapOpticalDevicePENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_OpticalDevicePENDEventIndication.Severity"
::= { ibmSystempTrapOpticalDevicePENDBindings 4 }

ibmSystempTrapOpticalDevicePENDDescription OBJECT-TYPE
   SYNTAX         SnmpAdminString
   ACCESS         read-only
   STATUS         mandatory
   DESCRIPTION    "The Event text of the trap"
-- REFERENCE      "POWER_OpticalDevicePENDEventIndication.Description"
::= { ibmSystempTrapOpticalDevicePENDBindings 5 }

ibmSystempTrapOpticalDevicePENDTimeStamp OBJECT-TYPE
   SYNTAX         Datetime
   ACCESS         read-only
   STATUS         mandatory
   DESCRIPTION    "The time that the trap occurred"
-- REFERENCE      "POWER_OpticalDevicePENDEventIndication.TimeStamp"
::= { ibmSystempTrapOpticalDevicePENDBindings 6 }


ibmSystempTrapOpticalDevicePERF TRAP-TYPE
   ENTERPRISE     ibmSystemMIB
   VARIABLES    {
      ibmSystempTrapOpticalDevicePERFProviderName,
      ibmSystempTrapOpticalDevicePERFEventID,
      ibmSystempTrapOpticalDevicePERFAME,
      ibmSystempTrapOpticalDevicePERFSeverity,
      ibmSystempTrapOpticalDevicePERFDescription,
      ibmSystempTrapOpticalDevicePERFTimeStamp
   }
   DESCRIPTION    "A System p event has occurred"
-- REFERENCE      "POWER_OpticalDevicePERFEventIndication"
::= 590

ibmSystempTrapOpticalDevicePERFBindings OBJECT IDENTIFIER ::= { ibmSystemTrap 590 }

ibmSystempTrapOpticalDevicePERFProviderName OBJECT-TYPE
   SYNTAX         String
   ACCESS         read-only
   STATUS         mandatory
   DESCRIPTION    "The name of the CIM Provider that monitors this device"
-- REFERENCE      "POWER_OpticalDevicePERFEventIndication.ProviderName"
::= { ibmSystempTrapOpticalDevicePERFBindings 1 }

ibmSystempTrapOpticalDevicePERFEventID OBJECT-TYPE
   SYNTAX         String
   ACCESS         read-only
   STATUS         mandatory
   DESCRIPTION    "A unique EventID that identifies this trap" 
-- REFERENCE      "POWER_OpticalDevicePERFEventIndication.EventID"
::= { ibmSystempTrapOpticalDevicePERFBindings 2 }

ibmSystempTrapOpticalDevicePERFAME OBJECT-TYPE
   SYNTAX         String
   ACCESS         read-only
   STATUS         mandatory
   DESCRIPTION    "A unique string that identifies the monitored device"
-- REFERENCE      "POWER_OpticalDevicePERFEventIndication.AlertingManagedElement"
::= { ibmSystempTrapOpticalDevicePERFBindings 3 }

ibmSystempTrapOpticalDevicePERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_OpticalDevicePERFEventIndication.Severity"
::= { ibmSystempTrapOpticalDevicePERFBindings 4 }

ibmSystempTrapOpticalDevicePERFDescription OBJECT-TYPE
   SYNTAX         SnmpAdminString
   ACCESS         read-only
   STATUS         mandatory
   DESCRIPTION    "The Event text of the trap"
-- REFERENCE      "POWER_OpticalDevicePERFEventIndication.Description"
::= { ibmSystempTrapOpticalDevicePERFBindings 5 }

ibmSystempTrapOpticalDevicePERFTimeStamp OBJECT-TYPE
   SYNTAX         Datetime
   ACCESS         read-only
   STATUS         mandatory
   DESCRIPTION    "The time that the trap occurred"
-- REFERENCE      "POWER_OpticalDevicePERFEventIndication.TimeStamp"
::= { ibmSystempTrapOpticalDevicePERFBindings 6 }


ibmSystempTrapOpticalDeviceUNKNOWN TRAP-TYPE
   ENTERPRISE     ibmSystemMIB
   VARIABLES    {
      ibmSystempTrapOpticalDeviceUNKNOWNProviderName,
      ibmSystempTrapOpticalDeviceUNKNOWNEventID,
      ibmSystempTrapOpticalDeviceUNKNOWNAME,
      ibmSystempTrapOpticalDeviceUNKNOWNSeverity,
      ibmSystempTrapOpticalDeviceUNKNOWNDescription,
      ibmSystempTrapOpticalDeviceUNKNOWNTimeStamp
   }
   DESCRIPTION    "A System p event has occurred"
-- REFERENCE      "POWER_OpticalDeviceUNKNOWNEventIndication"
::= 591

ibmSystempTrapOpticalDeviceUNKNOWNBindings OBJECT IDENTIFIER ::= { ibmSystemTrap 591 }

ibmSystempTrapOpticalDeviceUNKNOWNProviderName OBJECT-TYPE
   SYNTAX         String
   ACCESS         read-only
   STATUS         mandatory
   DESCRIPTION    "The name of the CIM Provider that monitors this device"
-- REFERENCE      "POWER_OpticalDeviceUNKNOWNEventIndication.ProviderName"
::= { ibmSystempTrapOpticalDeviceUNKNOWNBindings 1 }

ibmSystempTrapOpticalDeviceUNKNOWNEventID OBJECT-TYPE
   SYNTAX         String
   ACCESS         read-only
   STATUS         mandatory
   DESCRIPTION    "A unique EventID that identifies this trap" 
-- REFERENCE      "POWER_OpticalDeviceUNKNOWNEventIndication.EventID"
::= { ibmSystempTrapOpticalDeviceUNKNOWNBindings 2 }

ibmSystempTrapOpticalDeviceUNKNOWNAME OBJECT-TYPE
   SYNTAX         String
   ACCESS         read-only
   STATUS         mandatory
   DESCRIPTION    "A unique string that identifies the monitored device"
-- REFERENCE      "POWER_OpticalDeviceUNKNOWNEventIndication.AlertingManagedElement"
::= { ibmSystempTrapOpticalDeviceUNKNOWNBindings 3 }

ibmSystempTrapOpticalDeviceUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_OpticalDeviceUNKNOWNEventIndication.Severity"
::= { ibmSystempTrapOpticalDeviceUNKNOWNBindings 4 }

ibmSystempTrapOpticalDeviceUNKNOWNDescription OBJECT-TYPE
   SYNTAX         SnmpAdminString
   ACCESS         read-only
   STATUS         mandatory
   DESCRIPTION    "The Event text of the trap"
-- REFERENCE      "POWER_OpticalDeviceUNKNOWNEventIndication.Description"
::= { ibmSystempTrapOpticalDeviceUNKNOWNBindings 5 }

ibmSystempTrapOpticalDeviceUNKNOWNTimeStamp OBJECT-TYPE
   SYNTAX         Datetime
   ACCESS         read-only
   STATUS         mandatory
   DESCRIPTION    "The time that the trap occurred"
-- REFERENCE      "POWER_OpticalDeviceUNKNOWNEventIndication.TimeStamp"
::= { ibmSystempTrapOpticalDeviceUNKNOWNBindings 6 }


ibmSystempTrapOpticalDevicePERM TRAP-TYPE
   ENTERPRISE     ibmSystemMIB
   VARIABLES    {
      ibmSystempTrapOpticalDevicePERMProviderName,
      ibmSystempTrapOpticalDevicePERMEventID,
      ibmSystempTrapOpticalDevicePERMAME,
      ibmSystempTrapOpticalDevicePERMSeverity,
      ibmSystempTrapOpticalDevicePERMDescription,
      ibmSystempTrapOpticalDevicePERMTimeStamp
   }
   DESCRIPTION    "A System p event has occurred"
-- REFERENCE      "POWER_OpticalDevicePERMEventIndication"
::= 592

ibmSystempTrapOpticalDevicePERMBindings OBJECT IDENTIFIER ::= { ibmSystemTrap 592 }

ibmSystempTrapOpticalDevicePERMProviderName OBJECT-TYPE
   SYNTAX         String
   ACCESS         read-only
   STATUS         mandatory
   DESCRIPTION    "The name of the CIM Provider that monitors this device"
-- REFERENCE      "POWER_OpticalDevicePERMEventIndication.ProviderName"
::= { ibmSystempTrapOpticalDevicePERMBindings 1 }

ibmSystempTrapOpticalDevicePERMEventID OBJECT-TYPE
   SYNTAX         String
   ACCESS         read-only
   STATUS         mandatory
   DESCRIPTION    "A unique EventID that identifies this trap" 
-- REFERENCE      "POWER_OpticalDevicePERMEventIndication.EventID"
::= { ibmSystempTrapOpticalDevicePERMBindings 2 }

ibmSystempTrapOpticalDevicePERMAME OBJECT-TYPE
   SYNTAX         String
   ACCESS         read-only
   STATUS         mandatory
   DESCRIPTION    "A unique string that identifies the monitored device"
-- REFERENCE      "POWER_OpticalDevicePERMEventIndication.AlertingManagedElement"
::= { ibmSystempTrapOpticalDevicePERMBindings 3 }

ibmSystempTrapOpticalDevicePERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_OpticalDevicePERMEventIndication.Severity"
::= { ibmSystempTrapOpticalDevicePERMBindings 4 }

ibmSystempTrapOpticalDevicePERMDescription OBJECT-TYPE
   SYNTAX         SnmpAdminString
   ACCESS         read-only
   STATUS         mandatory
   DESCRIPTION    "The Event text of the trap"
-- REFERENCE      "POWER_OpticalDevicePERMEventIndication.Description"
::= { ibmSystempTrapOpticalDevicePERMBindings 5 }

ibmSystempTrapOpticalDevicePERMTimeStamp OBJECT-TYPE
   SYNTAX         Datetime
   ACCESS         read-only
   STATUS         mandatory
   DESCRIPTION    "The time that the trap occurred"
-- REFERENCE      "POWER_OpticalDevicePERMEventIndication.TimeStamp"
::= { ibmSystempTrapOpticalDevicePERMBindings 6 }


ibmSystempTrapiSCSITOEINFO TRAP-TYPE
   ENTERPRISE     ibmSystemMIB
   VARIABLES    {
      ibmSystempTrapiSCSITOEINFOProviderName,
      ibmSystempTrapiSCSITOEINFOEventID,
      ibmSystempTrapiSCSITOEINFOAME,
      ibmSystempTrapiSCSITOEINFOSeverity,
      ibmSystempTrapiSCSITOEINFODescription,
      ibmSystempTrapiSCSITOEINFOTimeStamp
   }
   DESCRIPTION    "A System p event has occurred"
-- REFERENCE      "POWER_iSCSITOEINFOEventIndication"
::= 593

ibmSystempTrapiSCSITOEINFOBindings OBJECT IDENTIFIER ::= { ibmSystemTrap 593 }

ibmSystempTrapiSCSITOEINFOProviderName OBJECT-TYPE
   SYNTAX         String
   ACCESS         read-only
   STATUS         mandatory
   DESCRIPTION    "The name of the CIM Provider that monitors this device"
-- REFERENCE      "POWER_iSCSITOEINFOEventIndication.ProviderName"
::= { ibmSystempTrapiSCSITOEINFOBindings 1 }

ibmSystempTrapiSCSITOEINFOEventID OBJECT-TYPE
   SYNTAX         String
   ACCESS         read-only
   STATUS         mandatory
   DESCRIPTION    "A unique EventID that identifies this trap" 
-- REFERENCE      "POWER_iSCSITOEINFOEventIndication.EventID"
::= { ibmSystempTrapiSCSITOEINFOBindings 2 }

ibmSystempTrapiSCSITOEINFOAME OBJECT-TYPE
   SYNTAX         String
   ACCESS         read-only
   STATUS         mandatory
   DESCRIPTION    "A unique string that identifies the monitored device"
-- REFERENCE      "POWER_iSCSITOEINFOEventIndication.AlertingManagedElement"
::= { ibmSystempTrapiSCSITOEINFOBindings 3 }

ibmSystempTrapiSCSITOEINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_iSCSITOEINFOEventIndication.Severity"
::= { ibmSystempTrapiSCSITOEINFOBindings 4 }

ibmSystempTrapiSCSITOEINFODescription OBJECT-TYPE
   SYNTAX         SnmpAdminString
   ACCESS         read-only
   STATUS         mandatory
   DESCRIPTION    "The Event text of the trap"
-- REFERENCE      "POWER_iSCSITOEINFOEventIndication.Description"
::= { ibmSystempTrapiSCSITOEINFOBindings 5 }

ibmSystempTrapiSCSITOEINFOTimeStamp OBJECT-TYPE
   SYNTAX         Datetime
   ACCESS         read-only
   STATUS         mandatory
   DESCRIPTION    "The time that the trap occurred"
-- REFERENCE      "POWER_iSCSITOEINFOEventIndication.TimeStamp"
::= { ibmSystempTrapiSCSITOEINFOBindings 6 }


ibmSystempTrapiSCSITOETEMP TRAP-TYPE
   ENTERPRISE     ibmSystemMIB
   VARIABLES    {
      ibmSystempTrapiSCSITOETEMPProviderName,
      ibmSystempTrapiSCSITOETEMPEventID,
      ibmSystempTrapiSCSITOETEMPAME,
      ibmSystempTrapiSCSITOETEMPSeverity,
      ibmSystempTrapiSCSITOETEMPDescription,
      ibmSystempTrapiSCSITOETEMPTimeStamp
   }
   DESCRIPTION    "A System p event has occurred"
-- REFERENCE      "POWER_iSCSITOETEMPEventIndication"
::= 594

ibmSystempTrapiSCSITOETEMPBindings OBJECT IDENTIFIER ::= { ibmSystemTrap 594 }

ibmSystempTrapiSCSITOETEMPProviderName OBJECT-TYPE
   SYNTAX         String
   ACCESS         read-only
   STATUS         mandatory
   DESCRIPTION    "The name of the CIM Provider that monitors this device"
-- REFERENCE      "POWER_iSCSITOETEMPEventIndication.ProviderName"
::= { ibmSystempTrapiSCSITOETEMPBindings 1 }

ibmSystempTrapiSCSITOETEMPEventID OBJECT-TYPE
   SYNTAX         String
   ACCESS         read-only
   STATUS         mandatory
   DESCRIPTION    "A unique EventID that identifies this trap" 
-- REFERENCE      "POWER_iSCSITOETEMPEventIndication.EventID"
::= { ibmSystempTrapiSCSITOETEMPBindings 2 }

ibmSystempTrapiSCSITOETEMPAME OBJECT-TYPE
   SYNTAX         String
   ACCESS         read-only
   STATUS         mandatory
   DESCRIPTION    "A unique string that identifies the monitored device"
-- REFERENCE      "POWER_iSCSITOETEMPEventIndication.AlertingManagedElement"
::= { ibmSystempTrapiSCSITOETEMPBindings 3 }

ibmSystempTrapiSCSITOETEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_iSCSITOETEMPEventIndication.Severity"
::= { ibmSystempTrapiSCSITOETEMPBindings 4 }

ibmSystempTrapiSCSITOETEMPDescription OBJECT-TYPE
   SYNTAX         SnmpAdminString
   ACCESS         read-only
   STATUS         mandatory
   DESCRIPTION    "The Event text of the trap"
-- REFERENCE      "POWER_iSCSITOETEMPEventIndication.Description"
::= { ibmSystempTrapiSCSITOETEMPBindings 5 }

ibmSystempTrapiSCSITOETEMPTimeStamp OBJECT-TYPE
   SYNTAX         Datetime
   ACCESS         read-only
   STATUS         mandatory
   DESCRIPTION    "The time that the trap occurred"
-- REFERENCE      "POWER_iSCSITOETEMPEventIndication.TimeStamp"
::= { ibmSystempTrapiSCSITOETEMPBindings 6 }


ibmSystempTrapiSCSITOEPEND TRAP-TYPE
   ENTERPRISE     ibmSystemMIB
   VARIABLES    {
      ibmSystempTrapiSCSITOEPENDProviderName,
      ibmSystempTrapiSCSITOEPENDEventID,
      ibmSystempTrapiSCSITOEPENDAME,
      ibmSystempTrapiSCSITOEPENDSeverity,
      ibmSystempTrapiSCSITOEPENDDescription,
      ibmSystempTrapiSCSITOEPENDTimeStamp
   }
   DESCRIPTION    "A System p event has occurred"
-- REFERENCE      "POWER_iSCSITOEPENDEventIndication"
::= 595

ibmSystempTrapiSCSITOEPENDBindings OBJECT IDENTIFIER ::= { ibmSystemTrap 595 }

ibmSystempTrapiSCSITOEPENDProviderName OBJECT-TYPE
   SYNTAX         String
   ACCESS         read-only
   STATUS         mandatory
   DESCRIPTION    "The name of the CIM Provider that monitors this device"
-- REFERENCE      "POWER_iSCSITOEPENDEventIndication.ProviderName"
::= { ibmSystempTrapiSCSITOEPENDBindings 1 }

ibmSystempTrapiSCSITOEPENDEventID OBJECT-TYPE
   SYNTAX         String
   ACCESS         read-only
   STATUS         mandatory
   DESCRIPTION    "A unique EventID that identifies this trap" 
-- REFERENCE      "POWER_iSCSITOEPENDEventIndication.EventID"
::= { ibmSystempTrapiSCSITOEPENDBindings 2 }

ibmSystempTrapiSCSITOEPENDAME OBJECT-TYPE
   SYNTAX         String
   ACCESS         read-only
   STATUS         mandatory
   DESCRIPTION    "A unique string that identifies the monitored device"
-- REFERENCE      "POWER_iSCSITOEPENDEventIndication.AlertingManagedElement"
::= { ibmSystempTrapiSCSITOEPENDBindings 3 }

ibmSystempTrapiSCSITOEPENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_iSCSITOEPENDEventIndication.Severity"
::= { ibmSystempTrapiSCSITOEPENDBindings 4 }

ibmSystempTrapiSCSITOEPENDDescription OBJECT-TYPE
   SYNTAX         SnmpAdminString
   ACCESS         read-only
   STATUS         mandatory
   DESCRIPTION    "The Event text of the trap"
-- REFERENCE      "POWER_iSCSITOEPENDEventIndication.Description"
::= { ibmSystempTrapiSCSITOEPENDBindings 5 }

ibmSystempTrapiSCSITOEPENDTimeStamp OBJECT-TYPE
   SYNTAX         Datetime
   ACCESS         read-only
   STATUS         mandatory
   DESCRIPTION    "The time that the trap occurred"
-- REFERENCE      "POWER_iSCSITOEPENDEventIndication.TimeStamp"
::= { ibmSystempTrapiSCSITOEPENDBindings 6 }


ibmSystempTrapiSCSITOEPERF TRAP-TYPE
   ENTERPRISE     ibmSystemMIB
   VARIABLES    {
      ibmSystempTrapiSCSITOEPERFProviderName,
      ibmSystempTrapiSCSITOEPERFEventID,
      ibmSystempTrapiSCSITOEPERFAME,
      ibmSystempTrapiSCSITOEPERFSeverity,
      ibmSystempTrapiSCSITOEPERFDescription,
      ibmSystempTrapiSCSITOEPERFTimeStamp
   }
   DESCRIPTION    "A System p event has occurred"
-- REFERENCE      "POWER_iSCSITOEPERFEventIndication"
::= 596

ibmSystempTrapiSCSITOEPERFBindings OBJECT IDENTIFIER ::= { ibmSystemTrap 596 }

ibmSystempTrapiSCSITOEPERFProviderName OBJECT-TYPE
   SYNTAX         String
   ACCESS         read-only
   STATUS         mandatory
   DESCRIPTION    "The name of the CIM Provider that monitors this device"
-- REFERENCE      "POWER_iSCSITOEPERFEventIndication.ProviderName"
::= { ibmSystempTrapiSCSITOEPERFBindings 1 }

ibmSystempTrapiSCSITOEPERFEventID OBJECT-TYPE
   SYNTAX         String
   ACCESS         read-only
   STATUS         mandatory
   DESCRIPTION    "A unique EventID that identifies this trap" 
-- REFERENCE      "POWER_iSCSITOEPERFEventIndication.EventID"
::= { ibmSystempTrapiSCSITOEPERFBindings 2 }

ibmSystempTrapiSCSITOEPERFAME OBJECT-TYPE
   SYNTAX         String
   ACCESS         read-only
   STATUS         mandatory
   DESCRIPTION    "A unique string that identifies the monitored device"
-- REFERENCE      "POWER_iSCSITOEPERFEventIndication.AlertingManagedElement"
::= { ibmSystempTrapiSCSITOEPERFBindings 3 }

ibmSystempTrapiSCSITOEPERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_iSCSITOEPERFEventIndication.Severity"
::= { ibmSystempTrapiSCSITOEPERFBindings 4 }

ibmSystempTrapiSCSITOEPERFDescription OBJECT-TYPE
   SYNTAX         SnmpAdminString
   ACCESS         read-only
   STATUS         mandatory
   DESCRIPTION    "The Event text of the trap"
-- REFERENCE      "POWER_iSCSITOEPERFEventIndication.Description"
::= { ibmSystempTrapiSCSITOEPERFBindings 5 }

ibmSystempTrapiSCSITOEPERFTimeStamp OBJECT-TYPE
   SYNTAX         Datetime
   ACCESS         read-only
   STATUS         mandatory
   DESCRIPTION    "The time that the trap occurred"
-- REFERENCE      "POWER_iSCSITOEPERFEventIndication.TimeStamp"
::= { ibmSystempTrapiSCSITOEPERFBindings 6 }


ibmSystempTrapiSCSITOEUNKNOWN TRAP-TYPE
   ENTERPRISE     ibmSystemMIB
   VARIABLES    {
      ibmSystempTrapiSCSITOEUNKNOWNProviderName,
      ibmSystempTrapiSCSITOEUNKNOWNEventID,
      ibmSystempTrapiSCSITOEUNKNOWNAME,
      ibmSystempTrapiSCSITOEUNKNOWNSeverity,
      ibmSystempTrapiSCSITOEUNKNOWNDescription,
      ibmSystempTrapiSCSITOEUNKNOWNTimeStamp
   }
   DESCRIPTION    "A System p event has occurred"
-- REFERENCE      "POWER_iSCSITOEUNKNOWNEventIndication"
::= 597

ibmSystempTrapiSCSITOEUNKNOWNBindings OBJECT IDENTIFIER ::= { ibmSystemTrap 597 }

ibmSystempTrapiSCSITOEUNKNOWNProviderName OBJECT-TYPE
   SYNTAX         String
   ACCESS         read-only
   STATUS         mandatory
   DESCRIPTION    "The name of the CIM Provider that monitors this device"
-- REFERENCE      "POWER_iSCSITOEUNKNOWNEventIndication.ProviderName"
::= { ibmSystempTrapiSCSITOEUNKNOWNBindings 1 }

ibmSystempTrapiSCSITOEUNKNOWNEventID OBJECT-TYPE
   SYNTAX         String
   ACCESS         read-only
   STATUS         mandatory
   DESCRIPTION    "A unique EventID that identifies this trap" 
-- REFERENCE      "POWER_iSCSITOEUNKNOWNEventIndication.EventID"
::= { ibmSystempTrapiSCSITOEUNKNOWNBindings 2 }

ibmSystempTrapiSCSITOEUNKNOWNAME OBJECT-TYPE
   SYNTAX         String
   ACCESS         read-only
   STATUS         mandatory
   DESCRIPTION    "A unique string that identifies the monitored device"
-- REFERENCE      "POWER_iSCSITOEUNKNOWNEventIndication.AlertingManagedElement"
::= { ibmSystempTrapiSCSITOEUNKNOWNBindings 3 }

ibmSystempTrapiSCSITOEUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_iSCSITOEUNKNOWNEventIndication.Severity"
::= { ibmSystempTrapiSCSITOEUNKNOWNBindings 4 }

ibmSystempTrapiSCSITOEUNKNOWNDescription OBJECT-TYPE
   SYNTAX         SnmpAdminString
   ACCESS         read-only
   STATUS         mandatory
   DESCRIPTION    "The Event text of the trap"
-- REFERENCE      "POWER_iSCSITOEUNKNOWNEventIndication.Description"
::= { ibmSystempTrapiSCSITOEUNKNOWNBindings 5 }

ibmSystempTrapiSCSITOEUNKNOWNTimeStamp OBJECT-TYPE
   SYNTAX         Datetime
   ACCESS         read-only
   STATUS         mandatory
   DESCRIPTION    "The time that the trap occurred"
-- REFERENCE      "POWER_iSCSITOEUNKNOWNEventIndication.TimeStamp"
::= { ibmSystempTrapiSCSITOEUNKNOWNBindings 6 }


ibmSystempTrapiSCSITOEPERM TRAP-TYPE
   ENTERPRISE     ibmSystemMIB
   VARIABLES    {
      ibmSystempTrapiSCSITOEPERMProviderName,
      ibmSystempTrapiSCSITOEPERMEventID,
      ibmSystempTrapiSCSITOEPERMAME,
      ibmSystempTrapiSCSITOEPERMSeverity,
      ibmSystempTrapiSCSITOEPERMDescription,
      ibmSystempTrapiSCSITOEPERMTimeStamp
   }
   DESCRIPTION    "A System p event has occurred"
-- REFERENCE      "POWER_iSCSITOEPERMEventIndication"
::= 598

ibmSystempTrapiSCSITOEPERMBindings OBJECT IDENTIFIER ::= { ibmSystemTrap 598 }

ibmSystempTrapiSCSITOEPERMProviderName OBJECT-TYPE
   SYNTAX         String
   ACCESS         read-only
   STATUS         mandatory
   DESCRIPTION    "The name of the CIM Provider that monitors this device"
-- REFERENCE      "POWER_iSCSITOEPERMEventIndication.ProviderName"
::= { ibmSystempTrapiSCSITOEPERMBindings 1 }

ibmSystempTrapiSCSITOEPERMEventID OBJECT-TYPE
   SYNTAX         String
   ACCESS         read-only
   STATUS         mandatory
   DESCRIPTION    "A unique EventID that identifies this trap" 
-- REFERENCE      "POWER_iSCSITOEPERMEventIndication.EventID"
::= { ibmSystempTrapiSCSITOEPERMBindings 2 }

ibmSystempTrapiSCSITOEPERMAME OBJECT-TYPE
   SYNTAX         String
   ACCESS         read-only
   STATUS         mandatory
   DESCRIPTION    "A unique string that identifies the monitored device"
-- REFERENCE      "POWER_iSCSITOEPERMEventIndication.AlertingManagedElement"
::= { ibmSystempTrapiSCSITOEPERMBindings 3 }

ibmSystempTrapiSCSITOEPERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_iSCSITOEPERMEventIndication.Severity"
::= { ibmSystempTrapiSCSITOEPERMBindings 4 }

ibmSystempTrapiSCSITOEPERMDescription OBJECT-TYPE
   SYNTAX         SnmpAdminString
   ACCESS         read-only
   STATUS         mandatory
   DESCRIPTION    "The Event text of the trap"
-- REFERENCE      "POWER_iSCSITOEPERMEventIndication.Description"
::= { ibmSystempTrapiSCSITOEPERMBindings 5 }

ibmSystempTrapiSCSITOEPERMTimeStamp OBJECT-TYPE
   SYNTAX         Datetime
   ACCESS         read-only
   STATUS         mandatory
   DESCRIPTION    "The time that the trap occurred"
-- REFERENCE      "POWER_iSCSITOEPERMEventIndication.TimeStamp"
::= { ibmSystempTrapiSCSITOEPERMBindings 6 }


ibmSystempTrapSCSIEnclosureINFO TRAP-TYPE
   ENTERPRISE     ibmSystemMIB
   VARIABLES    {
      ibmSystempTrapSCSIEnclosureINFOProviderName,
      ibmSystempTrapSCSIEnclosureINFOEventID,
      ibmSystempTrapSCSIEnclosureINFOAME,
      ibmSystempTrapSCSIEnclosureINFOSeverity,
      ibmSystempTrapSCSIEnclosureINFODescription,
      ibmSystempTrapSCSIEnclosureINFOTimeStamp
   }
   DESCRIPTION    "A System p event has occurred"
-- REFERENCE      "POWER_SCSIEnclosureINFOEventIndication"
::= 599

ibmSystempTrapSCSIEnclosureINFOBindings OBJECT IDENTIFIER ::= { ibmSystemTrap 599 }

ibmSystempTrapSCSIEnclosureINFOProviderName OBJECT-TYPE
   SYNTAX         String
   ACCESS         read-only
   STATUS         mandatory
   DESCRIPTION    "The name of the CIM Provider that monitors this device"
-- REFERENCE      "POWER_SCSIEnclosureINFOEventIndication.ProviderName"
::= { ibmSystempTrapSCSIEnclosureINFOBindings 1 }

ibmSystempTrapSCSIEnclosureINFOEventID OBJECT-TYPE
   SYNTAX         String
   ACCESS         read-only
   STATUS         mandatory
   DESCRIPTION    "A unique EventID that identifies this trap" 
-- REFERENCE      "POWER_SCSIEnclosureINFOEventIndication.EventID"
::= { ibmSystempTrapSCSIEnclosureINFOBindings 2 }

ibmSystempTrapSCSIEnclosureINFOAME OBJECT-TYPE
   SYNTAX         String
   ACCESS         read-only
   STATUS         mandatory
   DESCRIPTION    "A unique string that identifies the monitored device"
-- REFERENCE      "POWER_SCSIEnclosureINFOEventIndication.AlertingManagedElement"
::= { ibmSystempTrapSCSIEnclosureINFOBindings 3 }

ibmSystempTrapSCSIEnclosureINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIEnclosureINFOEventIndication.Severity"
::= { ibmSystempTrapSCSIEnclosureINFOBindings 4 }

ibmSystempTrapSCSIEnclosureINFODescription OBJECT-TYPE
   SYNTAX         SnmpAdminString
   ACCESS         read-only
   STATUS         mandatory
   DESCRIPTION    "The Event text of the trap"
-- REFERENCE      "POWER_SCSIEnclosureINFOEventIndication.Description"
::= { ibmSystempTrapSCSIEnclosureINFOBindings 5 }

ibmSystempTrapSCSIEnclosureINFOTimeStamp OBJECT-TYPE
   SYNTAX         Datetime
   ACCESS         read-only
   STATUS         mandatory
   DESCRIPTION    "The time that the trap occurred"
-- REFERENCE      "POWER_SCSIEnclosureINFOEventIndication.TimeStamp"
::= { ibmSystempTrapSCSIEnclosureINFOBindings 6 }


ibmSystempTrapSCSIEnclosureTEMP TRAP-TYPE
   ENTERPRISE     ibmSystemMIB
   VARIABLES    {
      ibmSystempTrapSCSIEnclosureTEMPProviderName,
      ibmSystempTrapSCSIEnclosureTEMPEventID,
      ibmSystempTrapSCSIEnclosureTEMPAME,
      ibmSystempTrapSCSIEnclosureTEMPSeverity,
      ibmSystempTrapSCSIEnclosureTEMPDescription,
      ibmSystempTrapSCSIEnclosureTEMPTimeStamp
   }
   DESCRIPTION    "A System p event has occurred"
-- REFERENCE      "POWER_SCSIEnclosureTEMPEventIndication"
::= 600

ibmSystempTrapSCSIEnclosureTEMPBindings OBJECT IDENTIFIER ::= { ibmSystemTrap 600 }

ibmSystempTrapSCSIEnclosureTEMPProviderName OBJECT-TYPE
   SYNTAX         String
   ACCESS         read-only
   STATUS         mandatory
   DESCRIPTION    "The name of the CIM Provider that monitors this device"
-- REFERENCE      "POWER_SCSIEnclosureTEMPEventIndication.ProviderName"
::= { ibmSystempTrapSCSIEnclosureTEMPBindings 1 }

ibmSystempTrapSCSIEnclosureTEMPEventID OBJECT-TYPE
   SYNTAX         String
   ACCESS         read-only
   STATUS         mandatory
   DESCRIPTION    "A unique EventID that identifies this trap" 
-- REFERENCE      "POWER_SCSIEnclosureTEMPEventIndication.EventID"
::= { ibmSystempTrapSCSIEnclosureTEMPBindings 2 }

ibmSystempTrapSCSIEnclosureTEMPAME OBJECT-TYPE
   SYNTAX         String
   ACCESS         read-only
   STATUS         mandatory
   DESCRIPTION    "A unique string that identifies the monitored device"
-- REFERENCE      "POWER_SCSIEnclosureTEMPEventIndication.AlertingManagedElement"
::= { ibmSystempTrapSCSIEnclosureTEMPBindings 3 }

ibmSystempTrapSCSIEnclosureTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIEnclosureTEMPEventIndication.Severity"
::= { ibmSystempTrapSCSIEnclosureTEMPBindings 4 }

ibmSystempTrapSCSIEnclosureTEMPDescription OBJECT-TYPE
   SYNTAX         SnmpAdminString
   ACCESS         read-only
   STATUS         mandatory
   DESCRIPTION    "The Event text of the trap"
-- REFERENCE      "POWER_SCSIEnclosureTEMPEventIndication.Description"
::= { ibmSystempTrapSCSIEnclosureTEMPBindings 5 }

ibmSystempTrapSCSIEnclosureTEMPTimeStamp OBJECT-TYPE
   SYNTAX         Datetime
   ACCESS         read-only
   STATUS         mandatory
   DESCRIPTION    "The time that the trap occurred"
-- REFERENCE      "POWER_SCSIEnclosureTEMPEventIndication.TimeStamp"
::= { ibmSystempTrapSCSIEnclosureTEMPBindings 6 }


ibmSystempTrapSCSIEnclosurePEND TRAP-TYPE
   ENTERPRISE     ibmSystemMIB
   VARIABLES    {
      ibmSystempTrapSCSIEnclosurePENDProviderName,
      ibmSystempTrapSCSIEnclosurePENDEventID,
      ibmSystempTrapSCSIEnclosurePENDAME,
      ibmSystempTrapSCSIEnclosurePENDSeverity,
      ibmSystempTrapSCSIEnclosurePENDDescription,
      ibmSystempTrapSCSIEnclosurePENDTimeStamp
   }
   DESCRIPTION    "A System p event has occurred"
-- REFERENCE      "POWER_SCSIEnclosurePENDEventIndication"
::= 601

ibmSystempTrapSCSIEnclosurePENDBindings OBJECT IDENTIFIER ::= { ibmSystemTrap 601 }

ibmSystempTrapSCSIEnclosurePENDProviderName OBJECT-TYPE
   SYNTAX         String
   ACCESS         read-only
   STATUS         mandatory
   DESCRIPTION    "The name of the CIM Provider that monitors this device"
-- REFERENCE      "POWER_SCSIEnclosurePENDEventIndication.ProviderName"
::= { ibmSystempTrapSCSIEnclosurePENDBindings 1 }

ibmSystempTrapSCSIEnclosurePENDEventID OBJECT-TYPE
   SYNTAX         String
   ACCESS         read-only
   STATUS         mandatory
   DESCRIPTION    "A unique EventID that identifies this trap" 
-- REFERENCE      "POWER_SCSIEnclosurePENDEventIndication.EventID"
::= { ibmSystempTrapSCSIEnclosurePENDBindings 2 }

ibmSystempTrapSCSIEnclosurePENDAME OBJECT-TYPE
   SYNTAX         String
   ACCESS         read-only
   STATUS         mandatory
   DESCRIPTION    "A unique string that identifies the monitored device"
-- REFERENCE      "POWER_SCSIEnclosurePENDEventIndication.AlertingManagedElement"
::= { ibmSystempTrapSCSIEnclosurePENDBindings 3 }

ibmSystempTrapSCSIEnclosurePENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIEnclosurePENDEventIndication.Severity"
::= { ibmSystempTrapSCSIEnclosurePENDBindings 4 }

ibmSystempTrapSCSIEnclosurePENDDescription OBJECT-TYPE
   SYNTAX         SnmpAdminString
   ACCESS         read-only
   STATUS         mandatory
   DESCRIPTION    "The Event text of the trap"
-- REFERENCE      "POWER_SCSIEnclosurePENDEventIndication.Description"
::= { ibmSystempTrapSCSIEnclosurePENDBindings 5 }

ibmSystempTrapSCSIEnclosurePENDTimeStamp OBJECT-TYPE
   SYNTAX         Datetime
   ACCESS         read-only
   STATUS         mandatory
   DESCRIPTION    "The time that the trap occurred"
-- REFERENCE      "POWER_SCSIEnclosurePENDEventIndication.TimeStamp"
::= { ibmSystempTrapSCSIEnclosurePENDBindings 6 }


ibmSystempTrapSCSIEnclosurePERF TRAP-TYPE
   ENTERPRISE     ibmSystemMIB
   VARIABLES    {
      ibmSystempTrapSCSIEnclosurePERFProviderName,
      ibmSystempTrapSCSIEnclosurePERFEventID,
      ibmSystempTrapSCSIEnclosurePERFAME,
      ibmSystempTrapSCSIEnclosurePERFSeverity,
      ibmSystempTrapSCSIEnclosurePERFDescription,
      ibmSystempTrapSCSIEnclosurePERFTimeStamp
   }
   DESCRIPTION    "A System p event has occurred"
-- REFERENCE      "POWER_SCSIEnclosurePERFEventIndication"
::= 602

ibmSystempTrapSCSIEnclosurePERFBindings OBJECT IDENTIFIER ::= { ibmSystemTrap 602 }

ibmSystempTrapSCSIEnclosurePERFProviderName OBJECT-TYPE
   SYNTAX         String
   ACCESS         read-only
   STATUS         mandatory
   DESCRIPTION    "The name of the CIM Provider that monitors this device"
-- REFERENCE      "POWER_SCSIEnclosurePERFEventIndication.ProviderName"
::= { ibmSystempTrapSCSIEnclosurePERFBindings 1 }

ibmSystempTrapSCSIEnclosurePERFEventID OBJECT-TYPE
   SYNTAX         String
   ACCESS         read-only
   STATUS         mandatory
   DESCRIPTION    "A unique EventID that identifies this trap" 
-- REFERENCE      "POWER_SCSIEnclosurePERFEventIndication.EventID"
::= { ibmSystempTrapSCSIEnclosurePERFBindings 2 }

ibmSystempTrapSCSIEnclosurePERFAME OBJECT-TYPE
   SYNTAX         String
   ACCESS         read-only
   STATUS         mandatory
   DESCRIPTION    "A unique string that identifies the monitored device"
-- REFERENCE      "POWER_SCSIEnclosurePERFEventIndication.AlertingManagedElement"
::= { ibmSystempTrapSCSIEnclosurePERFBindings 3 }

ibmSystempTrapSCSIEnclosurePERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIEnclosurePERFEventIndication.Severity"
::= { ibmSystempTrapSCSIEnclosurePERFBindings 4 }

ibmSystempTrapSCSIEnclosurePERFDescription OBJECT-TYPE
   SYNTAX         SnmpAdminString
   ACCESS         read-only
   STATUS         mandatory
   DESCRIPTION    "The Event text of the trap"
-- REFERENCE      "POWER_SCSIEnclosurePERFEventIndication.Description"
::= { ibmSystempTrapSCSIEnclosurePERFBindings 5 }

ibmSystempTrapSCSIEnclosurePERFTimeStamp OBJECT-TYPE
   SYNTAX         Datetime
   ACCESS         read-only
   STATUS         mandatory
   DESCRIPTION    "The time that the trap occurred"
-- REFERENCE      "POWER_SCSIEnclosurePERFEventIndication.TimeStamp"
::= { ibmSystempTrapSCSIEnclosurePERFBindings 6 }


ibmSystempTrapSCSIEnclosureUNKNOWN TRAP-TYPE
   ENTERPRISE     ibmSystemMIB
   VARIABLES    {
      ibmSystempTrapSCSIEnclosureUNKNOWNProviderName,
      ibmSystempTrapSCSIEnclosureUNKNOWNEventID,
      ibmSystempTrapSCSIEnclosureUNKNOWNAME,
      ibmSystempTrapSCSIEnclosureUNKNOWNSeverity,
      ibmSystempTrapSCSIEnclosureUNKNOWNDescription,
      ibmSystempTrapSCSIEnclosureUNKNOWNTimeStamp
   }
   DESCRIPTION    "A System p event has occurred"
-- REFERENCE      "POWER_SCSIEnclosureUNKNOWNEventIndication"
::= 603

ibmSystempTrapSCSIEnclosureUNKNOWNBindings OBJECT IDENTIFIER ::= { ibmSystemTrap 603 }

ibmSystempTrapSCSIEnclosureUNKNOWNProviderName OBJECT-TYPE
   SYNTAX         String
   ACCESS         read-only
   STATUS         mandatory
   DESCRIPTION    "The name of the CIM Provider that monitors this device"
-- REFERENCE      "POWER_SCSIEnclosureUNKNOWNEventIndication.ProviderName"
::= { ibmSystempTrapSCSIEnclosureUNKNOWNBindings 1 }

ibmSystempTrapSCSIEnclosureUNKNOWNEventID OBJECT-TYPE
   SYNTAX         String
   ACCESS         read-only
   STATUS         mandatory
   DESCRIPTION    "A unique EventID that identifies this trap" 
-- REFERENCE      "POWER_SCSIEnclosureUNKNOWNEventIndication.EventID"
::= { ibmSystempTrapSCSIEnclosureUNKNOWNBindings 2 }

ibmSystempTrapSCSIEnclosureUNKNOWNAME OBJECT-TYPE
   SYNTAX         String
   ACCESS         read-only
   STATUS         mandatory
   DESCRIPTION    "A unique string that identifies the monitored device"
-- REFERENCE      "POWER_SCSIEnclosureUNKNOWNEventIndication.AlertingManagedElement"
::= { ibmSystempTrapSCSIEnclosureUNKNOWNBindings 3 }

ibmSystempTrapSCSIEnclosureUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIEnclosureUNKNOWNEventIndication.Severity"
::= { ibmSystempTrapSCSIEnclosureUNKNOWNBindings 4 }

ibmSystempTrapSCSIEnclosureUNKNOWNDescription OBJECT-TYPE
   SYNTAX         SnmpAdminString
   ACCESS         read-only
   STATUS         mandatory
   DESCRIPTION    "The Event text of the trap"
-- REFERENCE      "POWER_SCSIEnclosureUNKNOWNEventIndication.Description"
::= { ibmSystempTrapSCSIEnclosureUNKNOWNBindings 5 }

ibmSystempTrapSCSIEnclosureUNKNOWNTimeStamp OBJECT-TYPE
   SYNTAX         Datetime
   ACCESS         read-only
   STATUS         mandatory
   DESCRIPTION    "The time that the trap occurred"
-- REFERENCE      "POWER_SCSIEnclosureUNKNOWNEventIndication.TimeStamp"
::= { ibmSystempTrapSCSIEnclosureUNKNOWNBindings 6 }


ibmSystempTrapSCSIEnclosurePERM TRAP-TYPE
   ENTERPRISE     ibmSystemMIB
   VARIABLES    {
      ibmSystempTrapSCSIEnclosurePERMProviderName,
      ibmSystempTrapSCSIEnclosurePERMEventID,
      ibmSystempTrapSCSIEnclosurePERMAME,
      ibmSystempTrapSCSIEnclosurePERMSeverity,
      ibmSystempTrapSCSIEnclosurePERMDescription,
      ibmSystempTrapSCSIEnclosurePERMTimeStamp
   }
   DESCRIPTION    "A System p event has occurred"
-- REFERENCE      "POWER_SCSIEnclosurePERMEventIndication"
::= 604

ibmSystempTrapSCSIEnclosurePERMBindings OBJECT IDENTIFIER ::= { ibmSystemTrap 604 }

ibmSystempTrapSCSIEnclosurePERMProviderName OBJECT-TYPE
   SYNTAX         String
   ACCESS         read-only
   STATUS         mandatory
   DESCRIPTION    "The name of the CIM Provider that monitors this device"
-- REFERENCE      "POWER_SCSIEnclosurePERMEventIndication.ProviderName"
::= { ibmSystempTrapSCSIEnclosurePERMBindings 1 }

ibmSystempTrapSCSIEnclosurePERMEventID OBJECT-TYPE
   SYNTAX         String
   ACCESS         read-only
   STATUS         mandatory
   DESCRIPTION    "A unique EventID that identifies this trap" 
-- REFERENCE      "POWER_SCSIEnclosurePERMEventIndication.EventID"
::= { ibmSystempTrapSCSIEnclosurePERMBindings 2 }

ibmSystempTrapSCSIEnclosurePERMAME OBJECT-TYPE
   SYNTAX         String
   ACCESS         read-only
   STATUS         mandatory
   DESCRIPTION    "A unique string that identifies the monitored device"
-- REFERENCE      "POWER_SCSIEnclosurePERMEventIndication.AlertingManagedElement"
::= { ibmSystempTrapSCSIEnclosurePERMBindings 3 }

ibmSystempTrapSCSIEnclosurePERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_SCSIEnclosurePERMEventIndication.Severity"
::= { ibmSystempTrapSCSIEnclosurePERMBindings 4 }

ibmSystempTrapSCSIEnclosurePERMDescription OBJECT-TYPE
   SYNTAX         SnmpAdminString
   ACCESS         read-only
   STATUS         mandatory
   DESCRIPTION    "The Event text of the trap"
-- REFERENCE      "POWER_SCSIEnclosurePERMEventIndication.Description"
::= { ibmSystempTrapSCSIEnclosurePERMBindings 5 }

ibmSystempTrapSCSIEnclosurePERMTimeStamp OBJECT-TYPE
   SYNTAX         Datetime
   ACCESS         read-only
   STATUS         mandatory
   DESCRIPTION    "The time that the trap occurred"
-- REFERENCE      "POWER_SCSIEnclosurePERMEventIndication.TimeStamp"
::= { ibmSystempTrapSCSIEnclosurePERMBindings 6 }


ibmSystempTrapUSBDisketteINFO TRAP-TYPE
   ENTERPRISE     ibmSystemMIB
   VARIABLES    {
      ibmSystempTrapUSBDisketteINFOProviderName,
      ibmSystempTrapUSBDisketteINFOEventID,
      ibmSystempTrapUSBDisketteINFOAME,
      ibmSystempTrapUSBDisketteINFOSeverity,
      ibmSystempTrapUSBDisketteINFODescription,
      ibmSystempTrapUSBDisketteINFOTimeStamp
   }
   DESCRIPTION    "A System p event has occurred"
-- REFERENCE      "POWER_USBDisketteINFOEventIndication"
::= 605

ibmSystempTrapUSBDisketteINFOBindings OBJECT IDENTIFIER ::= { ibmSystemTrap 605 }

ibmSystempTrapUSBDisketteINFOProviderName OBJECT-TYPE
   SYNTAX         String
   ACCESS         read-only
   STATUS         mandatory
   DESCRIPTION    "The name of the CIM Provider that monitors this device"
-- REFERENCE      "POWER_USBDisketteINFOEventIndication.ProviderName"
::= { ibmSystempTrapUSBDisketteINFOBindings 1 }

ibmSystempTrapUSBDisketteINFOEventID OBJECT-TYPE
   SYNTAX         String
   ACCESS         read-only
   STATUS         mandatory
   DESCRIPTION    "A unique EventID that identifies this trap" 
-- REFERENCE      "POWER_USBDisketteINFOEventIndication.EventID"
::= { ibmSystempTrapUSBDisketteINFOBindings 2 }

ibmSystempTrapUSBDisketteINFOAME OBJECT-TYPE
   SYNTAX         String
   ACCESS         read-only
   STATUS         mandatory
   DESCRIPTION    "A unique string that identifies the monitored device"
-- REFERENCE      "POWER_USBDisketteINFOEventIndication.AlertingManagedElement"
::= { ibmSystempTrapUSBDisketteINFOBindings 3 }

ibmSystempTrapUSBDisketteINFOSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBDisketteINFOEventIndication.Severity"
::= { ibmSystempTrapUSBDisketteINFOBindings 4 }

ibmSystempTrapUSBDisketteINFODescription OBJECT-TYPE
   SYNTAX         SnmpAdminString
   ACCESS         read-only
   STATUS         mandatory
   DESCRIPTION    "The Event text of the trap"
-- REFERENCE      "POWER_USBDisketteINFOEventIndication.Description"
::= { ibmSystempTrapUSBDisketteINFOBindings 5 }

ibmSystempTrapUSBDisketteINFOTimeStamp OBJECT-TYPE
   SYNTAX         Datetime
   ACCESS         read-only
   STATUS         mandatory
   DESCRIPTION    "The time that the trap occurred"
-- REFERENCE      "POWER_USBDisketteINFOEventIndication.TimeStamp"
::= { ibmSystempTrapUSBDisketteINFOBindings 6 }


ibmSystempTrapUSBDisketteTEMP TRAP-TYPE
   ENTERPRISE     ibmSystemMIB
   VARIABLES    {
      ibmSystempTrapUSBDisketteTEMPProviderName,
      ibmSystempTrapUSBDisketteTEMPEventID,
      ibmSystempTrapUSBDisketteTEMPAME,
      ibmSystempTrapUSBDisketteTEMPSeverity,
      ibmSystempTrapUSBDisketteTEMPDescription,
      ibmSystempTrapUSBDisketteTEMPTimeStamp
   }
   DESCRIPTION    "A System p event has occurred"
-- REFERENCE      "POWER_USBDisketteTEMPEventIndication"
::= 606

ibmSystempTrapUSBDisketteTEMPBindings OBJECT IDENTIFIER ::= { ibmSystemTrap 606 }

ibmSystempTrapUSBDisketteTEMPProviderName OBJECT-TYPE
   SYNTAX         String
   ACCESS         read-only
   STATUS         mandatory
   DESCRIPTION    "The name of the CIM Provider that monitors this device"
-- REFERENCE      "POWER_USBDisketteTEMPEventIndication.ProviderName"
::= { ibmSystempTrapUSBDisketteTEMPBindings 1 }

ibmSystempTrapUSBDisketteTEMPEventID OBJECT-TYPE
   SYNTAX         String
   ACCESS         read-only
   STATUS         mandatory
   DESCRIPTION    "A unique EventID that identifies this trap" 
-- REFERENCE      "POWER_USBDisketteTEMPEventIndication.EventID"
::= { ibmSystempTrapUSBDisketteTEMPBindings 2 }

ibmSystempTrapUSBDisketteTEMPAME OBJECT-TYPE
   SYNTAX         String
   ACCESS         read-only
   STATUS         mandatory
   DESCRIPTION    "A unique string that identifies the monitored device"
-- REFERENCE      "POWER_USBDisketteTEMPEventIndication.AlertingManagedElement"
::= { ibmSystempTrapUSBDisketteTEMPBindings 3 }

ibmSystempTrapUSBDisketteTEMPSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBDisketteTEMPEventIndication.Severity"
::= { ibmSystempTrapUSBDisketteTEMPBindings 4 }

ibmSystempTrapUSBDisketteTEMPDescription OBJECT-TYPE
   SYNTAX         SnmpAdminString
   ACCESS         read-only
   STATUS         mandatory
   DESCRIPTION    "The Event text of the trap"
-- REFERENCE      "POWER_USBDisketteTEMPEventIndication.Description"
::= { ibmSystempTrapUSBDisketteTEMPBindings 5 }

ibmSystempTrapUSBDisketteTEMPTimeStamp OBJECT-TYPE
   SYNTAX         Datetime
   ACCESS         read-only
   STATUS         mandatory
   DESCRIPTION    "The time that the trap occurred"
-- REFERENCE      "POWER_USBDisketteTEMPEventIndication.TimeStamp"
::= { ibmSystempTrapUSBDisketteTEMPBindings 6 }


ibmSystempTrapUSBDiskettePEND TRAP-TYPE
   ENTERPRISE     ibmSystemMIB
   VARIABLES    {
      ibmSystempTrapUSBDiskettePENDProviderName,
      ibmSystempTrapUSBDiskettePENDEventID,
      ibmSystempTrapUSBDiskettePENDAME,
      ibmSystempTrapUSBDiskettePENDSeverity,
      ibmSystempTrapUSBDiskettePENDDescription,
      ibmSystempTrapUSBDiskettePENDTimeStamp
   }
   DESCRIPTION    "A System p event has occurred"
-- REFERENCE      "POWER_USBDiskettePENDEventIndication"
::= 607

ibmSystempTrapUSBDiskettePENDBindings OBJECT IDENTIFIER ::= { ibmSystemTrap 607 }

ibmSystempTrapUSBDiskettePENDProviderName OBJECT-TYPE
   SYNTAX         String
   ACCESS         read-only
   STATUS         mandatory
   DESCRIPTION    "The name of the CIM Provider that monitors this device"
-- REFERENCE      "POWER_USBDiskettePENDEventIndication.ProviderName"
::= { ibmSystempTrapUSBDiskettePENDBindings 1 }

ibmSystempTrapUSBDiskettePENDEventID OBJECT-TYPE
   SYNTAX         String
   ACCESS         read-only
   STATUS         mandatory
   DESCRIPTION    "A unique EventID that identifies this trap" 
-- REFERENCE      "POWER_USBDiskettePENDEventIndication.EventID"
::= { ibmSystempTrapUSBDiskettePENDBindings 2 }

ibmSystempTrapUSBDiskettePENDAME OBJECT-TYPE
   SYNTAX         String
   ACCESS         read-only
   STATUS         mandatory
   DESCRIPTION    "A unique string that identifies the monitored device"
-- REFERENCE      "POWER_USBDiskettePENDEventIndication.AlertingManagedElement"
::= { ibmSystempTrapUSBDiskettePENDBindings 3 }

ibmSystempTrapUSBDiskettePENDSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBDiskettePENDEventIndication.Severity"
::= { ibmSystempTrapUSBDiskettePENDBindings 4 }

ibmSystempTrapUSBDiskettePENDDescription OBJECT-TYPE
   SYNTAX         SnmpAdminString
   ACCESS         read-only
   STATUS         mandatory
   DESCRIPTION    "The Event text of the trap"
-- REFERENCE      "POWER_USBDiskettePENDEventIndication.Description"
::= { ibmSystempTrapUSBDiskettePENDBindings 5 }

ibmSystempTrapUSBDiskettePENDTimeStamp OBJECT-TYPE
   SYNTAX         Datetime
   ACCESS         read-only
   STATUS         mandatory
   DESCRIPTION    "The time that the trap occurred"
-- REFERENCE      "POWER_USBDiskettePENDEventIndication.TimeStamp"
::= { ibmSystempTrapUSBDiskettePENDBindings 6 }


ibmSystempTrapUSBDiskettePERF TRAP-TYPE
   ENTERPRISE     ibmSystemMIB
   VARIABLES    {
      ibmSystempTrapUSBDiskettePERFProviderName,
      ibmSystempTrapUSBDiskettePERFEventID,
      ibmSystempTrapUSBDiskettePERFAME,
      ibmSystempTrapUSBDiskettePERFSeverity,
      ibmSystempTrapUSBDiskettePERFDescription,
      ibmSystempTrapUSBDiskettePERFTimeStamp
   }
   DESCRIPTION    "A System p event has occurred"
-- REFERENCE      "POWER_USBDiskettePERFEventIndication"
::= 608

ibmSystempTrapUSBDiskettePERFBindings OBJECT IDENTIFIER ::= { ibmSystemTrap 608 }

ibmSystempTrapUSBDiskettePERFProviderName OBJECT-TYPE
   SYNTAX         String
   ACCESS         read-only
   STATUS         mandatory
   DESCRIPTION    "The name of the CIM Provider that monitors this device"
-- REFERENCE      "POWER_USBDiskettePERFEventIndication.ProviderName"
::= { ibmSystempTrapUSBDiskettePERFBindings 1 }

ibmSystempTrapUSBDiskettePERFEventID OBJECT-TYPE
   SYNTAX         String
   ACCESS         read-only
   STATUS         mandatory
   DESCRIPTION    "A unique EventID that identifies this trap" 
-- REFERENCE      "POWER_USBDiskettePERFEventIndication.EventID"
::= { ibmSystempTrapUSBDiskettePERFBindings 2 }

ibmSystempTrapUSBDiskettePERFAME OBJECT-TYPE
   SYNTAX         String
   ACCESS         read-only
   STATUS         mandatory
   DESCRIPTION    "A unique string that identifies the monitored device"
-- REFERENCE      "POWER_USBDiskettePERFEventIndication.AlertingManagedElement"
::= { ibmSystempTrapUSBDiskettePERFBindings 3 }

ibmSystempTrapUSBDiskettePERFSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBDiskettePERFEventIndication.Severity"
::= { ibmSystempTrapUSBDiskettePERFBindings 4 }

ibmSystempTrapUSBDiskettePERFDescription OBJECT-TYPE
   SYNTAX         SnmpAdminString
   ACCESS         read-only
   STATUS         mandatory
   DESCRIPTION    "The Event text of the trap"
-- REFERENCE      "POWER_USBDiskettePERFEventIndication.Description"
::= { ibmSystempTrapUSBDiskettePERFBindings 5 }

ibmSystempTrapUSBDiskettePERFTimeStamp OBJECT-TYPE
   SYNTAX         Datetime
   ACCESS         read-only
   STATUS         mandatory
   DESCRIPTION    "The time that the trap occurred"
-- REFERENCE      "POWER_USBDiskettePERFEventIndication.TimeStamp"
::= { ibmSystempTrapUSBDiskettePERFBindings 6 }


ibmSystempTrapUSBDisketteUNKNOWN TRAP-TYPE
   ENTERPRISE     ibmSystemMIB
   VARIABLES    {
      ibmSystempTrapUSBDisketteUNKNOWNProviderName,
      ibmSystempTrapUSBDisketteUNKNOWNEventID,
      ibmSystempTrapUSBDisketteUNKNOWNAME,
      ibmSystempTrapUSBDisketteUNKNOWNSeverity,
      ibmSystempTrapUSBDisketteUNKNOWNDescription,
      ibmSystempTrapUSBDisketteUNKNOWNTimeStamp
   }
   DESCRIPTION    "A System p event has occurred"
-- REFERENCE      "POWER_USBDisketteUNKNOWNEventIndication"
::= 609

ibmSystempTrapUSBDisketteUNKNOWNBindings OBJECT IDENTIFIER ::= { ibmSystemTrap 609 }

ibmSystempTrapUSBDisketteUNKNOWNProviderName OBJECT-TYPE
   SYNTAX         String
   ACCESS         read-only
   STATUS         mandatory
   DESCRIPTION    "The name of the CIM Provider that monitors this device"
-- REFERENCE      "POWER_USBDisketteUNKNOWNEventIndication.ProviderName"
::= { ibmSystempTrapUSBDisketteUNKNOWNBindings 1 }

ibmSystempTrapUSBDisketteUNKNOWNEventID OBJECT-TYPE
   SYNTAX         String
   ACCESS         read-only
   STATUS         mandatory
   DESCRIPTION    "A unique EventID that identifies this trap" 
-- REFERENCE      "POWER_USBDisketteUNKNOWNEventIndication.EventID"
::= { ibmSystempTrapUSBDisketteUNKNOWNBindings 2 }

ibmSystempTrapUSBDisketteUNKNOWNAME OBJECT-TYPE
   SYNTAX         String
   ACCESS         read-only
   STATUS         mandatory
   DESCRIPTION    "A unique string that identifies the monitored device"
-- REFERENCE      "POWER_USBDisketteUNKNOWNEventIndication.AlertingManagedElement"
::= { ibmSystempTrapUSBDisketteUNKNOWNBindings 3 }

ibmSystempTrapUSBDisketteUNKNOWNSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBDisketteUNKNOWNEventIndication.Severity"
::= { ibmSystempTrapUSBDisketteUNKNOWNBindings 4 }

ibmSystempTrapUSBDisketteUNKNOWNDescription OBJECT-TYPE
   SYNTAX         SnmpAdminString
   ACCESS         read-only
   STATUS         mandatory
   DESCRIPTION    "The Event text of the trap"
-- REFERENCE      "POWER_USBDisketteUNKNOWNEventIndication.Description"
::= { ibmSystempTrapUSBDisketteUNKNOWNBindings 5 }

ibmSystempTrapUSBDisketteUNKNOWNTimeStamp OBJECT-TYPE
   SYNTAX         Datetime
   ACCESS         read-only
   STATUS         mandatory
   DESCRIPTION    "The time that the trap occurred"
-- REFERENCE      "POWER_USBDisketteUNKNOWNEventIndication.TimeStamp"
::= { ibmSystempTrapUSBDisketteUNKNOWNBindings 6 }


ibmSystempTrapUSBDiskettePERM TRAP-TYPE
   ENTERPRISE     ibmSystemMIB
   VARIABLES    {
      ibmSystempTrapUSBDiskettePERMProviderName,
      ibmSystempTrapUSBDiskettePERMEventID,
      ibmSystempTrapUSBDiskettePERMAME,
      ibmSystempTrapUSBDiskettePERMSeverity,
      ibmSystempTrapUSBDiskettePERMDescription,
      ibmSystempTrapUSBDiskettePERMTimeStamp
   }
   DESCRIPTION    "A System p event has occurred"
-- REFERENCE      "POWER_USBDiskettePERMEventIndication"
::= 610

ibmSystempTrapUSBDiskettePERMBindings OBJECT IDENTIFIER ::= { ibmSystemTrap 610 }

ibmSystempTrapUSBDiskettePERMProviderName OBJECT-TYPE
   SYNTAX         String
   ACCESS         read-only
   STATUS         mandatory
   DESCRIPTION    "The name of the CIM Provider that monitors this device"
-- REFERENCE      "POWER_USBDiskettePERMEventIndication.ProviderName"
::= { ibmSystempTrapUSBDiskettePERMBindings 1 }

ibmSystempTrapUSBDiskettePERMEventID OBJECT-TYPE
   SYNTAX         String
   ACCESS         read-only
   STATUS         mandatory
   DESCRIPTION    "A unique EventID that identifies this trap" 
-- REFERENCE      "POWER_USBDiskettePERMEventIndication.EventID"
::= { ibmSystempTrapUSBDiskettePERMBindings 2 }

ibmSystempTrapUSBDiskettePERMAME OBJECT-TYPE
   SYNTAX         String
   ACCESS         read-only
   STATUS         mandatory
   DESCRIPTION    "A unique string that identifies the monitored device"
-- REFERENCE      "POWER_USBDiskettePERMEventIndication.AlertingManagedElement"
::= { ibmSystempTrapUSBDiskettePERMBindings 3 }

ibmSystempTrapUSBDiskettePERMSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_USBDiskettePERMEventIndication.Severity"
::= { ibmSystempTrapUSBDiskettePERMBindings 4 }

ibmSystempTrapUSBDiskettePERMDescription OBJECT-TYPE
   SYNTAX         SnmpAdminString
   ACCESS         read-only
   STATUS         mandatory
   DESCRIPTION    "The Event text of the trap"
-- REFERENCE      "POWER_USBDiskettePERMEventIndication.Description"
::= { ibmSystempTrapUSBDiskettePERMBindings 5 }

ibmSystempTrapUSBDiskettePERMTimeStamp OBJECT-TYPE
   SYNTAX         Datetime
   ACCESS         read-only
   STATUS         mandatory
   DESCRIPTION    "The time that the trap occurred"
-- REFERENCE      "POWER_USBDiskettePERMEventIndication.TimeStamp"
::= { ibmSystempTrapUSBDiskettePERMBindings 6 }


ibmSystempTrapMenugoalCECHW TRAP-TYPE
   ENTERPRISE     ibmSystemMIB
   VARIABLES    {
      ibmSystempTrapMenugoalCECHWProviderName,
      ibmSystempTrapMenugoalCECHWEventID,
      ibmSystempTrapMenugoalCECHWAME,
      ibmSystempTrapMenugoalCECHWSeverity,
      ibmSystempTrapMenugoalCECHWDescription,
      ibmSystempTrapMenugoalCECHWTimeStamp
   }
   DESCRIPTION    "A System p event has occurred"
-- REFERENCE      "POWER_MenugoalCECHWEventIndication"
::= 611

ibmSystempTrapMenugoalCECHWBindings OBJECT IDENTIFIER ::= { ibmSystemTrap 611 }

ibmSystempTrapMenugoalCECHWProviderName OBJECT-TYPE
   SYNTAX         String
   ACCESS         read-only
   STATUS         mandatory
   DESCRIPTION    "The name of the CIM Provider that monitors this device"
-- REFERENCE      "POWER_MenugoalCECHWEventIndication.ProviderName"
::= { ibmSystempTrapMenugoalCECHWBindings 1 }

ibmSystempTrapMenugoalCECHWEventID OBJECT-TYPE
   SYNTAX         String
   ACCESS         read-only
   STATUS         mandatory
   DESCRIPTION    "A unique EventID that identifies this trap" 
-- REFERENCE      "POWER_MenugoalCECHWEventIndication.EventID"
::= { ibmSystempTrapMenugoalCECHWBindings 2 }

ibmSystempTrapMenugoalCECHWAME OBJECT-TYPE
   SYNTAX         String
   ACCESS         read-only
   STATUS         mandatory
   DESCRIPTION    "A unique string that identifies the monitored device"
-- REFERENCE      "POWER_MenugoalCECHWEventIndication.AlertingManagedElement"
::= { ibmSystempTrapMenugoalCECHWBindings 3 }

ibmSystempTrapMenugoalCECHWSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalCECHWEventIndication.Severity"
::= { ibmSystempTrapMenugoalCECHWBindings 4 }

ibmSystempTrapMenugoalCECHWDescription OBJECT-TYPE
   SYNTAX         SnmpAdminString
   ACCESS         read-only
   STATUS         mandatory
   DESCRIPTION    "The Event text of the trap"
-- REFERENCE      "POWER_MenugoalCECHWEventIndication.Description"
::= { ibmSystempTrapMenugoalCECHWBindings 5 }

ibmSystempTrapMenugoalCECHWTimeStamp OBJECT-TYPE
   SYNTAX         Datetime
   ACCESS         read-only
   STATUS         mandatory
   DESCRIPTION    "The time that the trap occurred"
-- REFERENCE      "POWER_MenugoalCECHWEventIndication.TimeStamp"
::= { ibmSystempTrapMenugoalCECHWBindings 6 }


ibmSystempTrapMenugoalExternalEnvironment TRAP-TYPE
   ENTERPRISE     ibmSystemMIB
   VARIABLES    {
      ibmSystempTrapMenugoalExternalEnvironmentProviderName,
      ibmSystempTrapMenugoalExternalEnvironmentEventID,
      ibmSystempTrapMenugoalExternalEnvironmentAME,
      ibmSystempTrapMenugoalExternalEnvironmentSeverity,
      ibmSystempTrapMenugoalExternalEnvironmentDescription,
      ibmSystempTrapMenugoalExternalEnvironmentTimeStamp
   }
   DESCRIPTION    "A System p event has occurred"
-- REFERENCE      "POWER_MenugoalExternalEnvironmentEventIndication"
::= 612

ibmSystempTrapMenugoalExternalEnvironmentBindings OBJECT IDENTIFIER ::= { ibmSystemTrap 612 }

ibmSystempTrapMenugoalExternalEnvironmentProviderName OBJECT-TYPE
   SYNTAX         String
   ACCESS         read-only
   STATUS         mandatory
   DESCRIPTION    "The name of the CIM Provider that monitors this device"
-- REFERENCE      "POWER_MenugoalExternalEnvironmentEventIndication.ProviderName"
::= { ibmSystempTrapMenugoalExternalEnvironmentBindings 1 }

ibmSystempTrapMenugoalExternalEnvironmentEventID OBJECT-TYPE
   SYNTAX         String
   ACCESS         read-only
   STATUS         mandatory
   DESCRIPTION    "A unique EventID that identifies this trap" 
-- REFERENCE      "POWER_MenugoalExternalEnvironmentEventIndication.EventID"
::= { ibmSystempTrapMenugoalExternalEnvironmentBindings 2 }

ibmSystempTrapMenugoalExternalEnvironmentAME OBJECT-TYPE
   SYNTAX         String
   ACCESS         read-only
   STATUS         mandatory
   DESCRIPTION    "A unique string that identifies the monitored device"
-- REFERENCE      "POWER_MenugoalExternalEnvironmentEventIndication.AlertingManagedElement"
::= { ibmSystempTrapMenugoalExternalEnvironmentBindings 3 }

ibmSystempTrapMenugoalExternalEnvironmentSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalExternalEnvironmentEventIndication.Severity"
::= { ibmSystempTrapMenugoalExternalEnvironmentBindings 4 }

ibmSystempTrapMenugoalExternalEnvironmentDescription OBJECT-TYPE
   SYNTAX         SnmpAdminString
   ACCESS         read-only
   STATUS         mandatory
   DESCRIPTION    "The Event text of the trap"
-- REFERENCE      "POWER_MenugoalExternalEnvironmentEventIndication.Description"
::= { ibmSystempTrapMenugoalExternalEnvironmentBindings 5 }

ibmSystempTrapMenugoalExternalEnvironmentTimeStamp OBJECT-TYPE
   SYNTAX         Datetime
   ACCESS         read-only
   STATUS         mandatory
   DESCRIPTION    "The time that the trap occurred"
-- REFERENCE      "POWER_MenugoalExternalEnvironmentEventIndication.TimeStamp"
::= { ibmSystempTrapMenugoalExternalEnvironmentBindings 6 }


ibmSystempTrapMenugoalFan TRAP-TYPE
   ENTERPRISE     ibmSystemMIB
   VARIABLES    {
      ibmSystempTrapMenugoalFanProviderName,
      ibmSystempTrapMenugoalFanEventID,
      ibmSystempTrapMenugoalFanAME,
      ibmSystempTrapMenugoalFanSeverity,
      ibmSystempTrapMenugoalFanDescription,
      ibmSystempTrapMenugoalFanTimeStamp
   }
   DESCRIPTION    "A System p event has occurred"
-- REFERENCE      "POWER_MenugoalFanEventIndication"
::= 613

ibmSystempTrapMenugoalFanBindings OBJECT IDENTIFIER ::= { ibmSystemTrap 613 }

ibmSystempTrapMenugoalFanProviderName OBJECT-TYPE
   SYNTAX         String
   ACCESS         read-only
   STATUS         mandatory
   DESCRIPTION    "The name of the CIM Provider that monitors this device"
-- REFERENCE      "POWER_MenugoalFanEventIndication.ProviderName"
::= { ibmSystempTrapMenugoalFanBindings 1 }

ibmSystempTrapMenugoalFanEventID OBJECT-TYPE
   SYNTAX         String
   ACCESS         read-only
   STATUS         mandatory
   DESCRIPTION    "A unique EventID that identifies this trap" 
-- REFERENCE      "POWER_MenugoalFanEventIndication.EventID"
::= { ibmSystempTrapMenugoalFanBindings 2 }

ibmSystempTrapMenugoalFanAME OBJECT-TYPE
   SYNTAX         String
   ACCESS         read-only
   STATUS         mandatory
   DESCRIPTION    "A unique string that identifies the monitored device"
-- REFERENCE      "POWER_MenugoalFanEventIndication.AlertingManagedElement"
::= { ibmSystempTrapMenugoalFanBindings 3 }

ibmSystempTrapMenugoalFanSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalFanEventIndication.Severity"
::= { ibmSystempTrapMenugoalFanBindings 4 }

ibmSystempTrapMenugoalFanDescription OBJECT-TYPE
   SYNTAX         SnmpAdminString
   ACCESS         read-only
   STATUS         mandatory
   DESCRIPTION    "The Event text of the trap"
-- REFERENCE      "POWER_MenugoalFanEventIndication.Description"
::= { ibmSystempTrapMenugoalFanBindings 5 }

ibmSystempTrapMenugoalFanTimeStamp OBJECT-TYPE
   SYNTAX         Datetime
   ACCESS         read-only
   STATUS         mandatory
   DESCRIPTION    "The time that the trap occurred"
-- REFERENCE      "POWER_MenugoalFanEventIndication.TimeStamp"
::= { ibmSystempTrapMenugoalFanBindings 6 }


ibmSystempTrapMenugoalIOAdapter TRAP-TYPE
   ENTERPRISE     ibmSystemMIB
   VARIABLES    {
      ibmSystempTrapMenugoalIOAdapterProviderName,
      ibmSystempTrapMenugoalIOAdapterEventID,
      ibmSystempTrapMenugoalIOAdapterAME,
      ibmSystempTrapMenugoalIOAdapterSeverity,
      ibmSystempTrapMenugoalIOAdapterDescription,
      ibmSystempTrapMenugoalIOAdapterTimeStamp
   }
   DESCRIPTION    "A System p event has occurred"
-- REFERENCE      "POWER_MenugoalIOAdapterEventIndication"
::= 614

ibmSystempTrapMenugoalIOAdapterBindings OBJECT IDENTIFIER ::= { ibmSystemTrap 614 }

ibmSystempTrapMenugoalIOAdapterProviderName OBJECT-TYPE
   SYNTAX         String
   ACCESS         read-only
   STATUS         mandatory
   DESCRIPTION    "The name of the CIM Provider that monitors this device"
-- REFERENCE      "POWER_MenugoalIOAdapterEventIndication.ProviderName"
::= { ibmSystempTrapMenugoalIOAdapterBindings 1 }

ibmSystempTrapMenugoalIOAdapterEventID OBJECT-TYPE
   SYNTAX         String
   ACCESS         read-only
   STATUS         mandatory
   DESCRIPTION    "A unique EventID that identifies this trap" 
-- REFERENCE      "POWER_MenugoalIOAdapterEventIndication.EventID"
::= { ibmSystempTrapMenugoalIOAdapterBindings 2 }

ibmSystempTrapMenugoalIOAdapterAME OBJECT-TYPE
   SYNTAX         String
   ACCESS         read-only
   STATUS         mandatory
   DESCRIPTION    "A unique string that identifies the monitored device"
-- REFERENCE      "POWER_MenugoalIOAdapterEventIndication.AlertingManagedElement"
::= { ibmSystempTrapMenugoalIOAdapterBindings 3 }

ibmSystempTrapMenugoalIOAdapterSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalIOAdapterEventIndication.Severity"
::= { ibmSystempTrapMenugoalIOAdapterBindings 4 }

ibmSystempTrapMenugoalIOAdapterDescription OBJECT-TYPE
   SYNTAX         SnmpAdminString
   ACCESS         read-only
   STATUS         mandatory
   DESCRIPTION    "The Event text of the trap"
-- REFERENCE      "POWER_MenugoalIOAdapterEventIndication.Description"
::= { ibmSystempTrapMenugoalIOAdapterBindings 5 }

ibmSystempTrapMenugoalIOAdapterTimeStamp OBJECT-TYPE
   SYNTAX         Datetime
   ACCESS         read-only
   STATUS         mandatory
   DESCRIPTION    "The time that the trap occurred"
-- REFERENCE      "POWER_MenugoalIOAdapterEventIndication.TimeStamp"
::= { ibmSystempTrapMenugoalIOAdapterBindings 6 }


ibmSystempTrapMenugoalIOSubsystem TRAP-TYPE
   ENTERPRISE     ibmSystemMIB
   VARIABLES    {
      ibmSystempTrapMenugoalIOSubsystemProviderName,
      ibmSystempTrapMenugoalIOSubsystemEventID,
      ibmSystempTrapMenugoalIOSubsystemAME,
      ibmSystempTrapMenugoalIOSubsystemSeverity,
      ibmSystempTrapMenugoalIOSubsystemDescription,
      ibmSystempTrapMenugoalIOSubsystemTimeStamp
   }
   DESCRIPTION    "A System p event has occurred"
-- REFERENCE      "POWER_MenugoalIOSubsystemEventIndication"
::= 615

ibmSystempTrapMenugoalIOSubsystemBindings OBJECT IDENTIFIER ::= { ibmSystemTrap 615 }

ibmSystempTrapMenugoalIOSubsystemProviderName OBJECT-TYPE
   SYNTAX         String
   ACCESS         read-only
   STATUS         mandatory
   DESCRIPTION    "The name of the CIM Provider that monitors this device"
-- REFERENCE      "POWER_MenugoalIOSubsystemEventIndication.ProviderName"
::= { ibmSystempTrapMenugoalIOSubsystemBindings 1 }

ibmSystempTrapMenugoalIOSubsystemEventID OBJECT-TYPE
   SYNTAX         String
   ACCESS         read-only
   STATUS         mandatory
   DESCRIPTION    "A unique EventID that identifies this trap" 
-- REFERENCE      "POWER_MenugoalIOSubsystemEventIndication.EventID"
::= { ibmSystempTrapMenugoalIOSubsystemBindings 2 }

ibmSystempTrapMenugoalIOSubsystemAME OBJECT-TYPE
   SYNTAX         String
   ACCESS         read-only
   STATUS         mandatory
   DESCRIPTION    "A unique string that identifies the monitored device"
-- REFERENCE      "POWER_MenugoalIOSubsystemEventIndication.AlertingManagedElement"
::= { ibmSystempTrapMenugoalIOSubsystemBindings 3 }

ibmSystempTrapMenugoalIOSubsystemSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalIOSubsystemEventIndication.Severity"
::= { ibmSystempTrapMenugoalIOSubsystemBindings 4 }

ibmSystempTrapMenugoalIOSubsystemDescription OBJECT-TYPE
   SYNTAX         SnmpAdminString
   ACCESS         read-only
   STATUS         mandatory
   DESCRIPTION    "The Event text of the trap"
-- REFERENCE      "POWER_MenugoalIOSubsystemEventIndication.Description"
::= { ibmSystempTrapMenugoalIOSubsystemBindings 5 }

ibmSystempTrapMenugoalIOSubsystemTimeStamp OBJECT-TYPE
   SYNTAX         Datetime
   ACCESS         read-only
   STATUS         mandatory
   DESCRIPTION    "The time that the trap occurred"
-- REFERENCE      "POWER_MenugoalIOSubsystemEventIndication.TimeStamp"
::= { ibmSystempTrapMenugoalIOSubsystemBindings 6 }


ibmSystempTrapMenugoalMemory TRAP-TYPE
   ENTERPRISE     ibmSystemMIB
   VARIABLES    {
      ibmSystempTrapMenugoalMemoryProviderName,
      ibmSystempTrapMenugoalMemoryEventID,
      ibmSystempTrapMenugoalMemoryAME,
      ibmSystempTrapMenugoalMemorySeverity,
      ibmSystempTrapMenugoalMemoryDescription,
      ibmSystempTrapMenugoalMemoryTimeStamp
   }
   DESCRIPTION    "A System p event has occurred"
-- REFERENCE      "POWER_MenugoalMemoryEventIndication"
::= 616

ibmSystempTrapMenugoalMemoryBindings OBJECT IDENTIFIER ::= { ibmSystemTrap 616 }

ibmSystempTrapMenugoalMemoryProviderName OBJECT-TYPE
   SYNTAX         String
   ACCESS         read-only
   STATUS         mandatory
   DESCRIPTION    "The name of the CIM Provider that monitors this device"
-- REFERENCE      "POWER_MenugoalMemoryEventIndication.ProviderName"
::= { ibmSystempTrapMenugoalMemoryBindings 1 }

ibmSystempTrapMenugoalMemoryEventID OBJECT-TYPE
   SYNTAX         String
   ACCESS         read-only
   STATUS         mandatory
   DESCRIPTION    "A unique EventID that identifies this trap" 
-- REFERENCE      "POWER_MenugoalMemoryEventIndication.EventID"
::= { ibmSystempTrapMenugoalMemoryBindings 2 }

ibmSystempTrapMenugoalMemoryAME OBJECT-TYPE
   SYNTAX         String
   ACCESS         read-only
   STATUS         mandatory
   DESCRIPTION    "A unique string that identifies the monitored device"
-- REFERENCE      "POWER_MenugoalMemoryEventIndication.AlertingManagedElement"
::= { ibmSystempTrapMenugoalMemoryBindings 3 }

ibmSystempTrapMenugoalMemorySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalMemoryEventIndication.Severity"
::= { ibmSystempTrapMenugoalMemoryBindings 4 }

ibmSystempTrapMenugoalMemoryDescription OBJECT-TYPE
   SYNTAX         SnmpAdminString
   ACCESS         read-only
   STATUS         mandatory
   DESCRIPTION    "The Event text of the trap"
-- REFERENCE      "POWER_MenugoalMemoryEventIndication.Description"
::= { ibmSystempTrapMenugoalMemoryBindings 5 }

ibmSystempTrapMenugoalMemoryTimeStamp OBJECT-TYPE
   SYNTAX         Datetime
   ACCESS         read-only
   STATUS         mandatory
   DESCRIPTION    "The time that the trap occurred"
-- REFERENCE      "POWER_MenugoalMemoryEventIndication.TimeStamp"
::= { ibmSystempTrapMenugoalMemoryBindings 6 }


ibmSystempTrapMenugoalOtherSubsystem TRAP-TYPE
   ENTERPRISE     ibmSystemMIB
   VARIABLES    {
      ibmSystempTrapMenugoalOtherSubsystemProviderName,
      ibmSystempTrapMenugoalOtherSubsystemEventID,
      ibmSystempTrapMenugoalOtherSubsystemAME,
      ibmSystempTrapMenugoalOtherSubsystemSeverity,
      ibmSystempTrapMenugoalOtherSubsystemDescription,
      ibmSystempTrapMenugoalOtherSubsystemTimeStamp
   }
   DESCRIPTION    "A System p event has occurred"
-- REFERENCE      "POWER_MenugoalOtherSubsystemEventIndication"
::= 617

ibmSystempTrapMenugoalOtherSubsystemBindings OBJECT IDENTIFIER ::= { ibmSystemTrap 617 }

ibmSystempTrapMenugoalOtherSubsystemProviderName OBJECT-TYPE
   SYNTAX         String
   ACCESS         read-only
   STATUS         mandatory
   DESCRIPTION    "The name of the CIM Provider that monitors this device"
-- REFERENCE      "POWER_MenugoalOtherSubsystemEventIndication.ProviderName"
::= { ibmSystempTrapMenugoalOtherSubsystemBindings 1 }

ibmSystempTrapMenugoalOtherSubsystemEventID OBJECT-TYPE
   SYNTAX         String
   ACCESS         read-only
   STATUS         mandatory
   DESCRIPTION    "A unique EventID that identifies this trap" 
-- REFERENCE      "POWER_MenugoalOtherSubsystemEventIndication.EventID"
::= { ibmSystempTrapMenugoalOtherSubsystemBindings 2 }

ibmSystempTrapMenugoalOtherSubsystemAME OBJECT-TYPE
   SYNTAX         String
   ACCESS         read-only
   STATUS         mandatory
   DESCRIPTION    "A unique string that identifies the monitored device"
-- REFERENCE      "POWER_MenugoalOtherSubsystemEventIndication.AlertingManagedElement"
::= { ibmSystempTrapMenugoalOtherSubsystemBindings 3 }

ibmSystempTrapMenugoalOtherSubsystemSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalOtherSubsystemEventIndication.Severity"
::= { ibmSystempTrapMenugoalOtherSubsystemBindings 4 }

ibmSystempTrapMenugoalOtherSubsystemDescription OBJECT-TYPE
   SYNTAX         SnmpAdminString
   ACCESS         read-only
   STATUS         mandatory
   DESCRIPTION    "The Event text of the trap"
-- REFERENCE      "POWER_MenugoalOtherSubsystemEventIndication.Description"
::= { ibmSystempTrapMenugoalOtherSubsystemBindings 5 }

ibmSystempTrapMenugoalOtherSubsystemTimeStamp OBJECT-TYPE
   SYNTAX         Datetime
   ACCESS         read-only
   STATUS         mandatory
   DESCRIPTION    "The time that the trap occurred"
-- REFERENCE      "POWER_MenugoalOtherSubsystemEventIndication.TimeStamp"
::= { ibmSystempTrapMenugoalOtherSubsystemBindings 6 }


ibmSystempTrapMenugoalPlatformFirmware TRAP-TYPE
   ENTERPRISE     ibmSystemMIB
   VARIABLES    {
      ibmSystempTrapMenugoalPlatformFirmwareProviderName,
      ibmSystempTrapMenugoalPlatformFirmwareEventID,
      ibmSystempTrapMenugoalPlatformFirmwareAME,
      ibmSystempTrapMenugoalPlatformFirmwareSeverity,
      ibmSystempTrapMenugoalPlatformFirmwareDescription,
      ibmSystempTrapMenugoalPlatformFirmwareTimeStamp
   }
   DESCRIPTION    "A System p event has occurred"
-- REFERENCE      "POWER_MenugoalPlatformFirmwareEventIndication"
::= 618

ibmSystempTrapMenugoalPlatformFirmwareBindings OBJECT IDENTIFIER ::= { ibmSystemTrap 618 }

ibmSystempTrapMenugoalPlatformFirmwareProviderName OBJECT-TYPE
   SYNTAX         String
   ACCESS         read-only
   STATUS         mandatory
   DESCRIPTION    "The name of the CIM Provider that monitors this device"
-- REFERENCE      "POWER_MenugoalPlatformFirmwareEventIndication.ProviderName"
::= { ibmSystempTrapMenugoalPlatformFirmwareBindings 1 }

ibmSystempTrapMenugoalPlatformFirmwareEventID OBJECT-TYPE
   SYNTAX         String
   ACCESS         read-only
   STATUS         mandatory
   DESCRIPTION    "A unique EventID that identifies this trap" 
-- REFERENCE      "POWER_MenugoalPlatformFirmwareEventIndication.EventID"
::= { ibmSystempTrapMenugoalPlatformFirmwareBindings 2 }

ibmSystempTrapMenugoalPlatformFirmwareAME OBJECT-TYPE
   SYNTAX         String
   ACCESS         read-only
   STATUS         mandatory
   DESCRIPTION    "A unique string that identifies the monitored device"
-- REFERENCE      "POWER_MenugoalPlatformFirmwareEventIndication.AlertingManagedElement"
::= { ibmSystempTrapMenugoalPlatformFirmwareBindings 3 }

ibmSystempTrapMenugoalPlatformFirmwareSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalPlatformFirmwareEventIndication.Severity"
::= { ibmSystempTrapMenugoalPlatformFirmwareBindings 4 }

ibmSystempTrapMenugoalPlatformFirmwareDescription OBJECT-TYPE
   SYNTAX         SnmpAdminString
   ACCESS         read-only
   STATUS         mandatory
   DESCRIPTION    "The Event text of the trap"
-- REFERENCE      "POWER_MenugoalPlatformFirmwareEventIndication.Description"
::= { ibmSystempTrapMenugoalPlatformFirmwareBindings 5 }

ibmSystempTrapMenugoalPlatformFirmwareTimeStamp OBJECT-TYPE
   SYNTAX         Datetime
   ACCESS         read-only
   STATUS         mandatory
   DESCRIPTION    "The time that the trap occurred"
-- REFERENCE      "POWER_MenugoalPlatformFirmwareEventIndication.TimeStamp"
::= { ibmSystempTrapMenugoalPlatformFirmwareBindings 6 }


ibmSystempTrapMenugoalPowerCooling TRAP-TYPE
   ENTERPRISE     ibmSystemMIB
   VARIABLES    {
      ibmSystempTrapMenugoalPowerCoolingProviderName,
      ibmSystempTrapMenugoalPowerCoolingEventID,
      ibmSystempTrapMenugoalPowerCoolingAME,
      ibmSystempTrapMenugoalPowerCoolingSeverity,
      ibmSystempTrapMenugoalPowerCoolingDescription,
      ibmSystempTrapMenugoalPowerCoolingTimeStamp
   }
   DESCRIPTION    "A System p event has occurred"
-- REFERENCE      "POWER_MenugoalPowerCoolingEventIndication"
::= 619

ibmSystempTrapMenugoalPowerCoolingBindings OBJECT IDENTIFIER ::= { ibmSystemTrap 619 }

ibmSystempTrapMenugoalPowerCoolingProviderName OBJECT-TYPE
   SYNTAX         String
   ACCESS         read-only
   STATUS         mandatory
   DESCRIPTION    "The name of the CIM Provider that monitors this device"
-- REFERENCE      "POWER_MenugoalPowerCoolingEventIndication.ProviderName"
::= { ibmSystempTrapMenugoalPowerCoolingBindings 1 }

ibmSystempTrapMenugoalPowerCoolingEventID OBJECT-TYPE
   SYNTAX         String
   ACCESS         read-only
   STATUS         mandatory
   DESCRIPTION    "A unique EventID that identifies this trap" 
-- REFERENCE      "POWER_MenugoalPowerCoolingEventIndication.EventID"
::= { ibmSystempTrapMenugoalPowerCoolingBindings 2 }

ibmSystempTrapMenugoalPowerCoolingAME OBJECT-TYPE
   SYNTAX         String
   ACCESS         read-only
   STATUS         mandatory
   DESCRIPTION    "A unique string that identifies the monitored device"
-- REFERENCE      "POWER_MenugoalPowerCoolingEventIndication.AlertingManagedElement"
::= { ibmSystempTrapMenugoalPowerCoolingBindings 3 }

ibmSystempTrapMenugoalPowerCoolingSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalPowerCoolingEventIndication.Severity"
::= { ibmSystempTrapMenugoalPowerCoolingBindings 4 }

ibmSystempTrapMenugoalPowerCoolingDescription OBJECT-TYPE
   SYNTAX         SnmpAdminString
   ACCESS         read-only
   STATUS         mandatory
   DESCRIPTION    "The Event text of the trap"
-- REFERENCE      "POWER_MenugoalPowerCoolingEventIndication.Description"
::= { ibmSystempTrapMenugoalPowerCoolingBindings 5 }

ibmSystempTrapMenugoalPowerCoolingTimeStamp OBJECT-TYPE
   SYNTAX         Datetime
   ACCESS         read-only
   STATUS         mandatory
   DESCRIPTION    "The time that the trap occurred"
-- REFERENCE      "POWER_MenugoalPowerCoolingEventIndication.TimeStamp"
::= { ibmSystempTrapMenugoalPowerCoolingBindings 6 }


ibmSystempTrapMenugoalPowerSupply TRAP-TYPE
   ENTERPRISE     ibmSystemMIB
   VARIABLES    {
      ibmSystempTrapMenugoalPowerSupplyProviderName,
      ibmSystempTrapMenugoalPowerSupplyEventID,
      ibmSystempTrapMenugoalPowerSupplyAME,
      ibmSystempTrapMenugoalPowerSupplySeverity,
      ibmSystempTrapMenugoalPowerSupplyDescription,
      ibmSystempTrapMenugoalPowerSupplyTimeStamp
   }
   DESCRIPTION    "A System p event has occurred"
-- REFERENCE      "POWER_MenugoalPowerSupplyEventIndication"
::= 620

ibmSystempTrapMenugoalPowerSupplyBindings OBJECT IDENTIFIER ::= { ibmSystemTrap 620 }

ibmSystempTrapMenugoalPowerSupplyProviderName OBJECT-TYPE
   SYNTAX         String
   ACCESS         read-only
   STATUS         mandatory
   DESCRIPTION    "The name of the CIM Provider that monitors this device"
-- REFERENCE      "POWER_MenugoalPowerSupplyEventIndication.ProviderName"
::= { ibmSystempTrapMenugoalPowerSupplyBindings 1 }

ibmSystempTrapMenugoalPowerSupplyEventID OBJECT-TYPE
   SYNTAX         String
   ACCESS         read-only
   STATUS         mandatory
   DESCRIPTION    "A unique EventID that identifies this trap" 
-- REFERENCE      "POWER_MenugoalPowerSupplyEventIndication.EventID"
::= { ibmSystempTrapMenugoalPowerSupplyBindings 2 }

ibmSystempTrapMenugoalPowerSupplyAME OBJECT-TYPE
   SYNTAX         String
   ACCESS         read-only
   STATUS         mandatory
   DESCRIPTION    "A unique string that identifies the monitored device"
-- REFERENCE      "POWER_MenugoalPowerSupplyEventIndication.AlertingManagedElement"
::= { ibmSystempTrapMenugoalPowerSupplyBindings 3 }

ibmSystempTrapMenugoalPowerSupplySeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalPowerSupplyEventIndication.Severity"
::= { ibmSystempTrapMenugoalPowerSupplyBindings 4 }

ibmSystempTrapMenugoalPowerSupplyDescription OBJECT-TYPE
   SYNTAX         SnmpAdminString
   ACCESS         read-only
   STATUS         mandatory
   DESCRIPTION    "The Event text of the trap"
-- REFERENCE      "POWER_MenugoalPowerSupplyEventIndication.Description"
::= { ibmSystempTrapMenugoalPowerSupplyBindings 5 }

ibmSystempTrapMenugoalPowerSupplyTimeStamp OBJECT-TYPE
   SYNTAX         Datetime
   ACCESS         read-only
   STATUS         mandatory
   DESCRIPTION    "The time that the trap occurred"
-- REFERENCE      "POWER_MenugoalPowerSupplyEventIndication.TimeStamp"
::= { ibmSystempTrapMenugoalPowerSupplyBindings 6 }


ibmSystempTrapMenugoalProcessor TRAP-TYPE
   ENTERPRISE     ibmSystemMIB
   VARIABLES    {
      ibmSystempTrapMenugoalProcessorProviderName,
      ibmSystempTrapMenugoalProcessorEventID,
      ibmSystempTrapMenugoalProcessorAME,
      ibmSystempTrapMenugoalProcessorSeverity,
      ibmSystempTrapMenugoalProcessorDescription,
      ibmSystempTrapMenugoalProcessorTimeStamp
   }
   DESCRIPTION    "A System p event has occurred"
-- REFERENCE      "POWER_MenugoalProcessorEventIndication"
::= 621

ibmSystempTrapMenugoalProcessorBindings OBJECT IDENTIFIER ::= { ibmSystemTrap 621 }

ibmSystempTrapMenugoalProcessorProviderName OBJECT-TYPE
   SYNTAX         String
   ACCESS         read-only
   STATUS         mandatory
   DESCRIPTION    "The name of the CIM Provider that monitors this device"
-- REFERENCE      "POWER_MenugoalProcessorEventIndication.ProviderName"
::= { ibmSystempTrapMenugoalProcessorBindings 1 }

ibmSystempTrapMenugoalProcessorEventID OBJECT-TYPE
   SYNTAX         String
   ACCESS         read-only
   STATUS         mandatory
   DESCRIPTION    "A unique EventID that identifies this trap" 
-- REFERENCE      "POWER_MenugoalProcessorEventIndication.EventID"
::= { ibmSystempTrapMenugoalProcessorBindings 2 }

ibmSystempTrapMenugoalProcessorAME OBJECT-TYPE
   SYNTAX         String
   ACCESS         read-only
   STATUS         mandatory
   DESCRIPTION    "A unique string that identifies the monitored device"
-- REFERENCE      "POWER_MenugoalProcessorEventIndication.AlertingManagedElement"
::= { ibmSystempTrapMenugoalProcessorBindings 3 }

ibmSystempTrapMenugoalProcessorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalProcessorEventIndication.Severity"
::= { ibmSystempTrapMenugoalProcessorBindings 4 }

ibmSystempTrapMenugoalProcessorDescription OBJECT-TYPE
   SYNTAX         SnmpAdminString
   ACCESS         read-only
   STATUS         mandatory
   DESCRIPTION    "The Event text of the trap"
-- REFERENCE      "POWER_MenugoalProcessorEventIndication.Description"
::= { ibmSystempTrapMenugoalProcessorBindings 5 }

ibmSystempTrapMenugoalProcessorTimeStamp OBJECT-TYPE
   SYNTAX         Datetime
   ACCESS         read-only
   STATUS         mandatory
   DESCRIPTION    "The time that the trap occurred"
-- REFERENCE      "POWER_MenugoalProcessorEventIndication.TimeStamp"
::= { ibmSystempTrapMenugoalProcessorBindings 6 }


ibmSystempTrapMenugoalSurveillanceError TRAP-TYPE
   ENTERPRISE     ibmSystemMIB
   VARIABLES    {
      ibmSystempTrapMenugoalSurveillanceErrorProviderName,
      ibmSystempTrapMenugoalSurveillanceErrorEventID,
      ibmSystempTrapMenugoalSurveillanceErrorAME,
      ibmSystempTrapMenugoalSurveillanceErrorSeverity,
      ibmSystempTrapMenugoalSurveillanceErrorDescription,
      ibmSystempTrapMenugoalSurveillanceErrorTimeStamp
   }
   DESCRIPTION    "A System p event has occurred"
-- REFERENCE      "POWER_MenugoalSurveillanceErrorEventIndication"
::= 622

ibmSystempTrapMenugoalSurveillanceErrorBindings OBJECT IDENTIFIER ::= { ibmSystemTrap 622 }

ibmSystempTrapMenugoalSurveillanceErrorProviderName OBJECT-TYPE
   SYNTAX         String
   ACCESS         read-only
   STATUS         mandatory
   DESCRIPTION    "The name of the CIM Provider that monitors this device"
-- REFERENCE      "POWER_MenugoalSurveillanceErrorEventIndication.ProviderName"
::= { ibmSystempTrapMenugoalSurveillanceErrorBindings 1 }

ibmSystempTrapMenugoalSurveillanceErrorEventID OBJECT-TYPE
   SYNTAX         String
   ACCESS         read-only
   STATUS         mandatory
   DESCRIPTION    "A unique EventID that identifies this trap" 
-- REFERENCE      "POWER_MenugoalSurveillanceErrorEventIndication.EventID"
::= { ibmSystempTrapMenugoalSurveillanceErrorBindings 2 }

ibmSystempTrapMenugoalSurveillanceErrorAME OBJECT-TYPE
   SYNTAX         String
   ACCESS         read-only
   STATUS         mandatory
   DESCRIPTION    "A unique string that identifies the monitored device"
-- REFERENCE      "POWER_MenugoalSurveillanceErrorEventIndication.AlertingManagedElement"
::= { ibmSystempTrapMenugoalSurveillanceErrorBindings 3 }

ibmSystempTrapMenugoalSurveillanceErrorSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalSurveillanceErrorEventIndication.Severity"
::= { ibmSystempTrapMenugoalSurveillanceErrorBindings 4 }

ibmSystempTrapMenugoalSurveillanceErrorDescription OBJECT-TYPE
   SYNTAX         SnmpAdminString
   ACCESS         read-only
   STATUS         mandatory
   DESCRIPTION    "The Event text of the trap"
-- REFERENCE      "POWER_MenugoalSurveillanceErrorEventIndication.Description"
::= { ibmSystempTrapMenugoalSurveillanceErrorBindings 5 }

ibmSystempTrapMenugoalSurveillanceErrorTimeStamp OBJECT-TYPE
   SYNTAX         Datetime
   ACCESS         read-only
   STATUS         mandatory
   DESCRIPTION    "The time that the trap occurred"
-- REFERENCE      "POWER_MenugoalSurveillanceErrorEventIndication.TimeStamp"
::= { ibmSystempTrapMenugoalSurveillanceErrorBindings 6 }


ibmSystempTrapMenugoalSysPlanarEvent TRAP-TYPE
   ENTERPRISE     ibmSystemMIB
   VARIABLES    {
      ibmSystempTrapMenugoalSysPlanarEventProviderName,
      ibmSystempTrapMenugoalSysPlanarEventEventID,
      ibmSystempTrapMenugoalSysPlanarEventAME,
      ibmSystempTrapMenugoalSysPlanarEventSeverity,
      ibmSystempTrapMenugoalSysPlanarEventDescription,
      ibmSystempTrapMenugoalSysPlanarEventTimeStamp
   }
   DESCRIPTION    "A System p event has occurred"
-- REFERENCE      "POWER_MenugoalSysPlanarEventEventIndication"
::= 623

ibmSystempTrapMenugoalSysPlanarEventBindings OBJECT IDENTIFIER ::= { ibmSystemTrap 623 }

ibmSystempTrapMenugoalSysPlanarEventProviderName OBJECT-TYPE
   SYNTAX         String
   ACCESS         read-only
   STATUS         mandatory
   DESCRIPTION    "The name of the CIM Provider that monitors this device"
-- REFERENCE      "POWER_MenugoalSysPlanarEventEventIndication.ProviderName"
::= { ibmSystempTrapMenugoalSysPlanarEventBindings 1 }

ibmSystempTrapMenugoalSysPlanarEventEventID OBJECT-TYPE
   SYNTAX         String
   ACCESS         read-only
   STATUS         mandatory
   DESCRIPTION    "A unique EventID that identifies this trap" 
-- REFERENCE      "POWER_MenugoalSysPlanarEventEventIndication.EventID"
::= { ibmSystempTrapMenugoalSysPlanarEventBindings 2 }

ibmSystempTrapMenugoalSysPlanarEventAME OBJECT-TYPE
   SYNTAX         String
   ACCESS         read-only
   STATUS         mandatory
   DESCRIPTION    "A unique string that identifies the monitored device"
-- REFERENCE      "POWER_MenugoalSysPlanarEventEventIndication.AlertingManagedElement"
::= { ibmSystempTrapMenugoalSysPlanarEventBindings 3 }

ibmSystempTrapMenugoalSysPlanarEventSeverity OBJECT-TYPE
   SYNTAX         Uint16
   ACCESS         read-only
   STATUS         mandatory
   DESCRIPTION    "0=Normall -- The trap indicates a normal condition
                   1=Warning -- The trap indicates a warning condition
                   2=Critical -- The trap indicates a critical condition"
-- REFERENCE      "POWER_MenugoalSysPlanarEventEventIndication.Severity"
::= { ibmSystempTrapMenugoalSysPlanarEventBindings 4 }

ibmSystempTrapMenugoalSysPlanarEventDescription OBJECT-TYPE
   SYNTAX         SnmpAdminString
   ACCESS         read-only
   STATUS         mandatory
   DESCRIPTION    "The Event text of the trap"
-- REFERENCE      "POWER_MenugoalSysPlanarEventEventIndication.Description"
::= { ibmSystempTrapMenugoalSysPlanarEventBindings 5 }

ibmSystempTrapMenugoalSysPlanarEventTimeStamp OBJECT-TYPE
   SYNTAX         Datetime
   ACCESS         read-only
   STATUS         mandatory
   DESCRIPTION    "The time that the trap occurred"
-- REFERENCE      "POWER_MenugoalSysPlanarEventEventIndication.TimeStamp"
::= { ibmSystempTrapMenugoalSysPlanarEventBindings 6 }

END
