-- extracted from draft-ietf-ccamp-gmpls-te-mib-09.txt
-- at Fri Jun  3 06:33:28 2005

   IANA-GMPLS-MIB DEFINITIONS ::= BEGIN

   IMPORTS
       MODULE-IDENTITY, transmission       FROM SNMPv2-SMI  -- RFC2578
       TEXTUAL-CONVENTION                  FROM SNMPv2-TC;  -- RFC2579

   ianaGmpls MODULE-IDENTITY
       LAST-UPDATED "200505200001Z" -- 20 May 2005 00:00:01 GMT
       ORGANIZATION "IANA"
       CONTACT-INFO
                  "        Internet Assigned Numbers Authority
                   Postal: USC/Information Sciences Institute
                           4676 Admiralty Way, Marina del Rey, CA 90292
                   Tel:    +1 310 822 1511
                   E-Mail: iana@isi.edu"
       DESCRIPTION
            "The MIB module which defines the GMPLS textual
             conventions for use as enumerations within GMPLS MIB
             modules, thus protecting those MIB modules from changes
             to the enumerations."
       -- Revision history.
          REVISION
               "200505200001Z" -- 20 May 2005 00:00:01 GMT
         DESCRIPTION
           -- RFC Editor: Please see the IANA Considerations Section.
           -- RFC-editor please fill in XXXX
           "Initial version issued as part of RFC XXXX."
       ::= { transmission 1 }

   IANAGmplsLSPEncoding ::= TEXTUAL-CONVENTION
       STATUS       current
       DESCRIPTION
            "This data type is used as the syntax of the
             gmplsTunnelLSPEncoding object in the definition of
             GMPLS-TE-MIB's gmplsTunnelTable.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu).

             gmplsTunnelLSPEncoding is used to represent and control
             the LSP encoding type of an LSP signaled by a GMPLS
             signaling protocol. The relationship between the
             assignment of gmplsTunnelLSPEncoding values and of the
             values used to represent LSP encoding types within the
             GMPLS signaling protocols is solely the purview of IANA
             and is subject to change without notice."
       REFERENCE
            "1. Berger, L., et al., Generalized Multi-Protocol
                Label Switching (GMPLS) Signaling Functional
                Description, RFC 3471, January 2003.
             2. D. Papadimitriou (Editor), Generalized MPLS
                Signalling Extensions for G.709 Optical Transport
                Networks Control, draft-ietf-ccamp-gmpls-g709,
                work in progress."
       SYNTAX  INTEGER {
                  tunnelLspNotGmpls (0),          -- GMPLS is not in use
                  tunnelLspPacket (1),            -- Packet
                  tunnelLspEthernet (2),          -- Ethernet
                  tunnelLspAnsiEtsiPdh (3),       -- PDH
                  -- the value 4 is deprecated
                  tunnelLspSdhSonet (5),          -- SDH or SONET
                  -- the value 6 is deprecated
                  tunnelLspDigitalWrapper (7),    -- Digital Wrapper
                  tunnelLspLambda (8),            -- Lambda
                  tunnelLspFiber (9),             -- Fiber
                  -- the value 10 is deprecated
                  tunnelLspFiberChannel (11),     -- Fiber Channel
                  tunnelDigitalPath (12),         -- Digital Path
                  tunnelOpticalChannel (13)       -- Optical Channel
                }

   IANAGmplsSwitchingType ::= TEXTUAL-CONVENTION
       STATUS       current
       DESCRIPTION
            "This data type is used as the syntax of the
             gmplsTunnelSwitchingType object in the definition of
             GMPLS-TE-MIB's gmplsTunnelTable.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu).

             gmplsTunnelSwitchingType is used to represent and
             control the LSP switching type of an LSP signaled by a
             GMPLS signaling protocol. The relationship between the
             assignment of gmplsTunnelSwitchingType values and of the
             values used to represent LSP switching types within the
             GMPLS signaling protocols is solely the purview of IANA
             and is subject to change without notice."
       REFERENCE
            "1. Kompella, K., Rekhter, Y. (Editors), Routing Extensions
                in Support of Generalized Multi-Protocol Label Switching
                draft-ietf-ccamp-gmpls-routing, work in progress.
             2. Berger, L., et al., Generalized Multi-Protocol
                Label Switching (GMPLS) Signaling Functional
                Description, RFC 3471, January 2003."
       SYNTAX  INTEGER {
                  unknown (0),   -- none of the following, or not known
                  psc1 (1),      -- Packet-Switch-Capable 1
                  psc2 (2),      -- Packet-Switch-Capable 2
                  psc3 (3),      -- Packet-Switch-Capable 3
                  psc4 (4),      -- Packet-Switch-Capable 4
                  l2sc (51),     -- Layer-2-Switch-Capable
                  tdm (100),     -- Time-Division-Multiplex
                  lsc (150),     -- Lambda-Switch-Capable
                  fsc (200)      -- Fiber-Switch-Capable
                }

   IANAGmplsGPid ::= TEXTUAL-CONVENTION
       STATUS       current
       DESCRIPTION
            "This data type is used as the syntax of the
             gmplsTunnelGPid object in the definition of
             GMPLS-TE-MIB's gmplsTunnelTable.
             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu).

             gmplsTunnelGPid is used to represent and control the LSP
             Generalized Protocol Identifier (G-PID) of an LSP
             signaled by a GMPLS signaling protocol. The relationship
             between the assignment of gmplsTunnelGPid values and of
             the values used to represent G-PIDs within the GMPLS
             signaling protocols is solely the purview of IANA and is
             subject to change without notice."
        REFERENCE
            "1. Berger, L., et al., Generalized Multi-Protocol
                Label Switching (GMPLS) Signaling Functional
                Description, RFC 3471, January 2003.
             2. D. Papadimitriou (Editor), Generalized MPLS
                Signalling Extensions for G.709 Optical Transport
                Networks Control, draft-ietf-ccamp-gmpls-g709,
                work in progress."
        SYNTAX  INTEGER {
                  unknown(0),      -- unknown or none of the following
                  asynchE4(5),
                  asynchDS3T3(6),
                  asynchE3(7),
                  bitsynchE3(8),
                  bytesynchE3(9),
                  asynchDS2T2(10),
                  bitsynchDS2T2(11),
                  asynchE1(13),
                  bytesynchE1(14),
                  bytesynch31ByDS0(15),
                  asynchDS1T1(16),
                  bitsynchDS1T1(17),
                  bytesynchDS1T1(18),
                  vc1vc12(19),
                  ds1SFAsynch(22),
                  ds1ESFAsynch(23),
                  ds3M23Asynch(24),
                  ds3CBitParityAsynch(25),
                  vtLovc(26),
                  stsSpeHovc(27),
                  posNoScramble16BitCrc(28),
                  posNoScramble32BitCrc(29),
                  posScramble16BitCrc(30),
                  posScramble32BitCrc(31),
                  atm(32),
                  ethernet(33),
                  sdhSonet(34),
                  digitalwrapper(36),
                  lambda(37),
                  ansiEtsiPdh (38),
                  lapsSdh (40),
                  fddi (41),
                  dqdb (42),
                  fiberChannel3 (43),
                  hdlc (44),
                  ethernetV2DixOnly (45),
                  ethernet802dot3Only (46),
                  g709ODUj (47),
                  g709OTUk (48),
                  g709CBRorCBRa (49),
                  g709CBRb (50),
                  g709BSOT (51),
                  g709BSNT (52),
                  gfpIPorPPP (53),
                  gfpEthernetMAC (54),
                  gfpEthernetPHY (55),
                  g709ESCON (56),
                  g709FICON (57),
                  g709FiberChannel (58)
                }

   IANAGmplsAdminStatusFlags ::= TEXTUAL-CONVENTION
       STATUS       current
       DESCRIPTION
            "This data type is used as the syntax of the
             gmplsTunnelAdminStatusFlags object in the definition of
             GMPLS-TE-MIB's gmplsTunnelTable.

             The definition of this textual convention with the
             addition of newly assigned values is published
             periodically by the IANA, in either the Assigned
             Numbers RFC, or some derivative of it specific to
             Internet Network Management number assignments. (The
             latest arrangements can be obtained by contacting the
             IANA.)

             Requests for new values should be made to IANA via
             email (iana@isi.edu).

             gmplsTunnelAdminStatusFlags determines the setting of the
             Admin Status flags in the Admin Status object or TLV, as
             described in RFC 3471. Setting this object to a non-zero
             value will result in the inclusion of the Admin Status
             object or TLV on signaling messages.

             The relationship between the assignment of
             gmplsTunnelAdminStatusFlags values and of the bit flags
             in the Admin Status object or TLV within the GMPLS
             signaling protocols is solely the purview of IANA and is
             subject to change without notice."
      REFERENCE
            "Berger, L., et al., Generalized Multi-Protocol Label
             Switching (GMPLS) Signaling Functional Description,
             RFC 3471, January 2003."
      SYNTAX  BITS {
                     delInProgress (0),
                     adminDown (1),
                     testing (2),
                     reflect (31)
                   }

   END

-- 
--    Copyright (C) The Internet Society (2005). This document is subject
--    to the rights, licenses and restrictions contained in BCP 78, and
--    except as set forth therein, the authors retain all their rights.
-- 
--    This document and the information contained herein are provided on an
--    "AS IS" basis and THE CONTRIBUTOR, THE ORGANIZATION HE/SHE REPRESENTS
--    OR IS SPONSORED BY (IF ANY), THE INTERNET SOCIETY AND THE INTERNET
--    ENGINEERING TASK FORCE DISCLAIM ALL WARRANTIES, EXPRESS OR IMPLIED,
--    INCLUDING BUT NOT LIMITED TO ANY WARRANTY THAT THE USE OF THE
--    INFORMATION HEREIN WILL NOT INFRINGE ANY RIGHTS OR ANY IMPLIED
--    WARRANTIES OF MERCHANTABILITY OR FITNESS FOR A PARTICULAR PURPOSE.
