INTEL-GEN-MIB DEFINITIONS ::= BEGIN

-- Copyright (C) 1997-2000 Intel Corporation. All rights reserved.
--
-- Main Intel MIB, 00-03-02
--
-- This MIB defined the main management information shared by all
-- Intel newtorking devices.
--
-- Build 9+JBA (With extensions for the Monee project and Firmare v4.2. Not for public release)

IMPORTS
        enterprises, IpAddress, TimeTicks FROM RFC1155-SMI
        OBJECT-TYPE                       FROM RFC-1212
        DisplayString                     FROM RFC1213-MIB
        TRAP-TYPE                         FROM RFC-1215;

        intel                   OBJECT IDENTIFIER     ::= { enterprises 343 }

--  MIB-II sysObjId section
--  All Intel Networking Products supporting this MIB must have their
--  system object ID defined in the sysProducts section below:

         sysProducts            OBJECT IDENTIFIER     ::= { intel 5 }
           switches             OBJECT IDENTIFIER     ::= { sysProducts 1 }
             express10          OBJECT IDENTIFIER     ::= { switches 1 }
             express10plus      OBJECT IDENTIFIER     ::= { switches 2 }
             express100fx       OBJECT IDENTIFIER     ::= { switches 3 }
             express550t        OBJECT IDENTIFIER     ::= { switches 4 }
             express550f        OBJECT IDENTIFIER     ::= { switches 5 }
             express510t        OBJECT IDENTIFIER     ::= { switches 6 }
             express520t        OBJECT IDENTIFIER     ::= { switches 7 }
             expressGigaSwitch  OBJECT IDENTIFIER     ::= { switches 8 }
             express460t-16     OBJECT IDENTIFIER     ::= { switches 9 }
             express460t-24     OBJECT IDENTIFIER     ::= { switches 10 }
             nstructure560t     OBJECT IDENTIFIER     ::= { switches 11 }
             nstructure560tr    OBJECT IDENTIFIER     ::= { switches 13 }
             nstructure560fr    OBJECT IDENTIFIER     ::= { switches 14 }

           routers              OBJECT IDENTIFIER     ::= { sysProducts 2 }
             express9100        OBJECT IDENTIFIER     ::= { routers 1 }
             express920x        OBJECT IDENTIFIER     ::= { routers 2 }
             express9300        OBJECT IDENTIFIER     ::= { routers 3 }
             express9400        OBJECT IDENTIFIER     ::= { routers 4 }
             express8100st      OBJECT IDENTIFIER     ::= { routers 5 }
             express8100u       OBJECT IDENTIFIER     ::= { routers 6 }
             express8100x       OBJECT IDENTIFIER     ::= { routers 7 }
             express8100fr      OBJECT IDENTIFIER     ::= { routers 8 }
             express9520st      OBJECT IDENTIFIER     ::= { routers 9 }
             express9520u       OBJECT IDENTIFIER     ::= { routers 10 }
             express9510st      OBJECT IDENTIFIER     ::= { routers 11 }
             express9510u       OBJECT IDENTIFIER     ::= { routers 12 }
             express9515st      OBJECT IDENTIFIER     ::= { routers 13 }
             express9515u       OBJECT IDENTIFIER     ::= { routers 14 }    
             express9525st      OBJECT IDENTIFIER     ::= { routers 15 }
             express9525u       OBJECT IDENTIFIER     ::= { routers 16 }
             express8210        OBJECT IDENTIFIER     ::= { routers 17 }
             express8220        OBJECT IDENTIFIER     ::= { routers 18 }
             express9530        OBJECT IDENTIFIER     ::= { routers 19 }
             express9535        OBJECT IDENTIFIER     ::= { routers 20 }
             express9545st      OBJECT IDENTIFIER     ::= { routers 21 }
             express9545u       OBJECT IDENTIFIER     ::= { routers 22 }
             express8100wV4     OBJECT IDENTIFIER     ::= { routers 23 }
             express8100stV4    OBJECT IDENTIFIER     ::= { routers 27 }
             express8100uV4     OBJECT IDENTIFIER     ::= { routers 28 }

           hubs                 OBJECT IDENTIFIER     ::= { sysProducts 3 }
             express110-12      OBJECT IDENTIFIER     ::= { hubs 1 }
             express110-24      OBJECT IDENTIFIER     ::= { hubs 2 }
             express210-12      OBJECT IDENTIFIER     ::= { hubs 3 }
             express210-24      OBJECT IDENTIFIER     ::= { hubs 4 }
             express220-12      OBJECT IDENTIFIER     ::= { hubs 5 }
             express220-24      OBJECT IDENTIFIER     ::= { hubs 6 }
             express330-16      OBJECT IDENTIFIER     ::= { hubs 7 }
             express330-24      OBJECT IDENTIFIER     ::= { hubs 8 }

           stacks               OBJECT IDENTIFIER     ::= { sysProducts 4 }
             nstructure560      OBJECT IDENTIFIER     ::= { stacks 1 }
              nstructure560s    OBJECT IDENTIFIER     ::= { nstructure560 1 }
              nstructure560l3s  OBJECT IDENTIFIER     ::= { nstructure560 2 }

--  MIB-II extension section

         mib2ext                OBJECT IDENTIFIER     ::= { intel 6 }
           system               OBJECT IDENTIFIER     ::= { mib2ext 1 }
           ip                   OBJECT IDENTIFIER     ::= { mib2ext 2 }
           snmp                 OBJECT IDENTIFIER     ::= { mib2ext 3 }

-- Common extension MIB's
--         diag                 OBJECT IDENTIFIER     ::= { mib2ext 4 }
--         http                 OBJECT IDENTIFIER     ::= { mib2ext 5 }
--         tcp                  OBJECT IDENTIFIER     ::= { mib2ext 6 }
--         dhcps                OBJECT IDENTIFIER     ::= { mib2ext 7 }
--         evlog                OBJECT IDENTIFIER     ::= { mib2ext 8 }
--         fwmod                OBJECT IDENTIFIER     ::= { mib2ext 9 }
--         confctl              OBJECT IDENTIFIER     ::= { mib2ext 50 }
--         nettime              OBJECT IDENTIFIER     ::= { mib2ext 51 }

-- Switch related extension MIB's
--         es500                OBJECT IDENTIFIER     ::= { mib2ext 10 }
--         vlan                 OBJECT IDENTIFIER     ::= { mib2ext 11 }
--         l3Link               OBJECT IDENTIFIER     ::= { mib2ext 12 }
--         esGigaSwitch         OBJECT IDENTIFIER     ::= { mib2ext 13 }
--         es600                OBJECT IDENTIFIER     ::= { mib2ext 14 }
--         priority             OBJECT IDENTIFIER     ::= { mib2ext 15 }
--         protocolFilter       OBJECT IDENTIFIER     ::= { mib2ext 16 }
--         es400                OBJECT IDENTIFIER     ::= { mib2ext 17 }
--         qBridgeExtMIB        OBJECT IDENTIFIER     ::= { mib2ext 18 }
--         pbridge              OBJECT IDENTIFIER     ::= { mib2ext 19 }

-- Router related extension MIB's
--         mpLink               OBJECT IDENTIFIER     ::= { mib2ext 20 }
--         iprouter             OBJECT IDENTIFIER     ::= { mib2ext 21 }
--         ipx                  OBJECT IDENTIFIER     ::= { mib2ext 22 }
--         ppp                  OBJECT IDENTIFIER     ::= { mib2ext 23 }
--         amod                 OBJECT IDENTIFIER     ::= { mib2ext 24 }
--         wbr                  OBJECT IDENTIFIER     ::= { mib2ext 25 }
--         tunnel               OBJECT IDENTIFIER     ::= { mib2ext 26 }
--         x25                  OBJECT IDENTIFIER     ::= { mib2ext 27 }
--         fr                   OBJECT IDENTIFIER     ::= { mib2ext 28 }
--         isdn                 OBJECT IDENTIFIER     ::= { mib2ext 29 }
--         hdlc                 OBJECT IDENTIFIER     ::= { mib2ext 30 }
--         lapb2                OBJECT IDENTIFIER     ::= { mib2ext 31 }
--         ipmrouter            OBJECT IDENTIFIER     ::= { mib2ext 32 }
--         rsvp                 OBJECT IDENTIFIER     ::= { mib2ext 33 }
--         ipf                  OBJECT IDENTIFIER     ::= { mib2ext 34 }
--         igmppru              OBJECT IDENTIFIER     ::= { mib2ext 35 }
--         csuhw                OBJECT IDENTIFIER     ::= { mib2ext 36 }
--         tcache               OBJECT IDENTIFIER     ::= { mib2ext 37 }

-- Hub related extension MIB's

-- Intel HW description section

         hw                     OBJECT IDENTIFIER     ::= { intel 7 }
           stack                OBJECT IDENTIFIER     ::= { hw 1 }
           chassis              OBJECT IDENTIFIER     ::= { hw 2 }

--         A chassis is an box (with no intelligence) containing modules
--         An intelligent chassis is represented as a chassis and a module

           modules              OBJECT IDENTIFIER     ::= { hw 3 }

--         A module is an intelligent module that plugs into a chassis

           mediamodules         OBJECT IDENTIFIER     ::= { hw 4 }

--         A media module is an module (with no intelligence) containing ports.
--         It plugs into a module

           ports                OBJECT IDENTIFIER     ::= { hw 5 }

-- Intel HW extension section

           stackext             OBJECT IDENTIFIER     ::= { hw 11 }
--           lcd                OBJECT IDENTIFIER     ::= { stackext 1 }
           chassisext           OBJECT IDENTIFIER     ::= { hw 12 }
--           psu                OBJECT IDENTIFIER     ::= { chassisext 1 }
           modulesext           OBJECT IDENTIFIER     ::= { hw 13 }
--           rmodext            OBJECT IDENTIFIER     ::= { modulesext 1 }
--           modconf            OBJECT IDENTIFIER     ::= { modulesext 2 }
           mediamodulesext      OBJECT IDENTIFIER     ::= { hw 14 }
           portsext             OBJECT IDENTIFIER     ::= { hw 15 }
--           pneighbor          OBJECT IDENTIFIER     ::= { portsext 1 }

-- *************************** intel.mib2ext.system ***************************

sysVendorName   OBJECT-TYPE
    SYNTAX  DisplayString (SIZE (128))
    ACCESS  read-only
    STATUS  mandatory
    DESCRIPTION
            "Must return: Intel Corporation."
    ::= { system 1 }

sysProductName   OBJECT-TYPE
    SYNTAX  DisplayString (SIZE (128))
    ACCESS  read-only
    STATUS  mandatory
    DESCRIPTION
            "Full name of device. Excludes the Sub Type information."
    ::= { system 2 }

sysProductSubType   OBJECT-TYPE
    SYNTAX  DisplayString (SIZE (128))
    ACCESS  read-only
    STATUS  mandatory
    DESCRIPTION
            "Sub Type description of device. For example, national,
             special, or test versions."
    ::= { system 3 }

sysMibVersion   OBJECT-TYPE
    SYNTAX  DisplayString (SIZE (8))
    ACCESS  read-only
    STATUS  mandatory
    DESCRIPTION
            "Version of the INTEL-GEN-MIB supported by the device's SNMP agent.
            Syntax: A.BC xxx

            A (1-9): Changes when B overflows, or when object STATUS is
                     changed to obsolete.

            B (0-9): Changed when new (major) object(s) are added to the MIB
                     (Not objects below the sysProducts section).

            C (0-9): Changed when adding a new enumeration or making minor
                     changes to an object.

            xxx:     For Intel internal use only

            Version Log:
            1.00: First version."
    ::= { system 4 }

sysTimeOfDay  OBJECT-TYPE
    SYNTAX  INTEGER
    ACCESS  read-write
    STATUS  mandatory
    DESCRIPTION
            "The device's expression of the local date and time of day.
             The time is expressed in seconds since midnight (0 hour),
             January 1, 1970.

             0 is returned if the device does not support a real-time clock."
    ::= { system 5 }

sysSystemDate  OBJECT-TYPE
    SYNTAX  OCTET STRING (SIZE (0..11)) -- 0 | 8 | 11
    ACCESS  read-write
    STATUS  optional
    DESCRIPTION
            "The device's expression of the local date, time of day,
             and time zone. The syntax is identical to the DateAndTime
             format defined in RFC-1514.

             field  octets  contents                  range
             _____  ______  ________                  _____
             1      1-2     year                      0..65536
                            (in network byte order)
             2       3      month                     1..12
             3       4      day                       1..31
             4       5      hour                      0..23
             5       6      minutes                   0..59
             6       7      seconds                   0..60
                            (use 60 for leap-second)
             7       8      deci-seconds              0..9
             8       9      direction from UTC        '+' / '-'
                            (in ASCII notation)
             9      10      hours from UTC            0..11
             10     11      minutes from UTC          0..59

             Note: If only the local time is known, then time-zone
             information (fields 8-10) is not present.

             An empty string is returned if the device does not support
             a real-time clock."
    ::= { system 6 }

sysReset OBJECT-TYPE
    SYNTAX  INTEGER {
                    resetCold(1),
                    resetWarm(2),
                    resetStackCold(3),
                    resetStackWarm(4)
                    }
    ACCESS  write-only
    STATUS  mandatory
    DESCRIPTION
            "Resets the agent/device.
             resetCold(1): Restarts as if the device was powered off then on.
             resetWarm(2): Restarts the currently active software.
             resetStackCold(3): Restarts a multi agent stack as if the stack was powered off then on.
             resetStackWarm(4): Restarts the currently active software for each devices in a multi agent stack."
    ::= { system 7 }

sysConfTable OBJECT-TYPE
    SYNTAX  SEQUENCE OF SysConfEntry
    ACCESS  not-accessible
    STATUS  mandatory
    DESCRIPTION
            "This table is used to describe the state of the device's
             configuration."
    ::= { system 8 }

    sysConfEntry OBJECT-TYPE
             SYNTAX  SysConfEntry
             ACCESS  not-accessible
             STATUS  mandatory
             DESCRIPTION
                     "Configuration information entry:
                      Index 1 is the active configuration.
                      Index 2 is the backup configuration (if it exists)."
--             INDEX   { INTEGER }
             ::= { sysConfTable 1 }

    SysConfEntry ::= SEQUENCE {
       confStatus       INTEGER,
       confName         OCTET STRING (SIZE (0..256)),
       confTime         INTEGER,
       confTftpIp       IpAddress
    }

    confStatus OBJECT-TYPE
             SYNTAX  INTEGER {
                             unknown(1),
                             default(2),
                             loaded(3),
                             changed(4),
                             saved(5)
                             }
             ACCESS  read-only
             STATUS  mandatory
             DESCRIPTION
                     "unknown(1):
                      default(2): (Index 1) default configuration.

                      loaded(3):  (Index 1) configuration loaded
                                  from a TFTP server.

                      changed(4): (Index 1) modified, but not copied
                                  to the backup.

                      saved(5):   (Index 1) active configuration
                                  and backup copies are identical.
                                  (Index 2) always returns 'saved(5)'
                                  (if it exists)."
             ::= { sysConfEntry 1 }

    confName OBJECT-TYPE
             SYNTAX  OCTET STRING (SIZE (0..256))
             ACCESS  read-only
             STATUS  mandatory
             DESCRIPTION
                     "The configuration filename (0 to 256 bytes).
                      Use this name when using TFTP to download
                      the configuration.

                      An empty string is returned if configuration
                      files are not supported for the device."
             ::= { sysConfEntry 2 }

    confTime OBJECT-TYPE
             SYNTAX  INTEGER
             ACCESS  read-only
             STATUS  mandatory
             DESCRIPTION
                     "sysTimeOfDay of the last time the configuration was
                      modified, loaded, or saved to backup."
             ::= { sysConfEntry 3 }

    confTftpIp OBJECT-TYPE
             SYNTAX  IpAddress
             ACCESS  read-only
             STATUS  mandatory
             DESCRIPTION
                     "IP address of the TFTP server from which the
                      configuration was loaded.

                      0 is returned if the configuration was not loaded
                      from a server."
             ::= { sysConfEntry 4 }

sysConfChange OBJECT-TYPE
    SYNTAX  INTEGER {
                    useDefaultConf(1),
                    useDefaultConfKeepIp(2),
                    useBackupConf(3),
                    createBackupConf(4),
                    createDefBackupConf(5),
                    useStackBackupConf(6),
                    createStackBackupConf(7),
                    stackTftpUploadLock(8),
                    stackTftpUploadUnlockActivate(9),
                    stackTftpUploadUnlockCancel(10),
                    stackTftpUploadKeepAlive(11),
                    stackUseDefaultConf(12),
                    stackUseDefaultConfKeepIp(13),
                    stackCreateDefBackupConf(14)
                    }
    ACCESS  write-only
    STATUS  mandatory
    DESCRIPTION
            "Object used to activate and backup configurations:

             useDefaultConf(1):       Load the factory default configuration
                                      as the active configuration.

             useDefaultConfKeepIp(2): Same as useDefaultConf(1), but
                                      keep the current IP address.

             useBackupConf(3):        Load the backup configuration
                                      as the active configuration.

             createBackupConf(4):     Save the active configuration as the
                                      backup configuration.

             createDefBackupConf(5):  Combine useDefaultConf(1) and
                                      createBackupConf(4) and use as the
                                      factory default.

             useStackBackupConf(6):   Load the backup configuration
                                      as the active configuration. For all
                                      modules in a stack.

             createStackBackupConf(7):Save the active configuration as the
                                      backup configuration. For all
                                      modules in a stack.

             stackTftpUploadLock(8):  Lock for TFTP upload of configuration
                                      to all modules in a stack. Used to 
                                      syncronise external backup configuration 
                                      actions. 60 sec inactivity timeout on 
                                      the lock.

             stackTftpUploadUnlockActivate(9): Unlock and activate uploaded
                                      configuration for for all modules in a 
                                      stack.

             stackTftpUploadUnlockCancel(10): Unlock and cancel uploaded
                                      configuration for for all modules in a 
                                      stack.

             stackTftpUploadKeepAlive(11): Inform device that TFTP upload
                                      still in progress and mgt station is 
                                      alive.

             stackUseDefaultConf(12): Load the factory default configuration
                                      as the active configuration for each device
                                      in a multi agent stack.

             stackUseDefaultConfKeepIp(13): Same as stackUseDefaultConf(1), but
                                      keep the current IP addresses.
                                      
             stackCreateDefBackupConf(14): Combine stackUseDefaultConf(12) and
                                      createStackBackupConf(7). Thus, restore the
                                      factory default configuration and save it as
                                      the backup configuration for all modules
                                      in the stack."
    ::= { system 9 }

sysLogTable OBJECT-TYPE
    SYNTAX  SEQUENCE OF SysLogEntry
    ACCESS  not-accessible
    STATUS  mandatory
    DESCRIPTION
            "This table is used to configure and monitor the agent's
             log files. The log files are read with TFTP."
    ::= { system 10 }

    sysLogEntry OBJECT-TYPE
             SYNTAX  SysLogEntry
             ACCESS  not-accessible
             STATUS  mandatory
             DESCRIPTION
                     "Entry with a description of a log."
             INDEX   { logType }
             ::= { sysLogTable 1 }

    SysLogEntry ::= SEQUENCE {
       logType              INTEGER,
       logEntries           INTEGER,
       logFileName          DisplayString (SIZE (128)),
       logLastChanged       TimeTicks
    }

    logType OBJECT-TYPE
             SYNTAX  INTEGER {
                             logSystem(1),
                             logError(2)
                             }
             ACCESS  read-only
             STATUS  mandatory
             DESCRIPTION
                     "The type of log:
                      logSystem(1): Log of system events.
                      logError(2):  Log of errors."
             ::= { sysLogEntry 1 }

    logEntries  OBJECT-TYPE
             SYNTAX  INTEGER
             ACCESS  read-write
             STATUS  mandatory
             DESCRIPTION
                     "The number of entries in the log. Setting the
                      value to zero will clear the log. Setting any
                      other value is invalid."
             ::= { sysLogEntry 2 }

    logFileName OBJECT-TYPE
             SYNTAX  DisplayString (SIZE (128))
             ACCESS  read-only
             STATUS  mandatory
             DESCRIPTION
                     "Filename of the log file. Use this name when
                      using TFTP to download the log."
             ::= { sysLogEntry 3 }

    logLastChanged OBJECT-TYPE
             SYNTAX  TimeTicks
             ACCESS  read-only
             STATUS  mandatory
             DESCRIPTION
                     "sysUpTime of the last change to the log."
             ::= { sysLogEntry 4 }

     sysConfRollbackTimeout OBJECT-TYPE
         SYNTAX  INTEGER
         ACCESS  read-write
         STATUS  mandatory
         DESCRIPTION
                 "This object is used to activate and deactivate the 
                  configuration rollback mechanism.
                  Set to 0 to deactivate.
                  Set to x (x > 0) to activate in x seconds."
         ::= { system 11 }

sysConfChangeLastResponse OBJECT-TYPE
    SYNTAX  INTEGER {
                    success(1),
                    noEditingRightsVlan(2),
                    noEditingRightsLocalParm(3),
                    flashOperationFailed(4),
                    flashOperationNothingToLoad(5),
                    tftpOperationFailed(6),
                    tftpOperationNoLock(7),
                    tftpOperationStackMemberMissingParmFile(8),
                    tftpOperationMissingParmFile(9),
                    tftpOperationMissingNvpFile(10),
                    tftpOperationMgtTimeout(11),
                    factoryDefaultOperationFailed(12),
                    stackMemberRejectsOperation(13),
                    intraStackCommunicationError(16),
                    internalError(17),
                    notReady(99)
                    }
    ACCESS  read-only
    STATUS  mandatory
    DESCRIPTION
             "This object is used in conjunction with the 
              sysConfChange object, to be read after setting 
              a value for sysConfChange to obtain status of that
              operation. When this object returns notReady(99) snmp
              client must poll again, until it returns a valid
              response different from notReady(99).
                    success(1):
                        Last SET request of SysConfChange object was successful. 
                        Mgt station should continue process.
                    noEditingRightsVlan(2):
                        The VLAN configuration is busy, probable causes:
                        VLAN is being edited somewhere else (editToken
                        taken) VLAN is distributing configuration among the
                        switches
                        Mgt station should check the editToken state and advice 
                        the user to wait or force a release of the token, if taken.  
                        If not taken advice user to wait until configuration is no 
                        longer busy and try again.
                    noEditingRightsLocalParm(3):
                        A switch is having the local parameters modified.
                        Mgt station should advice user to wait and try again.
                    flashOperationFailed(4):
                        A switch failed loading the configuration from Flash.
                        Mgt station should advice user to check status of the 
                        switches and possibly try again later.
                    flashOperationNothingToLoad(5):
                        The contacted switch didn't have a configuration saved in 
                        Flash + Mgt station should advice the user that this switch 
                        never had a configuration saved, and the load from Flash has 
                        been aborted.  This could occur if the contacted switch is new 
                        in the stack, and thus haven't had anything saved yet, or if the 
                        user simply never saved anything in Flash. 
                        Mgt station should advice user to save configuration in flash 
                        for entire stack always.
                    tftpOperationFailed(6):
                        The TFTP of files to the switches failed
                        Mgt station should advice user to check status of the switches 
                        and possibly try again later.
                    tftpOperationNoLock(7):
                        The stack TFTP lock has not been set by Mgt station.
                        Mgt station should advice user that someone may have tampered 
                        with the stack (reset, re-config) while the process was ongoing.  
                        (This could also be due to an error by the Mgt platform or switch)
                    tftpOperationStackMemberMissingParmFile(8):
                        One or more of the switches in the stack (other than the contacted 
                        switch) didn't receive a parameter block file yet.
                        Mgt station should advice user to check status of the stack, if new 
                        switches were added since the configuration was backed-up, 
                        or during the process, this could be the problem.
                    tftpOperationMissingParmFile(9):
                        The contacted switch didn't receive a parameter block file yet.
                        Mgt should advice user that a proper parameter block file wasn't 
                        received on the contacted switch. Data may have been corrupted.
                    tftpOperationMissingNvpFile(10):
                        The contacted switch didn't receive a network vlan policy file yet.
                        Mgt should advice user that a proper nvp file wasn't received on 
                        the contacted switch. Data may have been corrupted.
                    tftpOperationMgtTimeout(11):
                        The contacted switch didn't receive a keep-alive signal from 
                        the Mgt station for 60 seconds.
                        If Mgt is still there it should advice the user to check connection 
                        between Mgt station and switch.
                    factoryDefaultOperationFailed(12):
                        A switch failed loading the configuration from default parameters.
                        Mgt station should advice user to check status of the switches and 
                        possibly try again later.
                    stackMemberRejectsOperation(13):
                        A switch (other than the contacted) couldn't initiate the desired 
                        operation.
                        Mgt should advice the user to check the stack status. If switches 
                        were added or removed during the operation this may have caused 
                        the problem.
                    intraStackCommunicationError(16):
                        Communication between the stack members failed.
                        Mgt should advice user to check cable connections and status of 
                        the switches, and possibly try operation again.
                    internalError(17):
                        This should never occur, and would indicate that a switch is in 
                        a fatal state of error.
                        Mgt should advice the user to report the problem to support.                        
                    notReady(99):"
   ::= { system 12 }

sysLocalMangementTimeout OBJECT-TYPE
    SYNTAX  INTEGER
    ACCESS  read-write
    STATUS  mandatory
    DESCRIPTION
            "The users conection to the local management system will be terminated by the 
             device if it is idle for more than this timeout value. Time is in minutes. 
             0 indicates no termination will occour."
    ::= { system 13 }

-- ***************** intel.mib2ext.ip *****************

ipConfTable OBJECT-TYPE
    SYNTAX  SEQUENCE OF IpConfEntry
    ACCESS  not-accessible
    STATUS  mandatory
    DESCRIPTION
            "IP configuration table:
             The first table entry (index 1) shows the current values.
             The second entry (index 2) contains the values you wish to set.
             To activate the second entry, set ipConf2Activate = active(1)."
    ::= { ip 1 }

    ipConfEntry OBJECT-TYPE
             SYNTAX  IpConfEntry
             ACCESS  not-accessible
             STATUS  mandatory
             DESCRIPTION
                     "This table is used to view and modify the agent's
                      IP configuration:
                      Index 1 is the currently active configuration
                              (read only).
                      Index 2 is the new configuration, which is activated
                              by setting ipConf2Activate = active(1)."
--             INDEX   { INTEGER }
             ::= { ipConfTable 1 }

    IpConfEntry ::= SEQUENCE {
       ipAddressAssignment  INTEGER,
       ipAddress            IpAddress,
       ipSubNetMask         IpAddress,
       ipRouterAddress      IpAddress,
       ipBroadcastAddress   IpAddress,
       ipBootpServerAddress IpAddress
    }

    ipAddressAssignment   OBJECT-TYPE
             SYNTAX  INTEGER {
                             fixed(1),
                             bootp(2)
                             }
             ACCESS  read-write
             STATUS  mandatory
             DESCRIPTION
                     "Determines how the management agent gets its IP
                      configuration:

                      fixed(1): Get configuration from ipAddress,
                                ipSubNetMask, ... in this table.

                      bootp(2): Get configuration from a BOOTP server
                                (ipBootpServerAddress)."
             ::= { ipConfEntry    1 }

    ipAddress   OBJECT-TYPE
             SYNTAX  IpAddress
             ACCESS  read-write
             STATUS  mandatory
             DESCRIPTION
                     "IP address for the device and agent."
             ::= { ipConfEntry    2 }

    ipSubNetMask   OBJECT-TYPE
             SYNTAX  IpAddress
             ACCESS  read-write
             STATUS  mandatory
             DESCRIPTION
                     "Network (subnet) mask for the device and agent."
             ::= { ipConfEntry    3 }

    ipRouterAddress   OBJECT-TYPE
             SYNTAX  IpAddress
             ACCESS  read-write
             STATUS  mandatory
             DESCRIPTION
                     "Gateway (router) address for the device and agent."
             ::= { ipConfEntry    4 }

    ipBroadcastAddress   OBJECT-TYPE
             SYNTAX  IpAddress
             ACCESS  read-write
             STATUS  mandatory
             DESCRIPTION
                     "Broadcast address for the device and agent."
             ::= { ipConfEntry    5 }

    ipBootpServerAddress   OBJECT-TYPE
             SYNTAX  IpAddress
             ACCESS  read-write
             STATUS  mandatory
             DESCRIPTION
                     "If ipAddressAssignment = bootp(2), then this
                      is the IP address of the BOOTP/DHCP server used
                      to get the current address.

                      If 0.0.0.0, then BOOTP/DHCP requests are multicasted."
             ::= { ipConfEntry    6 }

ipConf2Activate OBJECT-TYPE
    SYNTAX  INTEGER {
                    active(1)
                    }
    ACCESS  write-only
    STATUS  mandatory
    DESCRIPTION
            "Activates the second IP configuration set.
             Warning! This may reset the device in some implementations."
    ::= { ip 2 }

ipModuleConfTable OBJECT-TYPE
    SYNTAX  SEQUENCE OF IpModuleConfEntry
         ACCESS  not-accessible
    STATUS  optional
    DESCRIPTION
            "IP module configuration table:
			 This is a version of the ipConfTable indexed by Chassis, Module"
    ::= { ip 3}

    ipModuleConfEntry OBJECT-TYPE
             SYNTAX  IpModuleConfEntry
             ACCESS  not-accessible
             STATUS  mandatory
             DESCRIPTION
                     "This table is used to view and modify the module agent's
                      IP configuration:"
             INDEX   { ipModuleChassisIndex, ipModuleModuleIndex, ipModuleConfigIndex }
             ::= { ipModuleConfTable 1 }

    IpModuleConfEntry ::= SEQUENCE {
       ipModuleChassisIndex       INTEGER,
       ipModuleModuleIndex        INTEGER,
       ipModuleConfigIndex        INTEGER,
       ipModuleAddressAssignment  INTEGER,
       ipModuleAddress            IpAddress,
       ipModuleSubNetMask         IpAddress,
       ipModuleRouterAddress      IpAddress,
       ipModuleBroadcastAddress   IpAddress,
       ipModuleBootpServerAddress IpAddress
    }

	ipModuleChassisIndex   OBJECT-TYPE
        SYNTAX  INTEGER
        ACCESS  read-only
        STATUS  mandatory
        DESCRIPTION
                "Chassis number in stack that contains the module."
        ::= { ipModuleConfEntry    1 }

	ipModuleModuleIndex   OBJECT-TYPE
        SYNTAX  INTEGER
	    ACCESS  read-only
        STATUS  mandatory
        DESCRIPTION
                "Module number in the chassis."
        ::= { ipModuleConfEntry    2 }

	ipModuleConfigIndex   OBJECT-TYPE
        SYNTAX  INTEGER
	    ACCESS  read-only
        STATUS  mandatory
        DESCRIPTION
                "Configuration number in the module.
                 Index 1 is the currently active configuration
                         (read only).
                 Index 2 is the new configuration, which is activated
                         by setting ipConf2Activate = active(1)."
        ::= { ipModuleConfEntry    3 }


    ipModuleAddressAssignment   OBJECT-TYPE
             SYNTAX  INTEGER {
                             fixed(1),
                             bootp(2)
                             }
             ACCESS  read-write
             STATUS  mandatory
             DESCRIPTION
                     "Determines how the management agent gets its IP
                      configuration:

                      fixed(1): Get configuration from ipModuleAddress,
                                ipModuleSubNetMask, ... in this table.

                      bootp(2): Get configuration from a BOOTP server
                                (ipModuleBootpServerAddress)."
             ::= { ipModuleConfEntry    4 }

    ipModuleAddress   OBJECT-TYPE
             SYNTAX  IpAddress
             ACCESS  read-write
             STATUS  mandatory
             DESCRIPTION
                     "IP address for the module."
             ::= { ipModuleConfEntry    5 }

    ipModuleSubNetMask   OBJECT-TYPE
             SYNTAX  IpAddress
             ACCESS  read-write
             STATUS  mandatory
             DESCRIPTION
                     "Network (subnet) mask for the module."
             ::= { ipModuleConfEntry    6 }

    ipModuleRouterAddress   OBJECT-TYPE
             SYNTAX  IpAddress
             ACCESS  read-write
             STATUS  mandatory
             DESCRIPTION
                     "Gateway (router) address for the module."
             ::= { ipModuleConfEntry    7 }

    ipModuleBroadcastAddress   OBJECT-TYPE
             SYNTAX  IpAddress
             ACCESS  read-write
             STATUS  mandatory
             DESCRIPTION
                     "Broadcast address for the module."
             ::= { ipModuleConfEntry    8 }

    ipModuleBootpServerAddress   OBJECT-TYPE
             SYNTAX  IpAddress
             ACCESS  read-write
             STATUS  mandatory
             DESCRIPTION
                     "If ipModuleAddressAssignment = bootp(2), then this
                      is the IP address of the BOOTP/DHCP server used
                      to get the current address.

                      If 0.0.0.0, then BOOTP/DHCP requests are multicasted."
             ::= { ipModuleConfEntry    9 }

ipModuleConf2Activate OBJECT-TYPE
    SYNTAX  INTEGER {
                    active(1)
                    }
    ACCESS  write-only
    STATUS  optional
    DESCRIPTION
            "Activates the second IP configuration set for all modules.
             Warning! This may reset one or more of the chassis or modules in some implementations."
    ::= { ip 4 }

ipModuleConf2Confirm OBJECT-TYPE
    SYNTAX  INTEGER {
                    confirm(1)
                    }
    ACCESS  write-only
    STATUS  optional
    DESCRIPTION
            "If not set to confirm(1) within a short period of time (60 sec) after ipModuleConf2Activate 
             is set to active(1), then all modules should revert to their original ip configuration."
    ::= { ip 5 }

-- *************************** intel.mib2ext.snmp ***************************

snmpAuthMaxEntries OBJECT-TYPE
    SYNTAX INTEGER
    ACCESS  read-only
    STATUS  mandatory
    DESCRIPTION
            "Maximum number of entries in the access authentication
             table (snmpAuthTable)."
    ::= { snmp 1 }

snmpAuthTableLastChange  OBJECT-TYPE
    SYNTAX  TimeTicks
    ACCESS  read-only
    STATUS  mandatory
    DESCRIPTION
            "sysUpTime of last change to snmpAuthTable."
    ::= { snmp 2 }

snmpAuthTable OBJECT-TYPE
    SYNTAX  SEQUENCE OF SnmpAuthEntry
    ACCESS  not-accessible
    STATUS  mandatory
    DESCRIPTION
            "Management access authentication table. "
    ::= { snmp 3 }

    snmpAuthEntry OBJECT-TYPE
             SYNTAX  SnmpAuthEntry
             ACCESS  not-accessible
             STATUS  mandatory
             DESCRIPTION
                     "Authentication entry."
             INDEX   { authNumber }
             ::= { snmpAuthTable 1 }

    SnmpAuthEntry ::= SEQUENCE {
       authNumber                    INTEGER,
       authProtocolAccessIpCommunity OCTET STRING (SIZE (10..41)),
       authDelete                    INTEGER
    }

    authNumber OBJECT-TYPE
             SYNTAX  INTEGER
             ACCESS  read-only
             STATUS  mandatory
             DESCRIPTION
                     "A number that uniquely identifies an authentication
                      entry."
             ::= { snmpAuthEntry 1 }

    authProtocolAccessIpCommunity OBJECT-TYPE
             SYNTAX  OCTET STRING (SIZE (10..41))
             ACCESS  read-write
             STATUS  mandatory
             DESCRIPTION
                     "This object contains the Protocol (1 byte), Access
                      (1 byte), IP address (4 byte), IP subnet mask (4 byte),
                      and Community (0 to 31 byte). Not all protocols are
                      supported by all devices.

                      Protocol:
                       snmp(1),
                       telnet(2),
                       http(3),
                       tftp(4),
                       ftp(5)

                      Access:                         Protocols:
                       noAccess(1),                    All
                       readOnly(2),                    All
                       writeOnly(3),                   Not snmp(1) or telnet(2)
                       readWrite(4),                   All
                       readOnlySecureSNMPObjects(5),   snmp(1)
                       readWriteSecureSNMPObjects(6)   snmp(1)

                      If the IP address is zero, then any IP address is
                      allowed. If the IP subnet mask is not 255.255.255.255,
                      then any IP address is an IP network address.

                      IP network addresses can't overlap for a given protocol.
                      If an IP address and an IP network address overlap for a
                      given protocol, then the access field of the IP address
                      is used. The community string is only used for SNMP
                      access. If the community string is zero length, then any
                      value of community is allowed."
             ::= { snmpAuthEntry 2 }

    authDelete OBJECT-TYPE
             SYNTAX  INTEGER {
                               delete(1)
                             }
             ACCESS  write-only
             STATUS  mandatory
             DESCRIPTION
                     "The snmpAuthEntry is removed when set to delete(1)."
             ::= { snmpAuthEntry 3 }

snmpTrapMaxEntries OBJECT-TYPE
    SYNTAX INTEGER
    ACCESS  read-only
    STATUS  mandatory
    DESCRIPTION
            "Maximum number of entries in the trapTable."
    ::= { snmp 4 }

snmpTrapTable OBJECT-TYPE
    SYNTAX  SEQUENCE OF SnmpTrapEntry
    ACCESS  not-accessible
    STATUS  mandatory
    DESCRIPTION
            "Host Trap list."
    ::= { snmp 5 }

    snmpTrapEntry OBJECT-TYPE
             SYNTAX  SnmpTrapEntry
             ACCESS  not-accessible
             STATUS  mandatory
             DESCRIPTION
                     "Host Trap entry."
             INDEX   { trapNumber }
             ::= { snmpTrapTable 1 }

    SnmpTrapEntry ::= SEQUENCE {
       trapNumber                  INTEGER,
       trapIpAndGroupAndCommunity  OCTET STRING (SIZE (8..39)),
       trapDelete                  INTEGER
    }

    trapNumber OBJECT-TYPE
             SYNTAX  INTEGER
             ACCESS  read-only
             STATUS  mandatory
             DESCRIPTION
                     "A number that uniquely identifies a trap entry."
             ::= { snmpTrapEntry 1 }

    trapIpAndGroupAndCommunity OBJECT-TYPE
             SYNTAX  OCTET STRING (SIZE (8..39))
             ACCESS  read-write
             STATUS  mandatory
             DESCRIPTION
                     "This object contains the IP address (4 byte), the
                      trap groups (32 bit = 4 byte), and the community
                      (0 to 31 byte) used in the trap. The trap groups
                      section is stored as a 32-bit little-endian value.

                      Groups:
                      bit 1: all traps
                      bit 2: configuration related traps
                      bit 3: hardware state related traps
                      bit 4: diagnostics related traps"

             ::= { snmpTrapEntry 2 }

    trapDelete OBJECT-TYPE
             SYNTAX  INTEGER {
                             delete(1)
                             }
             ACCESS  write-only
             STATUS  mandatory
             DESCRIPTION
                     "The trapEntry is removed when set to delete(1)."
             ::= { snmpTrapEntry 3 }

snmpAccessTable OBJECT-TYPE
    SYNTAX  SEQUENCE OF SnmpAccessEntry
    ACCESS  not-accessible
    STATUS  mandatory
    DESCRIPTION
            "Management access list. This is a list of all IP
             addresses that have passed the authentication table."
    ::= { snmp 6 }

    snmpAccessEntry OBJECT-TYPE
        SYNTAX  SnmpAccessEntry
        ACCESS  not-accessible
        STATUS  mandatory
        DESCRIPTION
                "Management access entry."
        --INDEX   { INTEGER }
        ::= { snmpAccessTable 1 }

    SnmpAccessEntry ::= SEQUENCE {
        snmpAccessIP       IpAddress,
        snmpAccessTime     INTEGER,
        snmpAccessProtocol INTEGER,
        snmpAccessType     INTEGER
    }

    snmpAccessIP OBJECT-TYPE
        SYNTAX  IpAddress
        ACCESS  read-only
        STATUS  mandatory
        DESCRIPTION
                "IP addresses of devices that have successfully cleared
                 the authentication table."
        ::= { snmpAccessEntry 1 }

    snmpAccessTime OBJECT-TYPE
        SYNTAX  INTEGER
        ACCESS  read-only
        STATUS  mandatory
        DESCRIPTION
                "sysTimeOfDay of the last successful access from this IP address."
             ::= { snmpAccessEntry 2 }

    snmpAccessProtocol OBJECT-TYPE
        SYNTAX  INTEGER {
                        snmp(1),
                        telnet(2),
                        http(3),
                        tftp(4),
                        ftp(5)
                        }
        ACCESS  read-only
        STATUS  mandatory
        DESCRIPTION
                "Protocol used for successful access from this IP address."
             ::= { snmpAccessEntry 3 }

    snmpAccessType OBJECT-TYPE
        SYNTAX  INTEGER {
                        noAccess(1),
                        readOnly(2),
                        writeOnly(3),
                        readWrite(4),
                        readOnlySecureSNMPObjects(5),
                        readWriteSecureSNMPObjects(6)
                        }
        ACCESS  read-only
        STATUS  mandatory
        DESCRIPTION
                "Types of successful access from this IP address.
                 Access:                         Protocols:
                   noAccess(1),                    All
                   readOnly(2),                    All
                   writeOnly(3),                   All except for snmp(1) and telnet(2)
                   readWrite(4),                   All
                   readOnlySecureSNMPObjects(5),   snmp(1) only
                   readWriteSecureSNMPObjects(6)   snmp(1) only"
             ::= { snmpAccessEntry 4 }

-- *************************** intel.hw.stack ***************************

stackClass OBJECT-TYPE
    SYNTAX INTEGER {
                   standalone(1),
                   chassis(2),
                   multiagentstack(3),
                   singleagentstack(4)
                   }
    ACCESS  read-only
    STATUS  mandatory
    DESCRIPTION
            "This object identifies which type of stack the
             device is a part of:

             standalone(1):       Not a stack. (stackMaxChassis=1,
                                  chassisMaxModules=1).

             chassis(2):          Not a stack. (stackMaxChassis=1,
                                  chassisMaxModules>1).

             multiagentstack(3):  Stack of chassis' with their
                                  own management agents.

             singleagentstack(4): Stack of chassis' with a single
                                  management agent."

-- Express Routers return standalone(1),
-- A single or two back-to-back connected Express Switch 500s return
-- standalone(1)
-- Express Switch 10 or 10+ return chassis(2)
-- Express Switch 500s connected to a Stacking Module return multiagentstack(3)
-- Hubs with a management module return singleagentstack(4)

    ::= { stack 1 }

stackMaxChassis OBJECT-TYPE
    SYNTAX INTEGER
    ACCESS  read-only
    STATUS  mandatory
    DESCRIPTION
            "The maximum number of chassis' in a stack.
             Returns one (1) if stackClass = standalone(1) or chassis(2)."
    ::= { stack 2 }

stackChassis OBJECT-TYPE
    SYNTAX INTEGER
    ACCESS  read-only
    STATUS  mandatory
    DESCRIPTION
            "The actual number of chassis' in a stack.
             Returns one (1) if stackClass = standalone(1) or chassis(2)."
    ::= { stack 3 }

stackAgentChassis OBJECT-TYPE
    SYNTAX INTEGER
    ACCESS  read-only
    STATUS  mandatory
    DESCRIPTION
            "Which chassis in a stack contains the agent.
             Possible values are 1..stackMaxChassis.
             Returns one (1) if stackClass = standalone(1) or chassis(2)."
    ::= { stack 4 }

stackAgentModule   OBJECT-TYPE
    SYNTAX  INTEGER
    ACCESS  read-only
    STATUS  mandatory
    DESCRIPTION
            "Which module in the chassis selected by stackAgentChassis
             contains the agent.
             Possible values are 1..chassisMaxModules for the selected
             chassis.
             Returns one (1) if stackClass = standalone(1)."
    ::= { stack 5 }

stackUserAssignedName   OBJECT-TYPE
    SYNTAX  DisplayString (SIZE (0..24))
    ACCESS  read-write
    STATUS  mandatory
    DESCRIPTION
            "User-definable information about the stack."
    ::= { stack 6 }

stackID   OBJECT-TYPE
    SYNTAX  OCTET STRING (SIZE (0..31))
    ACCESS  read-write
    STATUS  optional
    DESCRIPTION
            "Unique identifier used to identify which stack a device last belonged to.
			 Automatically genarated when a new stack is created. Based on MAC addresses."
    ::= { stack 7 }

stackTopology   OBJECT-TYPE
    SYNTAX  INTEGER {
                    chain(1),
                    star(2),
                    tree(3)
                    }
    ACCESS  read-only
    STATUS  optional
    DESCRIPTION
            "Stack topology type"
    ::= { stack 8 }

stackMultiAgentDefultChassisModule OBJECT-TYPE
    SYNTAX OCTET STRING (SIZE (8))
    ACCESS  read-write
    STATUS  mandatory
    DESCRIPTION
            "This object contains the Chassis and Module numbers to be used
             when using a non indexed MIB on a multi agent stack.
             Chassis index (4 byte (big-endian)), Module index (4 byte (big-endian))"
   ::= { stack 9 }

-- *************************** intel.hw.chassis ***************************

chassisTable   OBJECT-TYPE
    SYNTAX  SEQUENCE OF ChassisEntry
    ACCESS  not-accessible
    STATUS  mandatory
    DESCRIPTION
            "Possible values of indices are
             1..stackChassis"
    ::= { chassis    1 }

chassisEntry   OBJECT-TYPE
    SYNTAX  ChassisEntry
    ACCESS  not-accessible
    STATUS  mandatory
    DESCRIPTION
            "Possible values of indices are
             1..stackChassis"
    INDEX   {  chassisIndex }
    ::= { chassisTable  1 }

ChassisEntry ::=
    SEQUENCE {
            chassisIndex                    INTEGER,
            chassisType                     INTEGER,
            chassisMaxModules               INTEGER,
            chassisModules                  INTEGER,
            chassisUserAssignedType         DisplayString (SIZE (0..24)),
            chassisUserAssignedNumber       DisplayString (SIZE (0..24)),
            chassisUserAssignedName         DisplayString (SIZE (0..24)),
            chassisMaxPSUs                  INTEGER
    }

chassisIndex   OBJECT-TYPE
    SYNTAX  INTEGER
    ACCESS  read-only
    STATUS  mandatory
    DESCRIPTION
            "Chassis number in the stack."
    ::= { chassisEntry    1 }

chassisType OBJECT-TYPE
    SYNTAX  INTEGER {
                    unavailable(1),
                    campus8tx(2),
                    campus8fx(3),
                    desktop24tx(4),
                    stackable12tx(5),
                    stackable24tx(6),
                    stackable16tx(7),
                    desktop16tx(8)
                    }
    ACCESS  read-only
    STATUS  mandatory
    DESCRIPTION
            "Hardware identification for the chassis."
    ::= { chassisEntry 2 }

chassisMaxModules OBJECT-TYPE
    SYNTAX  INTEGER
    ACCESS  read-only
    STATUS  mandatory
    DESCRIPTION
            "The maximum number of modules in this chassis.
             Returns one (1) if stackClass = standalone(1)."
    ::= { chassisEntry 3 }

chassisModules OBJECT-TYPE
    SYNTAX INTEGER
    ACCESS  read-only
    STATUS  mandatory
    DESCRIPTION
            "The actual number of modules in this chassis.
             Possible values are 1..chassisMaxModules.
             Returns one (1) if stackClass = standalone(1)."
    ::= { chassisEntry 4 }

chassisUserAssignedType   OBJECT-TYPE
    SYNTAX  DisplayString (SIZE (0..24))
    ACCESS  read-write
    STATUS  mandatory
    DESCRIPTION
            "User-definable information about the chassis."
    ::= { chassisEntry 5 }

chassisUserAssignedNumber   OBJECT-TYPE
    SYNTAX  DisplayString (SIZE (0..24))
    ACCESS  read-write
    STATUS  mandatory
    DESCRIPTION
            "User-definable information about the chassis."
    ::= { chassisEntry 6 }

chassisUserAssignedName   OBJECT-TYPE
    SYNTAX  DisplayString (SIZE (0..24))
    ACCESS  read-write
    STATUS  mandatory
    DESCRIPTION
            "User-definable information about the chassis."
    ::= { chassisEntry 7 }

chassisMaxPSUs OBJECT-TYPE
    SYNTAX  INTEGER
    ACCESS  read-only
    STATUS  mandatory
    DESCRIPTION
            "The maximum number of power supply units in this chassis.
             Detailed information about the power supply units is located 
             in the psuTable (a chassis extension MIB)."
    ::= { chassisEntry 8 }

-- *************************** intel.hw.module ***************************

moduleTable   OBJECT-TYPE
    SYNTAX  SEQUENCE OF ModuleEntry
    ACCESS  not-accessible
    STATUS  mandatory
    DESCRIPTION
            "Possible values of indices are
             1..stackMaxChassis and 1..chassisMaxModules"
    ::= { modules    1 }

moduleEntry   OBJECT-TYPE
    SYNTAX  ModuleEntry
    ACCESS  not-accessible
    STATUS  mandatory
    DESCRIPTION
            "Possible values of indices are
             1..stackMaxChassis and 1..chassisMaxModules"
    INDEX   {  moduleChassisIndex, moduleIndex }
    ::= { moduleTable  1 }

ModuleEntry ::=
    SEQUENCE {
            moduleChassisIndex              INTEGER,
            moduleIndex                     INTEGER,
            moduleType                      INTEGER,
            moduleFirstPort                 INTEGER,
            moduleNumberOfPorts             INTEGER,
            moduleMaxMediaModules           INTEGER,
            moduleUserAssignedType          DisplayString (SIZE (0..24)),
            moduleUserAssignedNumber        DisplayString (SIZE (0..24)),
            moduleUserAssignedName          DisplayString (SIZE (0..24)),
            moduleRAM                       INTEGER,
            moduleEPROM                     INTEGER,
            moduleFLASHPROM                 INTEGER,
            moduleLEDInfo                   OCTET STRING (SIZE (2..32)),
            moduleAllPortType               OCTET STRING,
            moduleAllPortLEDInfo            OCTET STRING,
            moduleAllPortStatus             OCTET STRING,
            moduleLastPortChange            TimeTicks,
            moduleMacAddress                OCTET STRING (SIZE (6)),
            moduleIpAddress                 IpAddress,
            moduleSerialNumber              DisplayString (SIZE (0..32)),
            moduleVersion                   INTEGER,
            moduleSwStatus                  INTEGER,
            moduleSwName                    OCTET STRING,
            moduleSwDescription             DisplayString,
            moduleSwLoadTime                INTEGER,
            moduleSwTftpIp                  IpAddress,
            moduleBackupSwStatus            INTEGER,
            moduleBackupSwName              OCTET STRING,
            moduleBackupSwDescription       DisplayString,
            moduleBackupSwLoadTime          INTEGER,
            moduleBackupSwTftpIp            IpAddress,
            moduleSwTftpIpAndSwName         OCTET STRING (SIZE (4..260)),
            moduleSwUpdateResult            INTEGER,
            moduleSpecificObject            OCTET STRING (SIZE (0..256)),
            moduleTemperatureStatus         INTEGER,
            moduleBootSectionVersion        INTEGER
            }

moduleChassisIndex   OBJECT-TYPE
        SYNTAX  INTEGER
        ACCESS  read-only
        STATUS  mandatory
        DESCRIPTION
                "Chassis number in stack that contains the module."
        ::= { moduleEntry    1 }

moduleIndex   OBJECT-TYPE
    SYNTAX  INTEGER
    ACCESS  read-only
    STATUS  mandatory
    DESCRIPTION
            "Module number in the chassis."
    ::= { moduleEntry    2 }

moduleType OBJECT-TYPE
    SYNTAX  INTEGER {
                    unavailable(1),
                    express550t(2),
                    express550f(3),
                    express510t(4),
                    express8100st(5),
                    express8100u(6),
                    express8100x(7),
                    express8100fr(8),
                    express110p12(20),
                    express110p24(21),
                    express110management(22),
                    express110bridge(23),
                    express110managementWithRMON(24),
                    express210p12(25),
                    express210p24(26),
                    express220p12(27),
                    express220p24(28),
                    express330p16(29),
                    express330p24(30),
                    express300management(31),
                    express300txuplink(32),
                    express300fxuplink(33),
                    express460tp16(34),
                    express460tp24(35),
                    nstructure560t(36),
                    nstructure560tr(38),
                    nstructure560fr(39)
                    }
    ACCESS  read-only
    STATUS  mandatory
    DESCRIPTION
            "Hardware identification for the module."
    ::= { moduleEntry 3 }

moduleFirstPort OBJECT-TYPE
    SYNTAX  INTEGER
    ACCESS  read-only
    STATUS  mandatory
    DESCRIPTION
            "The portIndex of the first port on the module."
    ::= { moduleEntry 4 }

moduleNumberOfPorts   OBJECT-TYPE
    SYNTAX  INTEGER
    ACCESS  read-only
    STATUS  mandatory
    DESCRIPTION
            "Number of ports on the module."
    ::= { moduleEntry    5 }

moduleMaxMediaModules   OBJECT-TYPE
    SYNTAX  INTEGER
    ACCESS  read-only
    STATUS  mandatory
    DESCRIPTION
            "Maximum number of media modules on the module.
             Returns 0 if none."
    ::= { moduleEntry    6 }

moduleUserAssignedType   OBJECT-TYPE
    SYNTAX  DisplayString (SIZE (0..24))
    ACCESS  read-write
    STATUS  mandatory
    DESCRIPTION
            "User-definable information about the module."
    ::= { moduleEntry 7 }

moduleUserAssignedNumber   OBJECT-TYPE
    SYNTAX  DisplayString (SIZE (0..24))
    ACCESS  read-write
    STATUS  mandatory
    DESCRIPTION
            "User-definable information about the module."
    ::= { moduleEntry 8 }

moduleUserAssignedName   OBJECT-TYPE
    SYNTAX  DisplayString (SIZE (0..24))
    ACCESS  read-write
    STATUS  mandatory
    DESCRIPTION
            "User-definable information about the module."
    ::= { moduleEntry 9 }

moduleRAM   OBJECT-TYPE
    SYNTAX  INTEGER
    ACCESS  read-only
    STATUS  mandatory
    DESCRIPTION
            "Displays the module's RAM size in bytes."
    ::= { moduleEntry    10 }

moduleEPROM   OBJECT-TYPE
    SYNTAX  INTEGER
    ACCESS  read-only
    STATUS  mandatory
    DESCRIPTION
            "Displays the module's EPROM size in bytes."
    ::= { moduleEntry    11 }

moduleFLASHPROM   OBJECT-TYPE
    SYNTAX  INTEGER
    ACCESS  read-only
    STATUS  mandatory
    DESCRIPTION
            "Displays the module's Flash Memory size in bytes."
    ::= { moduleEntry    12 }


moduleLEDInfo   OBJECT-TYPE
    SYNTAX  OCTET STRING (SIZE (2..32))
    ACCESS  read-only
    STATUS  mandatory
    DESCRIPTION
            "State of all non-port LEDs on the module.

             There is one byte per LED:
               Byte 1 is the Power LED.
               Byte 2 is the Status LED.
             The rest are module specific.

             The most significant bit is used for blink/solid:
                Off = The LED is lit permanently.
                On = The LED blinks.

             The three least significant bits are used for color:
                1 = not lit
                2 = green
                3 = yellow
                4 = blue
                5 = red
                0+6+7 not used

             The four remaining bits are currently unused and must be 0."
    ::= { moduleEntry  13 }

moduleAllPortType    OBJECT-TYPE
    SYNTAX  OCTET STRING
    ACCESS  read-only
    STATUS  mandatory
    DESCRIPTION
            "Type of all ports in the module. One byte per port. The values
             are coded like portType."
    ::= { moduleEntry  14  }

moduleAllPortLEDInfo   OBJECT-TYPE
    SYNTAX  OCTET STRING
    ACCESS  read-only
    STATUS  mandatory
    DESCRIPTION
            "The current state of all port LEDs on the module.
             X bytes per port on the module, where X = the normal
             number of LEDs per port on this module.

             There is one byte per LED.

             The most significant bit is used for blink/solid:
                Off = The LED is lit permanently.
                On = The LED blinks.

             The three least significant bits are used for color:
                1 = not lit,
                2 = green,
                3 = yellow,
                4 = blue,
                5 = red,
                0+6+7 not used

             The four remaining bits are currently unused and must be 0."
    ::= { moduleEntry  15  }

moduleAllPortStatus   OBJECT-TYPE
    SYNTAX  OCTET STRING
    ACCESS  read-only
    STATUS  mandatory
    DESCRIPTION
            "The current operational state for all ports on this module.
             This is an array of bit arrays which represents the state
             of the port.

             bit 0: disabled due to configuration
             bit 1: hardware error
             bit 2: no linkpulse
             bit 3: disabled by manager
             bit 4: disabled by access control
             bit 5: disabled by redundancy"
    ::= { moduleEntry  16 }

moduleLastPortChange OBJECT-TYPE
    SYNTAX  TimeTicks
    ACCESS  read-only
    STATUS  mandatory
    DESCRIPTION
            "sysUpTime of last change to any of the AllPort values above."
    ::= { moduleEntry  17 }

moduleMacAddress OBJECT-TYPE
        SYNTAX  OCTET STRING (SIZE (6))
        ACCESS  read-only
        STATUS  mandatory
        DESCRIPTION
                "The base MAC address allocated for MAC interfaces
                 on this module.
                 Returns 00,00,00,00,00,00 if not used."
    ::= { moduleEntry 18 }

moduleIpAddress   OBJECT-TYPE
    SYNTAX  IpAddress
    ACCESS  read-only
    STATUS  mandatory
    DESCRIPTION
            "The IP address of the agent located in this module.
             Returns 0.0.0.0 if no agent is located in this module"
    ::= { moduleEntry 19 }

moduleSerialNumber OBJECT-TYPE
    SYNTAX  DisplayString (SIZE (0..32))
    ACCESS  read-only
    STATUS  mandatory
    DESCRIPTION
            "Module serial number."
    ::= { moduleEntry 20 }

moduleVersion OBJECT-TYPE
    SYNTAX  INTEGER
    ACCESS  read-only
    STATUS  mandatory
    DESCRIPTION
            "The hardware version number for this module.
             First version is 0, second is 1, and so on."
    ::= { moduleEntry 21 }

moduleSwStatus OBJECT-TYPE
    SYNTAX  INTEGER {
                    notsupported(1),
                    nosoftware(2),
                    unavailable(3),
                    approved(4),
                    experimental(5)
                    }
    ACCESS  read-write
    STATUS  mandatory
    DESCRIPTION
            "The state of the active software on the module.
             This is for single software devices.

             notsupported(1): This module does not support software.

             nosoftware(2):   This module does not currently have software.

             unavailable(3):  This module is currently not able get the
                              software status.

             approved(4):     This software is used after power off
                              or a resetCold(1).

             experimental(5): Software must be approved to be used
                              after any type of reset.

             The only permitted set operation is to change the status
             from experimental(5) to approved(4) or to change the status
             from approved(4) to nosoftware(2); this requires 
             moduleBackupSwStatus == approved(4)."
    ::= { moduleEntry 22 }

moduleSwName OBJECT-TYPE
    SYNTAX  OCTET STRING (SIZE (0..256))
    ACCESS  read-only
    STATUS  mandatory
    DESCRIPTION
            "The active software's filename (0 to 256 bytes)."
    ::= { moduleEntry 23 }

moduleSwDescription OBJECT-TYPE
    SYNTAX  DisplayString
    ACCESS  read-only
    STATUS  mandatory
    DESCRIPTION
            "Description of the active software."
    ::= { moduleEntry 24 }

moduleSwLoadTime OBJECT-TYPE
    SYNTAX  INTEGER
    ACCESS  read-only
    STATUS  mandatory
    DESCRIPTION
            "sysTimeOfDay of last time the active software was loaded
             from a TFTP server or flash memory."
    ::= { moduleEntry 25 }

moduleSwTftpIp OBJECT-TYPE
    SYNTAX  IpAddress
    ACCESS  read-only
    STATUS  mandatory
    DESCRIPTION
            "IP address of the TFTP server from which the active
             software was loaded. Returns 0.0.0.0 for factory-loaded
             software or software loaded by a non IP-based connection
             to the device (for example, a serial cable connection)."
    ::= { moduleEntry 26 }

moduleBackupSwStatus OBJECT-TYPE
    SYNTAX  INTEGER {
                    notsupported(1),
                    nosoftware(2),
                    unavailable(3),
                    approved(4),
                    experimental(5)
                    }
    ACCESS  read-only
    STATUS  mandatory
    DESCRIPTION
            "The state of the module's backup software:

             notsupported(1): This module does not support a backup software.

             nosoftware(2):   This module does not currently have backup
                              software.

             unavailable(3):  This module is not currently able to get the
                              backup software status.

             approved(4):     Software is used after a resetWarm(2) 
                              unless moduleSwStatus == approved(4).

             experimental(5): Never returned.

             The only permitted set operation is to change the status
             from approved(4) to nosoftware(2); this requires 
             moduleSwStatus == approved(4)."
    ::= { moduleEntry 27 }

moduleBackupSwName OBJECT-TYPE
    SYNTAX  OCTET STRING (SIZE (0..256))
    ACCESS  read-only
    STATUS  mandatory
    DESCRIPTION
            "The backup software's filename (0 to 256 bytes)."
    ::= { moduleEntry 28 }

moduleBackupSwDescription OBJECT-TYPE
    SYNTAX  DisplayString
    ACCESS  read-only
    STATUS  mandatory
    DESCRIPTION
            "Description of the backup software."
    ::= { moduleEntry 29 }

moduleBackupSwLoadTime OBJECT-TYPE
    SYNTAX  INTEGER
    ACCESS  read-only
    STATUS  mandatory
    DESCRIPTION
            "sysTimeOfDay of last time the backup software was saved
             to Flash Memory."
    ::= { moduleEntry 30 }


moduleBackupSwTftpIp OBJECT-TYPE
    SYNTAX  IpAddress
    ACCESS  read-only
    STATUS  mandatory
    DESCRIPTION
            "IP address of the TFTP server from which the software
             was originally loaded."
    ::= { moduleEntry 31 }

moduleSwTftpIpAndSwName OBJECT-TYPE
    SYNTAX  OCTET STRING (SIZE (4..260))
    ACCESS  read-write
    STATUS  mandatory
    DESCRIPTION
            "This object contains the IP address of the TFTP
             server (4 bytes) and the software filename
             (0 to 256 bytes). This is used to initiate a
             software update. The result of the upgrade is
             accessible in moduleSwUpdateResult."
    ::= { moduleEntry 32 }

moduleSwUpdateResult OBJECT-TYPE
    SYNTAX  INTEGER {
               noError(1),
               swUpdateRunning(2),
               errorUnknown(3),
               errorNoTftpServer(4),
               errorNoSoftware(5),
               errorSoftwareMismatch(6),
               errorMoreFlash(7),
               errorMoreRAM(8)
               }
    ACCESS  read-only
    STATUS  mandatory
    DESCRIPTION
            "The result of software update initiated by setting
             moduleSwTftpIpAndSwName:

             noError(1):               The last upgrade ended successfully.
                                       No upgrade currently in progress.

             swUpdateRunning(2):       An upgrade is currently in progress.

             errorUnknown(3):          The last upgrade failed.

             errorNoTftpServer(4):     The last upgrade failed. Server not
                                       found.

             errorNoSoftware(5):       The last upgrade failed. File not found
                                       on server.

             errorSoftwareMismatch(6): The last upgrade failed. The software
                                       loaded was not for this device type.

             errorMoreFlash(7):        The last upgrade failed. Insufficient
                                       Flash Memory.

             errorMoreRAM(8):          The last upgrade failed. Insufficient
                                       RAM."
    ::= { moduleEntry 33 }

moduleSpecificObject OBJECT-TYPE
    SYNTAX  OCTET STRING (SIZE (0..256))
    ACCESS  write-only
    STATUS  mandatory
    DESCRIPTION
            "Used for module specific configuration."
    ::= { moduleEntry 34 }

moduleTemperatureStatus OBJECT-TYPE        
    SYNTAX  INTEGER {
                     normal(1),
                     high(2),
                     critical(3),
                     unavailable(99)
                    }
    ACCESS  read-only
    STATUS  optional
    DESCRIPTION
            "Indication of the modules temperature.
             normal(1):       Temperature within normal opperational specification
             high(2):         Temperature obove normal opperational specification (Check air circulation)
             critical(3):     Temperature critically obove normal opperational specification (Chut device the device imediatlly)
             unavailable(99): No temperature censor in the device."
    ::= { moduleEntry 35 }

moduleBootSectionVersion OBJECT-TYPE
    SYNTAX  INTEGER
    ACCESS  read-only
    STATUS  mandatory
    DESCRIPTION
            "The version number for the Boot section of this module.
             Major version number = moduleBootSectionVersion / 256
             Minor version number = moduleBootSectionVersion % 256"
    ::= { moduleEntry 36 }

-- *************************** intel.hw.mediamodules **************************

mediaModuleTable   OBJECT-TYPE
    SYNTAX  SEQUENCE OF MediaModuleEntry
    ACCESS  not-accessible
    STATUS  mandatory
    DESCRIPTION
            "Possible values of indices are
             1..moduleMaxMediaModules"
    ::= { mediamodules    1 }

mediaModuleEntry   OBJECT-TYPE
    SYNTAX  MediaModuleEntry
    ACCESS  not-accessible
    STATUS  mandatory
    DESCRIPTION
            "Possible values of indices are
             1..stackMaxChassis, 1..chassisMaxModules
             and 1..moduleMaxMediaModules"
    INDEX   { mediaModuleChassisIndex,mediaModuleModuleIndex,mediaModuleIndex }
            ::= { mediaModuleTable  1 }

MediaModuleEntry ::=
   SEQUENCE {
            mediaModuleChassisIndex         INTEGER,
            mediaModuleModuleIndex          INTEGER,
            mediaModuleIndex                INTEGER,
            mediaModuleType                 INTEGER,
            mediaModuleFirstPort            INTEGER,
            mediaModuleNumberOfPorts        INTEGER,
            mediaModuleVersion              INTEGER
            }

mediaModuleChassisIndex   OBJECT-TYPE
    SYNTAX  INTEGER
    ACCESS  read-only
    STATUS  mandatory
    DESCRIPTION
            "The chassis number that contains the module that contains
             the media modules."
    ::= { mediaModuleEntry    1 }

mediaModuleModuleIndex   OBJECT-TYPE
    SYNTAX  INTEGER
    ACCESS  read-only
    STATUS  mandatory
    DESCRIPTION
            "The module number that contains the media module."
    ::= { mediaModuleEntry    2 }

mediaModuleIndex   OBJECT-TYPE
    SYNTAX  INTEGER
    ACCESS  read-only
    STATUS  mandatory
    DESCRIPTION
            "Media module number in the module."
    ::= { mediaModuleEntry    3 }

mediaModuleType OBJECT-TYPE
    SYNTAX  INTEGER {
                    unavailable(1),
                    mediaModule4tx(2),
                    mediaModule2fx(3),
                    mediaModuleSMM(4),
                    mediaModule1sx(5),
                    mediaModuleMMM(6),
                    mediaModule1sxSMM(7),
                    mediaModule1lxSMM(8),
                    mediaModule1atmmm(9),
                    mediaModule1atmsm(10),
                    mediaModule1atmutp(11),
                    mediaModule1lx(12),
                    mediaModule1000bt(13)
                    }
    ACCESS  read-only
    STATUS  mandatory
    DESCRIPTION
            "The product identification of the media module."
    ::= { mediaModuleEntry 4 }

mediaModuleFirstPort OBJECT-TYPE
    SYNTAX  INTEGER
    ACCESS  read-only
    STATUS  mandatory
    DESCRIPTION
            "The portIndex of the first port on the media module."
    ::= { mediaModuleEntry 5 }

mediaModuleNumberOfPorts OBJECT-TYPE
    SYNTAX  INTEGER
    ACCESS  read-only
    STATUS  mandatory
    DESCRIPTION
            "The number of ports on the media module."
    ::= { mediaModuleEntry 6 }

mediaModuleVersion   OBJECT-TYPE
    SYNTAX  INTEGER
    ACCESS  read-only
    STATUS  mandatory
    DESCRIPTION
            "Hardware version number for this media module.
             First version is 0, second is 1, and so on."
    ::= { mediaModuleEntry    7 }

-- *************************** intel.hw.port ***************************

portTable   OBJECT-TYPE
    SYNTAX  SEQUENCE OF PortEntry
    ACCESS  not-accessible
    STATUS  mandatory
    DESCRIPTION
            "Possible values of indices are
             1..chassisModules"
    ::= { ports    1 }

portEntry   OBJECT-TYPE
    SYNTAX  PortEntry
    ACCESS  not-accessible
    STATUS  mandatory
    DESCRIPTION
            "Possible values of indices are
             1..chassisModules"
    INDEX   {  portChassisIndex, portModuleIndex, portIndex }
    ::= { portTable  1 }

PortEntry ::=
    SEQUENCE {
             portChassisIndex                INTEGER,
             portModuleIndex                 INTEGER,
             portIndex                       INTEGER,
             portMediaModuleIndex            INTEGER,
             portIfIndex                     INTEGER,
             portType                        INTEGER,
             portStatus                      INTEGER,
             portLEDInfo                     OCTET STRING,
             portTimeSinceLastStateChange    TimeTicks,
             portResetAllCounters            INTEGER,
             portReset                       INTEGER,
             portLastErrorID                 INTEGER,
             portUserAssignedName            DisplayString (SIZE (0..32))
             }

portChassisIndex   OBJECT-TYPE
    SYNTAX  INTEGER
    ACCESS  read-only
    STATUS  mandatory
    DESCRIPTION
            "The chassis number that contains the module."
    ::= { portEntry    1 }

portModuleIndex   OBJECT-TYPE
    SYNTAX  INTEGER
    ACCESS  read-only
    STATUS  mandatory
    DESCRIPTION
            "The module number that contains the port."
    ::= { portEntry    2 }

portIndex   OBJECT-TYPE
    SYNTAX  INTEGER
    ACCESS  read-only
    STATUS  mandatory
    DESCRIPTION
            "The port number in the module."
    ::= { portEntry    3 }

portMediaModuleIndex   OBJECT-TYPE
    SYNTAX  INTEGER
    ACCESS  read-only
    STATUS  mandatory
    DESCRIPTION
            "The media module number in the module.
             Returns 0 if the port is not on a media module."
    ::= { portEntry    4 }

portIfIndex   OBJECT-TYPE
    SYNTAX  INTEGER
    ACCESS  read-only
    STATUS  mandatory
    DESCRIPTION
            "The index value which uniquely identifies the
             interface to which this port is assigned.
             This is the same interface as identified by the
             same value of ifIndex.
             Returns 0 if the port is not a part of an interface."
    ::= { portEntry    5 }


portType   OBJECT-TYPE
    SYNTAX  INTEGER {
                    tpfd(1),
                    fomm(2),
                    fosm(3),
                    hundredbasetx(4),
                    hundredbasefx(5),
                    core(6),
                    serialwan(7),
                    isdnU(8),
                    isdnST(9),
                    gigabasesxlx(10),
                    tenbasetx(11),
                    oc3mm(12),
                    oc3sm(13),
                    utp5(14),
                    csu(15),
                    console(16),
                    gigabasesx(17),
                    gigabaselx(18),
                    gigabaset(19)
                    }
    ACCESS  read-only
    STATUS  mandatory
    DESCRIPTION
            "Type of the port.

             tpfd(1)          : 10Mb Twisted pair full duplex port
             fomm(2)          : 10Mb Fiber-optic multi-mode port
             fosm(3)          : 10Mb Fiber-optic single-mode port
             hundredbasetx(4) : 100Mb Twisted pair port
             hundredbasefx(5) : 100Mb Fiber-optic port
             core(6)          : Stack interface port
             serialwan(7)     : Serial Wan Interface Port
             isdnU(8)         : ISDN Basic Rate U interface
             isdnST(9)        : ISDN Basic Rate S/T Interface
             gigabasesxlx(10) : 1Gb sx or lx port
             tenbasetx(11)    : 10Mb Twisted pair port
             oc3mm(12)        : ATM oc3 multi mode 155MB port
             oc3sm(13)        : ATM oc3 single mode 155MB port
             utp5(14)         : ATM 155MB utp5 port
             csu(15)          : 1,544 Mb T1 Channel Service Unit port
             console(16)      : RS-232 Console port
             gigabasesx(17)   : 1Gb sx port
             gigabaselx(18)   : 1Gb lx port
             gigabaset(19)    : 1Gb tx port"
    ::= { portEntry    6 }

portStatus   OBJECT-TYPE
    SYNTAX  INTEGER
    ACCESS  read-only
    STATUS  mandatory
    DESCRIPTION
            "The current operational state. This is a bit
             array which represents the state of the port.

             bit 0: disabled by configuration
             bit 1: hardware error
             bit 2: no link pulse
             bit 3: disabled by manager
             bit 4: disabled by access control
             bit 5: disabled by redundancy"
    ::= { portEntry    7 }

portLEDInfo   OBJECT-TYPE
    SYNTAX  OCTET STRING
    ACCESS  read-only
    STATUS  mandatory
    DESCRIPTION
            "State of all LEDs for the port (external ports only).

             There is one byte per LED.

             The most significant bit is used for blink/solid:
                Off = The LED is lit permanently.
                On = The LED blinks.

             The three least significant bits are used for color:
                1 = not lit
                2 = green
                3 = yellow
                4 = blue
                5 = red
                0+6+7 not used

             The four remaining bits are currently unused and must be 0."

    ::= { portEntry    8 }

portTimeSinceLastStateChange   OBJECT-TYPE
    SYNTAX  TimeTicks
    ACCESS  read-only
    STATUS  mandatory
    DESCRIPTION
            "sysUpTime of last portState change."
    ::= { portEntry    9 }

portResetAllCounters   OBJECT-TYPE
    SYNTAX  INTEGER  {
                          reset(1),
                          notreset(2)
                    }
    ACCESS  read-write
    STATUS  mandatory
    DESCRIPTION
            "Reset all port counters to zero. This is not recommended
             because it violates the SNMP specification."
    ::= { portEntry    10 }

portReset   OBJECT-TYPE
    SYNTAX  INTEGER {
                    reset(1),
                    notreset(2),
                    holdinreset(3)
                    }
    ACCESS  read-write
    STATUS  mandatory
    DESCRIPTION
            "Reset the port at the media level."
    ::= { portEntry    11 }

portLastErrorID   OBJECT-TYPE
    SYNTAX  INTEGER {
                    noError(1),
                    badPhy(2),
                    polarity(3),
                    wrongSpeedLP(4),
                    jabberSeen(5),
                    partition(6),
                    reserved1(7),
                    reserved2(8)
                    }
    ACCESS  read-only
    STATUS  mandatory
    DESCRIPTION
            "Type of last error that occurred on the port since the last
             link status change. badPhy is a hardware problem with the hub
             port. polarity means there's a cabling problem between the hub
             and the attached device. wrongSpeedLP means the device attached
             to the port is operating at the wrong speed. jabberSeen means
             you may have a faulty device attached to the port. partition
             means the port was automatically partitioned at least once. "
    ::= { portEntry    12 }

portUserAssignedName   OBJECT-TYPE
    SYNTAX  DisplayString (SIZE (0..32))
    ACCESS  read-write
    STATUS  mandatory
    DESCRIPTION
            "User-definable information about the port."
    ::= { portEntry 13 }
 

-- *************************** Trap section ***************************

snmpAuthViolation TRAP-TYPE
    ENTERPRISE  snmp
    VARIABLES   { snmpAccessIP, snmpAccessTime, snmpAccessProtocol, snmpAccessType }
    DESCRIPTION
            "This trap is sent when a device attempting to access the device fails 
             to pass the snmpAuthTable for any of the supported protocols. 
             If it is the SNMP protocol that is violated then the device must also 
             send the 'Authentication failure' trap defined in MIB-2."
    ::= 1

snmpLoginViolation TRAP-TYPE
    ENTERPRISE  snmp
    VARIABLES   { snmpAccessIP, snmpAccessTime, snmpAccessProtocol, snmpAccessType }
    DESCRIPTION
            "This trap is sent when a device attempting to access the device fails 
             to pass the user/password authentication for any of the supported protocols."
    ::= 2

chassisInserted TRAP-TYPE
    ENTERPRISE  chassis
    VARIABLES   { chassisIndex }
    DESCRIPTION
            "This trap is sent when a chassis is inserted in the
             stack."
    ::= 1

chassisRemoved TRAP-TYPE
    ENTERPRISE  chassis
    VARIABLES   { chassisIndex }
    DESCRIPTION
            "This trap is sent when a chassis is removed from
             the stack."
    ::= 2

moduleInserted TRAP-TYPE
    ENTERPRISE  modules
    VARIABLES   { moduleChassisIndex,moduleIndex }
    DESCRIPTION
            "This trap is sent when a module is inserted in
             the chassis."
    ::= 1

moduleRemoved TRAP-TYPE
    ENTERPRISE  modules
    VARIABLES   { moduleChassisIndex,moduleIndex }
    DESCRIPTION
            "This trap is sent when a module is removed from
             the chassis."
    ::= 2

moduleTemperatureEvent TRAP-TYPE
        ENTERPRISE  modules
        VARIABLES   { moduleTemperatureStatus, moduleChassisIndex, moduleIndex }
        DESCRIPTION
             "This trap indicates that the temparature of the
              module has changed"
    ::= 3

mediaModuleInserted TRAP-TYPE
    ENTERPRISE  mediamodules
    VARIABLES   { moduleChassisIndex,moduleIndex,mediaModuleIndex }
    DESCRIPTION
            "This trap is sent when a media module is inserted in
             the chassis/module."
    ::= 1

mediaModuleRemoved TRAP-TYPE
    ENTERPRISE  mediamodules
    VARIABLES   { moduleChassisIndex,moduleIndex,mediaModuleIndex }
    DESCRIPTION
            "This trap is sent when a media module is removed from
             the chassis/module."
    ::= 2

END
