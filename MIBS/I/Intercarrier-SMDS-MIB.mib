Intercarrier-SMDS-MIB DEFINITIONS ::= BEGIN
          IMPORTS
                 enterprises, Gauge
                          FROM RFC1155-SMI
                  DisplayString
                          FROM RFC1213-MIB
                  OBJECT-TYPE
                          FROM RFC-1212;

          --  This MIB module uses the extended OBJECT-TYPE macro as
          --  defined in RFC 1212.

                bellcore              OBJECT IDENTIFIER ::= { enterprises 148 }
                requirements          OBJECT IDENTIFIER ::= { bellcore 1 }
                taTsv001237           OBJECT IDENTIFIER ::= { requirements 4 }
                smdsIomServMIB        OBJECT IDENTIFIER ::= { taTsv001237 1 }
                smdsIomServObjects    OBJECT IDENTIFIER ::= { smdsIomServMIB 1 }

          -- In addition to the imports, two object types have been
          -- defined for this MIB module:
          -- SMDSAddress and CCode.

                SMDSAddress ::= OCTET STRING (SIZE(8))

          -- This object type reflects an SMDS address
          -- associated with an SNI.

                CCode ::= INTEGER (1..9999)

          -- This object type reflects a 4 decimal digit code
          -- associated with an IC or LEC.



















          -- The XA-SMDS Subscription Profile Group

          -- Implementation of this group is mandatory for all systems
          -- that perform Intercarrier SMDS.

          -- This group has one table:
          --   Aggregated Access Classes.


          -- Aggregated Access Classes Table

          smdsIomAggAccClTable OBJECT-TYPE
              SYNTAX  SEQUENCE OF SmdsIomAggAccClEntry
              ACCESS  not-accessible
              STATUS  mandatory
              DESCRIPTION
                      "The Aggregated Access Class Table"
              ::= { smdsIomServObjects 1 }

          smdsIomAggAccClEntry OBJECT-TYPE
              SYNTAX  SmdsIomAggAccClEntry
              ACCESS  not-accessible
              STATUS  mandatory
              DESCRIPTION
                      "An entry in the Aggregated Access Class Table"
              INDEX   { smdsIomAggAccClIcIndex }
              ::= { smdsIomAggAccClTable 1 }

          SmdsIomAggAccClEntry ::=
              SEQUENCE {
                  smdsIomAggAccClIcIndex
                     CCode,
                  smdsIomAggAccClValue
                      INTEGER
              }

          smdsIomAggAccClIcIndex OBJECT-TYPE
              SYNTAX  CCode
              ACCESS  read-only
              STATUS  mandatory
              DESCRIPTION
                      "The IC's SMDS CIC"
              ::= { smdsIomAggAccClEntry 1 }









          smdsIomAggAccClValue OBJECT-TYPE
              SYNTAX  INTEGER (1..65535)
              ACCESS  read-only
              STATUS  mandatory
              DESCRIPTION
                      "The value of this object reflects the
                      aggregated access classes in Megabits per second
                      of the end-users who have preselected an IC."
              ::= { smdsIomAggAccClEntry 2 }











































          -- The Intercarrier SMDS-Related Information Group

          -- Implementation of this group is mandatory for all systems
          -- that perform Intercarrier SMDS.

          -- This group consists of 5 tables:
          --     LEC Network Addresses,
          --     ICI Configuration,
          --     Nested Group Address (NGA),
          --     SNI-Related Current Information, and
          --     SNI-Related Interval Information.


          -- LEC Network Addresses Table
          -- This table lists up to the first six digits following
          -- the country code
          -- of addresses served by the LEC's network.
          -- Note that this table has been designed to support
          -- both North American and European addressing.

          smdsIomLecNetAddrTable OBJECT-TYPE
              SYNTAX  SEQUENCE OF SmdsIomLecNetAddrEntry
              ACCESS  not-accessible
              STATUS  mandatory
              DESCRIPTION
                      "This table lists network addresses, their
                      address types (whether or not the address is an
                      Embodied SAC) and the SMDS addresses of the test
                      SNIs associated with the network addresses."
              ::= { smdsIomServObjects 2 }

          smdsIomLecNetAddrEntry OBJECT-TYPE
              SYNTAX  SmdsIomLecNetAddrEntry
              ACCESS  not-accessible
              STATUS  mandatory
              DESCRIPTION
                      "An entry in the LEC Network Address Table"
              INDEX   { smdsIomLecNetAddrIndex }
              ::= { smdsIomLecNetAddrTable 1 }













          SmdsIomLecNetAddrEntry ::=
              SEQUENCE {
                smdsIomLecNetAddrIndex
                      INTEGER,
                smdsIomLecNetAddrDigits
                      INTEGER,
                smdsIomLecNetAddrAddrType
                      INTEGER,
                smdsIomLecNetAddrTestSNI
                      SMDSAddress
                }

          smdsIomLecNetAddrIndex OBJECT-TYPE
              SYNTAX  INTEGER (1..65535)
              ACCESS  read-only
              STATUS  mandatory
              DESCRIPTION
                      "This object is used to index
                      smdsIomLecNetAddrTable."
              ::= { smdsIomLecNetAddrEntry 1 }

          smdsIomLecNetAddrDigits OBJECT-TYPE
              SYNTAX INTEGER (1..999999)
              ACCESS  read-only
              STATUS  mandatory
              DESCRIPTION
                      "The value of this object reflects up to the
                      first six digits following the country code of
                      an SMDS Address served by the LEC's network."
              ::= { smdsIomLecNetAddrEntry 2 }

          smdsIomLecNetAddrAddrType OBJECT-TYPE
              SYNTAX  INTEGER {
                network(1),
                embodiedsac(2)
                }
              ACCESS  read-only
              STATUS  mandatory
              DESCRIPTION
                      "The value of this object indicates the type of
                      address reflected in smdsIomLecNetAddrDigits."
               ::= { smdsIomLecNetAddrEntry 3 }










           smdsIomLecNetAddrTestSNI OBJECT-TYPE
              SYNTAX SMDSAddress
              ACCESS  read-only
              STATUS  mandatory
              DESCRIPTION
                      "The value of this object reflects an SMDS
                      Address assigned to the Test SNI that is
                      associated with smdsIomLecNetAddrDigits."
               ::= { smdsIomLecNetAddrEntry 4 }



          -- ICI Configuration Table
          -- This table provides ICI configuration information

          smdsIomIciConfigTable OBJECT-TYPE
              SYNTAX  SEQUENCE OF SmdsIomIciConfigEntry
              ACCESS  not-accessible
              STATUS  mandatory
              DESCRIPTION
                      "This table lists the ICI Transmission Path
                      Identifier, the ICI ifIndex, Location, and
                      MCDUs."
              ::= { smdsIomServObjects 3 }

          smdsIomIciConfigEntry OBJECT-TYPE
              SYNTAX  SmdsIomIciConfigEntry
              ACCESS  not-accessible
              STATUS  mandatory
              DESCRIPTION
                      "An entry in the ICI Configuration Information
                      Table"
              INDEX   { smdsIomIciConfigIciTransPathIdIndex }
              ::= { smdsIomIciConfigTable 1 }

          SmdsIomIciConfigEntry ::=
              SEQUENCE {
                smdsIomIciConfigIciTransPathIdIndex
                      DisplayString,
                smdsIomIciConfigIfIndex
                      INTEGER,
                 smdsIomIciConfigIciLocation
                      DisplayString,
                smdsIomIciConfigIciMcdus
                      INTEGER







            }

          smdsIomIciConfigIciTransPathIdIndex OBJECT-TYPE
              SYNTAX DisplayString (SIZE (1..255) )
              ACCESS  read-only
              STATUS  mandatory
              DESCRIPTION
                      "The value of this object reflects an identifier
                      assigned to an ICI as part of the provisioning
                      process."
              ::= { smdsIomIciConfigEntry 1 }

          smdsIomIciConfigIfIndex OBJECT-TYPE
              SYNTAX  INTEGER (1..65535)
              ACCESS  read-only
              STATUS  mandatory
              DESCRIPTION
                      "The value of this object identifies the ifIndex
                      associated with the ICIP sublayer of the ICI."
              ::= { smdsIomIciConfigEntry 2 }

          smdsIomIciConfigIciLocation OBJECT-TYPE
              SYNTAX  DisplayString
              ACCESS  read-only
              STATUS  mandatory
              DESCRIPTION
                      "The value of this object indicates the location
                      of the LEC SS at which the ICI is terminated."
             ::= { smdsIomIciConfigEntry 3 }

           smdsIomIciConfigIciMcdus OBJECT-TYPE
              SYNTAX INTEGER{
                mcdus128(1),
                mcdus511(2)
                }
                ACCESS  read-only
                STATUS  mandatory
              DESCRIPTION
                      "The value of this object reflects the maximum
                      data units in transit concurrently.  For Phase 1
                      Exchange Access SMDS, the two acceptable values
                      are: 128 and 511."
              ::= { smdsIomIciConfigEntry 4 }









          -- NGA Table
          -- This table provides all the individual addresses that
          -- are members of a particular Nested Group Address (NGA).

          smdsIomNgaTable OBJECT-TYPE
              SYNTAX  SEQUENCE OF SmdsIomNgaEntry
              ACCESS  not-accessible
              STATUS  mandatory
              DESCRIPTION
                      "This table lists the individual addresses that
                      are members of a particular NGA."
              ::= { smdsIomServObjects 4 }

          smdsIomNgaEntry OBJECT-TYPE
              SYNTAX  SmdsIomNgaEntry
              ACCESS  not-accessible
              STATUS  mandatory
              DESCRIPTION
                      "An entry in the NGA Table"
              INDEX   { smdsIomNgaCountryCodeIndex,
                        smdsIomNgaDestinCodeIndex,
                        smdsIomNgaSubscriberNoIndex,
                        smdsIomNgaMemberCountryCodeIndex,
                        smdsIomNgaMemberDestinCodeIndex,
                        smdsIomNgaMemberSubscriberNoIndex }
              ::= { smdsIomNgaTable 1 }

          SmdsIomNgaEntry ::=
              SEQUENCE {
                smdsIomNgaCountryCodeIndex
                      INTEGER,
                smdsIomNgaDestinCodeIndex
                      INTEGER,
                smdsIomNgaSubscriberNoIndex
                      INTEGER,
                smdsIomNgaMemberCountryCodeIndex
                      INTEGER,
                smdsIomNgaMemberDestinCodeIndex
                      INTEGER,
                smdsIomNgaMemberSubscriberNoIndex
                      INTEGER,
                smdsIomNgaAddress
                      SMDSAddress,
                smdsIomNgaMember
                      SMDSAddress







            }

          smdsIomNgaCountryCodeIndex OBJECT-TYPE
              SYNTAX INTEGER (1..999)
              ACCESS  read-only
              STATUS  mandatory
              DESCRIPTION
                      "The value of this object identifies the country
                      code portion of the NGA."
              ::= { smdsIomNgaEntry 1 }

          smdsIomNgaDestinCodeIndex  OBJECT-TYPE
              SYNTAX INTEGER (1..999999999)
              ACCESS  read-only
              STATUS  mandatory
              DESCRIPTION
                      "This object reflects the destination code
                      portion of the NGA.  For North America, the
                      destination code is the first three digits
                      following the country code."
              ::= {  smdsIomNgaEntry 2 }

           smdsIomNgaSubscriberNoIndex OBJECT-TYPE
              SYNTAX INTEGER (1..999999999)
              ACCESS  read-only
              STATUS  mandatory
              DESCRIPTION
                      "This object reflects the subscriber number
                      portion of the NGA. For North America, the
                      subscriber number is the last seven digits of
                      the SMDS address of the NGA."
             ::= { smdsIomNgaEntry 3 }

          smdsIomNgaMemberCountryCodeIndex OBJECT-TYPE
              SYNTAX INTEGER (1..999)
              ACCESS  read-only
              STATUS  mandatory
              DESCRIPTION
                      "The value of this object identifies the country
                      code portion of an individual address that is a
                      member of the NGA."
              ::= { smdsIomNgaEntry 4 }










          smdsIomNgaMemberDestinCodeIndex OBJECT-TYPE
              SYNTAX INTEGER (1..999999999)
              ACCESS  read-only
              STATUS  mandatory
              DESCRIPTION
                      "This object reflects the destination code
                      portion of an individual address that is a
                      member of the NGA."
              ::= { smdsIomNgaEntry 5 }

          smdsIomNgaMemberSubscriberNoIndex OBJECT-TYPE
              SYNTAX INTEGER (1..999999999)
              ACCESS  read-only
              STATUS  mandatory
              DESCRIPTION
                      "This object reflects the subscriber number
                      portion of an individual address that is a
                      member of the NGA."
              ::= { smdsIomNgaEntry 6 }

          smdsIomNgaAddress OBJECT-TYPE
              SYNTAX SMDSAddress
              ACCESS  read-only
              STATUS  mandatory
              DESCRIPTION
                      "The value of this object identifies the NGA."
              ::= { smdsIomNgaEntry 7 }

          smdsIomNgaMember OBJECT-TYPE
              SYNTAX SMDSAddress
              ACCESS  read-only
              STATUS  mandatory
              DESCRIPTION
                      "The value of this object identifies an
                      individual address that is a member of the NGA."
              ::= {   smdsIomNgaEntry 8 }
















          -- SNI-Related Current Information Table
          -- This table provides current SNI-related information such as:
          -- address screening violations, SIP L3_PDU error ratio,
          -- and discards due to service disagreements.

           smdsIomSniCurrentInfoTable OBJECT-TYPE
              SYNTAX  SEQUENCE OF SmdsIomSniCurrentInfoEntry
              ACCESS  not-accessible
              STATUS  mandatory
              DESCRIPTION
                      "This table provides current SNI-related
                      information."
              ::= { smdsIomServObjects 5 }

           smdsIomSniCurrentInfoEntry OBJECT-TYPE
              SYNTAX   SmdsIomSniCurrentInfoEntry
              ACCESS  not-accessible
              STATUS  mandatory
              DESCRIPTION
                      "An entry in the SNI-Related Current Information
                      Table"
              INDEX   {  smdsIomSniCurrentInfoIfIndex }
              ::= {  smdsIomSniCurrentInfoTable 1 }

           SmdsIomSniCurrentInfoEntry ::=
              SEQUENCE {
                smdsIomSniCurrentInfoIfIndex
                      INTEGER,
                smdsIomSniCurrentInfoSourceAddrScreenViolations
                      Gauge,
                smdsIomSniCurrentInfoDestinAddrScreenViolations
                      Gauge,
                smdsIomSniCurrentInfoSipErrorRatio
                       INTEGER,
                smdsIomSniCurrentInfoServDisagreeDiscards
                      Gauge
                }

          smdsIomSniCurrentInfoIfIndex OBJECT-TYPE
              SYNTAX INTEGER (0..65535)
              ACCESS  read-only
              STATUS  mandatory
              DESCRIPTION
                      "The value of this object identifies the ifIndex
                      associated with the appropriate SNI sublayer.







                      For more information, refer to TR-TSV-001062."
              ::= { smdsIomSniCurrentInfoEntry 1 }

          smdsIomSniCurrentInfoSourceAddrScreenViolations  OBJECT-TYPE
              SYNTAX Gauge
              ACCESS  read-only
              STATUS  mandatory
              DESCRIPTION
                      "The value of this object reflects the number of
                      SIP L3_PDUs discarded because the source address
                      violated the address screening."
              ::= { smdsIomSniCurrentInfoEntry 2 }

          smdsIomSniCurrentInfoDestinAddrScreenViolations  OBJECT-TYPE
              SYNTAX Gauge
              ACCESS  read-only
              STATUS  mandatory
              DESCRIPTION
                      "The value of this object reflects the number of
                      SIP L3_PDUs discarded because the destination
                      address violated the address screening."
              ::= { smdsIomSniCurrentInfoEntry 3 }

           smdsIomSniCurrentInfoSipErrorRatio  OBJECT-TYPE
              SYNTAX INTEGER (1..65535)
              ACCESS  read-only
              STATUS  mandatory
              DESCRIPTION
                      "The value of this object reflects the result
                      multiplied by a factor of 1000 of the ratio of
                      the number of errored SIP L3_PDUs to the number
                      of total incoming SIP L3_PDUs."
              ::= { smdsIomSniCurrentInfoEntry 4 }

            smdsIomSniCurrentInfoServDisagreeDiscards  OBJECT-TYPE
              SYNTAX Gauge
              ACCESS  read-only
              STATUS  mandatory
              DESCRIPTION
                      " The value of this object reflects the number
                      of SIP L3_PDUs discarded because of service
                      disagreements."
              ::= { smdsIomSniCurrentInfoEntry 5 }









          -- SNI-Related Interval Information Table
          -- This table provides SNI-related information for four 15-minute
          -- intervals preceding the current interval.  This table provides
          -- information on the SIP L3_PDU error ratio and
          -- discards due to service disagreements.

           smdsIomSniIntervalInfoTable OBJECT-TYPE
              SYNTAX  SEQUENCE OF SmdsIomSniIntervalInfoEntry
              ACCESS  not-accessible
              STATUS  mandatory
              DESCRIPTION
                      "This table provides SNI-related information
                      from previous intervals."
              ::= { smdsIomServObjects 6 }

           smdsIomSniIntervalInfoEntry OBJECT-TYPE
              SYNTAX   SmdsIomSniIntervalInfoEntry
              ACCESS  not-accessible
              STATUS  mandatory
              DESCRIPTION
                      "An entry in the SNI-Related Interval
                      Information Table"
              INDEX   {  smdsIomSniIntervalInfoIfIndex,
                          smdsIomSniIntervalInfoIntervalIndex }
              ::= {  smdsIomSniIntervalInfoTable 1 }

           SmdsIomSniIntervalInfoEntry ::=
              SEQUENCE {
                smdsIomSniIntervalInfoIfIndex
                      INTEGER,
                smdsIomSniIntervalInfoIntervalIndex
                      INTEGER,
                smdsIomSniIntervalInfoSipErrorRatio
                       INTEGER,
                smdsIomSniIntervalInfoServDisagreeDiscards
                      Gauge
                }

          smdsIomSniIntervalInfoIfIndex OBJECT-TYPE
              SYNTAX INTEGER (0..65535)
              ACCESS  read-only
              STATUS  mandatory
              DESCRIPTION
                      "The value of this object identifies the ifIndex
                      associated with the appropriate SNI sublayer.







                      For more information, refer to TR-TSV-001062."
              ::= { smdsIomSniIntervalInfoEntry 1 }

          smdsIomSniIntervalInfoIntervalIndex OBJECT-TYPE
              SYNTAX INTEGER (1..4)
              ACCESS  read-only
              STATUS  mandatory
              DESCRIPTION
                      "The value of this object identifies the
                      interval index associated with the SNI-related
                      information.  An index of '1' is used to
                      indicate the most recent interval and an index
                      '4' is used to indicate the latest interval for
                      which information is maintained."
              ::= { smdsIomSniIntervalInfoEntry 2 }

           smdsIomSniIntervalInfoSipErrorRatio  OBJECT-TYPE
              SYNTAX INTEGER (1..65535)
              ACCESS  read-only
              STATUS  mandatory
              DESCRIPTION
                      "The value of this object reflects the result
                      multiplied by a factor of 1000 of the ratio of
                      the number of errored SIP L3_PDUs to the number
                      of total incoming SIP L3_PDUs."
              ::= { smdsIomSniIntervalInfoEntry 3 }

            smdsIomSniIntervalInfoServDisagreeDiscards  OBJECT-TYPE
              SYNTAX Gauge
              ACCESS  read-only
              STATUS  mandatory
              DESCRIPTION
                      " The value of this object reflects the number
                      of SIP L3_PDUs discarded because of service
                      disagreements."
              ::= { smdsIomSniIntervalInfoEntry 4 }
















          -- The Inter-Carrier Interface Protocol (ICIP) Level 3 Group


          -- Implementation of this group is mandatory for all systems
          -- that perform intercarrier SMDS.

          -- This group consists of 2 tables:
          --    ICIP Level 3 Current Table, and
          --    ICIP Level 3 Interval Table.
          -- For SMDS XA-OM and ECOM,
          -- counts are collected over 15 minute intervals.

          -- ICIP Level 3 Current Table
          -- This table contains the current interval counts for the
          -- ICIP Level 3 of a given ICI.

          smdsIomIcipL3CurrentTable OBJECT-TYPE
              SYNTAX  SEQUENCE OF SmdsIomIcipL3CurrentEntry
              ACCESS  not-accessible
              STATUS  mandatory
              DESCRIPTION
                      "The ICIP Level 3 Current Table"
              ::= { smdsIomServObjects 7 }

          smdsIomIcipL3CurrentEntry OBJECT-TYPE
              SYNTAX SmdsIomIcipL3CurrentEntry
              ACCESS  not-accessible
              STATUS  mandatory
              DESCRIPTION
                      "An entry in the ICIP Level 3 Current Table"
              INDEX   { smdsIomIcipL3CurrentIfIndex }
              ::= { smdsIomIcipL3CurrentTable 1 }

          SmdsIomIcipL3CurrentEntry ::=
              SEQUENCE {
                smdsIomIcipL3CurrentIfIndex
                      INTEGER,
                smdsIomIcipL3CurrentCSInvalidFieldsDiscards
                      Gauge,
                smdsIomIcipL3CurrentCSIncorrectFieldsDiscards
                      Gauge,
                smdsIomIcipL3CurrentHeaderBEtagDiscards
                      Gauge,
                smdsIomIcipL3CurrentBAsizeDiscards
                      Gauge,







                smdsIomIcipL3CurrentLengthFieldDiscards
                      Gauge,
                smdsIomIcipL3CurrentCSSInvalidFieldsDiscards
                      Gauge,
                smdsIomIcipL3CurrentCSSRoutingErrorsDiscards
                      Gauge
              }

            smdsIomIcipL3CurrentIfIndex OBJECT-TYPE
              SYNTAX INTEGER (0..65535)
              ACCESS  read-only
              STATUS  mandatory
              DESCRIPTION
                      "The value of this object identifies the ifIndex
                      associated with the ICIP sublayer of the ICI."
              ::= { smdsIomIcipL3CurrentEntry 1 }

          smdsIomIcipL3CurrentCSInvalidFieldsDiscards  OBJECT-TYPE
              SYNTAX Gauge
              ACCESS  read-only
              STATUS  mandatory
              DESCRIPTION
                      "The value of this object reflects the number of
                      ICIP L3_PDUs discarded because of invalid fields
                      that occurred at the convergence sublayer."
              ::= { smdsIomIcipL3CurrentEntry 2 }

           smdsIomIcipL3CurrentCSIncorrectFieldsDiscards  OBJECT-TYPE
              SYNTAX Gauge
              ACCESS  read-only
              STATUS  mandatory
              DESCRIPTION
                      "The value of this object reflects the number of
                      ICIP L3_PDUs discarded because of incorrect
                      fields that occurred at the convergence
                      sublayer."
              ::= { smdsIomIcipL3CurrentEntry 3 }















           smdsIomIcipL3CurrentHeaderBEtagDiscards  OBJECT-TYPE
              SYNTAX Gauge
              ACCESS  read-only
              STATUS  mandatory
              DESCRIPTION
                      "The value of this object reflects the number of
                      ICIP L3_PDUs discarded because of the Header
                      BEtag not equaling the Trailer BEtag."
              ::= { smdsIomIcipL3CurrentEntry 4 }

            smdsIomIcipL3CurrentBAsizeDiscards  OBJECT-TYPE
              SYNTAX Gauge
              ACCESS  read-only
              STATUS  mandatory
              DESCRIPTION
                      " The value of this object reflects the number
                      of ICIP L3_PDUs discarded because of the BAsize
                      not equaling the Length field."
              ::= { smdsIomIcipL3CurrentEntry 5 }

            smdsIomIcipL3CurrentLengthFieldDiscards OBJECT-TYPE
              SYNTAX Gauge
              ACCESS  read-only
              STATUS  mandatory
              DESCRIPTION
                      " The value of this object reflects the number
                      of ICIP L3_PDUs discarded because of the Length
                      field not equaling the number of octets in the
                      portion of the L3_PDU that extends from the
                      Destination Address field up to and including
                      the End-User Data field and Service-Specific
                      Pad."
              ::= { smdsIomIcipL3CurrentEntry  6 }

           smdsIomIcipL3CurrentCSSInvalidFieldsDiscards OBJECT-TYPE
              SYNTAX Gauge
              ACCESS  read-only
              STATUS  mandatory
              DESCRIPTION
                      " The value of this object reflects the number
                      of ICIP L3_PDUs discarded because of invalid
                      fields that occurred at the connectionless
                      service sublayer."
              ::= { smdsIomIcipL3CurrentEntry  7 }








           smdsIomIcipL3CurrentCSSRoutingErrorsDiscards OBJECT-TYPE
              SYNTAX Gauge
              ACCESS  read-only
              STATUS  mandatory
              DESCRIPTION
                      " The value of this object reflects the number
                      of ICIP L3_PDUs discarded because of routing
                      errors that occurred at the connectionless
                      service sublayer."
              ::= { smdsIomIcipL3CurrentEntry  8 }


          -- ICIP Level 3 Interval Table
          -- This table contains the performance counts for
          -- the past 8 intervals of ICIP Level 3 of an ICI.
          -- It is possible that less than 8 intervals may be reflected
          -- because the SS or ICI has not been on line for the
          -- entire 2 hours.

          smdsIomIcipL3IntervalTable OBJECT-TYPE
              SYNTAX  SEQUENCE OF SmdsIomIcipL3IntervalEntry
              ACCESS  not-accessible
              STATUS  mandatory
              DESCRIPTION
                      "The ICIP Level 3 Interval Table"
              ::= { smdsIomServObjects 8 }

          smdsIomIcipL3IntervalEntry OBJECT-TYPE
              SYNTAX SmdsIomIcipL3IntervalEntry
              ACCESS  not-accessible
              STATUS  mandatory
              DESCRIPTION
                      "An entry in the ICIP Level 3 Interval Table"
              INDEX   { smdsIomIcipL3IntervalIfIndex,
                        smdsIomIcipL3IntervalIntervalIndex }
              ::= { smdsIomIcipL3IntervalTable 1 }

          SmdsIomIcipL3IntervalEntry ::=
              SEQUENCE {
                smdsIomIcipL3IntervalIfIndex
                      INTEGER,
                smdsIomIcipL3IntervalIntervalIndex
                      INTEGER,
                smdsIomIcipL3IntervalCSInvalidFieldsDiscards
                      Gauge,







                smdsIomIcipL3IntervalCSIncorrectFieldsDiscards
                      Gauge,
                smdsIomIcipL3IntervalHeaderBEtagDiscards
                      Gauge,
                smdsIomIcipL3IntervalBAsizeDiscards
                      Gauge,
                smdsIomIcipL3IntervalLengthFieldDiscards
                      Gauge,
                smdsIomIcipL3IntervalCSSInvalidFieldsDiscards
                      Gauge,
                smdsIomIcipL3IntervalCSSRoutingErrorsDiscards
                      Gauge
              }

            smdsIomIcipL3IntervalIfIndex OBJECT-TYPE
              SYNTAX INTEGER (0..65535)
              ACCESS  read-only
              STATUS  mandatory
              DESCRIPTION
                      "The value of this object identifies the ifIndex
                      associated with the ICIP sublayer of the ICI."
              ::= { smdsIomIcipL3IntervalEntry 1 }

            smdsIomIcipL3IntervalIntervalIndex OBJECT-TYPE
              SYNTAX INTEGER (1..8)
              ACCESS  read-only
              STATUS  mandatory
              DESCRIPTION
                      "The value of this object identifies the
                      interval in which the counts occurred.  A value
                      of '1' indicates the most recently completed
                      interval while a value of '8' indicates least
                      recently completed interval."
              ::= { smdsIomIcipL3IntervalEntry 2 }

          smdsIomIcipL3IntervalCSInvalidFieldsDiscards  OBJECT-TYPE
              SYNTAX Gauge
              ACCESS  read-only
              STATUS  mandatory
              DESCRIPTION
                      "The value of this object reflects the number of
                      ICIP L3_PDUs discarded because of invalid fields
                      that occurred at the convergence sublayer."
              ::= { smdsIomIcipL3IntervalEntry 3 }








           smdsIomIcipL3IntervalCSIncorrectFieldsDiscards  OBJECT-TYPE
              SYNTAX Gauge
              ACCESS  read-only
              STATUS  mandatory
              DESCRIPTION
                      "The value of this object reflects the number of
                      ICIP L3_PDUs discarded because of incorrect
                      fields that occurred at the convergence
                      sublayer."
              ::= { smdsIomIcipL3IntervalEntry 4 }


           smdsIomIcipL3IntervalHeaderBEtagDiscards  OBJECT-TYPE
              SYNTAX Gauge
              ACCESS  read-only
              STATUS  mandatory
              DESCRIPTION
                      "The value of this object reflects the number of
                      ICIP L3_PDUs discarded because of the Header
                      BEtag not equaling the Trailer BEtag."
              ::= { smdsIomIcipL3IntervalEntry 5 }

            smdsIomIcipL3IntervalBAsizeDiscards  OBJECT-TYPE
              SYNTAX Gauge
              ACCESS  read-only
              STATUS  mandatory
              DESCRIPTION
                      " The value of this object reflects the number
                      of ICIP L3_PDUs discarded because of the BAsize
                      not equaling the Length field."
              ::= { smdsIomIcipL3IntervalEntry  6 }

            smdsIomIcipL3IntervalLengthFieldDiscards OBJECT-TYPE
              SYNTAX Gauge
              ACCESS  read-only
              STATUS  mandatory
              DESCRIPTION
                      " The value of this object reflects the number
                      of ICIP L3_PDUs discarded because of the Length
                      field not equaling the number of octets in the
                      portion of the L3_PDU that extends from the
                      Destination Address field up to and including
                      the End-User Data field and Service-Specific
                      Pad."
              ::= { smdsIomIcipL3IntervalEntry  7 }







           smdsIomIcipL3IntervalCSSInvalidFieldsDiscards OBJECT-TYPE
              SYNTAX Gauge
              ACCESS  read-only
              STATUS  mandatory
              DESCRIPTION
                      " The value of this object reflects the number
                      of ICIP L3_PDUs discarded because of invalid
                      fields that occurred at the connectionless
                      service sublayer."
              ::= { smdsIomIcipL3IntervalEntry  8 }

           smdsIomIcipL3IntervalCSSRoutingErrorsDiscards OBJECT-TYPE
              SYNTAX Gauge
              ACCESS  read-only
              STATUS  mandatory
              DESCRIPTION
                      " The value of this object reflects the number
                      of ICIP L3_PDUs discarded because of routing
                      errors that occurred at the connectionless
                      service sublayer."
              ::= { smdsIomIcipL3IntervalEntry  9 }































          -- The Inter-Carrier Interface Protocol (ICIP) Level 2 Group

          -- Implementation of this group is mandatory for all systems
          -- that perform intercarrier SMDS.

          -- This group consists of 2 tables:
          --    ICIP Level 2 Current Table, and
          --    ICIP Level 2 Interval Table.
          -- For SMDS XA-OM and ECOM, counts are
          -- collected over 15 minute intervals.

          -- ICIP Level 2 Current Table
          -- This table contains the current interval performance counts
          -- for the ICIP Level 2 of a given ICI.

          smdsIomIcipL2CurrentTable OBJECT-TYPE
              SYNTAX  SEQUENCE OF SmdsIomIcipL2CurrentEntry
              ACCESS  not-accessible
              STATUS  mandatory
              DESCRIPTION
                      "The ICIP Level 2 Current Count Table"
              ::= { smdsIomServObjects 9 }

          smdsIomIcipL2CurrentEntry OBJECT-TYPE
              SYNTAX SmdsIomIcipL2CurrentEntry
              ACCESS  not-accessible
              STATUS  mandatory
              DESCRIPTION
                      "An entry in the ICIP Level 2 Current Table"
              INDEX   { smdsIomIcipL2CurrentIfIndex }
              ::= { smdsIomIcipL2CurrentTable 1 }

          SmdsIomIcipL2CurrentEntry ::=
              SEQUENCE {
                smdsIomIcipL2CurrentIfIndex
                      INTEGER,
                smdsIomIcipL2CurrentTotalOut
                      Gauge,
                smdsIomIcipL2CurrentCongestionDiscards
                      Gauge,
                smdsIomIcipL2CurrentCellInvalidFieldsDiscards
                      Gauge,
                smdsIomIcipL2CurrentSARInvalidFieldsDiscards
                      Gauge,
                smdsIomIcipL2CurrentSARIncorrectFieldsDiscards







                      Gauge,
               smdsIomIcipL2CurrentCRCViolationsDiscards
                      Gauge,
                smdsIomIcipL2CurrentComsEomsDiscards
                      Gauge,
                smdsIomIcipL2CurrentBomsEomsDiscards
                      Gauge,
                smdsIomIcipL2CurrentMRIDiscards
                      Gauge
              }

            smdsIomIcipL2CurrentIfIndex OBJECT-TYPE
              SYNTAX INTEGER (0..65535)
              ACCESS  read-only
              STATUS  mandatory
              DESCRIPTION
                      "The value of this object identifies the ifIndex
                      associated with the ICIP sublayer of the ICI."
              ::= { smdsIomIcipL2CurrentEntry 1 }

           smdsIomIcipL2CurrentTotalOut  OBJECT-TYPE
              SYNTAX Gauge
              ACCESS  read-only
              STATUS  mandatory
              DESCRIPTION
                      "The value of this object reflects the number of
                      ICIP L2_PDUs sent across an ICI."
              ::= { smdsIomIcipL2CurrentEntry 2 }

            smdsIomIcipL2CurrentCongestionDiscards OBJECT-TYPE
              SYNTAX Gauge
              ACCESS  read-only
              STATUS  mandatory
              DESCRIPTION
                      "The value of this object reflects the number of
                      ICIP L2_PDUs discarded because an ICI was in
                      congestion."
              ::= { smdsIomIcipL2CurrentEntry 3 }














            smdsIomIcipL2CurrentCellInvalidFieldsDiscards  OBJECT-TYPE
              SYNTAX Gauge
              ACCESS  read-only
              STATUS  mandatory
              DESCRIPTION
                      "The value of this object reflects the number of
                      ICIP L2_PDUs discarded because of invalid fields
                      that occurred at the cell sublayer."
              ::= { smdsIomIcipL2CurrentEntry 4 }

            smdsIomIcipL2CurrentSARInvalidFieldsDiscards  OBJECT-TYPE
              SYNTAX Gauge
              ACCESS  read-only
              STATUS  mandatory
              DESCRIPTION
                      " The value of this object reflects the number
                      of ICIP L2_PDUs discarded because of invalid
                      fields that occurred at the Segmentation and
                      Reassembly (SAR) sublayer."
              ::= { smdsIomIcipL2CurrentEntry  5 }

            smdsIomIcipL2CurrentSARIncorrectFieldsDiscards OBJECT-TYPE
              SYNTAX Gauge
              ACCESS  read-only
              STATUS  mandatory
              DESCRIPTION
                      " The value of this object reflects the number
                      of ICIP L2_PDUs discarded because of incorrect
                      fields that occurred at the SAR sublayer."
              ::= { smdsIomIcipL2CurrentEntry  6 }

             smdsIomIcipL2CurrentCRCViolationsDiscards OBJECT-TYPE
              SYNTAX Gauge
              ACCESS  read-only
              STATUS  mandatory
              DESCRIPTION
                      " The value of this object reflects the number
                      of ICIP L2_PDUs discarded because the payload
                      Cyclic Redundancy Check (CRC) was incorrect."
              ::= { smdsIomIcipL2CurrentEntry  7 }












             smdsIomIcipL2CurrentComsEomsDiscards OBJECT-TYPE
              SYNTAX Gauge
              ACCESS  read-only
              STATUS  mandatory
              DESCRIPTION
                      " The value of this object reflects the number
                      of ICIP L2_PDUs discarded because the sequence
                      number of the Continuation of Message (COM) or
                      End of Message (EOM) was not incremented by 1
                      relative to the previous L2_PDU received with
                      the same Message Identifier (MID)."
              ::= {smdsIomIcipL2CurrentEntry  8 }

            smdsIomIcipL2CurrentBomsEomsDiscards OBJECT-TYPE
              SYNTAX Gauge
              ACCESS  read-only
              STATUS  mandatory
              DESCRIPTION
                      " The value of this object reflects the number
                      of ICIP L3_PDUs discarded because the MID of a
                      Beginning of Message (BOM) was currently active
                      or the MID of an EOM was not currently active."
              ::= { smdsIomIcipL2CurrentEntry  9 }

            smdsIomIcipL2CurrentMRIDiscards OBJECT-TYPE
              SYNTAX Gauge
              ACCESS  read-only
              STATUS  mandatory
              DESCRIPTION
                      " The value of this object reflects the number
                      of ICIP L2_PDUs discarded because of MRI
                      Timeout."
              ::= { smdsIomIcipL2CurrentEntry  10 }



















          -- ICIP Level 2 Interval Table
          -- This table contains the performance counts for
          -- the past 8 intervals of ICIP Level 2 of an ICI.
          -- It is possible that less than 8 intervals may be reflected because
          -- the SS or ICI has not been on line for the entire 2 hours.

            smdsIomIcipL2IntervalTable OBJECT-TYPE
              SYNTAX  SEQUENCE OF SmdsIomIcipL2IntervalEntry
              ACCESS  not-accessible
              STATUS  mandatory
              DESCRIPTION
                      "The ICIP Level 2 Interval Table"
              ::= { smdsIomServObjects 10 }

            smdsIomIcipL2IntervalEntry OBJECT-TYPE
              SYNTAX SmdsIomIcipL2IntervalEntry
              ACCESS  not-accessible
              STATUS  mandatory
              DESCRIPTION
                      "An entry in the ICIP Level 2 Interval Table"
              INDEX   { smdsIomIcipL2IntervalIfIndex,
                        smdsIomIcipL2IntervalIntervalIndex }
              ::= { smdsIomIcipL2IntervalTable 1 }

            SmdsIomIcipL2IntervalEntry ::=
              SEQUENCE {
                smdsIomIcipL2IntervalIfIndex
                      INTEGER,
                smdsIomIcipL2IntervalIntervalIndex
                      INTEGER,
                smdsIomIcipL2IntervalTotalOut
                      Gauge,
                smdsIomIcipL2IntervalCongestionDiscards
                      Gauge,
                smdsIomIcipL2IntervalCellInvalidFieldsDiscards
                      Gauge,
                smdsIomIcipL2IntervalSARInvalidFieldsDiscards
                      Gauge,
                smdsIomIcipL2IntervalSARIncorrectFieldsDiscards
                      Gauge,
                smdsIomIcipL2IntervalCRCViolationsDiscards
                      Gauge,
                smdsIomIcipL2IntervalComsEomsDiscards
                      Gauge,
                smdsIomIcipL2IntervalBomsEomsDiscards







                      Gauge,
                smdsIomIcipL2IntervalMRIDiscards
                      Gauge
              }

            smdsIomIcipL2IntervalIfIndex OBJECT-TYPE
              SYNTAX INTEGER (0..65535)
              ACCESS  read-only
              STATUS  mandatory
              DESCRIPTION
                      "The value of this object identifies the ifIndex
                      associated with the ICIP sublayer of the ICI."
              ::= { smdsIomIcipL2IntervalEntry 1 }

            smdsIomIcipL2IntervalIntervalIndex OBJECT-TYPE
              SYNTAX INTEGER (1..8)
              ACCESS  read-only
              STATUS  mandatory
              DESCRIPTION
                      "The value of this object identifies the
                      interval in which the counts occurred.  A value
                      of '1' indicates the most recently completed
                      interval while a value of '8' indicates least
                      recently completed interval."
              ::= { smdsIomIcipL2IntervalEntry 2 }

            smdsIomIcipL2IntervalTotalOut  OBJECT-TYPE
              SYNTAX Gauge
              ACCESS  read-only
              STATUS  mandatory
              DESCRIPTION
                      "The value of this object reflects the number of
                      ICIP L2_PDUs sent across an ICI."
              ::= { smdsIomIcipL2IntervalEntry 3 }

            smdsIomIcipL2IntervalCongestionDiscards OBJECT-TYPE
              SYNTAX Gauge
              ACCESS  read-only
              STATUS  mandatory
              DESCRIPTION
                      "The value of this object reflects the number of
                      ICIP L2_PDUs discarded because an ICI was in
                      congestion."
              ::= { smdsIomIcipL2IntervalEntry 4 }








            smdsIomIcipL2IntervalCellInvalidFieldsDiscards  OBJECT-TYPE
              SYNTAX Gauge
              ACCESS  read-only
              STATUS  mandatory
              DESCRIPTION
                      "The value of this object reflects the number of
                      ICIP L2_PDUs discarded because of invalid fields
                      that occurred at the cell sublayer."
              ::= { smdsIomIcipL2IntervalEntry 5 }

            smdsIomIcipL2IntervalSARInvalidFieldsDiscards  OBJECT-TYPE
              SYNTAX Gauge
              ACCESS  read-only
              STATUS  mandatory
              DESCRIPTION
                      " The value of this object reflects the number
                      of ICIP L2_PDUs discarded because of invalid
                      fields that occurred at the Segmentation and
                      Reassembly (SAR) sublayer."
              ::= { smdsIomIcipL2IntervalEntry  6 }

            smdsIomIcipL2IntervalSARIncorrectFieldsDiscards OBJECT-TYPE
              SYNTAX Gauge
              ACCESS  read-only
              STATUS  mandatory
              DESCRIPTION
                      " The value of this object reflects the number
                      of ICIP L2_PDUs discarded because of incorrect
                      fields that occurred at the SAR sublayer."
              ::= { smdsIomIcipL2IntervalEntry  7 }

            smdsIomIcipL2IntervalCRCViolationsDiscards OBJECT-TYPE
              SYNTAX Gauge
              ACCESS  read-only
              STATUS  mandatory
              DESCRIPTION
                      " The value of this object reflects the number
                      of ICIP L2_PDUs discarded because the payload
                      Cyclic Redundancy Check (CRC) was incorrect."
              ::= { smdsIomIcipL2IntervalEntry  8 }












             smdsIomIcipL2IntervalComsEomsDiscards OBJECT-TYPE
              SYNTAX Gauge
              ACCESS  read-only
              STATUS  mandatory
              DESCRIPTION
                      " The value of this object reflects the number
                      of ICIP L2_PDUs discarded because the sequence
                      number of the Continuation of Message (COM) or
                      End of Message (EOM) was not incremented by 1
                      relative to the previous L2_PDU received with
                      the same Message Identifier (MID)."
              ::= { smdsIomIcipL2IntervalEntry  9 }

            smdsIomIcipL2IntervalBomsEomsDiscards OBJECT-TYPE
              SYNTAX Gauge
              ACCESS  read-only
              STATUS  mandatory
              DESCRIPTION
                      " The value of this object reflects the number
                      of ICIP L3_PDUs discarded because the MID of a
                      Beginning of Message (BOM) was currently active
                      or the MID of an EOM was not currently active."
              ::= { smdsIomIcipL2IntervalEntry  10 }

            smdsIomIcipL2IntervalMRIDiscards OBJECT-TYPE
              SYNTAX Gauge
              ACCESS  read-only
              STATUS  mandatory
              DESCRIPTION
                      " The value of this object reflects the number
                      of ICIP L2_PDUs discarded because of MRI
                      Timeout."
              ::= { smdsIomIcipL2IntervalEntry  11 }



















          -- The Inter-Carrier Interface Protocol (ICIP) Physical Layer
          -- Convergence Procedure (PLCP) Group

          -- Implementation of this group is mandatory for all systems
          -- that perform intercarrier SMDS.

          -- This group consists of 2 tables:
          --    ICIP PLCP Current Table, and
          --    ICIP PLCP Interval Table.
          -- For SMDS XA-OM and ECOM, counts are collected over 15
          -- minute intervals.

          -- ICIP PLCP Current Table
          -- This table contains the current performance counts for the
          -- ICIP PLCP of a given ICI.

          smdsIomIcipPlcpCurrentTable OBJECT-TYPE
              SYNTAX  SEQUENCE OF SmdsIomIcipPlcpCurrentEntry
              ACCESS  not-accessible
              STATUS  mandatory
              DESCRIPTION
                      "The ICIP PLCP Current Table"
              ::= { smdsIomServObjects 11 }

          smdsIomIcipPlcpCurrentEntry OBJECT-TYPE
              SYNTAX SmdsIomIcipPlcpCurrentEntry
              ACCESS  not-accessible
              STATUS  mandatory
              DESCRIPTION
                      "An entry in the ICIP Level 2 Current Table"
              INDEX   { smdsIomIcipPlcpCurrentIfIndex }
              ::= { smdsIomIcipPlcpCurrentTable 1 }

          SmdsIomIcipPlcpCurrentEntry ::=
              SEQUENCE {
                smdsIomIcipPlcpCurrentIfIndex
                      INTEGER,
                smdsIomIcipPlcpCurrentSEFS
                      Gauge,
                smdsIomIcipPlcpCurrentAlarmState
                     INTEGER,
                smdsIomIcipPlcpCurrentUnavailSeconds
                      Gauge
              }








            smdsIomIcipPlcpCurrentIfIndex OBJECT-TYPE
              SYNTAX INTEGER (0..65535)
              ACCESS  read-only
              STATUS  mandatory
              DESCRIPTION
                      "The value of this object identifies the ifIndex
                      associated with the ICIP sublayer of the ICI."
              ::= { smdsIomIcipPlcpCurrentEntry 1 }

          smdsIomIcipPlcpCurrentSEFS  OBJECT-TYPE
              SYNTAX Gauge
              ACCESS  read-only
              STATUS  mandatory
              DESCRIPTION
                      "The value of this object reflects the number of
                      one-second intervals containing one or more
                      Severely Errored Framing (SEF) events."
              ::= { smdsIomIcipPlcpCurrentEntry 2 }

          smdsIomIcipPlcpCurrentAlarmState OBJECT-TYPE
              SYNTAX INTEGER {
                noAlarm (1),
                receivedFarEndAlarm (2),
                incomingLOF (3)
              }
              ACCESS  read-only
              STATUS  mandatory
              DESCRIPTION
                      "The value of this object reflects the alarm
                      state of the ICIP PLCP. The value noAlarm means
                      that there are no alarms present.  The value
                      receivedFarEndAlarm means that the DS3 PLCP
                      received an incoming Yellow Signal.  The value
                      incomingLOF means that the DS3 PLCP has declared
                      a Loss of Frame (LOF) failure condition."
              ::= { smdsIomIcipPlcpCurrentEntry 3 }
















            smdsIomIcipPlcpCurrentUnavailSeconds  OBJECT-TYPE
              SYNTAX Gauge
              ACCESS  read-only
              STATUS  mandatory
              DESCRIPTION
                      "The value of this object reflects the number of
                      seconds during which the PLCP is considered
                      unavailable."
              ::= {smdsIomIcipPlcpCurrentEntry 4 }



          -- ICIP PLCP Interval Table
          -- This table contains the performance counts for
          -- the past 8 intervals of ICIP PLCP of an ICI.
          -- It is possible that less than 8 intervals may be reflected
          -- because the SS or ICI has not been on line
          -- for the entire 2 hours.

            smdsIomIcipPlcpIntervalTable OBJECT-TYPE
              SYNTAX  SEQUENCE OF SmdsIomIcipPlcpIntervalEntry
              ACCESS  not-accessible
              STATUS  mandatory
              DESCRIPTION
                      "The ICIP PLCP Interval Table"
              ::= { smdsIomServObjects 12 }

            smdsIomIcipPlcpIntervalEntry OBJECT-TYPE
              SYNTAX SmdsIomIcipPlcpIntervalEntry
              ACCESS  not-accessible
              STATUS  mandatory
              DESCRIPTION
                      "An entry in the ICIP PLCP Interval Table"
              INDEX   { smdsIomIcipPlcpIntervalIfIndex,
                        smdsIomIcipPlcpIntervalIntervalIndex }
              ::= { smdsIomIcipPlcpIntervalTable 1 }

            SmdsIomIcipPlcpIntervalEntry ::=
              SEQUENCE {
                smdsIomIcipPlcpIntervalIfIndex
                      INTEGER,
                smdsIomIcipPlcpIntervalIntervalIndex
                      INTEGER,
                smdsIomIcipPlcpIntervalSEFS
                      Gauge,







                smdsIomIcipPlcpIntervalUnavailSeconds
                      Gauge
                }

            smdsIomIcipPlcpIntervalIfIndex OBJECT-TYPE
              SYNTAX INTEGER (0..65535)
              ACCESS  read-only
              STATUS  mandatory
              DESCRIPTION
                      "The value of this object identifies the ifIndex
                      associated with the ICIP sublayer of the ICI."
              ::= { smdsIomIcipPlcpIntervalEntry 1 }

            smdsIomIcipPlcpIntervalIntervalIndex OBJECT-TYPE
              SYNTAX INTEGER (1..8)
              ACCESS  read-only
              STATUS  mandatory
              DESCRIPTION
                      "The value of this object identifies the
                      interval in which the counts occurred.  A value
                      of '1' indicates the most recently completed
                      interval while a value of '8' indicates least
                      recently completed interval."
              ::= { smdsIomIcipPlcpIntervalEntry 2 }

            smdsIomIcipPlcpIntervalSEFS  OBJECT-TYPE
              SYNTAX Gauge
              ACCESS  read-only
              STATUS  mandatory
              DESCRIPTION
                      "The value of this object reflects the number of
                      one-second intervals containing one or more
                      Severely Errored Framing (SEF) events."
              ::= { smdsIomIcipPlcpIntervalEntry 3 }

            smdsIomIcipPlcpIntervalUnavailSeconds OBJECT-TYPE
              SYNTAX Gauge
              ACCESS  read-only
              STATUS  mandatory
              DESCRIPTION
                      "The value of this object reflects the number of
                      seconds during which the PLCP is considered
                      unavailable."
              ::= { smdsIomIcipPlcpIntervalEntry 4 }
          END
