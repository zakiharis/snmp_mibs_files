INTEL-ES400-MIB DEFINITIONS ::= BEGIN

--
-- Copyright (C) 1999-2000 Intel Corporation. All rights reserved.
--
-- Notes: Switch MIB for 
--
--   Intel Express 460T Standalone Switch
--   Intel NetStructure(TM) 470T Switch
--   Intel NetStructure(TM) 470F Switch
--

    IMPORTS
        
        enterprises, TimeTicks, Counter, IpAddress FROM RFC1155-SMI
        DisplayString, PhysAddress                 FROM RFC1213-MIB
        OBJECT-TYPE                                FROM RFC-1212
        TRAP-TYPE                                  FROM RFC-1215;
    
    intel                    OBJECT IDENTIFIER     ::= { enterprises 343 }
    mib2ext                  OBJECT IDENTIFIER     ::= { intel 6 }

    es400                    OBJECT IDENTIFIER ::= { mib2ext 17 }
    es400Agent               OBJECT IDENTIFIER ::= { es400 1 }
    es400Chassis             OBJECT IDENTIFIER ::= { es400 2 }
    es400Port                OBJECT IDENTIFIER ::= { es400 3 }
    es400FDb                 OBJECT IDENTIFIER ::= { es400 4 }
    es400LinkAggr            OBJECT IDENTIFIER ::= { es400 5 }
    es400PortMirror          OBJECT IDENTIFIER ::= { es400 6 }
    es400IgmpSnoop           OBJECT IDENTIFIER ::= { es400 7 }
    es400Vlan                OBJECT IDENTIFIER ::= { es400 8 }

    MacAddress      ::= OCTET STRING(SIZE(6))
    PortList        ::= OCTET STRING(SIZE(4))
    VlanIndex       ::= INTEGER

    es400AgentInfo          OBJECT IDENTIFIER ::= { es400Agent 1 }
    
    es400AgentRuntimeSwVersion OBJECT-TYPE
        SYNTAX  DisplayString (SIZE (0..12))
        ACCESS  read-only
        STATUS  mandatory
        DESCRIPTION
            "This is a textual description of the runtime software version and
             revision. If the version number is one and revision number is zero
             es400AgentRuntimeSwVersion would be 'Ver. 1.0'"
        ::= { es400AgentInfo 1 }

    es400AgentPromFwVersion OBJECT-TYPE
        SYNTAX  DisplayString (SIZE (0..12))
        ACCESS  read-only
        STATUS  mandatory
        DESCRIPTION
            "This is a textual description of the agent PROM firmware version
             and revision. If the version number is one and revision number is
             zero es400AgentPromFwVersion would be 'Ver. 1.0'"
        ::= { es400AgentInfo 2 }

    es400AgentHwRevision OBJECT-TYPE
        SYNTAX  INTEGER
        ACCESS  read-only
        STATUS  mandatory
        DESCRIPTION
            "This is a integer number of the hardware revision."
        ::= { es400AgentInfo 3 }
    
    es400AgentMgmtProtocolCapability OBJECT-TYPE
        SYNTAX  INTEGER {   
                    other(1),
                    snmp-ip(2),
                    snmp-ipx(3),
                    snmp-ip-ipx(4)
                }
        ACCESS  read-only
        STATUS  mandatory
        DESCRIPTION
            "The network management protocol(s) supported by this agent."
        ::= { es400AgentInfo 4 }


    es400AgentMibSupportTable OBJECT-TYPE
        SYNTAX  SEQUENCE OF Es400AgentMibSupportEntry
        ACCESS  not-accessible
        STATUS  mandatory
        DESCRIPTION
            "A list of MIB capability entries supported by this agent."    
        ::= { es400AgentInfo 5 }

    es400AgentMibSupportEntry OBJECT-TYPE
        SYNTAX  Es400AgentMibSupportEntry
        ACCESS  not-accessible
        STATUS  mandatory
        DESCRIPTION
            "A MIB capability entry contains objects describing a particular MIB
             supported by this agent."
        INDEX   { es400AgentMibSupportIndex }
        ::= { es400AgentMibSupportTable 1 }

    Es400AgentMibSupportEntry ::= 
        SEQUENCE {
            es400AgentMibSupportIndex
                INTEGER,
            es400AgentMibSupportDescr
                DisplayString,
            es400AgentMibSupportVersion
                INTEGER,
            es400AgentMibSupportType
                INTEGER
        }

    es400AgentMibSupportIndex OBJECT-TYPE
        SYNTAX  INTEGER 
        ACCESS  read-only
        STATUS  mandatory
        DESCRIPTION
            "A list of es400AgentMibSupportDescr entries."
        ::= { es400AgentMibSupportEntry 1 }

    es400AgentMibSupportDescr OBJECT-TYPE
        SYNTAX  DisplayString (SIZE (0..16))
        ACCESS  read-only
        STATUS  mandatory
        DESCRIPTION
            "The name of the MIB supported by the agent."
        ::= { es400AgentMibSupportEntry 2 }

    es400AgentMibSupportVersion OBJECT-TYPE
        SYNTAX  INTEGER 
        ACCESS  read-only
        STATUS  mandatory
        DESCRIPTION
            "The version of the MIB specified in this entry."
        ::= { es400AgentMibSupportEntry 3 }

    es400AgentMibSupportType OBJECT-TYPE
        SYNTAX  INTEGER {
                    other(1),
                    standard(2),
                    proprietary(3),
                    experiment(4)
                }
        ACCESS  read-only
        STATUS  mandatory
        DESCRIPTION
            "The type of the MIB specified in this entry."
        ::= { es400AgentMibSupportEntry 4 }

    es400AgentConfig        OBJECT IDENTIFIER ::= { es400Agent 2 }

    es400AgentSwUpdateMode OBJECT-TYPE
        SYNTAX  INTEGER {
                    other(1),
                    network-load(2),
                    out-of-band-load(3)
                }
        ACCESS  read-write
        STATUS  mandatory
        DESCRIPTION
            "The download media used by the system to download the runtime
             software."
        ::= { es400AgentConfig 1 }

    es400AgentSwUpdateCtrl OBJECT-TYPE
        SYNTAX  INTEGER {
                    other(1),
                    disabled(2),
                    enabled(3)
                }
        ACCESS  read-write
        STATUS  mandatory
        DESCRIPTION
            "Current status of configuration software download control. The setting is 
            effective the next time you reset or power on the hub." 
        ::= { es400AgentConfig 2 }

    es400AgentBootFile OBJECT-TYPE
        SYNTAX  DisplayString  (SIZE (0..64))
        ACCESS  read-write
        STATUS  mandatory
        DESCRIPTION
            "The name of the configuration file to be downloaded from the TFTP server
            when software update is enabled."
        ::= { es400AgentConfig 3 }

    es400AgentFirmwareUpdateCtrl OBJECT-TYPE
        SYNTAX  INTEGER {
                    other(1),
                    disabled(2),
                    enabled(3)
                }
        ACCESS  read-write
        STATUS  mandatory
        DESCRIPTION
            "Current status of firmware software download control. The setting is 
            effective the next time you reset or power on the hub." 
        ::= { es400AgentConfig 4 }

    es400AgentFirmwareFile OBJECT-TYPE
        SYNTAX  DisplayString  (SIZE (0..64))
        ACCESS  read-write
        STATUS  mandatory
        DESCRIPTION
            "The name of the firmware file to be downloaded from the TFTP server 
            when software update is enabled."
        ::= { es400AgentConfig 5 }
    

    es400AgentSystemReset OBJECT-TYPE
        SYNTAX  INTEGER {
                    other(1),
                    cold-start(2),
                    warm-start(3),
                    no-reset(4)
                }
        ACCESS  read-write
        STATUS  mandatory
        DESCRIPTION
            "This object indicates the agent system reset state. Setting this
             object to no-reset(4) has no effect. Setting this object to
             cold-start(2) or warm-start(3) will reset the agent. The agent 
             always returns no-reset(4) when this object is read."
        ::= { es400AgentConfig 6 }

    es400AgentRs232PortConfig OBJECT-TYPE
        SYNTAX  INTEGER  {
                    other(1),
                    console(2),
                    out-of-band(3)
                }
        ACCESS  read-write
        STATUS  mandatory
        DESCRIPTION
            "This object indicates the RS-232C mode while device restart."
        ::= { es400AgentConfig 7 }

    es400AgentOutOfBandBaudRateConfig OBJECT-TYPE
        SYNTAX  INTEGER {
                    other(1),
                    baudRate-2400 (2),
                    baudRate-9600 (3),
                    baudRate-19200(4),
                    baudRate-38400(5)
                }
        ACCESS  read-write
        STATUS  mandatory
        DESCRIPTION
            "This object indicates the out_of_band baud rate while device
             restart."
        ::= { es400AgentConfig 8 }

    
    es400AgentIpConfig      OBJECT IDENTIFIER ::= { es400Agent 3 }

    es400AgentIpNumOfIf OBJECT-TYPE
        SYNTAX  INTEGER
        ACCESS  read-only
        STATUS  mandatory
        DESCRIPTION
            "The total number of IP interfaces supported by this agent."
        ::= {  es400AgentIpConfig 1 }

    es400AgentIpIfTable OBJECT-TYPE
        SYNTAX  SEQUENCE OF Es400AgentIpIfEntry
        ACCESS  not-accessible
        STATUS  mandatory
        DESCRIPTION
            "A list of IP interface entries supported by the agent."
        ::= {  es400AgentIpConfig 2 }

    es400AgentIpIfEntry OBJECT-TYPE
        SYNTAX  Es400AgentIpIfEntry
        ACCESS  not-accessible
        STATUS  mandatory
        DESCRIPTION
            "An es400AgentIPIfEntry contains information about a particular IP
             interface."
        INDEX   { es400AgentIpIfIndex }
        ::= { es400AgentIpIfTable 1 }

    Es400AgentIpIfEntry ::= 
        SEQUENCE {
            es400AgentIpIfIndex
                INTEGER,
            es400AgentIpIfAddress 
                IpAddress,
            es400AgentIpIfNetMask
                IpAddress,
            es400AgentIpIfDefaultRouter
                IpAddress,
            es400AgentIpIfMacAddr
                PhysAddress,
            es400AgentIpIfType
                INTEGER                                                   
        }

    es400AgentIpIfIndex OBJECT-TYPE
        SYNTAX  INTEGER (1..255)
        ACCESS  read-only
        STATUS  mandatory
        DESCRIPTION
            "This object uniquely identifies the IP interface number in the
             es400AgentIpIfTable. This value should never greater than es400AgentIpNumOfIf"
        ::= {  es400AgentIpIfEntry 1 }

    es400AgentIpIfAddress OBJECT-TYPE
        SYNTAX  IpAddress
        ACCESS  read-write
        STATUS  mandatory
        DESCRIPTION
            "The IP address of the interface."
        ::= {  es400AgentIpIfEntry 2 }

    es400AgentIpIfNetMask OBJECT-TYPE
        SYNTAX  IpAddress
        ACCESS  read-write
        STATUS  mandatory
        DESCRIPTION
            "The IP net mask for this interface."
        ::= {  es400AgentIpIfEntry 3 }

    es400AgentIpIfDefaultRouter OBJECT-TYPE
        SYNTAX  IpAddress
        ACCESS  read-write
        STATUS  mandatory
        DESCRIPTION
            "The default gateway for this IP interface."
        ::= {  es400AgentIpIfEntry 4 }

    es400AgentIpIfMacAddr OBJECT-TYPE
        SYNTAX  PhysAddress
        ACCESS  read-only
        STATUS  mandatory
        DESCRIPTION
            "The MAC address of this IP interface. For interfaces which do not
             have such an address. (e.g., a serial line), this object should
             contain an octet string of zero length."
        ::= {  es400AgentIpIfEntry 5 }

    es400AgentIpIfType OBJECT-TYPE
        SYNTAX  INTEGER {
                    other(1),          -- none of the following
                    ethernet-csmacd(6),
                    slip(28)           -- generic SLIP
                }
        ACCESS  read-only
        STATUS  mandatory
        DESCRIPTION
            "The physical layer interface of the IP interface."
        ::= {  es400AgentIpIfEntry 6 }

    es400AgentIpBootServerAddr OBJECT-TYPE
        SYNTAX  IpAddress
        ACCESS  read-write
        STATUS  mandatory
        DESCRIPTION
            "The IP Address of Boot Server."
        ::= {  es400AgentIpConfig 3 }

    es400AgentIpGetIpFromBootpServer OBJECT-TYPE
        SYNTAX  INTEGER {
                    other(1),
                    disabled(2),
                    enabled(3)
                }
        ACCESS  read-write
        STATUS  mandatory
        DESCRIPTION
            "This object indicates whether the agent get its system IP address
             from Bootp server at start up."
        ::= { es400AgentIpConfig 4 }

    es400AgentIpUnauthAddr OBJECT-TYPE
        SYNTAX  IpAddress
        ACCESS  read-only
        STATUS  mandatory
        DESCRIPTION
            "The IP address of an unauthorized SNMP packet."
        ::= { es400AgentIpConfig 5 }

    es400AgentIpUnauthComm OBJECT-TYPE
        SYNTAX  DisplayString (SIZE (0..40))
        ACCESS  read-only
        STATUS  mandatory
        DESCRIPTION
            "The community string of an unauthorized SNMP packet."
        ::= { es400AgentIpConfig 6 }

    es400AgentIpLastBootServerAddr OBJECT-TYPE
        SYNTAX  IpAddress
        ACCESS  read-only
        STATUS  mandatory
        DESCRIPTION
           "The last IP address used as Boot server IP address."
        ::= {  es400AgentIpConfig 7 }

    es400AgentIpLastIpAddr OBJECT-TYPE
        SYNTAX  IpAddress
        ACCESS  read-only
        STATUS  mandatory
        DESCRIPTION
            "The last IP address used as the agent system IP address."
        ::= {  es400AgentIpConfig 8 }

    es400AgentTrapAddressTable OBJECT-TYPE
        SYNTAX  SEQUENCE OF Es400AgentTrapAddressEntry
        ACCESS  not-accessible
        STATUS  mandatory
        DESCRIPTION
            "A list of trap manager entries to which to send SNMP traps ."
        ::= { es400Agent 4 }

    es400AgentTrapAddressEntry OBJECT-TYPE
        SYNTAX  Es400AgentTrapAddressEntry
        ACCESS  not-accessible
        STATUS  mandatory
        DESCRIPTION
            "This entry contains the particular trap manager settings."
        INDEX   { es400AgentTrapIndex }
        ::= { es400AgentTrapAddressTable 1 }

    Es400AgentTrapAddressEntry ::= 
        SEQUENCE {
            es400AgentTrapIndex
                INTEGER,
            es400AgentTrapAddressIp
                IpAddress,
            es400AgentTrapAddressComm
                DisplayString,
            es400AgentTrapAddressStatus
                INTEGER
        }
        
    es400AgentTrapIndex OBJECT-TYPE
        SYNTAX  INTEGER
        ACCESS  read-only
        STATUS  mandatory
        DESCRIPTION
            "The table index to receive SNMP traps from this device."
        ::= { es400AgentTrapAddressEntry 1 }    

    es400AgentTrapAddressIp OBJECT-TYPE
        SYNTAX  IpAddress
        ACCESS  read-write
        STATUS  mandatory
        DESCRIPTION
            "The IP address to receive SNMP traps from this device."
        ::= { es400AgentTrapAddressEntry 2 }

    es400AgentTrapAddressComm OBJECT-TYPE
        SYNTAX  DisplayString (SIZE (0..40))
        ACCESS  read-write
        STATUS  mandatory
        DESCRIPTION
            "The community string of the SNMP trap packet sent to the trap
             manager."
        ::= { es400AgentTrapAddressEntry 3 }

    es400AgentTrapAddressStatus OBJECT-TYPE
        SYNTAX  INTEGER {
                    other(1),
                    disabled(2),
                    enabled(3)
                }
        ACCESS  read-write
        STATUS  mandatory
        DESCRIPTION
            "This object indicates whether or not the trap should be send to
             this trap manager."
        ::= { es400AgentTrapAddressEntry 4 }


    es400ChassisInfo               OBJECT IDENTIFIER ::= { es400Chassis 1 }

    es400ChassisInfoSystemUpTime OBJECT-TYPE
        SYNTAX TimeTicks
        ACCESS read-only
        STATUS mandatory
        DESCRIPTION
            "The value of sysUpTime at the time the switch entered its 
            current operational state. If the current state was entered 
            prior to the last re-initialization, then this object contains
            a zero value. This value is in units of seconds."
        ::= { es400ChassisInfo 1 }

    es400ChassisInfoTotalNumOfPort OBJECT-TYPE
        SYNTAX INTEGER
        ACCESS read-only
        STATUS mandatory
        DESCRIPTION
            "The number of ports within this switch. This value is the sum
             of the ports within this switch."
        ::= { es400ChassisInfo 2 }

    es400ChassisInfoNumOfPortInUse OBJECT-TYPE
        SYNTAX INTEGER
        ACCESS read-only
        STATUS mandatory
        DESCRIPTION
            "The number of ports in this switch connected to the segment or
             the end stations."
        ::= { es400ChassisInfo 3 }

    es400ChassisInfoConsoleInUse   OBJECT-TYPE
        SYNTAX INTEGER {
               other(1),
               in-use(2),
               not-in-use(3)
               }
        ACCESS read-only
        STATUS mandatory
        DESCRIPTION
            "This usage indication of console system."
        ::= { es400ChassisInfo 4 }

    es400ChassisInfoFrontPanelLedStatus OBJECT-TYPE
        SYNTAX OCTET STRING (SIZE (0..127))
        ACCESS read-only
        STATUS mandatory
        DESCRIPTION
            "This object is a set of LED indications. The first two octets is 
             defined as system LED. The first LED is power LED. The second LED
             is status LED. The other octets following the second octets
             are the port LED. Every two bytes are presented to a port. The first
             byte is presentd to the Link/Activity LED. The second byte is presented
             to the Speed LED.
             
             There is one byte per LED.

             The most significant bit is used for blink/solid:
                Off = The LED is lit permanently.
                On = The LED blinks.

             The three least significant bits are used for color:
                1 = not lit,
                2 = green,
                3 = yellow,(orange)
                4 = blue,
                5 = red,
                0+6+7 not used

             The four remaining bits are currently unused and must be 0."
        ::= { es400ChassisInfo 5 }

    es400ChassisInfoSaveCfg OBJECT-TYPE
        SYNTAX INTEGER {
               other(1),
               proceeding(2),
               completed(3),
               changed-not-save(4),
               failed(5)
               }
        ACCESS read-only
        STATUS mandatory
        DESCRIPTION
            "This object indicates the status of the device configuration.
            
            other(1) - this entry is currently in use but the conditions 
                     under which it will remain so are different from each 
                     of the following values.
            proceeding(2) - the device configuration is saving into the NV-RAM.
            completed(3) - all of the device configuration parameters have been
                     saved into NV-RAM.
            changed-not-save - some of the device configuration parameters have
                     been changed but not saved into NV-RAM.
            failed(5) - The processing of saving device configuration is failed."
        ::= { es400ChassisInfo 6 }

    es400ChassisConfig               OBJECT IDENTIFIER ::= { es400Chassis 2 }

    es400ChassisConfigStpState OBJECT-TYPE
        SYNTAX INTEGER {
               other(1),
               disabled(2),
               enabled(3)
               }
        ACCESS read-write
        STATUS mandatory
        DESCRIPTION
            "This object can be enabled or disabled spanning tree algorithm
             during runtime of the system.When the device is in 802.1Q Vlan
             mode, this object will be enabled and cannot be disabled."
        ::= { es400ChassisConfig 1 }

    es400ChassisConfigIGMPCaptureState OBJECT-TYPE
        SYNTAX INTEGER {
               other(1),
               disabled(2),
               enabled(3)
               }
        ACCESS read-write
        STATUS mandatory
        DESCRIPTION
            "This object indicates Internet Group Management Protocol (IGMP) capture
             function is enabled or disabled."
        ::= { es400ChassisConfig 2 }

    es400ChassisConfigPartitionModeState OBJECT-TYPE
        SYNTAX INTEGER {
               other(1),
               disabled(2),
               enabled(3)
               }
        ACCESS read-write
        STATUS mandatory
        DESCRIPTION
            "This object used to enable or disable port auto partition. When the
             object apply for all ports of the device"
        ::= { es400ChassisConfig 3 }

    es400ChassisConfigTableLockState OBJECT-TYPE
       SYNTAX  INTEGER {
               other(1),
               disabled(2),
               enabled(3)
               }
       ACCESS  read-write
       STATUS  mandatory
       DESCRIPTION
           "This object indicates whether the address table is locked.
           In other words, the address table doesn't learn any more new address.
           The aging timer is suspended when the address table is locked. As long
           as the table is locked, all of the frames are dropped if the destination
           can not be found in the address."
       ::= { es400ChassisConfig 4 }

    es400ChassisConfigSaveCfg OBJECT-TYPE
        SYNTAX INTEGER
        ACCESS write-only
        STATUS mandatory
        DESCRIPTION
            "As the object is set, the current device configuration is save 
             into to NV-RAM."
        ::= { es400ChassisConfig 5 }

    es400ChassisConfigHOLState OBJECT-TYPE
        SYNTAX INTEGER {
               other(1),
               disabled(2),
               enabled(3)
               }
        ACCESS read-write
        STATUS mandatory
        DESCRIPTION
            "The object provides a way to prevent HOL (Head Of Line) blocking
            between ports. HOL protection may prevent forwarding a packet to
            a blocking port.The idea relies on the assumption that it is better
            to discard packets destined to blocking ports, then to let them consume
            more and more buffers in the input-port's Rx-counters because eventually 
            these input ports may become totally blocked. The meanings of the values
            are:

            other(1) - this entry is currently in use but the conditions under
                which it will remain so are different from each of the following
                values.
            disabled(2) - HOL function disable for device.
            enabled(3) - HOL function enable for device." 
        ::= { es400ChassisConfig 6 }

    es400ChassisConfigAddrLookupModes OBJECT-TYPE
        SYNTAX INTEGER {
               other(1),
               sequential-mode(2),
               random-mode(3)
               }
        ACCESS read-write
        STATUS mandatory
        DESCRIPTION
            "The object provides a way to select the algorithm that optimizes the lookup
            depending on the network configuration. The setting will be effective after
            next system reboot.

            The meanings of the values are:

            other(1) - this entry is currently in use but the conditions under
                which it will remain so are different from each of the following
                values.
            sequential-mode(2) - Uses MAC address, optimized for sequential address (basic mode
                or tag mode).
            random-mode(3) - Uses MAC address, optimized for random address (basic mode or tag
                mode)."
        ::= { es400ChassisConfig 7 }

    es400ChassisConfigUploadImageFileName OBJECT-TYPE
        SYNTAX  DisplayString  (SIZE (0..64))
        ACCESS  read-write
        STATUS  mandatory
        DESCRIPTION
            "The name of the image file to be uploaded from the device to TFTP server 
             when enabling image upload function (by writing es400ChassisConfigUploadImage)."
        ::= { es400ChassisConfig 8 }

    es400ChassisConfigUploadImage OBJECT-TYPE
        SYNTAX  INTEGER
        ACCESS  write-only
        STATUS  mandatory
        DESCRIPTION
            "Image file upload control. Writing it by any value will
             immediately invoke image upload function." 
        ::= { es400ChassisConfig 9 }

    es400ChassisConfigHighPriorityServiceRatio OBJECT-TYPE
        SYNTAX INTEGER {
               other(1),
               pkt-1high-1low(2),
               pkt-4high-1low(3),
               pkt-8high-1low(4),
               pkt-12high-1low(5),
               all-high-before-low(6)
               }
        ACCESS read-write
        STATUS mandatory
        DESCRIPTION
            "The object provides a way to select an internal round-robin priority
             weight between low-priority queue and high-priority queue.

             The meanings of the values are:

             other(1) - this entry is currently in use but the conditions under
                  which it will remain so are different from each of the following
                  values.
             pkt-1high-1low(2) - 1 pkt transmitted from HIGH, 1 pkt from LOW.
             pkt-4high-1low(3) - 4 pkt transmitted from HIGH, 1 pkt from LOW.
             pkt-8high-1low(4) - 8 pkt transmitted from HIGH, 1 pkt from LOW.
             pkt-12high-1low(5) - 12 pkt transmitted from HIGH, 1 pkt from LOW.
             all-high-before-low(6) - all pkt transmitted from HIGH, 0 pkt from LOW.
                  LOW will be served only if HIGH is empty. If HIGH queue is emptied
                  before finishing the count, the count will be reset until next 
                  first HIGH comes in." 
        ::= { es400ChassisConfig 10 }

    es400ChassisAlarm              OBJECT IDENTIFIER ::= { es400Chassis 3 }

    es400ChassisAlarmPartition OBJECT-TYPE
        SYNTAX INTEGER {
               other(1),
               disabled(2),
               enabled(3)
               }
        ACCESS read-write
        STATUS mandatory
        DESCRIPTION
            "Depending on this object, the device send a trap or not when
            any one of the device's ports was partitioned."
       ::= { es400ChassisAlarm 1 } 

    es400ChassisAlarmNewRoot OBJECT-TYPE
        SYNTAX INTEGER {
               other(1),
               disabled(2),
               enabled(3)
               }
        ACCESS read-write
        STATUS mandatory
        DESCRIPTION
            "When the device has become the new root of the Spanning Tree, this
             object decide whether to send a new root trap."
        ::= { es400ChassisAlarm 2 }

    es400ChassisAlarmTopologyChange OBJECT-TYPE
        SYNTAX INTEGER {
               other(1),
               disabled(2),
               enabled(3)
               }
        ACCESS read-write
        STATUS mandatory
        DESCRIPTION
            "This object determine to send a trap or not when the switch topology
             was changed. If the object is enabled(3), the topologyChange trap is
             sent by the device when any of its configured ports transitions from
             the Learning state to the Forwarding state, or from the Forwarding state
             to the Blocking state. For the same port tranition, the device doesn't
             send the trap if this object value is disabled or other."
        ::= { es400ChassisAlarm 3 }

    es400ChassisAlarmLinkChange OBJECT-TYPE
        SYNTAX INTEGER {
               other(1),
               disabled(2),
               enabled(3)
               }
        ACCESS read-write
        STATUS mandatory
        DESCRIPTION
            "This object determine to send a trap or not when the link 
             was changed. If the object is enabled(3), the Link Change trap is
             sent by the device when any of its ports link change. The device doesn't
             send the trap if this object value is disabled or other."
        ::= { es400ChassisAlarm 4 }

    es400PortInfoTable OBJECT-TYPE
        SYNTAX  SEQUENCE OF Es400PortInfoEntry
        ACCESS  not-accessible
        STATUS  mandatory
        DESCRIPTION
            "A table that contains information about every port."
        ::= { es400Port 1 }

    es400PortInfoEntry OBJECT-TYPE
        SYNTAX  Es400PortInfoEntry
        ACCESS  not-accessible
        STATUS  mandatory
        DESCRIPTION
            "A list of information for each port of the device."
        INDEX   { es400PortInfoIndex }
        ::= { es400PortInfoTable 1 }

    Es400PortInfoEntry ::= 
        SEQUENCE {
            es400PortInfoIndex
                INTEGER,
            es400PortInfoType
                INTEGER,
            es400PortInfoLinkStatus
                INTEGER,
            es400PortInfoNwayStatus
                INTEGER,
            es400PortInfoFlowCtrlStatus
                INTEGER
        }

    es400PortInfoIndex OBJECT-TYPE
        SYNTAX INTEGER
        ACCESS read-only
        STATUS mandatory
        DESCRIPTION
            "This object indicates switch port number.(1..Max port number)"
        ::= { es400PortInfoEntry 1 }

    es400PortInfoType OBJECT-TYPE
        SYNTAX INTEGER {
               other(1),
               portType-UTP(2),
               portType-AUI(3),
               portType-Fiber(4),
               portType-BNC(5)
               }
        ACCESS read-only
        STATUS mandatory
        DESCRIPTION
            "This object indicates the connector type of this port."
        ::= { es400PortInfoEntry 2 }

    es400PortInfoLinkStatus OBJECT-TYPE
        SYNTAX INTEGER {
               other(1),
               link-pass(2),
               link-fail(3)
               }
        ACCESS read-only
        STATUS mandatory
        DESCRIPTION
            "This object indicates the port link status."
        ::= { es400PortInfoEntry 3 }

    es400PortInfoNwayStatus OBJECT-TYPE
        SYNTAX INTEGER {
               other(1),
               half-10Mbps(2),
               full-10Mbps(3),
               half-100Mbps(4),
               full-100Mbps(5),
               half-1Gigabps(6),
               full-1Gigabps(7)
               }
        ACCESS read-only
        STATUS mandatory
        DESCRIPTION
            "This object indicates the port speed and duplex mode."
        ::= { es400PortInfoEntry 4 }

    es400PortInfoFlowCtrlStatus OBJECT-TYPE
        SYNTAX INTEGER {
               other(1),
               flowctrl-disabled(2),
               flowctrl-enabled(3),
               backpressure-disabled(4),
               backpressure-enabled(5)
               }
        ACCESS read-only
        STATUS mandatory
        DESCRIPTION
            "This object indicates the port flow control status."
        ::= { es400PortInfoEntry 5 }

    es400PortConfigTable OBJECT-TYPE
        SYNTAX SEQUENCE OF Es400PortConfigEntry
        ACCESS not-accessible
        STATUS mandatory
        DESCRIPTION
            "A table that contains control information about every port."
        ::= { es400Port 2 }

    es400PortConfigEntry OBJECT-TYPE
        SYNTAX Es400PortConfigEntry
        ACCESS not-accessible
        STATUS mandatory
        DESCRIPTION
            "A list of control information for each port of the device."
        INDEX  { es400PortConfigIndex }
        ::= { es400PortConfigTable 1 }

    Es400PortConfigEntry ::= 
        SEQUENCE {
            es400PortConfigIndex
                INTEGER,
            es400PortConfigAdminState
                INTEGER,
            es400PortConfigLinkStatusAlarmState
                INTEGER,
            es400PortConfigNwayState
                INTEGER,
            es400PortConfigFlowCtrlState
                INTEGER,
            es400PortConfigBackPressState
                INTEGER,
            es400PortConfigLockState
                INTEGER,
            es400PortConfigPriority
                INTEGER,
            es400PortConfigStpState
                INTEGER,
            es400PortConfigHOLState
                INTEGER,
            es400PortConfigBroadcastStormThr
                INTEGER,
            es400PortConfigBroadcastStormCtrl
                INTEGER,
            es400PortConfigCleanAllStatisticCounter
                INTEGER
        }

    es400PortConfigIndex OBJECT-TYPE
        SYNTAX INTEGER
        ACCESS read-only
        STATUS mandatory
        DESCRIPTION
            "This object indicates the device port number.(1..Max port number)"
        ::= { es400PortConfigEntry 1 }

    es400PortConfigAdminState OBJECT-TYPE
        SYNTAX INTEGER {
               other(1),
               disabled(2),
               enabled(3)
               }
        ACCESS read-write
        STATUS mandatory
        DESCRIPTION
            "This object decide the port enabled or disabled."
        ::= { es400PortConfigEntry 2 }

    es400PortConfigLinkStatusAlarmState OBJECT-TYPE
        SYNTAX INTEGER {
               other(1),
               disabled(2),
               enabled(3)
               }
        ACCESS read-write
        STATUS mandatory
        DESCRIPTION
            "Depending on this object to determine to send a trap or
            not when link status changes ."
        ::= { es400PortConfigEntry 3 }
 
    es400PortConfigNwayState OBJECT-TYPE
        SYNTAX INTEGER {
               other(1),
               nway-enabled(2),
               nway-disabled-10Mbps-Half(3),
               nway-disabled-10Mbps-Full(4),
               nway-disabled-100Mbps-Half(5),
               nway-disabled-100Mbps-Full(6),
               nway-disabled-1Gigabps-Half(7),
               nway-disabled-1Gigabps-Full(8)
               }
        ACCESS read-write
        STATUS mandatory
        DESCRIPTION
            "Chose the port speed, duplex mode, and N-Way function mode."
        ::= { es400PortConfigEntry 4 }

    es400PortConfigFlowCtrlState OBJECT-TYPE
        SYNTAX INTEGER {
               other(1),
               disabled(2),
               enabled(3)
               }
        ACCESS read-write
        STATUS mandatory
        DESCRIPTION
            "Set IEEE 802.3x compliant flow control function as enabled or disabled.
             And IEEE 802.3x compliant flow control function work only when the port
             is in full duplex mode.If the port is set Auto-negotiation enabled, the 
             object stands for flow control capability. The results should be referred 
             to es400PortInfoFlowCtrlStatus object. If the port is in force mode, 
             this objects is simply used to set the flow control state (on/off). In 
             force mode, if you change it from enabled to disabled state, it will work
             after next system restart. But the flow control changing from disabled to
             enabled state, it will immediately work."
        ::= { es400PortConfigEntry 5 }

    es400PortConfigBackPressState OBJECT-TYPE
        SYNTAX INTEGER {
               other(1),
               disabled(2),
               enabled(3)
               }
        ACCESS read-write
        STATUS mandatory
        DESCRIPTION
            "Depending on this object determine to enable or disable the 
             backpressure function when the port is working in half duplex mode."
        ::= { es400PortConfigEntry 6 }

    es400PortConfigLockState OBJECT-TYPE
        SYNTAX INTEGER {
               other(1),
               disable(2),
               enable(3)
               }
        ACCESS read-write
        STATUS mandatory
        DESCRIPTION
            "The state of this entry.  When the es400ChassisConfigTableLockState
             object is enabled, the state is not changed. The meanings of the
             values are:

            other(1)   - this entry is currently in use but the conditions under
                         which it will remain so are different from each of the 
                         following values.
            disable(2) - Port lock funtion disable.
            enable(3) -  Locking a port. Once the port is locked, it will not
                         learn new SA addresses, and drop unknown/moved-SA packets
                         forwarding to/from such ports. This is a way to prevent
                         undesired traffic from being received or transmmited on
                         the port. Note that locking a port doesn't lock the MAC
                         address entries associated with the locked port, i.e. the
                         existing address entries of the locked port will be age
                         out even though it is locked."
        ::= { es400PortConfigEntry 7 }

    es400PortConfigPriority OBJECT-TYPE
        SYNTAX INTEGER {
               other(1),
               default(2),
               force-low-priority(3),
               force-high-priority(4)
               }
        ACCESS read-write
        STATUS mandatory
        DESCRIPTION
            "The priority queueing for packets received on this port, except for
            BPDU/IGMP packets and packets with unknown unicast destination address.
            IGMP and BPDU packets are always routed with high priority; packets with 
            unknown unicast destination addresses are always routed with low priority.
            Other packets follow the rules below:

            other(1)   - this entry is currently in use but the conditions under
                         which it will remain so are different from each of the 
                         following values.
                         
            default(2) - A packet is normally classified as low priority
                         ,unless at least one of the following is true:
                         
                         .The packet contained a TAG (per 802.1Q definition) with the 
                          priority greater or equal to 4.
                         .The address-table entry for the destination address had Pd=HIGH.
                         
            force-low_priority(3) - A packet is normally classified as low priority.
            force-high_priority(4) - A packet is normally classified as high
                                     priority."
        ::= { es400PortConfigEntry 8 }

    es400PortConfigStpState OBJECT-TYPE
        SYNTAX INTEGER {
               other(1),
               disabled(2),
               enabled(3)
               }
        ACCESS read-write
        STATUS mandatory
        DESCRIPTION
            "The state of STP(spanning tree algorithm) operation on this port. That's
            meaning the port whether add in the STP. The value enabled(3) indicates 
            that STP is enabled on this port, as long as es400ChassisConfigStpState
            is also enabled for this device.When disabled(2) but es400ChassisConfigStpState
            is still enabled for the device, STP is disabled on this port : any BPDU 
            packets received will be discarded and no BPDU packets will be propagated
            from the port.When the device is in 802.1Q Vlan mode, this object will be
            enabled and cannot be disabled."
        ::= { es400PortConfigEntry 9 }

    es400PortConfigHOLState OBJECT-TYPE
        SYNTAX INTEGER {
               other(1),
               disabled(2),
               enabled(3)
               }
        ACCESS read-write
        STATUS mandatory
        DESCRIPTION
            "The object provides a way to prevent HOL (Head Of Line) blocking
            between ports. HOL protection may prevent forwarding a packet to
            a blocking port.The idea relies on the assumption that it is better
            to discard packets destined to blocking ports, then to let them consume
            more and more buffers in the input-port's Rx-counters because eventually 
            these input ports may become totally blocked. The value enabled(3)
            indicates that HOL function is enabled on this port, as long as 
            es400ChassisConfigHOLState is also enabled for this device. When 
            disabled(2) but es400ChassisConfigHOLState is still enabled for the
            device, HOL function is disabled on this port. The meanings of the 
            values are:

            other(1) - this entry is currently in use but the conditions under
                which it will remain so are different from each of the following
                values.
            disabled(2) - HOL function disable.
            enabled(3) - HOL function enable." 
        ::= { es400PortConfigEntry 10 }

    es400PortConfigBroadcastStormThr OBJECT-TYPE
        SYNTAX INTEGER
        ACCESS read-write
        STATUS mandatory
        DESCRIPTION
            "This object contains the setting of the broadcast storm threshold
             control on each port. The threshold value is represented by the
             percentage of the port's total bandwidth used by broadcast traffic.
             The broadcast storm control function is enabled/disabled by
             es400PortConfigBroadcastStormCtrl object. When broadcast storm control
             function is enabled, if broadcast traffic for a port rises above the
             threshold, the port will be blocked and a trap is sent to management
             user. When the broadcast storm traffic falls below the threshold, the
             blocked port will forward packets again and a trap is sent to management
             user too. The maximum value is 20"
        ::= { es400PortConfigEntry 11 }

    es400PortConfigBroadcastStormCtrl OBJECT-TYPE
        SYNTAX INTEGER {
               other(1),
               disabled(2),
               enabled(3)
               }
        ACCESS read-write
        STATUS mandatory
        DESCRIPTION
            "This object indicates whether to enable the broadcast storm control.
             Refer to es400PortConfigBroadcastStormThr for details.
           
             other(1) - this entry is currently in use but the conditions under
                which it will remain so are different from each of the following
                values.
             disabled(2) - disable the broadcast storm control function .
             enabled(3) - enable the broadcast storm control function ."
        ::= { es400PortConfigEntry 12 }

    es400PortConfigCleanAllStatisticCounter OBJECT-TYPE
        SYNTAX INTEGER
        ACCESS write-only
        STATUS mandatory
        DESCRIPTION
            "Setting this object will reset current device's all statistic counters."
        ::= { es400PortConfigEntry 13 }

    es400PortStatTable OBJECT-TYPE
        SYNTAX SEQUENCE OF Es400PortStatEntry
        ACCESS not-accessible
        STATUS mandatory
        DESCRIPTION
            "A list of port statistic Counter entries."
        ::= { es400Port 3 }

    es400PortStatEntry OBJECT-TYPE
        SYNTAX Es400PortStatEntry
        ACCESS not-accessible
        STATUS mandatory
        DESCRIPTION
            "This entry include all the port statistic Counter which support
            by the device, like Bytes received, Bytes Sent ..."
        INDEX  { es400PortStatIndex }
        ::= { es400PortStatTable 1 }

    Es400PortStatEntry ::= 
        SEQUENCE {
            es400PortStatIndex
                INTEGER,
            es400PortStatByteRx
                Counter,
            es400PortStatByteTx
                Counter,
            es400PortStatFrameRx
                Counter,
            es400PortStatFrameTx
                Counter,
            es400PortStatTotalBytesRx
                Counter,
            es400PortStatTotalFramesRx
                Counter,
            es400PortStatBroadcastFramesRx
                Counter,
            es400PortStatMulticastFramesRx
                Counter,
            es400PortStatCRCError
                Counter,
            es400PortStatOversizeFrames
                Counter,
            es400PortStatFragments
                Counter,
            es400PortStatJabber
                Counter,
            es400PortStatCollision
                Counter,
            es400PortStatLateCollision
                Counter,
            es400PortStatFrames-64-bytes
                Counter,
            es400PortStatFrames-65-127-bytes
                Counter,
            es400PortStatFrames-128-255-bytes
                Counter,
            es400PortStatFrames-256-511-bytes
                Counter,
            es400PortStatFrames-512-1023-bytes
                Counter,
            es400PortStatFrames-1024-1536-bytes
                Counter,
            es400PortStatFramesDroppedFrames
                Counter,
            es400PortStatMulticastFramesTx
                Counter,
            es400PortStatBroadcastFramesTx
                Counter,
            es400PortStatUndersizeFrames
                Counter
        }

    es400PortStatIndex OBJECT-TYPE
        SYNTAX INTEGER
        ACCESS read-only
        STATUS mandatory
        DESCRIPTION
            "This object indicates the device port number.(1..Max port number)"
        ::= { es400PortStatEntry 1 }

    es400PortStatByteRx OBJECT-TYPE
        SYNTAX Counter
        ACCESS read-only
        STATUS mandatory
        DESCRIPTION
            "es400ChassisConfigCounterMode = 2(switched-frames):This counter is incre-
            mented once for every data octet of good packets(unicast + multi-
            cast + broadcast) received.
            
             es400ChassisConfigCounterMode = 3(all-frames):This counter is incremented
            once for every data octet of good packets(unicast + multicast + 
            broadcast packets) and for local and dropped packets."
        ::= { es400PortStatEntry 2 }

    es400PortStatByteTx OBJECT-TYPE
        SYNTAX Counter
        ACCESS read-only
        STATUS mandatory
        DESCRIPTION
            "This counter is incremented once for every data octet of a trans-
            mitted good packet."
        ::= { es400PortStatEntry 3 }

    es400PortStatFrameRx OBJECT-TYPE
        SYNTAX Counter
        ACCESS read-only
        STATUS mandatory
        DESCRIPTION
            "es400ChassisConfigCounterMode = 2(switched-frames):This counter is incre-
            mented once for every good packet(unicast + multicast + broadcast
            ) received.
            
             es400ChassisConfigCounterMode = 3(all-frames):This counter is incremented
            once for every good packet(unicast + multicast + broadcast packets)
            and for local and dropped packets received."
        ::= { es400PortStatEntry 4 }

    es400PortStatFrameTx OBJECT-TYPE
        SYNTAX Counter
        ACCESS read-only
        STATUS mandatory
        DESCRIPTION
            "This counter is incremented once for every transmitted good packet."
        ::= { es400PortStatEntry 5 }

    es400PortStatTotalBytesRx OBJECT-TYPE
        SYNTAX Counter
        ACCESS read-only
        STATUS mandatory
        DESCRIPTION
            "This counter is incremented once for every data octet of all 
            received packets. This include data octets of rejected and local
            packets which are not forwarded to the switching core for trans-
            mission. This counter should reflect all the data octets received 
            on the line. Note: A nibble is not counted as a whole byte."
        ::= { es400PortStatEntry 6 }

    es400PortStatTotalFramesRx OBJECT-TYPE
        SYNTAX Counter
        ACCESS read-only
        STATUS mandatory
        DESCRIPTION
            "This counter is incremented once for every received packets. This
            include rejected and local packets which are not forwarded to the
            switching core for transmission. This counter should reflect all
            packets received on the line."
        ::= { es400PortStatEntry 7 }

    es400PortStatBroadcastFramesRx OBJECT-TYPE
        SYNTAX Counter
        ACCESS read-only
        STATUS mandatory
        DESCRIPTION
            "es400ChassisConfigCounterMode = 2(switched-frames):This counter is incre-
            mented once for every good broadcast packet received.
            
             es400ChassisConfigCounterMode = 3(all-frames):This counter is incremented
            once for every good broadcast packet received and for local and 
            dropped broadcast packets."
        ::= { es400PortStatEntry 8 }

    
    es400PortStatMulticastFramesRx OBJECT-TYPE
        SYNTAX Counter
        ACCESS read-only
        STATUS mandatory
        DESCRIPTION
            "es400ChassisConfigCounterMode = 2(switched-frames):This counter is incre-
            mented once for every good multicast packet received.
            
             es400ChassisConfigCounterMode = 3(all-frames):This counter is incremented
            once for every good multicast packet received and for local and 
            dropped multicast packets. This counter does not include broad-
            cast packets."
        ::= { es400PortStatEntry 9 }

    es400PortStatCRCError OBJECT-TYPE
        SYNTAX Counter
        ACCESS read-only
        STATUS mandatory
        DESCRIPTION
            "This counter is incremented once for every received packet which
            meets all the following conditions:
            1.Packet data length is between 64 and 1518 bytes inclusive.
            2.Packet has invalid CRC.
            3.Collision event , late collision event and receive error event
              have not been detected."
        ::= { es400PortStatEntry 10 }

    es400PortStatOversizeFrames OBJECT-TYPE
        SYNTAX Counter
        ACCESS read-only
        STATUS mandatory
        DESCRIPTION
            "The number of good frames with length more than 1518 bytes."
        ::= { es400PortStatEntry 11 }

    es400PortStatFragments OBJECT-TYPE
        SYNTAX Counter
        ACCESS read-only
        STATUS mandatory
        DESCRIPTION
            "This counter is incremented once for every received packet which
            meets all the following conditions:
            1.Packet data length is less than 64 bytes or packet withourt SFD
              and is less than 64 bytes in length.
            2.Packet has invalid CRC.
            3.Collision event , late collision event and receive error event
              have not been detected."
        ::= { es400PortStatEntry 12 }

    es400PortStatJabber OBJECT-TYPE
        SYNTAX Counter
        ACCESS read-only
        STATUS mandatory
        DESCRIPTION
            "The number of frames with length more than 1518 bytes and with
            CRC error or misaligned."
        ::= { es400PortStatEntry 13 }

    es400PortStatCollision OBJECT-TYPE
        SYNTAX Counter
        ACCESS read-only
        STATUS mandatory
        DESCRIPTION
            "The number of Collisions"
        ::= { es400PortStatEntry 14 }

    es400PortStatLateCollision OBJECT-TYPE
        SYNTAX Counter
        ACCESS read-only
        STATUS mandatory
        DESCRIPTION
            "The number of Late Collision(collision occurring later than
            576th transmitted bit)."
        ::= { es400PortStatEntry 15 }

    es400PortStatFrames-64-bytes OBJECT-TYPE
        SYNTAX Counter
        ACCESS read-only
        STATUS mandatory
        DESCRIPTION
            "This counter is incremented once for every received and trans-
            mitted packet with size of 64 bytes. This counter includes reject-
            ed received and transmitted packets."
        ::= { es400PortStatEntry 16 }

    es400PortStatFrames-65-127-bytes OBJECT-TYPE
        SYNTAX Counter
        ACCESS read-only
        STATUS mandatory
        DESCRIPTION
            "This counter is incremented once for every received and trans-
            mitted packet with size of 65 to 127 bytes. This counter includes
            rejected received and transmitted packets."
        ::= { es400PortStatEntry 17 }

    es400PortStatFrames-128-255-bytes OBJECT-TYPE
        SYNTAX Counter
        ACCESS read-only
        STATUS mandatory
        DESCRIPTION
            "This counter is incremented once for every received and trans-
            mitted packet with size of 128 to 255 bytes. This counter includes
            rejected received and transmitted packets."
        ::= { es400PortStatEntry 18 }

    es400PortStatFrames-256-511-bytes OBJECT-TYPE
        SYNTAX Counter
        ACCESS read-only
        STATUS mandatory
        DESCRIPTION
            "This counter is incremented once for every received and trans-
            mitted packet with size of 256 to 511 bytes. This counter includes
            rejected received and transmitted packets."
        ::= { es400PortStatEntry 19 }

    es400PortStatFrames-512-1023-bytes OBJECT-TYPE
        SYNTAX Counter
        ACCESS read-only
        STATUS mandatory
        DESCRIPTION
            "This counter is incremented once for every received and trans-
            mitted packet with size of 512 to 1023 bytes. This counter includ-
            es rejected received and transmitted packets."
        ::= { es400PortStatEntry 20 }

    es400PortStatFrames-1024-1536-bytes OBJECT-TYPE
        SYNTAX Counter
        ACCESS read-only
        STATUS mandatory
        DESCRIPTION
            "This counter is incremented once for every received and trans-
            mitted packet with size of 1024 to 1536 bytes. This counter includ-
            es rejected received and transmitted packets."
        ::= { es400PortStatEntry 21 }

    es400PortStatFramesDroppedFrames OBJECT-TYPE
        SYNTAX Counter
        ACCESS read-only
        STATUS mandatory
        DESCRIPTION
            "This counter is incremented once for every received dropped pack-
            et."
        ::= { es400PortStatEntry 22 }

    es400PortStatMulticastFramesTx OBJECT-TYPE
        SYNTAX Counter
        ACCESS read-only
        STATUS mandatory
        DESCRIPTION
            "The number of multicast frames sent. This counter does not include
            broadcast packets."
        ::= { es400PortStatEntry 23 }

    es400PortStatBroadcastFramesTx OBJECT-TYPE
        SYNTAX Counter
        ACCESS read-only
        STATUS mandatory
        DESCRIPTION
            "The number of broadcast frames sent."
        ::= { es400PortStatEntry 24 }

    es400PortStatUndersizeFrames OBJECT-TYPE
        SYNTAX Counter
        ACCESS read-only
        STATUS mandatory
        DESCRIPTION
            "This counter is incremented once for every received packet which
            meets all the following conditions:
            1.Packet data length is less than 64 bytes.
            2.Packet has valid CRC.
            3.Collision event , late collision event and receive error event
              have not been detected."
        ::= { es400PortStatEntry 25 }

    es400FDbStaticTable OBJECT-TYPE
        SYNTAX SEQUENCE OF Es400FDbStaticEntry
        ACCESS not-accessible
        STATUS mandatory
        DESCRIPTION
            "Like typical legacy bridge devices, FDB table records the mapping
             of Source MAC Address and its associated source port, and forward
             incoming packets to its destination port according to the Destination
             MAC Address of the packet as well as the MAC-port pair entries of the
             FDB table. Note that the priority of FDB table entries is lower
             than Filtering Table, i.e. if there is a table hash collision between
             the entries of FDB Table and Filtering Table inside the switch H/W
             address table, then Filtering Table entry overwrite the colliding entry
             of FDB Table. See es400FDbFilterTable description also."
        ::= { es400FDb 1 }

    es400FDbStaticEntry OBJECT-TYPE
        SYNTAX Es400FDbStaticEntry
        ACCESS not-accessible
        STATUS mandatory
        DESCRIPTION
            "A list of information specifies which ports the frames with specific 
             destination MAC address to go."
        INDEX  { es400FdbStaticVid , es400FDbStaticAddressIndex }
        ::= { es400FDbStaticTable 1 }

    Es400FDbStaticEntry ::= 
        SEQUENCE {
            es400FdbStaticVid
                INTEGER,
            es400FDbStaticAddressIndex
                MacAddress,
            es400FDbStaticPortMap
                OCTET STRING,
            es400FDbStaticState
                INTEGER,
            es400FDbStaticStatus
                INTEGER    
        }

    es400FdbStaticVid OBJECT-TYPE
        SYNTAX INTEGER
        ACCESS read-only
        STATUS mandatory
        DESCRIPTION
            "This object indicates the VLAN-ID. If the es400VlanInfoStatus
             is port-base mode , the object ranges from 1 to 12. If VLAN 
             is in mac-based mode or disabled, the object indicates the
             default VLAN-ID (0)."
        ::= { es400FDbStaticEntry 1 }

    es400FDbStaticAddressIndex OBJECT-TYPE
        SYNTAX MacAddress
        ACCESS read-only
        STATUS mandatory
        DESCRIPTION
            "The destination MAC address in a frame to which this entry's 
            forwarding information applies. This object can take the value of
            an unicast address or the multicast address."
        ::= { es400FDbStaticEntry 2 }

    es400FDbStaticPortMap OBJECT-TYPE
        SYNTAX OCTET STRING (SIZE (1..4))
        ACCESS read-write
        STATUS mandatory
        DESCRIPTION
            "The set of ports to which frames received from a specific port
            and destined for a specific MAC address, are allowed to be 
            forwarded.  Each octet within the value of this object specifies
            a set of eight ports, with the first octet specifying ports 1 
            through 8, the second octet specifying ports 9 through 16, etc.
            Within each octet, the most significant bit represents the lowest
            numbered port, and the least significant bit represents the highest
            numbered port.  Thus, each port of the bridge is represented by 
            a single bit within the value of this object.  If that bit has a
            value of '1' then that port is included in the set of ports; the
            port is not included if its bit has a value of '0'.(Note that the
            setting of the bit corresponding to the port from which a frame 
            is received is irrelevant.)"
        ::= { es400FDbStaticEntry 3 }

    es400FDbStaticState OBJECT-TYPE
        SYNTAX INTEGER {
               other(1),
               invalid(2),
               valid(3)
               }
        ACCESS read-write
        STATUS mandatory
        DESCRIPTION
            "This object indicates the status of this entry.
 
            other(1) - this entry is currently in use but the conditions under
                which it will remain so are different from each of the following
                values.
            invalid(2) - writing this value to the object, and then the corresponding
                entry will be removed from the table.
            valid(3) - this entry is reside in the table."
        ::= { es400FDbStaticEntry 4 }

    es400FDbStaticStatus OBJECT-TYPE
        SYNTAX INTEGER {
               other(1),
               apply(2),
               not-apply(3)
               }
        ACCESS read-only
        STATUS mandatory
        DESCRIPTION
            "This object indicates the status of this entry.
 
            other(1) - this entry is currently in use but the conditions under
                which it will remain so are different from each of the following
                values.
            apply(2) - this entry is currently in use and reside in the table.
            not-apply(3) - this entry is reside in the table but currently not
                           in use due to conflict with filter table."
        ::= { es400FDbStaticEntry 5 }

    es400FDbFilterTable OBJECT-TYPE
        SYNTAX SEQUENCE OF Es400FDbFilterEntry
        ACCESS not-accessible
        STATUS mandatory
        DESCRIPTION
            "A table which contains the filtering information of the
            unicast/multicast entries. This table is used by the transparent
            switching function in determining how to filter the received frames.
            The Filtering Table entries' priority overrides Static FDB Table
            as well as IGMP table entries, say, if there is a hash table entry
            collision between Filtering Table and Static FDB Table setting in
            the switch device's H/W address table, then Filter Table entry setting
            overwrites the colliding entry in Static FDB Table. See 
            es400FDbStaticTable description also."
        ::= { es400FDb 2 }

    es400FDbFilterEntry OBJECT-TYPE
        SYNTAX Es400FDbFilterEntry
        ACCESS not-accessible
        STATUS mandatory
        DESCRIPTION
            "A list of information about a specific unicast/multicast MAC address
            for which the switch has filtering information."
        INDEX  { es400FdbFilterVid , es400FDbFilterAddressIndex }
        ::= { es400FDbFilterTable 1 }

    Es400FDbFilterEntry ::= 
        SEQUENCE {
            es400FdbFilterVid
                INTEGER,
            es400FDbFilterAddressIndex
                MacAddress,
            es400FDbFilterState
                INTEGER
        }

    es400FdbFilterVid OBJECT-TYPE
        SYNTAX INTEGER
        ACCESS read-only
        STATUS mandatory
        DESCRIPTION
            "This object indicates the VLAN-ID. If the es400VlanInfoStatus
             is port-base mode , the object ranges from 1 to 12. If VLAN 
             is in mac-based mode or disabled, the object indicates the 
             default VLAN-ID (0)."
        ::= { es400FDbFilterEntry 1 }

    es400FDbFilterAddressIndex OBJECT-TYPE
        SYNTAX MacAddress
        ACCESS read-only
        STATUS mandatory
        DESCRIPTION
            "This object indicates a unicast/multicast MAC address for which the bridge
            has filtering information."
        ::= { es400FDbFilterEntry 2 }

    es400FDbFilterState OBJECT-TYPE
        SYNTAX INTEGER {
               other(1),
               dst-src-addr(2),
               invalid(3)
               }
        ACCESS read-write
        STATUS mandatory
        DESCRIPTION
            "This object indicates the status of this entry. 

            other(1) - this entry is currently in use but the conditions under
                which it will remain so are different from each of the following
                values.
            dst-src-addr(2) - recieved frames's destination address or source
                address are currently used to be filtered as it meets with 
                the MAC address entry of the table.
            invalid(3) - writing this value to the object, and then the corresponding
                entry will be removed from the table."
        ::= { es400FDbFilterEntry 3 }

    portPartition TRAP-TYPE
              ENTERPRISE es400
              VARIABLES {
	      es400PortInfoIndex
              }
              DESCRIPTION
                      "The trap is sent whenever the port state enter the 
                      Partion mode when more than 61 collisions occur while
                      trasmitting."
		::= 1

    linkChangeEvent TRAP-TYPE
              ENTERPRISE es400
              VARIABLES { 
              es400PortInfoIndex
              }
              DESCRIPTION
                      "The trap is sent whenever the link state of a port changes
                      from link up to link down or from link down to link up"
                ::= 2

    broadcastRisingStorm TRAP-TYPE
              ENTERPRISE es400
              VARIABLES { 
              es400PortInfoIndex
              }
              DESCRIPTION
                      "The trap indicates that broadcast higher rising threshold
                      . This trap including the port ID"
                ::= 3

    broadcastFallingStorm TRAP-TYPE
              ENTERPRISE es400
              VARIABLES { 
              es400PortInfoIndex
              }
              DESCRIPTION
                      "The trap indicates that broadcast higher falling threshold
                      . This trap including the port ID"
                ::= 4

    es400LinkAggrTable OBJECT-TYPE
        SYNTAX SEQUENCE OF Es400LinkAggrEntry
        ACCESS not-accessible
        STATUS mandatory
        DESCRIPTION
            "This table specifys which ports group a set of ports(up to 8)
             into a single logical link."
        ::= { es400LinkAggr 1 }

    es400LinkAggrEntry OBJECT-TYPE
        SYNTAX Es400LinkAggrEntry
        ACCESS not-accessible
        STATUS mandatory
        DESCRIPTION
            "A list of information specifies which ports group a set of 
             ports(up to 8) into a single logical link."
        INDEX  { es400LinkAggrIndex }
        ::= { es400LinkAggrTable 1 }

    Es400LinkAggrEntry ::= 
        SEQUENCE {
            es400LinkAggrIndex
                INTEGER,
            es400LinkAggrName
                DisplayString,
            es400LinkAggrMasterPort
                INTEGER,
            es400LinkAggrMemberNum
                INTEGER,
            es400LinkAggrState
                INTEGER
        }

    es400LinkAggrIndex OBJECT-TYPE
        SYNTAX INTEGER
        ACCESS read-only
        STATUS mandatory
        DESCRIPTION
            "The index of logical port trunk.The device max support 4 trunk groups.
             The trunk group number depend on the total number of device ports and
             the existence of module."
        ::= { es400LinkAggrEntry 1 }

    es400LinkAggrName OBJECT-TYPE
        SYNTAX DisplayString (SIZE (30))
        ACCESS read-write
        STATUS mandatory
        DESCRIPTION
            "The name of logical port trunk."
        ::= { es400LinkAggrEntry 2 }

    es400LinkAggrMasterPort OBJECT-TYPE
        SYNTAX INTEGER
        ACCESS read-only
        STATUS mandatory
        DESCRIPTION
            "The object indicates the master port number of the port trunk entry.The 
             first port of the trunk is implicitly configured to be the master logical 
             port.When using Port Trunk, you can not configure the other ports of 
             the group except the master port. Their configuration must be same as the
             master port (e.g. speed, duplex, enabled/disabled, flow control, and so on)." 
        ::= { es400LinkAggrEntry 3 }

    es400LinkAggrMemberNum OBJECT-TYPE
        SYNTAX INTEGER
        ACCESS read-write
        STATUS mandatory
        DESCRIPTION
            "Indicate how many number of ports is included in this Trunk. If
             the trunk is located at expansion module (i.e. es400LinkAggrIndex
             equals to 4(24 ports) or 3(16 ports)) and the module is 100-FX,
             the maximum number of ports in the trunk is 2. The maximum number
             of ports is 8 for other trunks." 
        ::= { es400LinkAggrEntry 4 }
    
    es400LinkAggrState OBJECT-TYPE
        SYNTAX INTEGER {
               other(1),
               disabled(2),
               enabled(3)
               }
        ACCESS read-write
        STATUS mandatory
        DESCRIPTION
            "This object decide the port trunk enabled or disabled."
        ::= { es400LinkAggrEntry 5 }

    es400PortMirrorCtrlTable OBJECT-TYPE
        SYNTAX SEQUENCE OF Es400PortMirrorCtrlEntry
        ACCESS not-accessible
        STATUS mandatory
        DESCRIPTION
            "A list of port snooping entries.Port snooping function provide an easy
            way to monitor traffic on any port. In this way any good packets appears
            on the source mirror port also shows up on the target mirror port and 
            doesn't to reconstruct the LAN."
        ::= { es400PortMirror 1 }

    es400PortMirrorCtrlEntry OBJECT-TYPE
        SYNTAX Es400PortMirrorCtrlEntry
        ACCESS not-accessible
        STATUS mandatory
        DESCRIPTION
            "A list of information provide an easy way to monitor traffic on any port.
            The use can bring a fancy network monitor attaching to any target mirror 
            port and set the port to be monitored as source mirror port. "
        INDEX  { es400PortMirrorCtrlIndex }
        ::= { es400PortMirrorCtrlTable 1 }

    Es400PortMirrorCtrlEntry ::= 
        SEQUENCE {
            es400PortMirrorCtrlIndex
                INTEGER,
            es400PortMirrorCtrlSourcePort
                INTEGER,
            es400PortMirrorCtrlTargetPort
                INTEGER,
            es400PortMirrorCtrlState
                INTEGER
        }
        
    es400PortMirrorCtrlIndex OBJECT-TYPE
        SYNTAX INTEGER
        ACCESS read-only
        STATUS mandatory
        DESCRIPTION
            "This object indicates the port snooping entry number.There is just only 
            one now."
        ::= { es400PortMirrorCtrlEntry 1 }    
        
    es400PortMirrorCtrlSourcePort OBJECT-TYPE
        SYNTAX INTEGER (1..26)
        ACCESS read-write
        STATUS mandatory
        DESCRIPTION
            "This object indicates switch which port will be mirrored."
        ::= { es400PortMirrorCtrlEntry 2 }

    es400PortMirrorCtrlTargetPort OBJECT-TYPE
        SYNTAX INTEGER (1..26)
        ACCESS read-write
        STATUS mandatory
        DESCRIPTION
            "This object indicates switch which port will sniff another port.
             A aggregate port member cannot be configured as a target mirroring 
             port."
        ::= { es400PortMirrorCtrlEntry 3 }

    es400PortMirrorCtrlState OBJECT-TYPE
        SYNTAX INTEGER {
               other(1),
               disable(2),
               enable(3)
               }
        ACCESS read-write
        STATUS mandatory
        DESCRIPTION
            "This object indicates the status of this entry. 

            other(1)   - this entry is currently in use but the conditions under
                         which it will remain so are different from each of the 
                         following values.
            disable(2) - Mirror funtion disable.
            enable(3) -  Mirror funtion enable and mirror received or transmit
                         packet by mirror source port."
        ::= { es400PortMirrorCtrlEntry 4 }

    es400IgmpSnoopConfigTable OBJECT-TYPE
        SYNTAX SEQUENCE OF Es400IgmpSnoopConfigEntry
        ACCESS not-accessible
        STATUS mandatory
        DESCRIPTION
            "The table controls the Vlan's IGMP function. Its scale depends on
             current VLAN state (es400VlanInfoStatus). If VLAN is disabled or
             in Mac-Base mode, there is only one entry in the table, with
             index 1. If VLAN is in Port-Base or 802.1q mode, the number of
             entries can be up to 12, with index range from 1 to 12. When in
             802.1q mode, this entry table is only valid in static registration
             entries."
        ::= { es400IgmpSnoop 1 }

    es400IgmpSnoopConfigEntry OBJECT-TYPE
        SYNTAX Es400IgmpSnoopConfigEntry
        ACCESS not-accessible
        STATUS mandatory
        DESCRIPTION
            "The entry in IGMP control table (es400IgmpSnoopConfigTable). The 
             entry is effective only when IGMP capture switch (es400Chassis-
             ConfigIGMPCaptureState) is enabled."
        INDEX  { es400IgmpSnoopConfigIndex }
        ::= { es400IgmpSnoopConfigTable 1 }

    Es400IgmpSnoopConfigEntry ::= 
        SEQUENCE {
            es400IgmpSnoopConfigIndex
                INTEGER,
            es400IgmpSnoopConfigVid
                INTEGER,
            es400IgmpSnoopConfigTimer
                INTEGER,
            es400IgmpSnoopConfigState
                INTEGER
        }

    es400IgmpSnoopConfigIndex OBJECT-TYPE
        SYNTAX INTEGER (1..12)
        ACCESS read-only
        STATUS mandatory
        DESCRIPTION
            "This object indicates the IGMP control entry number.Its scale depends on
             current VLAN state (es400VlanInfoStatus). If VLAN is disabled or in
             Mac-Base mode, there is only one entry in the table, with index 1.
             If VLAN is in Port-Base or 802.1q mode, the number of entries is 12, 
             with index range from 1 to 12."
        ::= { es400IgmpSnoopConfigEntry 1 }

    es400IgmpSnoopConfigVid OBJECT-TYPE
        SYNTAX INTEGER
        ACCESS read-write
        STATUS mandatory
        DESCRIPTION
            "This object indicates the IGMP control entry's VLAN id. If VLAN is
             disabled or in Mac-Base mode, the Vid is always 0 and cannot be changed
             by management users. If VLAN is in Port-Base mode, the Vid is arranged
             from 1 to 12 , fixed form. If VLAN is in 802.1q mode, the Vid setting 
             can vary from 1 to 4094 by management user, and the Vid in each entry
             must be unique in the IGMP Control Table."
        ::= { es400IgmpSnoopConfigEntry 2 }

    es400IgmpSnoopConfigTimer OBJECT-TYPE
        SYNTAX INTEGER (30..9999)
        ACCESS read-write
        STATUS mandatory
        DESCRIPTION
            "The timer value for sending IGMP query packet when none 
             was sent by the multicast router in the LAN. The timer works
             in per-VLAN basis. Our device will be activated to send the query
             message if the timer is expired. Please reference RFC2236-1997.
             And it recommends a default of 125 seconds. The timeout value must 
             be at least 30 seconds."
        DEFVAL      { 300 }
        ::= { es400IgmpSnoopConfigEntry 3 }

    es400IgmpSnoopConfigState OBJECT-TYPE
        SYNTAX INTEGER {
               other(1),
               disable(2),
               enable(3)
               }
        ACCESS read-write
        STATUS mandatory
        DESCRIPTION
            "This object indicates the status of this entry.

            other(1)   - this entry is currently in use but the conditions under
                         which it will remain so are different from each of the 
                         following values.
            disable(2) - IGMP funtion is disabled for this entry.
            enable(3) -  IGMP funtion is enabled for this entry."
        ::= { es400IgmpSnoopConfigEntry 4 }

    es400IgmpSnoopInfoTable OBJECT-TYPE
        SYNTAX SEQUENCE OF Es400IgmpSnoopInfoEntry
        ACCESS not-accessible
        STATUS mandatory
        DESCRIPTION
            "The table contains the number current IGMP query packets which
             is captured by this device, as well as the IGMP query packets
             sent by the device."
        ::= { es400IgmpSnoop 2 }

    es400IgmpSnoopInfoEntry OBJECT-TYPE
        SYNTAX Es400IgmpSnoopInfoEntry
        ACCESS not-accessible
        STATUS mandatory
        DESCRIPTION
            "Information about current IGMP query information, provided that
             es400ChassisConfigIGMPCaptureState and es400IgmpSnoopConfigState of
             associated VLAN entry are all enabled."
        INDEX  { es400IgmpSnoopInfoIndex }
        ::= { es400IgmpSnoopInfoTable 1 }

    Es400IgmpSnoopInfoEntry ::= 
        SEQUENCE {
            es400IgmpSnoopInfoIndex
                INTEGER,
            es400IgmpSnoopInfoVid
                INTEGER,
            es400IgmpSnoopInfoQueryCount
                INTEGER,
            es400IgmpSnoopInfoTxQueryCount
                INTEGER
        }

    es400IgmpSnoopInfoIndex OBJECT-TYPE
        SYNTAX INTEGER (1..12)
        ACCESS read-only
        STATUS mandatory
        DESCRIPTION
            "This object indicates the IGMP query information entry number. It could
             be up to 12 entries, depending on current number of VLAN entries."
        ::= { es400IgmpSnoopInfoEntry 1 }

    es400IgmpSnoopInfoVid OBJECT-TYPE
        SYNTAX INTEGER
        ACCESS read-only
        STATUS mandatory
        DESCRIPTION
            "This object indicates the Vid of associated IGMP info table entry. It
             follows es400IgmpSnoopConfigVid in the associated entry of IGMP control
             table (es400IgmpSnoopConfigTable)."
        ::= { es400IgmpSnoopInfoEntry 2 }

    es400IgmpSnoopInfoQueryCount OBJECT-TYPE
        SYNTAX INTEGER
        ACCESS read-only
        STATUS mandatory
        DESCRIPTION
            "This object indicates the number of query packets received since the
             IGMP function enabled, in per-VLAN basis."
        ::= { es400IgmpSnoopInfoEntry 3 }

    es400IgmpSnoopInfoTxQueryCount OBJECT-TYPE
        SYNTAX INTEGER
        ACCESS read-only
        STATUS mandatory
        DESCRIPTION
            "This object indicates the send count of IGMP query messages, in
             per-VLAN basis. In case of IGMP timer expiration, the switch
             sends IGMP query packets to related VLAN member ports and increment
             this object by 1."
        ::= { es400IgmpSnoopInfoEntry 4 }

    es400IgmpSnoopTable OBJECT-TYPE
        SYNTAX SEQUENCE OF Es400IgmpSnoopEntry
        ACCESS not-accessible
        STATUS mandatory
        DESCRIPTION
            "The table containing current IGMP information which captured by this 
            device, provided that es400ChassisConfigIGMPCaptureState and 
            es400IgmpSnoopConfigState of associated VLAN entry are all enabled. Note
            that the priority of IGMP table entries is lower than Filtering Table,
            i.e. if there is a table hash collision between the entries of IGMP Table
            and Filtering Table inside the switch H/W address table, then Filtering 
            Table entry overwrite the colliding entry of IGMP Table. See 
            es400FDbFilterTable description also."
        ::= { es400IgmpSnoop 3 }

    es400IgmpSnoopEntry OBJECT-TYPE
        SYNTAX Es400IgmpSnoopEntry
        ACCESS not-accessible
        STATUS mandatory
        DESCRIPTION
            "Information about current IGMP information which captured by this 
            device , provided that es400ChassisConfigIGMPCaptureState and 
            es400IgmpSnoopConfigState of associated VLAN entry are all enabled."
        INDEX  { es400IgmpSnoopVid , es400IgmpSnoopGroupIpAddr }
        ::= { es400IgmpSnoopTable 1 }

    Es400IgmpSnoopEntry ::= 
        SEQUENCE {
            es400IgmpSnoopVid
                INTEGER,
            es400IgmpSnoopGroupIpAddr
                IpAddress,
            es400IgmpSnoopMacAddr
                MacAddress,
            es400IgmpSnoopPortMap
                PortList,
            es400IgmpSnoopReportCount
                INTEGER
        }

    es400IgmpSnoopVid OBJECT-TYPE
        SYNTAX INTEGER
        ACCESS read-only
        STATUS mandatory
        DESCRIPTION
            "This object indicates the Vid of individual IGMP table entry. It
             shows the Vid of IGMP report information captured on network."
        ::= { es400IgmpSnoopEntry 1 }

    es400IgmpSnoopGroupIpAddr OBJECT-TYPE
        SYNTAX IpAddress
        ACCESS read-only
        STATUS mandatory
        DESCRIPTION
            "This object is identify group ip address which is captured from
            IGMP packet, in per-Vlan basis."
        ::= { es400IgmpSnoopEntry 2 }

    es400IgmpSnoopMacAddr OBJECT-TYPE
        SYNTAX MacAddress
        ACCESS read-only
        STATUS mandatory
        DESCRIPTION
            "This object is identify mac address which is corresponding
            to es400IgmpSnoopGroupIpAddr, in per-Vlan basis.."
        ::= { es400IgmpSnoopEntry 3 }

    es400IgmpSnoopPortMap OBJECT-TYPE
        SYNTAX PortList
        ACCESS read-only
        STATUS mandatory
        DESCRIPTION
            "This object indicates which ports are belong to the same multicast 
            group, in per-Vlan basis. Each multicast group has a octect string 
            to indicate with port map. The most significant bit represents the
            lowest numbered port, and the least significant bit represents the
            highest numbered port."
        ::= { es400IgmpSnoopEntry 4 }

    es400IgmpSnoopReportCount OBJECT-TYPE
        SYNTAX INTEGER
        ACCESS read-only
        STATUS mandatory
        DESCRIPTION
            "This object indicate how much report packet was receive by our
             device corresponding with this entry from IGMP function enabled,
             in per-Vlan basis." 
        ::= { es400IgmpSnoopEntry 5 }

    es400VlanConfigMode OBJECT-TYPE
        SYNTAX  INTEGER {
                    other(1),
                    disabled(2),    -- Vlan function be disable
                    mac-base(3),    -- proprietary mac base Vlan
                    port-base(4),   -- proprietary port base Vlan
                    ieee8021q(5)    -- 802.1q gvrp base Vlan
                }
        ACCESS  read-write
        STATUS  mandatory
        DESCRIPTION
            "This object control which Vlan function will be enable (or disable)
             when the switch hub restart at the startup (power on) or warm 
             start." 
        ::= { es400Vlan 1 }

    es400VlanInfoStatus OBJECT-TYPE
        SYNTAX  INTEGER {
                    other(1),
                    disabled(2),    -- Vlan function be disable
                    mac-base(3),    -- proprietary mac base Vlan
                    port-base(4),   -- proprietary port base Vlan
                    ieee8021q(5)    -- 802.1q gvrp base Vlan
                }
        ACCESS  read-only
        STATUS  mandatory
        DESCRIPTION
            "This object indicate which Vlan function be enable (or disable)
             in mandatoryly stage. There are no effect when change es400VlanConfigMode
             vlaue in the system running."
        ::= { es400Vlan 2 }

    es400VlanSnmpPortInfo OBJECT-TYPE
        SYNTAX  VlanIndex (1..4094)
        ACCESS  read-write
        STATUS  mandatory
        DESCRIPTION
            "This object controls which Vlan is binded with system snmp port.
             Its scale depends on current VLAN state (es400VlanInfoStatus). 
             If VLAN is disabled or in Mac-Base mode, the Vid is always 0
             and cannot be changed by management users. If VLAN is in 802.1q
             mode, the Vid setting can vary from 1 to 4094 by management user.
             If VLAN is in Port-Base mode, the Vid setting can vary from 1 to
             12 by management user."
        ::= { es400Vlan 3 }

    es400MacVlan   OBJECT IDENTIFIER ::= { es400Vlan 4 }

    es400MacVlanTotalNum OBJECT-TYPE
        SYNTAX  INTEGER
        ACCESS  read-only
        STATUS  mandatory
        DESCRIPTION
            "The total number of Mac base Vlan within this switch hub."
        ::= { es400MacVlan 1 }

    es400MacVlanConfigTable OBJECT-TYPE
        SYNTAX  SEQUENCE OF Es400MacVlanConfigEntry
        ACCESS  not-accessible
        STATUS  mandatory
        DESCRIPTION
            "A table that contains MAC-Based VLAN list entries for the switch.
             Management users can create a MAC-Based VLAN entry by adding a new
             list (es400MacVlanConfigEntry) in this table."
        ::= { es400MacVlan 2 }

    es400MacVlanConfigEntry OBJECT-TYPE
        SYNTAX  Es400MacVlanConfigEntry
        ACCESS  not-accessible
        STATUS  mandatory
        DESCRIPTION
            "A list of information about a specific MAC-Based VLAN configuration
             in es400MacVlanConfigTable."
        INDEX   { es400MacVlanDesc }
        ::= { es400MacVlanConfigTable 1 }

    Es400MacVlanConfigEntry ::= 
        SEQUENCE {
            es400MacVlanDesc
                DisplayString,
            es400MacVlanMacMemberNum
                INTEGER,    
            es400MacVlanCtrlState
                INTEGER
        }

    es400MacVlanDesc OBJECT-TYPE
        SYNTAX  DisplayString (SIZE (1..12))
        ACCESS  read-only
        STATUS  mandatory
        DESCRIPTION
            "A textual description of the Mac Base Vlan."
        ::= { es400MacVlanConfigEntry 1 }

    es400MacVlanMacMemberNum OBJECT-TYPE
        SYNTAX  INTEGER
        ACCESS  read-only
        STATUS  mandatory
        DESCRIPTION
            "This object indicates the total number of MAC addresses contained
             in the VLAN entry."
        ::= { es400MacVlanConfigEntry 2 }

    es400MacVlanCtrlState OBJECT-TYPE
        SYNTAX  INTEGER {
                    other(1),
                    disabled(2),
                    enabled(3)
                }
        ACCESS  read-write
        STATUS  mandatory
        DESCRIPTION
            "This object indicates the MacBase Vlan state. Writing disabled
             value to the object will remove the corresponding entry from the
             table."
        ::= { es400MacVlanConfigEntry 3 }

    es400MacVlanAddrTotalNum OBJECT-TYPE
        SYNTAX  INTEGER
        ACCESS  read-only
        STATUS  mandatory
        DESCRIPTION
            "The total number of Mac base Vlan address entry within this switch 
             hub."
        ::= { es400MacVlan 3 }

    es400MacVlanAddrTable OBJECT-TYPE
        SYNTAX  SEQUENCE OF SwMacBaseVlanAddrEntry
        ACCESS  not-accessible
        STATUS  mandatory
        DESCRIPTION
            "A table that contains information about unicast entries for which 
             the switch has forwarding and/or filtering information. This 
             information is used by the transparent switching function in
             determining how to propagate a received frame. Note that the
             priority of MacVlanAddr table entries is lowest than Filtering
             Table and FDB Table, i.e. if there is a table hash collision between
             the entries of MacVlanAddr Table and Filtering Table inside the switch
             H/W address table, then Filtering Table entry overwrite the colliding
             entry of MacVlanAddr Table. This state is same of FDB table. See
             es400FDbFilterTable and es400FDbStaticTable
             description also."
        ::= { es400MacVlan 4 }

    es400MacVlanAddrEntry OBJECT-TYPE
        SYNTAX  SwMacBaseVlanAddrEntry
        ACCESS  not-accessible
        STATUS  mandatory
        DESCRIPTION
            "A list of information about a specific unicast MAC address for which
             the switch has some forwarding and/or filtering information."
        INDEX   { es400MacVlanAddress }
        ::= { es400MacVlanAddrTable 1 }
        
    SwMacBaseVlanAddrEntry ::= 
        SEQUENCE {
            es400MacVlanAddress
                MacAddress,
            es400MacVlanAddrDesc
                DisplayString,
            es400MacVlanAddrState
                INTEGER,
            es400MacVlanAddrStatus
                INTEGER
        }        
        
    es400MacVlanAddress OBJECT-TYPE
        SYNTAX  MacAddress
        ACCESS  read-only
        STATUS  mandatory
        DESCRIPTION
            "This object indictaes a unicast MAC address for which the bridge
             has forwarding and/or filtering information."
        ::= { es400MacVlanAddrEntry 1 }

    es400MacVlanAddrDesc OBJECT-TYPE
        SYNTAX  DisplayString (SIZE (1..12))
        ACCESS  read-write
        STATUS  mandatory
        DESCRIPTION
            "This object references to the MAC-Base VLAN description (es400MacVlanDesc)
             which the MAC address belong to. You must update the VLAN description
             with an VLAN description which is already exist on MAC-Base VLAN control
             table. If the VLAN description on the MAC-Base VLAN  control table doesn't
             exist , the corresponding entry will be removed from the table."
        ::= { es400MacVlanAddrEntry 2 }

    es400MacVlanAddrState OBJECT-TYPE
        SYNTAX  INTEGER {
                    other(1),
                    invalid(2),
                    valid(3)
                }
        ACCESS  read-write
        STATUS  mandatory
        DESCRIPTION
            "This object indicates the MacBase Vlan Address entry state.

            other(1) - this entry is currently in use but the conditions under
                which it will remain so are different from each of the following
                values.
            invalid(2) - writing this value to the object, and then the corresponding
                entry will be removed from the table.
            valid(3) - this entry is reside in the table."
        ::= { es400MacVlanAddrEntry 3 }

    es400MacVlanAddrStatus OBJECT-TYPE
        SYNTAX  INTEGER {
                other(1),
                apply(2),
                not-apply(3)
                }
        ACCESS  read-only
        STATUS  mandatory
        DESCRIPTION
            "This object indicates the MacBase Vlan Address entry state.

            other(1) - this entry is currently in use but the conditions under
                which it will remain so are different from each of the following
                values.
            apply(2) - this entry is currently in use and reside in the table.
            not-apply(3) - this entry is reside in the table but currently not
                           in use due to conflict with filter table."
        ::= { es400MacVlanAddrEntry 4 }

    es400PortVlan   OBJECT IDENTIFIER ::= { es400Vlan 5 }

    es400PortVlanTotalNum OBJECT-TYPE
        SYNTAX  INTEGER
        ACCESS  read-only
        STATUS  mandatory
        DESCRIPTION
            "The total number of Port-Base Vlan which is in enabled state
             within this switch hub."
        ::= { es400PortVlan 1 }

    es400PortVlanDefaultVlanTable OBJECT-TYPE
        SYNTAX  SEQUENCE OF Es400PortVlanDefaultVlanEntry
        ACCESS  not-accessible
        STATUS  mandatory
        DESCRIPTION
            "A table that contains default Port-Based VLAN list entries for the 
             switch. The entry (Vid = 1,i.e. es400PortVlanDefaultPvid = 1) is 
             defalut Port-Based VLAN , maintained by system."
        ::= { es400PortVlan 2 }

    es400PortVlanDefaultVlanEntry OBJECT-TYPE
        SYNTAX  Es400PortVlanDefaultVlanEntry
        ACCESS  not-accessible
        STATUS  mandatory
        DESCRIPTION
            "A list of default Port-Based VLAN information in 
             es400PortVlanDefaultVlanTable."
        INDEX   { es400PortVlanDefaultPvid }
        ::= { es400PortVlanDefaultVlanTable 1 }

    Es400PortVlanDefaultVlanEntry ::= 
        SEQUENCE {
            es400PortVlanDefaultPvid
                INTEGER,
            es400PortVlanDefaultDesc
                DisplayString,
            es400PortVlanDefaultPortList
                PortList,
            es400PortVlanDefaultPortNumber
                INTEGER
        }

    es400PortVlanDefaultPvid OBJECT-TYPE
        SYNTAX  INTEGER
        ACCESS  read-only
        STATUS  mandatory
        DESCRIPTION
            "This object indicates the default Port-Base Vlan ID. It occupies only 
             1 entry in VLAN table, with VID=1."
        ::= { es400PortVlanDefaultVlanEntry 1 }

    es400PortVlanDefaultDesc OBJECT-TYPE
        SYNTAX  DisplayString (SIZE (1..12))
        ACCESS  read-only
        STATUS  mandatory
        DESCRIPTION
            "A textual description of the Port-Base Vlan."
        ::= { es400PortVlanDefaultVlanEntry 2 }

    es400PortVlanDefaultPortList OBJECT-TYPE
        SYNTAX  PortList
        ACCESS  read-only
        STATUS  mandatory
        DESCRIPTION
            "This object indicates the port member set of the specified Vlan.
             Each Vlan has a octect string to indicate the port map. The most
             significant bit represents the lowest numbered port, and the
             least significant bit represents the highest numbered port."
        ::= { es400PortVlanDefaultVlanEntry 3 }

    es400PortVlanDefaultPortNumber OBJECT-TYPE
        SYNTAX  INTEGER
        ACCESS  read-only
        STATUS  mandatory
        DESCRIPTION
            "This object indicates the number of ports of the entry."
        ::= { es400PortVlanDefaultVlanEntry 4 }

    es400PortVlanConfigTable OBJECT-TYPE
        SYNTAX  SEQUENCE OF Es400PortVlanConfigEntry
        ACCESS  not-accessible
        STATUS  mandatory
        DESCRIPTION
            "A table that contains Port-Based VLAN list entries for the switch.
             The device can't support port overlapping in Port-Based VLAN."
        ::= { es400PortVlan 3 }

    es400PortVlanConfigEntry OBJECT-TYPE
        SYNTAX  Es400PortVlanConfigEntry
        ACCESS  not-accessible
        STATUS  mandatory
        DESCRIPTION
            "A list of information about a specific Port-Based VLAN configuration
             in es400PortVlanConfigTable."
        INDEX   { es400PortVlanConfigPvid }
        ::= { es400PortVlanConfigTable 1 }

    Es400PortVlanConfigEntry ::= 
        SEQUENCE {
            es400PortVlanConfigPvid
                INTEGER,
            es400PortVlanConfigDesc
                DisplayString,
            es400PortVlanConfigPortList
                PortList,
            es400PortVlanConfigPortNumber
                INTEGER,
            es400PortVlanConfigState
                INTEGER
        }

    es400PortVlanConfigPvid OBJECT-TYPE
        SYNTAX  INTEGER (2..12)
        ACCESS  read-only
        STATUS  mandatory
        DESCRIPTION
            "This object indicates the Port-Base Vlan ID. There are up to 11 entries
             for current product now. The object range varies from 2 to 12."
        ::= { es400PortVlanConfigEntry 1 }

    es400PortVlanConfigDesc OBJECT-TYPE
        SYNTAX  DisplayString (SIZE (1..12))
        ACCESS  read-write
        STATUS  mandatory
        DESCRIPTION
            "A textual description of the Port-Base Vlan. It cannot be a null string.
             And each description must be unique in the table."
        ::= { es400PortVlanConfigEntry 2 }

    es400PortVlanConfigPortList OBJECT-TYPE
        SYNTAX  PortList
        ACCESS  read-write
        STATUS  mandatory
        DESCRIPTION
            "This object indicates which ports are belong to the Vlan. Each Vlan
             has a octect string to indicate with port map. The most significant
             bit represents the lowest numbered port, and the least significant 
             bit represents the highest numbered port."
        ::= { es400PortVlanConfigEntry 3 }

    es400PortVlanConfigPortNumber OBJECT-TYPE
        SYNTAX  INTEGER
        ACCESS  read-only
        STATUS  mandatory
        DESCRIPTION
            "This object indicates the number of ports of the entry."
        ::= { es400PortVlanConfigEntry 4 }

    es400PortVlanConfigState OBJECT-TYPE
        SYNTAX  INTEGER {
                    other(1),
                    disabled(2),
                    enabled(3)
                }
        ACCESS  read-write
        STATUS  mandatory
        DESCRIPTION
            " This object indicates the Port-Base Vlan state.
 
            other(1) - this entry is currently in use but the conditions under
                which it will remain so are different from each of the following
                values.
            disabled(2) - writing this value to the object, and then the corresponding
                entry will be removed from the table.
            enabled(3) - this entry is reside in the table."
        ::= { es400PortVlanConfigEntry 5 }

END
