-- 	$Id: shiva-serial.asn,v 1.7 1996/01/16 16:48:09 dfox Exp $

--
-- 	Copyright 1992, 1993, 1995, 1996 Shiva Corporation
--

-- This MIB has been replaced by the SHIVA-LINE-MIB and SHIVA-SLOT-MIB.
-- It is not included in LanRover/Access Switch and subsequent products.

SHIVA-SERIAL-MIB DEFINITIONS ::= BEGIN

IMPORTS
	DisplayString
		FROM RFC1213-MIB
	OBJECT-TYPE
		FROM RFC-1212		-- Concise MIB Definitions
	serial
		FROM SHIVA-MIB;


-- serial port table

-- for the care and feeding of async serial ports with modems attached

    serialPortTable OBJECT-TYPE
	SYNTAX	SEQUENCE OF SerialPortEntry
	ACCESS	not-accessible
	STATUS	deprecated
	DESCRIPTION
		"Table of serial port initialization parameters and status."
	::= { serial 1 }

    serialPortEntry OBJECT-TYPE
	SYNTAX	SerialPortEntry
	ACCESS	not-accessible
	STATUS	deprecated
	DESCRIPTION
		"initialization parameters and status for a serial port."
	INDEX { serialPortIndex }
	::= { serialPortTable 1 }

    SerialPortEntry ::= SEQUENCE {
	serialPortIndex		INTEGER,
	serialPortName		DisplayString,
	serialPortStatus	INTEGER,
	serialPortModemName	DisplayString,
	serialPortAnswerInit	DisplayString,
	serialPortInitRate	INTEGER,
	serialPortInitFlow	INTEGER,
	serialPortSignals	INTEGER,
	serialPortModemType	INTEGER,
	serialPortInitString	DisplayString
    }

    serialPortIndex OBJECT-TYPE
	SYNTAX	INTEGER
	ACCESS	read-only
	STATUS	deprecated
	DESCRIPTION
		"Serial port number which corresponds to an
		instance of rs232PortIndex."
	::= { serialPortEntry 1 }

    serialPortName OBJECT-TYPE
	SYNTAX	DisplayString
	ACCESS	read-only
	STATUS	deprecated
	DESCRIPTION
		"The name of this port, as used to retrieve configuration."
	::= { serialPortEntry 2 }

    serialPortStatus OBJECT-TYPE
	SYNTAX	INTEGER {
		disabled(1),
		initializing(2),
		idle(3),
		packet(4),	-- in use for packet-oriented networking
		character(5)	-- in use for character-oriented I/O
	}
	ACCESS	read-write
	STATUS	deprecated
	DESCRIPTION
		"Serial port status.  Setting serialPortStatus
		to initializing(2) forces the port to be reinitialized."
	::= { serialPortEntry 3 }

    serialPortModemName OBJECT-TYPE
	SYNTAX	DisplayString
	ACCESS	read-write
	STATUS	deprecated
	DESCRIPTION
		"The name of the type of modem connected to this port."
	::= { serialPortEntry 4 }

    serialPortAnswerInit OBJECT-TYPE
	SYNTAX	DisplayString
	ACCESS	read-write
	STATUS	deprecated
	DESCRIPTION
		"The initialization string to put the modem in auto-answer
		mode."
	::= { serialPortEntry 5 }

    serialPortInitRate OBJECT-TYPE
	SYNTAX	INTEGER
	ACCESS	read-write
	STATUS	deprecated
	DESCRIPTION
		"The rate in bits per second at which to initialize
		the port."
	::= { serialPortEntry 6 }

    serialPortInitFlow OBJECT-TYPE
	SYNTAX	INTEGER { none(1), hardware(2), software(3) }
	ACCESS	read-write
	STATUS	deprecated
	DESCRIPTION
		"The flow control setting to initialize the port with."
	::= { serialPortEntry 7 }

    serialPortSignals OBJECT-TYPE
	SYNTAX	INTEGER
	ACCESS	read-only
	STATUS	deprecated
	DESCRIPTION
		"The current status of control signals on this port,
		as the sum of the following bits;
			0	Ready To Send
			1	Clear To Send
			2	Data Set Ready
			3	Data Terminal Ready
			4	Ring Indicate
			5	Data Carrier (Rcvd Line Signal) Detect
			6	Signal Quality Detect
			7	Signaling Rate Selector
			8	Secondary RTS
			9	Secondary CTS
			10	Secondary DCD."
	::= { serialPortEntry 8 }

    serialPortModemType OBJECT-TYPE
	SYNTAX	INTEGER {
		absent(1),
		internal(2),
		external(3)
	}
	ACCESS	read-only
	STATUS	deprecated
	DESCRIPTION
		"Serial port modem type."
	::= { serialPortEntry 9 }

    serialPortInitString OBJECT-TYPE
	SYNTAX	DisplayString
	ACCESS	read-write
	STATUS	deprecated
	DESCRIPTION
		"The initialization string to put the modem in dial
		mode."
	::= { serialPortEntry 10 }

-- serial port group names

    groupTable	OBJECT-TYPE
	SYNTAX	SEQUENCE OF GroupEntry
	ACCESS	not-accessible
	STATUS	deprecated
	DESCRIPTION
		"A table of serial port group names."
	::= { serial 2 }

    groupEntry	OBJECT-TYPE
	SYNTAX	GroupEntry
	ACCESS	not-accessible
	STATUS	deprecated
	DESCRIPTION
		"A serial port group name table entry."
	INDEX { groupName }
	::= { groupTable 1 }

    GroupEntry ::= SEQUENCE {
	groupName	DisplayString
    }

    groupName	OBJECT-TYPE
	SYNTAX	DisplayString
	ACCESS	read-only
	STATUS	deprecated
	DESCRIPTION
		"A serial port group name."
	::= { groupEntry 1 }

-- number of serial ports

    numSerialSlots	OBJECT-TYPE
	SYNTAX	INTEGER
	ACCESS	read-only
	STATUS	deprecated
	DESCRIPTION
		"Number of serial slots."
	::= { serial 3 }

    numSerialCards	OBJECT-TYPE
	SYNTAX	INTEGER
	ACCESS	read-only
	STATUS	deprecated
	DESCRIPTION
		"Number of serial cards."
	::= { serial 4 }


END
