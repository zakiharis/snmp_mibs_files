-- 	$Id: shiva.asn,v 1.16 91/10/29 20:13:10 phil Exp $
 --
 -- 	Copyright 1990, 1991 Shiva Corporation
 --

 -- This file describes the Shiva Enterprise MIB, as supported by
 -- K-STAR Release 9.1. It includes object identifiers and object
 -- definitions for the Shiva Enterprise MIB only, and should be
 -- useful for compilation by a management tool in order to extend the
 -- tool to support the Shiva MIB.

 -- The companion file "mib.txt" describes all the variables supported
 -- by this release of K-STAR, and should be useful as a summary of
 -- FastPath SNMP functionality.

    SHIVA-MIB DEFINITIONS ::= BEGIN
  
    IMPORTS
  	enterprises, NetworkAddress, IpAddress, Counter, Gauge, TimeTicks 
  		FROM RFC1155-SMI
	ifIndex
		FROM RFC1158-MIB
	DisplayString FROM SNMPv2-TC
	OBJECT-TYPE
		FROM RFC-1212		-- Concise MIB Definitions
	TRAP-TYPE
		FROM RFC-1215;		-- Trap Conventions Memo
  
  -- The essential tree structure is defined here, in a level-order traversal. 
  -- The individual objects in each group are defined later, in a preorder
  -- traversal.  Each named node (except the individual objects) is identified 
  -- by a comment of the form
  --	Node: node-name	
  -- where node-name is the last element of the Object ID.  This should make
  -- it easy to use an editor to search this file for a particular group.
  --

  	shiva		OBJECT IDENTIFIER ::= { enterprises 166 }
  
  	sSystems	OBJECT IDENTIFIER ::= { shiva 1 }
  	products	OBJECT IDENTIFIER ::= { shiva 2 }
  	protocols	OBJECT IDENTIFIER ::= { shiva 3 }
  	temporary	OBJECT IDENTIFIER ::= { shiva 4 }
  	nortelSpecific	OBJECT IDENTIFIER ::= { shiva 5 }
  	shivaVpn	OBJECT IDENTIFIER ::= { shiva 6 }

	messageLog	OBJECT IDENTIFIER ::= { sSystems 1 }
	scc			OBJECT IDENTIFIER ::= { sSystems 2 }
	sam			OBJECT IDENTIFIER ::= { sSystems 3 }
	users		OBJECT IDENTIFIER ::= { sSystems 5 }
	log			OBJECT IDENTIFIER ::= { sSystems 6 }
	version		OBJECT IDENTIFIER ::= { sSystems 7 }
	memory		OBJECT IDENTIFIER ::= { sSystems 8 }
	time		OBJECT IDENTIFIER ::= { sSystems 9 }
	features	OBJECT IDENTIFIER ::= { sSystems 10 }
	config		OBJECT IDENTIFIER ::= { sSystems 11 }
	serial		OBJECT IDENTIFIER ::= { sSystems 12 }
	session		OBJECT IDENTIFIER ::= { sSystems 14 }
	lanToLAN	OBJECT IDENTIFIER ::= { sSystems 15 }
	modem		OBJECT IDENTIFIER ::= { sSystems 16 }
	line		OBJECT IDENTIFIER ::= { sSystems 17 }
	slot		OBJECT IDENTIFIER ::= { sSystems 18 }
	perfAcct	OBJECT IDENTIFIER ::= { sSystems 19 }
	call		OBJECT IDENTIFIER ::= { sSystems 20 }
	acct		OBJECT IDENTIFIER ::= { sSystems 21 }
	dmc			OBJECT IDENTIFIER ::= { sSystems 22 }
	flash		OBJECT IDENTIFIER ::= { sSystems 23 }
	pburst		OBJECT IDENTIFIER ::= { sSystems 24 }
	process		OBJECT IDENTIFIER ::= { sSystems 25 }
	l2f			OBJECT IDENTIFIER ::= { sSystems 26 }
	lineTest	OBJECT IDENTIFIER ::= { sSystems 27 }
	psurf		OBJECT IDENTIFIER ::= { sSystems 28 }
	conformance	OBJECT IDENTIFIER ::= { sSystems 29 }
	power		OBJECT IDENTIFIER ::= { sSystems 30 }

	fastpath	OBJECT IDENTIFIER ::= { products 1 }
	nmV32e		OBJECT IDENTIFIER ::= { products 2 }
	lanrover	OBJECT IDENTIFIER ::= { products 3 }
	ibm8235		OBJECT IDENTIFIER ::= { products 4 }
	hpdialalan	OBJECT IDENTIFIER ::= { products 5 }
	nme			OBJECT IDENTIFIER ::= { products 6 }
	rapport8	OBJECT IDENTIFIER ::= { products 7 }
	lraccess	OBJECT IDENTIFIER ::= { products 8 }
	rapport112	OBJECT IDENTIFIER ::= { products 9 }
	ibm8235i40	OBJECT IDENTIFIER ::= { products 10 }
	lanroverd56	OBJECT IDENTIFIER ::= { products 11 }
	products12	OBJECT IDENTIFIER ::= { products 12 }
	products13	OBJECT IDENTIFIER ::= { products 13 }
	lanrovervg	OBJECT IDENTIFIER ::= { products 14 }
	accessMgr	OBJECT IDENTIFIER ::= { products 15 }

  	fpBuffer	OBJECT IDENTIFIER ::= { fastpath 1 }
  	fpConf		OBJECT IDENTIFIER ::= { fastpath 2 }
	k-star		OBJECT IDENTIFIER ::= { fastpath 3 }

  	tBap		OBJECT IDENTIFIER ::= { temporary 1 }
  	tATalk		OBJECT IDENTIFIER ::= { temporary 2 }
  	tIP			OBJECT IDENTIFIER ::= { temporary 3 }
  	tCommunity	OBJECT IDENTIFIER ::= { temporary 4 }
	tEther		OBJECT IDENTIFIER ::= { temporary 5 }
	tNetWare	OBJECT IDENTIFIER ::= { temporary 6 }
	tdot5		OBJECT IDENTIFIER ::= { temporary 7 }
	tChipSets	OBJECT IDENTIFIER ::= { temporary 8 }
	tFilters	OBJECT IDENTIFIER ::= { temporary 9 }
	tPPP		OBJECT IDENTIFIER ::= { temporary 10 }
	tRadius		OBJECT IDENTIFIER ::= { temporary 11 }
	temporary12	OBJECT IDENTIFIER ::= { temporary 12 }


  -- Node: shiva
  -- Node: sSystems
  -- Node: messageLog	The message log holds a list of ASCII strings
  --			which correspond to the last N diagnostic messages
  --			generated by the device.

    mLogEntryCount OBJECT-TYPE
  	SYNTAX	INTEGER
  	ACCESS  read-only
   	STATUS  mandatory
  	DESCRIPTION
  		"The number of entries currently in the message log buffer."
    ::= { messageLog 1 }

    mLogNewMessageTrapEnable OBJECT-TYPE
  	SYNTAX	INTEGER {
		disabled(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
  	ACCESS  read-write
   	STATUS  mandatory	--  unimplemented in K-STAR 9.0, 9.1
  	DESCRIPTION
  		"Enables or disables the generation of mLogNewMessage Traps
		 of a priority numerically equal or lower than the value of 
		 this variable."
	DEFVAL { disabled }
    ::= { messageLog 2 }

    mLogBuffer OBJECT-TYPE
  	SYNTAX	SEQUENCE OF MLogEntry
  	ACCESS  not-accessible
   	STATUS  mandatory
  	DESCRIPTION
  		"A list of message log entries."
    ::= { messageLog 3 }

    mLogMessage OBJECT-TYPE
  	SYNTAX	MLogEntry
  	ACCESS  not-accessible
   	STATUS  mandatory
  	DESCRIPTION
  		"An entry in the message log.  Entries are indexed by
		counting integers.  Since the earliest messages are dropped
		from the log when it overflows, the first row in the table
		is not necessarily row 1.  Therefore, a Get-Next request
		should be issued to determine the index of the first row."
	--INDEX	{ INTEGER }
    ::= { mLogBuffer 1 }

    MLogEntry ::= SEQUENCE {
	mLogTimeStamp	TimeTicks,
	mLogPriority	INTEGER,
	mLogMessageText	DisplayString,
	mLogTimeOfDay	INTEGER
    }

    mLogTimeStamp OBJECT-TYPE
  	SYNTAX	TimeTicks
  	ACCESS  read-only
   	STATUS  mandatory
  	DESCRIPTION
  		"The time the message was generated, measured in number of
		ticks since the device started."
    ::= { mLogMessage 1 }

    mLogPriority OBJECT-TYPE
  	SYNTAX	INTEGER {
		not-possible(1),
		emerg(2),	-- system is unusable
		alert(3),	-- action must be taken immediately
		crit(4),	-- critical conditions
		err(5),		-- error conditions
		warning(6),	-- warning conditions
		notice(7),	-- normal but significant condition
		info(8),	-- informational
		debug(9)	-- debug-level messages
	}
  	ACCESS  read-only
   	STATUS  mandatory
  	DESCRIPTION
  		"The priority of the log message.
		This field is for future use. All messages are
		currently logged at priority 'notice'"
    ::= { mLogMessage 2 }

    mLogMessageText OBJECT-TYPE
  	SYNTAX	DisplayString
  	ACCESS  read-only
   	STATUS  mandatory
  	DESCRIPTION
  		"The text of the log message."
    ::= { mLogMessage 3 }

    mLogTimeOfDay OBJECT-TYPE
  	SYNTAX	INTEGER
  	ACCESS  read-only
   	STATUS  mandatory
  	DESCRIPTION
  		"The time of day at which the message is logged.  This is
		expressed in seconds."
    ::= { mLogMessage 4 }

  -- Node: scc		These are counters associated with the SCC on a device
  --			which has localtalk ports.

    sccTable OBJECT-TYPE
  	SYNTAX  SEQUENCE OF SCCEntry
  	ACCESS  not-accessible
  	STATUS  mandatory
	DESCRIPTION
		"Each row of this table describes a (Zilog) 8530 
		Serial Communications Controller."
    ::= { scc 1 }
	
    sccEntry OBJECT-TYPE
  	SYNTAX  SCCEntry
  	ACCESS  not-accessible
  	STATUS  mandatory
	DESCRIPTION
		"The object type of the rows in sccTable.  If an interface
		does not have an SCC there will not be a row in the table
		for that interface's value of ifIndex."
	INDEX	{ ifIndex }
    ::= { sccTable 1 }

    SCCEntry ::= SEQUENCE {
	sccInterrupts		Counter,
	sccAborts  		Counter,
	sccSpuriousInts		Counter,
	sccDeferTimeouts  	Counter,
	sccOverruns		Counter,
	sccUnderruns   		Counter
    }

    sccInterrupts OBJECT-TYPE
  	SYNTAX  Counter
  	ACCESS  read-only
  	STATUS  mandatory
	DESCRIPTION
		"Number of receive interrupts generated by the SCC."
    ::= { sccEntry 1 }

    sccAborts OBJECT-TYPE
  	SYNTAX  Counter
  	ACCESS  read-only
  	STATUS  mandatory
	DESCRIPTION
		"The number of abort interrupts generated by the SCC."
    ::= { sccEntry 2 }

    sccSpuriousInts OBJECT-TYPE
  	SYNTAX  Counter
  	ACCESS  read-only
  	STATUS  mandatory
	DESCRIPTION
		"The number of spurious interrupts generated by the SCC."
    ::= { sccEntry 3 }

    sccDeferTimeouts OBJECT-TYPE
  	SYNTAX  Counter
  	ACCESS  read-only
  	STATUS  mandatory
	DESCRIPTION
		"Total number of defer timeouts.  A defer timeout is the
		condition in which the line did not become idle for one
		and a half packet times, while the SCC was waiting to
		transmit, forcing a reset of the receiver.  This event
		could indicate a misbehaving localtalk device."
    ::= { sccEntry 4 }

    sccOverruns OBJECT-TYPE
  	SYNTAX  Counter
  	ACCESS  read-only
  	STATUS  mandatory
	DESCRIPTION
		"Total receive overruns."
    ::= { sccEntry 5 }

    sccUnderruns OBJECT-TYPE
  	SYNTAX  Counter
  	ACCESS  read-only
  	STATUS  mandatory
	DESCRIPTION
		"Total receive underruns."
    ::= { sccEntry 6 }

  -- Node: products
  -- Node: fastpath
  -- Node: fpBuffer

    bufferSize OBJECT-TYPE
  	SYNTAX  INTEGER
  	ACCESS  read-only
  	STATUS  mandatory
	DESCRIPTION
		"The size of the buffers in the buffer pool.  All buffers are
		the same size."
    ::= { fpBuffer 1 }

    bufferAvail OBJECT-TYPE
  	SYNTAX  INTEGER
  	ACCESS  read-only
  	STATUS  mandatory
	DESCRIPTION
		"The total number of buffers initialized.  This does not
		indicate the number of currently free buffers.  Rather
		it is the total number of buffers which were created and
		made free at boot time."
    ::= { fpBuffer 2 }

    bufferDrops OBJECT-TYPE
  	SYNTAX  Counter
  	ACCESS  read-only
  	STATUS  mandatory
	DESCRIPTION
		"The total number of times that a buffer was requested when
		none was available."
    ::= { fpBuffer 3 }

    bufferTypeTable OBJECT-TYPE
  	SYNTAX  SEQUENCE OF BufferTypeEntry
  	ACCESS  not-accessible
  	STATUS  mandatory
	DESCRIPTION
		"Each row of this table describes statistics on buffers
		allocated for a specific purpose. The sum of bufferTypeCount
		for all rows should always equal the bufferAvail count."
    ::= { fpBuffer 4 }

    bufferTypeEntry OBJECT-TYPE
  	SYNTAX  BufferTypeEntry
  	ACCESS  not-accessible
  	STATUS  mandatory
	DESCRIPTION
		"The object type of the rows in bufferTypeTable."
	INDEX	{ bufferTypeIndex }
    ::= { bufferTypeTable 1 }

    BufferTypeEntry ::= SEQUENCE {
  	bufferTypeIndex		INTEGER,
  	bufferTypeType		INTEGER,
  	bufferTypeDescr		DisplayString,
  	bufferTypeCount		INTEGER,
	bufferTypeDrops 	Counter,
	bufferTypeRequests	Counter,
	bufferTypeMaximum	Counter
    }

    bufferTypeIndex OBJECT-TYPE
  	SYNTAX  INTEGER
  	ACCESS  read-only
  	STATUS  mandatory
	DESCRIPTION
		"The enumeration of each buffer type row."
    ::= { bufferTypeEntry 1 }

    bufferTypeType OBJECT-TYPE
  	SYNTAX  INTEGER {
  		other(1),
  		free(2),	-- free for anyone to use
  		localtalk(3),	-- received localtalk data
  		ethernet(4),	-- received ethernet data
  		arp(5),		-- Address Resolution Protocol
  		data(6),	-- general data (packets under construction)
  		erbf(7),	-- available for ethernet receive
  		etbf(8),	-- awaiting ethernet transmit complete
  		malloc(9)	-- long-term storage
  	}
  	ACCESS  read-only
  	STATUS  mandatory
	DESCRIPTION
		"enumerated type of buffer type."
    ::= { bufferTypeEntry 2 }

    bufferTypeDescr OBJECT-TYPE
  	SYNTAX  DisplayString
  	ACCESS  read-only
  	STATUS  mandatory
	DESCRIPTION
		"Text description of buffer type."
    ::= { bufferTypeEntry 3 }

    bufferTypeCount OBJECT-TYPE
  	SYNTAX  INTEGER
  	ACCESS  read-only
  	STATUS  mandatory
	DESCRIPTION
		"The number of buffers of the type which is described by
		the value of bufferTypeType for this row."
    ::= { bufferTypeEntry 4 }

    bufferTypeDrops OBJECT-TYPE
  	SYNTAX  INTEGER			-- should be Counter
  	ACCESS  read-only
  	STATUS  mandatory
	DESCRIPTION
		"The number of requests for buffers this type which were
		not fulfilled because no free buffers were available."
    ::= { bufferTypeEntry 5 }

    bufferTypeRequests OBJECT-TYPE
  	SYNTAX  INTEGER			-- should be Counter
  	ACCESS  read-only
  	STATUS  mandatory
	DESCRIPTION
		"The number of times buffers of this type were requested."
    ::= { bufferTypeEntry 6 }

    bufferTypeMaximum OBJECT-TYPE
  	SYNTAX  INTEGER
  	ACCESS  read-only
  	STATUS  mandatory
	DESCRIPTION
		"A high water mark for buffers of this type.
		This number represents the greatest number of buffers
		of this type ever allocated concurrently."
    ::= { bufferTypeEntry 7 }

  -- Node: fpConf	The FastPath System Configuration Group.  The FastPath
  --			has other configuration variables in other parts of
  --			this and other MIBS.  These variables are those
  --			which are exclusivley associated with the FastPath
  --			architecture/OS, and not with any specific protocol or
  --			function supported by the device.

    confReboot OBJECT-TYPE
  	SYNTAX  TimeTicks
  	ACCESS  read-write
  	STATUS  mandatory
	DESCRIPTION
		"The amount of time, in hundredths of a second, until the
		device reboots itself."
    ::= { fpConf 1 }

    confCheckSum OBJECT-TYPE
  	SYNTAX  INTEGER { valid(1), invalid(2) }
  	ACCESS  read-write
  	STATUS  mandatory
	DESCRIPTION
		"Indicates the validity of the FastPath's configuration.  If
		written to, allows the management station to flush the
		configuration (by setting invalid), or to protect it (by
		setting valid)."
    ::= { fpConf 2 }

    codeCheckSum OBJECT-TYPE
  	SYNTAX  INTEGER  { valid(1), invalid(2) }
  	ACCESS  read-write
  	STATUS  mandatory
	DESCRIPTION
		"Indicates the validity of the FastPath's downloaded image.
		If written to, allows the management station to flush the
		downloaded image (by setting invalid), or to protect the
		it (by setting valid)."
    ::= { fpConf 3 }

    promVersion OBJECT-TYPE
  	SYNTAX  INTEGER
  	ACCESS  read-only
  	STATUS  mandatory
	DESCRIPTION
		"The version number of the PROM multiplied by 100, for
		instance, PROM version 4.1 would return 410."
    ::= { fpConf 4 }

    hwStatus OBJECT-TYPE
  	SYNTAX  INTEGER
  	ACCESS  read-only
  	STATUS  mandatory
	DESCRIPTION
		"This integer is a bit mask which holds the following flags:
			0x000001 - LocalTalk failed tests
			0x000002 - Ethernet controller failed tests
			0x000004 - FP4: The battery is low
			0x000008 - Expansion RAM is present
			0x000010 - FP4: Ethernet 12V Fuse blown
			0x000020 - Expansion RAM failed tests
			0x000040 - FP4: Disable Enet CRS jumper installed
			0x000080 - FP4: Disable Enet SQE jumper installed
			0x000100 - Software Jumper 1 installed
			0x000200 - Software Jumper 2 installed
			0x000400 - Software Jumper 3 installed
			0x000800 - Software Jumper 4 installed
			0x007000 - FP5: EtherModule type field
			0x008000 - FP5: EtherModule type field is valid
			0x010000 - FP5: RAM Bank 3 is present
			0x020000 - FP5: RAM Bank 3 failed tests
			0x040000 - FP5: RAM Bank 4 is present
			0x080000 - FP5: RAM Bank 4 failed tests
			0x100000 - FP5: Downloader mode
			0x200000 - FP5: Software Jumper 5 installed
			0x400000 - FP5: Hardware has LocalTalk IOP"
    ::= { fpConf 5 }

    confWhyReboot OBJECT-TYPE
  	SYNTAX  INTEGER {
		other(1),		-- none of the following
		hardware(2),		-- hardware maintenance
		firmware(3),		-- firmware maintenance
		software(4),		-- software maintenance
		config(5)		-- configuration change
	}
  	ACCESS  read-write
  	STATUS  mandatory
	DESCRIPTION
		"Reason code for reboot scheduled by confReboot"
    ::= { fpConf 6 }

    confWhoReboot OBJECT-TYPE
  	SYNTAX  DisplayString
  	ACCESS  read-write
  	STATUS  mandatory
	DESCRIPTION
		"Person responsible for reboot scheduled by confReboot"
    ::= { fpConf 7 }

    confRebootComment OBJECT-TYPE
  	SYNTAX  DisplayString
  	ACCESS  read-write
  	STATUS  mandatory
	DESCRIPTION
		"Comment string for reboot scheduled by confReboot"
    ::= { fpConf 8 }

    confHowReboot OBJECT-TYPE
  	SYNTAX  INTEGER {
		restart(1),		-- reboot, with 25sec delay
					-- checking conf and code sums
		go(2),			-- immediate restart
					-- without checking sums
		pause(3),		-- stay in PROM/VROM mode
		reset(4),		-- reset code and configuration
		bootprom(5)		-- reboot to BOOTPROM (FP5 only)
	}
  	ACCESS  read-write
  	STATUS  mandatory
	DESCRIPTION
		"Action taken when reboot scheduled by confReboot occurs"
    ::= { fpConf 9 }

  -- Node: tATalk	Supplementary AppleTalk-related variables.
  --			This group is in the temporary area because there is
  --			an Experimental AppleTalk MIB which will become an
  --			Internet Standard, and which may someday hold these
  --			variables

    tRTMPEntryTimeouts OBJECT-TYPE
  	SYNTAX	INTEGER			-- should be Counter
  	ACCESS  read-only
  	STATUS  mandatory
  	DESCRIPTION
  		"The number of entries which were removed from 
		routing table because the aging algorithm
  		indicated that they were invalid."
    ::= { tATalk 1 }

    tRTMPEntryDeletes OBJECT-TYPE
  	SYNTAX	INTEGER			-- should be Counter
  	ACCESS  read-only
  	STATUS  mandatory
  	DESCRIPTION
  		"The number of entries which were removed from the
  		routing table for any reason other than aging, for
  		instance, due to a command from a Network
  		Management station."
    ::= { tATalk 2 }

    tRTMPEntryEqualReplaces OBJECT-TYPE
  	SYNTAX	INTEGER			-- should be Counter
  	ACCESS  read-only
  	STATUS  mandatory
  	DESCRIPTION
  		"The number of entries whose route was replaced by
  		another route with the same hop count."
    ::= { tATalk 3 }

    tRTMPEntryBetterReplaces OBJECT-TYPE
  	SYNTAX	INTEGER			-- should be Counter
  	ACCESS  read-only
  	STATUS  mandatory
  	DESCRIPTION
  		"The number of entries whose route was replaced by
  		another route with a lower hop count."
    ::= { tATalk 4 }

    tRTMPEntryAdds OBJECT-TYPE
  	SYNTAX	INTEGER			-- should be Counter
  	ACCESS  read-only
  	STATUS  mandatory
  	DESCRIPTION
  		"The number of new entries which have been added to
  		the table."
    ::= { tATalk 5 }

    tRTMPZeroCounters OBJECT-TYPE
  	SYNTAX	INTEGER { zero(1) }
  	ACCESS  write-only
  	STATUS  mandatory
  	DESCRIPTION
  		"Writing this variable causes all the RTMP variables
  		in this group to be set to zero."
    ::= { tATalk 6 }

    tZIPDeletes OBJECT-TYPE
  	SYNTAX	INTEGER
  	ACCESS  read-only
  	STATUS  mandatory
  	DESCRIPTION
  		"The number of Zones which have been deleted from the
  		Zone Table."
    ::= { tATalk 7 }

    tZIPAdds OBJECT-TYPE
  	SYNTAX	INTEGER
  	ACCESS  read-only
  	STATUS  mandatory
  	DESCRIPTION
  		"The number of Zones which have been added to the
  		Zone Table."
    ::= { tATalk 8 }

    tZIPZeroCounters OBJECT-TYPE
  	SYNTAX	INTEGER { zero(1) }
  	ACCESS  write-only
  	STATUS  mandatory
  	DESCRIPTION
  		"Writing this variable causes all the ZIP variables
  		in this group to be set to zero."
    ::= { tATalk 9 }

    tAARPClearCache OBJECT-TYPE
  	SYNTAX	INTEGER { clear(1) }
  	ACCESS  write-only
  	STATUS  mandatory
  	DESCRIPTION
  		"Writing this variable clears the AARP Cache."
    ::= { tATalk 10 }

    tKIPRoutesValid OBJECT-TYPE
 	SYNTAX  INTEGER { valid(1), invalid(2) }
 	ACCESS  read-write
 	STATUS  mandatory
	DESCRIPTION
		"This variable can be used to force KIP to reacquire its
	 	configuration information."
   ::= { tATalk 11 }

  -- Node: tIP	Supplementary TCP/IP-related variables

    tARPClearCache OBJECT-TYPE
  	SYNTAX	INTEGER { clear(1) }
  	ACCESS  write-only
  	STATUS  mandatory
  	DESCRIPTION
  		"Writing this variable clears the ARP Cache."
    ::= { tIP 1 }

    tIPClearRoutingTable OBJECT-TYPE
  	SYNTAX	INTEGER { clear(1) }
  	ACCESS  write-only
  	STATUS  mandatory
  	DESCRIPTION
  		"Writing this variable clears the entire IP routing
  		table."
    ::= { tIP 2 }

  -- Node: tCommunity	Variables for configuring SNMP access to a device
  --			This group is in the temporary area because it
  --			it will be affected by the SNMP Authentication
  --			mechanisms which are currently being defined.  More
  --			importantly, this is an experiment.

    tCommunityTrapHostType OBJECT-TYPE
  	SYNTAX	INTEGER {
  		unconfigured(1), 	-- address to be ignored
  		ip(2) 			-- address is a four byte IP address
  	}
  	ACCESS  read-write
   	STATUS  mandatory
  	DESCRIPTION
  		"This is the address family of the trap host.  The Trap Host
		is the host to which the device sends all traps."
    ::= { tCommunity 1 }

    tCommunityTrapHostAddress OBJECT-TYPE
  	SYNTAX	OCTET STRING
  	ACCESS  read-write
   	STATUS  mandatory
  	DESCRIPTION
  		"This is the Network Address of the host.  It is interpreted
		according to the value of tCommunityTrapHostType."
    ::= { tCommunity 2 }

    tCommunitySetHostType OBJECT-TYPE
  	SYNTAX	INTEGER {
  		unconfigured(1), 	-- address to be ignored
  		ip(2) 			-- address is a four byte IP address
  	}
  	ACCESS  read-write
   	STATUS  mandatory
  	DESCRIPTION
  		"This is the address family of the set host.  The Set Host is
		a host which is privileged to change any MIB variable."
    ::= { tCommunity 3 }

    tCommunitySetHostAddress OBJECT-TYPE
  	SYNTAX	OCTET STRING
  	ACCESS  read-write
   	STATUS  mandatory
  	DESCRIPTION
  		"This is the Network Address of the Set Host.  It is
		interpreted  according to the value of
		tCommunityTrapHostType."
    ::= { tCommunity 4 }

    tCommunityList OBJECT-TYPE
	SYNTAX SEQUENCE OF TCommunity
	ACCESS not-accessible
	STATUS mandatory
	DESCRIPTION
		"The Communities Table describes the various communities
		known to the the device."
    ::= { tCommunity 5 }

     tCommunityEntry OBJECT-TYPE
	SYNTAX	TCommunity
	ACCESS	not-accessible
	STATUS	mandatory
	DESCRIPTION
		"The type of a row object in the community table.  This
		represents a single SNMP Community.  Community entries
		are indexed by counting integers starting with 1."
	--INDEX { INTEGER }
    ::= { tCommunityList 1 }

   TCommunity ::= SEQUENCE {
	tCommunityName		DisplayString,
	tCommunityAccess	INTEGER
    }

    tCommunityName OBJECT-TYPE
	SYNTAX DisplayString
	ACCESS read-write
	STATUS mandatory
	DESCRIPTION
		"The name of this community."
    ::= { tCommunityEntry 1 }

    tCommunityAccess OBJECT-TYPE
	SYNTAX INTEGER {
		no-access(1),		
		read-only-access(2),	-- name changed for Sun Net Manager!
		clear-statistics(3),
		configure(4)
	}
	ACCESS read-write
	STATUS mandatory
	DESCRIPTION
		"This defines the privilege of the community.  A 'read-only'
		community can examine any readable variable.  A
		'clear-statistics' community can reset non-critical counters.
		A 'configure' community has complete privileges.  By setting
		the community access to 'no-access', a management station
		can deny all access by that community."
    ::= { tCommunityEntry 2 }
	

  -- Node: tEther	Variables which give statistics for ethernet.
  --			This group is in the temporary area because it
  --			it should be replaced by the IETF Ethernet
  --			MIB.  This group corresponds to the ethernet
  --			group in the Kinetics/Excellan FastPath MIB.

    tEtherTable OBJECT-TYPE
	SYNTAX SEQUENCE OF TEther
	ACCESS not-accessible
	STATUS mandatory
	DESCRIPTION
		"Table of statistics for the ethernet interfaces of a device."
    ::= { tEther 1 }

     tEtherEntry OBJECT-TYPE
	SYNTAX	TEther
	ACCESS	not-accessible
	STATUS	mandatory
	DESCRIPTION
		"The type of a row object in the ethernet table.  This
		represents a single Ethernet Interface.  If an interface
		is not an Ethernet interface, there will not be a row in
		this table for that interface's value of ifIndex."
	INDEX { ifIndex }
    ::= { tEtherTable 1 }

   TEther ::= SEQUENCE {
	    etherCRCErrors	Counter,
	    etherAlignErrors	Counter,
	    etherResourceErrors	Counter,
	    etherOverrunErrors	Counter,
	    etherInPackets	Counter,
	    etherOutPackets	Counter,
	    etherBadTransmits	Counter,
	    etherOversizeFrames	Counter,
	    etherSpurRUReadys	Counter,
	    etherSpurCUActives	Counter,
	    etherSpurUnknowns	Counter,
	    etherBcastDrops	Counter,
	    etherReceiverRestarts Counter,
	    etherReinterrupts	Counter,
	    etherBufferReroutes	Counter,
	    etherBufferDrops	Counter,
	    etherCollisions	Counter,
	    etherDefers		Counter,
	    etherDMAUnderruns	Counter,
	    etherMaxCollisions	Counter,
	    etherNoCarriers	Counter,
	    etherNoCTSs		Counter,
	    etherNoSQEs		Counter
    }

    etherCRCErrors OBJECT-TYPE
	    SYNTAX  Counter
	    ACCESS  read-only
	    STATUS  mandatory
	    DESCRIPTION
		"The total number of CRC errors
		on this ethernet interface"
	    ::= { tEtherEntry 1 }

    etherAlignErrors OBJECT-TYPE
	    SYNTAX  Counter
	    ACCESS  read-only
	    STATUS  mandatory
	    DESCRIPTION
		"The total number of alignment errors
		on this ethernet interface."
	    ::= { tEtherEntry 2 }

    etherResourceErrors OBJECT-TYPE
	    SYNTAX  Counter
	    ACCESS  read-only
	    STATUS  mandatory
	    DESCRIPTION
		"The total number of errors due to lack of resources
		on this ethernet interface."
	    ::= { tEtherEntry 3 }

    etherOverrunErrors OBJECT-TYPE
	    SYNTAX  Counter
	    ACCESS  read-only
	    STATUS  mandatory
	    DESCRIPTION
		"The total number of overrun errors
		on this ethernet interface."
	    ::= { tEtherEntry 4 }

    etherInPackets OBJECT-TYPE
	    SYNTAX  Counter
	    ACCESS  read-only
	    STATUS  mandatory
	    DESCRIPTION
		"The total number of input packets on this ethernet interface."
	    ::= { tEtherEntry 5 }

    etherOutPackets OBJECT-TYPE
	    SYNTAX  Counter
	    ACCESS  read-only
	    STATUS  mandatory
	    DESCRIPTION
		"The total number of output packets
		on this ethernet interface."
	    ::= { tEtherEntry 6 }

    etherBadTransmits OBJECT-TYPE
	    SYNTAX  Counter
	    ACCESS  read-only
	    STATUS  mandatory
	    DESCRIPTION
		"The total number of transmission errors
		on this ethernet interface."
	    ::= { tEtherEntry 7 }

    etherOversizeFrames OBJECT-TYPE
	    SYNTAX  Counter
	    ACCESS  read-only
	    STATUS  mandatory
	    DESCRIPTION
		"The total number of oversize frame errors
		on this ethernet interface."
	    ::= { tEtherEntry 8 }

    etherSpurRUReadys OBJECT-TYPE
	    SYNTAX  Counter
	    ACCESS  read-only
	    STATUS  mandatory
	    DESCRIPTION
		"The total number of spurious RU Ready interrupts
		on this ethernet interface."
	    ::= { tEtherEntry 9 }

    etherSpurCUActives OBJECT-TYPE
	    SYNTAX  Counter
	    ACCESS  read-only
	    STATUS  mandatory
	    DESCRIPTION
		"The total number of spurious CU Active interrupts
		on this ethernet interface."
	    ::= { tEtherEntry 10 }

    etherSpurUnknowns OBJECT-TYPE
	    SYNTAX  Counter
	    ACCESS  read-only
	    STATUS  mandatory
	    DESCRIPTION
		"The total number of unknown spurious interrupts
		on this ethernet interface."
	    ::= { tEtherEntry 11 }

    etherBcastDrops OBJECT-TYPE
	    SYNTAX  Counter
	    ACCESS  read-only
	    STATUS  mandatory
	    DESCRIPTION
		"The total number of broadcast packets dropped
		to free resources on this ethernet interface."
	    ::= { tEtherEntry 12 }

    etherReceiverRestarts OBJECT-TYPE
	    SYNTAX  Counter
	    ACCESS  read-only
	    STATUS  mandatory
	    DESCRIPTION
		"The total number of receiver restarts
		on this ethernet interface."
	    ::= { tEtherEntry 13 }

    etherReinterrupts OBJECT-TYPE
	    SYNTAX  Counter
	    ACCESS  read-only
	    STATUS  mandatory
	    DESCRIPTION
		"The total number of reinterrupts on this ethernet interface."
	    ::= { tEtherEntry 14 }

    etherBufferReroutes OBJECT-TYPE
	    SYNTAX  Counter
	    ACCESS  read-only
	    STATUS  mandatory
	    DESCRIPTION
		"The total number of buffers taken off of queues
		to service incoming packets on this ethernet interface."
	    ::= { tEtherEntry 15 }

    etherBufferDrops OBJECT-TYPE
	    SYNTAX  Counter
	    ACCESS  read-only
	    STATUS  mandatory
	    DESCRIPTION
		"The total number of buffers dropped
		on this ethernet interface."
	    ::= { tEtherEntry 16 }

    etherCollisions OBJECT-TYPE
	    SYNTAX  Counter
	    ACCESS  read-only
	    STATUS  mandatory
	    DESCRIPTION
		"The total number of collisions encountered
		on this ethernet interface."
	    ::= { tEtherEntry 17 }

    etherDefers OBJECT-TYPE
	    SYNTAX  Counter
	    ACCESS  read-only
	    STATUS  mandatory
	    DESCRIPTION
		"The total number of deferrals encountered
		on this ethernet interface."
	    ::= { tEtherEntry 18 }

    etherDMAUnderruns OBJECT-TYPE
	    SYNTAX  Counter
	    ACCESS  read-only
	    STATUS  mandatory
	    DESCRIPTION
		"The total number of DMA Underruns
		on this ethernet interface."
	    ::= { tEtherEntry 19 }

    etherMaxCollisions OBJECT-TYPE
	    SYNTAX  Counter
	    ACCESS  read-only
	    STATUS  mandatory
	    DESCRIPTION
		"The total number of packets dropped
		on this ethernet interface because
		they encountered more than 16 collisions."
	    ::= { tEtherEntry 20 }

    etherNoCarriers OBJECT-TYPE
	    SYNTAX  Counter
	    ACCESS  read-only
	    STATUS  mandatory
	    DESCRIPTION
		"The total number of no carrier errors
		experienced on this ethernet interface."
	    ::= { tEtherEntry 21 }

    etherNoCTSs OBJECT-TYPE
	    SYNTAX  Counter
	    ACCESS  read-only
	    STATUS  mandatory
	    DESCRIPTION
		"The total number of no CTS errors
		experienced on this ethernet interface."
	    ::= { tEtherEntry 22 }

    etherNoSQEs OBJECT-TYPE
	    SYNTAX  Counter
	    ACCESS  read-only
	    STATUS  mandatory
	    DESCRIPTION
		"The total number of no SQE errors
		experienced on this ethernet interface."
	    ::= { tEtherEntry 23 }

    END
