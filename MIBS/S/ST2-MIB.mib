ST2-MIB DEFINITIONS ::= BEGIN

         IMPORTS
              IpAddress, Counter, Gauge, TimeTicks
                     FROM RFC1155-SMI
              OBJECT-TYPE
                     FROM RFC-1212
              DisplayString
                     FROM RFC1213-MIB
	      wfSt2Group
	      	     FROM Wellfleet-ST2-MIB;


-- ST2 MIB

stii          OBJECT IDENTIFIER ::= { wfSt2Group 5 }

-- st2 Object Definitions

st2AgentCopyright OBJECT-TYPE
    SYNTAX  DisplayString
    ACCESS  read-only
    STATUS  mandatory
    DESCRIPTION
      "provider of (company which wrote) the ST-II agent code, code release info and copyright info"
    ::= { stii 1 }

st2ProtoVersion OBJECT-TYPE
    SYNTAX  DisplayString
    ACCESS  read-only
    STATUS  mandatory
    DESCRIPTION
      "version of ST-II running; RFC-1190 for starters"
    ::= { stii 2 }

st2FlowSpecVersion OBJECT-TYPE
    SYNTAX  INTEGER
    ACCESS  read-only
    STATUS  mandatory
    DESCRIPTION
      "registered version number of Flow Spec"
    ::= { stii 3 }

st2AgentType OBJECT-TYPE
    SYNTAX  INTEGER {
	other(1),
	intermediateSystem(2),
	endSystem(3),
	intermediateAndEndSystem(4)
	}
    ACCESS  read-only
    STATUS  mandatory
    DESCRIPTION
      "whether this system performs ST-II end-system or intermediate-system functions or both"
    ::= { stii 4 }

st2RoutingDerived OBJECT-TYPE
    SYNTAX  INTEGER {
	other(1),
	fixed(2),
	regularIP(3)
	}
    ACCESS  read-only
    STATUS  mandatory
    DESCRIPTION
      "where does ST-II get routes from, whether IP routing tables or some other means"
    ::= { stii 5 }

st2ToAccept OBJECT-TYPE
    SYNTAX  TimeTicks
    ACCESS  read-write
    STATUS  mandatory
    DESCRIPTION
      "Initial hop-by-hop timeout for acknowledgment of ACCEPT"
    ::= { stii 6 }

st2NAccept OBJECT-TYPE
    SYNTAX  INTEGER
    ACCESS  read-write
    STATUS  mandatory
    DESCRIPTION
      "number of ACCEPT retries before returning a failure"
    ::= { stii 7 }

st2ToConnect OBJECT-TYPE
    SYNTAX  TimeTicks
    ACCESS  read-write
    STATUS  mandatory
    DESCRIPTION
      "Initial hop-by-hop timeout for acknowledgment of CONNECT"
    ::= { stii 8 }

st2NConnect OBJECT-TYPE
    SYNTAX  INTEGER
    ACCESS  read-write
    STATUS  mandatory
    DESCRIPTION
      "number of CONNECT retries before returning a failure"
    ::= { stii 9 }

st2ToDisconnect OBJECT-TYPE
    SYNTAX  TimeTicks
    ACCESS  read-write
    STATUS  mandatory
    DESCRIPTION
      "Initial hop-by-hop timeout for acknowledgment of DISCONNECT"
    ::= { stii 10 }

st2NDisconnect OBJECT-TYPE
    SYNTAX  INTEGER
    ACCESS  read-write
    STATUS  mandatory
    DESCRIPTION
      "number of DISCONNECT retries before returning a failure"
    ::= { stii 11 }

st2ToHidAck OBJECT-TYPE
    SYNTAX  TimeTicks
    ACCESS  read-write
    STATUS  mandatory
    DESCRIPTION
      "Initial hop-by-hop timeout for acknowledgment of HID-CHANGE-REQUEST"
    ::= { stii 12 }

st2NHidAck OBJECT-TYPE
    SYNTAX  INTEGER
    ACCESS  read-write
    STATUS  mandatory
    DESCRIPTION
      "number of HID-CHANGE-REQUEST retries before returning a failure"
    ::= { stii 13 }

st2ToHidChange OBJECT-TYPE
    SYNTAX  TimeTicks
    ACCESS  read-write
    STATUS  mandatory
    DESCRIPTION
      "Initial hop-by-hop timeout for acknowledgment of HID-CHANGE"
    ::= { stii 14 }

st2NHidChange OBJECT-TYPE
    SYNTAX  INTEGER
    ACCESS  read-write
    STATUS  mandatory
    DESCRIPTION
      "number of HID-CHANGE retries before returning a failure"
    ::= { stii 15 }

st2ToNotify OBJECT-TYPE
    SYNTAX  TimeTicks
    ACCESS  read-write
    STATUS  mandatory
    DESCRIPTION
      "Initial hop-by-hop timeout for acknowledgment of NOTIFY"
    ::= { stii 16 }

st2NNotify OBJECT-TYPE
    SYNTAX  INTEGER
    ACCESS  read-write
    STATUS  mandatory
    DESCRIPTION
      "number of NOTIFY retries before returning a failure"
    ::= { stii 17 }

st2ToRefuse OBJECT-TYPE
    SYNTAX  TimeTicks
    ACCESS  read-write
    STATUS  mandatory
    DESCRIPTION
      "Initial hop-by-hop timeout for acknowledgment of REFUSE"
    ::= { stii 18 }

st2NRefuse OBJECT-TYPE
    SYNTAX  INTEGER
    ACCESS  read-write
    STATUS  mandatory
    DESCRIPTION
      "number of REFUSE retries before returning a failure"
    ::= { stii 19 }

st2ToReroute OBJECT-TYPE
    SYNTAX  TimeTicks
    ACCESS  read-write
    STATUS  mandatory
    DESCRIPTION
      "Timeout for receipt of ACCEPT or REFUSE from targets during failure recovery, allowing intermediate systems time to try recovery"
    ::= { stii 20 }

st2NReroute OBJECT-TYPE
    SYNTAX  INTEGER
    ACCESS  read-write
    STATUS  mandatory
    DESCRIPTION
      "number of CONNECT retries before returning a failure from targets"
    ::= { stii 21 }

st2ToEnd2End OBJECT-TYPE
    SYNTAX  TimeTicks
    ACCESS  read-write
    STATUS  mandatory
    DESCRIPTION
      "End-to-end timeout for receipt of ACCEPT or REFUSE from targets by origin during failure recovery, allowing intermediate systems time to try recovery"
    ::= { stii 22 }

st2NEnd2End OBJECT-TYPE
    SYNTAX  INTEGER
    ACCESS  read-write
    STATUS  mandatory
    DESCRIPTION
      "number of CONNECT retries before origin returns a failure from targets"
    ::= { stii 23 }

st2NHidAbort OBJECT-TYPE
    SYNTAX  INTEGER
    ACCESS  read-write
    STATUS  mandatory
    DESCRIPTION
      "Number of rejected HID proposals before aborting the HID negotiation process"
    ::= { stii 24 }

st2HelloTimerHoldDown OBJECT-TYPE
    SYNTAX  TimeTicks
    ACCESS  read-write
    STATUS  mandatory
    DESCRIPTION
      "Interval that Restarted bit must be set after ST Agent restart"
    ::= { stii 25 }

st2HelloLossFactor OBJECT-TYPE
    SYNTAX  INTEGER
    ACCESS  read-write
    STATUS  mandatory
    DESCRIPTION
      "Number of consecutively missed HELLO messages before declaring link failure to neighbor"
    ::= { stii 26 }

st2DefaultRecoveryTimeout OBJECT-TYPE
    SYNTAX  TimeTicks
    ACCESS  read-write
    STATUS  mandatory
    DESCRIPTION
      "Default for interval between successive HELLOs to/from active neighbors"
    ::= { stii 27 }

st2DefaultHelloFactor OBJECT-TYPE
    SYNTAX  INTEGER
    ACCESS  read-write
    STATUS  mandatory
    DESCRIPTION
      "HELLO filtering function factor"
    ::= { stii 28 }

st2ScmpRcvdOctets OBJECT-TYPE
    SYNTAX  Counter
    ACCESS  read-only
    STATUS  mandatory
    DESCRIPTION
      "Total octets of SCMP messages received"
    ::= { stii 29 }

st2ScmpSentOctets OBJECT-TYPE
    SYNTAX  Counter
    ACCESS  read-only
    STATUS  mandatory
    DESCRIPTION
      "Total octets of SCMP messages sent"
    ::= { stii 30 }

st2ScmpRcvdBadTypes OBJECT-TYPE
    SYNTAX  Counter
    ACCESS  read-only
    STATUS  mandatory
    DESCRIPTION
      "Count of SCMP messages received with bad type field"
    ::= { stii 31 }

st2ScmpRcvdBadCks OBJECT-TYPE
    SYNTAX  Counter
    ACCESS  read-only
    STATUS  mandatory
    DESCRIPTION
      "Count of SCMP messages received with bad checksum"
    ::= { stii 32 }

st2ScmpSentAccepts OBJECT-TYPE
    SYNTAX  Counter
    ACCESS  read-only
    STATUS  mandatory
    DESCRIPTION
      "Count of SCMP ACCEPT messages sent"
    ::= { stii 33 }

st2ScmpSentAcks OBJECT-TYPE
    SYNTAX  Counter
    ACCESS  read-only
    STATUS  mandatory
    DESCRIPTION
      "Count of SCMP ACK messages sent"
    ::= { stii 34 }

st2ScmpSentChanges OBJECT-TYPE
    SYNTAX  Counter
    ACCESS  read-only
    STATUS  mandatory
    DESCRIPTION
      "Count of SCMP CHANGE messages sent"
    ::= { stii 35 }

st2ScmpSentChangeReqs OBJECT-TYPE
    SYNTAX  Counter
    ACCESS  read-only
    STATUS  mandatory
    DESCRIPTION
      "Count of SCMP CHANGE-REQUEST messages sent"
    ::= { stii 36 }

st2ScmpSentConnects OBJECT-TYPE
    SYNTAX  Counter
    ACCESS  read-only
    STATUS  mandatory
    DESCRIPTION
      "Count of SCMP CONNECT messages sent"
    ::= { stii 37 }

st2ScmpSentDisconnects OBJECT-TYPE
    SYNTAX  Counter
    ACCESS  read-only
    STATUS  mandatory
    DESCRIPTION
      "Count of SCMP DISCONNECT messages sent"
    ::= { stii 38 }

st2ScmpSentErrorInReqs OBJECT-TYPE
    SYNTAX  Counter
    ACCESS  read-only
    STATUS  mandatory
    DESCRIPTION
      "Count of SCMP ERROR-IN-REQUEST messages sent"
    ::= { stii 39 }

st2ScmpSentErrorInResps OBJECT-TYPE
    SYNTAX  Counter
    ACCESS  read-only
    STATUS  mandatory
    DESCRIPTION
      "Count of SCMP ERROR-IN-RESPONSE messages sent"
    ::= { stii 40 }

st2ScmpSentHellos OBJECT-TYPE
    SYNTAX  Counter
    ACCESS  read-only
    STATUS  mandatory
    DESCRIPTION
      "Count of SCMP HELLO messages sent"
    ::= { stii 41 }

st2ScmpSentHidApproves OBJECT-TYPE
    SYNTAX  Counter
    ACCESS  read-only
    STATUS  mandatory
    DESCRIPTION
      "Count of SCMP HID-APPROVE messages sent"
    ::= { stii 42 }

st2ScmpSentHidChanges OBJECT-TYPE
    SYNTAX  Counter
    ACCESS  read-only
    STATUS  mandatory
    DESCRIPTION
      "Count of SCMP HID-CHANGE messages sent"
    ::= { stii 43 }

st2ScmpSentHidChangeReqs OBJECT-TYPE
    SYNTAX  Counter
    ACCESS  read-only
    STATUS  mandatory
    DESCRIPTION
      "Count of SCMP HID-CHANGE-REQUEST messages sent"
    ::= { stii 44 }

st2ScmpSentHidRejects OBJECT-TYPE
    SYNTAX  Counter
    ACCESS  read-only
    STATUS  mandatory
    DESCRIPTION
      "Count of SCMP HID-REJECT messages sent"
    ::= { stii 45 }

st2ScmpSentNotifys OBJECT-TYPE
    SYNTAX  Counter
    ACCESS  read-only
    STATUS  mandatory
    DESCRIPTION
      "Count of SCMP NOTIFY messages sent"
    ::= { stii 46 }

st2ScmpSentRefuses OBJECT-TYPE
    SYNTAX  Counter
    ACCESS  read-only
    STATUS  mandatory
    DESCRIPTION
      "Count of SCMP REFUSE messages sent"
    ::= { stii 47 }

st2ScmpSentStatus OBJECT-TYPE
    SYNTAX  Counter
    ACCESS  read-only
    STATUS  mandatory
    DESCRIPTION
      "Count of SCMP STATUS messages sent"
    ::= { stii 48 }

st2ScmpSentStatusResps OBJECT-TYPE
    SYNTAX  Counter
    ACCESS  read-only
    STATUS  mandatory
    DESCRIPTION
      "Count of SCMP STATUS-RESPONSE messages sent"
    ::= { stii 49 }

st2ScmpRcvdAccepts OBJECT-TYPE
    SYNTAX  Counter
    ACCESS  read-only
    STATUS  mandatory
    DESCRIPTION
      "Count of SCMP ACCEPT messages received"
    ::= { stii 50 }

st2ScmpRcvdAcks OBJECT-TYPE
    SYNTAX  Counter
    ACCESS  read-only
    STATUS  mandatory
    DESCRIPTION
      "Count of SCMP ACK messages received"
    ::= { stii 51 }

st2ScmpRcvdChanges OBJECT-TYPE
    SYNTAX  Counter
    ACCESS  read-only
    STATUS  mandatory
    DESCRIPTION
      "Count of SCMP CHANGE messages received"
    ::= { stii 52 }

st2ScmpRcvdChangeReqs OBJECT-TYPE
    SYNTAX  Counter
    ACCESS  read-only
    STATUS  mandatory
    DESCRIPTION
      "Count of SCMP CHANGE-REQUEST messages received"
    ::= { stii 53 }

st2ScmpRcvdConnects OBJECT-TYPE
    SYNTAX  Counter
    ACCESS  read-only
    STATUS  mandatory
    DESCRIPTION
      "Count of SCMP CONNECT messages received"
    ::= { stii 54 }

st2ScmpRcvdDisconnects OBJECT-TYPE
    SYNTAX  Counter
    ACCESS  read-only
    STATUS  mandatory
    DESCRIPTION
      "Count of SCMP DISCONNECT messages received"
    ::= { stii 55 }

st2ScmpRcvdErrorInReqs OBJECT-TYPE
    SYNTAX  Counter
    ACCESS  read-only
    STATUS  mandatory
    DESCRIPTION
      "Count of SCMP ERROR-IN-REQUEST messages received"
    ::= { stii 56 }

st2ScmpRcvdErrorInResps OBJECT-TYPE
    SYNTAX  Counter
    ACCESS  read-only
    STATUS  mandatory
    DESCRIPTION
      "Count of SCMP ERROR-IN-RESPONSE messages received"
    ::= { stii 57 }

st2ScmpRcvdHellos OBJECT-TYPE
    SYNTAX  Counter
    ACCESS  read-only
    STATUS  mandatory
    DESCRIPTION
      "Count of SCMP HELLO messages received"
    ::= { stii 58 }

st2ScmpRcvdHidApproves OBJECT-TYPE
    SYNTAX  Counter
    ACCESS  read-only
    STATUS  mandatory
    DESCRIPTION
      "Count of SCMP HID-APPROVE messages received"
    ::= { stii 59 }

st2ScmpRcvdHidChanges OBJECT-TYPE
    SYNTAX  Counter
    ACCESS  read-only
    STATUS  mandatory
    DESCRIPTION
      "Count of SCMP HID-CHANGE messages received"
    ::= { stii 60 }

st2ScmpRcvdHidChangeReqs OBJECT-TYPE
    SYNTAX  Counter
    ACCESS  read-only
    STATUS  mandatory
    DESCRIPTION
      "Count of SCMP HID-CHANGE-REQUEST messages received"
    ::= { stii 61 }

st2ScmpRcvdHidRejects OBJECT-TYPE
    SYNTAX  Counter
    ACCESS  read-only
    STATUS  mandatory
    DESCRIPTION
      "Count of SCMP HID-REJECT messages received"
    ::= { stii 62 }

st2ScmpRcvdNotifys OBJECT-TYPE
    SYNTAX  Counter
    ACCESS  read-only
    STATUS  mandatory
    DESCRIPTION
      "Count of SCMP NOTIFY messages received"
    ::= { stii 63 }

st2ScmpRcvdRefuses OBJECT-TYPE
    SYNTAX  Counter
    ACCESS  read-only
    STATUS  mandatory
    DESCRIPTION
      "Count of SCMP REFUSE messages received"
    ::= { stii 64 }

st2ScmpRcvdStatus OBJECT-TYPE
    SYNTAX  Counter
    ACCESS  read-only
    STATUS  mandatory
    DESCRIPTION
      "Count of SCMP STATUS messages received"
    ::= { stii 65 }

st2ScmpRcvdStatusResps OBJECT-TYPE
    SYNTAX  Counter
    ACCESS  read-only
    STATUS  mandatory
    DESCRIPTION
      "Count of SCMP STATUS-RESPONSE messages received"
    ::= { stii 66 }

st2ScmpRcvdErrorSnap OBJECT-TYPE
    SYNTAX  OCTET STRING (SIZE (20))
    ACCESS  read-only
    STATUS  mandatory
    DESCRIPTION
      "Contents from last SCMP packet received with error"
    ::= { stii 67 }

st2ScmpRcvdBadTypeTime OBJECT-TYPE
    SYNTAX  TimeTicks
    ACCESS  read-only
    STATUS  mandatory
    DESCRIPTION
      "Time that last SCMP packet was received with bad Type field"
    ::= { stii 68 }

st2ScmpRcvdBadCksTime OBJECT-TYPE
    SYNTAX  TimeTicks
    ACCESS  read-only
    STATUS  mandatory
    DESCRIPTION
      "Time that last SCMP packet was received with bad checksum"
    ::= { stii 69 }

st2OriginOpens OBJECT-TYPE
    SYNTAX  Counter
    ACCESS  read-only
    STATUS  mandatory
    DESCRIPTION
      "Count of streams opened with this agent as origin, but they may have since been closed"
    ::= { stii 70 }

st2IntermedOpens OBJECT-TYPE
    SYNTAX  Counter
    ACCESS  read-only
    STATUS  mandatory
    DESCRIPTION
      "Count of streams opened with this agent as intermediate system"
    ::= { stii 71 }

st2TargetOpens OBJECT-TYPE
    SYNTAX  Counter
    ACCESS  read-only
    STATUS  mandatory
    DESCRIPTION
      "Count of streams opened with this agent as target (destination) - may also be counted in intermediate"
    ::= { stii 72 }

st2FailOpens OBJECT-TYPE
    SYNTAX  Counter
    ACCESS  read-only
    STATUS  mandatory
    DESCRIPTION
      "Count of stream opens attempted which did not complete"
    ::= { stii 73 }

st2AcceptTimeouts OBJECT-TYPE
    SYNTAX  Counter
    ACCESS  read-only
    STATUS  mandatory
    DESCRIPTION
      "Count of stream opens failed because ACCEPT did not get acknowledged"
    ::= { stii 74 }

st2ParamChangeFails OBJECT-TYPE
    SYNTAX  Counter
    ACCESS  read-only
    STATUS  mandatory
    DESCRIPTION
      "Count of stream parameter changes which failed"
    ::= { stii 75 }

st2NumStreamEntries OBJECT-TYPE
    SYNTAX  Gauge
    ACCESS  read-only
    STATUS  mandatory
    DESCRIPTION
      "Count of stream table entries (extent of streams table)"
    ::= { stii 76 }

st2NumOpenStreams OBJECT-TYPE
    SYNTAX  Gauge
    ACCESS  read-only
    STATUS  mandatory
    DESCRIPTION
      "Count of streams which are open (number of table entries for them)"
    ::= { stii 77 }

st2NumOpenOriginStreams OBJECT-TYPE
    SYNTAX  Gauge
    ACCESS  read-only
    STATUS  mandatory
    DESCRIPTION
      "Count of current open streams which were originated here"
    ::= { stii 78 }

st2NumHops OBJECT-TYPE
    SYNTAX  Gauge
    ACCESS  read-only
    STATUS  mandatory
    DESCRIPTION
      "Count of Hop entries (extent of next-hop table)"
    ::= { stii 79 }

st2NumNeighbors OBJECT-TYPE
    SYNTAX  Gauge
    ACCESS  read-only
    STATUS  mandatory
    DESCRIPTION
      "Count of Neighbor entries (extent of neighbor table)"
    ::= { stii 80 }

st2NumTargets OBJECT-TYPE
    SYNTAX  Gauge
    ACCESS  read-only
    STATUS  mandatory
    DESCRIPTION
      "Count of target entries (extent of target table)"
    ::= { stii 81 }

st2NumGroups OBJECT-TYPE
    SYNTAX  Gauge
    ACCESS  read-only
    STATUS  mandatory
    DESCRIPTION
      "count of group entries (extent of groups table)"
    ::= { stii 82 }

st2NumSubgroups OBJECT-TYPE
    SYNTAX  Gauge
    ACCESS  read-only
    STATUS  mandatory
    DESCRIPTION
      "Count of subgroup entries (extent of subgroups table)"
    ::= { stii 83 }

st2RouteFailures OBJECT-TYPE
    SYNTAX  Counter
    ACCESS  read-only
    STATUS  mandatory
    DESCRIPTION
      "Count of stream opens failed because no route found"
    ::= { stii 84 }

st2RouteLoops OBJECT-TYPE
    SYNTAX  Counter
    ACCESS  read-only
    STATUS  mandatory
    DESCRIPTION
      "Count of stream opens failed because route inconsistency found, e.g. potential or actual loop"
    ::= { stii 85 }

st2ScmpRetrans OBJECT-TYPE
    SYNTAX  Counter
    ACCESS  read-only
    STATUS  mandatory
    DESCRIPTION
      "count of SCMP control timeout and retransmissions"
    ::= { stii 86 }

st2StreamTable OBJECT-TYPE
    SYNTAX  SEQUENCE OF St2StreamEntry
    ACCESS  not-accessible
    STATUS  mandatory
    DESCRIPTION
      "table of information for each stream"
    ::= { stii 87 }

-- table name stream, upper Stream, syntax SEQUENCE OF St2StreamEntry
st2StreamEntry OBJECT-TYPE
    SYNTAX  St2StreamEntry
    ACCESS  not-accessible
    STATUS  mandatory
DESCRIPTION ""
    INDEX   { st2StreamName, st2StreamPrevHopAddr, st2StreamPrevHopVlid }
    ::= { st2StreamTable 1 }

St2StreamEntry ::=
    SEQUENCE {
        st2StreamName                    OCTET STRING,
	st2StreamPrevHopAddr		 IpAddress,
	st2StreamPrevHopVlid		 INTEGER,
        st2StreamStartTime               TimeTicks,
        st2StreamState                   INTEGER,
        st2StreamStateTime               TimeTicks,
        st2StreamRole                    INTEGER,
        st2StreamGroup                   OCTET STRING,
        st2StreamNumSubgroups            Gauge,
        st2StreamNumNextHops             Gauge,
        st2StreamNumTargets              Gauge,
        st2StreamRefuses                 Counter,
        st2StreamFlowspecChanges         Counter,
        st2StreamFlowDutyFactor          INTEGER,
        st2StreamFlowErrorRate           INTEGER,
        st2StreamFlowPrecedence          INTEGER,
        st2StreamFlowReliability         INTEGER,
        st2StreamFlowTradeoffs           INTEGER,
        st2StreamFlowRecoveryTimeout     INTEGER,
        st2StreamFlowLimitOnCost         INTEGER,
        st2StreamFlowLimitOnDelay        INTEGER,
        st2StreamFlowLimitOnPduBytes     INTEGER,
        st2StreamFlowLimitOnPduRate      INTEGER,
        st2StreamFlowMinBytesXRate       INTEGER,
        st2StreamFlowMeanDelay           INTEGER,
        st2StreamFlowDelayVariance       INTEGER,
        st2StreamFlowDesPduBytes         INTEGER,
        st2StreamFlowDesPduRate          INTEGER,
        st2StreamOptionPtp               INTEGER,
        st2StreamOptionFdx               INTEGER,
        st2StreamOptionRecover           INTEGER,
        st2StreamOptionReverseCharge     INTEGER,
        st2StreamOptionTimestamp         INTEGER
    }

st2StreamName OBJECT-TYPE
    SYNTAX  OCTET STRING (SIZE (10))
    ACCESS  read-only
    STATUS  mandatory
    DESCRIPTION
      "internal format name of this stream"
    ::= { st2StreamEntry 1 }

st2StreamPrevHopAddr OBJECT-TYPE
    SYNTAX  IpAddress
    ACCESS  read-only
    STATUS  mandatory
    DESCRIPTION
      "previous hop entry which feeds data to this node"
    ::= { st2StreamEntry 2 }

st2StreamPrevHopVlid OBJECT-TYPE
    SYNTAX  INTEGER (1..'FFFF'h)
    ACCESS  read-only
    STATUS  mandatory
    DESCRIPTION
      "virtual link identifier of the previous hop"
    ::= { st2StreamEntry 3 }

st2StreamStartTime OBJECT-TYPE
    SYNTAX  TimeTicks
    ACCESS  read-only
    STATUS  mandatory
    DESCRIPTION
      "timestamp when this stream was first entered in this table"
    ::= { st2StreamEntry 4 }

st2StreamState OBJECT-TYPE
    SYNTAX  INTEGER {
	other(1),
	idle(2),
	hidNotOk(3),
	acceptable(4),
	active(5),
	activeReduced(6),
	passive(7)
	}
    ACCESS  read-only
    STATUS  mandatory
    DESCRIPTION
      "current state of this stream at this node"
    ::= { st2StreamEntry 5 }

st2StreamStateTime OBJECT-TYPE
    SYNTAX  TimeTicks
    ACCESS  read-only
    STATUS  mandatory
    DESCRIPTION
      "time this stream entered its current state"
    ::= { st2StreamEntry 6 }

st2StreamRole OBJECT-TYPE
    SYNTAX  INTEGER {
	other(1),
	origin(2),
	target(3),
	intermediate(4),
	intermediateAndTarget(5)
	}
    ACCESS  read-only
    STATUS  mandatory
    DESCRIPTION
      "role that this agent performs for this stream"
    ::= { st2StreamEntry 7 }

st2StreamGroup OBJECT-TYPE
    SYNTAX  OCTET STRING (SIZE (10))
    ACCESS  read-only
    STATUS  mandatory
    DESCRIPTION
      "group (if any) which this stream is in"
    ::= { st2StreamEntry 8 }

st2StreamNumSubgroups OBJECT-TYPE
    SYNTAX  Gauge
    ACCESS  read-only
    STATUS  mandatory
    DESCRIPTION
      "number of subgroups which this stream is in (get info from subgroup table)"
    ::= { st2StreamEntry 9 }

st2StreamNumNextHops OBJECT-TYPE
    SYNTAX  Gauge
    ACCESS  read-only
    STATUS  mandatory
    DESCRIPTION
      "number of nexthops to which this stream feeds data (get info from hop table)"
    ::= { st2StreamEntry 10 }

st2StreamNumTargets OBJECT-TYPE
    SYNTAX  Gauge
    ACCESS  read-only
    STATUS  mandatory
    DESCRIPTION
      "number of targets to which this stream feeds data (get info from target table)"
    ::= { st2StreamEntry 11 }

st2StreamRefuses OBJECT-TYPE
    SYNTAX  Counter
    ACCESS  read-only
    STATUS  mandatory
    DESCRIPTION
      "number of times this stream has suffered the ignominy of getting changes refused"
    ::= { st2StreamEntry 12 }

st2StreamFlowspecChanges OBJECT-TYPE
    SYNTAX  Counter
    ACCESS  read-only
    STATUS  mandatory
    DESCRIPTION
      "number of times this flowspec has been changed over the duration of this stream."
    ::= { st2StreamEntry 13 }

st2StreamFlowPrecedence OBJECT-TYPE
    SYNTAX  INTEGER (0..'FF'h)
    ACCESS  read-only
    STATUS  mandatory
    DESCRIPTION
      "flowspec precedence field (8 bits) -- NOTE: THIS MOVES DOWN BELOW ERROR RATE"
    ::= { st2StreamEntry 14 }

st2StreamFlowDutyFactor OBJECT-TYPE
    SYNTAX  INTEGER (0..'FF'h)
    ACCESS  read-only
    STATUS  mandatory
    DESCRIPTION
      "flowspec dutyfactor field (8 bits)"
    ::= { st2StreamEntry 15 }

st2StreamFlowErrorRate OBJECT-TYPE
    SYNTAX  INTEGER (0..'FF'h)
    ACCESS  read-only
    STATUS  mandatory
    DESCRIPTION
      "flowspec error rate field (8 bits)"
    ::= { st2StreamEntry 16 }

st2StreamFlowReliability OBJECT-TYPE
    SYNTAX  INTEGER (0..'FF'h)
    ACCESS  read-only
    STATUS  mandatory
    DESCRIPTION
      "flowspec reliability field (8 bits)"
    ::= { st2StreamEntry 17 }

st2StreamFlowTradeoffs OBJECT-TYPE
    SYNTAX  INTEGER (0..'FFFF'h)
    ACCESS  read-only
    STATUS  mandatory
    DESCRIPTION
      "flowspec tradeoffs field (16 bits)"
    ::= { st2StreamEntry 18 }

st2StreamFlowRecoveryTimeout OBJECT-TYPE
    SYNTAX  INTEGER (0..'FFFF'h)
    ACCESS  read-only
    STATUS  mandatory
    DESCRIPTION
      "flowspec recovery timeout field (16 bits)"
    ::= { st2StreamEntry 19 }

st2StreamFlowLimitOnCost OBJECT-TYPE
    SYNTAX  INTEGER (0..'FFFF'h)
    ACCESS  read-only
    STATUS  mandatory
    DESCRIPTION
      "flowspec limit on cost field (16 bits)"
    ::= { st2StreamEntry 20 }

st2StreamFlowLimitOnDelay OBJECT-TYPE
    SYNTAX  INTEGER (0..'FFFF'h)
    ACCESS  read-only
    STATUS  mandatory
    DESCRIPTION
      "flowspec limit on delay field (16 bits)"
    ::= { st2StreamEntry 21 }

st2StreamFlowLimitOnPduBytes OBJECT-TYPE
    SYNTAX  INTEGER (0..'FFFF'h)
    ACCESS  read-only
    STATUS  mandatory
    DESCRIPTION
      "flowspec LIMIT ON PDU BYTES (pdu size in octets) field (16 bits)"
    ::= { st2StreamEntry 22 }

st2StreamFlowLimitOnPduRate OBJECT-TYPE
    SYNTAX  INTEGER (0..'FFFF'h)
    ACCESS  read-only
    STATUS  mandatory
    DESCRIPTION
      "flowspec limit on pdu rate field (16 bits)"
    ::= { st2StreamEntry 23 }

st2StreamFlowMinBytesXRate OBJECT-TYPE
    SYNTAX  INTEGER (0..'FFFF'h)
    ACCESS  read-only
    STATUS  mandatory
    DESCRIPTION
      "flowspec min bytes x rate field (product gives bandwidth in bytes per 10 seconds; divide by 1250 for Kbits per second) (32 bits)"
    ::= { st2StreamEntry 24 }

st2StreamFlowMeanDelay OBJECT-TYPE
    SYNTAX  INTEGER (0..'FFFF'h)
    ACCESS  read-only
    STATUS  mandatory
    DESCRIPTION
      "flowspec accumulated mean delay field (32 bits)"
    ::= { st2StreamEntry 25 }

st2StreamFlowDelayVariance OBJECT-TYPE
    SYNTAX  INTEGER (0..'FFFF'h)
    ACCESS  read-only
    STATUS  mandatory
    DESCRIPTION
      "flowspec accumulated delay variance field (32 bits)"
    ::= { st2StreamEntry 26 }

st2StreamFlowDesPduBytes OBJECT-TYPE
    SYNTAX  INTEGER (0..'FFFF'h)
    ACCESS  read-only
    STATUS  mandatory
    DESCRIPTION
      "flowspec desired pdu bytes (size) field (16 bits)"
    ::= { st2StreamEntry 27 }

st2StreamFlowDesPduRate OBJECT-TYPE
    SYNTAX  INTEGER (0..'FFFF'h)
    ACCESS  read-only
    STATUS  mandatory
    DESCRIPTION
      "flowspec desired pdu rate field (16 bits)"
    ::= { st2StreamEntry 28 }

st2StreamOptionPtp OBJECT-TYPE
    SYNTAX  INTEGER { true(1), false(2) }
    ACCESS  read-only
    STATUS  mandatory
    DESCRIPTION
      "true if POINT TO POINT option specified on this stream"
    ::= { st2StreamEntry 29 }

st2StreamOptionFdx OBJECT-TYPE
    SYNTAX  INTEGER { true(1), false(2) }
    ACCESS  read-only
    STATUS  mandatory
    DESCRIPTION
      "true if FULL DUPLEX option specified on this stream; reverse stream is the same but takes a separate stream table entry in this MIB"
    ::= { st2StreamEntry 30 }

st2StreamOptionRecover OBJECT-TYPE
    SYNTAX  INTEGER { true(1), false(2) }
    ACCESS  read-only
    STATUS  mandatory
    DESCRIPTION
      "false if NO RECOVERY option specified for this stream"
    ::= { st2StreamEntry 31 }

st2StreamOptionReverseCharge OBJECT-TYPE
    SYNTAX  INTEGER { true(1), false(2) }
    ACCESS  read-only
    STATUS  mandatory
    DESCRIPTION
      "true if REVERSE CHARGE option specified for this stream"
    ::= { st2StreamEntry 32 }

st2StreamOptionTimestamp OBJECT-TYPE
    SYNTAX  INTEGER (0..3)
    ACCESS  read-only
    STATUS  mandatory
    DESCRIPTION
      "the TIMESTAMP option specified for this stream"
    ::= { st2StreamEntry 33 }

-- st2 Hop Table

st2HopTable OBJECT-TYPE
    SYNTAX  SEQUENCE OF St2HopEntry
    ACCESS  not-accessible
    STATUS  mandatory
    DESCRIPTION
      "table of information for each prev- or next-hop"
    ::= { stii 88 }

-- table name hop, upper Hop, syntax SEQUENCE OF St2HopEntry

st2HopEntry OBJECT-TYPE
    SYNTAX  St2HopEntry
    ACCESS  not-accessible
    STATUS  mandatory
DESCRIPTION ""
 INDEX {st2StreamName,st2StreamPrevHopAddr,st2StreamPrevHopVlid,st2HopNeighborAddr}
    ::= { st2HopTable 1 }

St2HopEntry ::=
    SEQUENCE {
        st2HopHid                        INTEGER,
        st2HopMyVlid                     INTEGER,
        st2HopYourVlid                   INTEGER,
        st2HopState                      INTEGER,
        st2HopStateTime                  TimeTicks,
        st2HopNumTargets                 Gauge,
        st2HopMcastAddr                  IpAddress,
        st2HopErrorCode                  INTEGER,
        st2HopDetectorAddr               IpAddress,
        st2HopNeighborAddr               IpAddress,
        st2HopStreamName                 OCTET STRING,
        st2HopPkts                       Counter,
        st2HopOctets                     Counter,
        st2HopDiscards                   Counter,
        st2HopIpEncap                    INTEGER,
        st2HopIpAddr                     IpAddress,
        st2HopRole                       INTEGER,
        st2HopInterfaceIndex             INTEGER,
        st2HopErrorTime                  TimeTicks
    }

st2HopHid OBJECT-TYPE
    SYNTAX  INTEGER (0..'FFFF'h)
    ACCESS  read-only
    STATUS  mandatory
    DESCRIPTION
      "HID which this node has negotiated with this next hop (and all others on a multicast)"
    ::= { st2HopEntry 1 }

st2HopMyVlid OBJECT-TYPE
    SYNTAX  INTEGER (0..'FFFF'h)
    ACCESS  read-only
    STATUS  mandatory
    DESCRIPTION
      "VLID (table index or something) by which this next hop addresses me"
    ::= { st2HopEntry 2 }

st2HopYourVlid OBJECT-TYPE
    SYNTAX  INTEGER (0..'FFFF'h)
    ACCESS  read-only
    STATUS  mandatory
    DESCRIPTION
      "VLID (table index or something) by which I address this next hop"
    ::= { st2HopEntry 3 }

st2HopState OBJECT-TYPE
    SYNTAX  INTEGER {
	ok(1),
	open(2),
	negotiating(3)
	}
    ACCESS  read-only
    STATUS  mandatory
    DESCRIPTION
      "state of negotiation for this stream to this hop"
    ::= { st2HopEntry 4 }

st2HopStateTime OBJECT-TYPE
    SYNTAX  TimeTicks
    ACCESS  read-only
    STATUS  mandatory
    DESCRIPTION
      "time this state was entered"
    ::= { st2HopEntry 5 }

st2HopNumTargets OBJECT-TYPE
    SYNTAX  Gauge
    ACCESS  read-only
    STATUS  mandatory
    DESCRIPTION
      "number of targets reached via this next hop"
    ::= { st2HopEntry 6 }

st2HopMcastAddr OBJECT-TYPE
    SYNTAX  IpAddress
    ACCESS  read-only
    STATUS  mandatory
    DESCRIPTION
      "multicast address, if any, used to reach this hop and others on same net (for current ST-II, this does not work here)(this should be an IP multicast address, or some magic IP address which translates into local-net multicast"
    ::= { st2HopEntry 7 }

st2HopErrorCode OBJECT-TYPE
    SYNTAX  INTEGER
    ACCESS  read-only
    STATUS  mandatory
    DESCRIPTION
      "refuse code or other error indicator received from next hop"
    ::= { st2HopEntry 8 }

st2HopDetectorAddr OBJECT-TYPE
    SYNTAX  IpAddress
    ACCESS  read-only
    STATUS  mandatory
    DESCRIPTION
      "detector address field from error message received from next hop"
    ::= { st2HopEntry 9 }

st2HopNeighborAddr OBJECT-TYPE
    SYNTAX  IpAddress
    ACCESS  read-only
    STATUS  mandatory
    DESCRIPTION
      "ip address of neighbor which is this next hop (it has the info rfc1190 to all next hops for streams which go through that node)"
    ::= { st2HopEntry 10 }

st2HopStreamName OBJECT-TYPE
    SYNTAX  OCTET STRING (SIZE (10))
    ACCESS  read-only
    STATUS  mandatory
    DESCRIPTION
      "back pointer to stream for which this is a hop"
    ::= { st2HopEntry 11 }

st2HopPkts OBJECT-TYPE
    SYNTAX  Counter
    ACCESS  read-only
    STATUS  mandatory
    DESCRIPTION
      "count of packets received from this hop in this stream, or sent in this stream to this hop, depending on st2HopRole"
    ::= { st2HopEntry 12 }

st2HopOctets OBJECT-TYPE
    SYNTAX  Counter
    ACCESS  read-only
    STATUS  mandatory
    DESCRIPTION
      "count of octets received from this hop in this stream, or sent in this stream to this hop, depending on st2HopRole"
    ::= { st2HopEntry 13 }

st2HopDiscards OBJECT-TYPE
    SYNTAX  Counter
    ACCESS  read-only
    STATUS  mandatory
    DESCRIPTION
      "count of packets received from this hop in this stream and not processed, or not able to be sent in this stream to this hop, depending on st2HopRole"
    ::= { st2HopEntry 14 }

st2HopIpEncap OBJECT-TYPE
    SYNTAX  INTEGER { true(1), false(2) }
    ACCESS  read-only
    STATUS  mandatory
    DESCRIPTION
      "true if data for this stream is sent with IP encapsulation to this next hop"
    ::= { st2HopEntry 15 }

st2HopIpAddr OBJECT-TYPE
    SYNTAX  IpAddress
    ACCESS  read-only
    STATUS  mandatory
    DESCRIPTION
      "if ip encapsulation is on, this is the direct (local) next hop IP address of the next router on the path.  the ST agent next hop can be further away.  Implementations might store this so as to bypass the IP routing function."
    ::= { st2HopEntry 16 }

st2HopRole OBJECT-TYPE
    SYNTAX  INTEGER { nexthop(1), prevhop(2) }
    ACCESS  read-only
    STATUS  mandatory
    DESCRIPTION
      "tells whether this hop entry is a previous-hop for this stream or a next-hop.  this is to help identify whether the packet, octet and discard counters are for input from a prev-hop or output to a next-hop."
    ::= { st2HopEntry 17 }

st2HopInterfaceIndex OBJECT-TYPE
    SYNTAX  INTEGER
    ACCESS  read-only
    STATUS  mandatory
    DESCRIPTION
      "Interface Index"
    ::= { st2HopEntry 18 }

st2HopErrorTime OBJECT-TYPE
    SYNTAX  TimeTicks
    ACCESS  read-only
    STATUS  mandatory
    DESCRIPTION
      "Time when refuse code or other error occurs"
    ::= { st2HopEntry 19 }


-- st2 Neighbor Table

st2NeighborTable OBJECT-TYPE
    SYNTAX  SEQUENCE OF St2NeighborEntry
    ACCESS  not-accessible
    STATUS  mandatory
    DESCRIPTION
      "table of information for each neighbor common info"
    ::= { stii 89 }

-- table name neighbor, upper Neighbor, syntax SEQUENCE OF St2NeighborEntry

st2NeighborEntry OBJECT-TYPE
    SYNTAX  St2NeighborEntry
    ACCESS  not-accessible
    STATUS  mandatory
DESCRIPTION ""
    INDEX   { st2NeighborAddr }
    ::= { st2NeighborTable 1 }

St2NeighborEntry ::=
    SEQUENCE {
        st2NeighborAddr                  IpAddress,
        st2NeighborState                 INTEGER,
        st2NeighborStateTime             TimeTicks,
        st2NeighborNumHops               Gauge,
        st2NeighborHelloTimer            TimeTicks,
        st2NeighborHelloRcvdTime         TimeTicks,
        st2NeighborDataRcvdTime          TimeTicks,
        st2NeighborAckRequested          INTEGER,
        st2NeighborRestarted             INTEGER,
        st2NeighborSentHellos            Counter,
        st2NeighborRcvdHellos            Counter,
        st2NeighborMissedHellos          Counter,
        st2NeighborRoundTripTime         TimeTicks,
        st2NeighborInterfaceIdx          INTEGER,
        st2NeighborStBadMsgs             Counter,
        st2NeighborScmpBadMsgs           Counter
    }

st2NeighborAddr OBJECT-TYPE
    SYNTAX  IpAddress
    ACCESS  read-only
    STATUS  mandatory
    DESCRIPTION
      "address of neighbor ST Agent serving as nexthop or previous hop for one or more streams"
    ::= { st2NeighborEntry 1 }

st2NeighborState OBJECT-TYPE
    SYNTAX  INTEGER {
	up(1),
	down(2)
	}
    ACCESS  read-only
    STATUS  mandatory
    DESCRIPTION
      "state of neighbor ST Agent w.r.t. hellos and data"
    ::= { st2NeighborEntry 2 }

st2NeighborStateTime OBJECT-TYPE
    SYNTAX  TimeTicks
    ACCESS  read-only
    STATUS  mandatory
    DESCRIPTION
      "time entered this state of neighbor ST Agent"
    ::= { st2NeighborEntry 3 }

st2NeighborNumHops OBJECT-TYPE
    SYNTAX  Gauge
    ACCESS  read-only
    STATUS  mandatory
    DESCRIPTION
      "number of hops using this neighbor for next or prev"
    ::= { st2NeighborEntry 4 }

st2NeighborHelloTimer OBJECT-TYPE
    SYNTAX  TimeTicks
    ACCESS  read-only
    STATUS  mandatory
    DESCRIPTION
      "min of hello times based on RecoveryTimeout for all streams via this neighbor - or possibly default.  Note: ST specifies this in milliseconds"
    ::= { st2NeighborEntry 5 }

st2NeighborHelloRcvdTime OBJECT-TYPE
    SYNTAX  TimeTicks
    ACCESS  read-only
    STATUS  mandatory
    DESCRIPTION
      "timestamp when most recent hello received from this neighbor"
    ::= { st2NeighborEntry 6 }

st2NeighborDataRcvdTime OBJECT-TYPE
    SYNTAX  TimeTicks
    ACCESS  read-only
    STATUS  mandatory
    DESCRIPTION
      "timestamp when most recent ST data received from this neighbor - this may be updated infrequently, perhaps every couple of seconds"
    ::= { st2NeighborEntry 7 }

st2NeighborAckRequested OBJECT-TYPE
    SYNTAX  INTEGER { true(1), false(2) }
    ACCESS  read-only
    STATUS  mandatory
    DESCRIPTION
      "I have requested an ACK from this neighbor, still outstanding - for RTT estimation"
    ::= { st2NeighborEntry 8 }

st2NeighborRestarted OBJECT-TYPE
    SYNTAX  INTEGER { true(1), false(2) }
    ACCESS  read-only
    STATUS  mandatory
    DESCRIPTION
      "hello received from this neighbor with the restart bit on indicating neighbor has restarted recently"
    ::= { st2NeighborEntry 9 }

st2NeighborSentHellos OBJECT-TYPE
    SYNTAX  Counter
    ACCESS  read-only
    STATUS  mandatory
    DESCRIPTION
      "count of hellos sent to this neighbor"
    ::= { st2NeighborEntry 10 }

st2NeighborRcvdHellos OBJECT-TYPE
    SYNTAX  Counter
    ACCESS  read-only
    STATUS  mandatory
    DESCRIPTION
      "count of hellos received from this neighbor"
    ::= { st2NeighborEntry 11 }

st2NeighborMissedHellos OBJECT-TYPE
    SYNTAX  Counter
    ACCESS  read-only
    STATUS  mandatory
    DESCRIPTION
      "count of hellos expected which were not received from this neighbor"
    ::= { st2NeighborEntry 12 }

st2NeighborRoundTripTime OBJECT-TYPE
    SYNTAX  TimeTicks
    ACCESS  read-only
    STATUS  mandatory
    DESCRIPTION
      "current estimate of round trip time to this neighbor based on hello exchanges"
    ::= { st2NeighborEntry 13 }

st2NeighborInterfaceIdx OBJECT-TYPE
    SYNTAX  INTEGER
    ACCESS  read-only
    STATUS  mandatory
    DESCRIPTION
      "internal index of interface which reaches this neighbor"
    ::= { st2NeighborEntry 14 }

st2NeighborStBadMsgs OBJECT-TYPE
    SYNTAX  Counter
    ACCESS  read-only
    STATUS  mandatory
    DESCRIPTION
      "count of bad stream data messages received from this neighbor"
    ::= { st2NeighborEntry 15 }

st2NeighborScmpBadMsgs OBJECT-TYPE
    SYNTAX  Counter
    ACCESS  read-only
    STATUS  mandatory
    DESCRIPTION
      "count of bad stream control messages received from this neighbor"
    ::= { st2NeighborEntry 16 }

-- st2 Target Table

st2TargetTable OBJECT-TYPE
    SYNTAX  SEQUENCE OF St2TargetEntry
    ACCESS  not-accessible
    STATUS  mandatory
    DESCRIPTION
      "table of information for each target"
    ::= { stii 90 }

-- table name target, upper Target, syntax SEQUENCE OF St2TargetEntry

st2TargetEntry OBJECT-TYPE
    SYNTAX  St2TargetEntry
    ACCESS  not-accessible
    STATUS  mandatory
DESCRIPTION ""
    INDEX   { st2StreamName, st2TargetAddr }
    ::= { st2TargetTable 1 }

St2TargetEntry ::=
    SEQUENCE {
        st2TargetAddr                    IpAddress,
        st2TargetHop                     IpAddress,
        st2TargetStreamName              OCTET STRING
    }

st2TargetAddr OBJECT-TYPE
    SYNTAX  IpAddress
    ACCESS  read-only
    STATUS  mandatory
    DESCRIPTION
      "ip address of target"
    ::= { st2TargetEntry 1 }

st2TargetHop OBJECT-TYPE
    SYNTAX  IpAddress
    ACCESS  read-only
    STATUS  mandatory
    DESCRIPTION
      "ip address of the nexthop which gets to this target"
    ::= { st2TargetEntry 2 }

st2TargetStreamName OBJECT-TYPE
    SYNTAX  OCTET STRING (SIZE (10))
    ACCESS  read-only
    STATUS  mandatory
    DESCRIPTION
      "name of the stream this target is a member of"
    ::= { st2TargetEntry 3 }

-- st2 Group Table

st2GroupTable OBJECT-TYPE
    SYNTAX  SEQUENCE OF St2GroupEntry
    ACCESS  not-accessible
    STATUS  mandatory
    DESCRIPTION
      "table of information for each group"
    ::= { stii 91 }

-- table name group, upper Group, syntax SEQUENCE OF St2GroupEntry

st2GroupEntry OBJECT-TYPE
    SYNTAX  St2GroupEntry
    ACCESS  not-accessible
    STATUS  mandatory
DESCRIPTION ""
    INDEX   { st2GroupName }
    ::= { st2GroupTable 1 }

St2GroupEntry ::=
    SEQUENCE {
        st2GroupName                     OCTET STRING,
        st2GroupId                       INTEGER,
        st2GroupNumStreams               Gauge,
        st2GroupNumSubgroups             Gauge
    }

st2GroupName OBJECT-TYPE
    SYNTAX  OCTET STRING (SIZE (10))
    ACCESS  read-only
    STATUS  mandatory
    DESCRIPTION
      "the ST-II name of this group of streams"
    ::= { st2GroupEntry 1 }

st2GroupId OBJECT-TYPE
    SYNTAX  INTEGER (0..'FFFF'h)
    ACCESS  read-only
    STATUS  mandatory
    DESCRIPTION
      "a group identifier"
    ::= { st2GroupEntry 2 }

st2GroupNumStreams OBJECT-TYPE
    SYNTAX  Gauge
    ACCESS  read-only
    STATUS  mandatory
    DESCRIPTION
      "number of streams which are members of this group"
    ::= { st2GroupEntry 3 }

st2GroupNumSubgroups OBJECT-TYPE
    SYNTAX  Gauge
    ACCESS  read-only
    STATUS  mandatory
    DESCRIPTION
      "number of subgroups in this group"
    ::= { st2GroupEntry 4 }

-- st2 Subgroup Table

st2SubgroupTable OBJECT-TYPE
    SYNTAX  SEQUENCE OF St2SubgroupEntry
    ACCESS  not-accessible
    STATUS  mandatory
    DESCRIPTION
      "table of information for each sub-group"
    ::= { stii 92 }

-- table name subgroup, upper Subgroup, syntax SEQUENCE OF St2SubgroupEntry

st2SubgroupEntry OBJECT-TYPE
    SYNTAX  St2SubgroupEntry
    ACCESS  not-accessible
    STATUS  mandatory
DESCRIPTION ""
    INDEX   { st2SubgroupIndex }
    ::= { st2SubgroupTable 1 }

St2SubgroupEntry ::=
    SEQUENCE {
        st2SubgroupGroup                 OCTET STRING,
        st2SubgroupNumStreams            Gauge,
        st2SubgroupIndex                 INTEGER
    }

st2SubgroupGroup OBJECT-TYPE
    SYNTAX  OCTET STRING (SIZE (10))
    ACCESS  read-only
    STATUS  mandatory
    DESCRIPTION
      "group which this subgroup is a member"
    ::= { st2SubgroupEntry 1 }

st2SubgroupNumStreams OBJECT-TYPE
    SYNTAX  Gauge
    ACCESS  read-only
    STATUS  mandatory
    DESCRIPTION
      "number of streams in this subgroup"
    ::= { st2SubgroupEntry 2 }

st2SubgroupIndex OBJECT-TYPE
    SYNTAX  INTEGER (0..'FFFF'h)
    ACCESS  read-only
    STATUS  mandatory
    DESCRIPTION
      "internal index into sub-group table"
    ::= { st2SubgroupEntry 3 }

-- st2 Interface Table

st2InterfaceTable OBJECT-TYPE
    SYNTAX  SEQUENCE OF St2InterfaceEntry
    ACCESS  not-accessible
    STATUS  mandatory
    DESCRIPTION
      "table of information for each interface"
    ::= { stii 93 }

-- table name interface, upper Interface, syntax SEQUENCE OF St2InterfaceEntry

st2InterfaceEntry OBJECT-TYPE
    SYNTAX  St2InterfaceEntry
    ACCESS  not-accessible
    STATUS  mandatory
DESCRIPTION ""
    INDEX   { st2InterfaceIndex }
    ::= { st2InterfaceTable 1 }

St2InterfaceEntry ::=
    SEQUENCE {
        st2InterfaceIndex                INTEGER,
        st2InterfaceNumInStreams         Gauge,
        st2InterfaceNumOutStreams        Gauge,
        st2InterfaceNumNeighbors         Gauge,
        st2InterfaceInBwReserved         Gauge,
        st2InterfaceInBwReservable       Gauge,
        st2InterfaceOutBwReserved        Gauge,
        st2InterfaceOutBwReservable      Gauge,
	st2InterfaceTotRcvdPkts		 Counter,
	st2InterfaceTotSentPkts		 Counter,
	st2InterfaceTotRcvdOctets	 Counter,
	st2InterfaceTotSentOctets	 Counter,
	st2InterfaceRcvdHdrErrors	 Counter,
	st2InterfaceRcvdHidErrors	 Counter,
	st2InterfaceRcvdLenErrors	 Counter,
	st2InterfaceRcvdHdrErrorTime	 TimeTicks,
	st2InterfaceRcvdHidErrorTime	 TimeTicks,
	st2InterfaceRcvdLenErrorTime	 TimeTicks,
	st2InterfaceRcvdErrorSnap	 DisplayString,
	st2InterfaceRcvdPktDrops	 Counter,
	st2InterfaceSentPktDrops	 Counter,
	st2InterfaceIpAddr	 	 IpAddress
    }

st2InterfaceIndex OBJECT-TYPE
    SYNTAX  INTEGER
    ACCESS  read-only
    STATUS  mandatory
    DESCRIPTION
      "interface index of this interface - like ifIndex from main MIB"
    ::= { st2InterfaceEntry 1 }

st2InterfaceNumInStreams OBJECT-TYPE
    SYNTAX  Gauge
    ACCESS  read-only
    STATUS  mandatory
    DESCRIPTION
      "number of streams coming in this interface"
    ::= { st2InterfaceEntry 2 }

st2InterfaceNumOutStreams OBJECT-TYPE
    SYNTAX  Gauge
    ACCESS  read-only
    STATUS  mandatory
    DESCRIPTION
      "number of streams going out this interface"
    ::= { st2InterfaceEntry 3 }

st2InterfaceNumNeighbors OBJECT-TYPE
    SYNTAX  Gauge
    ACCESS  read-only
    STATUS  mandatory
    DESCRIPTION
      "number of neighbors on this interface being used as prev or next hop"
    ::= { st2InterfaceEntry 4 }

st2InterfaceInBwReserved OBJECT-TYPE
    SYNTAX  Gauge
    ACCESS  read-only
    STATUS  mandatory
    DESCRIPTION
      "total of flowspec (bytes x rate) into this interface in units of bits-per-second"
    ::= { st2InterfaceEntry 5 }

st2InterfaceInBwReservable OBJECT-TYPE
    SYNTAX  Gauge
    ACCESS  read-write
    STATUS  mandatory
    DESCRIPTION
      "amount of bandwidth remaining able to be reserved for input into this interface in units of bits-per-second"
    ::= { st2InterfaceEntry 6 }

st2InterfaceOutBwReserved OBJECT-TYPE
    SYNTAX  Gauge
    ACCESS  read-only
    STATUS  mandatory
    DESCRIPTION
      "total of flowspec (bytes x rate) out of this interface in units of bits-per-second"
    ::= { st2InterfaceEntry 7 }

st2InterfaceOutBwReservable OBJECT-TYPE
    SYNTAX  Gauge
    ACCESS  read-write
    STATUS  mandatory
    DESCRIPTION
      "amount of bandwidth remaining able to be reserved for output out of this interface in units of bits-per-second"
    ::= { st2InterfaceEntry 8 }

st2InterfaceTotRcvdPkts OBJECT-TYPE
    SYNTAX  Counter
    ACCESS  read-only
    STATUS  mandatory
    DESCRIPTION
      "Count of stream data packets received overall (for streams both current and expired)"
    ::= { st2InterfaceEntry 9 }

st2InterfaceTotSentPkts OBJECT-TYPE
    SYNTAX  Counter
    ACCESS  read-only
    STATUS  mandatory
    DESCRIPTION
      "Count of stream data packets sent overall (??) including replications for multiple output interfaces and multiple next-hops when multicast is not used ( make this per interface ??)"
    ::= { st2InterfaceEntry 10 }

st2InterfaceTotRcvdOctets OBJECT-TYPE
    SYNTAX  Counter
    ACCESS  read-only
    STATUS  mandatory
    DESCRIPTION
      "Count of stream data octets received overall"
    ::= { st2InterfaceEntry 11 }

st2InterfaceTotSentOctets OBJECT-TYPE
    SYNTAX  Counter
    ACCESS  read-only
    STATUS  mandatory
    DESCRIPTION
      "Count of stream data octets sent"
    ::= { st2InterfaceEntry 12 }

st2InterfaceRcvdHdrErrors OBJECT-TYPE
    SYNTAX  Counter
    ACCESS  read-only
    STATUS  mandatory
    DESCRIPTION
      "Count of stream data packets received with header format errors"
    ::= { st2InterfaceEntry 13 }

st2InterfaceRcvdHidErrors OBJECT-TYPE
    SYNTAX  Counter
    ACCESS  read-only
    STATUS  mandatory
    DESCRIPTION
      "Count of stream data packets received with errors in HID"
    ::= { st2InterfaceEntry 14 }

st2InterfaceRcvdLenErrors OBJECT-TYPE
    SYNTAX  Counter
    ACCESS  read-only
    STATUS  mandatory
    DESCRIPTION
      "Count of stream data packets received with errors in length"
    ::= { st2InterfaceEntry 15 }

st2InterfaceRcvdHdrErrorTime OBJECT-TYPE
    SYNTAX  TimeTicks
    ACCESS  read-only
    STATUS  mandatory
    DESCRIPTION
      "Time of last stream data packet received with header format errors"
    ::= { st2InterfaceEntry 16 }

st2InterfaceRcvdHidErrorTime OBJECT-TYPE
    SYNTAX  TimeTicks
    ACCESS  read-only
    STATUS  mandatory
    DESCRIPTION
      "Time of last stream data packet received with errors in HID"
    ::= { st2InterfaceEntry 17 }

st2InterfaceRcvdLenErrorTime OBJECT-TYPE
    SYNTAX  TimeTicks
    ACCESS  read-only
    STATUS  mandatory
    DESCRIPTION
      "Time of last stream data packet received with errors in length"
    ::= { st2InterfaceEntry 18 }

st2InterfaceRcvdErrorSnap OBJECT-TYPE
    SYNTAX  DisplayString
    ACCESS  read-only
    STATUS  mandatory
    DESCRIPTION
      "Contents from last stream data packet received with error"
    ::= { st2InterfaceEntry 19 }

st2InterfaceRcvdPktDrops OBJECT-TYPE
    SYNTAX  Counter
    ACCESS  read-only
    STATUS  mandatory
    DESCRIPTION
      "Count of stream data packets received and dropped due to resource limitations"
    ::= { st2InterfaceEntry 20 }

st2InterfaceSentPktDrops OBJECT-TYPE
    SYNTAX  Counter
    ACCESS  read-only
    STATUS  mandatory
    DESCRIPTION
      "Count of stream data packets sent and dropped due to resource limitations"
    ::= { st2InterfaceEntry 21 }

st2InterfaceIpAddr OBJECT-TYPE
    SYNTAX  IpAddress
    ACCESS  read-only
    STATUS  mandatory
    DESCRIPTION
      "Interface Ip address"
    ::= { st2InterfaceEntry 22 }

st2LastCloseStreamName OBJECT-TYPE
    SYNTAX  OCTET STRING (SIZE (10))
    ACCESS  read-only
    STATUS  mandatory
    DESCRIPTION
      "Last close stream name"
    ::= { stii 94 }

st2LastClosePrevHopIpAddr OBJECT-TYPE
    SYNTAX  IpAddress
    ACCESS  read-only
    STATUS  mandatory
    DESCRIPTION
      "Last close previous hop Ip address"
    ::= { stii 95 }

st2LastCloseReasonCode OBJECT-TYPE
    SYNTAX  INTEGER
    ACCESS  read-only
    STATUS  mandatory
    DESCRIPTION
      "Reason code field from the last close message"
    ::= { stii 96 }

st2LastCloseDetectorIpAddress OBJECT-TYPE
    SYNTAX  IpAddress
    ACCESS  read-only
    STATUS  mandatory
    DESCRIPTION
      "detector address from the last close message"
    ::= { stii 97 }

st2LastCloseTime OBJECT-TYPE
    SYNTAX  TimeTicks
    ACCESS  read-only
    STATUS  mandatory
    DESCRIPTION
      "sysuptime when the last close received"
    ::= { stii 98 }


END
