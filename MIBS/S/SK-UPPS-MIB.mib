SK-UPPS-MIB DEFINITIONS ::= BEGIN

-- Title:  SysKonnect SK-UPPS-MIB Extension version 2.1
-- Date:   February, 1995
-- By:     Hubert Weiler <hweiler@skd.de> and Georg Klug <gklug@skd.de>

IMPORTS
	enterprises, OBJECT-TYPE, Counter,
	Gauge, TimeTicks, DisplayString
	    FROM RFC1155-SMI;

-- *******************************************************************
-- Type Aliases
-- *******************************************************************

FddiMACLongAddressType ::= OCTET STRING (SIZE (6))

sk			OBJECT IDENTIFIER ::= { enterprises 179 }
skMibs			OBJECT IDENTIFIER ::= { sk 2 }

sk-board		OBJECT IDENTIFIER ::= { skMibs 2 }
sk-board-status		OBJECT IDENTIFIER ::= { sk-board 1 }
sk-board-client		OBJECT IDENTIFIER ::= { sk-board 2 }

eth			OBJECT IDENTIFIER ::= { sk-board 3 }
tok			OBJECT IDENTIFIER ::= { sk-board 4 }
fddi			OBJECT IDENTIFIER ::= { sk-board 5 }
sk-board-statistics	OBJECT IDENTIFIER ::= { sk-board 6 }


-- the Board Status group
-- Instances of these object types represent status
-- information of a network adapter runnning
-- the DLI.

stTable OBJECT-TYPE
	SYNTAX  SEQUENCE OF StEntry
	ACCESS  not-accessible
	STATUS  mandatory
	DESCRIPTION
		"A list of board status entries."
	::= { sk-board-status 1 }

stEntry OBJECT-TYPE
	SYNTAX  StEntry
	ACCESS  not-accessible
	STATUS  mandatory
	DESCRIPTION
		"A board status entry containing information
		common to a given board."
	INDEX   { stIfIndex }
	::= { stTable 1 }

StEntry ::= SEQUENCE {
	stIfIndex
	  INTEGER,
	stVersion
	  DisplayString,
	stLogAddress
	  OCTET STRING,
	stInterrupt
	  INTEGER,
	stBaseAddress
	  DisplayString,
	stRAMSize
	  DisplayString,
	stIOPort
	  DisplayString,
	stDMALine
	  INTEGER,
	stNumMbufs
	  INTEGER,
	stMaxTxMbufs
	  INTEGER,
	stMaxRxMbufs
	  INTEGER,
	stCurrentPacketFilter
	  INTEGER,
	stServiceInterrupt
	  DisplayString,
	stOEMSignature
	  DisplayString,
	stTopology
	  INTEGER,
	stIORange
	  INTEGER
}

stIfIndex OBJECT-TYPE
	SYNTAX  INTEGER
	ACCESS  read-only
	STATUS  mandatory
	DESCRIPTION
		"The ifIndex of the corresponding entry in the
		ifTable."
	::= { stEntry 1 }

stVersion OBJECT-TYPE
	SYNTAX  DisplayString (SIZE (0..255))
	ACCESS  read-only
	STATUS  mandatory
	DESCRIPTION
		"VersionNr. of the DLI"
	::= { stEntry 2 }

stLogAddress OBJECT-TYPE
	SYNTAX  OCTET STRING
	ACCESS  read-only
	STATUS  mandatory
	DESCRIPTION
		"This is the adapter's current logical node
		address.  In normal case this address is
		equal to the value of PHYSADDR.  If the DLI
		wants to change the logical address, it
		calls DriverChangeAddress."
	::= { stEntry 3 }

stInterrupt OBJECT-TYPE
	SYNTAX  INTEGER
	ACCESS  read-only
	STATUS  mandatory
	DESCRIPTION
		"This is the IRQ line used by the adapter
		(-1 if none)."
	::= { stEntry 4 }

stBaseAddress OBJECT-TYPE
	SYNTAX  DisplayString (SIZE (0..255))
	ACCESS  read-only
	STATUS  mandatory
	DESCRIPTION
		"This is the segment address (base) at which
		the adapter's RAM is located in the address
		space of the PC (0 if adapter has no shared
		memory)."
	::= { stEntry 5 }

stRAMSize OBJECT-TYPE
	SYNTAX  DisplayString (SIZE (0..255))
	ACCESS  read-only
	STATUS  mandatory
	DESCRIPTION
		"This is the size in bytes of the shared memory
		on the adapter."
	::= { stEntry 6 }

stIOPort OBJECT-TYPE
	SYNTAX  DisplayString (SIZE (0..255))
	ACCESS  read-only
	STATUS  mandatory
	DESCRIPTION
		"This is the first I/O port address (base)
		used by the adapter (0 if none)."
	::= { stEntry 7 }

stDMALine OBJECT-TYPE
	SYNTAX  INTEGER
	ACCESS  read-only
	STATUS  mandatory
	DESCRIPTION
		"This is the DMA channel number used by the
		adapter (-1 if none)."
	::= { stEntry 8 }

stNumMbufs OBJECT-TYPE
	SYNTAX  INTEGER
	ACCESS  read-only
	STATUS  mandatory
	DESCRIPTION
		"This is the total number of all Mbufs.
		Mbuf is a data structure in the DLI whichs
		includes the necessary information to
		coordinate the interaction of various
		functions and events between the DLI
		and the protocol clients."
	::= { stEntry 9 }

stMaxTxMbufs OBJECT-TYPE
	SYNTAX  INTEGER
	ACCESS  read-only
	STATUS  mandatory
	DESCRIPTION
		"This is the maximum number of Mbufs that
		may be allocated by the protocol clients"
	::= { stEntry 10 }

stMaxRxMbufs OBJECT-TYPE
	SYNTAX  INTEGER
	ACCESS  read-only
	STATUS  mandatory
	DESCRIPTION
		"The number of Mbufs destined for packet
		reception can be calculated as
		NumMbufs - MaxTXMbufs."
	::= { stEntry 11 }

stCurrentPacketFilter OBJECT-TYPE
	SYNTAX  INTEGER
	ACCESS  read-only
	STATUS  mandatory
	DESCRIPTION
		"This variable is a value representing
		the address types that are received by the
		driver.	Default is O.
		Then, for each address type A, with the
		value 1 - 4, the power of two of (A - 1) is
		added. 	
		Address types:
		1	Direct addressing (+Broadcast)
		2	Multicast or group addressing
			plus functional addresses
		3	Promiscuous mode
		4	Source routing

		If the variable has the value O,
		this object will not be supported.  "
	::= { stEntry 12 }


stServiceInterrupt OBJECT-TYPE
	SYNTAX  DisplayString (SIZE (0..255))
	ACCESS  read-only
	STATUS  mandatory
	DESCRIPTION
	      "This is the service interrupt occupied by
	      UPPSDLI.  It can be set at start of the DLI
	      (default:0x7c)."
	::= { stEntry 13 }

stOEMSignature OBJECT-TYPE
	SYNTAX  DisplayString (SIZE (0..255))
	ACCESS  read-only
	STATUS  mandatory
	DESCRIPTION
		"OEM-Signature"
	::= { stEntry 14 }

stTopology OBJECT-TYPE
	SYNTAX  INTEGER {
		ethernet(1),		
		fddi(2),
		token-ring(3)
	}
	ACCESS  read-only
	STATUS  mandatory
	DESCRIPTION
		"This field holds the network topology id.
		Topology ids are assigned by Schneider &
		Koch.  The following topology ids have been
		defined:

		 ID	Topology
		===	=========
		01h	Ethernet
		02h	FDDI
		03h	Token Ring"
	::= { stEntry 15 }

stIORange OBJECT-TYPE
	SYNTAX  INTEGER
	ACCESS  read-only
	STATUS  mandatory
	DESCRIPTION
		"Specifies the number of I/O ports following
		the I/O port base."
	::= { stEntry 16 }

-- the Board client group

clTable OBJECT-TYPE
	SYNTAX  SEQUENCE OF ClEntry
	ACCESS  not-accessible
	STATUS  mandatory
	DESCRIPTION
		"A list of clients."
	::= { sk-board-client 1 }

clEntry OBJECT-TYPE
	SYNTAX  ClEntry
	ACCESS  not-accessible
	STATUS  mandatory
	DESCRIPTION
		"A client entry containing information common
		to a given client."
	INDEX   { clPID }
	::= { clTable 1 }

ClEntry ::= SEQUENCE {
	clIfIndex
	  INTEGER,
	clType
	  DisplayString,
	clMulticast
	  INTEGER,
	clName
	  DisplayString,
	clMode
	  INTEGER,
	clPID
	  INTEGER
}

clIfIndex OBJECT-TYPE
	SYNTAX  INTEGER
	ACCESS  read-only
	STATUS  mandatory
	DESCRIPTION
		"The corresponding ifIndex of the given
		client."
	::= { clEntry 1 }

clType OBJECT-TYPE
	SYNTAX  DisplayString (SIZE (0..255))
	ACCESS  read-only
	STATUS  mandatory
	DESCRIPTION
		"This object represents the protocol type to be
		opened.  The protocol types are the following:

		Mode (PMODE)	TYPE		Protocol
		 =========== ===============	==================
		Ethernet II	0000h		IEEE 802.3 (cf. below)
		Ethernet II	0001h-05DCh	'Dummy' = no reception!
		Ethernet II	05DDh-FFFEh	Ethernet II type code
		Ethernet II	FFFFh		Demultiplexor (or Promiscuous
						or Hook)
		IEEE SAP	xx00h		IEEE 802.2 Service Access Point
		IEEE SNAP	0000h-FFFFh	IEEE 802.2 SNAP Type Code

		Note that true ETHERNET II type code protocols
		can only have type codes 05DDh (1501 decimal) or
		higher.  A protocol with type code less than
		05DDh can be logged on at the DLI.  However,
		this protocol cannot receive packets, as packets
		with type code less than 05DDh are interpreted
		as IEEE 802.3 packets and will be routed to a
		possibly active IEEE 802.3 protocol or (if
		inactive) will be dismissed.  "
	::= { clEntry 2 }

clMulticast OBJECT-TYPE
	SYNTAX	 INTEGER
	ACCESS	 read-only
	STATUS	 mandatory
	DESCRIPTION
		"This is the number of multicast addresses      tered
		registered by the protocol."
	::= { clEntry 3 }

clName OBJECT-TYPE
	SYNTAX  DisplayString (SIZE (0..255))
	ACCESS  read-only
	STATUS  mandatory
	DESCRIPTION
		"This is a character chain that
		characterizes the protocol/application."
	::= { clEntry 4 }

clMode OBJECT-TYPE
	SYNTAX  INTEGER
	ACCESS  read-only
	STATUS  mandatory
	DESCRIPTION
		"This value represents the mode of the
		registered protocol (cf. UPPS Developers Kit)"
	::= { clEntry 5 }

clPID OBJECT-TYPE
	SYNTAX  INTEGER
	ACCESS  read-only
	STATUS  mandatory
	DESCRIPTION
		"This value represents a virtual board
		number to identify a protocol"
	::= { clEntry 6 }

-- Topology statistics
-- Instances of these object types represent attributes of an
-- interface to an Ethernet Token Ring or FDDI communications
-- medium.  Only one object group has to be implemented at the
-- same time depending on the hardware of the communication
-- adapter.

-- The ethernet object group is a part of the internet draft
-- 'ETHERNET LIKE OBJECTS'.

-- The FDDI object group is partially from the RFC1285
-- 'FDDI Management Information Base'.
-- textual conventions
-- FddiMACLongAddressType ::= OCTET STRING (SIZE (6))
-- The representation of long MAC addresses as management
-- values is in the IEEE (ANSI/IEEE P802.1A) canonical
-- notation for 48 bit addresses.  The canonical form is a
-- 6-octet string where the first octet contains the first 8
-- bits of the address, with the I/G (Individual/Group)
-- address bit as the least significant bit and the  U/L
-- (Universal/Local) bit as the next more significant bit,
-- and so on.  Note that the addresses in the SMT frames are
-- represented in FDDI MAC order.

-- The Token Ring object group is a summary of objects described
-- in the User's Guide for the TMS380 from Texas Instruments.

-- Ethernet statistics group

ethStatsTable OBJECT-TYPE
	SYNTAX  SEQUENCE OF EthStatsEntry
	ACCESS  not-accessible
	STATUS  mandatory
	DESCRIPTION
		"Statistics for a collection of ethernet-like
		interfaces attached to a particular system."
	::= { eth 1 }

ethStatsEntry OBJECT-TYPE
	SYNTAX  EthStatsEntry
	ACCESS  not-accessible
	STATUS  mandatory
	DESCRIPTION
		"Statistics for a particular interface to an
		ethernet-like medium."
	INDEX   {ethStatsIndex }
	::= { ethStatsTable 1 }

EthStatsEntry ::= SEQUENCE {
	ethStatsIndex
	  INTEGER,
	ethStatsAlignmentErrors
	  Counter,
	ethStatsFCSErrors
	  Counter,
	ethStatsSingleCollisionFrames
	  Counter,
	ethStatsMultipleCollisionFrames
	  Counter,
	ethStatsSQETestErrors
	  Counter,
	ethStatsDeferredTransmissions
	  Counter,
	ethStatsLateCollisions
	  Counter,
	ethStatsExcessiveCollisions
	  Counter,
	ethStatsInternalMacTransErrors
	  Counter,
	ethStatsCarrierSenseErrors
	  Counter,
	ethStatsExcessiveDeferrals
	  Counter,
	ethStatsFrameTooLongs
	  Counter,
	ethStatsInRangeLengthErrors
	  Counter,
	ethStatsOutOfRangeLengthFields
	  Counter,
	ethStatsInternalMacRecvErrors
	  Counter
}

ethStatsIndex OBJECT-TYPE
	SYNTAX  INTEGER
	ACCESS  read-only
	STATUS  mandatory
	DESCRIPTION
		"An index value that uniquely identifies an
		interface to an ethernet-like medium.  The
		interface identified by a particular value of
		this index is the same interface as identified
		by the same value of ifIndex."
	::= { ethStatsEntry 1 }

ethStatsAlignmentErrors OBJECT-TYPE
	SYNTAX  Counter
	ACCESS  read-only
	STATUS  mandatory
	DESCRIPTION
		"A count of frames received on a particular
		interface that are not an integral number of
		octets in length and do not pass the FCS check.

		The count represented by an instance of this
		object is incremented when the alignmentError
		status is returned by the MAC service to the LLC
		(or other MAC user). Received frames for which
		multiple error conditions obtain are, according
		tothe conventions of [9], counted exclusively
		according to the error status presented to the
		LLC."
	::= { ethStatsEntry 2 }

ethStatsFCSErrors OBJECT-TYPE
	SYNTAX  Counter
	ACCESS  read-only
	STATUS  mandatory
	DESCRIPTION
		"A count of frames received on a particular
		interface that are an integral number of octets
		in length but do not pass the FCS check.

		The count represented by an instance of this
		object is incremented when the frameCheckError
		status is returned by the MAC service to the LLC
		(or other MAC user). Received frames for which
		multiple error conditions obtain are, according
		tothe conventions of [9], counted exclusively
		according to the error status presented to the
		LLC."
	::= { ethStatsEntry 3 }

ethStatsSingleCollisionFrames OBJECT-TYPE
	SYNTAX  Counter
	ACCESS  read-only
	STATUS  mandatory
	DESCRIPTION
		"A count of successfully transmitted frames on a
		particular interface for which transmission is
		inhibited by exactly one collision.

		A frame that is counted by an instance of this
		object is also counted by the corresponding
		instance of either the ifOutUcastPkts or
		ifOutNUcastPkts object and is not counted by the
		corresponding instance of the
		ethStatsMultipleCollisionFrames object."
	::= { ethStatsEntry 4 }

ethStatsMultipleCollisionFrames OBJECT-TYPE
	SYNTAX  Counter
	ACCESS  read-only
	STATUS  mandatory
	DESCRIPTION
		"A count of successfully transmitted frames on a
		particular interface for which transmission is
		inhibited by more than one collision.

		A frame that is counted by an instance of this
		object is also counted by the corresponding
		instance of either the ifOutUcastPkts or
		ifOutNUcastPkts object and is not counted by the
		corresponding instance of the
		ethStatsSingleCollisionFrames object."
	::= { ethStatsEntry 5 }

ethStatsSQETestErrors OBJECT-TYPE
	SYNTAX  Counter
	ACCESS  read-only
	STATUS  mandatory
	DESCRIPTION
		"A count of times that the SQE TEST ERROR
		message is generated by the PLS sublayer for a
		particular interface.
		this object is not supported"
	::= { ethStatsEntry 6 }

ethStatsDeferredTransmissions OBJECT-TYPE
	SYNTAX  Counter
	ACCESS  read-only
	STATUS  mandatory
	DESCRIPTION
		"A count of frames for which the first
		transmission attempt on a particular interface
		is delayed because the medium is busy.
		The count represented by an instance of this
		object does not include frames involved in
		collisions."
	::= { ethStatsEntry 7 }

ethStatsLateCollisions OBJECT-TYPE
	SYNTAX  Counter
	ACCESS  read-only
	STATUS  mandatory
	DESCRIPTION
		"The number of times that a collision is
		detected on a particular interface later than
		512 bit-times into the transmission of a packet.

		Five hundred and twelve bit-times corresponds to
		51.2 microseconds on a 10 Mbit/s system. A
		(late) collision included in a count represented
		by an instance of this object is also considered
		as a (generic) collision for purposes of other
		collision-related statistics."
	::= { ethStatsEntry 8 }

ethStatsExcessiveCollisions OBJECT-TYPE
	SYNTAX  Counter
	ACCESS  read-only
	STATUS  mandatory
	DESCRIPTION
		"A count of frames for which transmission on a
		particular interface fails due to excessive
		collisions."
	::= { ethStatsEntry 9 }

ethStatsInternalMacTransErrors OBJECT-TYPE
	SYNTAX  Counter
	ACCESS  read-only
	STATUS  mandatory
	DESCRIPTION
		"A count of frames for which transmission on a
		particular interface fails due to an internal MAC
		sublayer transmit error. A frame is only counted
		by an instance of this object if it is not
		counted by the corresponding instance of either
		the ethStatsLateCollisions object, the
		ethStatsExcessiveCollisions object, the
		ethStatsCarrierSenseErrors object, or the
		ethStatsExcessiveDeferrals object.  The precise
		meaning of the count represented by an instance
		of this object is implementation- specific.  In
		particular, an instance of this object may
		represent a count of transmission errors on a
		particular interface that are not otherwise
		counted."
	::= { ethStatsEntry 10 }

ethStatsCarrierSenseErrors OBJECT-TYPE
	SYNTAX  Counter
	ACCESS  read-only
	STATUS  mandatory
	DESCRIPTION
	      "The number of times that the carrier sense
	      condition was lost or never asserted when
	      attempting to transmit a frame on a particular
	      interface.

	      The count represented by an instance of this
	      object is incremented at most once per
	      transmission attempt, even if the carrier sense
	      condition fluctuates during a transmission
	      attempt."
	::= { ethStatsEntry 11 }

ethStatsExcessiveDeferrals OBJECT-TYPE
	SYNTAX  Counter
	ACCESS  read-only
	STATUS  mandatory
	DESCRIPTION
	      "A count of frames for which transmission on a
	      particular interface is deferred for an
	      excessive period of time."
	::= { ethStatsEntry 12 }

ethStatsFrameTooLongs OBJECT-TYPE
	SYNTAX  Counter
	ACCESS  read-only
	STATUS  mandatory
	DESCRIPTION
	      "A count of frames received on a particular
	      interface that exceed the maximum permitted
	      frame size.
	      The count represented by an instance of this
	      object is incremented when the frameTooLong
	      status is returned by the MAC service to the LLC
	      (or other MAC user).  Received frames for which
	      multiple error conditions obtain are, according
	      to the conventions of [9], counted exclusively
	      according to the error status presented to the
	      LLC."
	::= { ethStatsEntry 13 }

ethStatsInRangeLengthErrors OBJECT-TYPE
	SYNTAX  Counter
	ACCESS  read-only
	STATUS  mandatory
	DESCRIPTION
	      "A count of frames received on a particular
	      interface with a length field value that falls
	      between the minimum unpadded LLC data size and
	      the maximum allowed LLC data size inclusive and
	      that does not match the number of LLC data
	      octets received.

		The count represented by an instance of this
		object also includes frames for which the length
		field value is less than the minimum unpadded
		LLC data size."
	::= { ethStatsEntry 14 }

ethStatsOutOfRangeLengthFields OBJECT-TYPE
	SYNTAX  Counter
	ACCESS  read-only
	STATUS  mandatory
	DESCRIPTION
		"A count of frames received on a particular
		interface for which the length field value
		exceeds the maximum allowed LLC data size.

		The count represented by an instance of this
		object is not incremented in implementations
		that observe Ethernet encapsulation conventions
		(by which the IEEE 802.3 length field is
		interpreted as the Ethernet Type field)."
	::= { ethStatsEntry 15 }

ethStatsInternalMacRecvErrors OBJECT-TYPE
	SYNTAX  Counter
	ACCESS  read-only
	STATUS  mandatory
	DESCRIPTION
		"A count of frames for which reception on a
		particular interface fails due to an internal
		MAC sublayer receive error.  A frame is only
		counted by an instance of this object if it is
		not counted by the corresponding instance of
		either the ethStatsFrameTooLongs object, the
		ethStatsAlignmentErrors object, the
		ethStatsFCSErrors object, the
		ethStatsInRangeLengthErrors object, or the
		ethStatsOutOfRangeLengthFields object.

		The precise meaning of the count represented by
		an instance of this object is implementation-
		specific.  In particular, an instance of this
		object may represent a count of receive errors
		on a particular interface that are not otherwise
		counted."
	::= { ethStatsEntry 16 }



-- Token Ring statistics group

tokStatsTable OBJECT-TYPE
	SYNTAX  SEQUENCE OF TokStatsEntry
	ACCESS  not-accessible
	STATUS  mandatory
	DESCRIPTION
		"Statistics for a collection of token-ring
		interfaces attached to a particular system."
	::= { tok 1 }

tokStatsEntry OBJECT-TYPE
	SYNTAX  TokStatsEntry
	ACCESS  not-accessible
	STATUS  mandatory
	DESCRIPTION
		"Statistics for a particular interface for Token
		Ring."
	INDEX   {tokStatsIndex }
	::= { tokStatsTable 1 }

TokStatsEntry ::= SEQUENCE {
	tokStatsIndex
	  INTEGER,
	tokStatsUpstreamNbr
	  OCTET STRING,
	tokStatsLocalRingNumber
	  INTEGER,
	tokStatsRingUpCounts
	  Counter,
	tokStatsSignalLossErrors
	  Counter,
	tokStatsLobeWireFaults
	  Counter,
	tokStatsRingRecoveryCounts
	  Counter,
	tokStatsLineErrors
	  Counter,
	tokStatsBurstErrors
	  Counter,
	tokStatsARI-FCIErrors
	  Counter,
	tokStatsLostFrameErrors
	  Counter,
	tokStatsReceiveCongestionErrors
	  Counter,
	tokStatsFrameCopiedErrors
	  Counter,
	tokStatsTokenErrors
	  Counter,
	tokStatsDMABusErrors
	  Counter,
	tokStatsDMAParityErrors
	  Counter,
	tokStatsReceiveOverflowErrors
	  Counter
}

tokStatsIndex OBJECT-TYPE
	SYNTAX  INTEGER
	ACCESS  read-only
	STATUS  mandatory
	DESCRIPTION
		"An index value that uniquely identifies an
		interface to a token-ring medium.  The interface
		identified by a particular value of this index
		is the same interface as identified by the same
		value of ifIndex."
	::= { tokStatsEntry 1 }

tokStatsUpstreamNbr OBJECT-TYPE
	SYNTAX  OCTET STRING
	ACCESS  read-only
	STATUS  mandatory
	DESCRIPTION
		"The MAC's upstream neighbour's long individual
		MAC address."
	::= { tokStatsEntry 2 }

tokStatsLocalRingNumber OBJECT-TYPE
	SYNTAX  INTEGER
	ACCESS  read-only
	STATUS  mandatory
	DESCRIPTION
		"The unique number of the local Token Ring"
	::= { tokStatsEntry 3 }

tokStatsRingUpCounts OBJECT-TYPE
	SYNTAX  Counter
	ACCESS  read-only
	STATUS  mandatory
	DESCRIPTION
		"The number of times the station made
		sucessfully an 'open adapter' "
	::= { tokStatsEntry 4 }

tokStatsSignalLossErrors OBJECT-TYPE
	SYNTAX  Counter
	ACCESS  read-only
	STATUS  mandatory
	DESCRIPTION
		"The number of times the adapter detected a loss
		of signal on the ring"
	::= { tokStatsEntry 5 }

tokStatsLobeWireFaults OBJECT-TYPE
	SYNTAX  Counter
	ACCESS  read-only
	STATUS  mandatory
	DESCRIPTION
		"The number of times the adapter detected an
		open or short circuit in the cable between the
		adapter and the wiring concentrator."
	::= { tokStatsEntry 6 }

tokStatsRingRecoveryCounts OBJECT-TYPE
	SYNTAX  Counter
	ACCESS  read-only
	STATUS  mandatory
	DESCRIPTION
		"The number of times the adapter observes claim
		token MAC frames on the ring.  The adapter may
		be transmitting the claim token frames."
	::= { tokStatsEntry 7 }

tokStatsLineErrors OBJECT-TYPE
	SYNTAX  Counter
	ACCESS  read-only
	STATUS  mandatory
	DESCRIPTION
		"The line error counter is incremented whenever

		1) a frame is repeated or copied, and
		2) the error detected indicator is zero in the
		incoming frame, and
		3) at least one of the following conditions
		exists:

		a) a code violation between the starting
		delimiter and the ending delimiter of the
		frame.
		b) a code violation in the token
		c) a Frame Check Sequence (FCS) error.

		When the line error is incremented, the EDI of
		the frame is set to one so that no further
		station count the error."
	::= { tokStatsEntry 8 }

tokStatsBurstErrors OBJECT-TYPE
	SYNTAX  Counter
	ACCESS  read-only
	STATUS  mandatory
	DESCRIPTION
		"The burst error counter is contained in all
		adapter configurations and is incremented when
		the adapter detects the absence of transitions
		for five half- bit times between SDEL and EDEL,
		or EDEL and SDEL.  Only one adapter detects the
		burst five condition because the adapter that
		detects a burst four condition (four half bit
		times without transition) directs its
		transmitter to transmit idles if the burst five
		condition is detected."
	::= { tokStatsEntry 9 }

tokStatsARI-FCIErrors OBJECT-TYPE
	SYNTAX  Counter
	ACCESS  read-only
	STATUS  mandatory
	DESCRIPTION
		"The ARI/FCI error counter is incremented when
		an adapter receives an Active Monitor Present
		(AMP)MAC frame with the ARI/FCI bits equal to
		zero and a Standby Monitor Present (SMP)MAC
		frame with the ARI/FCI bits equal to zero, or
		more than one SMP MAC frame with the ARI/FCI
		bits equal to zero, without receiving an
		intervening AMP MAC frame.  This condition
		indicates that the upstream neighbor is unable
		to set the ARI/FCI bits in a frame that it has
		copied."
	::= { tokStatsEntry 10 }


tokStatsLostFrameErrors OBJECT-TYPE
	SYNTAX  Counter
	ACCESS  read-only
	STATUS  mandatory
	DESCRIPTION
		"The lost frame error counter is incremented
		when an adapter is in transmit (stripping) mode
		and fails to receive the end of the frame
		transmitted."
	::= { tokStatsEntry 11 }


tokStatsReceiveCongestionErrors OBJECT-TYPE
	SYNTAX  Counter
	ACCESS  read-only
	STATUS  mandatory
	DESCRIPTION
		"The receive congestion error counter is
		incremented when an adapter in the repeat mode
		recognizes a frame addressed to it but has no
		buffer available to copy the frame."
	::= { tokStatsEntry 12 }


tokStatsFrameCopiedErrors OBJECT-TYPE
	SYNTAX  Counter
	ACCESS  read-only
	STATUS  mandatory
	DESCRIPTION
		"The frame copied error counter is incremented
		when an adapter in the repeat/receive mode
		recognizes a frame addressed to its specific
		address but finds the ARI bit not equal to zero.
		This indicates a possible line hit or duplicate
		address."
	::= { tokStatsEntry 13 }


tokStatsTokenErrors OBJECT-TYPE
	SYNTAX  Counter
	ACCESS  read-only
	STATUS  mandatory
	DESCRIPTION
		"The token error is active only in the active
		monitor station.  It is incremented when the
		active monitor detects an error with the token
		protocol as follows:

		1)The MONITOR_COUNT bit of a token with nonzero
		priority equals one.

		2)The MONITOR_COUNT bit of a frame equals one

		3)No token or frame is received within a 10-ms
		window

		4)The starting delimiter/token sequence has a
		code violation in an area where code violation
		must not exist."
	::= { tokStatsEntry 14 }


tokStatsDMABusErrors OBJECT-TYPE
	SYNTAX  Counter
	ACCESS  read-only
	STATUS  mandatory
	DESCRIPTION
		"The DMA bus error counter counts the
		occurrences of DMA bus errors that do not exceed
		the abort thresholds as specified in the
		Initialization parameters."

	::= { tokStatsEntry 15 }


tokStatsDMAParityErrors OBJECT-TYPE
	SYNTAX  Counter
	ACCESS  read-only
	STATUS  mandatory
	DESCRIPTION
		"The DMA parity error counter counts the
		occurrences of DMA parity errors that do not
		exceed the abort thresholds as specified in the
		Initialization parameters."
	::= { tokStatsEntry 16 }


tokStatsReceiveOverflowErrors OBJECT-TYPE
	SYNTAX  Counter
	ACCESS  read-only
	STATUS  mandatory
	DESCRIPTION
		"The Receive Overflow error counter counts the
		occurrences of packets which do not fit in one
		DLI Mbuf ( > 4504 Bytes)."
	::= { tokStatsEntry 17 }



-- FDDI statistics group

fddiStatsTable OBJECT-TYPE
	SYNTAX  SEQUENCE OF FddiStatsEntry
	ACCESS  not-accessible
	STATUS  mandatory
	DESCRIPTION
		"Statistics for a collection of fddi interfaces
		attached to a particular system."
	::= { fddi 1 }

fddiStatsEntry OBJECT-TYPE
	SYNTAX  FddiStatsEntry
	ACCESS  not-accessible
	STATUS  mandatory
	DESCRIPTION
		"Statistics for a particular interface to a fddi
		medium."
	INDEX   { fddiStatsIndex }
	::= { fddiStatsTable 1 }

FddiStatsEntry ::= SEQUENCE {
	fddiStatsIndex
	  INTEGER,
	fddiSMTOpVersionId
	  INTEGER,
	fddiSMTCFState
	  INTEGER,
	fddiSMTFrameSends
	  Counter,
	fddiSMTFrameReceives
	  Counter,
	fddiSMTRingUps
	  Counter,
	fddiMACUpstreamNbr
	  FddiMACLongAddressType,
	fddiMACDownstreamNbr
	  FddiMACLongAddressType,
	fddiMACFrameCts
	  Counter,
	fddiMACErrorCts
	  Counter,
	fddiMACLostCts
	  Counter,
	fddiPORT1LerEstimate
	  INTEGER,
	fddiPORT2LerEstimate
	  INTEGER,
	fddiATTACHMENTClass
	  INTEGER,
	fddiATTACHOptBypassPresent
	  INTEGER
}

fddiStatsIndex OBJECT-TYPE
	SYNTAX  INTEGER
	ACCESS  read-only
	STATUS  mandatory
	DESCRIPTION
		"An index value that uniquely identifies an
		interface to an fddi medium.  The interface
		identified by a particular value of this index
		is the same interface as identified by the same
		value of ifIndex."
	::= { fddiStatsEntry 1 }

fddiSMTOpVersionId OBJECT-TYPE
	SYNTAX  INTEGER (1..65535)
	ACCESS  read-only
	STATUS  mandatory
	DESCRIPTION
		"The version that this station is using for its
		operation (refer to ANSI 7.1.2.2)."
	REFERENCE
		"ANSI { fddiSMT 13 }"
	::= { fddiStatsEntry 2 }


fddiSMTCFState OBJECT-TYPE
	SYNTAX  INTEGER (0..12)
	ACCESS  read-only
	STATUS  mandatory
	DESCRIPTION
		"The attachment configuration for the station or
		concentrator (refer to ANSI SMT 9.7.4.3).
		The following values are possible:
		cf0(0), -- Isolated
		cf1(1), -- local_a
		cf2(2), -- local_b
		cf3(3), -- local_ab
		cf4(4), -- local_s
		cf5(5),  -- wrap_a
		cf6(6),  -- wrap_b
		cf7(7),  -- wrap_ab
		cf8(8),  -- wrap_s
		cf9(9),  -- c_wrap_a
		cf10(10),  -- c_wrap_b
		cf11(11),  -- c_wrap_s
		cf12(12)  -- thru"
	REFERENCE
		"ANSI { fddiSMT 42 }"
	::= { fddiStatsEntry 3 }


fddiSMTFrameSends OBJECT-TYPE
	SYNTAX  Counter
	ACCESS  read-only
	STATUS  mandatory
	DESCRIPTION
		"The number of SMT frames sent"
	::= { fddiStatsEntry 4 }


fddiSMTFrameReceives OBJECT-TYPE
	SYNTAX  Counter
	ACCESS  read-only
	STATUS  mandatory
	DESCRIPTION
		"The number of SMT frames received"
	::= { fddiStatsEntry 5 }


fddiSMTRingUps OBJECT-TYPE
	SYNTAX  Counter
	ACCESS  read-only
	STATUS  mandatory
	DESCRIPTION
		"The number of times the Ring came up"
	::= { fddiStatsEntry 6 }


fddiMACUpstreamNbr OBJECT-TYPE
	SYNTAX  FddiMACLongAddressType
	ACCESS  read-only
	STATUS  mandatory
	DESCRIPTION
		"The MAC's upstream neighbor's long individual
		MAC address.  It may be determined by the
		Neighbor Information Frame protocol (refer to
		ANSI SMT 7.2.1).  The value shall be reported as
		'00 00 F8 00 00 00' if it is unknown."
	REFERENCE
		"ANSI { fddiMAC 24 }"
	::= { fddiStatsEntry 7 }


fddiMACDownstreamNbr OBJECT-TYPE
	SYNTAX  FddiMACLongAddressType
	ACCESS  read-only
	STATUS  mandatory
	DESCRIPTION
		"The MAC's downstream neighbor's long individual
		MAC address.  It may be determined by the
		Neighbor Information Frame protocol (refer to
		ANSI SMT 7.2.1).  The value shall be reported as
		'00 00 F8 00 00 00' if it is unknown."
	REFERENCE
		"ANSI { fddiMAC 24 }"
	::= { fddiStatsEntry 8 }


fddiMACFrameCts OBJECT-TYPE
	SYNTAX  Counter
	ACCESS  read-only
	STATUS  mandatory
	DESCRIPTION
		"Frame_Counter (refer to ANSI MAC 2.2.1)."
	REFERENCE
		"ANSI { fddiMAC 71 }"
	::= { fddiStatsEntry 9 }

fddiMACErrorCts OBJECT-TYPE
	SYNTAX  Counter
	ACCESS  read-only
	STATUS  mandatory
	DESCRIPTION
		"Error_Counter (refer to ANSI MAC 2.2.1)."
	REFERENCE
		"ANSI { fddiMAC 81 }"
	::= { fddiStatsEntry 10 }


fddiMACLostCts OBJECT-TYPE
	SYNTAX  Counter
	ACCESS  read-only
	STATUS  mandatory
	DESCRIPTION
		"Lost_Counter (refer to ANSI MAC 2.2.1)."
	REFERENCE
		"ANSI { fddiMAC 82 }"
	::= { fddiStatsEntry 11 }


fddiPORT1LerEstimate OBJECT-TYPE
	SYNTAX  INTEGER (4..15)
	ACCESS  read-only
	STATUS  mandatory
	DESCRIPTION
		"A long term average link error rate of Port 1.
		It ranges from 10**-4 to 10**-15 and is reported
		as the absolute value of the exponent of the
		estimate."
	REFERENCE
		"ANSI { fddiPORT 51 }"
	::= { fddiStatsEntry 12 }


fddiPORT2LerEstimate OBJECT-TYPE
	SYNTAX  INTEGER (4..15)
	ACCESS  read-only
	STATUS  mandatory
	DESCRIPTION
		"A long term average link error rate of Port2.
		It ranges from 10**-4 to 10**-15 and is reported
		as the absolute value of the exponent of the
		estimate.  Returns Null if Port is not
		available"
	REFERENCE
		"ANSI { fddiPORT 51 }"
	::= { fddiStatsEntry 13 }


fddiATTACHMENTClass OBJECT-TYPE
	SYNTAX  INTEGER {
		single-attachment(1),
		dual-attachment(2),
		concentrator(3)
	}
	ACCESS  read-only
	STATUS  mandatory
	DESCRIPTION
		"The Attachment class.  This represents a PORT
		or a pair of PORTs plus the associated optional
		optical bypass that are managed as a functional
		unit.  The PORT associations are the following:

		single-attachment - S PORTs
		dual-attachment - A/B PORT Pairs
		concentrator - M PORTs "
	REFERENCE
		"ANSI { fddiATTACHMENT 11 }"
	::= { fddiStatsEntry 14 }


fddiATTACHOptBypassPresent OBJECT-TYPE
	SYNTAX  INTEGER { true(1), false(2) }
	ACCESS  read-only
	STATUS  mandatory
	DESCRIPTION

		"The value of this object is false for 'single-
		attachment'.
		Correct operation of CMT for single-attachment
		and concentrator attachments requires that a
		bypass function must not loopback the network
		side of the MIC, but only the node side."
	REFERENCE
		"ANSI { fddiATTACHMENT 12 }"
	::= { fddiStatsEntry 15 }


-- the Board statistics group

statsTable OBJECT-TYPE
	SYNTAX  SEQUENCE OF StatsEntry
	ACCESS  not-accessible
	STATUS  mandatory
	DESCRIPTION
		"A list of board statistic entries."
	::= { sk-board-statistics 1 }

statsEntry OBJECT-TYPE
	SYNTAX  StatsEntry
	ACCESS  not-accessible
	STATUS  mandatory
	DESCRIPTION
		"A board statistic entry containing information
		common to a given board."
	INDEX   { statsIfIndex }
	::= { statsTable 1 }

StatsEntry ::= SEQUENCE {
	statsIfIndex
	  INTEGER,
	statsFCSErrors
	  Counter,
	statsAlignmentErrors
	  Counter,
	statsFrameTooLongs
	  Counter
}

statsIfIndex OBJECT-TYPE
	SYNTAX  INTEGER
	ACCESS  read-only
	STATUS  mandatory
	DESCRIPTION
		"The ifIndex of the corresponding entry in
		the ifTable."
	::= { statsEntry 1 }

statsFCSErrors OBJECT-TYPE
	SYNTAX  Counter
	ACCESS  read-only
	STATUS  mandatory
	DESCRIPTION
		" The number of frames received with a Cyclic
		Redundancy Check error.
		This counter is incremented by the template
		part of the DLI not by the hardware driver as it
		it is done in the topology-specific statistics."
	::= { statsEntry 2 }

statsAlignmentErrors OBJECT-TYPE
	SYNTAX	 Counter
	ACCESS	 read-only
	STATUS	 mandatory
	DESCRIPTION	
		"The number of frames received, which did not
		end on a byte boundery.
		This counter is incremented by the template
		part of the DLI not by the hardware driver as it
		it is done in the topology-specific statistics."
	::= { statsEntry 3 }

statsFrameTooLongs OBJECT-TYPE
	SYNTAX  Counter
	ACCESS  read-only
	STATUS  mandatory
	DESCRIPTION
		"The number of frames received which were to long
		to fit in the data area of the Mbuf.
		This counter is incremented by the template
		part of the DLI not by the hardware driver as it
		it is done in the topology-specific statistics."
	::= { statsEntry 4 }

END
