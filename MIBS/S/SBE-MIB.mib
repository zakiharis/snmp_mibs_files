--
--                  START OF MIB DEFINITION FOR SBE 
--                  4/17/95

          SBE-MIB DEFINITIONS ::= BEGIN

          IMPORTS
						enterprises, IpAddress, TimeTicks
					FROM RFC1155-SMI
						DisplayString
					FROM RFC1213-MIB
						MacAddress
					FROM RFC1230-MIB
            TRAP-TYPE
					FROM RFC-1215
						OBJECT-TYPE
					FROM RFC-1212;

----------------------------------------------------------------------
-- Disclaimer 
--
--
-- "The SBE MIB is provided on an as-is basis.  No guarantee is provided
-- that this MIB will behave as specified when used by any application
-- other than Workshop.  No development guidelines are provided for
-- accessing the MIB other than the text contained within this document.
-- No technical support is provided for problems which may be encountered
-- when attempting to use this MIB directly by SNMP managers rather than
-- by Workshop.
-- 
-- Most of the MIB variables specified within this document can be
-- accessed directly by SNMP/IP management applications.  Many application
-- functions are covered - dynamic nX node discovery, configuration, event
-- logging, trap generation, software and sound files downloading,
-- statistics monitoring, dialing, etc.  However, the MIB was designed to
-- work with the SBE Workshop application and some operational details are
-- not documented within the MIB.  For example, some value checks are
-- required to be provided by Workshop; other value checks are provided by
-- the managed nX node.  Limited information is provided in the MIB text
-- as to the distribution of functionality between Workshop and the nX
-- node.  Also some control variables are only active when the nX node is
-- booting, and can only be accessed when communicating with SNMP over
-- Ethernet, RFC 1089."
----------------------------------------------------------------------
----------------------------------------------------------------------
-- Changes in sbe-mib.mib between release 1.2 and release 2.0
----------------------------------------------------------------------
-- Changed access fields of all indices to read-only.  This affects the
-- following items:
-- 
-- userName
-- ipStaticRouteDestinationAddress
-- ipxMultiFrameType
-- snmpCommunityName
-- snmpMacServerAddress
-- snmpIpServerAddress
-- destName
-- 
----------------------------------------------------------------------
-- Added the following items:
-- endOfSBEMib a dummyStopperForWorkshopForGetNext to prevent get next
--          running off the end.
-- wanISDNChannels, wanEnableDataCompression, and wanISDNChannelSpeed
--          to support ISDN.
-- ipDefaultGatewayIfType to replace ipDefaultGatewayType which used
--          the illegal enumerated value, zero, for type 'none'.
-- destAllowDynamicIPAddr, destISDNChannels, and destDialoutPhoneNumber2
--          for supporting Dynamic IP Address control and multi-link PPP.
-- Chat Script Table which contains the chat script related fields
--          for destinations (sites).
-- syActivatedLevel and syBaseActivationLevel for use in upgrading
--          software and piracy protection.
-- sySerialNumber for use by manufacturing.
----------------------------------------------------------------------
-- Deprecated the following unimplemented/unused items:
-- 
-- syFlashConfigurationSetName
-- syRegisteredFlag
-- syConfigurationMode
-- sySWVersion
-- syDebugBitmask
-- userDialOutMax
-- ipxManualSetNetworkAddress
-- ipxManualNetworkAddress
-- ipxRipReceiveBroadcastFlag
-- ipxRipSendInterval
-- ipxSapReceiveAdvertisementFlag
-- ipxSapSendInterval
-- ipxNetbios
-- ipxNetAddressAutoLearnFlag
----------------------------------------------------------------------
-- Edited the description fields of the following items to more
-- accurately reflect implementation:
-- 
-- syConfigurationLockFlag
-- syBootInfo
-- userStatus
-- wanLinkLayerProtocolType
-- wanISDNNTTCard
-- ipxConfiguredFlag
-- snmpCommunityPermission
-- destDialoutProtoSupport
-- destPorts
-- destLinkLayerProtocolType
-- eventData
-- fileTransferRemoteFileName
-- fileTransferLocalFileName
----------------------------------------------------------------------
-- Modified the syntax and/or access fields of the following items to
-- reconcile discrepancies between the netXpand kernel(s) and netXpand
-- Workshop:
-- 
-- syBootOrder
-- syMtuMru
-- syControlVariableStringOne
-- syDialbackRetryInterval
-- syDialbackRetryLimit
-- syBridgeProtocol
-- holidayDate
-- userPassword
-- wanLinkLayerType
-- wanIPAddress
-- ipWanDestinationName
-- ipStaticRouteDestinationName
-- ipxNetAddressAutoLearnStateCounter
-- snmpCommunityName
-- destName
-- destDialoutUserName
-- destDialoutPassword
-- destPorts
-- destDialoutStatus
-- destLinkLayerType
-- destTSDPortGroup
-- eventData
-- syDirStatus
-- fileTransferStatus
-- fileTransferRemoteAddr
-- fileTransferRemoteFileName
-- fileTransferLocalFileName
----------------------------------------------------------------------
----------------------------------------------------------------------
--                      SBE PRIVATE BRANCH 
----------------------------------------------------------------------

sbe      OBJECT IDENTIFIER ::= { enterprises 1055 }

system      OBJECT IDENTIFIER ::= { sbe 1 }
--     %{ return SNMP-SBEMIB-SystemAccess(snmpi); %}
   
router      OBJECT IDENTIFIER ::= { sbe 2 }

discovery   OBJECT IDENTIFIER ::= { sbe 3 }
--     %{ return SNMP-SBEMIB-DiscoveryGroup(snmpi); %}

fileMgmt OBJECT IDENTIFIER ::= { sbe 4 }
--     %{ return SNMP-SBEMIB-FileManagementGroup(snmpi); %}
  
modempool OBJECT IDENTIFIER ::= { sbe 6 }
--     %{ return SNMP-SBEMIB-ModemPoolAccess(snmpi); %}

endOfSBEMib OBJECT IDENTIFIER ::= { sbe 65535 }
  
----------------------------------------------------------------------
--                      sbe.system  BRANCH 
----------------------------------------------------------------------

--General Settings
--Only one copy of each of these settings exists per nX product.

--syNodeName OBJECT-TYPE
--        SYNTAX  DisplayString ( SIZE (1..19) )
--        ACCESS  read-write
--        STATUS  mandatory
--        DESCRIPTION
--               "(Factory Default) ProductName(6)-MacAddress(12), 
--				  e.g. SoHo-3744FF858912
--
--                On nX: both ram and flash, field trial 1
--
--                This is the name which will be used by Workshop to identify 
--                the nX product.  It will be displayed by Workshop, 
--                for example as the caption for the product's MDI window.  
--                The name has no importance to the nX product.  
--                The user will probably change the name to be something 
--                meaningful.  This field forms the second half of the 
--                object retrieved from the device using the SNMP Get 
--                command with the sysName variable (which is read-only 
--                in MIB-II, size up to 255).  See also Model Type object. "
--        ::= { system 1 }

syDateTime OBJECT-TYPE
        SYNTAX  OCTET STRING (SIZE(8))
        ACCESS  read-write
        STATUS  mandatory
        DESCRIPTION
                "Default value on nX: zero
                On nX: stored in clock chip

                Format: Century, year, month, day, hour, min, sec.
                each occupies one octet in binary value."
        ::= { system 1 }

--syContactInformation OBJECT-TYPE
--        SYNTAX  DisplayString ( SIZE (0..211) )
--        ACCESS  read-write
--        STATUS  mandatory
--        DESCRIPTION
--                "Default value on nX: empty
--                On nX: in flash, field trial 1
--
--                This is set by the user.  It is used during the 
--                registration process   It will probably also be used 
--                during on-line support. This field is also retrieved 
--                from the device using the SNMP Get command with the 
--                sysContact variable (which is read-only in MIB-II, 
--                size up to 255).
--                The nX does not use this object and therefore does not 
--                know how it is sub-divided into separate data items.  
--                Workshop shows these data items as separate fields.
--
--                This field contains in order, the following fixed length 
--                character strings (i.e. blank padded to specified length):
--                Name[30].  Name of a contact person responsible for 
--                            operation of the nX product.
--                Company[30].  Company name of the contact person.
--                Address[30].  Address for the contact person.
--                City[20].  City for the contact person.
--                State or Province[10].  State or province for the contact 
--                            person.
--                Zip Code or Postal Code[11].  Zip code or postal code 
--                            for the contact person.
--                Country[20].  Mailing country for the contact person.
--                Phone Number[30].  Phone Number for the contact person
--                Fax Number [30].  Fax Number for the contact person"
--        ::= { system 3 }

--syLocationOfProduct OBJECT-TYPE
--        SYNTAX  DisplayString ( SIZE (0..30) )
--        ACCESS  read-write
--        STATUS  mandatory
--        DESCRIPTION
--                "Default value on nX: empty
--                On nX: in flash, field trial 1
--
--                This is set by the user.  It should be set to something 
--                meaningful to describe the location of the nX product, 
--                e.g. '3rd floor wiring closet'.  This field can be viewed 
--                and used by the user to remember where the nX product is 
--                located.  It is also used in MIBs to describe the 
--                location of the device. This field is also retrieved 
--                from the device using the SNMP Get command with the 
--               sysLocation variable (which is read-only in MIB-II, 
--                size up to 255)."
--        ::= { system 4 }

-- syFlashConfigurationSetName OBJECT-TYPE
--         SYNTAX  OCTET STRING ( SIZE (0..31) )
--         ACCESS  read-only
--         STATUS  deprecated
--         DESCRIPTION
--                 "THIS ITEM IS NOT IMPLEMENTED!"
--         ::= { system 2 }

syRAMConfigurationChangedFlag OBJECT-TYPE
        SYNTAX  INTEGER { same(1), different(2) }
        ACCESS  read-only
        STATUS  mandatory
        DESCRIPTION
                "Default value on nX: set to 'same' when booted from 
                flash, 'different' otherwise
                On nX: (not needed?) in ram, field trial 2

                This field is used by Workshop to determine if the 
                RAM image currently being executed on the nX product 
                is identical to the image in the LX's flash.  Whenever 
                part of the RAM image is changed (currently only via 
                SNMP), this value is set to 'different' by the LX."
        ::= { system 3 }

-- syRegisteredFlag OBJECT-TYPE
--         SYNTAX  INTEGER { no(1), yes(2) }
--         ACCESS  read-only
--         STATUS  deprecated
--         DESCRIPTION
--                 "THIS ITEM IS NOT IMPLEMENTED!"
--         ::= { system 4 }

syConfigurationLockFlag OBJECT-TYPE
        SYNTAX  INTEGER { locked(1), unlocked(2) }
        ACCESS  read-write
        STATUS  mandatory
        DESCRIPTION
	"Default value on nX: 'unlocked(2)'

         This field is used by Workshop to determine whether 
         the nX unit is enabled to allow configuration.  When
         this field is set to locked(1), nX rejects the SET
         requests for all mib entries except this one. The 
         status of this field is also indicated by the lock
         LED on nX."
        ::= { system 5 }

-- syConfigurationMode OBJECT-TYPE
--         SYNTAX  INTEGER { ram(1), flash(2) }
--         ACCESS  read-only
--         STATUS  deprecated
--         DESCRIPTION
--                 "THIS ITEM IS NOT IMPLEMENTED!"
--         ::= { system 6 }

syModel OBJECT-TYPE
        SYNTAX  DisplayString (SIZE(0..31))
        ACCESS  read-only
        STATUS  mandatory
        DESCRIPTION
		" Default value on nX: factory setting
				On nX: in flash, field trial 1

		The product name, hardware revision, firmware revision, 
		and kernel revision for the nX Node product. 
		E.G.  SoHo/HW4/FW3/SW1.0V1.0

		Product names - SoHo, Central, ROUTEMAN, ROUTEMANXL
		Hardware Rev - HW Revision number, e.g. HW4
		Firmware Rev - FW Revision number, e.g. FW3
		Kernel Rev - SW Release-number Version-number, e.g. SW1.0V1.0

		Note: for Central we will define a second variable,
		   syCoprocessorModel."
        ::= { system 7 }

-- sySWVersion OBJECT-TYPE
-- 	SYNTAX DisplayString (SIZE(0..255))
--  	ACCESS read-only
-- 	STATUS deprecated
--   	DESCRIPTION
-- 		"Deprecated (AKA deleted). All info in sySWVersion is 
-- 		redundant with syFileVersion, just formatted differently."
-- 	::= { system 8 }

-- syDebugBitmask OBJECT-TYPE
--         SYNTAX  INTEGER
--         ACCESS  read-only
--         STATUS  deprecated
--         DESCRIPTION
--                 "THIS ITEM IS NOT IMPLEMENTED!"
--         ::= { system 9 }

syBootInfo OBJECT-TYPE
        SYNTAX  INTEGER
                {   normal-boot-from-LAN(1),
                    base-board-flash-corrupt(2),
                    missing-base-board-kernel-module(4),
                    daughter-board-flash-corrupt(8),
                    missing-daughter-board-kernel-module(16),
                    system-type-SoHo(32),
                    system-type-Central(64),
                    system-type-torte(128),
                    system-type-ROUTEMAN (256),
                    system-type-ROUTEMANXL (512),
                    system-type-ROUTEMANXLl (33280) 
                }
        ACCESS  read-only
        STATUS  deprecated
        DESCRIPTION
                "THIS ITEM IS NOT IMPLEMENTED!"
        ::= { system 10 }

syActivatedLevel OBJECT-TYPE
        SYNTAX DisplayString (SIZE(0..32))
        ACCESS read-write
        STATUS mandatory
        DESCRIPTION
            "Software feature activation level information. 
             This entry is maintained and used by Workshop."
        ::= { system 11 }

sySerialNumber OBJECT-TYPE
		SYNTAX OCTET STRING (SIZE(16))
		ACCESS read-only
		STATUS mandatory
		DESCRIPTION
                "A manufacturing only mib that will return the serial number
                 of the board. This function is reserved for manufacturing
                 test and may change as needed by manufacturing."
	::= { system 12 }

syBaseActivationLevel OBJECT-TYPE
        SYNTAX INTEGER { rOUTEMAN20Base(1),
                         soHo20Base(2),
                         central20Base(4),
                         rOUTEMANXL20Base(6),
                         soHoTest(11),
                         centralTest(12),
                         rOUTEMANTest(13),
                         rOUTEMANXLTest(14),
                         rOUTEMANXL201Base(15),
                         soHo21Base(16),
                         central21Base(18),
                         rOUTEMAN21Base(20),
                         rOUTEMANXL21Base(21),                         
                         soHo30Dormant(23),
                         central30Dormant(25),
                         rOUTEMAN30Dormant(27),
                         rOUTEMANX30Dormant(28)                         
                       }
        ACCESS read-only
        STATUS mandatory
        DESCRIPTION
            "Base level software feature information. 
             This entry is maintained by the nX unit and used by Workshop."
        ::= { system 13 }


----------------------------------------------------------------------
--                      sbe.router  BRANCH 
----------------------------------------------------------------------

routsys     OBJECT IDENTIFIER ::= { router 1 }
   
bridge      OBJECT IDENTIFIER ::= { router 2 }
   
ip          OBJECT IDENTIFIER ::= { router 3 }
   
ipx         OBJECT IDENTIFIER ::= { router 4 }
--     %{ return SNMP-SBEMIB-IPXAccess(snmpi); %}
   
wan         OBJECT IDENTIFIER ::= { router 5 }
   
destination OBJECT IDENTIFIER ::= { router 6 }
   
user        OBJECT IDENTIFIER ::= { router 7 }
   
manager     OBJECT IDENTIFIER ::= { router 8 }
   
holiday     OBJECT IDENTIFIER ::= { router 9 }
   
snmp   OBJECT IDENTIFIER ::= { router 10 }

event       OBJECT IDENTIFIER ::= { router 11 }
--                  %{ return SNMP-SBEMIB-EventLogAccess(snmpi); %}
   
  
----------------------------------------------------------------------
--                      sbe.router.routsys  BRANCH 
----------------------------------------------------------------------

syBootOrder OBJECT-TYPE
        SYNTAX  OCTET STRING ( SIZE ( 4 ) )
--     %{ return SNMP-SBEMIB-ControlGroup(snmpi); %}
        ACCESS  read-write
        STATUS  mandatory
        DESCRIPTION
                "enum values per octet:  1=Flash, 2=TFTP, 3=PCMCIA,
                4=LAN, 0=none
                Default value on nX: (Flash)
                On nX: in flash

                This field has one octet for each boot source from which 
                the nX product will attempt to boot.  The first choice 
                boot source is designated by the first byte, the second 
                choice by the second byte, etc.  In the first release 
                there are only two boot choices, but future versions 
                may have additional choices such as PCMCIA.  If the nX 
                detects that a boot choice is corrupted, it will ignore 
                that choice and proceed to the next choice.  The value 
                'none' is just used to fill any unused octets after the 
                choices have been specified."
        ::= { routsys 1 }
                 
syMtuMru OBJECT-TYPE
        SYNTAX  INTEGER (64..1500) 
--     %{ return SNMP-SBEMIB-ControlGroup(snmpi); %}
	ACCESS  read-only
        STATUS  mandatory
        DESCRIPTION
                "Default value on nX: 1500
                On nX: both ram and flash, field trial 2

                This field specifies the maximum size frame that the 
                nX product will send or receive, either on the LAN or 
                on a WAN port.  The maximum for Ethernet is 1500, 1492 
                for 802.3 with SNAP.  This is used by the nX product 
                to detect error frames (i.e. too long) and during PPP 
                negotiation.  The actual transfer size is negotiated, 
                by destination, when the connection is first made."
        ::= { routsys 2 }

syEventToLogThreshold OBJECT-TYPE
        SYNTAX  INTEGER (  1..10  )
--       %{ return SNMP-SBEMIB-EventLogControl(snmpi); %}
        ACCESS  read-write
        STATUS  mandatory
        DESCRIPTION
                "Default value on nX: 3
                On nX: both ram and flash, field trial 2

                All events generated by the nX product have an associated 
                severity level which ranges from 1 to 10.  The nX product 
                puts events of this threshold level and above into its
                internal circular log file.  Other events are discarded."
        ::= { routsys 3 }

syEventToTrapThreshold OBJECT-TYPE
        SYNTAX  INTEGER (  1..10  )
--    %{ return SNMP-SBEMIB-EventTrapControl(snmpi); %}
        ACCESS  read-write
        STATUS  mandatory
        DESCRIPTION
                "Default value on nX: 6
                On nX: both ram and flash, field trial 2

                All events generated by the nX product have an 
                associated severity level which ranges from 1 to 10.  
                For events of this threshold level and above, the nX 
                generates an SNMP trap."
        ::= { routsys 5 }

syControlOperation OBJECT-TYPE
        SYNTAX  INTEGER { none(1), 
        reboot(2), 
        clear-SNMP-statistics(3),
        dialout(4), 
        hangup(5),
        enable-port(6),
        disable-port(7), 
        disable-port-after-call(8), 
        crash(9), 
        change-password(10), 
        ram-to-Flash(11),
        start-tftp-download(12),
        reset-port(13),
        boot-override(14),        
        display-IP-Routes(15),
        display-IPX-Networks(16),
        display-IPX-Servers(17),
        reboot-file-transfer(18)
        }
--     %{ return SNMP-SBEMIB-ControlGroup(snmpi); %}

        ACCESS  read-write
        STATUS  mandatory
        DESCRIPTION
                "Default value on nX: 'none'
                On nX: in ram, field trial 1 except for 
                Clear-SNMP-statistics and Disable-port-after-call 
                which are field trial 2

                This object is set whenever Workshop wants the nX to 
                perform an operation.  Upon completion of the 
                operation, the nX sets the value back to 'none'.  
                Some operations use Control Variables as parameters 
                for the operation.  Any Control Variables must be 
                set in the same frame as the Control Operation to 
                insure that they are not changed by another Workshop 
                before the operation is performed.  After a Control 
                Operation is started, the values in the Control 
                Variables may no longer be valid.

                Reboot
                    When the value is 'reboot', the nX performs an 
                    immediate reboot.
                Clear-SNMP-statistics
                    When the value is 'clear-SNMP-statistics', the 
                    nX resets to zero all MIB statistics fields.
                Dialout
                    When the value is 'dialout', the nX performs a 
                    dialout to the destination identified in Control 
                    Variable String One.
                Hangup
                    When the value is 'hangup', the nX hangs up the 
                    non-leased line connection for the Destination 
                    identified in Control Variable String One.
                Enable port
                    When the value is 'enable-port', the nX enables 
                    the port identified by Control Variable Integer One.
                Disable port
                    When the value is 'disable-port', the nX disables 
                    the port identified by Control Variable Integer One.
                Disable-port-after-call
                    When the value is 'disable-port-after-call', the 
                    nX disables the port identified by Control Variable 
                    Integer One immediately after the current connection 
                    terminates.  This option allows gracefully taking 
                    the nX out of operation (except for leased lines).  
                    This option is not applicable to leased lines.
                Crash
                    When the value is 'crash', the nX stores its RAM 
                    memory contents to a PCMCIA card for off-line 
                    debugging.
                Change-password
                    When the value is 'change-password', the nX changes 
                    both the RAM and Flash password for a user.  The 
                    Control Variable String One contains the following 
                    zero terminated strings in order: User Name, old 
                    User Password, and new User Password. This is the 
                    only way to change passwords, except when defining 
                    a new user.
                RAM-to-Flash
                    When the value is 'RAM-to-Flash', the nX stores 
                    object values in RAM into Flash.
				start-tftp-download
                Reset-port
                    Hangup the port, if necessary and reinitialize the
                    modem.
                Display-IP-Routes
                    Show IP routes via event logger.
                Display-IPX-Networks
                    Show IPX Networks via event logger.
                Display-IPX-Servers
                    Show IPX Servers via event logger."

        ::= { routsys 7 }

syControlVariableStringOne OBJECT-TYPE
        SYNTAX  OCTET STRING (SIZE(1..64))
--     %{ return SNMP-SBEMIB-ControlGroup(snmpi); %}
        ACCESS  read-write    -- (never read)
        STATUS  mandatory
        DESCRIPTION
                "Default Value on nX: N/A
                On nX: in ram, field trial 1

                This object is used to store a DisplayString parameter 
                to a control operation.  Once the control operation 
                is started, the value is unspecified."
        ::= { routsys 8 }

syControlVariableIntegerOne OBJECT-TYPE
        SYNTAX  INTEGER (0..65535 )
--     %{ return SNMP-SBEMIB-ControlGroup(snmpi); %}
        ACCESS  read-write    -- (never read)
        STATUS  mandatory
        DESCRIPTION
                "Default Value on nX: N/A
                On nX: in ram, field trial 1

                This object is used to store an Integer parameter to 
                a control operation.  Once the control operation is 
                started, the value is unspecified."
        ::= { routsys 9 }

syDialinAuthentication OBJECT-TYPE
        SYNTAX  INTEGER { none(1), pap(2), chap(3), paporchap(4) }
--     %{ return SNMP-SBEMIB-ControlGroup(snmpi); %}
        ACCESS  read-write
        STATUS  mandatory
        DESCRIPTION
                "Default value on nX: 'none'
                On nX: both ram and flash. 

                This field identifies the type of authentication 
                negotiation that is to be performed during dialin 
                to this destination."
        ::= { routsys 10 }

syEventToSpeakThreshold OBJECT-TYPE
        SYNTAX  INTEGER (  1..10  )
--    %{ return SNMP-SBEMIB-EventSoundControl(snmpi); %}
        ACCESS  read-write
        STATUS  mandatory
        DESCRIPTION
                "Default value on nX: 6
                On nX: both ram and flash, field trial 2

                All events generated by the nX product have an 
                associated severity level which ranges from 1 to 10.  
                For events of this threshold level and above, the nX 
    speaks the error code to the speaker."
        ::= { routsys 11 }

syNumberOfTimesToSpeak OBJECT-TYPE
        SYNTAX  INTEGER (  1..10  )
--    %{ return SNMP-SBEMIB-EventSoundControl(snmpi); %}
        ACCESS  read-write
        STATUS  mandatory
        DESCRIPTION
                "Default value on nX: 3
                On nX: both ram and flash, field trial 2
 
                This item specifies the number of times an error code is
                spoken"
        ::= { routsys 12 }

sySaveRamToFlashState OBJECT-TYPE
		SYNTAX INTEGER { updating (1), idle (2)}
--    %{ return SNMP-SBEMIB-SaveRamToFlashState(snmpi); %}
		ACCESS read-only
		STATUS mandatory
		DESCRIPTION
		"This item specifies the state of the operation ram-to-Flash
		in the item syControlOperation. The valid states are: 
		updating and idle. updating state indicates that a write 
		to flash operation is in progress, idle state indicates idle."
		::= { routsys 13 }

syDialbackRetryInterval OBJECT-TYPE
        SYNTAX INTEGER ( 10..120 )
--     %{ return SNMP-SBEMIB-ControlGroup(snmpi); %}
        ACCESS read-write
        STATUS mandatory
        DESCRIPTION
                "This item specifies the number of seconds to pause before
                the next dialback call from Soho will be made. Default = 10"
        ::= { routsys 14 }

syDialbackRetryLimit OBJECT-TYPE
        SYNTAX INTEGER ( 1..10 )
--     %{ return SNMP-SBEMIB-ControlGroup(snmpi); %}
        ACCESS read-write
        STATUS mandatory
        DESCRIPTION
                "This item specifies the number of times that Soho will retry
                dialback call from Soho. Default is 3."
        ::= { routsys 15 }

syReverseCallbackTimeout OBJECT-TYPE
        SYNTAX INTEGER ( 30..300 )
--     %{ return SNMP-SBEMIB-ControlGroup(snmpi); %}
        ACCESS read-write
        STATUS mandatory
        DESCRIPTION
           "Default value on nX:  60 (seconds)

            Specifies the number of seconds to wait for an expected
            reverse callback before redialing."
        ::= { routsys 16 }



----------------------------------------------------------------------
--                      sbe.router.bridge  BRANCH 
----------------------------------------------------------------------

syBridgeConfiguredFlag OBJECT-TYPE
        SYNTAX  INTEGER { no(1), yes(2) }
--     %{ return SNMP-SBEMIB-BridgeAccess(snmpi); %}
        ACCESS  read-write
        STATUS  mandatory
        DESCRIPTION
                "Default value on nX: 'yes'
                On nX: both ram and flash, field trial 2

                If this object is 'no', syBridgeFilterFlag will be
                returned as 'other' by default regardless of the
                value that is previously set.
                If this is 'yes', syBridgeFilterFlag governs the
                bridging rule."
        ::= { bridge 1 }

syBridgeFilterFlag OBJECT-TYPE
        SYNTAX  INTEGER { other(1), include(2), exclude(4), all(8) }
--     %{ return SNMP-SBEMIB-BridgeAccess(snmpi); %}
        ACCESS  read-write
        STATUS  mandatory
        DESCRIPTION
                "Default value on nX: 'all'
                On nX: both ram and flash, field trial 2

                This value indicates the bridging rule for this
                nX product, whether to include or exclude packets
                for the protocols indicated in the Bridge Sub-Table.
                If the value is 'all', all protocols will be bridged.
                If the value is 'include', only the protocols listed
                in the Bridge Sub-Table are to be bridged over this
                port.  If the value is 'exclude', all packets except
                for the protocols listed in the Bridge Sub-Table are
                to be bridged."
        ::= { bridge 2 }

syBridgePriority OBJECT-TYPE
        SYNTAX  INTEGER (0..65535)
--     %{ return SNMP-SBEMIB-BridgeAccess(snmpi); %}
        ACCESS  read-write
        STATUS  mandatory
        DESCRIPTION
                "Default value on nX: 32768
                On nX: both ram and flash

                Used by the Spanning Tree Algorithm to determine
                who is the root bridge in the network."
        ::= { bridge 3 }


-- Bridge Table
-- This table has one row for each of the protocols, up to 16, 
-- that are to be bridged by the nX product.
-- There is only one copy of this table for the nX product.
-- Each row is identified by the protocol number.
-- Bridging rules are governed by syBridgeFilterFlag.

syBridgeTable OBJECT-TYPE
  SYNTAX SEQUENCE OF SyBridgeEntry
--     %{ return SNMP-SBEMIB-BridgeTableAccess(snmpi); %}
  ACCESS  not-accessible
  STATUS mandatory
  DESCRIPTION
                "Bridge table - one copy"
  ::={ bridge 4 }

syBridgeEntry OBJECT-TYPE
  SYNTAX SyBridgeEntry
  ACCESS not-accessible
  STATUS mandatory
  DESCRIPTION
                "The bridge table information for one protocol."
        INDEX { syBridgeProtocol }
  ::= { syBridgeTable 1 }


 SyBridgeEntry ::= SEQUENCE
   { syBridgeStatus INTEGER,
     syBridgeProtocol INTEGER
   }

syBridgeStatus OBJECT-TYPE
        SYNTAX  INTEGER { valid(1), 
     create-request(2),
     under-creation(3),
     invalid(4) }
        ACCESS  read-write
        STATUS  mandatory
        DESCRIPTION
                "Indication of whether or not a valid entry."
        ::= { syBridgeEntry 1 }

syBridgeProtocol OBJECT-TYPE
        SYNTAX  INTEGER
        ACCESS  read-only
        STATUS  mandatory
        DESCRIPTION
                "Default value on nX: none
                On nX: both ram and flash, field trial 2

                This column item contains the protocol number 
                for a protocol to be bridged.
                Bridging rules are governed by syBridgeFlag."
        ::= { syBridgeEntry 2 }

----------------------------------------------------------------------
--                      sbe.router.manager  BRANCH 
----------------------------------------------------------------------

mgrTimeoutForMACProtocolResponses OBJECT-TYPE
        SYNTAX  INTEGER (1..30)
--     %{ return SNMP-SBEMIB-ManagerGroup(snmpi); %}
        ACCESS  read-write
        STATUS  mandatory
        DESCRIPTION
                "Default value on nX: 5
                On nX: both ram and flash

                This object specifies the number of seconds Workshop 
                will wait for a response for a message sent to an nX 
                product before assuming that the packet was lost.  
                If this time elapses, Workshop will resend the packet.  
                Normally this time will be very short, but if the nX 
                product and Workshop are separated by slow WAN links, the 
                time will have to be increased.  The nX product does 
                not use this value."
        ::= { manager 1 }

mgrNumberOfRetriesForMACProtocolResponses OBJECT-TYPE
        SYNTAX  INTEGER (1..10)
--     %{ return SNMP-SBEMIB-ManagerGroup(snmpi); %}
        ACCESS  read-write
        STATUS  mandatory
        DESCRIPTION
                "Default value on nX: 3
                On nX: both ram and flash

                This object specifies the number of times Workshop will 
                retry sending to an nX product a message that timed 
                out before assuming that the packet cannot be sent.  
                If this count is reached, Workshop will stop trying to 
                send the packet and assume that the unit is no longer 
                responding (e.g. the connection has been terminated).  
                The nX product does not use this value."
        ::= { manager 2 }

mgrEventPollingInterval OBJECT-TYPE
        SYNTAX  INTEGER (1..65535)
--    %{ return SNMP-SBEMIB-EventPollControl(snmpi); %}
        ACCESS  read-write
        STATUS  mandatory
        DESCRIPTION
                "Default value on nX: 120
                On nX: both ram and flash, field trial 2

                This object specifies an interval, in seconds, at which 
                Workshop will poll the nX product in order to obtain 
                current data values with which to update displayed 
                screens.  The value of this object is most critical 
                when the log file is being written to disk because 
                if the interval is too long the nX product's circular 
                log buffer may not be large enough to hold all events 
                that occur between polls.  (Hopefully, the nX will 
                sequence number all log entries so Workshop can 
                determine if some entries have been missed by Workshop.)"
        ::= { manager 3 }


----------------------------------------------------------------------
--                      sbe.router.holiday  BRANCH 
----------------------------------------------------------------------
-- Holiday Table
-- This table is used to define holidays or other days when a 
-- different dialout schedule for destinations should be used.  
-- Each row in the table is indentified by a unique date.  
-- The nX product will limit the number of entries allowed in this table.

holidayMaxEntries OBJECT-TYPE
        SYNTAX  INTEGER
--     %{ return SNMP-SBEMIB-HolidayMaxEntryAccess(snmpi); %}
        ACCESS  read-only
        STATUS  mandatory
        DESCRIPTION
                "A value representing the maximum number of holiday entries
                 in the holiday table."
        ::= {holiday 1 }

holidayTable OBJECT-TYPE
 SYNTAX SEQUENCE OF HolidayEntry
     --%{ return SNMP-SBEMIB-HolidayAccess(snmpi); %}
 ACCESS not-accessible
 STATUS mandatory
 DESCRIPTION 
                "Holiday table - one copy"
 ::= {holiday 2}

holidayEntry OBJECT-TYPE
 SYNTAX HolidayEntry
 ACCESS not-accessible
 STATUS mandatory
 DESCRIPTION
               "The holiday information for one date."
 INDEX {holidayDate }
 ::= { holidayTable 1 }

 HolidayEntry ::= SEQUENCE {
    holidayStatus
      INTEGER,
    holidayDate
      DisplayString
    }

holidayStatus OBJECT-TYPE
        SYNTAX  INTEGER { 
       valid(1),
       create-request(2),
       under-creation(3),
       invalid(4),
       modify(5)      
       }
        ACCESS  read-write
        STATUS  mandatory
        DESCRIPTION
                "Indication of whether or not a valid entry."
        ::= { holidayEntry 1 }


holidayDate OBJECT-TYPE
        SYNTAX  DisplayString (SIZE(4)) 
                        -- in form of century, year, month, day (one octet each) 
        ACCESS  read-only
        STATUS  mandatory
        DESCRIPTION
                "Default value on nX: 0
                On nX: both ram and flash, field trial 2

                This item specifies a day which is designated as 
                a special dialout day.  The nX uses the month and day."
        ::= { holidayEntry 2 }

----------------------------------------------------------------------
--                      sbe.router.user  BRANCH 
----------------------------------------------------------------------

--User Table
--This table contains one row for every user allowed to dialin.  
--Each row is identified by a unique User Name.  If the User Table is empty, 
--there is no authentication on dialin or dialout.

 userMaxEntries OBJECT-TYPE
            SYNTAX  INTEGER
     			--%{ return SNMP-SBEMIB-UserMaxEntryAccess(snmpi); %}
            ACCESS  read-only
            STATUS  mandatory
            DESCRIPTION
                "A value representing the maximum number of user entries
                 in the user table."
            ::= {user 1 }
 
    userTable OBJECT-TYPE
              SYNTAX  SEQUENCE OF UserEntry
     			--%{ return SNMP-SBEMIB-UserAccess(snmpi); %}
              ACCESS  not-accessible
              STATUS  mandatory
              DESCRIPTION
                      "A list of user entries.  The number of
                      entries is given by the value of userNumber."
              ::= { user 2 }
   
    userEntry OBJECT-TYPE
              SYNTAX  UserEntry
              ACCESS  not-accessible
              STATUS  mandatory
              DESCRIPTION
                      "A user entry containing objects of users."
              INDEX   { userName }
              ::= { userTable 1 }
 
   UserEntry ::=
              SEQUENCE {
                  userStatus
                      INTEGER,
                  userName
                      DisplayString,
                  userPassword
                      DisplayString,
                  userPermissions
                      INTEGER,
                  userCallbackType
                      INTEGER,
                  userPhoneNo
                      DisplayString,
                  userDialInMax
                      INTEGER,
--                userDialOutMax
--                    INTEGER,
                  userIpAddress
                      IpAddress
              }
   
        userStatus OBJECT-TYPE
            SYNTAX INTEGER{
                           valid(1),          -- Creation of entry is complete
                           create-request(2), -- Request for creation of entry
                           under-creation(3), -- Entry under creation
                           invalid(4),        -- Request for deletion of entry
                           modify(5)          -- Request modification of entry
                          }
            ACCESS read-write
            STATUS mandatory
            DESCRIPTION
                "A value representing the current status of the user entry
                 for the index value, userName."
            ::={ userEntry 2}
 
        userName OBJECT-TYPE
            SYNTAX DisplayString (SIZE(0..31))
            ACCESS read-only
            STATUS mandatory
            DESCRIPTION
                "An octet string containing user supplied User Name which
                 identifies a dialin user. On dialin, this is used as the
                 login name for PAP or CHAP."
            ::={ userEntry 3}
    
        userPassword OBJECT-TYPE
            SYNTAX DisplayString (SIZE(0..31))
            ACCESS read-write
            STATUS mandatory
            DESCRIPTION
                "A display string containing user supplied User Password
                 for user identified by userName."
            ::={ userEntry 4}
    
        userPermissions OBJECT-TYPE
            SYNTAX INTEGER {
                    none(1),
                    dial-in(2),
                    dial-out(4)
                    }
            ACCESS read-write
            STATUS mandatory
            DESCRIPTION
                "A value representing the permissions the user identified
                by userName has, regarding access to the ports. If none(1)
                is specified, the user can neither dial out nor accept call.
                If dial-in(2) is specified, the user can dial-in. If
                dial-out(4) is specified, the user can dial-out. Specify
                dial-in(2)  and dial-out(4) permissions for both dial-in
                and dial-out privileges."
            ::= { userEntry 5}
 
        userCallbackType OBJECT-TYPE
            SYNTAX INTEGER {
                    none(1),
                    fixed(2)
                }
            ACCESS read-write
            STATUS mandatory
            DESCRIPTION
                "A value specifiying the type of callback to be used when
                user identified by userName connects. If none(1) is specified,
                the connection is maintained, and no callback is performed.
                If fixed(2) is specified, the connection is terminated after
                the proper authentication of the user is performed. The
                number stored in userPhoneNo is used to dialback."
            ::= { userEntry 6}
 
        userPhoneNo OBJECT-TYPE
            SYNTAX DisplayString (SIZE (0..31))
            ACCESS read-write
            STATUS mandatory
            DESCRIPTION
                "A phone number that is to be used for dialback."
            ::= { userEntry 7}
 
        userDialInMax OBJECT-TYPE
            SYNTAX INTEGER (0..65535)
            ACCESS read-write
            STATUS mandatory
            DESCRIPTION
                "A value representing the maximum time in minutes for a
                 dialin connection."
   ::= {userEntry 8}
 
--         userDialOutMax OBJECT-TYPE
--             SYNTAX INTEGER (0..65535)
--             ACCESS read-write
--             STATUS deprecated
--             DESCRIPTION
--                 "Deprecated (AKA deleted)."
--             ::= {userEntry 9}
 
        userIpAddress OBJECT-TYPE
            SYNTAX IpAddress
            ACCESS read-write
            STATUS mandatory
            DESCRIPTION
                " A value representing the IP Address to be used for the PPP
                dial-in connection."
            ::= {userEntry 10}

----------------------------------------------------------------------
--                      sbe.router.wan  BRANCH 
----------------------------------------------------------------------

-- wanPortTable OBJECT IDENTIFIER ::= { wan 1 }

wanPortTable OBJECT-TYPE
  SYNTAX SEQUENCE OF WanPortEntry
     --%{ return SNMP-SBEMIB-WANAccess(snmpi); %}
  ACCESS not-accessible
  STATUS mandatory
  DESCRIPTION
    "Each WAN port's information is contained in a row
                in a SNMP table.  The following describes the
                columns in the table.  Each row is uniquely
                identified by its Wan Port Number. (See also
                Port Sub-Data.)"
  ::= { wan 1 }


wanPortEntry OBJECT-TYPE
  SYNTAX WanPortEntry
  ACCESS not-accessible
  STATUS mandatory
  DESCRIPTION
    "The WAN table information for one WAN port." 
  INDEX { wanPortNumber }
  ::= { wanPortTable 2 }

  WanPortEntry ::= SEQUENCE
   {
    wanPortEntryStatus INTEGER,
    wanPortNumber INTEGER,
    wanPortEnabled INTEGER,
    wanDefaultDialinIPAddress IpAddress,
    wanDefaultDialinSubnetMask IpAddress,
    wanDefaultIPXNetworkAddress OCTET STRING,
    wanDefaultDialinIPXNodeAddress OCTET STRING,
    wanDialinAllowedFlag INTEGER,
    wanDialoutAllowedFlag INTEGER,
    wanLinkLayerType INTEGER,
    wanLinkLayerNRZFlag INTEGER,
    wanLinkLayerProtocolType INTEGER,
    wanLinkDialupFlag INTEGER,
    wanModemName DisplayString,
    wanModemSpeed INTEGER,
    wanModemInitializationString DisplayString,
    wanModemDialPrefix DisplayString,
    wanPortType INTEGER,
    wanPCMCIACardName DisplayString,
    wanIpRipReceiveAdvertisementFlag INTEGER,
    wanIpRipSendInterval INTEGER,
    wanIpxRipReceiveBroadcastFlag INTEGER,
    wanIpxRipSendInterval INTEGER,
    wanIpxSapReceiveAdvertisementFlag INTEGER,
    wanIpxSapSendInterval INTEGER,
    wanIpxNetbios INTEGER,  
    wanISDNSwitchType     INTEGER, 
    wanISDNCallingPhoneNoB1  DisplayString,
    wanISDNCallingPhoneNoB2  DisplayString,
    wanISDNSPID1 DisplayString,
    wanISDNSPID2 DisplayString,
    wanPortGroup INTEGER,
    wanISDNSubAddress1 DisplayString,
    wanISDNSubAddress2 DisplayString,
    wanISDNNTTCard INTEGER,
    wanISDNChannels INTEGER,
    wanEnableDataCompression INTEGER,
    wanISDNChannelSpeed INTEGER,
    wanUsageMode INTEGER,
    wanModemPoolGSN DisplayString,
    wanModemPoolSSN DisplayString
   }
    


wanPortEntryStatus OBJECT-TYPE
        SYNTAX  INTEGER {
       valid(1),
       create-request(2),
       under-creation(3),
       invalid(4),
       modify(5)      
      }
        ACCESS  read-write
        STATUS  mandatory
        DESCRIPTION
                "Indication of whether or not a valid entry."
        ::= { wanPortEntry 1 }

wanPortNumber OBJECT-TYPE
        SYNTAX  INTEGER ( 1..18 )
        ACCESS  read-only
        STATUS  mandatory
        DESCRIPTION
                "Default value on nX:  ascending integer, one for 
                each hardware WAN port: 1, 2, 3A, 3B, 4A, and 4B.
                On nX: both ram and flash, field trial 1

                This field is used to identify the Wan port to which 
                the information in this row of the table applies."
        ::= { wanPortEntry 2 }

wanPortEnabled OBJECT-TYPE
        SYNTAX  INTEGER { disabled(1), enabled(2) }
        ACCESS  read-only
        STATUS  mandatory
        DESCRIPTION
                "Default value on nX: disabled
                On nX: both ram and flash, field trial 1

                If this value is 'enabled', the Wan port is enabled.  
                If this value is 'disabled', if the Wan port is disabled."
        ::= { wanPortEntry 3 }

wanDefaultDialinIPAddress OBJECT-TYPE
        SYNTAX  IpAddress
        ACCESS  read-write
        STATUS  mandatory
        DESCRIPTION
                "Default value on nX: all zero
                On nX: both ram and flash, field trial 1

                If IP is configured, this field is required and is 
                used as the default IP address of the WAN port on 
                dialin unless overridden during dialin either by an 
                IP address from the User Table or by PPP negotiation.  
                The same value needs to be configured at the other 
                end of the WAN link (this could be a cause of user 
                error, but there is no way around it)."
        ::= { wanPortEntry 4 }

wanDefaultDialinSubnetMask OBJECT-TYPE
        SYNTAX  IpAddress
        ACCESS  read-write
        STATUS  mandatory
        DESCRIPTION
                "Default value on nX: all zero
                Default value in Workshop: 1's, based on Default Dialin 
                IP Address class
                On nX: both ram and flash, field trial 1

                If the Default Dialin IP Address is used, this object 
                is used as its Subnet Mask.
                Subnet masks allow the user to divide the local 
                network into sub-networks by specifying a subnet 
                mask.  The subnet mask, combined with the Dialin 
                IP Address field, determines which frames (packets) 
                are sent across the WAN port during dialin.  The 
                subnet masks are all 1's from the left for a 
                specified number of bits.  On Workshop, the subnet 
                mask will be entered as a number of bits from 0 to 32."
        ::= { wanPortEntry 5 }

wanDefaultIPXNetworkAddress OBJECT-TYPE
        SYNTAX  OCTET STRING (SIZE( 4 ))
        ACCESS  read-only
        STATUS  mandatory
        DESCRIPTION
                "Default value on nX: 0
                On nX: in ram, field trial 1

                If IPX is configured, this field indicates which 
                IPX network address is being used by this port.  
                The nX will automatically generate an address to 
                be used during dialout and, during dialin, will 
                accept the address from the calling node.  
                (The nX products use the SAP tables they 
                dynamically build to determined which network 
                numbers are already in use.)"
        ::= { wanPortEntry 6 }

wanDefaultDialinIPXNodeAddress OBJECT-TYPE
        SYNTAX  OCTET STRING (SIZE( 6 ))
        ACCESS  read-only
        STATUS  mandatory
        DESCRIPTION
                "Default value on nX: 0
                On nX: in ram, field trial 1

                If IPX is configured, this field specifies the 
                IPX node address that is being used by this port. 
                The nX will automatically generate an address to 
                be used during dialout and, during dialin, will 
                accept the address from the calling node."
        ::= { wanPortEntry 7 }

wanDialinAllowedFlag OBJECT-TYPE
        SYNTAX  INTEGER { no(1), yes(2) }
        ACCESS  read-write
        STATUS  mandatory
        DESCRIPTION
                "Default value on nX : 'yes'
                On nX: both ram and flash, field trial 2

                If this flag is 'yes', dialin access is allowed 
                on this port."
        ::= { wanPortEntry 8 }

wanDialoutAllowedFlag OBJECT-TYPE
        SYNTAX  INTEGER { no(1), yes(2) }
        ACCESS  read-write
        STATUS  mandatory
        DESCRIPTION
                "Default value on nX : 'yes'
                On nX: both ram and flash, field trial 2

                If this flag is 'yes', dialout is allowed on this port."
        ::= { wanPortEntry 9 }

wanLinkLayerType OBJECT-TYPE
        SYNTAX  INTEGER { async(1), sync(2), autosync(3) }
        ACCESS  read-write
        STATUS  mandatory
        DESCRIPTION
                "Default value on nX: async
                On nX: both ram and flash, field trial 1

                This object identifies the type of communication link 
                that is used by this WAN port.  Some data link types 
                require further qualification."
        ::= { wanPortEntry 10 }

wanLinkLayerNRZFlag OBJECT-TYPE
        SYNTAX  INTEGER { nrz(1), nrzi(2)  }
        ACCESS  read-write
        STATUS  mandatory
        DESCRIPTION
                "Default value on nX: nrz
                On nX: both ram and flash

                If appropriate for the Link Line Type, this flag 
                identifies whether the line is nrz or nrzi.  
                (See Destination NRZ Flag.)"
        ::= { wanPortEntry 11 }

wanLinkLayerProtocolType OBJECT-TYPE
        SYNTAX  INTEGER { 
        none(1),
        ppp(2),
        isdn(3),
        x25(4),
        framerelaydte(5),
        framerelaydce(6)
      } 
        ACCESS  read-write
        STATUS  mandatory
        DESCRIPTION
                "Default value on nX: ppp 
                On nX: both ram and flash,

  This flag identifies whether the Link Line Type is ppp.
  Other options are not supported at this time."
        ::= { wanPortEntry 12 }

wanLinkDialupFlag OBJECT-TYPE
        SYNTAX  INTEGER { dialup(1), dedicated(2), dtr-dial(3), isdn-dialup(4)}
        ACCESS  read-write
        STATUS  mandatory
        DESCRIPTION
                "Default value on nX: dialup
                dtr-dial(3) is obsolete (3/4/96)
                On nX: both ram and flash, field trial 1 (may be 
                encoded into Link Layer Type)

                If appropriate for the Link Line Type, this flag 
                identifies whether the line is dialup (switched), 
                dedicated, DTR dial, or ISDN dialup link."
        ::= { wanPortEntry 13 }

wanModemName OBJECT-TYPE
        SYNTAX  DisplayString (SIZE(0..51))
        ACCESS  read-write
        STATUS  mandatory
        DESCRIPTION
                "Default value on nX: empty
                On nX: both ram and flash, field trial 1

                This object contains the ASCII name of the modem.  
                It is used by Workshop to determine the initialization 
                modem string and maximum speed for this modem. 
                 This object is not used by the nX product.  
                 (If possible on Workshop, this field will be 
                 changed to something shorter, like an integer -  
                 if not will try to combine with PCMCIA Card Name.)"
        ::= { wanPortEntry 14 }

wanModemSpeed OBJECT-TYPE
        SYNTAX  INTEGER { twelvehundred(1200),
        twentyfourhundred(2400),
        fortyeighthundred(4800), 
        ninetysixhundred(9600), 
        nineteentwelve(19200),
        thirtyeigthfour(38400),
                          fiftysevensix(57600), 
        onefifteentwo(115200) }
        ACCESS  read-write
        STATUS  mandatory
        DESCRIPTION
                "Default value on nX: 9600
                On nX: both ram and flash, field trial 1

                This object contains an indicator of the speed at 
                which the nX product should communicate with the modem.  
                This value cannot be larger than that obtained from 
                the Modem File using the Modem Name.  (Note: The UART 
                does not support 14400 or 28800 directly so a higher 
                speed must be specified and hardware handshake will 
                be used to prevent overruns.)"
        ::= { wanPortEntry 15 }

wanModemInitializationString OBJECT-TYPE
        SYNTAX  DisplayString (SIZE(0..59))
        ACCESS  read-write
        STATUS  mandatory
        DESCRIPTION
                "Default value on nX: empty
                On nX: both ram and flash, field trial 1

                This object contains the ASCII string that is to be 
                sent to the modem whenever the modem is to be initialized."
        ::= { wanPortEntry 16 }

wanModemDialPrefix OBJECT-TYPE
        SYNTAX  DisplayString (SIZE(0..19))
        ACCESS  read-write
        STATUS  mandatory
        DESCRIPTION
                "Default value on nX: empty
                On nX: both ram and flash, field trial 1

                This is set by the user.  It contains the modem's 
                dial command (e.g. ATDT or ATDP) possibly suffixed 
                with the dial prefix, if any, to obtain an outside 
                phone line.  (Note that the user could include the 
                dial prefix in the Destination Phone Number instead.)  
                For example, at SBE this would be set to '8' if the 
                nX product's phone lines were inside lines.  This 
                string is long so it can include other items, such 
                as billing codes, if necessary.  (Will contain codes 
                to differentiate V.25 dialing from ATDT dialing.)"
        ::= { wanPortEntry 17 }

wanPortType OBJECT-TYPE
        SYNTAX  INTEGER { pcmcia(1), rs232(2), v35(4) }
        ACCESS  read-only
        STATUS  mandatory
        DESCRIPTION
                "Default value on nX: determined by hardware
                Workshop no longer sets this field

                This value indicates whether the port is PCMCIA, 
                or a D-shell connection - either RS232 or V.35."
        ::= { wanPortEntry 18 }

wanPCMCIACardName OBJECT-TYPE
        SYNTAX  DisplayString (SIZE ( 0..63 ))
        ACCESS  read-only
        STATUS  mandatory
        DESCRIPTION
                "Default value on nX: empty string if card not present, 
                 else product information from card
                On nX: from 'ram' (actually hardware), field trial 1
                Workshop no longer display this field
                This object returns the product information read 
                from a PCMCIA card.  If the returned value is a 0 
                length string, then the PCMCIA slot is empty.  
                (60 characters available from hardware.)"
        ::= { wanPortEntry 19 }

wanIpRipReceiveAdvertisementFlag OBJECT-TYPE
        SYNTAX  INTEGER { no(1), yes(2) }
        ACCESS  read-write
        STATUS  mandatory
        DESCRIPTION
                "Default value on nX: 'yes'
                On nX: both ram and flash, field trial 2

                If IP is configured, this object determines whether 
                or not the nX product will accept IP RIP (Routing 
                Information Protocol) from other routers on the 
                network.  Advertisements received will be added 
                to the nX product's dynamic routing table."
        ::= { wanPortEntry 20 }

wanIpRipSendInterval OBJECT-TYPE
        SYNTAX  INTEGER ( 0..65535 )
        ACCESS  read-write
        STATUS  mandatory
        DESCRIPTION
                "Default value on nX: 30
                On nX: both ram and flash, field trial 2

                If IP is configured, this object determines time, 
                in seconds, between nX broadcasts of the IP RIP 
                destination information in its routing tables.  
                If the value equals 0, RIP transmissions are not 
                sent."
        ::= { wanPortEntry 21 }

wanIpxRipReceiveBroadcastFlag OBJECT-TYPE
        SYNTAX  INTEGER { no(1), yes(2) }
        ACCESS  read-write
        STATUS  mandatory
        DESCRIPTION
                "Default value on nX: ''yes'
                On nX: both ram and flash, field trial 2

                If IPX is configured, this object determines 
                whether or not the nX product will accept IPX 
                RIP (Routing Information Protocol) from other
                routers on the network.  Broadcasts received 
                will be added to the nX product's dynamic 
                routing table."
        ::= { wanPortEntry 22 }

wanIpxRipSendInterval OBJECT-TYPE
        SYNTAX  INTEGER ( 0..65535 )
        ACCESS  read-write
        STATUS  mandatory
        DESCRIPTION
                "Default value on nX: 60
                On nX: both ram and flash, field trial 2

                If IPX is configured, this object determines 
                time, in seconds, between nX broadcasts of the 
                IPX RIP destination information in its routing 
                tables. If the value equals 0, RIP transmissions 
                are not sent."
        ::= { wanPortEntry 23 }

wanIpxSapReceiveAdvertisementFlag OBJECT-TYPE
        SYNTAX  INTEGER { no(1), yes(2) }
        ACCESS  read-write
        STATUS  mandatory
        DESCRIPTION
                "Default value on nX: ''yes'
                On nX: both ram and flash, field trial 2

                If IPX is configured, this object determines 
                whether or not the nX product will accept IPX 
                SAP advertisements from other routers on the 
                network.  Advertisements received will be added 
                to the nX product's dynamic SAP table."
        ::= { wanPortEntry 24 }

wanIpxSapSendInterval OBJECT-TYPE
        SYNTAX  INTEGER ( 0..65535 )
        ACCESS  read-write
        STATUS  mandatory
        DESCRIPTION
                "Default value on nX: 60
                On nX: both ram and flash, field trial 2

                If IPX is configured, this object determines 
                time, in seconds, between nX broadcasts of the 
                IPX SAP information in its routing tables.  If 
                the value equals 0, SAP advertisements are not 
                sent."
        ::= { wanPortEntry 25 }

wanIpxNetbios OBJECT-TYPE
        SYNTAX  INTEGER { no(1), yes(2) }
        ACCESS  read-write
        STATUS  mandatory
        DESCRIPTION
                "Default value on nX: 'no'
                On nX: both ram and flash, field trial 2

                If IPX is configured, this object determines 
                if NetBIOS broadcasts are to be forwarded 
                across interfaces.  (It appears this is only 
                needed if there is an application on the 
                network that initiates a connection with a 
                dialin client, see Shiva LanRover, page 10-6.)"
        ::= { wanPortEntry 26 }

wanISDNSwitchType OBJECT-TYPE
    SYNTAX  INTEGER {
			      other(1),
            dss1(2),            -- ITU DSS1 (formerly CCITT) Q.931
            etsi(3),            -- Europe / ETSI ETS300-102
                                -- plus supplementary services
                                -- (ETSI 300-xxx)
                                -- note that NET3, NET5 define
                                -- test procedures for ETS300-102
                                -- and are to be replaced by ICTR.
            btnr(4),            -- U.K.   / BTNR (BRI ?)
            dass2(5),           -- U.K.   / DASS2 (PRI)
            ess4(6),            -- U.S.A. / AT&T 4ESS
            ess5(7),            -- U.S.A. / AT&T 5ESS
            dms100(8),          -- U.S.A. / Northern Telecom DMS100/DMS250
            ni1(9),             -- U.S.A. / National ISDN 1 (BRI)
            ni2(10),            -- U.S.A. / National ISDN 2 (BRI, PRI)
            ni3(11),            -- U.S.A. / next one ?
            vn2(12),            -- France / VN2
            vn3(13),            -- France / VN3
            vn4(14),            -- France / VN4 (ETSI with changes)
            vn6(15),            -- France / VN6 (ETSI with changes)
                                -- delta document CSE P 10-21 A
                                -- test document  CSE P 10-20 A
            kdd(16),            -- Japan  / KDD
     			  ins64(17),          -- Japan  / NTT INS64
            itr6(18),           -- Germany/ 1TR6 (BRI, PRI)
            cornet(19),         -- Germany/ Siemens HiCom CORNET
            tad2(20),           -- ???    / (BRI)
            tad30(21),          -- ???    / (PRI)
            ts013(22),          -- Australia / TS013 (formerly TPH 1962, BRI)
            ts014(23),          -- Australia / TS014 (formerly TPH 1856, PRI)
            --
 --
            -- some specifications for ISDN leased lines, as
            -- existing in Germany and eventually in the U.S.,
            -- follow.
            --
            leased64s(24),      -- 1xB (Germany)
            leasedS01(25),      -- 1xB, 1xD (Germany)
            leasedS02(26),      -- 2xB, 1xD (Germany)
            leasedH0(27),       -- 6xB
            leasedT1(28),       -- 24xB
            leasedE1(29)        -- 30xB (Germany)
        }
        ACCESS read-write
        STATUS mandatory
        DESCRIPTION
            "The particular protocol type supported by the
            switch providing access to the ISDN network
            to which this subscriber interface is connected.
      Note: this entry definition is borrowed from the
      isdnSubTblSwitchType of the ISDN MIB Internet Draft"
    ::= { wanPortEntry 27 }
 

wanISDNCallingPhoneNoB1 OBJECT-TYPE
        SYNTAX  DisplayString ( SIZE( 0..31 ) )
        ACCESS  read-write
        STATUS  mandatory
        DESCRIPTION
                "Default value on nX: empty
 
                This item contains the calling phone number for the
        ISDN B1 channel. "
        ::= { wanPortEntry 28 }
 
wanISDNCallingPhoneNoB2 OBJECT-TYPE
        SYNTAX  DisplayString ( SIZE( 0..31 ) )
        ACCESS  read-write
        STATUS  mandatory
        DESCRIPTION
                "Default value on nX: empty
 
                This item contains the calling phone number for the
                ISDN B1 channel. "
        ::= { wanPortEntry 29 }
 
wanISDNSPID1  OBJECT-TYPE
    SYNTAX  DisplayString ( SIZE( 0..31 ) )
        ACCESS  read-write
        STATUS  mandatory
        DESCRIPTION
        "Default value on nX: empty
 
        This item contains the Service Profile Identifiers (SPID) for
        the  ISDN B1 channel. "
        ::= { wanPortEntry 30 }
 
wanISDNSPID2    OBJECT-TYPE
        SYNTAX  DisplayString ( SIZE( 0..31 ) )
        ACCESS  read-write
        STATUS  mandatory
        DESCRIPTION
        "Default value on nX: empty
 
        This item contains the Service Profile Identifiers (SPID) for
        the  ISDN B2 channel. "
        ::= { wanPortEntry 31 }

wanPortGroup OBJECT-TYPE
      SYNTAX  INTEGER { group(1), non-group(2) }
      ACCESS  read-write
      STATUS  mandatory
      DESCRIPTION
       "Default value on nX:  non-group(2) 
      
       This field is used to identify wether the Wan port is part of the 
       Hunt Group. Port group is used as hunt group in TSD for reserving 
       wan link capacity."
       ::= { wanPortEntry 32 }

wanISDNSubAddress1    OBJECT-TYPE
        SYNTAX  DisplayString ( SIZE( 0..31 ) )
        ACCESS  read-write
        STATUS  mandatory
        DESCRIPTION
        "Default value on nX: empty

        This item contains the subaddress for the  ISDN B1 channel. "
        ::= { wanPortEntry 33 }

wanISDNSubAddress2    OBJECT-TYPE
        SYNTAX  DisplayString ( SIZE( 0..31 ) )
        ACCESS  read-write
        STATUS  mandatory
        DESCRIPTION
                "Default value on nX: empty

                This item contains the subaddress for the  ISDN B2 channel. "
        ::= { wanPortEntry 34 }

wanISDNNTTCard    OBJECT-TYPE
	SYNTAX  INTEGER { no(1),  yes(2) }
        ACCESS  read-write
        STATUS  mandatory
        DESCRIPTION
                "Default value on nX: no(1)

                This item indicates whether this is an NTT ISDN card."
        ::= { wanPortEntry 35 }

wanISDNChannels    OBJECT-TYPE
        SYNTAX  INTEGER { oneb(1),  twob(2) }
        ACCESS  read-write
        STATUS  mandatory
        DESCRIPTION
                "Default value on nX: oneb(1)
 
                This item indicates the number B channels supported 
                by the ISDN card."
        ::= { wanPortEntry 36 }

wanEnableDataCompression OBJECT-TYPE
        SYNTAX  INTEGER { no(1), yes(2) }
        ACCESS  read-write
        STATUS  mandatory
        DESCRIPTION
                "Default value on nX: no.
                 this entry indicates whether to perform data compression
                 over the ppp connection."
        ::= { wanPortEntry 37 }

wanISDNChannelSpeed  OBJECT-TYPE
        SYNTAX  INTEGER { cs56(1),  cs64(2) }
        ACCESS  read-write
        STATUS  mandatory
        DESCRIPTION
                "Default value on nX: cs64.
 
                This entry is used to configure the B channel speed
                of the ISDN card."
        ::= { wanPortEntry 38 }

wanUsageMode OBJECT-TYPE
        SYNTAX  INTEGER { routing(1), modempool(2), share(3) }
        ACCESS  read-write
        STATUS  mandatory
        DESCRIPTION
                "Default value on nX: 1
                This value indicates how the port is used for 
                modem pooling. If 2 or 3 is set, the GSN and
		SSN also must be set.
		
		Note: This is a bit mapped field."
        ::= { wanPortEntry 39 }

wanModemPoolGSN OBJECT-TYPE
        SYNTAX  DisplayString (SIZE ( 0..8 ))
        ACCESS  read-write
        STATUS  mandatory
        DESCRIPTION
                "The General Service Name used for this port. Used for
		 Modem pooling"
        ::= { wanPortEntry 40 }

wanModemPoolSSN OBJECT-TYPE
        SYNTAX  DisplayString (SIZE ( 0..14 ))
        ACCESS  read-write
        STATUS  mandatory
        DESCRIPTION
                "The Specific Service Name used for this port. Used for
		 Modem pooling"
        ::= { wanPortEntry 41 }


-- Wan IP Address Table
-- This table is used to define a sharable pool of IP Addresses 
-- for remote dial-in user to access netXpand via PPP, if no
-- pre-assigned IP address used.

-- Wan IP Address Table
-- This table is used to define a sharable pool of IP Addresses 
-- for remote dial-in user to access netXpand via PPP, if no
-- pre-assigned IP address used.

wanIPAddressTable OBJECT-TYPE
        SYNTAX SEQUENCE OF WanIPAddressEntry
     --%{ return SNMP-SBEMIB-WANIPAccess(snmpi); %}
        ACCESS not-accessible
        STATUS mandatory
        DESCRIPTION 
                "WanIPAddress table - one copy"
        ::= {wan 2}

wanIPAddressEntry OBJECT-TYPE
        SYNTAX WanIPAddressEntry
        ACCESS not-accessible
        STATUS mandatory
        DESCRIPTION
                "           "
        INDEX {wanIPAddress }
        ::= { wanIPAddressTable 1 }

       WanIPAddressEntry ::= SEQUENCE {
          wanIPAddressStatus
            INTEGER,
          wanIPAddress
            IpAddress
        }

wanIPAddressStatus OBJECT-TYPE
        SYNTAX  INTEGER { 
       valid(1),
       create-request(2),
       under-creation(3),
       invalid(4),
       modify(5)      
        }
        ACCESS  read-write
        STATUS  mandatory
        DESCRIPTION
                "Indication of whether or not a valid entry."
        ::= { wanIPAddressEntry 1 }


wanIPAddress OBJECT-TYPE
        SYNTAX  IpAddress
        ACCESS  read-only
        STATUS  mandatory
        DESCRIPTION
                "Default value on nX: 0
                On nX: both ram and flash, field trial 2

                This item specifies an IP address in the shared pool for remote
                dial-in user."
        ::= { wanIPAddressEntry 2 }


-- Wan Port Statistics MIB

wanStatPortTable OBJECT-TYPE
  SYNTAX SEQUENCE OF WanStatPortEntry
     --%{ return SNMP-SBEMIB-WANStatAccess(snmpi); %}
  ACCESS not-accessible
  STATUS mandatory
  DESCRIPTION
                "Each WAN port's State and Statistical information
                is contained in a row in a SNMP table"
  ::= { wan 3 }


wanStatPortEntry OBJECT-TYPE
  SYNTAX WanStatPortEntry
  ACCESS not-accessible
  STATUS mandatory
  DESCRIPTION
    "The WAN table information for one WAN port." 
  INDEX { wanStatPortNumber }
  ::= { wanStatPortTable 1 }

  WanStatPortEntry ::= SEQUENCE
   {
    wanStatPortEntryStatus INTEGER,
    wanStatPortNumber INTEGER,
    wanStatPortState INTEGER,
    wanStatPortUserName DisplayString,
    wanStatPortFrameTransmitted INTEGER,
    wanStatPortFrameReceived INTEGER,
    wanStatPortTransmitError INTEGER,
    wanStatPortReceiveError INTEGER,
    wanStatPortTransmitQueueFull INTEGER,
    wanStatPortCallOriginated INTEGER,
    wanStatPortCallAnswered INTEGER,
    wanStatPortNoDialTone INTEGER,
    wanStatPortNoAnswer INTEGER,
    wanStatPortBusyDetected INTEGER,
    wanStatPortNoCarrier INTEGER,
    wanStatPortModemSignal INTEGER,
    wanStatPortConnDirection INTEGER,
    wanStatPortProtoUp INTEGER
    }

wanStatPortEntryStatus OBJECT-TYPE
        SYNTAX  INTEGER {
      valid(1),
      create-request(2),
      under-creation(3),
      invalid(4),
      modify(5)      
      }
        ACCESS  read-write
        STATUS  mandatory
        DESCRIPTION
                "Indication of whether or not a valid entry. This entry is used
                  only to maintain uniformity of all table structures. User can
                  neither delete nor add any entries in the table. Upon query,
                  nX shall always return valid."
        ::= { wanStatPortEntry 1 }

wanStatPortNumber OBJECT-TYPE
        SYNTAX  INTEGER ( 1..18 )
        ACCESS  read-only
        STATUS  mandatory
        DESCRIPTION
                "Same as in wanPortNumber."
        ::= { wanStatPortEntry 2 }

wanStatPortState OBJECT-TYPE
        SYNTAX  INTEGER { disconnected(1), connected(2) }
        ACCESS  read-only
        STATUS  mandatory
        DESCRIPTION
               "Default value on nX: disconnected."
        ::= { wanStatPortEntry 3 }

wanStatPortUserName OBJECT-TYPE
        SYNTAX  DisplayString ( SIZE ( 0..31 )  )
        ACCESS  read-only
        STATUS  mandatory
        DESCRIPTION
                "Currently connected Destination name or user name. Null
                  if unknown."
        ::= { wanStatPortEntry 4 }

wanStatPortFrameTransmitted OBJECT-TYPE
        SYNTAX  INTEGER
        ACCESS  read-write
        STATUS  mandatory
        DESCRIPTION
                "# of frames transmitted out of this port."
        ::= { wanStatPortEntry 5 }

wanStatPortFrameReceived OBJECT-TYPE
        SYNTAX  INTEGER
        ACCESS  read-write
        STATUS  mandatory
        DESCRIPTION
                "# of frames received from this port."
        ::= { wanStatPortEntry 6 }

wanStatPortTransmitError OBJECT-TYPE
        SYNTAX  INTEGER
        ACCESS  read-write
        STATUS  mandatory
        DESCRIPTION
                "# of transmit errors detected at this port."
        ::= { wanStatPortEntry 7 }

wanStatPortReceiveError OBJECT-TYPE
        SYNTAX  INTEGER
        ACCESS  read-write
        STATUS  mandatory
        DESCRIPTION
                "# of receive errors detected at this port."
        ::= { wanStatPortEntry 8 }

wanStatPortTransmitQueueFull OBJECT-TYPE
        SYNTAX  INTEGER
        ACCESS  read-write
        STATUS  mandatory
        DESCRIPTION
                "# of times transmit queue full detected at this port."
        ::= { wanStatPortEntry 9 }

-- The following statistics are modem related ----

wanStatPortCallOriginated OBJECT-TYPE
        SYNTAX  INTEGER
        ACCESS  read-write
        STATUS  mandatory
        DESCRIPTION
                "# of calls originated from this port. Includes
                 both success and fail."
        ::= { wanStatPortEntry 10 }

wanStatPortCallAnswered OBJECT-TYPE
        SYNTAX  INTEGER
        ACCESS  read-write
        STATUS  mandatory
        DESCRIPTION
                "# of answers succeeded at this port."
        ::= { wanStatPortEntry 11 }

wanStatPortNoDialTone OBJECT-TYPE
        SYNTAX  INTEGER
        ACCESS  read-write
        STATUS  mandatory
        DESCRIPTION
                "# of calls failed due to no dial tone. 
                 also counted also in CallOriginated"
        ::= { wanStatPortEntry 12 }

wanStatPortNoAnswer OBJECT-TYPE
        SYNTAX  INTEGER
        ACCESS  read-write
        STATUS  mandatory
        DESCRIPTION
                "# of calls failed due to no answer from remote.
                 also counted also in CallOriginated"
        ::= { wanStatPortEntry 13}

wanStatPortBusyDetected OBJECT-TYPE
        SYNTAX  INTEGER
        ACCESS  read-write
        STATUS  mandatory
        DESCRIPTION
                "# of calls failed due to line busy at remote.
                  also counted also in CallOriginated"
        ::= { wanStatPortEntry 14 }

wanStatPortNoCarrier OBJECT-TYPE
        SYNTAX  INTEGER
        ACCESS  read-write
        STATUS  mandatory
        DESCRIPTION
                "# of calls failed due to no carrier.
                  also counted also in CallOriginated"
        ::= { wanStatPortEntry 15 }

wanStatPortModemSignal OBJECT-TYPE
        SYNTAX  INTEGER
        ACCESS  read-only
        STATUS  mandatory
        DESCRIPTION
                "Modem signal state. Bit masked
                  DCD = 1, CTS =2, DTR = 4, RTS = 8, DSR =16 
                   Bit state: 1 = On "
        ::= { wanStatPortEntry 16 }

wanStatPortConnDirection OBJECT-TYPE
        SYNTAX  INTEGER { dialin(1), dialout(2), dedicated(3) }
        ACCESS  read-only
        STATUS  mandatory
        DESCRIPTION
                "Direction of the connection"
        ::= { wanStatPortEntry 17 }

wanStatPortProtoUp OBJECT-TYPE
        SYNTAX  INTEGER
        ACCESS  read-only
        STATUS  mandatory
        DESCRIPTION
                "This item is a bit encoded value representing various
                 protocols, which are currently up over this connection.
                 The encoded values are:
                 IP(1), IPX(2), Bridging(4), Compression(8).
                 Any combinations of these values are valid."
        ::= { wanStatPortEntry 18 }


-- Max entries in IP address pool

wanIPAddressMaxEntry OBJECT-TYPE
        SYNTAX  INTEGER
     		--%{ return SNMP-SBEMIB-WANIPMaxEntryAccess(snmpi); %}
        ACCESS  read-only
        STATUS  mandatory
        DESCRIPTION
                "maximum # of entry allowed in the wanIPAddressTable."
        ::= { wan 4 }


----------------------------------------------------------------------
--                      sbe.router.ip  BRANCH 
----------------------------------------------------------------------

ipConfiguredFlag OBJECT-TYPE
        SYNTAX  INTEGER { no(1), yes(2) }
     --%{ return SNMP-SBEMIB-IPAccess(snmpi); %}
        ACCESS  read-write
        STATUS  mandatory
        DESCRIPTION
                "Default value on nX: 'no'
                On nX: both ram and flash, field trial 1

                This object is 'no' if IP is not configured for 
                this LX-Product, 'yes' if it is configured."
        ::= { ip 1 }

ipLANAddress OBJECT-TYPE
        SYNTAX  IpAddress
     --%{ return SNMP-SBEMIB-IPAccess(snmpi); %}
        ACCESS  read-write
        STATUS  mandatory
        DESCRIPTION
                "Default value on nX: 0
                On nX: both ram and flash, field trial 1

                If IP is configured, this object contains the 
                IP address for the nX product's ethernet port 
                and the nX product itself.  The user must supply 
                this value if IP is configured.  When IP is 
                configured this value must not be 0."
        ::= { ip 2 }

ipLANSubnetMask OBJECT-TYPE
        SYNTAX  IpAddress
     --%{ return SNMP-SBEMIB-IPAccess(snmpi); %}
        ACCESS  read-write
        STATUS  mandatory
        DESCRIPTION
                "Default value on nX: N/A
                Default value in Workshop: 0
                On nX: both ram and flash, field trial 1

                If IP is configured, this object contains the 
                subnet mask which the nX product will use for 
                determining which packets are to be sent out 
                over this LAN port.  (A packet's IP address is 
                'anded' with the subnet mask and the result 
                compared against the port's IP address.  If 
                there is a match, the packet is sent over the 
                port, otherwise it isn't.)"
        ::= { ip 3 }

ipBroadcastAddress OBJECT-TYPE
        SYNTAX  IpAddress
     --%{ return SNMP-SBEMIB-IPOptions(snmpi); %}
        ACCESS  read-write
        STATUS  mandatory
        DESCRIPTION
                "Default value on nX: 0
                Default value in Workshop: 0
                On nX: both ram and flash, field trial 1

                If IP is configured, this object contains the IP 
                address which the nX product will use for sending 
                broadcast data.  (The nX listens for broadcast data 
                on broadcast addresses with both 0's and all 1's).  
                A zero value means no broadcasts can be sent.  
                This is used for sending RIP advertisements and 
                for indicating which broadcasts are to be forwarded 
                across ports."
        ::= { ip 4 }

ipDefaultGateway OBJECT-TYPE
        SYNTAX  IpAddress
     --%{ return SNMP-SBEMIB-IPOptions(snmpi); %}
        ACCESS  read-write
        STATUS  mandatory
        DESCRIPTION
                "Default value on nX: N/A
                Default value in Workshop: 0
                On nX: both ram and flash, field trial 2

                If IP is configured, this object contains the network 
                address to which the nX product will send all packets 
                that it cannot determine a route for the packet from
                its routing tables (both static and dynamic)."
        ::= { ip 5 }

ipRipReceiveAdvertisementFlag OBJECT-TYPE
        SYNTAX  INTEGER { no(1), yes(2) }
     --%{ return SNMP-SBEMIB-IPOptions(snmpi); %}
        ACCESS  read-write
        STATUS  mandatory
        DESCRIPTION
                "Default value on nX: 'yes'
                On nX: both ram and flash, field trial 2

                If IP is configured, this object determines whether 
                or not the nX product will accept IP RIP (Routing 
                Information Protocol) from other routers on the 
                network.  Advertisements received will be added 
                to the nX product's dynamic routing table."
        ::= { ip 6 }

ipRipSendInterval OBJECT-TYPE
        SYNTAX  INTEGER ( 0..65535 )
     --%{ return SNMP-SBEMIB-IPOptions(snmpi); %}
        ACCESS  read-write
        STATUS  mandatory
        DESCRIPTION
                "Default value on nX: 30
                On nX: both ram and flash, field trial 2

                If IP is configured, this object determines time, 
                in seconds, between nX broadcasts of the IP RIP 
                destination information in its routing tables.  
                If the value equals 0, RIP transmissions are not 
                sent."
        ::= { ip 7 }

ipDefaultGatewayType OBJECT-TYPE
        SYNTAX  INTEGER { none(0), lan(1), wan(2) }
     --%{ return SNMP-SBEMIB-IPOptions(snmpi); %}
        ACCESS  read-write
        STATUS  mandatory
        DESCRIPTION
                "Default value on nX: NONE
                On nX: both ram and flash, field trial 2

                If nX cannot determine a route for the packet from
                its routing table (both static and dynamic), the
                packet will be sent to a Default Gateway.
                If ipDefaultGatewayType is LAN, ipDefaultGateway
                address will be useed.  Otherwise, the Default Gateway
                is located at WAN port, the packet will be forwarded
                to the destination defined in ipWanDestinationName
                or ipWanUserName."
        ::= { ip 8 }

ipWanDestinationName OBJECT-TYPE
        SYNTAX  DisplayString ( SIZE ( 0..31 ))
     --%{ return SNMP-SBEMIB-IPOptions(snmpi); %}
        ACCESS  read-write
        STATUS  mandatory
        DESCRIPTION
                "Same as destName in the Destination Table."

        ::= { ip 9 }

ipWanUserName OBJECT-TYPE
        SYNTAX  DisplayString ( SIZE ( 0..31 ))
     --%{ return SNMP-SBEMIB-IPOptions(snmpi); %}
        ACCESS  read-write
        STATUS  mandatory
        DESCRIPTION
                "Same as userName in the User Table."

        ::= { ip 10 }

-- IP Static Routing Table
-- The IP Static Routing Table contains routes manually established
-- by the user.  Each row in the table is uniquely identified by the
-- IP Destination Address.  This table is only used if IP is configured.
-- Workshop sorts the table with the IP Destination Address only.
-- 'Duplicate' entries are not allowed.

-- In case of conflict with dynamically discovered routing information,
-- the dynamic information will take precedence within the LX.
-- Both static and dynamic routing table entries are broadcast.

ipStaticRouteMaxEntry OBJECT-TYPE
                SYNTAX INTEGER
                                 --%{ return SNMP-SBEMIB-IPOptions(snmpi); %}
                ACCESS read-only
                STATUS mandatory
                DESCRIPTION
                        "maximum # of entry allowed in the
                         ipStaticRouteTable.  Default to 32."
                ::= { ip 11 }
 
ipStaticRouteTable OBJECT-TYPE
                SYNTAX SEQUENCE OF IpStaticRouteEntry
                                 --%{ return SNMP-SBEMIB-StRouteAccess(snmpi); %}
                ACCESS not-accessible
                STATUS mandatory
                DESCRIPTION
                        "IP Static Route table - one copy per IP port."
                ::= { ip 12 }
 
-- The entry ipDefaultGatewayType needs to be depricated because it uses an
-- illegal enumerated value of zero for 'none'. ipDefaultGatewayIfType
-- supersedes the ipDefaultGatewayType. 

ipDefaultGatewayIfType OBJECT-TYPE
        SYNTAX  INTEGER {lan(1), wan(2), none(3) }
     --%{ return SNMP-SBEMIB-IPOptions(snmpi); %}
        ACCESS  read-write
        STATUS  mandatory
        DESCRIPTION
                "Default value on nX: NONE
                If nX cannot determine a route for the packet from
                its routing table (both static and dynamic), the
                packet will be sent to a Default Gateway.
                If ipDefaultGatewayType is LAN, ipDefaultGateway
                address will be useed.  Otherwise, the Default Gateway
                is located at WAN port, the packet will be forwarded
                to the destination defined in ipWanDestinationName
                or ipWanUserName."
        ::= { ip 13 }

ipBroadcastForwardTypes OBJECT-TYPE
        SYNTAX  INTEGER (1..15)
     --%{ return SNMP-SBEMIB-IPOptions(snmpi); %}
        ACCESS  read-write
        STATUS  mandatory
        DESCRIPTION
                "Default value on nX: 0

                This is a bit encoded value representing the types of IP
	        broadcast forwarding over WAN to be enabled. This is a 
                global setting for the NX. The mib entry 
                destDialoutProtoSupport is used to control the IP broadcast
                forwarding to an invidual site. The encoded values are:
                  NetBIOS(2), DNS(4), DHCP/BOOTP(8).
                Any combination of these values or NOBCASTFWD(1) are the
	        only valid values."
        ::= { ip 14 }

ipStaticRouteEntry OBJECT-TYPE
                SYNTAX IpStaticRouteEntry
                ACCESS not-accessible
                STATUS mandatory
                DESCRIPTION
                        "The static route information for one route for
                         this port."
                INDEX { ipStaticRouteDestinationAddress }
                ::= { ipStaticRouteTable 1 }
                
                IpStaticRouteEntry ::=       
                        SEQUENCE {
                                ipStaticRouteStatus INTEGER,
                                ipStaticRouteDestinationAddress IpAddress,
                                ipStaticRouteDestinationSubnetMask IpAddress,
                                ipStaticRouteDestinationHopCount INTEGER,
                                ipStaticRouteDestinationName DisplayString,
                                ipStaticRouteNetworkInterface INTEGER,
                                ipStaticRouteUserName DisplayString,
                                ipStaticRouteGateway IpAddress
                                }
 
ipStaticRouteStatus OBJECT-TYPE
        SYNTAX  INTEGER {
                             valid(1),
                             create-request(2),
                             under-creation(3),
                             invalid(4)
                         }
        ACCESS  read-write
        STATUS  mandatory
        DESCRIPTION
                "Indication of whether or not a valid entry."
        ::= { ipStaticRouteEntry 1 }

ipStaticRouteDestinationAddress OBJECT-TYPE
        SYNTAX  IpAddress
        ACCESS  read-only
        STATUS  mandatory
        DESCRIPTION
                "This is a destination network or host IP address.
                Packets that the nX product processes for this
                address will be routed as indicated by the
                remaining entries in this row.  This value
                has already been 'anded' with the IP Destination
                Subnet Mask."
        ::= { ipStaticRouteEntry 2 }

ipStaticRouteDestinationSubnetMask OBJECT-TYPE
        SYNTAX  IpAddress
        ACCESS  read-write
        STATUS  mandatory
        DESCRIPTION
                "Workshop should display by default the subnet mask based
                on class of destination IP address, the nX should not
                assume any default subnet value.

                This subnet mask is applied to destination address
                in packets processed by the nX product and then
                the resulting value is compared against the IP
                Destination Address.  If a match is found, the
                packet is forwarded over the indicated destination
                interface."
        ::= { ipStaticRouteEntry 3 }

ipStaticRouteDestinationHopCount OBJECT-TYPE
        SYNTAX  INTEGER ( 1..16 )
        ACCESS  read-write
        STATUS  mandatory
        DESCRIPTION
                "The value of this object indicates the number of
                hops between the nX product and the IP
                Destination Address.  The hop count is often
                used as an indicator of the relative cost for
                using this route.  This will be used by the LX
                to optimize the use of routes learned.  By IP
                convention, if the hop count equals 16 the
                routing entry is disabled."
        ::= { ipStaticRouteEntry 4 }

ipStaticRouteDestinationName OBJECT-TYPE
        SYNTAX  DisplayString ( SIZE ( 0..31 )  )
        ACCESS  read-write
        STATUS  mandatory
        DESCRIPTION
                "Same as destName in the Destination Table."

        ::= { ipStaticRouteEntry 5 }

ipStaticRouteNetworkInterface OBJECT-TYPE
        SYNTAX  INTEGER {
                          lan(1),
                          wan(2)
                         }
        ACCESS  read-write
        STATUS  mandatory
        DESCRIPTION
                "Indication of which interface type to route this
                 packet to.  If LAN is defined, ipStaticRouteGateway
                 must be defined.
                 Otherwise, at least one of ipStaticRouteUserName and
                 ipStaticRouteDestinationName must be defined."
        ::= { ipStaticRouteEntry 6 }

ipStaticRouteUserName OBJECT-TYPE
        SYNTAX  DisplayString ( SIZE ( 0..31 )  )
        ACCESS  read-write
        STATUS  mandatory
        DESCRIPTION
                "Same as userName in the User Table."

        ::= { ipStaticRouteEntry 7 }

ipStaticRouteGateway OBJECT-TYPE
        SYNTAX  IpAddress
        ACCESS  read-write
        STATUS  mandatory
        DESCRIPTION
                "This is the Gateway IP address of the static route."
        ::= { ipStaticRouteEntry 8 }

----------------------------------------------------------------------
--                      sbe.router.ipx  BRANCH 
----------------------------------------------------------------------

-- IPX Configuration OBJECT-TYPE
-- The following objects define the IP configuration information for 
-- this nX product.

ipxConfiguredFlag OBJECT-TYPE
        SYNTAX  INTEGER { ipx-and-auto-learn-both-off (1),
			  ipx-off-and-auto-learn-on   (2),
			  ipx-on-and-auto-learn-off   (3),
			  ipx-and-auto-learn-both-on  (4)
			}
        ACCESS  read-write
        STATUS  mandatory
        DESCRIPTION
                "Default value on nX: 'ipx-and-auto-learn-both-off (1)'
                On nX: both ram and flash,

                This object reflects the state of ipx and auto-learning
                configuration as described by the names of the values."
        ::= { ipx 1 }

-- ipxManualSetNetworkAddress OBJECT-TYPE
--         SYNTAX  INTEGER { no(1), yes(2) }
--         ACCESS  read-only
--         STATUS  deprecated
--         DESCRIPTION
--                 "THIS ITEM IS NOT IMPLEMENTED!"
--         ::= { ipx 2 }

-- ipxManualNetworkAddress OBJECT-TYPE
--         SYNTAX  OCTET STRING (SIZE ( 4 ) )
--         ACCESS  read-write
--         STATUS  deprecated
--         DESCRIPTION
--                 "THIS ITEM IS NOT IMPLEMENTED!"
--         ::= { ipx 3 }

-- ipxRipReceiveBroadcastFlag OBJECT-TYPE
--         SYNTAX  INTEGER { no(1), yes(2) }
--         ACCESS  read-only
--         STATUS  deprecated
--         DESCRIPTION
--                 "THIS ITEM IS NOT IMPLEMENTED!"
--         ::= { ipx 4 }

-- ipxRipSendInterval OBJECT-TYPE
--         SYNTAX  INTEGER ( 0..65535 )
--         ACCESS  read-only
--         STATUS  deprecated
--         DESCRIPTION
--                 "THIS ITEM IS NOT IMPLEMENTED!"
--         ::= { ipx 5 }

-- ipxSapReceiveAdvertisementFlag OBJECT-TYPE
--         SYNTAX  INTEGER { no(1), yes(2) }
--         ACCESS  read-only
--         STATUS  deprecated
--         DESCRIPTION
--                 "THIS ITEM IS NOT IMPLEMENTED!"
--         ::= { ipx 6 }

-- ipxSapSendInterval OBJECT-TYPE
--         SYNTAX  INTEGER ( 0..65535 )
--         ACCESS  read-only
--         STATUS  deprecated
--         DESCRIPTION
--                 "THIS ITEM IS NOT IMPLEMENTED!"
--         ::= { ipx 7 }

ipxNetbios OBJECT-TYPE
        SYNTAX  INTEGER { no(1), yes(2) }
        ACCESS  read-write
        STATUS  mandatory
        DESCRIPTION
                "Default value on nX: no (1)

                This object reflects the state of NetBIOS (IPX Type20)
		frame forwarding for the NX. NetBIOS forwarding is enabled 
		for a specific site only when this object is set to 'yes' and 
                NetBIOS/IPX bit is set in the destDialoutProtoSupport object 
                for the site."
        ::= { ipx 8 }

ipxMultiFrameTable OBJECT-TYPE
      SYNTAX SEQUENCE OF IpxMultiFrameEntry
                                 --%{ return SNMP-SBEMIB-IPXFrameAccess(snmpi); %}
      ACCESS not-accessible
      STATUS mandatory
      DESCRIPTION
              "IPX multifram type support, the table contains fix size of 4 
               entries. They can not be added or deleted."
      ::={ ipx 9 }
     
ipxMultiFrameEntry OBJECT-TYPE 
      SYNTAX  IpxMultiFrameEntry
      ACCESS not-accessible
      STATUS  mandatory
      DESCRIPTION
              "The community information for this community."
             INDEX { ipxMultiFrameType }
      ::= { ipxMultiFrameTable  1 }
     
      IpxMultiFrameEntry ::= SEQUENCE {
          ipxMultiFrameStatus INTEGER,
          ipxMultiFrameType INTEGER,
          ipxMultiFrameSelectFlag INTEGER,
          ipxMultiFrameNetworkAddress OCTET STRING
          }
     
ipxMultiFrameStatus OBJECT-TYPE
      SYNTAX  INTEGER { 
        valid(1),
        create-request(2),
        under-creation(3),
        invalid(4),
        modify(5)      
        }
      ACCESS  read-write
      STATUS  mandatory
      DESCRIPTION
              "Indication of whether or not a valid entry. User can only use 
               Modify"
      ::= { ipxMultiFrameEntry 1 }
     
     
ipxMultiFrameType OBJECT-TYPE
      SYNTAX  INTEGER {
         ieee-8022 (1),
         ieee-8023-raw (2),
         ieee-8022-SNAP (3),
         ethernet-II (4)
         }
      ACCESS  read-only
      STATUS  mandatory
      DESCRIPTION
              "Default value on nX: IEEE 802.2"
      ::= { ipxMultiFrameEntry 2 }
     
ipxMultiFrameSelectFlag OBJECT-TYPE
      SYNTAX  INTEGER { 
       no (1), 
       yes (2) 
       }
      ACCESS  read-write
      STATUS  mandatory
      DESCRIPTION
       "Default value on nX: there must be at least a entry is = yes"
      ::= { ipxMultiFrameEntry 3 }
     
ipxMultiFrameNetworkAddress OBJECT-TYPE
      SYNTAX  OCTET STRING (SIZE ( 4 ) )
      ACCESS  read-write
      STATUS  mandatory
      DESCRIPTION
              "Default value on nX: 0
               If IPX Manual Set Network Address is set to 'yes', 
               this object specifies the IPX Network Address that 
               the nX product will use for packets sent to it.  
               Normally the IPX Node Address is automatically 
               taken from the network."
      ::= { ipxMultiFrameEntry  4 }
     
-- ipxNetAddressAutoLearnFlag OBJECT-TYPE
--       SYNTAX  INTEGER { no(1), yes(2) }
--       ACCESS  read-only
--       STATUS  deprecated
--       DESCRIPTION
--        "THIS ITEM IS NOT IMPLEMENTED!"
--       ::= { ipx 10 }
     
ipxNetAddressAutoLearnStateCounter OBJECT-TYPE
      SYNTAX  INTEGER ( 0..70 )
      ACCESS  read-only
      STATUS  mandatory
      DESCRIPTION
       "Default value on nX: 0
     
       If IPX is configured, and Auto learn is Yes.
       this object determines
       the time (in sec) remaining in the IPX auto learn phase.
       If the value is non-zero, nX auto learn is in progress.
       Workshop will continue to poll this mib item, and 
       ipxMultiFrameTable."
      ::= { ipx 11 }

----------------------------------------------------------------------
--                      sbe.router.snmp  BRANCH 
----------------------------------------------------------------------

-- SNMP Community Names Table
-- This table contains a list of SNMP community names from which 
-- the nX product accepts SNMP messages.  A response to a message 
-- will be sent to the MAC or IP address of the sender.  Rows in the 
-- table are identified by the Community Name.

-- There will be pre-defined community names, such as one for Healthmeter.

snmpCommunityNameTable OBJECT-TYPE
  SYNTAX SEQUENCE OF SnmpCommunityNameEntry
  ACCESS not-accessible
  STATUS mandatory
  DESCRIPTION
   "Community name table"
  ::={ snmp 1 }

snmpCommunityNameEntry OBJECT-TYPE 
  SYNTAX  SnmpCommunityNameEntry
     --%{ return SNMP-SBEMIB-CommunityAccess(snmpi); %}
  ACCESS not-accessible
  STATUS  mandatory
  DESCRIPTION
   "The community information for this community."
  INDEX { snmpCommunityName }
  ::= { snmpCommunityNameTable  1 }

  SnmpCommunityNameEntry ::= SEQUENCE {
    snmpCommunityNameStatus  INTEGER,
    snmpCommunityName        DisplayString,
    snmpCommunityPermission  INTEGER
    }

snmpCommunityNameStatus OBJECT-TYPE
        SYNTAX  INTEGER { 
       valid(1),
       create-request(2),
       under-creation(3),
       invalid(4),
       modify(5)      
      }
        ACCESS  read-write
        STATUS  mandatory
        DESCRIPTION
                "Indication of whether or not a valid entry."
        ::= { snmpCommunityNameEntry 1 }


snmpCommunityName OBJECT-TYPE
        SYNTAX  DisplayString ( SIZE ( 0..31 )  )
        ACCESS  read-only
        STATUS  mandatory
        DESCRIPTION
                "Default value on nX: none
                On nX: both ram and flash, field trial 1

                This item defines a community name to be 
                recognized by the nX Product.  For convenience 
                of the user, Workshop will restrict community 
                strings to be ASCII characters."
        ::= { snmpCommunityNameEntry 2 }

snmpCommunityPermission OBJECT-TYPE
        SYNTAX  INTEGER { 
        readonly(1),  -- Indicates both SNMP GET and SNMP GETNEXT operations
                      -- can be performed
        readwrite(2), -- Indicates permission to perform all SNMP operations 
                      -- (GET, GETNEXT and SET) on all mib variables
        lanuser(3)    -- Allows GET and GETNEXT on all mib variables and SET
                      -- on syControlVariableStringOne and syControlOperation
        }
        ACCESS  read-write
        STATUS  mandatory
        DESCRIPTION
                "Default value on nX: Three rows are defined initially, one
                                      with each of the above permissions.
                On nX: both ram and flash

                This item defines the permission level for its associated
                Community Name."
        ::= { snmpCommunityNameEntry 3 }

-- SNMP MAC Server Table
-- This table contains one row for each MAC address which is to 
-- receive all SNMP traps generated by this nX product.  Currently, 
-- the nX product only accepts up to 3 MAC addresses.

snmpMacServerTable OBJECT-TYPE
  SYNTAX SEQUENCE OF SnmpMacServerEntry
  ACCESS not-accessible
  STATUS mandatory
  DESCRIPTION
   "SNMP MAC server table - one copy" 
  ::= { snmp 2 }

snmpMacServerEntry OBJECT-TYPE
  SYNTAX  SnmpMacServerEntry
     --%{ return SNMP-SBEMIB-MacServerAccess(snmpi); %}
  ACCESS not-accessible
  STATUS mandatory
  DESCRIPTION
   "The SNMP MAC server information for one server."
  INDEX { snmpMacServerAddress }
  ::= { snmpMacServerTable  1 }

  SnmpMacServerEntry ::= SEQUENCE {
    snmpMacServerStatus INTEGER,
    snmpMacServerAddress OCTET STRING
    }

snmpMacServerStatus OBJECT-TYPE
       SYNTAX  INTEGER { 
       valid(1),
       create-request(2),
       under-creation(3),
       invalid(4),
       modify(5)      
      }
        ACCESS  read-write
        STATUS  mandatory
        DESCRIPTION
                "Indication of whether or not a valid entry."
        ::= { snmpMacServerEntry 1 }


snmpMacServerAddress OBJECT-TYPE
        SYNTAX  OCTET STRING (SIZE ( 1..6 ))
        ACCESS  read-only
        STATUS  mandatory
        DESCRIPTION
                "Default value on nX: none
                On nX: both ram and flash, field trial 1

                This item contains the MAC address of the server 
                to which SNMP traps are to be sent.  A value of 
                zero indicates no server."
        ::= { snmpMacServerEntry 2 }

-- SNMP IP Server Table
-- This table contains one row for each IP address which is to 
-- receive all SNMP traps generated by this nX product.  Currently, 
-- the nX product only accepts up to 3 IP addresses.

snmpIpServerTable OBJECT-TYPE
  SYNTAX  SEQUENCE OF SnmpIpServerEntry
  ACCESS  not-accessible
  STATUS  mandatory
  DESCRIPTION
   "SNMP IP server table - one copy"
  ::= { snmp 3 }   

snmpIpServerEntry OBJECT-TYPE
  SYNTAX  SnmpIpServerEntry
     --%{ return SNMP-SBEMIB-IpServerAccess(snmpi); %}
  ACCESS not-accessible
  STATUS mandatory
  DESCRIPTION
   "The SNMP IP server information for one server."
  INDEX { snmpIpServerAddress }
  ::= { snmpIpServerTable 1 }
  
  SnmpIpServerEntry ::= SEQUENCE {
    snmpIpServerStatus INTEGER,
    snmpIpServerAddress IpAddress
    }

snmpIpServerStatus OBJECT-TYPE
        SYNTAX  INTEGER {
       valid(1),
       create-request(2),
       under-creation(3),
       invalid(4),
       modify(5)      
      }
        ACCESS  read-write
        STATUS  mandatory
        DESCRIPTION
                "Indication of whether or not a valid entry."
        ::= { snmpIpServerEntry 1 }

snmpIpServerAddress OBJECT-TYPE
        SYNTAX  IpAddress
        ACCESS  read-only
        STATUS  mandatory
        DESCRIPTION
                "Default value on nX: 0
                On nX: both ram and flash, field trial 1

                This item contains the IP address of the server 
                to which SNMP traps are to be sent.  A value of 
                zero indicates no server."
        ::= { snmpIpServerEntry 2 }

snmpCommunityNameMaxEntry OBJECT-TYPE
  SYNTAX  INTEGER
     --%{ return SNMP-SBEMIB-CommunityNameMaxEntryAccess(snmpi); %}
  ACCESS read-only
  STATUS  mandatory
  DESCRIPTION
   "Max # of entries allowed in snmpCommunityName table"
  ::= { snmp 4 }

----------------------------------------------------------------------
--                      sbe.router.destination  BRANCH 
----------------------------------------------------------------------

-- Destination Table
-- This table describes all of the destinations that can be reached 
-- via dialout.  There is one row for each destination.  Each row 
-- is identified by the Destination Name.  (In a future release 
-- there will also be destination groups.)

destTable OBJECT-TYPE
  SYNTAX  SEQUENCE OF DestEntry
     		--%{ return SNMP-SBEMIB-DestAccess(snmpi); %}
  ACCESS not-accessible
  STATUS  mandatory
  DESCRIPTION
   "Destination table - one copy"
  ::= { destination 1 }

destEntry  OBJECT-TYPE
  SYNTAX  DestEntry
  ACCESS  not-accessible
  STATUS  mandatory
  DESCRIPTION
   "The information for one destination."
  INDEX { destName }
  ::= { destTable 1 }

  DestEntry ::= SEQUENCE {
    destStatus INTEGER,
    destName   DisplayString,
    destType   INTEGER,
    destDialoutPhoneNumber DisplayString,
    destDialoutProtoSupport INTEGER,
    destDialoutIpxSupport INTEGER,
    destDialoutModemSpeed INTEGER,
    destPppMtuMru INTEGER,
    destDialoutHandshake INTEGER,
    destDialoutUserName DisplayString,
    destDialoutPassword DisplayString,
    destPorts INTEGER,
    destMaximumDialoutConnectTime INTEGER,
    destDialoutStatus INTEGER,
    destDialoutSchedule OCTET STRING,
    destHolidaySchedule INTEGER,
    destLinkLayerNRZFlag INTEGER,
    destLinkLayerProtocolType INTEGER,
    destLinkDialupFlag INTEGER,
    destPortType INTEGER,
    destLinkLayerType INTEGER,
    destDialoutStatusData OCTET STRING,
    destDialoutScheduleFlag INTEGER,
		destDialinUserName	DisplayString,
		destDialinPassword  DisplayString,
		destMaximumDialinConnectTime INTEGER,
	  destTSDFlag INTEGER,
	  destTSDInactivityTime INTEGER,
		destTSDMaxDownTime INTEGER,
		destTSDPortGroup INTEGER,
	  destManualDialCallback 	INTEGER,
    destAllowDynamicIPAddr INTEGER,
    destISDNChannels INTEGER,
    destDialoutPhoneNumber2 DisplayString,
    destTSDExpectCallback INTEGER
    }


destStatus OBJECT-TYPE
        SYNTAX  INTEGER { 
       valid(1),
       create-request(2),
       under-creation(3),
       invalid(4),
       modify(5)      
      }
        ACCESS  read-write
        STATUS  mandatory
        DESCRIPTION
                "Indication of whether or not a valid entry."
        ::= { destEntry 1 }


destName OBJECT-TYPE
        SYNTAX  DisplayString ( SIZE ( 0..31 )  )
        ACCESS  read-only
        STATUS  mandatory
        DESCRIPTION
                "Default value on nX: none
                On nX: both ram and flash, field trial 1

                This item contains a user supplied identification 
                for this destination.  This should be something 
                meaningful to the user, such as 'Home Office'.  
                In a later release, User Table entries will 
                include a destination field for dialout."
        ::= { destEntry 2 }

destType OBJECT-TYPE
        SYNTAX  INTEGER { lan-to-lan(1) }
        ACCESS  read-write
        STATUS  mandatory
        DESCRIPTION
                "Default value on nX: Lan-to-Lan
                On nX: (not necessary in first release) both 
                ram and flash, field trial 2

                This item indicates whether the destination is 
                a LAN or remote access.  A Lan destination 
                indicates Lan-to-Lan traffic over the link.  
                All destinations are PPP serial communication.  
                There will be other types, e.g. Remote-access, 
                in later versions of the LX."
        ::= { destEntry 3 }

destDialoutPhoneNumber OBJECT-TYPE
        SYNTAX  DisplayString ( SIZE( 0..31 ) )
        ACCESS  read-write
        STATUS  mandatory
        DESCRIPTION
                "Default value on nX: empty
                On nX: both ram and flash, field trial 1

                This item contains the phone number that is to be 
                used to call the destination.  This string 
                contains just the AT command set characters for 
                the phone number.  During dialout, the nX forms 
                the entire dialout string by prefixing this 
                item with the Modem Dial Prefix."
        ::= { destEntry 4 }

destDialoutProtoSupport OBJECT-TYPE
        SYNTAX  INTEGER (1..31)
        ACCESS  read-write
        STATUS  mandatory
        DESCRIPTION
          "Default value on nX: 0
           On nX: both ram and flash,

           This item is a bit encoded value representing various
           protocols to be enabled during the establishment of a WAN
	   connection. The encoded values are:
             IP(1), IPX(2), Bridging(4), NetBIOS/IPX(8), IPBCASTFWD(16).
           Any combination of IP, IPX and Bridging is valid. NetBIOS/IPX
           is valid only if IPX bit is set. IPBCASTFWD is valid only if IP
	   bit is set. Value zero is invalid" 
        ::= { destEntry 5 }

destDialoutIpxSupport OBJECT-TYPE
        SYNTAX  INTEGER { no(1), yes(2) }
        ACCESS  read-write
        STATUS  mandatory
        DESCRIPTION
        "NOTE: THIS FIELD IS NO LONGER IN USE. The field
         destDialoutProtoSupport is used to encode
         all protocols supported.

                Default value on nX: same as IP Configured Flag
                On nX: both ram and flash

                This item equals 'yes' if the dialout destination 
                supports IPX, and 'no' otherwise.  No IPX traffic 
                will be routed or bridged to this destination if 
                the value is 'no'. The IPX Configured Flag must 
                be 'yes' for this field to be 'yes'."
        ::= { destEntry 6 }

destDialoutModemSpeed OBJECT-TYPE
        SYNTAX  INTEGER { twelvehundred(1200),
        twentyfourhundred(2400),
        fortyeighthundred(4800), 
        ninetysixhundred(9600), 
        nineteentwelve(19200),
        thirtyeigthfour(38400),
        fiftysevensix(57600), 
        onefifteentwo(115200) }
        ACCESS  read-write
        STATUS  mandatory
        DESCRIPTION
                "Default value on nX: 'unspecified'
                On nX: both ram and flash,

                This item allows the user to override the Modem 
                Speed set up for the port for dialout calls to 
                this destination.  If the value of this item 
                is 'unspecified', then the Modem Speed for the 
                port is used.  The user might specify this to 
                shorten the time it takes for the modems to 
                negotiate speed."
        ::= { destEntry 7 }

destPppMtuMru OBJECT-TYPE
        SYNTAX  INTEGER (  64..1500 )
        ACCESS  read-write
        STATUS  mandatory
        DESCRIPTION
                "Default value on nX: 1500
                On nX: both ram and flash, field trial 2

                This field can be used to override the global 
                MTR/MTU.  The user should set this field if the 
                destination or the Wan link has special 
                requirements.  Any value less than the minimum 
                value allowed for a port's MTR/MRU will be 
                interpreted as an unspecified value and the 
                MTR/MRU value for the nX will be used.  
                (Perhaps the user could be asked for line 
                quality and the nX or Workshop automatically 
                determine MTU/MRU.)"
        ::= { destEntry 8 }

destDialoutHandshake OBJECT-TYPE
        SYNTAX  INTEGER { none(1), pap(2), chap(3) }
        ACCESS  read-write
        STATUS  mandatory
        DESCRIPTION
                "Default value on nX: 'none'
                On nX: both ram and flash, 'none' and 'PAP' 
                for field trial 1

                This field identifies the type of authorization 
                negotiation that is to be performed during dialout 
                to this destination.  (On dialin, the handshake 
                is determined by the caller.)"
        ::= { destEntry 9 }

destDialoutUserName OBJECT-TYPE
        SYNTAX  DisplayString ( SIZE ( 0..31 ))
        ACCESS  read-write
        STATUS  mandatory
        DESCRIPTION
                "Default value on nX: 0
                On nX: both ram and flash, field trial 1

                This value identifies a User Name for PAP or CHAP 
    dialout to this destination. 
                This entry is only valid if Destination 
                Handshake if a value other than 'none'."
        ::= { destEntry 10 }

destDialoutPassword OBJECT-TYPE
        SYNTAX  DisplayString ( SIZE ( 0..31 ))
        ACCESS  read-write 
        STATUS  mandatory
        DESCRIPTION
                "Default value on nX: 0
                On nX: both ram and flash, field trial 1

    This value identifies the user password for PAP or 
    CHAP dialout to this destination.
                This entry is only valid if Destination 
                Handshake if a value other than 'none'."
  ::= { destEntry 11 }

destPorts OBJECT-TYPE
  SYNTAX  INTEGER (1..18)
  ACCESS read-write
  STATUS mandatory
  DESCRIPTION
    "Default Value on nX:  0.

     This field indicates the port number associated with this site, if the
     link characteristic wanLinkDialupFlag is set to dedicated(2)."
  ::= { destEntry 12 }

destMaximumDialoutConnectTime OBJECT-TYPE
        SYNTAX  INTEGER ( 0..65535 )
        ACCESS  read-write
        STATUS  mandatory
        DESCRIPTION
                "Default value on nX:  0
                On nX: both ram and flash, field trial 1

                This object contains, in minutes, the maximum 
                time to leave this connection active for dialout.  
                After the time elapses, the nX will automatically 
                hangup the connection, assuming the user has not 
                already manually terminated the connection.  
                A value of zero means there is no time limit.  
                For any given call, this time by be shortened 
                because of a value in the User Maximum Dialout 
                Connect Time object.  (For dialin, the maximum 
                connect time comes from the User Table.)  
                (If we require a default user name for the 
                destination, we could take the maximum dialout 
                time from the User Table.)"
        ::= { destEntry 13 }

destDialoutStatus OBJECT-TYPE
        SYNTAX  INTEGER { none(1),
                          dialing(2),
                          connected(3),
                          connection-failed(4),
                          disconnected(5)
                        } 
        ACCESS  read-only
        STATUS  mandatory
        DESCRIPTION
                "Default value on nX: none

                This item is used by the Workshop to determine 
                the status of a dialout for this destination."
        ::= { destEntry 14 }

destDialoutSchedule OBJECT-TYPE
        SYNTAX  OCTET STRING ( SIZE(96) )
        ACCESS  read-write
        STATUS  mandatory
        DESCRIPTION
                "Default value on nX: 0
                On nX: both ram and flash, field trial 2

                This is a one-week bit map, with one bit for 
                every 15 minutes.  The string is organized a 
                8 groups of 12 bytes (96 bits), one group for 
                each day of the week plus the 8th for all 
                holidays, starting with Sunday, Monday, Tuesday, 
                Wednesday, Thursday, Friday, Saturday, Holiday. 
                The first bit in each 
                group is for midnight (12:00 AM) to 12:15 AM, 
                the next for 12:15 AM to 12:30 AM, etc.  
                If the bit for a time interval equals 1, a 
                dialout connection to this destination is to 
                be active during this time period.  If the bit 
                for a time interval equals 0, there is to be no 
                dialout connection to this destination during 
                this time period.

                This encoding of dialout times means dialout must 
                be specified in 15 minutes intervals.

                (Depending on the user interface, Workshop may be 
                able to reconstruct the user's input from this
                bit string.  If it can't, it will be necessary 
                to define an object that contains encoding for
                 Workshop -- or change this object so it can be 
                 used by both the nX and Workshop.)

                This field does not apply to leased lines."
        ::= { destEntry 15 }


destHolidaySchedule OBJECT-TYPE
       SYNTAX  INTEGER { normal(1), 
                         nodialout(2), 
                         sunday(3),
                         monday(4), 
                         tuesday(5), 
                         wednesday(6), 
                         thursday(7), 
                         friday(8), 
                         saturday(9) }
         ACCESS  read-write
         STATUS  mandatory
         DESCRIPTION
                 "Default value on nX: 0
                  NO LONGER USED.

                This item specifies which day's dialout schedule 
                is to be used for holidays.  For example, this 
                allows a person to specify that on holidays to 
                use Sunday's dialout schedule.  'Normal' indicates 
                that the day's standard dialout schedule is to be 
                used. 'Nodialout' indicates that no dialout at all 
                is to occur on holidays."

         ::= { destEntry 16 }

destLinkLayerNRZFlag OBJECT-TYPE
        SYNTAX  INTEGER { nrz(1), nrzi(2)  }
        ACCESS  read-write
        STATUS  mandatory
        DESCRIPTION
                "Default value on nX: nrz
                On nX: both ram and flash, field trial 1 
    (may be encoded into Link Layer Type)

                If appropriate for the Link Line Type, this flag 
                identifies whether the line is nrz or nrzi.  
                (See wan NRZ Flag.)"
        ::= { destEntry 17 }

destLinkLayerProtocolType OBJECT-TYPE
        SYNTAX  INTEGER { 
        none(1),
        ppp(2),
        isdn(3),
        x25(4),
        framerelaydte(5),
        framerelaydce(6)
      } 
        ACCESS  read-write
        STATUS  mandatory
        DESCRIPTION
                "Default value on nX: ppp 
                On nX: both ram and flash,

  This flag identifies whether the Link Line Type is ppp.
  Other options are not supported at this time."
        ::= { destEntry 18 }

destLinkDialupFlag OBJECT-TYPE
        SYNTAX  INTEGER { dialup(1), dedicated(2), dtr-dial(3), isdn-dialup(4) }
        ACCESS  read-write
        STATUS  mandatory
        DESCRIPTION
                "Default value on nX: dialup
                On nX: both ram and flash, field trial 1 (may be 
                encoded into Link Layer Type)

                If appropriate for the Link Line Type, this flag 
                identifies whether the line is dialup (switched), 
                dedicated, or DTR dial."
        ::= { destEntry 19 }

destPortType OBJECT-TYPE
        SYNTAX  INTEGER { pcmcia(1), rs232(2), v35(4) }
        ACCESS  read-write
        STATUS  mandatory
        DESCRIPTION
                "Default value on nX: determined by hardware
                On nX: from 'ram' (actually hardware), field trial 2

                This value indicates whether the dest port is PCMCIA, 
                or a D-shell connection - either RS232 or V.35."
        ::= { destEntry 20 }

destLinkLayerType OBJECT-TYPE
        SYNTAX  INTEGER { async(1), sync(2), autosync(3) }
        ACCESS  read-write
        STATUS  mandatory
        DESCRIPTION
                "Default value on nX: async
                On nX: both ram and flash, field trial 1

                This object identifies the type of communication link 
                that is used by this destination.  Some data link types 
                require further qualification."
        ::= { destEntry 21 }

destDialoutStatusData OBJECT-TYPE
        SYNTAX  OCTET STRING ( SIZE(1..64) )
        ACCESS  read-only
        STATUS  mandatory
        DESCRIPTION
            "It has the same format as the event messages:
            Message # : 2 bytes
            Date/Time stamping: 4 bytes (integer, msb first)
            Length: n bytes defining the size of the parameter list
            that folllows ( 0 is allowed)
            Message parameters: n bytes, associated with the message #. "
        ::= { destEntry 22 } 

destDialoutScheduleFlag OBJECT-TYPE
        SYNTAX INTEGER { disable(1), enable(2) }
        ACCESS read-write
        STATUS mandatory
        DESCRIPTION
            "Default value on nX: disable "
        ::= { destEntry 23 }

destDialinUserName OBJECT-TYPE
      SYNTAX DisplayString ( SIZE ( 0..31 ))
      ACCESS read-write
      STATUS mandatory
      DESCRIPTION
       "
       This value identifies a User Name for PAP or CHAP 
       dialin to this destination. "
      ::= { destEntry 24 }
     
destDialinPassword OBJECT-TYPE
      SYNTAX DisplayString ( SIZE ( 0..31 ))
      ACCESS read-write 
      STATUS mandatory
      DESCRIPTION
       "
       This value identifies the user password for PAP or 
       CHAP dialin to this destination."
      ::= { destEntry 25 }

destMaximumDialinConnectTime OBJECT-TYPE
      SYNTAX INTEGER ( 0..65535 )
      ACCESS read-write
      STATUS mandatory
      DESCRIPTION
       "
       This object contains, in minutes, the maximum 
       time to leave this connection active for dialin connections.
       After the time elapses, the nX will automatically 
       hangup the connection, assuming the user has not 
       already manually terminated the connection.
       A value of zero means there is no time limit."
      ::= { destEntry 26 }
     
destTSDFlag OBJECT-TYPE
      SYNTAX INTEGER { tsd (1), non-tsd(2) }
      ACCESS read-write
      STATUS mandatory
      DESCRIPTION
       "
       Default value on nX: non-tsd
     
       This entry defines this Destination (Site) to be either a 
        TSD or non-TSD site. If TSD site, then
        destTSDInactivityTime, destTSDMaxTime, and
        destPortGroup are meaningful. "
      ::= { destEntry 27 }

destTSDInactivityTime OBJECT-TYPE
      SYNTAX INTEGER ( 0..65535 )
      ACCESS read-write
      STATUS mandatory
      DESCRIPTION
       "
       This object contains, in minutes, the maximum 
       time.
       A value of zero means there is no time limit."
      ::= { destEntry 28}
     
destTSDMaxDownTime OBJECT-TYPE
      SYNTAX INTEGER ( 0..65535 )
      ACCESS read-write
      STATUS mandatory
      DESCRIPTION
       " A value of zero means there is no time limit."
      ::= { destEntry 29 }
     
destTSDPortGroup OBJECT-TYPE
      SYNTAX  INTEGER ( 1..128 )
      ACCESS  read-write
      STATUS  mandatory
      DESCRIPTION
       "Default value on nX:  0. 
      
       This field is used to identify the Wan port  # to which 
       this TSD entry is assigned. port group #128 is used as hunt group in
       TSD for reserving wan link capacity."
       ::= { destEntry 30 }

destManualDialCallback OBJECT-TYPE
	SYNTAX  INTEGER { no(1), yes(2) }
  ACCESS  read-write
  STATUS  mandatory
  DESCRIPTION
   " This item indicates whether callback is enabled in Manual Dial mode."
        ::= { destEntry 31 }

destAllowDynamicIPAddr OBJECT-TYPE
        SYNTAX  INTEGER { no(1), yes(2) }
        ACCESS  read-write
        STATUS  mandatory
        DESCRIPTION
                "this entry indicates whether the ip address provided by the
                 remote router (through IPCP negotiation), for the use on the
                 local WAN port, is permitted."
        ::= { destEntry 32 }

destISDNChannels    OBJECT-TYPE
        SYNTAX  INTEGER { oneb(1),  twob(2) }
        ACCESS  read-write
        STATUS  mandatory
        DESCRIPTION
                "This entry indicates the number B channels supported 
                by the ISDN card (configured from the port page)."
        ::= { destEntry 33 }

destDialoutPhoneNumber2 OBJECT-TYPE
        SYNTAX  DisplayString ( SIZE( 0..31 ) )
        ACCESS  read-write
        STATUS  mandatory
        DESCRIPTION
                "Default value on nX: empty
 
                This item contains the second phone number that is to be
                used to call the destination using the second ISDN B channel.  
                This string contains just the AT command set characters for
                the phone number.  During dialout, the nX forms
                the entire dialout string by prefixing this
                item with the Modem Dial Prefix."
        ::= { destEntry 34 }

destTSDExpectCallback OBJECT-TYPE
        SYNTAX  INTEGER {no(1), yes(2)}
        ACCESS  read-write
        STATUS  mandatory
        DESCRIPTION
           "Default value on nX: no

           Determines whether to expect a callback.  If callback is
           expected, re-dial should delay as specified by
           syReverseCallbackDelay"
        ::= { destEntry 35 }


destMaxEntry OBJECT-TYPE 
  SYNTAX  INTEGER
     		--%{ return SNMP-SBEMIB-DestMaxEntryAccess(snmpi); %}
  ACCESS read-only
  STATUS  mandatory
  DESCRIPTION
   "Max # of entries allowed in Destination table"
  ::= { destination 2 }

-- Chat Script Table
-- This table contains the chat script related fields for each destination
-- (site). There is one row for each destination. Each row is identified by 
-- the Destination (Site) Name. 
 
destScriptTable OBJECT-TYPE
        SYNTAX  SEQUENCE OF DestScriptEntry
     		--%{ return SNMP-ScriptDataAccess(snmpi); %}
        ACCESS not-accessible
        STATUS  mandatory
        DESCRIPTION
                "Destination script table"
        ::= { destination 3 }
 
destScriptEntry  OBJECT-TYPE
        SYNTAX  DestScriptEntry
        ACCESS  not-accessible
        STATUS  mandatory
        DESCRIPTION
                "Chat script information for a destination"
        INDEX { destinationName }
        ::= { destScriptTable 2 }
 
        DestScriptEntry ::= 
                SEQUENCE {
                        destScriptEntryStatus INTEGER,
                        destinationName   DisplayString,
                        destScriptUseFlag INTEGER,
                        destScriptTimeout INTEGER,
                        destScriptName DisplayString,
                        destScript DisplayString,
                        destScriptStartupCmd DisplayString
                }

destScriptEntryStatus OBJECT-TYPE
        SYNTAX  INTEGER { 
                valid(1),
                create-request(2),
                under-creation(3),
                invalid(4),
                modify(5)      
        }
        ACCESS  read-write
        STATUS  mandatory
        DESCRIPTION
                "Indication of whether or not a valid entry."
        ::= { destScriptEntry 1 }


destinationName OBJECT-TYPE
        SYNTAX  DisplayString ( SIZE ( 0..31 )  )
        ACCESS  read-only
        STATUS  mandatory
        DESCRIPTION
                "Same as destName in the Destination Table."
        ::= { destScriptEntry 2 }

destScriptUseFlag OBJECT-TYPE
        SYNTAX INTEGER { disable(1), enable(2) }
        ACCESS read-write
        STATUS mandatory 
        DESCRIPTION    
             "This entry indicates whether the script associated with this
              site should be executed or not."
        ::= { destScriptEntry 3 }
 
destScriptTimeout OBJECT-TYPE
        SYNTAX  INTEGER ( 0..65535 )
        ACCESS  read-write
        STATUS  mandatory
        DESCRIPTION
                "This field specifies the total time limit allocated for the
                 execution of the script to completion"
        ::= { destScriptEntry 4 }
 
destScriptName OBJECT-TYPE
        SYNTAX  DisplayString (SIZE(0..31))
        ACCESS  read-write
        STATUS  mandatory
        DESCRIPTION
                "This entry contains the the name of the script."
        ::= { destScriptEntry 5 }
 
destScript OBJECT-TYPE
        SYNTAX  DisplayString (SIZE(0..127))
        ACCESS  read-write
        STATUS  mandatory
        DESCRIPTION
                "This entry contains the chat script identified by the
                 entry destScriptName."
        ::= { destScriptEntry 6 }

destScriptStartupCmd OBJECT-TYPE
        SYNTAX  DisplayString (SIZE(0..31))
        ACCESS  read-write
        STATUS  mandatory
        DESCRIPTION
                "This entry contains the command used to indicate the service
                 type to the ISP, if required."
        ::= { destScriptEntry 7 }


----------------------------------------------------------------------
--                      sbe.router.event  BRANCH
----------------------------------------------------------------------
 
-- Event Log
-- This table is used to define event entry in predefined packed
-- format
 
eventTable OBJECT-TYPE
        SYNTAX SEQUENCE OF EventEntry
        ACCESS  not-accessible
        STATUS  mandatory
        DESCRIPTION
            "Event table - one copy "
        ::= { event 1 }
 
eventEntry OBJECT-TYPE
        SYNTAX  EventEntry
        ACCESS  not-accessible
        STATUS  mandatory
        DESCRIPTION
            "The event information of one event data."
        INDEX {eventGroupIndex }   
        ::= { eventTable 1}       
 
EventEntry ::= SEQUENCE {
        eventGroupIndex 
            INTEGER,   
        eventData    
            OCTET STRING 
        }
 
eventGroupIndex OBJECT-TYPE
        SYNTAX INTEGER (1..65535)
        ACCESS read-only
        STATUS mandatory 
        DESCRIPTION
            "index into the event log table entry. It is a reference point
            where the SNMP manager will issue the GET NEXT request to get
            the next group of events. nX needs to set this value to match
            the last SEQUENCE # that is returned in the eventData."
        ::= { eventEntry 1 }
 
eventData OBJECT-TYPE
        SYNTAX OCTET STRING (SIZE (1..1024))
        ACCESS read-only
        STATUS mandatory 
        DESCRIPTION
            "A group of event log entries.
            Each entry will be one event with the following format:
            Sequence #: 2 bytes
            Message # : 2 bytes
            Date/Time stamping: 4 bytes (integer, msb first)
            Length: n bytes defining the size of the parameter list
            that follows ( 0 is allowed)
            Message parameters: n bytes, associated with the message #. "
        ::= { eventEntry 2 } 

----------------------------------------------------------------------
--                      sbe.discovery  BRANCH 
----------------------------------------------------------------------

discNodeName OBJECT-TYPE
        SYNTAX  DisplayString ( SIZE (1..19) )
        ACCESS  read-only
        STATUS  mandatory
        DESCRIPTION
    "The Node Name consists of the hardware type and MAC address as
          follows:
              SoHo-001122334455   for SoHo,
              Central001122334455 for Central
              Torte-001122334455  for Torte (not available)
              Rout-001122334455   for ROUTEMAN (1/2 meg version)
              RoutXL-001122334455 for ROUTEMANXL  (1 meg version).  "
        ::= { discovery 1 }

discModel OBJECT-TYPE
        SYNTAX  INTEGER {
            soho  (256),
            central (257),
            torte   (258),
            routeman (259),
            routemanxl (260)
        }
        ACCESS  read-only
        STATUS  mandatory
        DESCRIPTION
    "The Model contains a numeric identifier for the hardware
            model, as follows:
                   256 - SoHo,
                   257 - Central,
                   258 - Torte (not available),
                   259 - ROUTEMAN,
                   260 - ROUTEMANXL (1 meg version). "
        ::= { discovery 2 }

discProto OBJECT-TYPE
        SYNTAX  INTEGER { mac(1), ip(2) }
        ACCESS  read-only
        STATUS  mandatory
        DESCRIPTION
    "The Discover Protocol is the protocol over which the
            last Get request was received from. "
        ::= { discovery 3 }


----------------------------------------------------------------------
--                      sbe.file-managment  BRANCH 
----------------------------------------------------------------------

syFMOperation OBJECT-TYPE
  SYNTAX  INTEGER {
    other       (1),
    beginCopy   (2),
    copyDone    (3),
    deleteFile  (4),
    renameFile  (5),
    listDir     (6),
    checkSum    (7),
    abortCopy   (8),
    getFileInfo (9)
  }
  ACCESS  read-write
  STATUS  mandatory
  DESCRIPTION
    "This object is used to initiate a file management operation.
     Operations are as described below.
     If this object is read, other(1) will be returned."
  ::= { fileMgmt 1 }

syFMTimeStamp OBJECT-TYPE
  SYNTAX  TimeTicks
  ACCESS  read-only
  STATUS  mandatory
  DESCRIPTION
    "This specifies the value of sysUpTime when
    the most recent file management operation was 
    initiated."
  ::= { fileMgmt 2 }

syFMError OBJECT-TYPE
  SYNTAX  INTEGER {
    none          (1), -- no operations since initialization
    successful    (2), -- the most recent operation was 
        -- successful
    inProgress    (3), -- another operation was already in 
        -- progress
    noResponse    (4), -- no response from the server
    noFile        (5),  -- the file or dir. could not be found
    noSpace       (6), -- no space on destination system
    noPermission  (7), -- community string violation
    timeout       (8), -- timeout during transfer
    badChecksum   (9), -- invalid file checksum computed
    badOperation  (10), -- invalid file operation
    aborted       (11), -- operation aborted by user
    other         (12)  -- an error not listed here
  }
  ACCESS  read-only
  STATUS  mandatory
  DESCRIPTION
      "This object identifies the results of the
      most recent attempt at a file operation.  If no
      file operations have been attempted since the
      system was initialized, this object will have the
      value none(1)."

  ::= { fileMgmt 3 }

syFileTransfer OBJECT IDENTIFIER ::= { fileMgmt 4 }
    --%{ return SNMP-SBEMIB-FileTransferGroup(snmpi); %}

syFileInfo     OBJECT IDENTIFIER ::= { fileMgmt 5 }
    --%{ return SNMP-SBEMIB-FileInfoGroup(snmpi); %}

syFileInfoVersion OBJECT-TYPE
        SYNTAX OCTET STRING (SIZE(128))
        ACCESS  read-only
        STATUS  mandatory
        DESCRIPTION
            "The version string from a module header.  
             Example, 
             $Release: 2.0.4a $File: lxkernel.gz $Type: kernelFile
             $DateTime: 07/09/96 19:11 $ProductType: SoHo $Lic: (C)1996 SBE,Inc

    	$Release: is a three part number X.Y.Z, e.g. 2.0.4a
    	$File: is up to 8.3 character file name, e.g. lxkernel.gz
    	$Type: is kernelFile or moduleFile
    	$DateTime: is Month/DayNumber/Year TimeOfDay
    	$ProductType: is the hardware, e.g. SoHo, Central, Routeman, RoutXL
   	$Lic: is (C) Year(s) SBE,Inc
  
    	Sound files and internal configuration files have null 
	    syFileInfoVersion strings."
		::= { syFileInfo 1}

syFileInfoChecksum OBJECT-TYPE
        SYNTAX OCTET STRING (SIZE(4))
        ACCESS  read-only
        STATUS  mandatory
        DESCRIPTION
                "This MIB entry is used to retrieve the Information
                related to a file on the nX File System. The File
                information contains version string, checksum and
                length of the file. Information in this field is
                mapped in to the file information structure by the
                nX and Workshop."
        ::= { syFileInfo 2}
 
syFileInfoLength OBJECT-TYPE
        SYNTAX OCTET STRING (SIZE(4))
        ACCESS  read-only
        STATUS  mandatory
        DESCRIPTION
                "This MIB entry is used to retrieve the Information
                related to a file on the nX File System. The File
                information contains version string, checksum and
                length of the file. Information in this field is
                mapped in to the file information structure by the
                nX and Workshop."
        ::= { syFileInfo 3}


syDirTable     OBJECT-TYPE
  SYNTAX  SEQUENCE OF SyDirEntry
    		--%{ return SNMP-SBEMIB-DirTable(snmpi); %}
        ACCESS not-accessible
        STATUS mandatory
        DESCRIPTION
            "The directory entry of one file."
        ::= { fileMgmt 6 }
 
syDirEntry OBJECT-TYPE
    SYNTAX  SyDirEntry
    ACCESS not-accessible
    STATUS mandatory
DESCRIPTION ""
    INDEX { syDirName }
        ::= { syDirTable 1}

    SyDirEntry ::= SEQUENCE {
        syDirStatus
            INTEGER,
        syDirName
            OCTET STRING (SIZE(1..13)),
        syDirCompressSize
            INTEGER,
        syDirVersion
            OCTET STRING (SIZE(1..128)),
        syDirUncompressSize
            INTEGER
        }
 
syDirStatus OBJECT-TYPE
        SYNTAX INTEGER
        {
       valid(1),
       create-request(2),
       under-creation(3),
       invalid(4),
       modify(5)      
        }
        ACCESS read-only
        STATUS mandatory
DESCRIPTION ""
        ::= { syDirEntry 1 }
 
syDirName OBJECT-TYPE
        SYNTAX OCTET STRING (SIZE(1..13))
        ACCESS read-only
        STATUS mandatory
DESCRIPTION ""
        ::= { syDirEntry 2 }
 
syDirCompressSize OBJECT-TYPE
        SYNTAX INTEGER
        ACCESS read-only
        STATUS mandatory
DESCRIPTION ""
        ::= { syDirEntry 3 }
 
syDirVersion OBJECT-TYPE
        SYNTAX OCTET STRING (SIZE(1..128))
        ACCESS read-only
        STATUS mandatory
DESCRIPTION ""
        ::= { syDirEntry 4 }

syDirUncompressSize OBJECT-TYPE
        SYNTAX INTEGER
        ACCESS read-only
        STATUS mandatory
DESCRIPTION ""
        ::= { syDirEntry 5 }
 

fileName    OBJECT-TYPE
        SYNTAX OCTET STRING (SIZE (1..13))
			--%{ return SNMP-SBEMIB-FileName(snmpi); %}
        ACCESS read-write
        STATUS mandatory
        DESCRIPTION
            "This field contains a null terminated string in the format of
            nnnnnnnn.xxx (DOS format file name). The file name is used
            by the delete file operation, or the get file info operation."
        ::= { fileMgmt 7 }
 
fileNameFrom        OBJECT-TYPE
        SYNTAX OCTET STRING (SIZE (1..13))
			--%{ return SNMP-SBEMIB-FileNameFrom(snmpi); %}
        ACCESS read-write
        STATUS mandatory
        DESCRIPTION
            "This field contains a null terminated string in the format of
            nnnnnnnn.xxx (DOS format file name). The file name is the old
            file name used by the rename file operation."
        ::= { fileMgmt 8 }
 
fileNameTo          OBJECT-TYPE
        SYNTAX OCTET STRING (SIZE (1..13))
			--%{ return SNMP-SBEMIB-FileNameTo(snmpi); %}
        ACCESS read-write
        STATUS mandatory
        DESCRIPTION
            "This field contains a null terminated string in the format of
            nnnnnnnn.xxx (DOS format file name). The file name is the new
            file name used by the rename file operation."
        ::= { fileMgmt 9 }




--
-- File Transfer Sub-Group
--
fileTransferStatus OBJECT-TYPE
  SYNTAX  INTEGER {
    inActive    (1),
    inProgress  (2),
    waitingCopy (3)
  }
  ACCESS  read-write
  STATUS  mandatory
  DESCRIPTION
    "This identifies the current status
    of the file Transfer operation.
    If there is a transfer in progress, this object
    will have the value inProgress(2).  Otherwise
    inactive(1) will be returned." 
 
  ::= { syFileTransfer 1 }
 
fileTransferStartTime OBJECT-TYPE
  SYNTAX  TimeTicks
  ACCESS  read-only
  STATUS  mandatory
  DESCRIPTION
    "This specifies the value of sysUpTime when
    the most recent file Transfer operation was 
    initiated."

  ::= { syFileTransfer 2 }

fileTransferFileLength OBJECT-TYPE
  SYNTAX OCTET STRING (SIZE (4))
--  SYNTAX  INTEGER
  ACCESS  read-write
  STATUS  mandatory
  DESCRIPTION
    "This specifies the total Data Length of current file
    being transferred, in bytes."

  ::= { syFileTransfer 3 }

fileTransferCheckSum OBJECT-TYPE
  SYNTAX  INTEGER
  ACCESS  read-write
  STATUS  mandatory
  DESCRIPTION
    "This specifies the CCITT cyclic redundancy checksum
     of current file being transffered."

  ::= { syFileTransfer 4 }

fileTransferDirection OBJECT-TYPE
  SYNTAX  INTEGER {
    none             (1),
    copyingFromLX    (2),
    copyingToLXRAM   (3),
    copyingToLXFlash (4)
  }
  ACCESS  read-only
  STATUS  mandatory
  DESCRIPTION
    "This identifies the current direction 
    of the file Transfer operation.
    If there is a transfer in progress, this object
    will have the value copyingFromLX(2), if file is
    being copied to the Box. Otherwise it will have
    copyingToLX(1). If no transfer in progress none will
    be returned." 

  ::= { syFileTransfer 5 }

fileTransferLastRcvTime OBJECT-TYPE
  SYNTAX  TimeTicks
  ACCESS  read-only
  STATUS  mandatory
  DESCRIPTION
    "This specifies the value of sysUpTime when
    the most recent file Object was received.
    This value is used to time out the File Transfer
    operation if no File Object is received within a
    timeout period."
  ::= { syFileTransfer 6 }

fileTransferRemoteAddr OBJECT-TYPE
  SYNTAX  MacAddress
  ACCESS  read-only
  STATUS  mandatory
  DESCRIPTION
    "This object specifies the MAC Address of
    the Remote management stations which initiated the 
    file transfer."

  ::= { syFileTransfer 7 }

fileTransferRemoteFileName OBJECT-TYPE
  SYNTAX  OCTET STRING (SIZE(12))
  ACCESS  read-write
  STATUS  mandatory
  DESCRIPTION
    "This specifies the path and name of a Remote file
     residing on the remote management station.
     sbeFileTransferRemoteAddr 
     For LAN Boot this item MUST be 12 characters in length!"

  ::= { syFileTransfer 8 }

fileTransferLocalFileName OBJECT-TYPE
  SYNTAX  DisplayString (SIZE(0..12))
  ACCESS  read-write
  STATUS  mandatory
  DESCRIPTION
    "This specifies the name of
    Local File being transferred. 
    For the File Transfer TO the remote station this becomes
    the name of the source file. For the FROM operation
    this is the name of the local file where the new file
    will be stored.
    For LAN Boot this item MUST be 12 characters in length!"

  ::= { syFileTransfer 9 }

fileTransferData OBJECT-TYPE
  SYNTAX OCTET STRING (SIZE (532))
  ACCESS read-write
  STATUS mandatory
  DESCRIPTION
    "This field contains the data of the file being
    transfered. The data has a header inside which contains
    information about the file being transfered and the 
    current data block."

  ::= { syFileTransfer 10 }

-- SBE Entreprises specific traps definition
-- Put here as a reference only.  The mpxsmnmpc does not handle
-- TRAP-TYPE (defined in RFC-1215).
 
--    awaitingCopyTrap    TRAP-TYPE
--        ENTERPRISE  sbe
--        VARIABLES   { syBootInfo }
--        DESCRIPTION 
--            "indicates to one or more boot servers that a boot image is
--            requested. The variable is defined in the system group above."
--        ::= 1
 
-- failedCoprocessorTrap
-- TBD

--    sbeEventTrap    TRAP-TYPE
--        ENTERPRISE  sbe
--        VARIABLES   { eventData }
--        DESCRIPTION 
--            " Event Trap message in the following format
--            Message # : 2 bytes
--            Date/Time stamping: 4 bytes (integer, msb first)
--            Length: n bytes defining the size of the parameter list
--            that folllows ( 0 is allowed)
--            Message parameters: n bytes, associated with the message #. "
--        ::= 3

----------------------------------------------------------------------
--                      sbe.modempool  BRANCH 
----------------------------------------------------------------------

modempoolEnabled OBJECT-TYPE
        SYNTAX  INTEGER { disabled(1), enabled(2) }
        ACCESS  read-write
        STATUS  mandatory
        DESCRIPTION
                "Default value on nX: disabled
                On nX: both ram and flash, field trial 1

                If this value is 'enabled', the modem pool is enabled.  
                If this value is 'disabled', if the modem pool is disabled."
        ::= { modempool 1 }

modempoolNodeName OBJECT-TYPE
        SYNTAX  DisplayString ( SIZE (1..8) )
        ACCESS  read-write
        STATUS  mandatory
        DESCRIPTION
    "The nodename contains the modem server name advertised in SAP and
     UDP broadcasts"
        ::= { modempool 2 }


modempoolProtoSupport OBJECT-TYPE
        SYNTAX  INTEGER (1..7)
        ACCESS  read-write
        STATUS  mandatory
        DESCRIPTION
          "Default value on nX: 0
           On nX: both ram and flash,

           This item is a bit encoded value representing various
           protocols to be used for server advertisement. The encoded
           values are:
             IP(1), IPX(2).
           Any combination of these values is valid.
           Zero is invalid" 
        ::= { modempool 3 }

dummyStopperForWorkshopForGetNext OBJECT-TYPE
        SYNTAX INTEGER
    		--%{ return forty-two(snmpi); %}
        ACCESS read-only
        STATUS mandatory
DESCRIPTION ""
        ::= { endOfSBEMib 1 }

END
