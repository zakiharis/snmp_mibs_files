SCC-ENTERPRISE-MIB DEFINITIONS ::= BEGIN

--
--  Definitions of the Enterprise MIB Hierarchy for
--            Storage Computer Corporation MIB Objects
--
--                  Name:    scc-enterprise-mib-v1-0.txt
--                  Version: 1.0
--                  Date:    
--                  Company: Storage Computer Corporation
--                  Mail:    raid7@world.std.com
--  
--  
--  Inquiries about the contents and use of this MIB may be sent to 
--  raid7@world.std.com
--
--  This mib defines the top level structure of the Storage Computer
--  Corp branch of enterprises as shown below:
--
--                    iso(1).org(3).dod(6).internet(1)
--                                 |
--                              private(4)
--                                 |
--                              enterprises(1)
--                                 |
--                              scc(1386)
--                                 |
--                 ._______________.________________.
--                 |                                |
--              products(1)                      sccMibs(2)
--                 |                                |
--                 |                    .___________.___________.
--                 |                    |                       |
--              sccRaid7              raid7(1)              raid7proxy(2)
--


IMPORTS
    enterprises
        FROM RFC1155-SMI;

scc                 OBJECT IDENTIFIER ::= { enterprises 1386 }

--
-- Products
--
sccProducts         OBJECT IDENTIFIER ::= { scc 1 }

sccRaid7            OBJECT IDENTIFIER ::= { sccProducts 1 }

--
-- Mibs
--

sccMibs             OBJECT IDENTIFIER ::= { scc 2 }

-- RAID7 - objects for managing sccRaid7 products
--         defined by scc-raid7-mib-v1-0.txt

raid7mib   OBJECT IDENTIFIER ::= { sccMibs 1 }

-- RAID7 Proxy - objects for managing the Raid7 SNMP Proxy Manager
--         defined by scc-raid7-proxy-mib-v1-0.txt

raid7proxy OBJECT IDENTIFIER ::= { sccMibs 2 }

END
