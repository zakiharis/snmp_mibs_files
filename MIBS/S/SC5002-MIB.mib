-- ****************************************************************************
--                             gdc5002.mib
-- ****************************************************************************

-- Copyright 1996 General DataComm Inc., All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.






--
-- ****************************************************************************
--                        Revision History
-- ****************************************************************************

--  Version   Date	   Name/Comments
--
--  1.00A     11-June-96   S. Veillette
--                         Initial version
--
--  1.00B     21-June-96   S. Veillette
--                         1) modify enums & descriptions of 
--                            sc5002NearEndAlarmWindow  & sc5002FarEndAlarmWindow
--
--  1.00C     25-June-96   A. Klatskin
--                         1) added maintenance and performance tables
--                            Differences from 7002:
--                            - separated ResetStats into
--                              near end and far end
--                            - separated Unavailable Time tables into
--                              near end and far end
--                            - added a bit to LedStatus to show when the
--                              TM led flashes
--                            - moved near end and far end ValidIntervals to 
--                              maintenance
--
--  1.00D     28-June-96   S. Veillette
--                         1) remove sc5002UnitCfgTable
--                         2) remove sc5002NormalTxClkSrc, sc5002FallbackTxClkSrc,
--                            sc5002LineCoding, sc5002InterfaceType, 
--                            sc5002NetworkConnection, and sc5002SignalMode
--                            from the sc5002NetworkCfgTable
--                         3) redefine enum's for the sc5002NearEndAlarmWindow
--                            and sc5002FarEndAlarmWindow
--
--  1.00E     28-June-96   S. Veillette
--                         1) add sc5002FallbackTimingActive
--                            OBJECT IDENTIFIER ::= { sc5002AlarmData 10 }
--
--  1.00F     03-June-96   S. Veillette
--                         1) change sc5002Framing to sc5002E1SignalingMode
--                            && modify enumerated choices
--
--
--  1.00G     09-July-96   S. Veillette
--                         1) remove enumeration value of ReportWhen (6)
--                            from sc5002NearEndAlarmWindow 
--                            and sc5002FarEndAlarmWindow objects
--
--  1.00H     12-July-96   C. Amorossi
--                         1) make sc5002NearEndStatLastInitialized &
--                            sc5002FarEndStatLastInitialized read-only
--                         2) change enumeration for sc5002SoftReset &
--                            sc5002DefaultInit
--
--  1.00J     22-July-96   J. Costa
--			   1) Added sc5002DiagTable
--
--  1.00K     05-Sept-96   C. Amorossi
--			   1) Removed sc5002SendCode, sc5002TestDuration,
--			      sc5002TestExecutionStatus, sc5002TestExceptions,
--			      sc5002TestResults and sc5002ResetTestResults
--			   2) Added sc5002TestResult
--
--  1.00L     09-Sept-96   C. Amorossi
--			   1) Added sc5002SysUpTime
--
--  1.00M     23-Sept-96   S. Veillette
--                         1) removed sc5002RcvrRange from the configuration table
--
--  1.00N     30-Oct-96    W. Meltzer
--                         1) Put one stray page feed character after a comment
--  1.00P     10-Nov-97    D. Baylis
--			   1) Added code download support
--  1.00Q     29-Jan-98    C. Amorossi
--			   1) Added sc5002FirmwareRev
-- ****************************************************************************




--
-- ****************************************************************************
--                          mib definitions begin
-- ****************************************************************************


SC5002-MIB DEFINITIONS ::= BEGIN

IMPORTS	enterprises    FROM RFC1155-SMI
	OBJECT-TYPE    FROM RFC-1212
	DisplayString  FROM RFC1213-MIB
	SCinstance     FROM GDCMACRO-MIB;

gdc 	               OBJECT IDENTIFIER ::= { enterprises 498 }
dsx1                   OBJECT IDENTIFIER ::= { gdc 6 }
sc5002                 OBJECT IDENTIFIER ::= { dsx1 8 }

sc5002Version          OBJECT IDENTIFIER ::= { sc5002 1 }
sc5002NetworkCfg       OBJECT IDENTIFIER ::= { sc5002 2 }
sc5002Alarms           OBJECT IDENTIFIER ::= { sc5002 3 }
sc5002Diagnostics      OBJECT IDENTIFIER ::= { sc5002 4 }
sc5002Maintenance      OBJECT IDENTIFIER ::= { sc5002 5 }
sc5002Performance      OBJECT IDENTIFIER ::= { sc5002 6 }


-- ****************************************************************************


sc5002MIBversion OBJECT-TYPE
    SYNTAX DisplayString (SIZE (5))
    ACCESS read-only
    STATUS mandatory
    DESCRIPTION
    "Identifies the version of the MIB. The format of the version
    is x.yzT, where 'x' identifies the major revision number, 'y'
    identifies the minor revision number, 'z' identifies the
    typographical revision, and T identifies the test revision.
    Upon formal release, no designation for the test revision will
    be present. Acceptable values for the individual revision
    components are as follows:
    x: 1 - 9,    y: 0 - 9,    z: 0 - 9,    T: A - Z"
    ::= { sc5002Version 1 }



--
-- ****************************************************************************
--                                Version Table
-- ****************************************************************************


sc5002VersionTable OBJECT-TYPE
    SYNTAX SEQUENCE OF Sc5002VersionEntry
    ACCESS not-accessible
    STATUS mandatory
    DESCRIPTION " "
    ::= { sc5002Version 2  }

sc5002VersionEntry OBJECT-TYPE
    SYNTAX Sc5002VersionEntry
    ACCESS not-accessible
    STATUS mandatory
    DESCRIPTION
        "An entry in the GDC SC5002 Version Table."
    INDEX	{ sc5002VersionIndex }
    ::= { sc5002VersionTable 1 }

Sc5002VersionEntry ::=
    SEQUENCE {
	sc5002VersionIndex    		SCinstance,
	sc5002ActiveFirmwareRev 	DisplayString,
	sc5002StoredFirmwareRev		DisplayString,
	sc5002BootRev			DisplayString,
	sc5002StoredFirmwareStatus	INTEGER,
	sc5002SwitchActiveFirmware	INTEGER,
	sc5002DownloadingMode          	INTEGER,
        sc5002FirmwareRev               DisplayString
    }

sc5002VersionIndex OBJECT-TYPE
    SYNTAX SCinstance
    ACCESS read-only
    STATUS mandatory
    DESCRIPTION
        "Identifies Version parameters associated with the managed object."
    ::= { sc5002VersionEntry 1 }


sc5002ActiveFirmwareRev OBJECT-TYPE
    SYNTAX DisplayString (SIZE(8))
    ACCESS read-only
    STATUS mandatory
    DESCRIPTION
        "The version number of the firmware currently executing.

	The format is MM.NN.BB where:
	
		MM: Major Revision (0-99)
		NN: Minor Revision (0-99)
		BB: Bug Fix Revision (0-99)

 	 	"
    ::= { sc5002VersionEntry 2 }

sc5002StoredFirmwareRev OBJECT-TYPE
    SYNTAX DisplayString (SIZE(8))
    ACCESS read-only
    STATUS mandatory
    DESCRIPTION
        "The version number of the firmware stored (in a compressed format) 
         but not currently executing.

	
		MM: Major Revision (0-99)
		NN: Minor Revision (0-99)
		BB: Bug Fix Revision (0-99)

	"
    ::= { sc5002VersionEntry 3 }

sc5002BootRev OBJECT-TYPE
    SYNTAX DisplayString (SIZE(2))
    ACCESS read-only
    STATUS mandatory
    DESCRIPTION
        "The version number of the bootstrap firmware. 

    	The version number of the firmware, to allow products to know which
    	revision is installed.  The released version number is sequenced from
    	--, A-, ... AA, ... ZZ.  
	"
    ::= { sc5002VersionEntry 4 }


sc5002StoredFirmwareStatus OBJECT-TYPE
    SYNTAX INTEGER {
        statBlank(1),                       
        statDownLoading(2),
	statOK(3),
	statCheckSumBad(4),    
	statUnZipping(5),
	statBadUnZip(6)                    
    }
    ACCESS read-only
    STATUS mandatory
    DESCRIPTION
        "This object represents the state of the Non-Active or Stored firmware:

        statBlank(1)    	Factory Default                  
        statDownLoading(2)	In process of downloading firmware

	statOK(3)		Zipped version checksum succesful (OK to switch)
				(can set sc5002SwitchActive to switchActive(2))
				
	statCheckSumBad(4)    	Failed checksum after download
	statUnZipping(5)	In process of uncompressing into active area
	statBadUnZip(6)      	Failed last uncompress              


	The object is read only.
	 "
    ::= { sc5002VersionEntry 5 }


sc5002SwitchActiveFirmware OBJECT-TYPE
    SYNTAX INTEGER {
        switchNorm(1),                  -- Read only
        switchActive(2)			-- Write only
    }
    ACCESS read-write
    STATUS mandatory
    DESCRIPTION
        "This object is used to switch the active executing firmware from the version 
	in sc5002ActiveRev to the version in sc5002StoredRev.

	When a  switchActive(2) is set (write only) the element will:
		1) reboot
		2) uncompress stored code into active area
		3) perform checksum on active area
		4) Set sc5002StoredStatus object to indicate results
		5) If succesfull:
			update sc5002ActiveFirmwareRev and sc5002StoredFirmwareRev
			and begin executing
		   If failed: 
			replace active area with previous revision


	The switchNorm(1) enumeration will always be read. 

	Setting switchActive(2) when the sc5002StoredStatus is not statOK(3) will
	result in an error.
	"
    ::= { sc5002VersionEntry 6 }


sc5002DownloadingMode OBJECT-TYPE
    SYNTAX INTEGER {
        disableAll(1),
        enableAndWait(2),
	enableAndSwitch(3)
    }
    ACCESS read-write
    STATUS mandatory
    DESCRIPTION
        "This object is used to configure the download mode:

        disableAll(1)		Prevents any firmware downloading to SC5002

        enableAndWait(2)        Allows downloading zipped code to be stored only!
								
	enableAndSwitch(3)	Allows downloading and then unzips and begins executing
				the new code

	"
    ::= { sc5002VersionEntry 7 }

sc5002FirmwareRev OBJECT-TYPE
    SYNTAX DisplayString (SIZE(2))
    ACCESS read-only
    STATUS mandatory
    DESCRIPTION
    "The version number of the firmware.  Released versions are sequenced
    from --, A-, ... AA, ... ZZ.  Test versions are from 01 to 99."
    ::= { sc5002VersionEntry 8 }








--
-- ****************************************************************************
--                         Network Configuration table
-- ****************************************************************************


sc5002NetworkCfgTable OBJECT-TYPE
    SYNTAX SEQUENCE OF Sc5002NetworkCfgEntry
    ACCESS not-accessible
    STATUS mandatory
    DESCRIPTION
    "This table contains objects that support the specific management
    requirements for configuring the SC5002 Network Interface level objects."
    ::= { sc5002NetworkCfg 1 }

sc5002NetworkCfgEntry OBJECT-TYPE
    SYNTAX Sc5002NetworkCfgEntry
    ACCESS not-accessible
    STATUS mandatory
    DESCRIPTION
    "The sc5002 Network Configuration Table Entry."
    INDEX { sc5002NetworkCfgIndex }
    ::= { sc5002NetworkCfgTable 1 }

Sc5002NetworkCfgEntry ::=
    SEQUENCE {
    sc5002NetworkCfgIndex     SCinstance,
    sc5002E1SignalingMode     INTEGER
    }

sc5002NetworkCfgIndex OBJECT-TYPE
    SYNTAX SCinstance
    ACCESS read-only
    STATUS mandatory
    DESCRIPTION
    "Integer value which uniquely identifies the SC5002 to which this
    entry is applicable. SCinstance is defined to be ssllddcc where:
    ss (byte value) - physical shelf slot location (01-32)
    ll (byte value) - line number (01-128)
    dd (byte value) - drop number (00-31)
    cc (byte value) - channel or interface number (always 00)"
    ::= { sc5002NetworkCfgEntry 1 }

sc5002E1SignalingMode OBJECT-TYPE
    SYNTAX  INTEGER {
    assocChanSigWithCRC4 (1),
    assocChanSigNoCRC4   (2)
    }
    ACCESS read-write
    STATUS mandatory
    DESCRIPTION
    "Specifies the channel signaling scheme for the E1 network interface."
    ::= { sc5002NetworkCfgEntry 2 }





--
-- ****************************************************************************
--                             Alarm Definitions
-- ****************************************************************************


sc5002AlarmData              OBJECT IDENTIFIER ::= { sc5002Alarms 1 }

sc5002NoResponse             OBJECT IDENTIFIER ::= { sc5002AlarmData  1 }

sc5002DiagRxErr              OBJECT IDENTIFIER ::= { sc5002AlarmData  2 }

sc5002PowerUp                OBJECT IDENTIFIER ::= { sc5002AlarmData  3 }

sc5002NvRamCorrupt           OBJECT IDENTIFIER ::= { sc5002AlarmData  4 }

sc5002UnitFailure            OBJECT IDENTIFIER ::= { sc5002AlarmData  5 }

sc5002TimingLoss             OBJECT IDENTIFIER ::= { sc5002AlarmData  6 }

sc5002LossOfSignal           OBJECT IDENTIFIER ::= { sc5002AlarmData  7 }

sc5002LossOfFrame            OBJECT IDENTIFIER ::= { sc5002AlarmData  8 }

sc5002AlarmIndSignal         OBJECT IDENTIFIER ::= { sc5002AlarmData  9 }

sc5002FallbackTimingActive   OBJECT IDENTIFIER ::= { sc5002AlarmData 10 }

sc5002NearEndLnCodeViol      OBJECT IDENTIFIER ::= { sc5002AlarmData 11 }

sc5002NearEndErrSec          OBJECT IDENTIFIER ::= { sc5002AlarmData 12 }

sc5002NearEndBkdBlkErr       OBJECT IDENTIFIER ::= { sc5002AlarmData 13 }

sc5002NearEndSevErrSec       OBJECT IDENTIFIER ::= { sc5002AlarmData 14 }

sc5002NearEndUnavlSec        OBJECT IDENTIFIER ::= { sc5002AlarmData 15 }

sc5002FarEndErrSec           OBJECT IDENTIFIER ::= { sc5002AlarmData 16 }

sc5002FarEndBkdBlkErr        OBJECT IDENTIFIER ::= { sc5002AlarmData 17 }

sc5002FarEndSevErrSec        OBJECT IDENTIFIER ::= { sc5002AlarmData 18 }

sc5002FarEndUnavlSec         OBJECT IDENTIFIER ::= { sc5002AlarmData 19 }






--
-- ****************************************************************************
--                     General Alarm Object Information
-- ****************************************************************************


--       Alarm                  Maskable     Window and     Reportable as 
--                                           Threshold      Major/Minor Alarm
--                                                          (future use ???)

--   sc5002NoResponse              no            no              no

--   sc5002DiagRxErr               no            no              no

--   sc5002PowerUp                 no            no              no

--   sc5002NvRamCorrupt            no            no              no

--   sc5002UnitFailure             no            no              no

--   sc5002TimingLoss              yes           no              yes

--   sc5002LossofSignal            yes           no              yes

--   sc5002LossOfFrame             yes           no              yes

--   sc5002AlarmIndSignal          yes           no              yes

--   sc5002FallbackTimingActive    yes           no              yes

--   sc5002NearEndLnCodeViol       yes           yes             yes

--   sc5002NearEndErrSec           yes           yes             yes

--   sc5002NearEndBkdBlkErr        yes           yes             yes
 
--   sc5002NearEndSevErrSec        yes           yes             yes

--   sc5002NearEndUnavlSec         yes           yes             yes

--   sc5002FarEndErrSec            yes           yes             yes

--   sc5002FarEndBkdBlkErr         yes           yes             yes

--   sc5002FarEndSevErrSec         yes           yes             yes

--   sc5002FarEndUnavlSec          yes           yes             yes






--
-- ****************************************************************************
--                        Near End Alarm Objects
-- ****************************************************************************

sc5002NearEndAlarmCfgTable OBJECT-TYPE
    SYNTAX SEQUENCE OF Sc5002NearEndAlarmCfgEntry
    ACCESS not-accessible
    STATUS mandatory
    DESCRIPTION
    "This table contains entries that configure Near End Alarm reporting."
    ::= { sc5002Alarms 2 }

sc5002NearEndAlarmCfgEntry OBJECT-TYPE
    SYNTAX Sc5002NearEndAlarmCfgEntry
    ACCESS not-accessible
    STATUS mandatory
    DESCRIPTION
    "An entry in the Near End Alarm Configuration table."
    INDEX { sc5002NearEndAlarmCfgIndex, sc5002NearEndAlarmCfgIdentifier }
    ::= { sc5002NearEndAlarmCfgTable 1 }

Sc5002NearEndAlarmCfgEntry ::=
    SEQUENCE {
    sc5002NearEndAlarmCfgIndex         SCinstance,
    sc5002NearEndAlarmCfgIdentifier    OBJECT IDENTIFIER,
    sc5002NearEndAlarmWindow           INTEGER,
    sc5002NearEndAlarmThreshold        INTEGER
    }

sc5002NearEndAlarmCfgIndex OBJECT-TYPE
    SYNTAX SCinstance
    ACCESS read-only
    STATUS mandatory
    DESCRIPTION
    "Integer value which uniquely identifies the SC5002 to which this
    entry is applicable. SCinstance is defined to be ssllddcc where:
    ss (byte value) - physical shelf slot location (01-32)
    ll (byte value) - line number (01-128)
    dd (byte value) - drop number (00-31)
    cc (byte value) - channel or interface number (always 00)"
    ::= { sc5002NearEndAlarmCfgEntry 1 }

sc5002NearEndAlarmCfgIdentifier OBJECT-TYPE
    SYNTAX OBJECT IDENTIFIER
    ACCESS read-only
    STATUS mandatory
    DESCRIPTION
    "format: iso.org.dod.internet.private.enterprises.gdc.
             dsx1.sc5002.sc5002Alarms.sc5002AlarmData.ALM
     example:  1.3.6.1.4.1.498.6.8.4.1.ALM
     where ALM = 1 for sc5002NoResponse alarm, 2 for sc5002DiagRxErr alarm,
                 etc., as specified in the Alarm Definitions above."
     ::= { sc5002NearEndAlarmCfgEntry 2 }

--

sc5002NearEndAlarmWindow OBJECT-TYPE
    SYNTAX INTEGER {
    win30sec    (1),
    win1min     (2),
    win15min    (3),
    win1hr      (4),
    win24hr     (5)
    }
    ACCESS  read-write
    STATUS  mandatory
    DESCRIPTION
    "The time period in which a specified number of events must occur,
    (specified by the alarm's threshold), before declaring an alarm condition.
    After reporting an Alarm condition and upon expiration of the window time
    period, the event count is reset to zero and another time period is begun.
    If the specified number of events is not exceeded within the next time
    period, an Alarm Cleared condition is reported."
    ::= { sc5002NearEndAlarmCfgEntry 3 }


sc5002NearEndAlarmThreshold OBJECT-TYPE
    SYNTAX INTEGER {
    thr1      (1),
    thr3      (2),
    thr10     (3),
    thr100    (4),
    thr1000   (5),
    thr10000  (6)
    }
    ACCESS  read-write
    STATUS  mandatory
    DESCRIPTION
    "The number of events which must be exceed, within the time period
    specified by the alarm's window, before declaring an alarm"
    ::= { sc5002NearEndAlarmCfgEntry 4 }






--
-- ****************************************************************************
--                         Far End Alarm Objects
-- ****************************************************************************

sc5002FarEndAlarmCfgTable OBJECT-TYPE
    SYNTAX SEQUENCE OF Sc5002FarEndAlarmCfgEntry
    ACCESS not-accessible
    STATUS mandatory
    DESCRIPTION
    "This table contains entries that configure Far End Alarm reporting."
    ::= { sc5002Alarms 3 }

sc5002FarEndAlarmCfgEntry OBJECT-TYPE
    SYNTAX Sc5002FarEndAlarmCfgEntry
    ACCESS not-accessible
    STATUS mandatory
    DESCRIPTION
    "An entry in the Far End Alarm Configuration table."
    INDEX { sc5002FarEndAlarmCfgIndex, sc5002FarEndAlarmCfgIdentifier }
    ::= { sc5002FarEndAlarmCfgTable 1 }

Sc5002FarEndAlarmCfgEntry ::=
    SEQUENCE {
    sc5002FarEndAlarmCfgIndex         SCinstance,
    sc5002FarEndAlarmCfgIdentifier    OBJECT IDENTIFIER,
    sc5002FarEndAlarmWindow           INTEGER,
    sc5002FarEndAlarmThreshold        INTEGER
    }

sc5002FarEndAlarmCfgIndex OBJECT-TYPE
    SYNTAX SCinstance
    ACCESS read-only
    STATUS mandatory
    DESCRIPTION
    "Integer value which uniquely identifies the SC5002 to which this
    entry is applicable. SCinstance is defined to be ssllddcc where:
    ss (byte value) - physical shelf slot location (01-32)
    ll (byte value) - line number (01-128)
    dd (byte value) - drop number (00-31)
    cc (byte value) - channel or interface number (always 00)"
    ::= { sc5002FarEndAlarmCfgEntry 1 }

sc5002FarEndAlarmCfgIdentifier OBJECT-TYPE
    SYNTAX OBJECT IDENTIFIER
    ACCESS read-only
    STATUS mandatory
    DESCRIPTION
    "format: iso.org.dod.internet.private.enterprises.gdc.
             dsx1.sc5002.sc5002Alarms.sc5002AlarmData.ALM
     example:  1.3.6.1.4.1.498.6.8.4.1.ALM
     where ALM = 1 for sc5002NoResponse alarm, 2 for sc5002DiagRxErr alarm,
                 etc., as specified in the Alarm Definitions above."
     ::= { sc5002FarEndAlarmCfgEntry 2 }

--

sc5002FarEndAlarmWindow OBJECT-TYPE
    SYNTAX INTEGER {
    win30sec    (1),
    win1min     (2),
    win15min    (3),
    win1hr      (4),
    win24hr     (5)
    }
    ACCESS  read-write
    STATUS  mandatory
    DESCRIPTION
    "The time period in which a specified number of events must occur,
    (specified by the alarm's threshold), before declaring an alarm condition.
    After reporting an Alarm condition and upon expiration of the window time
    period, the event count is reset to zero and another time period is begun.
    If the specified number of events is not exceeded within the next time
    period, an Alarm Cleared condition is reported."
    ::= { sc5002FarEndAlarmCfgEntry 3 }


sc5002FarEndAlarmThreshold OBJECT-TYPE
    SYNTAX INTEGER {
    thr1      (1),
    thr3      (2),
    thr10     (3),
    thr100    (4),
    thr1000   (5),
    thr10000  (6)
    }
    ACCESS  read-write
    STATUS  mandatory
    DESCRIPTION
    "The number of events which must be exceed, within the time period
    specified by the alarm's window, before declaring an alarm"
    ::= { sc5002FarEndAlarmCfgEntry 4 }






-- 
 -- ********************************************************************
 -- GDC 5002 Maintenance Table
 -- ********************************************************************

sc5002MaintenanceTable OBJECT-TYPE
	 SYNTAX SEQUENCE OF Sc5002MaintenanceEntry
	 ACCESS not-accessible
	 STATUS mandatory
	 DESCRIPTION
		 "The table describes the maintenance objects for 
		 the unit and references the unit interface (cc = 00)."
	 ::= { sc5002Maintenance 1  }

sc5002MaintenanceEntry OBJECT-TYPE
	 SYNTAX Sc5002MaintenanceEntry
	 ACCESS not-accessible
	 STATUS mandatory
	 DESCRIPTION
		 "An entry in the GDC E1 Maintenance Table."
	 INDEX  { sc5002MaintenanceLineIndex }
	 ::= { sc5002MaintenanceTable 1 }

Sc5002MaintenanceEntry ::=
	 SEQUENCE {
		  sc5002MaintenanceLineIndex
			 SCinstance,
		  sc5002SoftReset
			 INTEGER,
		  sc5002DefaultInit
			 INTEGER,
		  sc5002NearEndResetStats
			 INTEGER,
		  sc5002NearEndStatLastInitialized
			 INTEGER,
		  sc5002FarEndResetStats
			 INTEGER,
		  sc5002FarEndStatLastInitialized
			 INTEGER,
                  sc5002LedStatus
			 OCTET STRING,
                  sc5002NearEndValidIntervals 
			 INTEGER,
                  sc5002FarEndValidIntervals 
			 INTEGER,
		  sc5002SysUpTime
			 INTEGER
		 }

sc5002MaintenanceLineIndex OBJECT-TYPE
	 SYNTAX SCinstance
	 ACCESS read-only
	 STATUS mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002MaintenanceEntry 1 }

sc5002SoftReset		OBJECT-TYPE
	 SYNTAX INTEGER {
			 reset(1),
			 norm(2)
			 }
	 ACCESS read-write
	 STATUS mandatory
	 DESCRIPTION
		 "Supports the action of soft resetting the unit.  When this
		 object is set to reset(1), then the unit performs a soft
		 reset, whose meaning is specific to the type of unit being
		 managed. The value of norm(2) will be returned when 
		 the reset is complete.
		  
		 The value of norm(2) can not be set by management."

	 ::= { sc5002MaintenanceEntry 2 }


sc5002DefaultInit     	OBJECT-TYPE
	 SYNTAX INTEGER {
			 factoryDefault(1),
			 normal(2)

		 }
	 ACCESS read-write
	 STATUS mandatory
	 DESCRIPTION
		 "This is used to allow the NonVolatile Configuration to 
		 be set to a factory default state.  When this value is set to
		 factoryDefault(1) the unit will perform a reset to make the 
		 default configuration take effect. The value of normal(2) will 
		 be returned when the initialization is complete.

		 The value of normal(2) can not be set by management."
	 ::= { sc5002MaintenanceEntry 3 }

sc5002NearEndResetStats      	OBJECT-TYPE
	 SYNTAX  INTEGER        {
			 norm(1),
			 reset(2)
		 }
	 ACCESS  read-write
	 STATUS  mandatory
	 DESCRIPTION
		 "Supports the action of soft resetting the sc5002NearEndValidIntervals
		 object.  When this object is set to reset(2), then the unit
		 will reset the sc5002ValidIntervals object to zero.
		 The value of norm(1) can not be set by management."
	 ::= { sc5002MaintenanceEntry 4 }

sc5002NearEndStatLastInitialized      	OBJECT-TYPE
	SYNTAX  INTEGER (1..2147483647)
	ACCESS  read-only
	STATUS  mandatory
	DESCRIPTION
		"Number of seconds from midnight Dec 31, 1969 up until
         sc5002NearEndValidIntervals was last initialized to zero"
	::= {sc5002MaintenanceEntry 5}

sc5002FarEndResetStats      	OBJECT-TYPE
	 SYNTAX  INTEGER        {
			 norm(1),
			 reset(2)
		 }
	 ACCESS  read-write
	 STATUS  mandatory
	 DESCRIPTION
		 "Supports the action of soft resetting the sc5002FarEndValidIntervals
		 object.  When this object is set to reset(2), then the unit
		 will reset the sc5002ValidIntervals object to zero.
		 The value of norm(1) can not be set by management."
	 ::= { sc5002MaintenanceEntry 6 }

sc5002FarEndStatLastInitialized      	OBJECT-TYPE
	SYNTAX  INTEGER (1..2147483647)
	ACCESS  read-only
	STATUS  mandatory
	DESCRIPTION
		"Number of seconds from midnight Dec 31, 1969 up until
         sc5002FarEndValidIntervals was last initialized to zero"
	::= {sc5002MaintenanceEntry 7}

sc5002LedStatus 	OBJECT-TYPE
	 SYNTAX  OCTET STRING (SIZE(3))
	 ACCESS  read-only
	 STATUS  mandatory
	 DESCRIPTION
		 "Returns a bitwise snapshot of the front panel LED state.
		 Octet 1 bit 7 - not used
			 bit 6 - ON
			 bit 5 - INSV
			 bit 4 - RSP
			 bit 3 - TMG
			 bit 2 - NIU
			 bit 1 - D_I
			 bit 0 - future use

		 Octet 2 bit 7 - not used
			 bit 6 - future use
			 bit 5 - NTWK AIS
			 bit 4 - NTWK LCV
			 bit 3 - NTWK LOS
			 bit 2 - NTWK OOF
			 bit 1 - ALM
			 bit 0 - TM

		 Octet 3 bit 7 - not used
			 bit 6 - ST- future use
			 bit 5 - LT- future use
			 bit 4 - RL- future use
			 bit 3 - TM transitions/flashing
			 bit 2 - future use
			 bit 1 - future use
			 bit 0 - future use"
	 ::= { sc5002MaintenanceEntry 8 }

sc5002NearEndValidIntervals OBJECT-TYPE
	     SYNTAX  INTEGER (0..16)
	     ACCESS  read-only
	     STATUS  mandatory
	     DESCRIPTION
		"The number of  previous  intervals  for  which
		valid data was collected.  The value will be 16
		unless the interface was brought on-line within
		the last 4 hours, in which case the value will
		be the number of complete 15  minute  intervals
		the since interface has been online."
	    ::= { sc5002MaintenanceEntry 9 }

sc5002FarEndValidIntervals OBJECT-TYPE
	     SYNTAX  INTEGER (0..16)
	     ACCESS  read-only
	     STATUS  mandatory
	     DESCRIPTION
		"The number of  previous  intervals  for  which
		valid data was collected.  The value will be 16
		unless the interface was brought on-line within
		the last 4 hours, in which case the value will
		be the number of complete 15  minute  intervals
		the since interface has been online."
	    ::= { sc5002MaintenanceEntry 10 }

sc5002SysUpTime       	OBJECT-TYPE
	 SYNTAX INTEGER (1..2147483647)
	 ACCESS read-only
	 STATUS mandatory
	 DESCRIPTION
		 "This variable is used to report the elapsed system tick
		 time for conversion to real time at the controller and is
		 not related to the sysUpTime referenced in MIB-II.
		 Upon power-up of the unit, the elapsed time is cleared.
		 The elapsed time counter rolls over upon reaching the
		 maximum count."
	    ::= { sc5002MaintenanceEntry 11 }

-- 
 -- ********************************************************************
 -- Current 15 Near End Minute Performance Table
 -- ********************************************************************


 sc5002NearEndCurrent15MinTable    OBJECT-TYPE
	 SYNTAX  SEQUENCE OF Sc5002NearEndCurrent15MinEntry
	 ACCESS  not-accessible
	 STATUS  mandatory
	 DESCRIPTION
		 "The sc5002 Current table."
	 ::= { sc5002Performance 1 }


 sc5002NearEndCurrent15MinEntry    OBJECT-TYPE
	 SYNTAX  Sc5002NearEndCurrent15MinEntry
	 ACCESS  not-accessible
	 STATUS  mandatory
	 DESCRIPTION
		 "An entry in the sc5002 NearEnd Current table."
	 INDEX   { sc5002NearEndCurrent15MinIndex }
	 ::= { sc5002NearEndCurrent15MinTable 1 }

 Sc5002NearEndCurrent15MinEntry ::=
	 SEQUENCE {
		  sc5002NearEndCurrent15MinIndex
			 SCinstance,
		  sc5002NearEndCurrent15MinStat
			OCTET STRING
	  }

 sc5002NearEndCurrent15MinIndex    OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	    ::= { sc5002NearEndCurrent15MinEntry 1 }
--
 sc5002NearEndCurrent15MinStat    OBJECT-TYPE
	SYNTAX OCTET STRING (SIZE(12))
	ACCESS read-only
	STATUS mandatory
	DESCRIPTION
		 "Returns a bitwise snapshot of the current 15Min statistics.

		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0
--
		8.7	f/u
		8.6	f/u
		8.5	f/u
		8.4	f/u
		8.3	f/u
		8.2	2^9	UAS
		 .
		8.0	2^7

		9.7	f/u
		9.6	2^6	UAS
		  .
		9.0	2^0

		10.7	f/u
		10.6	f/u
		10.5	f/u
		10.4	f/u
		10.3	f/u
		10.2	Counter Overflow (>65535)	LCV
		10.1	2^15
		10.0	2^14

		11.7	f/u
		11.6	2^13	LCV
		  .
		11.0	2^7

		12.7	f/u
		12.6	2^6	LCV
		  .
		12.0	2^0
"

	::= {sc5002NearEndCurrent15MinEntry 2 }

--
 -- ********************************************************************
 -- Interval Near End Performance Table
 -- ********************************************************************


 sc5002NearEndIntervalTable   OBJECT-TYPE
	 SYNTAX  SEQUENCE OF Sc5002NearEndIntervalEntry
	 ACCESS  not-accessible
	 STATUS  mandatory
	 DESCRIPTION
		 "The sc5002 Interval table."

	 ::= { sc5002Performance 2 }


 sc5002NearEndIntervalEntry   OBJECT-TYPE
	 SYNTAX  Sc5002NearEndIntervalEntry
	 ACCESS  not-accessible
	 STATUS  mandatory
	 DESCRIPTION
		 "An entry in the E1 Interval table."
	 INDEX   { sc5002NearEndIntervalIndex, sc5002NearEndIntervalNumber }
	 ::= { sc5002NearEndIntervalTable 1 }

 Sc5002NearEndIntervalEntry ::=
	 SEQUENCE {
		  sc5002NearEndIntervalIndex
			 SCinstance,
		  sc5002NearEndIntervalNumber
			 INTEGER,
		  sc5002NearEndIntervalStat
			 OCTET STRING
	  }

 sc5002NearEndIntervalIndex   OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002NearEndIntervalEntry 1 }

 sc5002NearEndIntervalNumber   OBJECT-TYPE
	 SYNTAX INTEGER (1..16)
	 ACCESS read-only
	 STATUS mandatory
	 DESCRIPTION
		 "The number of Errored Seconds encountered by an E1
		 interface in one of the previous 16, individual 15 minute,
		 intervals."
	 ::= {sc5002NearEndIntervalEntry 2 }

-- 
 sc5002NearEndIntervalStat   OBJECT-TYPE
	 SYNTAX OCTET STRING (SIZE(12))
	 ACCESS read-only
	 STATUS mandatory
	 DESCRIPTION
		 "Returns a bitwise map of the
		 interface in one of the previous 16, individual 15 minute,
		 intervals.

		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0
--
		8.7	f/u
		8.6	f/u
		8.5	f/u
		8.4	f/u
		8.3	f/u
		8.2	2^9	UAS
		 .
		8.0	2^7

		9.7	f/u
		9.6	2^6	UAS
		  .
		9.0	2^0

		10.7	f/u
		10.6	f/u
		10.5	f/u
		10.4	f/u
		10.3	f/u
		10.2	Counter Overflow (>65535)	LCV
		10.1	2^15
		10.0	2^14

		11.7	f/u
		11.6	2^13	LCV
		  .
		11.0	2^7

		12.7	f/u
		12.6	2^6	LCV
		  .
		12.0	2^0

"
	 ::= {sc5002NearEndIntervalEntry 3 }

 -- ********************************************************************
 -- Current 24 Hour Near End Performance Table
 -- ********************************************************************


 sc5002NearEndCurrent24HrTable              OBJECT-TYPE
	 SYNTAX  SEQUENCE OF Sc5002NearEndCurrent24HrEntry
	 ACCESS  not-accessible
	 STATUS  mandatory
	 DESCRIPTION
		 "The E1 Current24Hr table.  4 hour interval."

	 ::= { sc5002Performance 3}
--
 sc5002NearEndCurrent24HrEntry              OBJECT-TYPE
	 SYNTAX  Sc5002NearEndCurrent24HrEntry
	 ACCESS  not-accessible
	 STATUS  mandatory
	 DESCRIPTION
		 "An entry in the E1 Total table."
	 INDEX   { sc5002NearEndCurrent24HrIndex }
	 ::= { sc5002NearEndCurrent24HrTable 1 }

 Sc5002NearEndCurrent24HrEntry ::=
	 SEQUENCE {
		  sc5002NearEndCurrent24HrIndex
			 SCinstance,
		  sc5002NearEndCurrent24HrStat
			 OCTET STRING
	  }

 sc5002NearEndCurrent24HrIndex              OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002NearEndCurrent24HrEntry 1 }

-- 
 sc5002NearEndCurrent24HrStat              OBJECT-TYPE
	 SYNTAX OCTET STRING (SIZE (15))
	 ACCESS read-only
	 STATUS mandatory
	 DESCRIPTION
		 "Returns a bitwise map of the current 24 hour table

		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14
--
		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0

		13.7	f/u
		13.6	f/u
		13.5	f/u
		13.4	f/u
		13.3	f/u
		13.2	1: Counter Overflow (>65535)	LCV
		13.1	2^15
		13.0	2^14

		14.7	f/u
		14.6	2^13				LCV
		 .
		14.0	2^7

		15.7	f/u
		15.6	2^6				LCV
		 .
		15.0	2^0

"
	 ::= {sc5002NearEndCurrent24HrEntry 2 }
--
 -- ********************************************************************
 -- Recent 24 Hour Near End Performance Table
 -- ********************************************************************


 sc5002NearEndRecent24HrTable              OBJECT-TYPE
	 SYNTAX  SEQUENCE OF Sc5002NearEndRecent24HrEntry
	 ACCESS  not-accessible
	 STATUS  mandatory
	 DESCRIPTION
		 "The E1 Recent24Hr table.  4 hour interval."

	 ::= { sc5002Performance 4}

 sc5002NearEndRecent24HrEntry              OBJECT-TYPE
	 SYNTAX  Sc5002NearEndRecent24HrEntry
	 ACCESS  not-accessible
	 STATUS  mandatory
	 DESCRIPTION
		 "An entry in the E1 Total table."
	 INDEX   { sc5002NearEndRecent24HrIndex }
	 ::= { sc5002NearEndRecent24HrTable 1 }

 Sc5002NearEndRecent24HrEntry ::=
	 SEQUENCE {
		  sc5002NearEndRecent24HrIndex
			 SCinstance,
		  sc5002NearEndRecent24HrStat
			 OCTET STRING
	  }

 sc5002NearEndRecent24HrIndex              OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002NearEndRecent24HrEntry 1 }

-- 
 sc5002NearEndRecent24HrStat              OBJECT-TYPE
	 SYNTAX OCTET STRING (SIZE (15))
	 ACCESS read-only
	 STATUS mandatory
	 DESCRIPTION
		 "Returns a bitwise map of the current 24 hour table

		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14
--
		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0

		13.7	f/u
		13.6	f/u
		13.5	f/u
		13.4	f/u
		13.3	f/u
		13.2	1: Counter Overflow (>65535)	LCV
		13.1	2^15
		13.0	2^14

		14.7	f/u
		14.6	2^13				LCV
		 .
		14.0	2^7

		15.7	f/u
		15.6	2^6				LCV
		 .
		15.0	2^0


"
	 ::= {sc5002NearEndRecent24HrEntry 2 }
--
 -- ********************************************************************
 -- Far End Current 15 Minute Performance Table
 -- ********************************************************************


 sc5002FarEndCurrent15MinTable      OBJECT-TYPE
	 SYNTAX  SEQUENCE OF Sc5002FarEndCurrent15MinEntry
	 ACCESS  not-accessible
	 STATUS  mandatory
	 DESCRIPTION
		 "The sc5002FarEnd Current 15 minute table."
	 ::= { sc5002Performance 5 }


 sc5002FarEndCurrent15MinEntry      OBJECT-TYPE
	 SYNTAX  Sc5002FarEndCurrent15MinEntry
	 ACCESS  not-accessible
	 STATUS  mandatory
	 DESCRIPTION
		 "An entry in the sc5002FarEnd Current 15 Minute table."
	 INDEX   { sc5002FarEndCurrent15MinIndex }
	 ::= { sc5002FarEndCurrent15MinTable 1 }

 Sc5002FarEndCurrent15MinEntry ::=
	 SEQUENCE {
		  sc5002FarEndCurrent15MinIndex
			 SCinstance,
		  sc5002FarEndCurrent15MinStat
			 OCTET STRING
	  }

 sc5002FarEndCurrent15MinIndex      OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	    ::= { sc5002FarEndCurrent15MinEntry 1 }

-- 
 sc5002FarEndCurrent15MinStat      OBJECT-TYPE
	SYNTAX OCTET STRING (SIZE(9))
	ACCESS read-only
	STATUS mandatory
	DESCRIPTION
		 "Returns a bitwise map of the far end
		 interface in one of the previous 16, individual 15 minute,
		 intervals.

		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0
--
		8.7	f/u
		8.6	f/u
		8.5	f/u
		8.4	f/u
		8.3	f/u
		8.2	2^9	UAS
		 .
		8.0	2^7

		9.7	f/u
		9.6	2^6	UAS
		  .
		9.0	2^0
"
	::= {sc5002FarEndCurrent15MinEntry 2 }


 -- ********************************************************************
 -- Interval Far End Performance Table
 -- ********************************************************************


 sc5002FarEndIntervalTable     OBJECT-TYPE
	 SYNTAX  SEQUENCE OF Sc5002FarEndIntervalEntry
	 ACCESS  not-accessible
	 STATUS  mandatory
	 DESCRIPTION
		 "The sc5002FarEnd Interval table."

	 ::= { sc5002Performance 6 }

--
 sc5002FarEndIntervalEntry     OBJECT-TYPE
	 SYNTAX  Sc5002FarEndIntervalEntry
	 ACCESS  not-accessible
	 STATUS  mandatory
	 DESCRIPTION
		 "An entry in the Interval table."
	 INDEX   { sc5002FarEndIntervalIndex, sc5002FarEndIntervalNumber }
	 ::= { sc5002FarEndIntervalTable 1 }

 Sc5002FarEndIntervalEntry ::=
	 SEQUENCE {
		  sc5002FarEndIntervalIndex
			 SCinstance,
		  sc5002FarEndIntervalNumber
			 INTEGER,
		  sc5002FarEndIntervalStat
			 OCTET STRING
	  }

 sc5002FarEndIntervalIndex     OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002FarEndIntervalEntry 1 }

 sc5002FarEndIntervalNumber    OBJECT-TYPE
	 SYNTAX  INTEGER (1..16)
	 ACCESS  read-only
	 STATUS  mandatory
	 DESCRIPTION
		 "A number between 1 and 16, where 1 is the most recently completed 
		 15 minute interval and 16 is the least recently completed 15 minutes  
		 interval   (assuming   that  all  16  intervals  are valid)."
	 ::= { sc5002FarEndIntervalEntry 2 }

 sc5002FarEndIntervalStat     OBJECT-TYPE
	 SYNTAX OCTET STRING (SIZE(9))
	 ACCESS read-only
	 STATUS mandatory
	 DESCRIPTION
		 "Returns a bitwise map of statistics for the far end
		 interface in the current 15 minute interval.
		1.7	f/u
		1.6	f/u
		1.5	f/u
		1.4	f/u
		1.3	f/u
		1.2	2^9	ES
		 .
		1.0	2^7

		2.7	f/u
		2.6	2^6
		  .
		2.0	2^0

		3.7	f/u
		3.6	f/u
		3.5	f/u
		3.4	f/u
		3.3	f/u
		3.2	2^9	SES
		  .
		3.0	2^7

		4.7	f/u
		4.6	2^6	SES
		 .
		4.0	2^0

		5.7	f/u
		5.6	f/u
		5.5	f/u
		5.4	f/u
		5.3	f/u
		5.2	Counter Overflow (>65535)	BBE
		5.1	2^15
		5.0	2^14

		6.7	f/u
		6.6	2^13	BBE
		  .
		6.0	2^7

		7.7	f/u
		7.6	2^6	BBE
		  .
		7.0	2^0

		8.7	f/u
		8.6	f/u
		8.5	f/u
		8.4	f/u
		8.3	f/u
		8.2	2^9	UAS
		 .
		8.0	2^7

		9.7	f/u
		9.6	2^6	UAS
		  .
		9.0	2^0
"
	 ::= {sc5002FarEndIntervalEntry 3 }

-- 
 -- ********************************************************************
 -- Current 24 Hour Far End Performance Table
 -- ********************************************************************


 sc5002CurrentFarEnd24HrTable                OBJECT-TYPE
	 SYNTAX  SEQUENCE OF Sc5002CurrentFarEnd24HrEntry
	 ACCESS  not-accessible
	 STATUS  mandatory
	 DESCRIPTION
		 "The Current 24 Hour table."

	 ::= { sc5002Performance 7 }

 sc5002CurrentFarEnd24HrEntry                OBJECT-TYPE
	 SYNTAX  Sc5002CurrentFarEnd24HrEntry
	 ACCESS  not-accessible
	 STATUS  mandatory
	 DESCRIPTION
		 "An entry in the Current 24 Hr table."
	 INDEX   { sc5002CurrentFarEnd24HrIndex }
	 ::= { sc5002CurrentFarEnd24HrTable 1 }

 Sc5002CurrentFarEnd24HrEntry ::=
	 SEQUENCE {
		  sc5002CurrentFarEnd24HrIndex
			 SCinstance,
		  sc5002CurrentFarEnd24HrStat
			 OCTET STRING
	  }

-- 
 sc5002CurrentFarEnd24HrIndex                OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002CurrentFarEnd24HrEntry 1 }

 sc5002CurrentFarEnd24HrStat                OBJECT-TYPE
	 SYNTAX OCTET STRING (SIZE(12))
	 ACCESS read-only
	 STATUS mandatory
	 DESCRIPTION
		 "Returns a bitwise map of statistics for the
		 interface in the current 24 hour interval.
		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0
--
		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0
"
	 ::= {sc5002CurrentFarEnd24HrEntry 2 }

 -- ********************************************************************
 -- Recent 24 Hour Far End Performance Table
 -- ********************************************************************


 sc5002RecentFarEnd24HrTable                OBJECT-TYPE
	 SYNTAX  SEQUENCE OF Sc5002RecentFarEnd24HrEntry
	 ACCESS  not-accessible
	 STATUS  mandatory
	 DESCRIPTION
		 "The Recent 24 Hour table."

	 ::= { sc5002Performance 8 }

-- 
 sc5002RecentFarEnd24HrEntry                OBJECT-TYPE
	 SYNTAX  Sc5002RecentFarEnd24HrEntry
	 ACCESS  not-accessible
	 STATUS  mandatory
	 DESCRIPTION
		 "An entry in the Recent 24 Hr table."
	 INDEX   { sc5002RecentFarEnd24HrIndex }
	 ::= { sc5002RecentFarEnd24HrTable 1 }

 Sc5002RecentFarEnd24HrEntry ::=
	 SEQUENCE {
		  sc5002RecentFarEnd24HrIndex
			 SCinstance,
		  sc5002RecentFarEnd24HrStat
			 OCTET STRING
	  }

--
  sc5002RecentFarEnd24HrIndex                OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002RecentFarEnd24HrEntry 1 }

 sc5002RecentFarEnd24HrStat                OBJECT-TYPE
	 SYNTAX OCTET STRING (SIZE(12))
	 ACCESS read-only
	 STATUS mandatory
	 DESCRIPTION
		 "Returns a bitwise map of statistics for the
		 interface in the Recent 24 hour interval.

		1.7	f/u
		1.6	f/u
		1.5	f/u
		1.4	f/u
		1.3	f/u
		1.2	1: Counter Overflow (>65535)	ES
		1.1	2^15
		1.0	2^14

		2.7	f/u
		2.6	2^13				ES
		 .
		2.0	2^7

		3.7	f/u
		3.6	2^6				ES
		 .
		3.0	2^0

		4.7	f/u
		4.6	f/u
		4.5	f/u
		4.4	f/u
		4.3	f/u
		4.2	1: Counter Overflow (>65535)	SES
		4.1	2^15
		4.0	2^14

		5.7	f/u
		5.6	2^13				SES
		 .
		5.0	2^7

		6.7	f/u
		6.6	2^6				SES
		 .
		6.0	2^0

		7.7	f/u
		7.6	f/u
		7.5	f/u
		7.4	f/u
		7.3	f/u
		7.2	1: Counter Overflow (>65535)	BBE
		7.1	2^15
		7.0	2^14

		8.7	f/u
		8.6	2^13				BBE
		 .
		8.0	2^7

		9.7	f/u
		9.6	2^6				BBE
		 .
		9.0	2^0

		10.7	f/u
		10.6	f/u
		10.5	f/u
		10.4	f/u
		10.3	f/u
		10.2	1: Counter Overflow (>65535)	UAS
		10.1	2^15
		10.0	2^14

		11.7	f/u
		11.6	2^13				UAS
		 .
		11.0	2^7

		12.7	f/u
		12.6	2^6				UAS
		 .
		12.0	2^0
"
	 ::= {sc5002RecentFarEnd24HrEntry 2 }

 -- ********************************************************************
 -- Unavailable Time Registers - Near end
 -- ********************************************************************

 sc5002NearEndUnavailableTimeRegTable     OBJECT-TYPE
	 SYNTAX  SEQUENCE OF Sc5002NearEndUnavailableTimeRegEntry
	 ACCESS  not-accessible
	 STATUS  mandatory
	 DESCRIPTION
		 "The sc5002 Unavailable Time Register table."

	 ::= { sc5002Performance 9 }


--
 sc5002NearEndUnavailableTimeRegEntry     OBJECT-TYPE
	 SYNTAX  Sc5002NearEndUnavailableTimeRegEntry
	 ACCESS  not-accessible
	 STATUS  mandatory
	 DESCRIPTION
		 "An entry in the Unavailable Time Register table."
	 INDEX   { sc5002NearEndUnavailableTimeRegIndex, sc5002NearEndUnavailableTimeRegNumber }
	 ::= { sc5002NearEndUnavailableTimeRegTable 1 }

 Sc5002NearEndUnavailableTimeRegEntry ::=
	 SEQUENCE {
		  sc5002NearEndUnavailableTimeRegIndex
			 SCinstance,
		  sc5002NearEndUnavailableTimeRegNumber
			 INTEGER,
		  sc5002NearEndUnavailableTimeRegStart
			 INTEGER,
		  sc5002NearEndUnavailableTimeRegStop
			 INTEGER
	  }

-- 
 sc5002NearEndUnavailableTimeRegIndex     OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002NearEndUnavailableTimeRegEntry 1 }

 sc5002NearEndUnavailableTimeRegNumber    OBJECT-TYPE
	 SYNTAX  INTEGER (1..6)
	 ACCESS  read-only
	 STATUS  mandatory
	 DESCRIPTION
		 "A number between 1 and 6, where the number is the number of the 
		 Unavailable Time Register."
	 ::= { sc5002NearEndUnavailableTimeRegEntry 2 }

 sc5002NearEndUnavailableTimeRegStart          OBJECT-TYPE
	SYNTAX  INTEGER (1..2147483647)
	ACCESS  read-only
	STATUS  mandatory
	DESCRIPTION
		"Start time of one of the Unavailable Time Registers."
	::= {sc5002NearEndUnavailableTimeRegEntry 3}

 sc5002NearEndUnavailableTimeRegStop          OBJECT-TYPE
	SYNTAX  INTEGER (1..2147483647)
	ACCESS  read-only
	STATUS  mandatory
	DESCRIPTION
		"Stop time of one of the Unavailable Time Registers."
	::= {sc5002NearEndUnavailableTimeRegEntry 4}

 -- ********************************************************************
 -- Unavailable Time Registers - Far end
 -- ********************************************************************

 sc5002FarEndUnavailableTimeRegTable     OBJECT-TYPE
	 SYNTAX  SEQUENCE OF Sc5002FarEndUnavailableTimeRegEntry
	 ACCESS  not-accessible
	 STATUS  mandatory
	 DESCRIPTION
		 "The sc5002 Unavailable Time Register table."

	 ::= { sc5002Performance 10 }


-- 
 sc5002FarEndUnavailableTimeRegEntry     OBJECT-TYPE
	 SYNTAX  Sc5002FarEndUnavailableTimeRegEntry
	 ACCESS  not-accessible
	 STATUS  mandatory
	 DESCRIPTION
		 "An entry in the Unavailable Time Register table."
	 INDEX   { sc5002FarEndUnavailableTimeRegIndex, sc5002FarEndUnavailableTimeRegNumber }
	 ::= { sc5002FarEndUnavailableTimeRegTable 1 }

 Sc5002FarEndUnavailableTimeRegEntry ::=
	 SEQUENCE {
		  sc5002FarEndUnavailableTimeRegIndex
			 SCinstance,
		  sc5002FarEndUnavailableTimeRegNumber
			 INTEGER,
		  sc5002FarEndUnavailableTimeRegStart
			 INTEGER,
		  sc5002FarEndUnavailableTimeRegStop
			 INTEGER
	  }

-- 
 sc5002FarEndUnavailableTimeRegIndex     OBJECT-TYPE
	 SYNTAX  SCinstance
	 ACCESS  read-only
	 STATUS  mandatory
	 DESCRIPTION
	 "Integer value which uniquely identifies the SC5002 to which this
    	  entry is applicable. SCinstance is defined to be ssllddcc where:
    	  ss (byte value) - physical shelf slot location (01-32)
    	  ll (byte value) - line number (01-128)
    	  dd (byte value) - drop number (00-31)
    	  cc (byte value) - channel or interface number (always 00)"
	 ::= { sc5002FarEndUnavailableTimeRegEntry 1 }

 sc5002FarEndUnavailableTimeRegNumber    OBJECT-TYPE
	 SYNTAX  INTEGER (1..6)
	 ACCESS  read-only
	 STATUS  mandatory
	 DESCRIPTION
		 "A number between 1 and 6, where the number is the number of the 
		 Unavailable Time Register."
	 ::= { sc5002FarEndUnavailableTimeRegEntry 2 }

 sc5002FarEndUnavailableTimeRegStart          OBJECT-TYPE
	SYNTAX  INTEGER (1..2147483647)
	ACCESS  read-only
	STATUS  mandatory
	DESCRIPTION
		"Start time of one of the Unavailable Time Registers."
	::= {sc5002FarEndUnavailableTimeRegEntry 3}

 sc5002FarEndUnavailableTimeRegStop          OBJECT-TYPE
	SYNTAX  INTEGER (1..2147483647)
	ACCESS  read-only
	STATUS  mandatory
	DESCRIPTION
		"Stop time of one of the Unavailable Time Registers."
	::= {sc5002FarEndUnavailableTimeRegEntry 4}


 -- ********************************************************************
 --                         Diagnostics Table
 -- ********************************************************************
 sc5002DiagTable OBJECT-TYPE
     SYNTAX SEQUENCE OF Sc5002DiagEntry
     ACCESS not-accessible
     STATUS mandatory
     DESCRIPTION
	 "The GDC 5002 Diagnostics table.  Information in the entries of
	 this table support diagnostics testing, both active testing
	 via patterns, and passive testing via loopbacks."
     ::= { sc5002Diagnostics 1 }

 sc5002DiagEntry OBJECT-TYPE
     SYNTAX Sc5002DiagEntry
     ACCESS not-accessible
     STATUS mandatory
     DESCRIPTION
	 "The GDC 5002 Diagnostics table entry."
     INDEX { sc5002DiagIndex }
     ::= { sc5002DiagTable 1 }

 Sc5002DiagEntry ::= 
     SEQUENCE {
	 sc5002DiagIndex      SCinstance,
	 sc5002LoopbackConfig INTEGER,
	 sc5002TestResult     INTEGER
     }

 sc5002DiagIndex OBJECT-TYPE
     SYNTAX SCinstance
     ACCESS read-only
     STATUS mandatory
     DESCRIPTION
    	"Integer value which uniquely identifies the SC5002 to which this
    	entry is applicable. SCinstance is defined to be ssllddcc where:
    	ss (byte value) - physical shelf slot location (01-32)
    	ll (byte value) - line number (01-128)
    	dd (byte value) - drop number (00-31)
    	cc (byte value) - channel or interface number (always 00)"
     ::= { sc5002DiagEntry 1 }

 sc5002LoopbackConfig OBJECT-TYPE
     SYNTAX INTEGER {
	 	     noLoopBack(1),
	 	     lineLoopBack(2),
	 	     unitTest(3)
                    }
     ACCESS read-write
     STATUS mandatory
     DESCRIPTION
		"Selects the test to run. 
		 A get of this object returns the test that is
		 currently running.  
		 A set of noLoopBack(1) ends the test that is 
		 currently running.  
		 A set of lineLoopBack(2) starts a line loop back test.
		 The line loop back test runs until a set of noLoopBack(1)
		 is sent.
		 A set of unitTest(3) starts a unit test.  The unit test
		 runs for 15 seconds."
	::= { sc5002DiagEntry 2 }

 sc5002TestResult  OBJECT-TYPE
     SYNTAX INTEGER {
			pass(1),
			fail(2)
		    }
     ACCESS read-only
     STATUS mandatory
     DESCRIPTION
	 "The results of the last diagnostic test completed.  The 
	  value returned is only valid if a get of 
	  sc5002LoopbackConfig returns noLoopBack(1)."
	::= { sc5002DiagEntry 3 }

-- ****************************************************************************
--                       mib definitions end
-- ****************************************************************************

END
