--
-- 1998, 1999, 2000 Shiva Corporation
--
-- Conformance statements for Shiva LanRover VPN Gateway and
-- LanRover VPN Express.
--

-- These conformance statements note what IETF MIBs, defined in the
-- SNMPv2-SMI syntax are implemented, are implemented.
-- The agent itself is an SNMPv1 agent.

SHIVA-LANROVER-VPN-GATEWAY-CAP DEFINITIONS ::= BEGIN

IMPORTS
    MODULE-IDENTITY
       FROM SNMPv2-SMI
    AGENT-CAPABILITIES
       FROM SNMPv2-CONF
    vpnLanRoverVPNGatewayCapabilities 
       FROM SHIVA-VPN-DEF;

shivaLanRoverVPNGatewayCapabilities MODULE-IDENTITY
    LAST-UPDATED	"9811052300Z"
    ORGANIZATION	"Shiva Corporation"
    CONTACT-INFO	"Shiva Corporation
			28 Crosby Drive
			Bedford, MA  01730"
    DESCRIPTION		"The Shiva LanRover VPN Gateway Capabilities module"
    REVISION		"9811052300Z"
    DESCRIPTION		"The initial revision of this module"
    ::= { vpnLanRoverVPNGatewayCapabilities 1 }
    

shivaLanRoverVPNGatewayAgent68 AGENT-CAPABILITIES
    PRODUCT-RELEASE "LanRover VPN Gateway 6.8"
    STATUS current
    DESCRIPTION
       "SNMP Agent implementation in LanRover VPN 
        Gateway and LanRover VPN Express 6.8 software.
	Describes only those MIBs that have SMIv2 MODULE-COMPLIANCE 
	macro."

    -- RFC 1573
    --
    SUPPORTS IF-MIB
        INCLUDES	{ ifGeneralGroup, ifPacketGroup }

	VARIATION	ifAdminStatus
            ACCESS	read-only
	    DESCRIPTION	"No write access allowed via SNMP."

	VARIATION	ifLinkUpDownTrapEnable
	    SYNTAX	INTEGER { disabled(2) }
	    ACCESS	read-only
	    DESCRIPTION "Write access is not required."

	VARIATION	ifPromiscuousMode
	    ACCESS	read-only
	    DESCRIPTION "Write access is not required."

	VARIATION	linkUp
	    ACCESS	not-implemented
	    DESCRIPTION	"Not implemented."
	
	VARIATION	linkDown
	    ACCESS	not-implemented
	    DESCRIPTION	"Not implemented."

    -- draft-ietf-ifmib-tunnel-mib-02.txt
    --
    -- Can't really cite it here, since the MODULE-IDENTITY has
    -- a name starting with a lower case letter, which is illegal.
    -- This leads to a black hole of errors in SMICng...

    SUPPORTS TUNNEL-MIB
            INCLUDES	{ tunnelMIBBasicGroup }

	VARIATION	tunnelIfHopLimit
	    ACCESS	read-only
	    DESCRIPTION "Write access is not required."

	VARIATION	tunnelIfPriority
	    ACCESS	read-only
	    DESCRIPTION "Write access is not required."

	VARIATION	tunnelIfEncapsLimit
	    ACCESS	read-only
	    DESCRIPTION "Write access is not required."

	VARIATION	tunnelConfigStatus
	    ACCESS	read-only
	    DESCRIPTION "Write access is not required."

    -- Implements MIB-II (RFC 1213).

    -- Also implements RFC 1354, the IP Forwarding Table MIB (SMIv1).
    -- (This will probably be replaced by the more appropriate RFC 2096
    -- in a future release.)

    ::= { vpnLanRoverVPNGatewayCapabilities 68 }


shivaLanRoverVPNGatewayAgent67 AGENT-CAPABILITIES
    PRODUCT-RELEASE "LanRover VPN Gateway 6.7"
    STATUS current
    DESCRIPTION
       "SNMP Agent implementation in LanRover VPN 
        Gateway and LanRover VPN Express 6.7 software.
	Describes only those MIBs that have SMIv2 MODULE-COMPLIANCE 
	macro."

    -- RFC 1573
    --
    SUPPORTS IF-MIB
        INCLUDES	{ ifGeneralGroup, ifPacketGroup }

	VARIATION	ifAdminStatus
            ACCESS	read-only
	    DESCRIPTION	"No write access allowed via SNMP."

	VARIATION	ifLinkUpDownTrapEnable
	    SYNTAX	INTEGER { disabled(2) }
	    ACCESS	read-only
	    DESCRIPTION "Write access is not required."

	VARIATION	ifPromiscuousMode
	    ACCESS	read-only
	    DESCRIPTION "Write access is not required."

	VARIATION	linkUp
	    ACCESS	not-implemented
	    DESCRIPTION	"Not implemented."
	
	VARIATION	linkDown
	    ACCESS	not-implemented
	    DESCRIPTION	"Not implemented."

    -- draft-ietf-ifmib-tunnel-mib-02.txt
    --
    -- Can't really cite it here, since the MODULE-IDENTITY has
    -- a name starting with a lower case letter, which is illegal.
    -- This leads to a black hole of errors in SMICng...

    SUPPORTS TUNNEL-MIB
            INCLUDES	{ tunnelMIBBasicGroup }

	VARIATION	tunnelIfHopLimit
	    ACCESS	read-only
	    DESCRIPTION "Write access is not required."

	VARIATION	tunnelIfPriority
	    ACCESS	read-only
	    DESCRIPTION "Write access is not required."

	VARIATION	tunnelIfEncapsLimit
	    ACCESS	read-only
	    DESCRIPTION "Write access is not required."

	VARIATION	tunnelConfigStatus
	    ACCESS	read-only
	    DESCRIPTION "Write access is not required."

    -- Implements MIB-II (RFC 1213).

    -- Also implements RFC 1354, the IP Forwarding Table MIB (SMIv1).
    -- (This will probably be replaced by the more appropriate RFC 2096
    -- in a future release.)

    ::= { vpnLanRoverVPNGatewayCapabilities 67 }


shivaLanRoverVPNGatewayAgent66 AGENT-CAPABILITIES
    PRODUCT-RELEASE "LanRover VPN Gateway 6.6"
    STATUS current
    DESCRIPTION
       "SNMP Agent implementation in LanRover VPN 
        Gateway and LanRover VPN Express 6.6 software.
	Describes only those MIBs that have SMIv2 MODULE-COMPLIANCE 
	macro."

    -- RFC 1573
    --
    SUPPORTS IF-MIB
        INCLUDES	{ ifGeneralGroup, ifPacketGroup }

	VARIATION	ifAdminStatus
            ACCESS	read-only
	    DESCRIPTION	"No write access allowed via SNMP."

	VARIATION	ifLinkUpDownTrapEnable
	    SYNTAX	INTEGER { disabled(2) }
	    ACCESS	read-only
	    DESCRIPTION "Write access is not required."

	VARIATION	ifPromiscuousMode
	    ACCESS	read-only
	    DESCRIPTION "Write access is not required."

	VARIATION	linkUp
	    ACCESS	not-implemented
	    DESCRIPTION	"Not implemented."
	
	VARIATION	linkDown
	    ACCESS	not-implemented
	    DESCRIPTION	"Not implemented."

    -- draft-ietf-ifmib-tunnel-mib-02.txt
    --
    -- Can't really cite it here, since the MODULE-IDENTITY has
    -- a name starting with a lower case letter, which is illegal.
    -- This leads to a black hole of errors in SMICng...

    SUPPORTS TUNNEL-MIB
            INCLUDES	{ tunnelMIBBasicGroup }

	VARIATION	tunnelIfHopLimit
	    ACCESS	read-only
	    DESCRIPTION "Write access is not required."

	VARIATION	tunnelIfPriority
	    ACCESS	read-only
	    DESCRIPTION "Write access is not required."

	VARIATION	tunnelIfEncapsLimit
	    ACCESS	read-only
	    DESCRIPTION "Write access is not required."

	VARIATION	tunnelConfigStatus
	    ACCESS	read-only
	    DESCRIPTION "Write access is not required."

    -- Implements MIB-II (RFC 1213).

    -- Also implements RFC 1354, the IP Forwarding Table MIB (SMIv1).
    -- (This will probably be replaced by the more appropriate RFC 2096
    -- in a future release.)

    ::= { vpnLanRoverVPNGatewayCapabilities 66 }


shivaLanRoverVPNGatewayAgent65 AGENT-CAPABILITIES
    PRODUCT-RELEASE "LanRover VPN Gateway 6.5"
    STATUS current
    DESCRIPTION
       "SNMP Agent implementation in LanRover VPN 
        Gateway 6.5 software.  Describes only those 
        MIBs that have SMIv2 MODULE-COMPLIANCE macro."

    -- RFC 1573
    --
    SUPPORTS IF-MIB
        INCLUDES	{ ifGeneralGroup, ifPacketGroup }

	VARIATION	ifAdminStatus
            ACCESS	read-only
	    DESCRIPTION	"No write access allowed via SNMP."

	VARIATION	ifLinkUpDownTrapEnable
	    SYNTAX	INTEGER { disabled(2) }
	    ACCESS	read-only
	    DESCRIPTION	"No write access allowed via SNMP.  These
			traps presently not implemented."

	VARIATION	ifPromiscuousMode
	    ACCESS	read-only
	    DESCRIPTION	"No write access allowed via SNMP."

	VARIATION	linkUp
	    ACCESS	not-implemented
	    DESCRIPTION	"Not implemented."
	
	VARIATION	linkDown
	    ACCESS	not-implemented
	    DESCRIPTION	"Not implemented."

    -- Implements MIB-II (RFC 1213).

    -- Also implements RFC 1354, the IP Forwarding Table MIB (SMIv1).

    ::= { vpnLanRoverVPNGatewayCapabilities 65 }

END
