STORMSHIELD-POLICY-MIB DEFINITIONS ::= BEGIN

   IMPORTS
      MODULE-IDENTITY, OBJECT-TYPE, Integer32   FROM SNMPv2-SMI
      DisplayString                             FROM RFC1213-MIB
      SnmpAdminString                           FROM SNMP-FRAMEWORK-MIB
      stormshieldMIB                            FROM STORMSHIELD-SMI-MIB;

   snsPolicy MODULE-IDENTITY
      LAST-UPDATED  "201702200000Z"
      ORGANIZATION  "Stormshield"
      CONTACT-INFO
         "Customer Support

         22 rue du Gouverneur General Eboue
         92130 Issy-les-Moulineaux
         FRANCE

         Tel: +33 (0)9 69 32 96 29
         E-mail: support@stormshield.eu
         http://www.stormshield.eu"
      DESCRIPTION   "stormshield policies"
      REVISION      "201702200000Z"
      DESCRIPTION   "Initial"
      ::= { stormshieldMIB 8 }

   snsPolicyTable OBJECT-TYPE
      SYNTAX SEQUENCE OF SnsPolicyEntry
      MAX-ACCESS not-accessible
      STATUS current
      DESCRIPTION "List of policies"
         ::= { snsPolicy 1 }

   snsPolicyEntry OBJECT-TYPE
      SYNTAX SnsPolicyEntry
      MAX-ACCESS not-accessible
      STATUS current
      DESCRIPTION
         "Each entry in the snsPolicyTable holds a set of information (name, active index)."
      INDEX  { snsPolicyIndex }
      ::= { snsPolicyTable 1 }

   SnsPolicyEntry ::= SEQUENCE {
          snsPolicyIndex         INTEGER,
         snsPolicyName            SnmpAdminString,
         snsPolicySlotName            SnmpAdminString,
         snsPolicyActive            DisplayString,
         snsPolicySync            Integer32
      }

   snsPolicyIndex OBJECT-TYPE
      SYNTAX INTEGER (1..65535)
      MAX-ACCESS read-only
      STATUS current
      DESCRIPTION
         "A unique value for the table. Its value
         ranges between 1 and 65535 and may not be contigous.
         the index has no other meaning but a pure index"
      ::= { snsPolicyEntry 1 }

    snsPolicyName OBJECT-TYPE
      SYNTAX SnmpAdminString
      MAX-ACCESS read-only
      STATUS current
      DESCRIPTION "Policy name"
      ::= { snsPolicyEntry 2 }

    snsPolicySlotName OBJECT-TYPE
      SYNTAX SnmpAdminString
      MAX-ACCESS read-only
      STATUS current
      DESCRIPTION "Slot name"
      ::= { snsPolicyEntry 3 }

   snsPolicyActive OBJECT-TYPE
      SYNTAX DisplayString
      MAX-ACCESS read-only
      STATUS current
      DESCRIPTION
         "Index of the currently active slot for the current policy"
      ::= { snsPolicyEntry 4 }

   snsPolicySync OBJECT-TYPE
      SYNTAX Integer32
      MAX-ACCESS read-only
      STATUS current
      DESCRIPTION "Sync"
	  ::= { snsPolicyEntry 5 }

END
