--
-- 	Copyright 1992, 1993, 1995, 1996, 1999 Shiva Corporation
--

SHIVA-LINETEST-MIB DEFINITIONS ::= BEGIN

IMPORTS
	Counter
		FROM RFC1155-SMI
	OBJECT-TYPE
		FROM RFC-1212		-- Concise MIB Definitions
	lineTest
		FROM SHIVA-MIB;

-- MIB for the line test functions which allow a range of loopback
-- tests to be performed on the individual lines or pairs of lines.

-- This MIB is only implemented on the LanRover/E XP16.  There are
-- no plans to implement it on any other platforms.

-- It is admitted that these tests should have been controlled by
-- the ifTestTable defined in RFC 1573.  But they are not.  There
-- will be serious problems if multiple managers attempt to use this
-- MIB at the same time.

    lineTestType OBJECT-TYPE
	SYNTAX 	INTEGER {
		loopback(1),
		at(2),
		dialpair(3)
	 }
	ACCESS	read-write
	STATUS	mandatory
	DESCRIPTION
		"Line test being performed."
	::= { lineTest 1  }

    lineTestOriginate OBJECT-TYPE
	SYNTAX 	INTEGER (1..16)
	ACCESS 	read-write
	STATUS	mandatory
	DESCRIPTION
		"For a single port test this variable is set 
		to the number of the port being tested. In a 
		pair dial test this variable is set to the 
		number of the calling port." 
	::= { lineTest 2 }

    lineTestTerminate OBJECT-TYPE
	SYNTAX 	INTEGER (1..16)
	ACCESS 	read-write
	STATUS	mandatory
	DESCRIPTION
		"In a pair dial test this variable is set to 
		the number of the called port." 
	::= { lineTest 3 }

    lineTestNumber OBJECT-TYPE
	SYNTAX	OCTET STRING(SIZE(64))
	ACCESS  read-write
	STATUS	mandatory
	DESCRIPTION
		"Number to dial for test."
	::= { lineTest 4 }

    lineTestLength OBJECT-TYPE
	SYNTAX	INTEGER(1..4294967295)
	ACCESS 	read-write
	STATUS 	mandatory
	DESCRIPTION
		"Data length of line test."
	::= { lineTest 5 }

    lineTestInitiate OBJECT-TYPE
	SYNTAX	INTEGER {
		start(1),
		end(2)
	 }
	ACCESS	read-write
	STATUS 	mandatory
	DESCRIPTION
		"Control variable to start and end the test."
	::= { lineTest 6 }

    lineTestConnect OBJECT-TYPE
	SYNTAX	Counter
	ACCESS	read-only
	STATUS 	mandatory
	DESCRIPTION
		"Connect speed indication for pair dial test."
	::= { lineTest 7 }

    lineTestBytesTx OBJECT-TYPE
	SYNTAX	Counter
	ACCESS	read-only
	STATUS 	mandatory
	DESCRIPTION
		"Bytes transmitted during test."
	::= { lineTest 8 }

    lineTestBytesRx OBJECT-TYPE
	SYNTAX	Counter
	ACCESS	read-only
	STATUS 	mandatory
	DESCRIPTION
		"Bytes received during test."
	::= { lineTest 9 }

    lineTestSuccess OBJECT-TYPE
	SYNTAX	INTEGER {
		testing(1),
		pass(2),
		failnomodem(3),
		faildial(4),
		failconnect(5),
		faildata(6)
	 }
	ACCESS	read-only
	STATUS 	mandatory
	DESCRIPTION
		"Pass fail indication for test."
	::= { lineTest 10 }

END
