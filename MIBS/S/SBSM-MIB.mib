-- extracted from draft-hardaker-snmp-session-sm-03.txt
-- at Tue Oct 19 06:23:45 2004

   SBSM-MIB DEFINITIONS ::= BEGIN


   IMPORTS
       MODULE-IDENTITY, OBJECT-TYPE, NOTIFICATION-TYPE, Integer32,
       Unsigned32, Counter32, experimental               FROM SNMPv2-SMI


       TEXTUAL-CONVENTION
                                           FROM SNMPv2-TC


       MODULE-COMPLIANCE, OBJECT-GROUP, NOTIFICATION-GROUP
                                           FROM SNMPv2-CONF


       InetAddressType, InetAddress, InetPortNumber
                                           FROM INET-ADDRESS-MIB
   ;


   --
   -- module identity
   --


   sbsmMIB MODULE-IDENTITY
       LAST-UPDATED "200402150000Z"
       ORGANIZATION "IETF non-existent SBSM Working Group"
       CONTACT-INFO "Wes Hardaker
                     Sparta, Inc.
                     P.O. Box 382
                     Davis, CA  95617
                     Phone: +1 530 792 1913
                     Email: hardaker@tislabs.com"
       DESCRIPTION
        "This MIB module defines objects for managing the SNMPv3 SBSM
        security module.


         Copyright (C) The Internet Society (2004). This version of
         this MIB module is part of RFC XXXX, see the RFC itself for
         full legal notices."


   -- Revision History
       REVISION     "200402150000Z"
       DESCRIPTION  "Initial version, published as RFC xxxx."
       -- RFC-editor assigns xxxx


   -- XXX: To be assigned by IANA
       ::= { experimental 1 }


   --
   -- groups of related objects
   --


   sbsmObjects         OBJECT IDENTIFIER
        ::= { sbsmMIB 1 }
   sbsmNotificationObjects   OBJECT IDENTIFIER
        ::= { sbsmMIB 2 }
   sbsmConformanceObjects    OBJECT IDENTIFIER
        ::= { sbsmMIB 3 }


   --
   -- Textual Conventions
   --


   sbsmCounterObjects OBJECT IDENTIFIER ::= { sbsmObjects 1 }
   sbsmSessionObjects OBJECT IDENTIFIER ::= { sbsmObjects 2 }
   sbsmCompressionDefinitions
      OBJECT IDENTIFIER ::= { sbsmObjects 3 }


   --
   -- Counter objects
   --
   sbsmSessionsEstablished OBJECT-TYPE
       SYNTAX      Counter32
       MAX-ACCESS  read-only
       STATUS      current
       DESCRIPTION
           ""
       ::= { sbsmCounterObjects 1}


   sbsmStatsUnsupportedSecLevels OBJECT-TYPE
       SYNTAX      Counter32
       MAX-ACCESS  read-only
       STATUS      current
       DESCRIPTION
           ""
       ::= { sbsmCounterObjects 2}


   sbsmStatsDecryptionErrors OBJECT-TYPE
       SYNTAX      Counter32
       MAX-ACCESS  read-only
       STATUS      current
       DESCRIPTION
           ""
       ::= { sbsmCounterObjects 3}


   sbsmStatsCompressionErrors OBJECT-TYPE
       SYNTAX      Counter32
       MAX-ACCESS  read-only
       STATUS      current
       DESCRIPTION
           ""
       ::= { sbsmCounterObjects 4}


   sbsmProtocolError OBJECT-TYPE
       SYNTAX      Counter32
       MAX-ACCESS  read-only
       STATUS      current
       DESCRIPTION
           ""
       ::= { sbsmCounterObjects 5}


   sbsmStatsWrongDigests OBJECT-TYPE
       SYNTAX      Counter32
       MAX-ACCESS  read-only
       STATUS      current
       DESCRIPTION
           ""
       ::= { sbsmCounterObjects 6}


   --
   -- Established sessions
   --


   sbsmSessionTable OBJECT-TYPE
       SYNTAX      SEQUENCE OF SbsmSessionEntry
       MAX-ACCESS  not-accessible
       STATUS      current
       DESCRIPTION
           "A table describing currenly open, currently being established
           or recently closed SBSM sessions."
       ::= { sbsmSessionObjects 1 }


   sbsmSessionEntry OBJECT-TYPE
       SYNTAX      SbsmSessionEntry
       MAX-ACCESS  not-accessible
       STATUS      current
       DESCRIPTION
           ""
       INDEX   { sbsmId }
       ::= { sbsmSessionTable 1 }


   SbsmSessionEntry ::= SEQUENCE {
       sbsmId            Unsigned32
   }


   sbsmId OBJECT-TYPE
       SYNTAX      Unsigned32
       MAX-ACCESS  read-only
       STATUS      current
       DESCRIPTION
           ""
       ::= { sbsmSessionEntry 1 }



   -- remote ID, state, alg types in use, started when, misc counters, ...
   -- (suggestions welcome)


   --
   -- Compression algorithms
   --
   sbsmNullCompressionAlgorithm
       OBJECT IDENTIFIER ::= { sbsmCompressionDefinitions 1 }


   sbsmGZipCompressionAlgorithm
       OBJECT IDENTIFIER ::= { sbsmCompressionDefinitions 1 }


   sbsmBZip2CompressionAlgorithm
       OBJECT IDENTIFIER ::= { sbsmCompressionDefinitions 1 }


   --
   -- other MIB items to do:
   --
   -- o notifications
   -- o configuration of policy.  eg: user A using algorthim B/C
   --   is different than user X using Y/Z.




   END

-- 
-- 
--    Copyright (C) The Internet Society (2004).  This document is subject
--    to the rights, licenses and restrictions contained in BCP 78, and
--    except as set forth therein, the authors retain all their rights.
-- 
-- 
-- 
-- Acknowledgment
-- 
-- 
--    Funding for the RFC Editor function is currently provided by the
--    Internet Society.
