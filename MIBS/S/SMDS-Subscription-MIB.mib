SMDS-Subscription-MIB DEFINITIONS ::= BEGIN

               IMPORTS
                       enterprises, Counter, TimeTicks
                               FROM RFC1155-SMI
                       DisplayString, ifIndex
                               FROM RFC1213-MIB
                       OBJECT-TYPE
                               FROM RFC-1212
                       TRAP-TYPE
                               FROM RFC-1215;

               --  This MIB module uses the extended OBJECT-TYPE macro as
               --  defined in RFC1212 and the TRAP-TYPE macro as
               --  defined in RFC1215.

               --  This is the MIB module for the SMDS Subscription related objects.

               bellcore         OBJECT IDENTIFIER ::= { enterprises 148 }
               requirements     OBJECT IDENTIFIER ::= { bellcore 1 }
               taTsv001062      OBJECT IDENTIFIER ::= { requirements 1 }
               smdsSubscr       OBJECT IDENTIFIER ::= { taTsv001062 2 }

               -- This is version 2.1 of this MIB module and obsoletes version 1.0
               -- and version 2.0.

               -- All representations of SMDS addresses in this MIB module use,
               -- as a textual convention (i.e., this convention does not affect
               -- their encoding), the data type:

               SMDSAddress ::= OCTET STRING (SIZE (8))
               -- the 60-bit SMDS address, preceded by 4 bits with the
               -- following values:
               -- "1100" when representing an individual address
               -- "1110" when representing a group address

               -- This MIB is divided into six MIB modules:  SMDS Subscription
               -- Parameters and Violations Group, SMDS Address Table Group, Address Screening
               -- Group, Group Addressing Information Group, Service Disagreements Group,
               -- and Exchange Access Component of Inter-exchange SMDS Group.

               -- The SMDS Subscription Parameter and Violations Group contains the SNI's
               -- service related information (e.g., Access Class and Maximum Concurrent Data Units







               -- In and Out) along with counts of SIP L3_PDUs that were discarded because of
               -- a service violation (e.g., exceeded the subscribed to access class).

               -- The SMDS Address Table Group contains the mapping between SMDS Addresses
               -- and the ifIndex for an SNI.  An SNI may have up to 16 addresses assigned to it.

               -- The Address Screening Group is a collection of six tables.  These six tables
               -- are used to identify up to 4 Individual Address Screens and up to 4 Group
               -- Address Screens.  Two tables are used to identify all the screens (i.e., there
               -- may be up to 8 screens) and the default screens for each SNI.  New screens can
               -- be created and deleted by using these tables.  The default screens may be
               -- changed also.  The Associated
               -- Addresses Group is used to associate the addresses assigned to the SNI to a particular
               -- individual address screen and a particular group address screen.
               -- This information is read/writable. The Screened
               -- Addresses Group identifies the addresses to be screened (i.e., whether you want
               -- to receive SIP L3_PDUs from or send them to a particular address) within the Individual
               -- Address Screens (up to 4) and the Group Address Screens (up to 4).  This information
               -- is read/writable.

               -- The Group Addressing Information Group is a collection of 5 tables.  The
               -- Group Address Group identifies the group address and the individual addresses
               -- that are identified by the group address, and this group also
               -- provides the number of individual addresses
               -- that are associated with the group address.  New individual addresses can be identified
               -- by the group address by adding it to this table, and addresses can also be deleted
               -- from this table.  Only the owner of the group address has read/write access on this
               -- information.  Members of the group address have only read access.
               -- New group addresses can not be created by using this table, new group
               -- addresses can only be assigned by the service provider.
               -- The Member Group Address Group identifies
               -- the individual address and all of the group addresses with which it is associated.
               -- Using this table, the group addresses can only be disassociated from the individual
               -- addresses; meaning that the group member may only delete the row and not create a new row
               -- in this table.  This capability is under study.
               -- Allowing the group member to disassociate their individual address from
               -- This group also provides the number of group addresses an individual address belongs and
               -- the number of group addresses that are assigned to each SNI.

               -- The Service Disagreement Group provides the latest occurrences of SIP L3_PDUs
               -- that were discarded because of particular service violations.  This information is provided
               -- in a log format.

               -- The Exchange Access Component of Inter-exchange SMDS Group is divided into
               -- three groups; the Exchange Access SMDS Subscription Parameters and Violations







               -- Group, the Carrier Blocking Group, and the Carrier Index Group.  The Exchange
               -- Access SMDS Subscription Parameters and Violations Group provides subscription
               -- parameter information (e.g., the Carrier selected to provide Exchange Access SMDS for this
               -- SNI) and counts of violations.  The Carrier Blocking Group provides information on the carriers
               -- that are blocking an SNI and the number of packets that were discarded per carrier.  The
               -- Carrier Index Group associates the carrier's interface(s) to the SMDS network as one
               -- interface and assigns an ifIndex to it.













































               -- The SMDS Subscription Parameters and
               -- Violations Group
               -- Implementation of this group is mandatory
               -- if providing SMDS CNM.
               -- Although some of the objects in this group are read-write,
               -- the write-capability is not supported by the agent.
               -- However, in the future, the management station when
               -- authorized may change the values for
               -- smdsMCDUsIn and
               -- smdsMCDUsOut.
               -- Assuming that the objects are in the customer's MIB
               -- View and the Access Control Table allows read-write access,
               -- in the mean time, the agent will return badValue for
               -- any Secure SNMP SET-Request on a read-write object.  The agent
               -- will return noSuchName for community-string based SET-Request on a
               -- read-write object.

               smdsSubscrTable  OBJECT-TYPE
                           SYNTAX  SEQUENCE OF SmdsSubscrEntry
                           ACCESS  not-accessible
                           STATUS  mandatory
                           DESCRIPTION
                                  "This table contains Subscriber-Network
                                  Interface (SNI)
                                  parameters and state variables, one entry
                                  per SIP port."
                           ::= { smdsSubscr 1 }

               smdsSubscrEntry  OBJECT-TYPE
                           SYNTAX  SmdsSubscrEntry
                           ACCESS  not-accessible
                           STATUS  mandatory
                           DESCRIPTION
                                  "This list contains Subscriber-Network
                                  Interface (SNI)
                                  parameters and state variables."
                           INDEX   { smdsSubscrIndex }
                          ::= { smdsSubscrTable 1 }

               SmdsSubscrEntry  ::= SEQUENCE {
                                  smdsSubscrIndex
                                      INTEGER,
                                  smdsContact
                                      DisplayString,
                                  smdsSNILocation







                                      DisplayString,
                                  smdsAccessClass
                                      INTEGER,
                                  smdsMCDUsIn
                                      INTEGER,
                                  smdsMCDUsInChange
                                      INTEGER,
                                  smdsMCDUsOut
                                      INTEGER,
                                  smdsMCDUsOutChange
                                      INTEGER,
                                  smdsUnassignedSAs
                                      Counter,
                                  smdsAccessClassExceededCounts
                                      Counter,
                                  smdsSAScreenViolations
                                      Counter,
                                  smdsDAScreenViolations
                                      Counter,
                                  smdsMCDUsExceededAtIngressCounts
                                      Counter,
                                  smdsMCDUsExceededAtEgressCounts
                                      Counter,
                                  smdsAddressCodes
                                      DisplayString
                              }


               smdsSubscrIndex  OBJECT-TYPE
                         SYNTAX  INTEGER (1..65535)
                         ACCESS  read-only
                         STATUS  mandatory
                         DESCRIPTION
                                "The value of this object identifies the
                                SIP port
                                interface for which this entry contains
                                management
                                information.  The value of this object
                                for a
                                particular interface has the same value
                                as the
                                ifIndex object, defined in RFC1213, for
                                the same
                                interface."
                         ::= { smdsSubscrEntry 1 }







               smdsContact OBJECT-TYPE
                   SYNTAX  DisplayString (SIZE(0..255))
                   ACCESS  read-only
                   STATUS  mandatory
                   DESCRIPTION
                           "The textual identification of the contact
                           person(s) or organization(s) for the
                           subscriber of this managed SNI, together with
                           information on how to contact this person or
                           organization (e.g., BCC information telephone
                           number, or email address)."
                  ::= { smdsSubscrEntry 2 }

              smdsSNILocation OBJECT-TYPE
                  SYNTAX  DisplayString (SIZE(0..255))
                  ACCESS  read-only
                  STATUS  mandatory
                  DESCRIPTION
                          "The physical location of the termination
                          point for this SNI on the Switching System
                          (e.g., CO Location)."
                 ::= { smdsSubscrEntry 3 }

             smdsAccessClass OBJECT-TYPE
                 SYNTAX INTEGER {
                        noClass (1),
                        class4  (2),
                        class10 (3),
                        class16 (4),
                        class25 (5),
                        class34 (6)
                 }
                 ACCESS  read-only
                 STATUS  mandatory
                 DESCRIPTION
                         "The currently subscribed-to access class for
                         this SNI.  For a DS3-based access path, the
                         value for this information indicates access
                         class and the Sustained Information Rate in
                         Mbps {4, 10, 16, 25, 34}.  There is no Access
                         Class enforcement for DS1-based access paths
                         and hence no related information (i.e.,
                         noClass)."
                ::= { smdsSubscrEntry 4 }








            smdsMCDUsIn OBJECT-TYPE
                SYNTAX INTEGER {
                       mcdusIn1 (1),
                       mcdusIn16 (2)
                }
                ACCESS  read-only
                STATUS  mandatory
                DESCRIPTION
                        "The maximum number of SMDS data units that may
                        be transferred concurrently over the SNI to the
                        SMDS SS.   Values can be 1 or 16."
               ::= { smdsSubscrEntry 5 }

           smdsMCDUsInChange OBJECT-TYPE
               SYNTAX INTEGER {
                      mcdusIn1 (1),
                      mcdusIn16 (2)
               }
               ACCESS  read-write
               STATUS  mandatory
               DESCRIPTION
                       "This object is used to change the value of
                       smdsMCDUsIn.  When the values of this object and
                       smdsMCDUsIn are equal, then no change is being
                       processed by the agent.  If they are not equal,
                       then the agent is processing a requested change.
                       The agent may refuse the change to be made and
                       thus return the value for smdsMCDUsInChange to
                       its previous value which is equal to the
                       smdsMCDUsIn value.  If the agent accepts the
                       change, the smdsMCDUsIn value will be set equal
                       to the smdsMCDUsInChange value.  The maximum
                       number of SMDS data units that may be transferred
                       concurrently over the SNI to the SMDS SS.
                       Values can be 1 or 16."
              ::= { smdsSubscrEntry 6 }

          smdsMCDUsOut OBJECT-TYPE
              SYNTAX INTEGER {
                     mcdusOut1 (1),
                     mcdusOut16 (2)
              }
              ACCESS  read-only
              STATUS  mandatory
              DESCRIPTION







                      "The maximum number of SMDS data units that may be
                      transferred concurrently over the SNI from the
                      SMDS SS.   Values can be 1 or 16."
              ::= { smdsSubscrEntry 7 }

          smdsMCDUsOutChange OBJECT-TYPE
              SYNTAX INTEGER {
                     mcdusOut1 (1),
                     mcdusOut16 (2)
              }
              ACCESS  read-write
              STATUS  mandatory
              DESCRIPTION
                      "This object is used to change the value of
                      smdsMCDUsOut.  When the values of this object and
                      smdsMCDUsOut are equal, then no change is being
                      processed by the agent.  If they are not equal,
                      then the agent is processing a requested change.
                      The agent may refuse the change to be made and
                      thus return the value for smdsMCDUsOutChange to
                      its previous value which is equal to the
                      smdsMCDUsOut value.  If the agent accepts the
                      change, the smdsMCDUsOut value will be set equal
                      to the smdsMCDUsOutChange value.  The maximum
                      number of SMDS data units that may be transferred
                      concurrently over the SNI from the SMDS SS.
                      Values can be 1 or 16."
              ::= { smdsSubscrEntry 8 }

          smdsUnassignedSAs OBJECT-TYPE
              SYNTAX  Counter
              ACCESS  read-only
              STATUS  mandatory
              DESCRIPTION
                      "The number of SIP L3_PDUs that have been
                      discarded by the SMDS SS because the source
                      addresses were not assigned to the SNI."
              ::= { smdsSubscrEntry 9 }

          smdsAccessClassExceededCounts OBJECT-TYPE
              SYNTAX  Counter
              ACCESS  read-only
              STATUS  mandatory
              DESCRIPTION
                      "A count of the number of L3_PDUs that were







                      discarded because the access class for this SNI
                      has been exceeded."
              ::= { smdsSubscrEntry 10 }

          smdsSAScreenViolations OBJECT-TYPE
              SYNTAX  Counter
              ACCESS  read-only
              STATUS  mandatory
              DESCRIPTION
                      "The number of SIP L3_PDUs  that violated the
                      address screen based on source address screening
                      for an SNI."
              ::= { smdsSubscrEntry 11 }

          smdsDAScreenViolations OBJECT-TYPE
              SYNTAX  Counter
              ACCESS  read-only
              STATUS  mandatory
              DESCRIPTION
                      "The number of SIP L3_PDUs  that violated the
                      address screen based on destination address
                      screening for an SNI."
              ::= { smdsSubscrEntry 12 }

          smdsMCDUsExceededAtIngressCounts OBJECT-TYPE
              SYNTAX  Counter
              ACCESS  read-only
              STATUS  mandatory
              DESCRIPTION
                      "The number of L3_PDUs that were discarded because
                      the MCDU was exceeded in the CPE to SMDS SS
                      direction."
              ::= { smdsSubscrEntry 13 }

          smdsMCDUsExceededAtEgressCounts OBJECT-TYPE
              SYNTAX  Counter
              ACCESS  read-only
              STATUS  mandatory
              DESCRIPTION
                      "The number of L3_PDUs that were discarded because
                      the MCDU was exceeded in the SMDS SS to CPE
                      direction."
              ::= { smdsSubscrEntry 14 }

          smdsAddressCodes OBJECT-TYPE







              SYNTAX  DisplayString (SIZE(0..255))
              ACCESS  read-only
              STATUS  mandatory
              DESCRIPTION
                      "This object provides hints on how an SMDS Address
                      is divided into three fields.  These three fields
                      are used as indices into tables that need to be
                      indexed by an SMDS address.  These three fields
                      provide for a user-friendly/readable format in
                      order to do SETs and GETs.  The three fields are
                      country code, destination code, and subscriber
                      number.  Each field MUST only contain 1 to 9
                      digits and must NOT start with a zero.  All SMDS
                      addresses will have a country code.  Most SMDS
                      addresses will have a destination code (e.g., in
                      the US this number is the area code).  The
                      subscriber number is the rest of the SMDS address,
                      which is less than or equal to the remaining 9
                      digits.  For those SMDS addresses that do not have
                      a destination code or whose subscriber number is
                      more than 9 digits long, the destination code and
                      the subscriber number must be divided in a logical
                      way. Also, if a field starts with zero(s), then
                      these zero(s) must be the trailing zero(s) of the
                      previous field.  It is up to the service provider
                      to determine this logic.  This object describes
                      the way that the SMDS addresses are divided for
                      this SNI (ifIndex).  For example, in the US, this
                      object will contain the following text:  'Country
                      code = 1. Destination code = area code (e.g.,
                      908). Subscriber number = the remaining 7 digits
                      (e.g., 7582107). The OID looks like
                      objectName.1.908.7582107 and the SMDSAddress =
                      C19087582107FFFF in Hex'."
              ::= { smdsSubscrEntry 15 }

















          -- The SMDS Address Table Group
          -- Implementation of this group
          -- is mandatory if providing SMDS CNM.

          subscriberAddressesTable  OBJECT-TYPE
              SYNTAX  SEQUENCE OF SubscriberAddressesEntry
              ACCESS  not-accessible
              STATUS  mandatory
              DESCRIPTION
                      "This table contains the SMDS addresses assigned
                      to each SNI (up to 16 addresses per SNI)."
              ::= { smdsSubscr 2 }

          subscriberAddressesEntry  OBJECT-TYPE
              SYNTAX  SubscriberAddressesEntry
              ACCESS  not-accessible
              STATUS  mandatory
              DESCRIPTION
                      "A valid SMDS individual address for this SNI and
                      an SNI index."
              INDEX   { subCountryCodeIndex, subDestinationCodeIndex,
                        subSubscriberNumberIndex }
              ::= { subscriberAddressesTable 1 }

          SubscriberAddressesEntry  ::= SEQUENCE {
              subCountryCodeIndex
                  INTEGER,
              subDestinationCodeIndex
                  INTEGER,
              subSubscriberNumberIndex
                  INTEGER,
              subscriberAddressesOnSNI
                  SMDSAddress,
              subscriberAddressesIndex
                  INTEGER
              }

          subCountryCodeIndex OBJECT-TYPE
              SYNTAX  INTEGER (1..4294967295)
              ACCESS  read-only
              STATUS  mandatory
              DESCRIPTION
                      "The country code portion of the SMDS Address.
                      For example, the country code of North America is
                      (1), the UK is (44), and Germany is (49)."







              ::= { subscriberAddressesEntry 1 }

          subDestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.
                      See smdsAddressCodes object."
              ::= { subscriberAddressesEntry 2 }

          subSubscriberNumberIndex OBJECT-TYPE
              SYNTAX  INTEGER (1..4294967295)
              ACCESS  read-only
              STATUS  mandatory
              DESCRIPTION
                      "The remaining digits of the SMDS address.  This
                      field will always be less than or equal to 9
                      digits long.  In North America, this field
                      contains the rest of the SMDS address (e.g., the
                      last 7 digits following the area code).  See
                      smdsAddressCodes object."
              ::= { subscriberAddressesEntry 3 }

          subscriberAddressesOnSNI OBJECT-TYPE
              SYNTAX  SMDSAddress
              ACCESS  read-only
              STATUS  mandatory
              DESCRIPTION
                      "An SMDS address that belongs to this SNI."
              ::= { subscriberAddressesEntry 4 }

          subscriberAddressesIndex  OBJECT-TYPE
              SYNTAX  INTEGER (1..65535)
              ACCESS  read-only
              STATUS  mandatory
              DESCRIPTION
                      "The value of this object identifies the SIP port
                      interface for which this entry contains management
                      information.  The value of this object for a







                      particular interface has the same value as the
                      ifIndex object, defined in RFC1213, for the same
                      interface."
              ::= { subscriberAddressesEntry 5 }
















































          -- The Address Screening Group
          -- Implementation of this group is mandatory
          -- if providing SMDS CNM.

          addressScreening OBJECT IDENTIFIER ::= { smdsSubscr 3 }

          -- The Address Screening Master Group

          addressScreeningMasterTable OBJECT-TYPE
              SYNTAX  SEQUENCE OF AddressScreeningMasterEntry
              ACCESS  not-accessible
              STATUS  mandatory
              DESCRIPTION
                      "This is the table for the address screens.  There
                      can be up to s individual address screens and up
                      to s group address screens per SNI
                      (sniScreenIndex).  The initial value for s
                      (screenIndex) is equal to 4.  In the future a
                      higher value of s may be supported.  The screens
                      are distinguished by their screenType (i.e.,
                      individual or group) and by the screenIndex (i.e.,
                      a value between 1 and s).

                      This list identifies the s screens associated with
                      an SNI accompanied by an indication (screenStatus)
                      of whether the screening comprises 'allowed
                      addresses' or 'disallowed addresses' (i.e.,
                      whether the screen is applied as an inclusionary
                      or exclusionary restriction), or whether the
                      screen is not used (i.e., screening is turned off
                      and all SIP L3_PDUs are allowed; this is
                      identified by an empty list) or multiple
                      individual and group address screens are not
                      supported by the network supporting SMDS.

                      Different addresses on an SNI may be associated
                      with different address screens (one individual and
                      one group address screen per associated SNI
                      individual address, and one individual address
                      screen per associated SNI group address).  This
                      information is included in the
                      associatedAddressesIndScreenTable and
                      associatedAddressesGrpScreenTable.  The
                      associatedAddressesIndScreenTable includes all the
                      addresses (associatedAddressInd) assigned to an







                      SNI (i.e., both individual and group addresses)
                      that are associated with a particular Individual
                      Address Screen (associatedScreenIndIndex).  The
                      associatedAddressesGrpScreenTable includes all the
                      addresses (associatedAddressGrp) assigned to an
                      SNI (i.e., only individual addresses) that are
                      associated with a particular Group Address Screen
                      (associatedScreenGrpIndex).

                      For every SNI, there are: 1) defIAScreenForIAs;
                      the default Individual Address Screen used for
                      destination address screening at the network
                      ingress and source address screening at the
                      network egress of individually addressed L3_PDUs
                      when the associated SNI address is an Individual
                      Address.  2) defGAScreenForIAs; the default Group
                      Address Screen used for destination address
                      screening at the network ingress of group
                      addressed L3_PDUs.  The associated SNI address
                      will always be an Individual Address (i.e., it is
                      the Source Address).  3) defIAScreenForGAs; the
                      default Individual Address Screen used for source
                      address screening at the network egress of
                      individually addressed L3_PDUs when the associated
                      SNI address is a Group Address (i.e., it is the
                      Destination Address).

                      The individual address screen (all the
                      iAScreeningAddresses for the s iAScreenIndices in
                      the individualAddressScreenTable) and the group
                      address screen (all the gAScreeningAddress for the
                      s gAScreenIndices in the groupAddressScreenTable)
                      together consist of up to n addresses.  The
                      initial value of n (numberValidEntries in the
                      numberAndDefaultScreeningTable) is defined as 128.
                      In the future a value of n up to 2048 may be
                      supported.

                      The individual address screen (iAScreeningAddress
                      in the individualAddressScreenTable) is used to
                      perform Destination Address Screening for
                      individually addressed data units (performed at
                      the network ingress) and Source Address Screening
                      for all data units (performed at the network
                      egress).  The group address screen







                      (gAScreeningAddress in the
                      groupAddressScreenTable) is used to perform
                      Destination Address Screening for group addressed
                      data units."
              ::= { addressScreening 1 }

          addressScreeningMasterEntry OBJECT-TYPE
              SYNTAX  AddressScreeningMasterEntry
              ACCESS  not-accessible
              STATUS  mandatory
              DESCRIPTION
                      "This list contains the SNI Index, the Screening
                      Table Index, whether the screening table is an
                      Individual Address Screen or Group Address Screen,
                      whether the screen is a list of allowed or
                      disallowed addresses, whether the screen is empty,
                      or whether multiple individual and group address
                      screens are not supported.  See reference TR-TSV-
                      000772."
              INDEX { sniScreenIndex, screenIndex, screenType }
              ::= { addressScreeningMasterTable 1 }

          AddressScreeningMasterEntry ::= SEQUENCE {
                   sniScreenIndex
                      INTEGER,
                   screenIndex
                      INTEGER,
                   screenType
                      INTEGER,
                   screenStatus
                      INTEGER,
                   screenStatusChange
                      INTEGER
                   }

          sniScreenIndex  OBJECT-TYPE
               SYNTAX  INTEGER (1..65535)
               ACCESS  read-only
               STATUS  mandatory
               DESCRIPTION
                      "The value of this object identifies the SIP Port
                      interface for which this entry contains management
                      information.  The value of this object for a
                      particular interface has the same value as the
                      ifIndex, defined in RFC1213, for the same







                      interface."
               ::= { addressScreeningMasterEntry 1 }

          screenIndex  OBJECT-TYPE
              SYNTAX  INTEGER (1..4)
              ACCESS  read-only
              STATUS  mandatory
              DESCRIPTION
                      "The value of this object identifies the individual
                      or group
                      address screening list.  There may be up to s
                      individual address screening lists and up to s
                      group address screening lists  per SNI.
                      The initial value of s
                      is defined to be 4.  In the future more screening
                      lists per SNI may be allowed.  For each SNI, there
                      must be at least one individual address screen and
                      one group address screen."
              ::= {  addressScreeningMasterEntry 2 }

          screenType  OBJECT-TYPE
              SYNTAX  INTEGER  {
                      individualScreen (1),
                      groupScreen (2)
              }
              ACCESS  read-only
              STATUS  mandatory
              DESCRIPTION
                      "The value of this object identifies whether
                      the screening table is either
                      an individual address screen
                      or a group address screen."
              ::= { addressScreeningMasterEntry 3 }

          screenStatus OBJECT-TYPE
              SYNTAX  INTEGER {
                   allowed (1),
                   disallowed (2),
                   empty (3),
                   notSupported (4)
              }
              ACCESS  read-only
              STATUS  mandatory
              DESCRIPTION
                      "The object identifies whether the screen contains







                      allowed or disallowed addresses.  The value of
                      this object is identical for an entire address
                      screen.  The value of empty implies that screening
                      is turned off (i.e., all L3_PDUs are allowed).
                      The value of notSupported implies that this
                      particular screenIndex is not available for this
                      SNI (sniScreenIndex) (i.e., the SNI supports less
                      than s individual address screens and less than s
                      group addresses screens).  An SNI must have at
                      least one Individual Address Screen and one Group
                      Address Screen in which all their SNI addresses
                      are associated with those screens.  See reference
                      TR-TSV-000772 for the requirements and objectives
                      on address screening."
              ::= { addressScreeningMasterEntry 4 }

          screenStatusChange OBJECT-TYPE
              SYNTAX  INTEGER {
                   allowed (1),
                   disallowed (2),
                   empty (3),
                   notSupported (4)
              }
              ACCESS  read-write
              STATUS  mandatory
              DESCRIPTION
                      "This object is used to change the screenStatus.
                      If this object is different from the screenStatus,
                      then the screenStatus is undergoing change.  When
                      these objects are the same, then the screenStatus
                      is stable.  The agent may refuse the change to be
                      made and thus return the value for
                      screenStatusChange to its previous value which is
                      equal to the screenStatus value.  If the agent
                      accepts the change, the screenStatus value will be
                      set equal to the screenStatusChange value.  An NMS
                      may SET the screenStatus to empty to clean out all
                      the addresses in an individualAddressScreenTable
                      or a groupAddressScreenTable.  The addresses in
                      the associatedAddressesIndScreenTable and
                      associatedAddressesGrpScreenTable would need to be
                      moved to another screening list (otherwise,
                      screening would be turned off for these addresses
                      and all packets will be allowed through for these
                      associated SNI addresses).  An NMS may not SET the







                      status of screenStatusChange if the value of
                      screenStatus is equal to notSupported and the
                      value of screenStatusChange is equal to
                      notSupported.  If an NMS tries to SET the status
                      of screenStatusChange to notSupported or to move
                      it from the notSupported state, then the agent
                      will return badValue.  An SNI must have at least
                      one Individual Address Screen and one Group
                      Address Screen, in which case all their SNI
                      addresses are associated with that screen.  See
                      reference TR-TSV-000772 for the requirements and
                      objectives on address screening."
              ::= { addressScreeningMasterEntry 5 }

          -- The number of addresses in the screening table group
          -- along with information about the default screens.
          -- Implementation of this group is mandatory if providing
          -- SMDS CNM.

          numberAndDefaultScreeningTable  OBJECT-TYPE
               SYNTAX  SEQUENCE OF NumberAndDefaultScreeningEntry
               ACCESS  not-accessible
               STATUS  mandatory
               DESCRIPTION
                       "This list identifies the total number of addresses
                       that are in all of the screens for the particular
                       SNI.  This list also identifies the default screens.
                       For every SNI, there are:
                       1) defIAScreenForIAs; the default Individual
                       Address Screen used
                       for destination address screening at the network ingress and
                       source address screening at the network egress of individually
                       addressed L3_PDUs when the associated SNI address is an Individual
                       Address.
                       2) defGAScreenForIAs; the default Group Address Screen used
                       for destination address screening at the network ingress of group
                       addressed L3_PDUs.  The associated SNI address will always be an
                       Individual Address (i.e., it is the Source Address).
                       3) defIAScreenForGAs; the default Individual Address Screen used
                       for source address screening at the network egress of individually
                       addressed L3_PDUs when the associated SNI address is a Group Address
                       (i.e., it is the Destination Address)."
               ::= { addressScreening 2 }

          numberAndDefaultScreeningEntry  OBJECT-TYPE







               SYNTAX  NumberAndDefaultScreeningEntry
               ACCESS  not-accessible
               STATUS  mandatory
               DESCRIPTION
                       "An SNI Index along with the number of
                       addresses in all of the screening lists and
                       the default screens for this SNI."
               INDEX { sniNumberIndex }
               ::= { numberAndDefaultScreeningTable 1 }

          NumberAndDefaultScreeningEntry ::= SEQUENCE {
                    sniNumberIndex
                       INTEGER,
                    defIAScreenForIAs
                       INTEGER,
                    defIAScreenForIAsChange
                       INTEGER,
                    defIAScreenForGAs
                       INTEGER,
                    defIAScreenForGAsChange
                       INTEGER,
                    defGAScreenForIAs
                       INTEGER,
                    defGAScreenForIAsChange
                       INTEGER,
                    numberValidEntries
                       INTEGER
                    }

          sniNumberIndex  OBJECT-TYPE
               SYNTAX  INTEGER (1..65535)
               ACCESS  read-only
               STATUS  mandatory
               DESCRIPTION
                      "The value of this object identifies the SIP Port
                      interface for which this entry contains management
                      information.  The value of this object for a
                      particular interface has the same value as the
                      ifIndex, defined in RFC1213, for the same
                      interface."
               ::= { numberAndDefaultScreeningEntry 1 }

          defIAScreenForIAs  OBJECT-TYPE
               SYNTAX  INTEGER (1..4)
               ACCESS  read-only







               STATUS  mandatory
               DESCRIPTION
                      "The value of this object identifies the default
                      Individual Address Screen for all Individual
                      Addresses associated with this SNI.  This value is
                      to guard against an assigned SNI Address not being
                      represented in one of the
                      associatedAddressesIndScreenTable."
               ::= { numberAndDefaultScreeningEntry 2 }

          defIAScreenForIAsChange  OBJECT-TYPE
               SYNTAX  INTEGER (1..4)
               ACCESS  read-write
               STATUS  mandatory
               DESCRIPTION
                      "This object is used to change the
                      defIAScreenForIAs.  When the value of this object
                      and defIAScreenForIAs are equal, then no change is
                      being processed by the agent.  If they are not
                      equal, then the agent is processing the requested
                      change.  The agent may refuse the change to be
                      made and thus return the value for
                      defIAScreenForIAsChange to its previous value
                      which is equal to the defIAScreenForIAs value.  If
                      the agent accepts the change, the
                      defIAScreenForIAs value will be set equal to the
                      defIAScreenForIAsChange value."
               ::= { numberAndDefaultScreeningEntry 3 }

          defIAScreenForGAs  OBJECT-TYPE
               SYNTAX  INTEGER (1..4)
               ACCESS  read-only
               STATUS  mandatory
               DESCRIPTION
                      "The value of this object identifies the default
                      Individual Address Screen for all Group Addresses
                      associated with this SNI.  This value is to guard
                      against an assigned SNI Address not being
                      represented in one of the
                      associatedAddressesIndScreenTable."
               ::= { numberAndDefaultScreeningEntry 4 }

          defIAScreenForGAsChange  OBJECT-TYPE
               SYNTAX  INTEGER (1..4)
               ACCESS  read-write







               STATUS  mandatory
               DESCRIPTION
                      "This object is used to change the
                      defIAScreenForGAs.  When the value for this object
                      and defIAScreenForGAs are equal, then no change is
                      being processed by the agent.  If they are not
                      equal, then the agent is processing the requested
                      change.  The agent may refuse the change to be
                      made and thus return the value for
                      defIAScreenForGAsChange to its previous value
                      which is equal to the defIAScreenForGAs value.  If
                      the agent accepts the change, the
                      defIAScreenForGAs value will be set equal to the
                      defIAScreenForGAsChange value."
               ::= { numberAndDefaultScreeningEntry 5 }

          defGAScreenForIAs  OBJECT-TYPE
               SYNTAX  INTEGER (1..4)
               ACCESS  read-only
               STATUS  mandatory
               DESCRIPTION
                      "The value of this object identifies the default
                      Group Address Screen for all Individual Addresses
                      associated with this SNI.  This value is to guard
                      against an assigned SNI Address not being
                      represented in one of the
                      associatedAddressesGrpScreenTable."
               ::= { numberAndDefaultScreeningEntry 6 }

          defGAScreenForIAsChange  OBJECT-TYPE
               SYNTAX  INTEGER (1..4)
               ACCESS  read-write
               STATUS  mandatory
               DESCRIPTION
                      "This object is used to change the
                      defGAScreenForIAs.  When the value of this object
                      and defGAScreenForIAs are equal, then no change is
                      being processed by the agent.  If they are not
                      equal, then the agent is processing the requested
                      change.  The agent may refuse the change to be
                      made and thus return the value for
                      defGAScreenForIAsChange to its previous value
                      which is equal to the defGAScreenForIAs value.  If
                      the agent accepts the change, the
                      defGAScreenForIAs value will be set equal to the







                      defGAScreenForIAsChange value."
               ::= { numberAndDefaultScreeningEntry 7 }

          numberValidEntries  OBJECT-TYPE
               SYNTAX  INTEGER (0..128)
               ACCESS  read-only
               STATUS  mandatory
               DESCRIPTION
                      "This value identifies the total number of
                      screened addresses in all (up to s+s = 8) address
                      screens.  The individual address screens (up to s)
                      and the group address screens (up to s) together
                      consist of up to n addresses.  The value of s is
                      initially equal to 4.  The initial value of n is
                      defined as 128.  In the future a value of n up to
                      2048 may be supported."
               ::= { numberAndDefaultScreeningEntry 8 }



































          -- The Associated Addresses Group
          -- Implementation of this group is mandatory
          -- if providing SMDS CNM.

          -- The Associated Addresses within an Individual Address Screen Group

          associatedAddressesIndScreenTable  OBJECT-TYPE
              SYNTAX  SEQUENCE OF AssociatedAddressesIndScreenEntry
              ACCESS  not-accessible
              STATUS  mandatory
              DESCRIPTION
                      "This list identifies the associated SNI addresses
                      per individual address screen.  Different
                      addresses on an SNI may be associated with
                      different individual address screens (one
                      individual address screen per associated address
                      on an SNI)."
              ::= { addressScreening 3 }

          associatedAddressesIndScreenEntry  OBJECT-TYPE
              SYNTAX  AssociatedAddressesIndScreenEntry
              ACCESS  not-accessible
              STATUS  mandatory
              DESCRIPTION
                      "An SNI index, a screening list index, the
                      associated addresses for the SNI for the
                      individual address screen, and whether the
                      associated address for the screen is valid or
                      invalid."
              INDEX   { associatedSNIIndIndex, associatedScreenIndIndex,
                        assocAddressTypeIndex, assocIndCountryCodeIndex,
                        assocIndDestinationCodeIndex,
                        assocIndSubscriberNumberIndex }
              ::= { associatedAddressesIndScreenTable 1 }

          AssociatedAddressesIndScreenEntry  ::= SEQUENCE {
              associatedSNIIndIndex
                  INTEGER,
              associatedScreenIndIndex
                  INTEGER,
              assocAddressTypeIndex
                  INTEGER,
              assocIndCountryCodeIndex
                  INTEGER,
              assocIndDestinationCodeIndex







                  INTEGER,
              assocIndSubscriberNumberIndex
                  INTEGER,
              associatedAddressInd
                  SMDSAddress,
              associatedAddressIndStatus
                  INTEGER,
              associatedAddressIndStatusChange
                  INTEGER
              }

          associatedSNIIndIndex OBJECT-TYPE
              SYNTAX  INTEGER (1..65535)
              ACCESS  read-only
              STATUS  mandatory
              DESCRIPTION
                      "The value of this object identifies the SIP Port
                      interface for which this entry contains management
                      information.  The value of this object for a particular
                      interface has the same value as the ifIndex, defined
                      in RFC1213, for the same interface."
              ::= { associatedAddressesIndScreenEntry 1 }

          associatedScreenIndIndex  OBJECT-TYPE
              SYNTAX  INTEGER (1..4)
              ACCESS  read-only
              STATUS  mandatory
              DESCRIPTION
                      "The value of this object identifies the individual
                      address screening list.  There are at least one
                      individual address screen and at most s
                      individual address screens per SNI.
                      The initial value of s
                      is defined to be 4.  In the future more screening
                      lists per SNI may be allowed.  The values of this object
                      correspond to the values of screenIndex in the
                      addressScreeningMasterTable."
              ::= {  associatedAddressesIndScreenEntry 2 }

          assocAddressTypeIndex  OBJECT-TYPE
              SYNTAX  INTEGER  {
                          individual(1),
                          group(2)
                      }
              ACCESS  read-only







              STATUS  mandatory
              DESCRIPTION
                      "The value of this object identifies the type
                      of address that is identified by the three
                      address sub-object identifiers assocIndCountryCodeIndex,
                      assocIndDestinationCodeIndex, assocIndSubscriberNumberIndex.
                      The address type can either be an individual or group
                      address.  See the object associatedAddressInd."
              ::= {  associatedAddressesIndScreenEntry 3 }

          assocIndCountryCodeIndex OBJECT-TYPE
              SYNTAX  INTEGER (1..4294967295)
              ACCESS  read-only
              STATUS  mandatory
              DESCRIPTION
                      "The country code portion of the SMDS Address.
                      For example, the country code of North America is
                      (1), the UK is (44), and Germany is (49)."
              ::= { associatedAddressesIndScreenEntry 4 }

          assocIndDestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.
                      See smdsAddressCodes object."
              ::= { associatedAddressesIndScreenEntry 5 }

          assocIndSubscriberNumberIndex OBJECT-TYPE
              SYNTAX  INTEGER (1..4294967295)
              ACCESS  read-only
              STATUS  mandatory
              DESCRIPTION
                      "The remaining digits of the SMDS address.  This
                      field will always be less than or equal to 9
                      digits long.  In North America, this field
                      contains the rest of the SMDS address (e.g., the
                      last 7 digits following the area code).  See
                      smdsAddressCodes object."







              ::= { associatedAddressesIndScreenEntry 6 }

          associatedAddressInd OBJECT-TYPE
              SYNTAX  SMDSAddress
              ACCESS  read-only
              STATUS  mandatory
              DESCRIPTION
                      "The value of this object identifies one of the
                      SMDS addresses for the SNI identified by the
                      associatedSNIIndIndex that belongs to this
                      individual address screen
                      (associatedScreenIndIndex).  This list will
                      contain both individual and group addresses,
                      because this list is used for both Destination
                      Address Screening and Source Address Screening;
                      the destination address in the L3_PDU that is
                      undergoing Source Address Screening may be either
                      a group or individual address that is assigned to
                      that SNI.  One screen will have a maximum of 64
                      associated addresses; up to a maximum of 16
                      individual addresses identifying an SNI and up to
                      a maximum of 48 group addresses identifying an
                      SNI."
              ::= { associatedAddressesIndScreenEntry 7 }

          associatedAddressIndStatus OBJECT-TYPE
              SYNTAX  INTEGER {
                   valid (1),
                   invalid (2)
              }
              ACCESS  read-only
              STATUS  mandatory
              DESCRIPTION
                      "The object identifies whether the associated
                      address is valid or invalid."
              ::= { associatedAddressesIndScreenEntry 8 }

          associatedAddressIndStatusChange OBJECT-TYPE
              SYNTAX  INTEGER {
                   valid (1),
                   invalid (2)
              }
              ACCESS  read-write
              STATUS  mandatory
              DESCRIPTION







                      "This object is used to change the
                      associatedAddressIndStatus.  When the value of
                      this object and associatedAddressIndStatus are
                      equal, then no change is being processed by the
                      agent.  If they are not equal, then the agent is
                      processing the requested change.  The agent may
                      refuse the change to be made and thus return the
                      value for associatedAddressIndStatusChange to its
                      previous value which is equal to the
                      associatedAddressIndStatus value.  If the agent
                      accepts the change, the associatedAddressIndStatus
                      value will be set equal to the
                      associatedAddressIndStatusChange value.  This
                      object is used to add/delete associated SNI
                      addresses -- associatedAddressInd (either
                      individual or group addresses) to  this table."
              ::= { associatedAddressesIndScreenEntry 9 }

          -- The Associated Addresses within a Group Address Screen Group

          associatedAddressesGrpScreenTable  OBJECT-TYPE
              SYNTAX  SEQUENCE OF AssociatedAddressesGrpScreenEntry
              ACCESS  not-accessible
              STATUS  mandatory
              DESCRIPTION
                      "This list identifies the associated SNI addresses
                      per group address screen.  Different addresses on
                      an SNI may be associated with different group
                      address screens (one group address screen per
                      associated address on an SNI)."
              ::= { addressScreening 4 }

          associatedAddressesGrpScreenEntry  OBJECT-TYPE
              SYNTAX  AssociatedAddressesGrpScreenEntry
              ACCESS  not-accessible
              STATUS  mandatory
              DESCRIPTION
                      "An SNI index, a screening list index, the
                      associated addresses for the SNI for the group
                      address screen, and whether the associated address
                      for the screen is valid or invalid."
              INDEX   { associatedSNIGrpIndex, associatedScreenGrpIndex,
                        assocGrpCountryCodeIndex, assocGrpDestinationCodeIndex,
                        assocGrpSubscriberNumberIndex }
              ::= { associatedAddressesGrpScreenTable 1 }







          AssociatedAddressesGrpScreenEntry  ::= SEQUENCE {
              associatedSNIGrpIndex
                  INTEGER,
              associatedScreenGrpIndex
                  INTEGER,
              assocGrpCountryCodeIndex
                  INTEGER,
              assocGrpDestinationCodeIndex
                  INTEGER,
              assocGrpSubscriberNumberIndex
                  INTEGER,
              associatedAddressGrp
                  SMDSAddress,
              associatedAddressGrpStatus
                  INTEGER,
              associatedAddressGrpStatusChange
                  INTEGER
              }

          associatedSNIGrpIndex OBJECT-TYPE
              SYNTAX  INTEGER (1..65535)
              ACCESS  read-only
              STATUS  mandatory
              DESCRIPTION
                      "The value of this object identifies the SIP Port
                      interface for which this entry contains management
                      information.  The value of this object for a particular
                      interface has the same value as the ifIndex, defined
                      in RFC1213, for the same interface."
              ::= { associatedAddressesGrpScreenEntry 1 }

          associatedScreenGrpIndex  OBJECT-TYPE
              SYNTAX  INTEGER (1..4)
              ACCESS  read-only
              STATUS  mandatory
              DESCRIPTION
                      "The value of this object identifies the group
                      address screening list.  There are at least
                      one group address screen and at most s
                      group address screens per SNI.
                      The initial value of s
                      is defined to be 4.  In the future more screening
                      lists per SNI may be allowed.  The values of this object
                      correspond to the values of screenIndex in the
                      addressScreeningMasterTable."







              ::= {  associatedAddressesGrpScreenEntry 2 }

          assocGrpCountryCodeIndex OBJECT-TYPE
              SYNTAX  INTEGER (1..4294967295)
              ACCESS  read-only
              STATUS  mandatory
              DESCRIPTION
                      "The country code portion of the SMDS Address.
                      For example, the country code of North America is
                      (1), the UK is (44), and Germany is (49)."
              ::= { associatedAddressesGrpScreenEntry 3 }

          assocGrpDestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.
                      See smdsAddressCodes object."
              ::= { associatedAddressesGrpScreenEntry 4 }

          assocGrpSubscriberNumberIndex OBJECT-TYPE
              SYNTAX  INTEGER (1..4294967295)
              ACCESS  read-only
              STATUS  mandatory
              DESCRIPTION
                      "The remaining digits of the SMDS address.  This
                      field will always be less than or equal to 9
                      digits long.  In North America, this field
                      contains the rest of the SMDS address (e.g., the
                      last 7 digits following the area code).  See
                      smdsAddressCodes object."
              ::= { associatedAddressesGrpScreenEntry 5 }

          associatedAddressGrp OBJECT-TYPE
              SYNTAX  SMDSAddress
              ACCESS  read-only
              STATUS  mandatory
              DESCRIPTION
                      "The value of this object identifies one of the







                      SMDS addresses for the SNI identified by the
                      associatedSNIGrpIndex that belongs to this group
                      address screen (associatedScreenGrpIndex).  This
                      list will contain only individual addresses,
                      because this list is used for only Destination
                      Address Screening; The Source Address in the
                      L3_PDU that is undergoing Destination Address
                      Screening is always an individual address.  One
                      screen will have a maximum of 16 associated
                      addresses; up to a maximum of 16 individual
                      addresses identifying an SNI."
              ::= { associatedAddressesGrpScreenEntry 6 }

          associatedAddressGrpStatus OBJECT-TYPE
              SYNTAX  INTEGER {
                   valid (1),
                   invalid (2)
              }
              ACCESS  read-only
              STATUS  mandatory
              DESCRIPTION
                      "The object identifies whether the associated
                      address is valid or invalid."
              ::= { associatedAddressesGrpScreenEntry 7 }

          associatedAddressGrpStatusChange OBJECT-TYPE
              SYNTAX  INTEGER {
                   valid (1),
                   invalid (2)
              }
              ACCESS  read-write
              STATUS  mandatory
              DESCRIPTION
                      "This object is used to change
                      associatedAddressGrpStatus.  When the value of
                      this object and associatedAddressGrpStatus are
                      equal, then no change is being processed by the
                      agent.  If they are not equal, then the agent is
                      processing the requested change.  The agent may
                      refuse the change to be made and thus return the
                      value for associatedAddressGrpStatusChange to its
                      previous value which is equal to the
                      associatedAddressGrpStatus value.  If the agent
                      accepts the change, the associatedAddressGrpStatus
                      value will be set equal to the







                      associatedAddressGrpStatusChange value.  The
                      object identifies whether the associated address
                      is valid or invalid.  This object is used to
                      add/delete associated SNI addresses --
                      associatedAddressGrp (only individual addresses)
                      to this table."
              ::= { associatedAddressesGrpScreenEntry 8 }













































          -- The Screened Addresses Group
          -- Implementation of this group is mandatory
          -- if providing SMDS CNM.

          -- The Individual Address Screen Group

          individualAddressScreenTable  OBJECT-TYPE
              SYNTAX  SEQUENCE OF IndividualAddressScreenEntry
              ACCESS  not-accessible
              STATUS  mandatory
              DESCRIPTION
                      "This list identifies the individual addresses
                      that will be screened per individual address
                      screen table.  The are up to s (s is equal to 4)
                      individual address screens per SNI and at least
                      one individual address screen per SNI.  The
                      Individual Address Screens and the Group Address
                      Screens together consist of up to n addresses.
                      The initial value of n is defined as 128. In the
                      future a value of n up to 2048 may be supported.
                      The Individual Address Screen is used to perform
                      Destination Address Screening for individually
                      addressed data units and Source Address Screening
                      for all data units.  The Group Address Screen is
                      used to perform Destination Address Screening for
                      group addressed data units."
              ::= { addressScreening 5 }

          individualAddressScreenEntry  OBJECT-TYPE
              SYNTAX  IndividualAddressScreenEntry
              ACCESS  not-accessible
              STATUS  mandatory
              DESCRIPTION
                      "An SNI index, a screening list index, the
                      individual addresses to be screened for the
                      individual address screen, and whether the
                      screened address is valid or invalid."
              INDEX   { iAScreenSNIIndex, iAScreenIndex,
                        iACountryCodeIndex, iADestinationCodeIndex,
                        iASubscriberNumberIndex }
              ::= { individualAddressScreenTable 1 }

          IndividualAddressScreenEntry  ::= SEQUENCE {
              iAScreenSNIIndex
                  INTEGER,







              iAScreenIndex
                  INTEGER,
              iACountryCodeIndex
                  INTEGER,
              iADestinationCodeIndex
                  INTEGER,
              iASubscriberNumberIndex
                  INTEGER,
              iAScreeningAddress
                  SMDSAddress,
              iAScreeningAddressStatus
                  INTEGER,
              iAScreeningAddressStatusChange
                  INTEGER
              }

          iAScreenSNIIndex OBJECT-TYPE
              SYNTAX  INTEGER (1..65535)
              ACCESS  read-only
              STATUS  mandatory
              DESCRIPTION
                      "The value of this object identifies the SIP Port
                      interface for which this entry contains management
                      information.  The value of this object for a particular
                      interface has the same value as the ifIndex, defined
                      in RFC1213, for the same interface."
              ::= { individualAddressScreenEntry 1 }

          iAScreenIndex  OBJECT-TYPE
              SYNTAX  INTEGER (1..4)
              ACCESS  read-only
              STATUS  mandatory
              DESCRIPTION
                      "The value of this object identifies the individual
                      address screening list.  There are at least one
                      individual address screen and at most s
                      individual address screens per SNI.
                      The initial value of s
                      is defined to be 4.  In the future more screening
                      lists per SNI may be allowed.  The values of this object
                      correspond to the values of screenIndex in the
                      addressScreeningMasterTable."
              ::= {  individualAddressScreenEntry 2 }

          iACountryCodeIndex OBJECT-TYPE







              SYNTAX  INTEGER (1..4294967295)
              ACCESS  read-only
              STATUS  mandatory
              DESCRIPTION
                      "The country code portion of the SMDS Address.
                      For example, the country code of North America is
                      (1), the UK is (44), and Germany is (49)."
              ::= { individualAddressScreenEntry 3 }

          iADestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.
                      See smdsAddressCodes object."
              ::= { individualAddressScreenEntry 4 }

          iASubscriberNumberIndex OBJECT-TYPE
              SYNTAX  INTEGER (1..4294967295)
              ACCESS  read-only
              STATUS  mandatory
              DESCRIPTION
                      "The remaining digits of the SMDS address.  This
                      field will always be less than or equal to 9
                      digits long.  In North America, this field
                      contains the rest of the SMDS address (e.g., the
                      last 7 digits following the area code).  See
                      smdsAddressCodes object."
              ::= { individualAddressScreenEntry 5 }

          iAScreeningAddress OBJECT-TYPE
              SYNTAX  SMDSAddress
              ACCESS  read-only
              STATUS  mandatory
              DESCRIPTION
                      "The value of this object identifies one of the
                      individual addresses to be screened for source and
                      destination address screening for the SNI
                      identified by the iAScreenSNIIndex and for the







                      particular individual address screen
                      (iAScreenIndex)."
              ::= { individualAddressScreenEntry 6 }

          iAScreeningAddressStatus OBJECT-TYPE
              SYNTAX  INTEGER {
                   valid (1),
                   invalid (2)
              }
              ACCESS  read-only
              STATUS  mandatory
              DESCRIPTION
                      "The object identifies whether the screened
                      address is valid or invalid."
              ::= { individualAddressScreenEntry 7 }

          iAScreeningAddressStatusChange OBJECT-TYPE
              SYNTAX  INTEGER {
                   valid (1),
                   invalid (2)
              }
              ACCESS  read-write
              STATUS  mandatory
              DESCRIPTION
                      "This object is used to change the
                      iAScreeningAddressStatus.  When the value of this
                      object and iAScreeningAddressStatus are equal,
                      then no change is being processed by the agent.
                      If they are not equal, then the agent is
                      processing the requested change.  The agent may
                      refuse the change to be made and thus return the
                      value for iAScreeningAddressStatusChange to its
                      previous value which is equal to the
                      iAScreeningAddressStatus value.  If the agent
                      accepts the change, the iAScreeningAddressStatus
                      value will be set equal to the
                      iAScreeningAddressStatusChange value.  This object
                      is used to add/delete individual addresses in the
                      Individual Address Screens -- iAScreeningAddress
                      to this table."
              ::= { individualAddressScreenEntry 8 }

          --  The Group Address Screen Group

          groupAddressScreenTable  OBJECT-TYPE







              SYNTAX  SEQUENCE OF GroupAddressScreenEntry
              ACCESS  not-accessible
              STATUS  mandatory
              DESCRIPTION
                      "This list identifies the group addresses that
                      will be screened per group address screen table.
                      The are up to s (s is equal to 4) group address
                      screens per SNI and at least one group address
                      screen per SNI.  The Individual Address Screen and
                      the Group Address Screen together consist of up to
                      n addresses.  The initial value of n is defined as
                      128. In the future a value of n up to 2048 may be
                      supported.  The Individual Address Screen is used
                      to perform Destination Address Screening for
                      individually addressed data units and Source
                      Address Screening for all data units.  The Group
                      Address Screen is used to perform Destination
                      Address Screening for group addressed data units."
              ::= { addressScreening 6 }

          groupAddressScreenEntry  OBJECT-TYPE
              SYNTAX  GroupAddressScreenEntry
              ACCESS  not-accessible
              STATUS  mandatory
              DESCRIPTION
                      "An SNI index, a screening list index, the group
                      addresses to be screened for the group address
                      screen, and whether the screened address is valid
                      or invalid."
              INDEX   { gAScreenSNIIndex, gAScreenIndex,
                        gACountryCodeGAIndex, gADestinationCodeGAIndex,
                        gASubscriberNumberGAIndex }
              ::= { groupAddressScreenTable 1 }

          GroupAddressScreenEntry  ::= SEQUENCE {
              gAScreenSNIIndex
                  INTEGER,
              gAScreenIndex
                  INTEGER,
              gACountryCodeGAIndex
                  INTEGER,
              gADestinationCodeGAIndex
                  INTEGER,
              gASubscriberNumberGAIndex
                  INTEGER,







              gAScreeningAddress
                  SMDSAddress,
              gAScreeningAddressStatus
                  INTEGER,
              gAScreeningAddressStatusChange
                  INTEGER
              }

          gAScreenSNIIndex OBJECT-TYPE
              SYNTAX  INTEGER (1..65535)
              ACCESS  read-only
              STATUS  mandatory
              DESCRIPTION
                      "The value of this object identifies the SIP Port
                      interface for which this entry contains management
                      information.  The value of this object for a particular
                      interface has the same value as the ifIndex, defined
                      in RFC1213, for the same interface."
              ::= { groupAddressScreenEntry 1 }

          gAScreenIndex  OBJECT-TYPE
              SYNTAX  INTEGER (1..4)
              ACCESS  read-only
              STATUS  mandatory
              DESCRIPTION
                      "The value of this object identifies the group
                      address screening list.  There are at least one
                      group address screen and at most s
                      group address screens per SNI.
                      The initial value of s
                      is defined to be 4.  In the future more screening
                      lists per SNI may be allowed.  The values of this object
                      correspond to the values of screenIndex in the
                      addressScreeningMasterTable."
              ::= {  groupAddressScreenEntry 2 }

          gACountryCodeGAIndex OBJECT-TYPE
              SYNTAX  INTEGER (1..4294967295)
              ACCESS  read-only
              STATUS  mandatory
              DESCRIPTION
                      "The country code portion of the SMDS Group
                      Address.  For example, the country code of North
                      America is (1), the UK is (44), and Germany is
                      (49)."







              ::= { groupAddressScreenEntry 3 }

          gADestinationCodeGAIndex OBJECT-TYPE
              SYNTAX  INTEGER (1..4294967295)
              ACCESS  read-only
              STATUS  mandatory
              DESCRIPTION
                      "The destination code portion of the SMDS Group
                      Address.  For example, in North American it is the
                      Area Code.  For many European countries, it is the
                      city code portion of the address.  For SMDS
                      addresses that do not distinguish such a code,
                      this field is the next set of numbers that make
                      logical sense.  See smdsAddressCodes object."
              ::= { groupAddressScreenEntry 4 }

          gASubscriberNumberGAIndex OBJECT-TYPE
              SYNTAX  INTEGER (1..4294967295)
              ACCESS  read-only
              STATUS  mandatory
              DESCRIPTION
                      "The remaining digits of the SMDS Group Address.
                      This field will always be less than or equal to 9
                      digits long.  In North America, this field
                      contains the rest of the SMDS address (e.g., the
                      last 7 digits following the area code).  See
                      smdsAddressCodes object."
              ::= { groupAddressScreenEntry 5 }

          gAScreeningAddress OBJECT-TYPE
              SYNTAX  SMDSAddress
              ACCESS  read-only
              STATUS  mandatory
              DESCRIPTION
                      "The value of this object identifies one of the
                      group addresses to be screened for destination
                      address screening for the SNI identified by the
                      gAScreenSNIIndex and for the particular group
                      address screen (gAScreenIndex)."
              ::= { groupAddressScreenEntry 6 }

          gAScreeningAddressStatus OBJECT-TYPE
              SYNTAX  INTEGER {
                   valid (1),
                   invalid (2)







              }
              ACCESS  read-only
              STATUS  mandatory
              DESCRIPTION
                      "The object identifies whether the screened
                      address is valid or invalid."
                ::= { groupAddressScreenEntry 7 }

          gAScreeningAddressStatusChange OBJECT-TYPE
              SYNTAX  INTEGER {
                   valid (1),
                   invalid (2)
              }
              ACCESS  read-write
              STATUS  mandatory
              DESCRIPTION
                      "This object is used to change the
                      gAScreeningAddressStatus.  When this object and
                      gAScreeningAddressStatus are equal, then no change
                      is being processed by the agent.  If they are not
                      equal, then the agent is processing the requested
                      change.  The agent may refuse the change to be
                      made and thus return the value for
                      gAScreeningAddressStatusChange to its previous
                      value which is equal to the
                      gAScreeningAddressStatus value.  If the agent
                      accepts the change, the gAScreeningAddressStatus
                      value will be set equal to the
                      gAScreeningAddressStatusChange value.  This object
                      is used to add/delete group addresses in the Group
                      Address Screens -- gAScreeningAddress to this
                      table."
                ::= { groupAddressScreenEntry 8 }



















          -- The Group Addressing Information Group
          -- Implementation of this group is
          -- mandatory if providing SMDS CNM.
          -- The Group Addressing Information is divided into
          -- two groups.  The Group Address Group provides all the
          -- individual addresses that are members of a particular
          -- group address.  The Member Group Address Group provides
          -- all the group addresses that a particular individual
          -- address is a member.

          groupAddressing OBJECT IDENTIFIER ::= { smdsSubscr 4 }


          -- The Group Address Group
          -- Implementation of this group is mandatory if providing
          -- SMDS CNM.

          groupAddressTable  OBJECT-TYPE
              SYNTAX  SEQUENCE OF GroupAddressEntry
              ACCESS  not-accessible
              STATUS  mandatory
              DESCRIPTION
                      "A table of all group addresses in the network and
                      the associated individual addresses identified by
                      each group address.  A group address identifies up
                      to m individual addresses.  An SMDS SS supports up
                      to n group addresses.  An group address can be
                      identified by up to p individual addresses.  A
                      particular SNI is identified by up to 48 group
                      addresses.  The initial values of m, n, and p are
                      defined as 128, 1024, and 32, respectively.   In
                      the future values of m and n of 2048 and 8192,
                      respectively, may be supported.

                      Changes in this table cause corresponding changes
                      in the memberGroupAddressTable,
                      numberMemberAddressesTable,
                      numberGAsForAddressTable, and
                      numberGAsForSNITable."
              ::= { groupAddressing 1 }

          groupAddressEntry  OBJECT-TYPE
              SYNTAX  GroupAddressEntry
              ACCESS  not-accessible
              STATUS  mandatory







              DESCRIPTION
                      "A Group Address and an address in that group and
                      whether that association is valid or invalid."
              INDEX   { groupCountryCodeGAIndex, groupDestinationCodeGAIndex,
                        groupSubscriberNumberGAIndex, groupCountryCodeIndex,
                        groupDestinationCodeIndex, groupSubscriberNumberIndex }
              ::= { groupAddressTable 1 }

          GroupAddressEntry  ::= SEQUENCE {
              groupCountryCodeGAIndex
                  INTEGER,
              groupDestinationCodeGAIndex
                  INTEGER,
              groupSubscriberNumberGAIndex
                  INTEGER,
              groupCountryCodeIndex
                  INTEGER,
              groupDestinationCodeIndex
                  INTEGER,
              groupSubscriberNumberIndex
                  INTEGER,
              groupAddress
                  SMDSAddress,
              groupMember
                  SMDSAddress,
              groupMemberStatus
                  INTEGER,
              groupMemberStatusChange
                  INTEGER
              }

          groupCountryCodeGAIndex OBJECT-TYPE
              SYNTAX  INTEGER (1..4294967295)
              ACCESS  read-only
              STATUS  mandatory
              DESCRIPTION
                      "The country code portion of the SMDS Group
                      Address.  For example, the country code of North
                      America is (1), the UK is (44), and Germany is
                      (49)."
              ::= { groupAddressEntry 1 }

          groupDestinationCodeGAIndex OBJECT-TYPE
              SYNTAX  INTEGER (1..4294967295)
              ACCESS  read-only







              STATUS  mandatory
              DESCRIPTION
                      "The destination code portion of the SMDS Group
                      Address.  For example, in North American it is the
                      Area Code.  For many European countries, it is the
                      city code portion of the address.  For SMDS
                      addresses that do not distinguish such a code,
                      this field is the next set of numbers that make
                      logical sense.  See smdsAddressCodes object."
              ::= { groupAddressEntry 2 }

          groupSubscriberNumberGAIndex OBJECT-TYPE
              SYNTAX  INTEGER (1..4294967295)
              ACCESS  read-only
              STATUS  mandatory
              DESCRIPTION
                      "The remaining digits of the SMDS Group Address.
                      This field will always be less than or equal to 9
                      digits long.  In North America, this field
                      contains the rest of the SMDS address (e.g., the
                      last 7 digits following the area code).  See
                      smdsAddressCodes object."
              ::= { groupAddressEntry 3 }

          groupCountryCodeIndex OBJECT-TYPE
              SYNTAX  INTEGER (1..4294967295)
              ACCESS  read-only
              STATUS  mandatory
              DESCRIPTION
                      "The country code portion of the SMDS Address.
                      For example, the country code of North America is
                      (1), the UK is (44), and Germany is (49)."
              ::= { groupAddressEntry 4 }

          groupDestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.







                      See smdsAddressCodes object."
              ::= { groupAddressEntry 5 }

          groupSubscriberNumberIndex OBJECT-TYPE
              SYNTAX  INTEGER (1..4294967295)
              ACCESS  read-only
              STATUS  mandatory
              DESCRIPTION
                      "The remaining digits of the SMDS Address.  This
                      field will always be less than or equal to 9
                      digits long.  In North America, this field
                      contains the rest of the SMDS address (e.g., the
                      last 7 digits following the area code).  See
                      smdsAddressCodes object."
              ::= { groupAddressEntry 6 }

          groupAddress OBJECT-TYPE
              SYNTAX  SMDSAddress
              ACCESS  read-only
              STATUS  mandatory
              DESCRIPTION
                      "A Group Address."
              ::= { groupAddressEntry 7 }

          groupMember OBJECT-TYPE
              SYNTAX  SMDSAddress
              ACCESS  read-only
              STATUS  mandatory
              DESCRIPTION
                      "An individual SMDS address that belongs to this
                      Group Address."
              ::= { groupAddressEntry 8 }

          groupMemberStatus OBJECT-TYPE
              SYNTAX  INTEGER  {
                   valid (1),
                   invalid (2)
              }
              ACCESS  read-only
              STATUS  mandatory
              DESCRIPTION
                      "The object identifies whether the groupMember is
                      valid or invalid.  See reference TA-TSV-001062."
              ::= { groupAddressEntry 9 }








          groupMemberStatusChange OBJECT-TYPE
              SYNTAX  INTEGER  {
                   valid (1),
                   invalid (2)
              }
              ACCESS  read-write
              STATUS  mandatory
              DESCRIPTION
                      "This object is used to change the
                      groupMemberStatus.  When the value of this object
                      and groupMemberStatus are equal, then no change is
                      being processed by the agent.  If they are not
                      equal, then the agent is processing the requested
                      change.  The agent may refuse the change to be
                      made and thus return the value for
                      groupMemberStatusChange to its previous value
                      which is equal to the groupMemberStatus value.  If
                      the agent accepts the change, the
                      groupMemberStatus value will be set equal to the
                      groupMemberStatusChange value.  This object is
                      used to add/delete a group member to a group
                      address.  Changes can only be made by a Group
                      Address Sponsor (the subscriber who requested the
                      group address from the service provider).  See
                      reference TA-TSV-001062.  Changes in this table
                      affect other tables in this group and the Member
                      Group Address Group."
              ::= { groupAddressEntry 10 }

          numberMemberAddressesTable  OBJECT-TYPE
              SYNTAX  SEQUENCE OF NumberMemberAddressesEntry
              ACCESS  not-accessible
              STATUS  mandatory
              DESCRIPTION
                      "This table contains the number of individual
                      addresses
                      that are associated with a group address.
                      Initially, there may be up to 128 individual
                      addresses that are identified by the group address."
              ::= { groupAddressing 2 }

          numberMemberAddressesEntry  OBJECT-TYPE
              SYNTAX  NumberMemberAddressesEntry
              ACCESS  not-accessible
              STATUS  mandatory







              DESCRIPTION
                      "A group address and the number of individual
                      addresses that are identified by it."
              INDEX { numberCountryCodeGAIndex, numberDestinationCodeGAIndex,
                      numberSubscriberNumberGAIndex }
              ::= { numberMemberAddressesTable 1 }

          NumberMemberAddressesEntry ::= SEQUENCE {
              numberCountryCodeGAIndex
                  INTEGER,
              numberDestinationCodeGAIndex
                  INTEGER,
              numberSubscriberNumberGAIndex
                  INTEGER,
              numberGroupAddress
                   SMDSAddress,
              numberIndAddresses
                   INTEGER
              }

          numberCountryCodeGAIndex OBJECT-TYPE
              SYNTAX  INTEGER (1..4294967295)
              ACCESS  read-only
              STATUS  mandatory
              DESCRIPTION
                      "The country code portion of the SMDS Group
                      Address.  For example, the country code of North
                      America is (1), the UK is (44), and Germany is
                      (49)."
              ::= { numberMemberAddressesEntry 1 }

          numberDestinationCodeGAIndex OBJECT-TYPE
              SYNTAX  INTEGER (1..4294967295)
              ACCESS  read-only
              STATUS  mandatory
              DESCRIPTION
                      "The destination code portion of the SMDS Group
                      Address.  For example, in North American it is the
                      Area Code.  For many European countries, it is the
                      city code portion of the address.  For SMDS
                      addresses that do not distinguish such a code,
                      this field is the next set of numbers that make
                      logical sense.  See smdsAddressCodes object."
              ::= { numberMemberAddressesEntry 2 }








          numberSubscriberNumberGAIndex OBJECT-TYPE
              SYNTAX  INTEGER (1..4294967295)
              ACCESS  read-only
              STATUS  mandatory
              DESCRIPTION
                      "The remaining digits of the SMDS Group Address.
                      This field will always be less than or equal to 9
                      digits long.  In North America, this field
                      contains the rest of the SMDS address (e.g., the
                      last 7 digits following the area code).  See
                      smdsAddressCodes object."
              ::= { numberMemberAddressesEntry 3 }

          numberGroupAddress OBJECT-TYPE
              SYNTAX  SMDSAddress
              ACCESS  read-only
              STATUS  mandatory
              DESCRIPTION
                      "A Group Address."
              ::= { numberMemberAddressesEntry 4 }

          numberIndAddresses OBJECT-TYPE
               SYNTAX  INTEGER (0..128)
               ACCESS  read-only
               STATUS  mandatory
               DESCRIPTION
                      "This value identifies the total number of
                      individual addresses that are associated with a
                      group address.  Initially, there may be up to 128
                      individual addresses that are associated with a
                      group address.  A group address may have no
                      members."
               ::= { numberMemberAddressesEntry 5 }


          -- The Member Group Address Group
          -- Implementation of this group is mandatory
          -- if providing SMDS CNM.

          memberGroupAddressTable  OBJECT-TYPE
              SYNTAX  SEQUENCE OF MemberGroupAddressEntry
              ACCESS  not-accessible
              STATUS  mandatory
              DESCRIPTION
                      "A table of all  individual addresses that are







                      members of group addresses and the group
                      address(es) they belong to.  A group address
                      identifies up to m individual addresses.  An SMDS
                      SS supports up to n group addresses.  An
                      individual address can be identified by up to p
                      group addresses.  A particular SNI is identified
                      by up to 48 group addresses.  The initial values
                      of m, n, and p are defined as 128, 1024, and 32,
                      respectively.   In the future values of m and n of
                      2048 and 8192, respectively, may be supported.

                      Changes in this table cause corresponding changes
                      in the groupAddressTable,
                      numberMemberAddressesTable,
                      numberGAsForAddressTable, and
                      numberGAsForSNITable."
              ::= { groupAddressing 3 }

          memberGroupAddressEntry  OBJECT-TYPE
              SYNTAX  MemberGroupAddressEntry
              ACCESS  not-accessible
              STATUS  mandatory
              DESCRIPTION
                      "An address and a Group Address in which it is a
                      member and whether that association is valid or
                      invalid."
              INDEX   { memberCountryCodeIndex, memberDestinationCodeIndex,
                        memberSubscriberNumberIndex, memberCountryCodeGAIndex,
                        memberDestinationCodeGAIndex, memberSubscriberNumberGAIndex }
              ::= { memberGroupAddressTable 1 }

          MemberGroupAddressEntry  ::= SEQUENCE {
              memberCountryCodeIndex
                  INTEGER,
              memberDestinationCodeIndex
                  INTEGER,
              memberSubscriberNumberIndex
                  INTEGER,
              memberCountryCodeGAIndex
                  INTEGER,
              memberDestinationCodeGAIndex
                  INTEGER,
              memberSubscriberNumberGAIndex
                  INTEGER,
              memberAddress







                  SMDSAddress,
              associatedGroupAddress
                  SMDSAddress,
              associatedGroupAddressStatus
                  INTEGER,
              associatedGroupAddressStatusChange
                  INTEGER
              }

          memberCountryCodeIndex OBJECT-TYPE
              SYNTAX  INTEGER (1..4294967295)
              ACCESS  read-only
              STATUS  mandatory
              DESCRIPTION
                      "The country code portion of the SMDS Address.
                      For example, the country code of North America is
                      (1), the UK is (44), and Germany is (49)."
              ::= { memberGroupAddressEntry 1 }

          memberDestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.
                      See smdsAddressCodes object."
              ::= { memberGroupAddressEntry 2 }

          memberSubscriberNumberIndex OBJECT-TYPE
              SYNTAX  INTEGER (1..4294967295)
              ACCESS  read-only
              STATUS  mandatory
              DESCRIPTION
                      "The remaining digits of the SMDS Address.  This
                      field will always be less than or equal to 9
                      digits long.  In North America, this field
                      contains the rest of the SMDS address (e.g., the
                      last 7 digits following the area code).  See
                      smdsAddressCodes object."
              ::= { memberGroupAddressEntry 3 }







          memberCountryCodeGAIndex OBJECT-TYPE
              SYNTAX  INTEGER (1..4294967295)
              ACCESS  read-only
              STATUS  mandatory
              DESCRIPTION
                      "The country code portion of the SMDS Group
                      Address.  For example, the country code of North
                      America is (1), the UK is (44), and Germany is
                      (49)."
              ::= { memberGroupAddressEntry 4 }

          memberDestinationCodeGAIndex OBJECT-TYPE
              SYNTAX  INTEGER (1..4294967295)
              ACCESS  read-only
              STATUS  mandatory
              DESCRIPTION
                      "The destination code portion of the SMDS Group
                      Address.  For example, in North American it is the
                      Area Code.  For many European countries, it is the
                      city code portion of the address.  For SMDS
                      addresses that do not distinguish such a code,
                      this field is the next set of numbers that make
                      logical sense.  See smdsAddressCodes object."
              ::= { memberGroupAddressEntry 5 }

          memberSubscriberNumberGAIndex OBJECT-TYPE
              SYNTAX  INTEGER (1..4294967295)
              ACCESS  read-only
              STATUS  mandatory
              DESCRIPTION
                      "The remaining digits of the SMDS Group Address.
                      This field will always be less than or equal to 9
                      digits long.  In North America, this field
                      contains the rest of the SMDS address (e.g., the
                      last 7 digits following the area code).  See
                      smdsAddressCodes object."
              ::= { memberGroupAddressEntry 6 }

          memberAddress OBJECT-TYPE
              SYNTAX  SMDSAddress
              ACCESS  read-only
              STATUS  mandatory
              DESCRIPTION
                      "An individual SMDS address."
              ::= { memberGroupAddressEntry 7 }







          associatedGroupAddress OBJECT-TYPE
              SYNTAX  SMDSAddress
              ACCESS  read-only
              STATUS  mandatory
              DESCRIPTION
                      "A Group Address of which the individual address
                      is a member."
              ::= { memberGroupAddressEntry 8 }

          associatedGroupAddressStatus OBJECT-TYPE
              SYNTAX  INTEGER  {
                   valid (1),
                   invalid (2)
              }
              ACCESS  read-only
              STATUS  mandatory
              DESCRIPTION
                      "The object identifies whether the
                      associatedGroupAddress is valid or invalid.  See
                      reference TA-TSV-001062."
              ::= { memberGroupAddressEntry 9 }

          associatedGroupAddressStatusChange OBJECT-TYPE
              SYNTAX  INTEGER  {
                   valid (1),
                   invalid (2)
              }
              ACCESS  read-write
              STATUS  mandatory
              DESCRIPTION
                      "This object is used to change the
                      associatedGroupAddressStatus.  When the value of
                      this object and associatedGroupAddressStatus are
                      equal, then no change is being processed by the
                      agent.  If they are not equal, then the agent is
                      processing the requested change.  The agent may
                      refuse the change to be made and thus return the
                      value for associatedGroupAddressStatusChange to
                      its previous value which is equal to the
                      associatedGroupAddressStatus value.  If the agent
                      accepts the change, the
                      associatedGroupAddressStatus value will be set
                      equal to the associatedGroupAddressStatusChange
                      value.  This object is used to only remove the
                      Individual Address (memberAddress) from being







                      associated with a Group Address
                      (associatedGroupAddress).  Changes may only be
                      made by the Group Member.  This capability is
                      under study.  See reference TA-TSV-001062."
              ::= { memberGroupAddressEntry 10 }

          numberGAsForAddressTable  OBJECT-TYPE
              SYNTAX  SEQUENCE OF NumberGAsForAddressEntry
              ACCESS  not-accessible
              STATUS  mandatory
              DESCRIPTION
                      "This table contains the number of group
                      addresses
                      that are associated with this individual address.
                      Initially, there may be up to 32 group
                      addresses that are associated by the individual
                      address."
              ::= { groupAddressing 4 }

          numberGAsForAddressEntry  OBJECT-TYPE
              SYNTAX  NumberGAsForAddressEntry
              ACCESS  not-accessible
              STATUS  mandatory
              DESCRIPTION
                      "An individual address and the number of group
                      addresses that are associated with it."
              INDEX { numberGAsCountryCodeIndex, numberGAsDestinationCodeIndex,
                      numberGAsSubscriberNumberIndex }
              ::= { numberGAsForAddressTable 1 }

          NumberGAsForAddressEntry ::= SEQUENCE {
              numberGAsCountryCodeIndex
                  INTEGER,
              numberGAsDestinationCodeIndex
                  INTEGER,
              numberGAsSubscriberNumberIndex
                  INTEGER,
              individualAddress
                   SMDSAddress,
              numberGroupAddresses
                   INTEGER
              }

          numberGAsCountryCodeIndex OBJECT-TYPE
              SYNTAX  INTEGER (1..4294967295)







              ACCESS  read-only
              STATUS  mandatory
              DESCRIPTION
                      "The country code portion of the SMDS Address.
                      For example, the country code of North America is
                      (1), the UK is (44), and Germany is (49)."
              ::= { numberGAsForAddressEntry 1 }

          numberGAsDestinationCodeIndex OBJECT-TYPE
              SYNTAX  INTEGER (1..4294967295)
              ACCESS  read-only
              STATUS  mandatory
              DESCRIPTION
                      "The destination code portion of the SMDS Address.
                      For example, in North American it is the Area
                      Code.  For many European countries, it is the city
                      code portion of the address.  For SMDS addresses
                      that do not distinguish such a code, this field is
                      the next set of numbers that make logical sense.
                      See smdsAddressCodes object."
              ::= { numberGAsForAddressEntry 2 }

          numberGAsSubscriberNumberIndex OBJECT-TYPE
              SYNTAX  INTEGER (1..4294967295)
              ACCESS  read-only
              STATUS  mandatory
              DESCRIPTION
                      "The remaining digits of the SMDS Address.  This
                      field will always be less than or equal to 9
                      digits long.  In North America, this field
                      contains the rest of the SMDS address (e.g., the
                      last 7 digits following the area code).  See
                      smdsAddressCodes object."
              ::= { numberGAsForAddressEntry 3 }

          individualAddress OBJECT-TYPE
              SYNTAX  SMDSAddress
              ACCESS  read-only
              STATUS  mandatory
              DESCRIPTION
                      "An individual SMDS Address that has at least one
                      group address associated with it."
              ::= { numberGAsForAddressEntry 4 }

          numberGroupAddresses OBJECT-TYPE







               SYNTAX  INTEGER (1..32)
               ACCESS  read-only
               STATUS  mandatory
               DESCRIPTION
                      "This value identifies the total number of group
                      addresses that are associated with an individual
                      address.  Initially, there may be up to 32 group
                      addresses that are associated with an individual
                      address.  This table only contains the individual
                      addresses that are associated with at least one
                      group address."
               ::= { numberGAsForAddressEntry 5 }

          numberGAsForSNITable  OBJECT-TYPE
              SYNTAX  SEQUENCE OF NumberGAsForSNIEntry
              ACCESS  not-accessible
              STATUS  mandatory
              DESCRIPTION
                      "This table contains the number of group
                      addresses
                      that are associated with an SNI.
                      Initially, there may be up to 48 group
                      addresses that identify the SNI."
              ::= { groupAddressing 5 }

          numberGAsForSNIEntry  OBJECT-TYPE
              SYNTAX  NumberGAsForSNIEntry
              ACCESS  not-accessible
              STATUS  mandatory
              DESCRIPTION
                      "An SNI Index along with the number of group
                      addresses that are identify it."
              INDEX { numberGAsSNIIndex }
              ::= { numberGAsForSNITable 1 }

          NumberGAsForSNIEntry ::= SEQUENCE {
              numberGAsSNIIndex
                   INTEGER,
              numberGAs
                   INTEGER
              }

          numberGAsSNIIndex OBJECT-TYPE
              SYNTAX  INTEGER (1..65535)
              ACCESS  read-only







              STATUS  mandatory
              DESCRIPTION
                      "The value of this object identifies the SIP port
                      interface for which this entry contains management
                      information.  The value of this object for a
                      particular interface has the same value as the
                      ifIndex object, defined in RFC1213, for the same
                      interface."
              ::= { numberGAsForSNIEntry 1 }

          numberGAs OBJECT-TYPE
               SYNTAX  INTEGER (0..48)
               ACCESS  read-only
               STATUS  mandatory
               DESCRIPTION
                      "This value identifies the total number of group
                      addresses that identify an SNI.  Initially, there
                      may be up to 48 group addresses that identify an
                      SNI."
               ::= { numberGAsForSNIEntry 2 }
































          -- The Service Disagreements Group
          -- Implementation of this group is mandatory
          -- if providing SMDS CNM.

          serviceDisagreementTable  OBJECT-TYPE
              SYNTAX  SEQUENCE OF ServiceDisagreementEntry
              ACCESS  not-accessible
              STATUS  mandatory
              DESCRIPTION
                      "A table that contains the latest occurrence of a:
                      - Source Address Screening Violation,
                      - Destination Address Screening Violation, and
                      - Unrecognized Source Address for SNI.
                      Each entry is indexed by SNI and service
                      disagreement type, and accompanied by a time-
                      stamp.  When the serviceDisagreementTimeStamp is
                      equal to zero, the ServiceDisagreementEntry does
                      not contain any valid information."
              ::= { smdsSubscr 5 }

          serviceDisagreementEntry  OBJECT-TYPE
              SYNTAX  ServiceDisagreementEntry
              ACCESS  not-accessible
              STATUS  mandatory
              DESCRIPTION
                      "An entry in the service disagreement table."
              INDEX   { sniSDIndex, serviceDisagreementType }
              ::= { serviceDisagreementTable 1 }

          ServiceDisagreementEntry ::= SEQUENCE {
              sniSDIndex
                  INTEGER,
              serviceDisagreementType
                  INTEGER,
              serviceDisagreementSA
                  SMDSAddress,
              serviceDisagreementDA
                  SMDSAddress,
              serviceDisagreementTimeStamp
                  TimeTicks
              }

          sniSDIndex OBJECT-TYPE
              SYNTAX  INTEGER (1..65535)
              ACCESS  read-only







              STATUS  mandatory
              DESCRIPTION
                      "The value of this object identifies the SIP port
                      interface for which this entry contains management
                      information.  The value of this object for a
                      particular interface has the same value as the
                      ifIndex object, defined in RFC1213, for the same
                      interface."
              ::= { serviceDisagreementEntry 1 }

          serviceDisagreementType OBJECT-TYPE
              SYNTAX  INTEGER {
                   sourceAddressScreenViolation (1),
                   destinationAddressScreenViolation (2),
                   invalidSourceAddressForSNI (3)
              }
              ACCESS  read-only
              STATUS  mandatory
              DESCRIPTION
                      "The type of service disagreement."
              ::= { serviceDisagreementEntry 2 }

          serviceDisagreementSA OBJECT-TYPE
              SYNTAX  SMDSAddress
              ACCESS  read-only
              STATUS  mandatory
              DESCRIPTION
                      "A rejected SMDS source address."
              ::= { serviceDisagreementEntry 3 }

          serviceDisagreementDA OBJECT-TYPE
              SYNTAX  SMDSAddress
              ACCESS  read-only
              STATUS  mandatory
              DESCRIPTION
                      "A rejected SMDS destination address."
              ::= { serviceDisagreementEntry 4 }

          serviceDisagreementTimeStamp OBJECT-TYPE
              SYNTAX  TimeTicks
              ACCESS  read-only
              STATUS  mandatory
              DESCRIPTION
                      "The timestamp for the service disagreement.  The
                      timestamp contains the value of sysUpTime at the







                      latest occurrence of this type of service
                      disagreement.  See textual description under
                      serviceDisagreementTable for boundary conditions."
              ::= { serviceDisagreementEntry 5 }
















































          -- The information to support the exchange access component
          -- of inter-exchange SMDS.
          -- See reference TR-TSV-001060
          -- for requirements.
          -- Implementation of this group is mandatory
          -- if providing SMDS CNM and Exchange Access SMDS.

          xaSmds   OBJECT IDENTIFIER ::= { smdsSubscr 6 }


          -- The Exchange Access SMDS Subscription Parameters and
          -- Violations Group
          -- Implementation of this group is mandatory
          -- if providing SMDS CNM and Exchange Access SMDS.

          -- Although some of the objects in this group are read-write,
          -- the write-capability is not supported by the agent.
          -- However, in the future, the management station, when
          -- authorized, may change the value for
          -- carrierPreselection.
          -- Assuming that the objects are in the customer's MIB
          -- View and the Access Control Table allows read-write access,
          -- in the mean time, the agent will return badValue for
          -- any Secure SNMP SET-Request on a read-write object.  The agent
          -- will return noSuchName for community-string based SET-Request on a
          -- read-write object.

          xaSmdsSubscrTable  OBJECT-TYPE
                      SYNTAX  SEQUENCE OF XaSmdsSubscrEntry
                      ACCESS  not-accessible
                      STATUS  mandatory
                      DESCRIPTION
                             "This table contains Subscriber-Network
                             Interface (SNI)
                             parameters and state variables, one entry
                             per SIP port, that is applicable for providing
                             interLATA SMDS to the end customer."
                      ::= { xaSmds 1 }

          xaSmdsSubscrEntry  OBJECT-TYPE
                      SYNTAX  XaSmdsSubscrEntry
                      ACCESS  not-accessible
                      STATUS  mandatory
                      DESCRIPTION
                             "This list contains Subscriber-Network







                             Interface (SNI)
                             parameters for interLATA SMDS
                             and state variables."
                      INDEX   { xaSmdsSubscrIndex }
                      ::= { xaSmdsSubscrTable 1 }

          XaSmdsSubscrEntry  ::= SEQUENCE {
                             xaSmdsSubscrIndex
                                 INTEGER,
                             carrierPreselection
                                 INTEGER,
                             carrierPreselectionChange
                                 INTEGER,
                             carrierSelectionViolations
                                 Counter
                         }


          xaSmdsSubscrIndex  OBJECT-TYPE
                    SYNTAX  INTEGER (1..65535)
                    ACCESS  read-only
                    STATUS  mandatory
                    DESCRIPTION
                           "The value of this object identifies the
                           SIP port
                           interface for which this entry contains
                           management
                           information.  The value of this object
                           for a
                           particular interface has the same value
                           as the
                           ifIndex object, defined in RFC1213, for
                           the same
                           interface."
                    ::= { xaSmdsSubscrEntry 1 }

          carrierPreselection OBJECT-TYPE
              SYNTAX  INTEGER (1..9999)
              ACCESS  read-only
              STATUS  mandatory
              DESCRIPTION
                      "The preselected carrier used to send inter-
                      exchange SMDS L3_PDUs.  If a carrier is not
                      preselected than this SMDS carrier code is all
                      zeros.  This object is equal to the CIC code for







                      the carrier."
              ::= { xaSmdsSubscrEntry 2 }

          carrierPreselectionChange OBJECT-TYPE
              SYNTAX  INTEGER (1..9999)
              ACCESS  read-write
              STATUS  mandatory
              DESCRIPTION
                      "This object is used to change the
                      carrierPreselection.  When the value of this
                      object and carrierPreselection are equal, then no
                      change is being processed by the agent.  If they
                      are not equal, then the agent is processing the
                      requested change.  The agent may refuse the change
                      to be made and thus return the value for
                      carrierPreselectionChange to its previous value
                      which is equal to the carrierPreselection value.
                      If the agent accepts the change, the
                      carrierPreselection value will be set equal to the
                      carrierPreselectionChange value."
              ::= { xaSmdsSubscrEntry 3 }

          carrierSelectionViolations OBJECT-TYPE
              SYNTAX  Counter
              ACCESS  read-only
              STATUS  mandatory
              DESCRIPTION
                      "The number of SIP L3_PDUs that were discarded
                      because an explicit carrier (CIC code) was
                      selected in the Carrier Selection field of the
                      Header Extension of an SIP L3_PDU and the
                      Destination Address was structured as an embodied
                      Service Access Code (SAC) plus the number of SIP
                      L3_PDUs that were discarded because of an
                      unauthorized carrier (CIC) was selected plus the
                      number of SIP L3_PDUs that were discarded because
                      they contained an explicit Carrier Selection
                      element (CIC code) that the SMDS SS did not
                      recognize.  The CIC may be a valid code for SMDS.
                      However, this SMDS SS that is serving this SNI is
                      not connected to that carrier or does not
                      recognize the code specified.  In some
                      jurisdictions not all carriers are authorized to
                      provide exchange service.  Hence, if the carrier
                      selection field contains a carrier's CIC code







                      (i.e., an explicit carrier selection has been
                      made) and that carrier is not authorized to
                      provide service between destination and source
                      addresses within the exchange service area, then
                      the SIP L3_PDU will be discarded.  See TR-TSV-
                      001060."
              ::= { xaSmdsSubscrEntry 4 }













































          -- The Carrier Blocking Group
          -- Implementation of this group is mandatory
          -- if providing SMDS CNM and Exchange Access SMDS.

          carrierBlockingTable  OBJECT-TYPE
                      SYNTAX  SEQUENCE OF CarrierBlockingEntry
                      ACCESS  not-accessible
                      STATUS  mandatory
                      DESCRIPTION
                             "This table contains a list
                             of carriers that are blocking
                             the end-customer's Subscriber-Network
                             Interface (SNI), whether the blocking
                             is turned on or off, and
                             contains the number of SIP L3_PDUs
                             that were discarded because
                             the carrier blocked packets from this SNI.
                             Initially, if no carriers are blocking an SNI, then
                             this table contains no information."
                      ::= { xaSmds 2 }

          carrierBlockingEntry  OBJECT-TYPE
                      SYNTAX  CarrierBlockingEntry
                      ACCESS  not-accessible
                      STATUS  mandatory
                      DESCRIPTION
                             "This list contains the Subscriber-Network
                             Interface (SNI) index, the carriers
                             that are blocking packets from that SNI, and
                             the number of SIP L3_PDUs that were blocked
                             per SMDS CIC code per SNI."
                      INDEX   { carrierBlockingIndex, carrierBlockingCodeIndex }
                      ::= { carrierBlockingTable 1 }

          CarrierBlockingEntry  ::= SEQUENCE {
                             carrierBlockingIndex
                                 INTEGER,
                             carrierBlockingCodeIndex
                                 INTEGER,
                             carrierBlockingStatus
                                 INTEGER,
                             carrierBlockingL3PDUs
                                 Counter
                        }








          carrierBlockingIndex  OBJECT-TYPE
                    SYNTAX  INTEGER (1..65535)
                    ACCESS  read-only
                    STATUS  mandatory
                    DESCRIPTION
                           "The value of this object identifies the
                           SIP port
                           interface for which this entry contains
                           management
                           information.  The value of this object
                           for a
                           particular interface has the same value
                           as the
                           ifIndex object, defined in RFC1213, for
                           the same
                           interface."
                    ::= { carrierBlockingEntry 1 }

          carrierBlockingCodeIndex  OBJECT-TYPE
                    SYNTAX  INTEGER (1..9999)
                    ACCESS  read-only
                    STATUS  mandatory
                    DESCRIPTION
                           "The value of this object identifies the
                           carrier code (CIC) in decimal form.
                           There may be up to 16
                           carriers that are blocking a particular
                           SNI.  Only interexchange carriers may
                           block an SNI."
                    ::= { carrierBlockingEntry 2 }

          carrierBlockingStatus OBJECT-TYPE
              SYNTAX  INTEGER  {
                 on  (1),
                 off (2)
              }
              ACCESS  read-only
              STATUS  mandatory
              DESCRIPTION
                      "Whether the carrier is presently blocking this
                      SNI (on) or whether blocking is turned off.  When
                      the carrierBlockingStatus is changed from on to
                      off, the carrierBlockingL3PDUs for this particular
                      carrierBlockingCodeIndex remain pegged at the
                      value when turned off.  When the







                      carrierBlockingStatus is turned on, the
                      carrierBlockingL3PDUs for this
                      carrierBlockingCodeIndex is reset to zero."
              ::= { carrierBlockingEntry 3 }

          carrierBlockingL3PDUs OBJECT-TYPE
              SYNTAX  Counter
              ACCESS  read-only
              STATUS  mandatory
              DESCRIPTION
                      "The number of SIP L3_PDUs that were discarded,
                      because the carrier blocked packets from that SNI.
                      This count may be zero.  When the
                      carrierBlockingStatus is changed from off to on,
                      the carrierBlockingL3PDUs counter is reset to
                      zero."
              ::= { carrierBlockingEntry 4 }


          -- The Carrier Index Group
          -- Implementation of this group is mandatory
          -- if providing SMDS CNM and Exchange Access SMDS.

          carrierIndexTable  OBJECT-TYPE
                      SYNTAX  SEQUENCE OF CarrierIndexEntry
                      ACCESS  not-accessible
                      STATUS  mandatory
                      DESCRIPTION
                             "The value of this object identifies the
                              interface(s) between the local service
                              provider and the particular other carriers
                              for which this entry contains
                              management
                              information.  The value of this object
                              for a
                              particular interface has the same value
                              as the
                              ifIndex object, defined in RFC1213, for
                              the same
                              interface."
                      ::= { xaSmds 3 }

          carrierIndexEntry  OBJECT-TYPE
                      SYNTAX  CarrierIndexEntry
                      ACCESS  not-accessible







                      STATUS  mandatory
                      DESCRIPTION
                             "This list contains the
                             carrier code of the carriers and the
                             respective ifIndex.  Only the interfaces
                             table from MIB II (RFC1213) is applicable for this
                             ifIndex and only the following items:
                             ifDescr, ifType, ifOperStatus, and
                             ifLastChange."
                      INDEX   { carrierIndexCode, carrierCodeType }
                      ::= { carrierIndexTable 1 }

          CarrierIndexEntry  ::= SEQUENCE {
                             carrierIndexCode
                                 INTEGER,
                             carrierCodeType
                                 INTEGER,
                             carrierIndex
                                 INTEGER
                        }

          carrierIndexCode  OBJECT-TYPE
                    SYNTAX  INTEGER (1..9999)
                    ACCESS  read-only
                    STATUS  mandatory
                    DESCRIPTION
                        "The carrier's code
                        (CIC or NECA code)
                        which is connected to
                        the serving network supporting SMDS."
                    ::= { carrierIndexEntry 1 }

          carrierCodeType  OBJECT-TYPE
                    SYNTAX  INTEGER  {
                                cic (1),
                                necacc (2)
                    }
                    ACCESS  read-only
                    STATUS  mandatory
                    DESCRIPTION
                        "Whether the carrier's code
                        which is connected to
                        the serving network supporting SMDS
                        is a CIC or NECA CC."
                    ::= { carrierIndexEntry 2 }







          carrierIndex  OBJECT-TYPE
                    SYNTAX  INTEGER (1..65535)
                    ACCESS  read-only
                    STATUS  mandatory
                    DESCRIPTION
                        "The carrier's ifIndex from RFC1213.
                         For SMDS CNM, this index models all
                         the interfaces (ICIs) between
                         an LEC and an ILEC or IEC
                         as the same interface."
                    ::= { carrierIndexEntry 3 }









































          -- Enterprise-specific traps for use with the SNMP-based
          -- SMDS Customer Network Management Service.
          -- Implementation of these traps are mandatory
          -- if providing SMDS CNM.

          -- This is the SMDS CNM Subscription MIB trap module.

          -- Trap definitions that follow are specified compliant with the
          -- SMI RFC1155, as amended by the extensions specified
          -- for concise MIB specifications RFC1212 and using the conventions for
          -- defining event notifications RFC1215.

          smdsSubscrEntryChange TRAP-TYPE
              ENTERPRISE  bellcore
              VARIABLES   { ifIndex }
              DESCRIPTION
                          "An smdsSubscrEntryChange trap signifies that
                          for this SNI one or more of the following subscription
                          parameters have been changed:
                             smdsContact(1)
                             smdsSNILocation(2)
                             smdsAccessClass(3)
                             smdsMCDUsIn(4)
                             smdsMCDUsOut(5)."
              ::= 1

          smdsAddressesEntryChange TRAP-TYPE
              ENTERPRISE  bellcore
              VARIABLES   { ifIndex }
              DESCRIPTION
                          "An smdsAddressesEntryChange trap signifies that
                          for this SNI the list of associated SMDS addresses
                          has been changed."
              ::= 2

          individualAddressScreenEntryChange TRAP-TYPE
              ENTERPRISE  bellcore
              VARIABLES   { ifIndex }
              DESCRIPTION
                          "An individualAddressScreenEntryChange
                           trap signifies that for this SNI a
                           change has been made to the
                           individual address screening tables."
              ::= 3








          groupAddressScreenEntryChange TRAP-TYPE
              ENTERPRISE  bellcore
              VARIABLES   { ifIndex }
              DESCRIPTION
                          "An groupAddressScreenEntryChange
                           trap signifies that for this SNI a
                           change has been made to the
                           group address screening tables."
              ::= 4

          groupAddressChange TRAP-TYPE
              ENTERPRISE  bellcore
              VARIABLES   { groupAddress }
              DESCRIPTION
                           "A groupAddressChange trap signifies that
                           for the list of SMDS addresses for this
                           group address has been changed, or that this
                           group address has been added or deleted."
              ::= 5

          excessiveAuthenticationFailure TRAP-TYPE
              ENTERPRISE  bellcore
              VARIABLES   { ifIndex }
              DESCRIPTION
                          "An excessiveAuthenticationFailure trap signifies that
                           n consecutive authentication failures have been
                           received for management requests for this SNI.
                           The value of n is 100."
              ::= 6

          xaSmdsSubscrEntryChange TRAP-TYPE
              ENTERPRISE  bellcore
              VARIABLES   { ifIndex }
              DESCRIPTION
                          "An xaSmdsSubscrEntryChange trap signifies that
                          for this SNI the carrierPreselection has
                          been changed."
              ::= 7

          carrierBlockingEntryChange TRAP-TYPE
              ENTERPRISE  bellcore
              VARIABLES   { ifIndex }
              DESCRIPTION
                          "A carrierBlockingEntryChange trap signifies that
                          for this SNI a new carrierBlockingCode has







                          been turned on (added to the list)
                          or one has been turned off."
              ::= 8

          END
