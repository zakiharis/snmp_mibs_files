-- 	$Id: shiva-modem.asn,v 1.7 1996/01/16 16:44:18 dfox Exp $

--
-- 	Copyright 1992, 1993, 1995, 1996 Shiva Corporation
--

-- This MIB has been replaced by the SHIVA-LINE-MIB and SHIVA-SLOT-MIB.
-- It is not included in LanRover/Access Switch and subsequent products.

SHIVA-MODEM-MIB DEFINITIONS ::= BEGIN

IMPORTS
	DisplayString
		FROM RFC1213-MIB
	OBJECT-TYPE
		FROM RFC-1212		-- Concise MIB Definitions
	modem
		FROM SHIVA-MIB;


-- internal modem table

    internalModemTable	OBJECT-TYPE
	SYNTAX	SEQUENCE OF InternalModemEntry
	ACCESS	not-accessible
	STATUS	deprecated
	DESCRIPTION
		"A table of internal modems."
	::= { modem 1 }

    internalModemEntry OBJECT-TYPE
	SYNTAX	InternalModemEntry
	ACCESS	not-accessible
	STATUS	deprecated
	DESCRIPTION
		"Internal modem parameters."
	INDEX { internalModemIndex }
	::= { internalModemTable 1 }

    InternalModemEntry ::= SEQUENCE {
	internalModemIndex	INTEGER,
	internalModemClass	INTEGER,
	internalModemName	DisplayString,
	internalModemFirmRev	DisplayString,
	internalModemDPRev	DisplayString,
	internalModemAnswerInit	DisplayString,
	internalModemConnSpeed	INTEGER,
	internalModemErrorCorr	INTEGER,
	internalModemDataCompr	INTEGER,
	internalModemEQM	INTEGER,
	internalModemAGC	INTEGER
    }

    internalModemIndex OBJECT-TYPE
	SYNTAX	INTEGER
	ACCESS	read-only
	STATUS	deprecated
	DESCRIPTION
		"Internal modem index."
	::= { internalModemEntry 1 }

    internalModemClass OBJECT-TYPE
	SYNTAX	INTEGER {
		unknown(1),
		uart(2),
		modem(3),
		switched56(4),
		bri(5),
		usart(6)
	}
	ACCESS	read-only
	STATUS	deprecated
	DESCRIPTION
		"Internal modem class."
	::= { internalModemEntry 2 }

    internalModemName OBJECT-TYPE
	SYNTAX	DisplayString
	ACCESS	read-only
	STATUS	deprecated
	DESCRIPTION
		"Internal modem name."
	::= { internalModemEntry 3 }

    internalModemFirmRev OBJECT-TYPE
	SYNTAX	DisplayString
	ACCESS	read-only
	STATUS	deprecated
	DESCRIPTION
		"Internal modem firmware revision."
	::= { internalModemEntry 4 }

    internalModemDPRev OBJECT-TYPE
	SYNTAX	DisplayString
	ACCESS	read-only
	STATUS	deprecated
	DESCRIPTION
		"Internal modem datapump revision."
	::= { internalModemEntry 5 }

    internalModemAnswerInit OBJECT-TYPE
	SYNTAX	DisplayString
	ACCESS	read-only
	STATUS	deprecated
	DESCRIPTION
		"Default answer init string for the internal modem."
	::= { internalModemEntry 6 }

    internalModemConnSpeed OBJECT-TYPE
	SYNTAX	INTEGER {
		unknown(1),
		bps300(2),
		bps600(3),
		bps1200(4),
		bps2400(5),
		bps4800(6),
		bps7200(7),
		bps9600(8),
		bps12000(9),
		bps14400(10),
		bps16800(11),
		bps19200(12),
		bps21600(13),
		bps24000(14),
		bps26400(15),
		bps28800(16)
	}
	ACCESS	read-only
	STATUS	deprecated
	DESCRIPTION
		"Internal modem line connection speed."
	::= { internalModemEntry 7 }

    internalModemErrorCorr OBJECT-TYPE
	SYNTAX	INTEGER {
		unknown(1),
		none(2),
		lapm(3),
		mnp4(4),
		mnp10(5)
	}
	ACCESS	read-only
	STATUS	deprecated
	DESCRIPTION
		"Internal modem error correction protocol."
	::= { internalModemEntry 8 }

    internalModemDataCompr OBJECT-TYPE
	SYNTAX	INTEGER {
		unknown(1),
		none(2),
		mnp5(3),
		v42bis(4)
	}
	ACCESS	read-only
	STATUS	deprecated
	DESCRIPTION
		"Internal modem line data compression type."
	::= { internalModemEntry 9 }

    internalModemEQM OBJECT-TYPE
	SYNTAX	INTEGER
	ACCESS	read-only
	STATUS	deprecated
	DESCRIPTION
		"Internal modem line signal quality."
	::= { internalModemEntry 10 }

    internalModemAGC OBJECT-TYPE
	SYNTAX	INTEGER
	ACCESS	read-only
	STATUS	deprecated
	DESCRIPTION
		"Internal modem line signal strength."
	::= { internalModemEntry 11 }


END
