--
-- she-melt-mib.mib
-- MIB generated by MG-SOFT Visual MIB Builder Version 6.0  Build 88
-- Thursday,  July 16,  2009 at 16:30:04
--

-- Start of ClearCase branch-information of current release:
-- she-melt-mib.mib   /main/she_r3.5_grf/5
-- End of ClearCase branch-information.

	SHE-MELT-MIB DEFINITIONS ::= BEGIN
 
		IMPORTS
			she			
				FROM AN-MIB			
			ifIndex,  InterfaceIndex			
				FROM IF-MIB			
			SheControlStatusType			
				FROM SHE-TC-MIB			
			OBJECT-GROUP,  MODULE-COMPLIANCE,  NOTIFICATION-GROUP			
				FROM SNMPv2-CONF			
			Integer32,  Unsigned32,  OBJECT-TYPE,  MODULE-IDENTITY,  NOTIFICATION-TYPE			
				FROM SNMPv2-SMI			
			TEXTUAL-CONVENTION			
				FROM SNMPv2-TC;
	
	
		sheMelt MODULE-IDENTITY 
			LAST-UPDATED "200907161600Z"		-- July 16,  2009 at 16:00 GMT
			ORGANIZATION 
				"Nokia Siemens Networks"
			CONTACT-INFO 
				"Gerd Barchmann
				COO BCS DSLAM RD SDE HW1
				
				gerd.barchmann@nsn.com"
			DESCRIPTION 
				" Definition of MELT (metallic line testing) feature control commands and results.
				
				New supported with R3.7M."
			REVISION "200812091400Z"		-- December 09,  2008 at 14:00 GMT
			DESCRIPTION 
				"First issue for SHE R3.7M."
			REVISION "200901211000Z"		-- January 21,  2009 at 10:00 GMT
			DESCRIPTION 
				"Update after review. 
				Define more detailed measurment result types.
				"
			REVISION "200903131136Z"		-- March 13,  2009 at 11:36 GMT
			DESCRIPTION 
				"Remove wetting current settings."
			REVISION "200904281416Z"		-- April 28,  2009 at 14:16 GMT
			DESCRIPTION 
				"Correct definition of SheMeltTestResultValidType."
			REVISION "200907161626Z"		-- July 16,  2009 at 16:26 GMT
			DESCRIPTION 
				"Modify unit of foreignCurrent result parameters from mA to uA. "
			::= { she 24 }

		
	
--
-- Textual conventions
--
	
		SheMeltTestRequestIfStateType ::= TEXTUAL-CONVENTION
			STATUS current
			DESCRIPTION 
				"The MELT state of a port (IfIndex).
				
				idle                -> no test running and test was never started since IU reset
				beingTested         -> test is running 
				applyingTestTone    -> test tone activated on line	
				testSucceeded(5)    -> line idle and MELT was successful finished
				testAborted         -> line idle and MELT aborted by operator or internal failure/timeout
				"
			SYNTAX INTEGER
				{
				idle(1), 
				beingTested(2), 
				applyingTestTone(3), 
				idleTestSucceeded(5), 
				idleTestAborted(6)
				}

		SheMeltTestRequestIuStateType ::= TEXTUAL-CONVENTION
			STATUS current
			DESCRIPTION 
				"The MELT state type of concerned IU.
				
				idle             -> no port of this iu under test - new test could be started
				beingTested      -> one port of this iu is currently under test - no new test could be started
				applyingTestTone -> one port of this iu has currently a test tone activated - no new test could be started
				"
			SYNTAX INTEGER
				{
				idle(1), 
				beingTested(2), 
				applyingTestTone(3)
				}

		SheMeltControlReqType ::= TEXTUAL-CONVENTION
			STATUS current
			DESCRIPTION 
				"The type for MELT test commands."
			SYNTAX INTEGER
				{
				noRequest(0), 
				setMeltTestParameters(1), 
				startMeltTest(2), 
				stopMeltTest(3), 
				activateTestTone(4), 
				deactivateTestTone(5), 
				setMeltTestRequestTestToneIndex(8), 
				createMeltTestToneEntry(10), 
				modifyMeltTestToneEntry(11), 
				deleteMeltTestToneEntry(12)
				}

		SheMeltControlReqResultType ::= TEXTUAL-CONVENTION
			STATUS current
			DESCRIPTION 
				"The result type for MELT command."
			SYNTAX INTEGER
				{
				meltRequestControlReqNotSupported(2), 
				commExecStarted(30), 
				paramFaulty(31), 
				requestBusy(32), 
				setDataFailed(34), 
				aswTimeout(35), 
				commandFailed(36), 
				commandSucceeded(37)
				}

		SheMeltTestResultStateType ::= TEXTUAL-CONVENTION
			STATUS current
			DESCRIPTION 
				"Status of the information contained in MeltTestResultTable.
				
				Values:
				notTested      -> port was not tested since reset,  all results not valid
				testFailed     -> port was tested but test failed,  all results not valid
				testSucceeded  -> port was tested successfuly,  check single result valid information"
			SYNTAX INTEGER
				{
				notTested(0), 
				testFailed(1), 
				testSucceeded(2)
				}

		SheMeltTestResultValidType ::= TEXTUAL-CONVENTION
			STATUS current
			DESCRIPTION 
				"Valid information for each single MELT result value.
				
				Values:
				invalid -> the shown result is not valid (maybe the test could not run because of external conditions)
				valid   -> trusted result
				aboveLimitOfMeasurementRange -> result is above HW measurement range 
				belowLimitOfMeasurementRange -> result is below HW measurement range "
			SYNTAX INTEGER
				{
				invalid(0), 
				valid(1), 
				aboveLimitOfMeasurementRange(2), 
				belowLimitOfMeasurementRange(3)
				}

		SheMeltTestResultCheckPpaType ::= TEXTUAL-CONVENTION
			STATUS current
			DESCRIPTION 
				"Used for result of CheckPpa test."
			SYNTAX INTEGER
				{
				notTested(0), 
				notDetected(1), 
				detectedRightPolarity(2), 
				detectedWrongPolarity(3)
				}

		SheMeltTestResultCheckType ::= TEXTUAL-CONVENTION
			STATUS current
			DESCRIPTION 
				"Used for result of CheckSplitter and CheckIad test."
			SYNTAX INTEGER
				{
				notTested(0), 
				notDetected(1), 
				detected(2)
				}

		SheMeltTestFrequencyType ::= TEXTUAL-CONVENTION
			STATUS current
			DESCRIPTION 
				"used for configuration of test frequency"
			SYNTAX Unsigned32 (10..32000)

		SheMeltTestToneFrequencyType ::= TEXTUAL-CONVENTION
			STATUS current
			DESCRIPTION 
				"used to configure used test tones"
			SYNTAX Unsigned32 (100..4000)

		SheMeltTestToneIndexType ::= TEXTUAL-CONVENTION
			STATUS current
			DESCRIPTION 
				"Used to identify a test tone set (assignment interface - test tone index)."
			SYNTAX Unsigned32 (1..32)

		SheMeltTestSignalLevelType ::= TEXTUAL-CONVENTION
			STATUS current
			DESCRIPTION 
				"used to configure test frequency and test tone level's"
			SYNTAX Integer32 (-20..3)

		SheMeltTestResultCapacityType ::= TEXTUAL-CONVENTION
			STATUS current
			DESCRIPTION 
				"Valid value range for Capacity measurement."
			SYNTAX Integer32 (0..100000)

		SheMeltTestResultResistanceType ::= TEXTUAL-CONVENTION
			STATUS current
			DESCRIPTION 
				"Valid value range for resistance measurement."
			SYNTAX Integer32 (0..20000000)

		SheMeltTestResultACVoltageType ::= TEXTUAL-CONVENTION
			STATUS current
			DESCRIPTION 
				"Valid value range for AC voltage measurement."
			SYNTAX Integer32 (0..4000)

		SheMeltTestResultACVoltageFrequencyType ::= TEXTUAL-CONVENTION
			STATUS current
			DESCRIPTION 
				"Valid value range for AC voltage frequency measurement."
			SYNTAX Integer32 (0..70)

		SheMeltTestResultDCVoltageType ::= TEXTUAL-CONVENTION
			STATUS current
			DESCRIPTION 
				"Valid value range for DC voltage measurement."
			SYNTAX Integer32 (-4000..4000)

		SheMeltTestResultForeignCurrentType ::= TEXTUAL-CONVENTION
			STATUS current
			DESCRIPTION 
				"Valid value range for current measurement."
			SYNTAX Integer32 (0..40)

		SheMeltTestResultConductanceType ::= TEXTUAL-CONVENTION
			STATUS current
			DESCRIPTION 
				"Valid value range for conductance and Susceptance measurement."
			SYNTAX Integer32 (0..10000000)

	
--
-- Node definitions
--
	
--  -----------------------------------------------------------------
-- sheMeltTestRequestObjects        
-- -----------------------------------------------------------------
-- 
		sheMeltTestRequestObjects OBJECT IDENTIFIER ::= { sheMelt 1 }

		
-- Parameters for MELT test values which depend on test conditions.
		sheMeltTestParameter OBJECT IDENTIFIER ::= { sheMeltTestRequestObjects 1 }

		
		sheMeltTestParameterFreq1 OBJECT-TYPE
			SYNTAX SheMeltTestFrequencyType
			UNITS "Hz"
			MAX-ACCESS read-only
			STATUS current
			DESCRIPTION
				"This parameter contains the used frequency 1 for MELT impedance/admittance test."
			DEFVAL { 1000 }
			::= { sheMeltTestParameter 1 }

		
		sheMeltTestRequestStateTable OBJECT-TYPE
			SYNTAX SEQUENCE OF SheMeltTestRequestStateEntry
			MAX-ACCESS not-accessible
			STATUS current
			DESCRIPTION
				"Each entry in this table contains the testing status of each IfIndex.
				Only indeces of MELT feature supporting interfaces are listed in this table!"
			::= { sheMeltTestRequestObjects 2 }

		
		sheMeltTestRequestStateEntry OBJECT-TYPE
			SYNTAX SheMeltTestRequestStateEntry
			MAX-ACCESS not-accessible
			STATUS current
			DESCRIPTION
				"An entry in sheMeltTestRequestIfTable."
			INDEX { ifIndex }
			::= { sheMeltTestRequestStateTable 1 }

		
		SheMeltTestRequestStateEntry ::=
			SEQUENCE { 
				sheMeltTestRequestIfState
					SheMeltTestRequestIfStateType, 
				sheMeltTestRequestIuState
					SheMeltTestRequestIuStateType, 
				sheMeltTestRequestTestToneIndex
					SheMeltTestToneIndexType
			 }

		sheMeltTestRequestIfState OBJECT-TYPE
			SYNTAX SheMeltTestRequestIfStateType
			MAX-ACCESS read-only
			STATUS current
			DESCRIPTION
				"The MELT status of this interface.
				
				Only one port of one IU could be under test at time.
				Ports on different IU's could be under test at the same time.
				Check the corresponding sheMeltTestRequestIuState for this precondition.
				
				NOTE:
				Wetting current injection will be autonomously interrupted,  if MELT or testTone insertion
				is started (WC configuration himself via sheXdslMib or sheShdslMib) for this interface as
				long as the test is running.
				Forgetting to stop test tone insertion will inhibit wetting current!"
			DEFVAL { idle }
			::= { sheMeltTestRequestStateEntry 1 }

		
		sheMeltTestRequestIuState OBJECT-TYPE
			SYNTAX SheMeltTestRequestIuStateType
			MAX-ACCESS read-only
			STATUS current
			DESCRIPTION
				"The MELT status of IU where this interface is located on.
				Every port must know whether this IU is under melt test already or not,  in order
				to decide if the melt test request on this port can be accepted. Only one port
				of one IU could be under test at time. Ports on different IU's could be under test at
				the same time."
			DEFVAL { idle }
			::= { sheMeltTestRequestStateEntry 2 }

		
		sheMeltTestRequestTestToneIndex OBJECT-TYPE
			SYNTAX SheMeltTestToneIndexType
			MAX-ACCESS read-only
			STATUS current
			DESCRIPTION
				"This parameter points on a valid entry of sheMeltTestToneTable.
				
				These configuration is needed for test tone insertion on this line.
				One default profile with index 1 will always exist and is assigned per default to each line!"
			DEFVAL { 1 }
			::= { sheMeltTestRequestStateEntry 3 }

		
--  -----------------------------------------------------------------
-- MELT Test request control group  
-- -----------------------------------------------------------------
-- 
		sheMeltTestRequestStateControl OBJECT IDENTIFIER ::= { sheMeltTestRequestObjects 3 }

		
		sheMeltTestRequestControlReq OBJECT-TYPE
			SYNTAX SheMeltControlReqType
			MAX-ACCESS read-write
			STATUS current
			DESCRIPTION
				"setMeltTestParameters (1):
				sheMeltTestRequestControlParameterFreq1
				
				startMeltTest (2):
				sheMeltTestRequestControlIndex
				
				stopMeltTest (3):
				sheMeltTestRequestControlIndex
				
				activateTestTone (4):
				sheMeltTestRequestControlIndex
				
				deactivateTestTone (5):
				sheMeltTestRequestControlIndex
				
				setMeltTestRequestTestToneIndex (8):
				sheMeltTestRequestControlIndex
				sheMeltTestRequestControlTestToneIndex"
			::= { sheMeltTestRequestStateControl 1 }

		
		sheMeltTestRequestControlIndex OBJECT-TYPE
			SYNTAX InterfaceIndex
			MAX-ACCESS read-write
			STATUS current
			DESCRIPTION
				"The interface index of the DSL central PPTP which should be configured."
			::= { sheMeltTestRequestStateControl 2 }

		
		sheMeltTestRequestControlStatus OBJECT-TYPE
			SYNTAX SheControlStatusType
			MAX-ACCESS read-only
			STATUS current
			DESCRIPTION
				"The status of a control request."
			::= { sheMeltTestRequestStateControl 3 }

		
		sheMeltTestRequestControlTimer OBJECT-TYPE
			SYNTAX Unsigned32
			MAX-ACCESS read-only
			STATUS current
			DESCRIPTION
				"The maximum wait time for the manager for a long running user command."
			::= { sheMeltTestRequestStateControl 4 }

		
		sheMeltTestRequestControlReqResult OBJECT-TYPE
			SYNTAX SheMeltControlReqResultType
			MAX-ACCESS read-only
			STATUS current
			DESCRIPTION
				"The result of the last user command."
			::= { sheMeltTestRequestStateControl 5 }

		
		sheMeltTestRequestControlReqTimeStamp OBJECT-TYPE
			SYNTAX Unsigned32
			UNITS "sec"
			MAX-ACCESS read-only
			STATUS current
			DESCRIPTION
				"The time stamp of the last command (end of command)."
			::= { sheMeltTestRequestStateControl 6 }

		
		sheMeltTestRequestControlTestToneIndex OBJECT-TYPE
			SYNTAX SheMeltTestToneIndexType
			MAX-ACCESS read-write
			STATUS current
			DESCRIPTION
				"look at table"
			::= { sheMeltTestRequestStateControl 7 }

		
		sheMeltTestRequestControlParameterFreq1 OBJECT-TYPE
			SYNTAX SheMeltTestFrequencyType
			UNITS "Hz"
			MAX-ACCESS read-write
			STATUS current
			DESCRIPTION
				"Look at basic parameter group."
			::= { sheMeltTestRequestStateControl 8 }

		
--  -----------------------------------------------------------------
-- sheMeltTestToneObjects        
-- -----------------------------------------------------------------
-- 
		sheMeltTestToneObjects OBJECT IDENTIFIER ::= { sheMelt 2 }

		
		sheMeltTestToneTable OBJECT-TYPE
			SYNTAX SEQUENCE OF SheMeltTestToneEntry
			MAX-ACCESS not-accessible
			STATUS current
			DESCRIPTION
				"Each entry in this table contains a set of parameters for test tone generation.
				These entries could be assigned to each interface.
				
				One default entry exist which could NOT be modified or deleted!"
			::= { sheMeltTestToneObjects 1 }

		
		sheMeltTestToneEntry OBJECT-TYPE
			SYNTAX SheMeltTestToneEntry
			MAX-ACCESS not-accessible
			STATUS current
			DESCRIPTION
				"An entry in sheMeltTestToneTable."
			INDEX { sheMeltTestToneIndex }
			::= { sheMeltTestToneTable 1 }

		
		SheMeltTestToneEntry ::=
			SEQUENCE { 
				sheMeltTestToneIndex
					SheMeltTestToneIndexType, 
				sheMeltTestToneFreq1
					SheMeltTestToneFrequencyType, 
				sheMeltTestToneFreq2
					SheMeltTestToneFrequencyType, 
				sheMeltTestToneLevel
					SheMeltTestSignalLevelType
			 }

		sheMeltTestToneIndex OBJECT-TYPE
			SYNTAX SheMeltTestToneIndexType
			MAX-ACCESS read-only
			STATUS current
			DESCRIPTION
				"This parameter is index of sheMeltTestToneTable.
				
				This configuration is needed for test tone insertion on the line.
				One default profile with index 1 will always exist and is assigned per default to each line!"
			::= { sheMeltTestToneEntry 1 }

		
		sheMeltTestToneFreq1 OBJECT-TYPE
			SYNTAX SheMeltTestToneFrequencyType
			UNITS "Hz"
			MAX-ACCESS read-only
			STATUS current
			DESCRIPTION
				"The test tone frequency 1 of test tone set."
			DEFVAL { 800 }
			::= { sheMeltTestToneEntry 2 }

		
		sheMeltTestToneFreq2 OBJECT-TYPE
			SYNTAX SheMeltTestToneFrequencyType
			UNITS "Hz"
			MAX-ACCESS read-only
			STATUS current
			DESCRIPTION
				"The test tone frequency 2 of test tone set."
			DEFVAL { 800 }
			::= { sheMeltTestToneEntry 3 }

		
		sheMeltTestToneLevel OBJECT-TYPE
			SYNTAX SheMeltTestSignalLevelType
			UNITS "dBm"
			MAX-ACCESS read-only
			STATUS current
			DESCRIPTION
				"The test tone level of test tone set."
			DEFVAL { 0 }
			::= { sheMeltTestToneEntry 4 }

		
--  -----------------------------------------------------------------
-- MELT Test tone control group  
-- -----------------------------------------------------------------
-- 
		sheMeltTestToneControl OBJECT IDENTIFIER ::= { sheMeltTestToneObjects 2 }

		
		sheMeltTestToneControlReq OBJECT-TYPE
			SYNTAX SheMeltControlReqType
			MAX-ACCESS read-write
			STATUS current
			DESCRIPTION
				"createMeltTestToneEntry (10): (index will autonomously generated by NE)
				sheMeltTestToneControlFreq1
				sheMeltTestToneControlFreq2
				sheMeltTestToneControlLevel
				
				modifyMeltTestToneEntry (11):
				sheMeltTestToneControlIndex
				sheMeltTestToneControlFreq1
				sheMeltTestToneControlFreq2
				sheMeltTestToneControlLevel
				
				deleteMeltTestToneEntry (12):
				sheMeltTestToneControlIndex
				"
			::= { sheMeltTestToneControl 1 }

		
		sheMeltTestToneControlIndex OBJECT-TYPE
			SYNTAX SheMeltTestToneIndexType
			MAX-ACCESS read-write
			STATUS current
			DESCRIPTION
				"The table index of the TestToneTable which should be configured.
				
				Default tone-set 1 could not be modified or deleted!"
			::= { sheMeltTestToneControl 2 }

		
		sheMeltTestToneControlStatus OBJECT-TYPE
			SYNTAX SheControlStatusType
			MAX-ACCESS read-only
			STATUS current
			DESCRIPTION
				"The status of a control request."
			::= { sheMeltTestToneControl 3 }

		
		sheMeltTestToneControlTimer OBJECT-TYPE
			SYNTAX Unsigned32
			MAX-ACCESS read-only
			STATUS current
			DESCRIPTION
				"The maximum wait time for the manager for a long running user command."
			::= { sheMeltTestToneControl 4 }

		
		sheMeltTestToneControlReqResult OBJECT-TYPE
			SYNTAX SheMeltControlReqResultType
			MAX-ACCESS read-only
			STATUS current
			DESCRIPTION
				"The result of the last user command."
			::= { sheMeltTestToneControl 5 }

		
		sheMeltTestToneControlReqTimeStamp OBJECT-TYPE
			SYNTAX Unsigned32
			UNITS "sec"
			MAX-ACCESS read-only
			STATUS current
			DESCRIPTION
				"The time stamp of the last command (end of command)."
			::= { sheMeltTestToneControl 6 }

		
		sheMeltTestToneControlFreq1 OBJECT-TYPE
			SYNTAX SheMeltTestToneFrequencyType
			UNITS "Hz"
			MAX-ACCESS read-write
			STATUS current
			DESCRIPTION
				"look at table"
			::= { sheMeltTestToneControl 7 }

		
		sheMeltTestToneControlFreq2 OBJECT-TYPE
			SYNTAX SheMeltTestToneFrequencyType
			UNITS "Hz"
			MAX-ACCESS read-write
			STATUS current
			DESCRIPTION
				"look at table"
			::= { sheMeltTestToneControl 8 }

		
		sheMeltTestToneControlLevel OBJECT-TYPE
			SYNTAX SheMeltTestSignalLevelType
			UNITS "dBm"
			MAX-ACCESS read-write
			STATUS current
			DESCRIPTION
				"look at table"
			::= { sheMeltTestToneControl 9 }

		
--  -----------------------------------------------------------------
-- sheMeltTestRequestObjects        
-- -----------------------------------------------------------------
-- 
		sheMeltTestResultObjects OBJECT IDENTIFIER ::= { sheMelt 3 }

		
		sheMeltTestResultTable OBJECT-TYPE
			SYNTAX SEQUENCE OF SheMeltTestResultEntry
			MAX-ACCESS not-accessible
			STATUS current
			DESCRIPTION
				"Each entry in this table contains the testing results of each IfIndex.
				Only indeces of MELT feature supporting interfaces are listed in this table!"
			::= { sheMeltTestResultObjects 1 }

		
		sheMeltTestResultEntry OBJECT-TYPE
			SYNTAX SheMeltTestResultEntry
			MAX-ACCESS not-accessible
			STATUS current
			DESCRIPTION
				"An entry in sheMeltTestResultTable."
			INDEX { ifIndex }
			::= { sheMeltTestResultTable 1 }

		
		SheMeltTestResultEntry ::=
			SEQUENCE { 
				sheMeltTestResultState
					SheMeltTestResultStateType, 
				sheMeltTestResultTimeStamp
					Unsigned32, 
				sheMeltTestResultCapacityAB
					SheMeltTestResultCapacityType, 
				sheMeltTestResultCapacityABValid
					SheMeltTestResultValidType, 
				sheMeltTestResultCapacityAE
					SheMeltTestResultCapacityType, 
				sheMeltTestResultCapacityAEValid
					SheMeltTestResultValidType, 
				sheMeltTestResultCapacityBE
					SheMeltTestResultCapacityType, 
				sheMeltTestResultCapacityBEValid
					SheMeltTestResultValidType, 
				sheMeltTestResultResistanceAB
					SheMeltTestResultResistanceType, 
				sheMeltTestResultResistanceABValid
					SheMeltTestResultValidType, 
				sheMeltTestResultResistanceBA
					SheMeltTestResultResistanceType, 
				sheMeltTestResultResistanceBAValid
					SheMeltTestResultValidType, 
				sheMeltTestResultResistanceAE
					SheMeltTestResultResistanceType, 
				sheMeltTestResultResistanceAEValid
					SheMeltTestResultValidType, 
				sheMeltTestResultResistanceBE
					SheMeltTestResultResistanceType, 
				sheMeltTestResultResistanceBEValid
					SheMeltTestResultValidType, 
				sheMeltTestResultForeignVoltageDcAB
					SheMeltTestResultDCVoltageType, 
				sheMeltTestResultForeignVoltageDcABValid
					SheMeltTestResultValidType, 
				sheMeltTestResultForeignVoltageDcAE
					SheMeltTestResultDCVoltageType, 
				sheMeltTestResultForeignVoltageDcAEValid
					SheMeltTestResultValidType, 
				sheMeltTestResultForeignVoltageDcBE
					SheMeltTestResultDCVoltageType, 
				sheMeltTestResultForeignVoltageDcBEValid
					SheMeltTestResultValidType, 
				sheMeltTestResultForeignVoltageAcAB
					SheMeltTestResultACVoltageType, 
				sheMeltTestResultForeignVoltageAcABValid
					SheMeltTestResultValidType, 
				sheMeltTestResultForeignVoltageAcAE
					SheMeltTestResultACVoltageType, 
				sheMeltTestResultForeignVoltageAcAEValid
					SheMeltTestResultValidType, 
				sheMeltTestResultForeignVoltageAcBE
					SheMeltTestResultACVoltageType, 
				sheMeltTestResultForeignVoltageAcBEValid
					SheMeltTestResultValidType, 
				sheMeltTestResultForeignVoltageAcFrequencyAB
					SheMeltTestResultACVoltageFrequencyType, 
				sheMeltTestResultForeignVoltageAcFrequencyABValid
					SheMeltTestResultValidType, 
				sheMeltTestResultForeignVoltageAcFrequencyAE
					SheMeltTestResultACVoltageFrequencyType, 
				sheMeltTestResultForeignVoltageAcFrequencyAEValid
					SheMeltTestResultValidType, 
				sheMeltTestResultForeignVoltageAcFrequencyBE
					SheMeltTestResultACVoltageFrequencyType, 
				sheMeltTestResultForeignVoltageAcFrequencyBEValid
					SheMeltTestResultValidType, 
				sheMeltTestResultForeignCurrentAB
					SheMeltTestResultForeignCurrentType, 
				sheMeltTestResultForeignCurrentABValid
					SheMeltTestResultValidType, 
				sheMeltTestResultForeignCurrentAE
					SheMeltTestResultForeignCurrentType, 
				sheMeltTestResultForeignCurrentAEValid
					SheMeltTestResultValidType, 
				sheMeltTestResultForeignCurrentBE
					SheMeltTestResultForeignCurrentType, 
				sheMeltTestResultForeignCurrentBEValid
					SheMeltTestResultValidType, 
				sheMeltTestResultConductanceAB
					SheMeltTestResultConductanceType, 
				sheMeltTestResultConductanceABValid
					SheMeltTestResultValidType, 
				sheMeltTestResultConductanceAE
					SheMeltTestResultConductanceType, 
				sheMeltTestResultConductanceAEValid
					SheMeltTestResultValidType, 
				sheMeltTestResultConductanceBE
					SheMeltTestResultConductanceType, 
				sheMeltTestResultConductanceBEValid
					SheMeltTestResultValidType, 
				sheMeltTestResultSusceptanceAB
					SheMeltTestResultConductanceType, 
				sheMeltTestResultSusceptanceABValid
					SheMeltTestResultValidType, 
				sheMeltTestResultSusceptanceAE
					SheMeltTestResultConductanceType, 
				sheMeltTestResultSusceptanceAEValid
					SheMeltTestResultValidType, 
				sheMeltTestResultSusceptanceBE
					SheMeltTestResultConductanceType, 
				sheMeltTestResultSusceptanceBEValid
					SheMeltTestResultValidType, 
				sheMeltTestResultCheckPPA
					SheMeltTestResultCheckPpaType, 
				sheMeltTestResultCheckSplitter
					SheMeltTestResultCheckType, 
				sheMeltTestResultCheckIAD
					SheMeltTestResultCheckType
			 }

		sheMeltTestResultState OBJECT-TYPE
			SYNTAX SheMeltTestResultStateType
			MAX-ACCESS read-only
			STATUS current
			DESCRIPTION
				"The MELT result status of this interface.
				"
			DEFVAL { notTested }
			::= { sheMeltTestResultEntry 1 }

		
		sheMeltTestResultTimeStamp OBJECT-TYPE
			SYNTAX Unsigned32
			UNITS "sec"
			MAX-ACCESS read-only
			STATUS current
			DESCRIPTION
				"Timestamp of last executed MELT."
			::= { sheMeltTestResultEntry 2 }

		
		sheMeltTestResultCapacityAB OBJECT-TYPE
			SYNTAX SheMeltTestResultCapacityType
			UNITS "nF"
			MAX-ACCESS read-only
			STATUS current
			DESCRIPTION
				"The MELT result for capacity a-wire - b-wire (ring - tip)."
			DEFVAL { 0 }
			::= { sheMeltTestResultEntry 3 }

		
		sheMeltTestResultCapacityABValid OBJECT-TYPE
			SYNTAX SheMeltTestResultValidType
			MAX-ACCESS read-only
			STATUS current
			DESCRIPTION
				"The valid information for capacitytest a-wire - b-wire,  if sheMeltTestResultState = testSucceeded.
				"
			DEFVAL { invalid }
			::= { sheMeltTestResultEntry 4 }

		
		sheMeltTestResultCapacityAE OBJECT-TYPE
			SYNTAX SheMeltTestResultCapacityType
			UNITS "nF"
			MAX-ACCESS read-only
			STATUS current
			DESCRIPTION
				"The MELT result for capacity a-wire - E (ring - earth)."
			DEFVAL { 0 }
			::= { sheMeltTestResultEntry 5 }

		
		sheMeltTestResultCapacityAEValid OBJECT-TYPE
			SYNTAX SheMeltTestResultValidType
			MAX-ACCESS read-only
			STATUS current
			DESCRIPTION
				"The valid information for capacitytest a-wire - earth,  if sheMeltTestResultState = testSucceeded.
				"
			DEFVAL { invalid }
			::= { sheMeltTestResultEntry 6 }

		
		sheMeltTestResultCapacityBE OBJECT-TYPE
			SYNTAX SheMeltTestResultCapacityType
			UNITS "nF"
			MAX-ACCESS read-only
			STATUS current
			DESCRIPTION
				"The MELT result for capacity b-wire - E (tip - earth)."
			DEFVAL { 0 }
			::= { sheMeltTestResultEntry 7 }

		
		sheMeltTestResultCapacityBEValid OBJECT-TYPE
			SYNTAX SheMeltTestResultValidType
			MAX-ACCESS read-only
			STATUS current
			DESCRIPTION
				"The valid information for capacitytest b-wire - earth,  if sheMeltTestResultState = testSucceeded.
				"
			DEFVAL { invalid }
			::= { sheMeltTestResultEntry 8 }

		
		sheMeltTestResultResistanceAB OBJECT-TYPE
			SYNTAX SheMeltTestResultResistanceType
			UNITS "Ohms"
			MAX-ACCESS read-only
			STATUS current
			DESCRIPTION
				"The MELT result for resistance  a-wire - b-wire (ring - tip).
				
				Note:
				The NMS should be able to show the values also in kOhms or MOhms for better readability."
			DEFVAL { 0 }
			::= { sheMeltTestResultEntry 9 }

		
		sheMeltTestResultResistanceABValid OBJECT-TYPE
			SYNTAX SheMeltTestResultValidType
			MAX-ACCESS read-only
			STATUS current
			DESCRIPTION
				"The valid information for resistancetest a-wire - b-wire,  if sheMeltTestResultState = testSucceeded.
				"
			DEFVAL { invalid }
			::= { sheMeltTestResultEntry 10 }

		
		sheMeltTestResultResistanceBA OBJECT-TYPE
			SYNTAX SheMeltTestResultResistanceType
			UNITS "Ohms"
			MAX-ACCESS read-only
			STATUS current
			DESCRIPTION
				"The MELT result for resistance b-wire - a-wire (tip - ring).
				
				Note:
				The NMS should be able to show the values also in kOhms or MOhms for better readability."
			DEFVAL { 0 }
			::= { sheMeltTestResultEntry 11 }

		
		sheMeltTestResultResistanceBAValid OBJECT-TYPE
			SYNTAX SheMeltTestResultValidType
			MAX-ACCESS read-only
			STATUS current
			DESCRIPTION
				"The valid information for resistancetest b-wire - a-wire,  if sheMeltTestResultState = testSucceeded.
				"
			DEFVAL { invalid }
			::= { sheMeltTestResultEntry 12 }

		
		sheMeltTestResultResistanceAE OBJECT-TYPE
			SYNTAX SheMeltTestResultResistanceType
			UNITS "Ohms"
			MAX-ACCESS read-only
			STATUS current
			DESCRIPTION
				"The MELT result for resistance a-wire - E (ring - earth).
				
				Note:
				The NMS should be able to show the values also in kOhms or MOhms for better readability."
			DEFVAL { 0 }
			::= { sheMeltTestResultEntry 13 }

		
		sheMeltTestResultResistanceAEValid OBJECT-TYPE
			SYNTAX SheMeltTestResultValidType
			MAX-ACCESS read-only
			STATUS current
			DESCRIPTION
				"The valid information for resistancetest a-wire - earth,  if sheMeltTestResultState = testSucceeded.
				"
			DEFVAL { invalid }
			::= { sheMeltTestResultEntry 14 }

		
		sheMeltTestResultResistanceBE OBJECT-TYPE
			SYNTAX SheMeltTestResultResistanceType
			UNITS "Ohms"
			MAX-ACCESS read-only
			STATUS current
			DESCRIPTION
				"The MELT result for resistance b-wire - E (tip - earth).
				
				Note:
				The NMS should be able to show the values also in kOhms or MOhms for better readability."
			DEFVAL { 0 }
			::= { sheMeltTestResultEntry 15 }

		
		sheMeltTestResultResistanceBEValid OBJECT-TYPE
			SYNTAX SheMeltTestResultValidType
			MAX-ACCESS read-only
			STATUS current
			DESCRIPTION
				"The valid information for resistancetest b-wire - earth,  if sheMeltTestResultState = testSucceeded.
				"
			DEFVAL { invalid }
			::= { sheMeltTestResultEntry 16 }

		
		sheMeltTestResultForeignVoltageDcAB OBJECT-TYPE
			SYNTAX SheMeltTestResultDCVoltageType
			UNITS "100 mV"
			MAX-ACCESS read-only
			STATUS current
			DESCRIPTION
				"The MELT result for foreign voltage DC  a-wire - b-wire (ring - tip)."
			DEFVAL { 0 }
			::= { sheMeltTestResultEntry 17 }

		
		sheMeltTestResultForeignVoltageDcABValid OBJECT-TYPE
			SYNTAX SheMeltTestResultValidType
			MAX-ACCESS read-only
			STATUS current
			DESCRIPTION
				"The valid information for foreignDcVoltagetest a-wire - b-wire,  if sheMeltTestResultState = testSucceeded.
				"
			DEFVAL { invalid }
			::= { sheMeltTestResultEntry 18 }

		
		sheMeltTestResultForeignVoltageDcAE OBJECT-TYPE
			SYNTAX SheMeltTestResultDCVoltageType
			UNITS "100 mV"
			MAX-ACCESS read-only
			STATUS current
			DESCRIPTION
				"The MELT result for foreign voltage DC a-wire - E (ring - earth)."
			DEFVAL { 0 }
			::= { sheMeltTestResultEntry 19 }

		
		sheMeltTestResultForeignVoltageDcAEValid OBJECT-TYPE
			SYNTAX SheMeltTestResultValidType
			MAX-ACCESS read-only
			STATUS current
			DESCRIPTION
				"The valid information for foreignDcVoltagetest a-wire - earth,  if sheMeltTestResultState = testSucceeded.
				"
			DEFVAL { invalid }
			::= { sheMeltTestResultEntry 20 }

		
		sheMeltTestResultForeignVoltageDcBE OBJECT-TYPE
			SYNTAX SheMeltTestResultDCVoltageType
			UNITS "100 mV"
			MAX-ACCESS read-only
			STATUS current
			DESCRIPTION
				"The MELT result for foreign voltage DC b-wire - E (tip - earth)."
			DEFVAL { 0 }
			::= { sheMeltTestResultEntry 21 }

		
		sheMeltTestResultForeignVoltageDcBEValid OBJECT-TYPE
			SYNTAX SheMeltTestResultValidType
			MAX-ACCESS read-only
			STATUS current
			DESCRIPTION
				"The valid information for foreignDcVoltagetest b-wire - earth,  if sheMeltTestResultState = testSucceeded.
				"
			DEFVAL { invalid }
			::= { sheMeltTestResultEntry 22 }

		
		sheMeltTestResultForeignVoltageAcAB OBJECT-TYPE
			SYNTAX SheMeltTestResultACVoltageType
			UNITS "100 mV"
			MAX-ACCESS read-only
			STATUS current
			DESCRIPTION
				"The MELT result for foreign voltage AC  a-wire - b-wire (ring - tip)."
			DEFVAL { 0 }
			::= { sheMeltTestResultEntry 23 }

		
		sheMeltTestResultForeignVoltageAcABValid OBJECT-TYPE
			SYNTAX SheMeltTestResultValidType
			MAX-ACCESS read-only
			STATUS current
			DESCRIPTION
				"The valid information for foreignAcVoltage test a-wire - b-wire,  if sheMeltTestResultState = testSucceeded.
				"
			DEFVAL { invalid }
			::= { sheMeltTestResultEntry 24 }

		
		sheMeltTestResultForeignVoltageAcAE OBJECT-TYPE
			SYNTAX SheMeltTestResultACVoltageType
			UNITS "100 mV"
			MAX-ACCESS read-only
			STATUS current
			DESCRIPTION
				"The MELT result for foreign voltage AC a-wire - E (ring - earth)."
			DEFVAL { 0 }
			::= { sheMeltTestResultEntry 25 }

		
		sheMeltTestResultForeignVoltageAcAEValid OBJECT-TYPE
			SYNTAX SheMeltTestResultValidType
			MAX-ACCESS read-only
			STATUS current
			DESCRIPTION
				"The valid information for foreignAcVoltagetest a-wire - earth,  if sheMeltTestResultState = testSucceeded.
				"
			DEFVAL { invalid }
			::= { sheMeltTestResultEntry 26 }

		
		sheMeltTestResultForeignVoltageAcBE OBJECT-TYPE
			SYNTAX SheMeltTestResultACVoltageType
			UNITS "100 mV"
			MAX-ACCESS read-only
			STATUS current
			DESCRIPTION
				"The MELT result for foreign voltage AC b-wire - E (tip - earth)."
			DEFVAL { 0 }
			::= { sheMeltTestResultEntry 27 }

		
		sheMeltTestResultForeignVoltageAcBEValid OBJECT-TYPE
			SYNTAX SheMeltTestResultValidType
			MAX-ACCESS read-only
			STATUS current
			DESCRIPTION
				"The valid information for foreignAcVoltagetest b-wire - earth,  if sheMeltTestResultState = testSucceeded.
				"
			DEFVAL { invalid }
			::= { sheMeltTestResultEntry 28 }

		
		sheMeltTestResultForeignVoltageAcFrequencyAB OBJECT-TYPE
			SYNTAX SheMeltTestResultACVoltageFrequencyType
			UNITS "Hz"
			MAX-ACCESS read-only
			STATUS current
			DESCRIPTION
				"The MELT result for foreign voltage AC frequency a-wire - b-wire (ring - tip)."
			DEFVAL { 0 }
			::= { sheMeltTestResultEntry 29 }

		
		sheMeltTestResultForeignVoltageAcFrequencyABValid OBJECT-TYPE
			SYNTAX SheMeltTestResultValidType
			MAX-ACCESS read-only
			STATUS current
			DESCRIPTION
				"The valid information for foreignAcVoltageFrequency test a-wire - b-wire,  if sheMeltTestResultState = testSucceeded.
				"
			DEFVAL { invalid }
			::= { sheMeltTestResultEntry 30 }

		
		sheMeltTestResultForeignVoltageAcFrequencyAE OBJECT-TYPE
			SYNTAX SheMeltTestResultACVoltageFrequencyType
			UNITS "Hz"
			MAX-ACCESS read-only
			STATUS current
			DESCRIPTION
				"The MELT result for foreign voltage AC frequency a-wire - earth (ring - earth)."
			DEFVAL { 0 }
			::= { sheMeltTestResultEntry 31 }

		
		sheMeltTestResultForeignVoltageAcFrequencyAEValid OBJECT-TYPE
			SYNTAX SheMeltTestResultValidType
			MAX-ACCESS read-only
			STATUS current
			DESCRIPTION
				"The valid information for foreignAcVoltageFrequency test a-wire - earth,  if sheMeltTestResultState = testSucceeded.
				"
			DEFVAL { invalid }
			::= { sheMeltTestResultEntry 32 }

		
		sheMeltTestResultForeignVoltageAcFrequencyBE OBJECT-TYPE
			SYNTAX SheMeltTestResultACVoltageFrequencyType
			UNITS "Hz"
			MAX-ACCESS read-only
			STATUS current
			DESCRIPTION
				"The MELT result for foreign voltage AC frequency b-wire - earth (tip - earth)."
			DEFVAL { 0 }
			::= { sheMeltTestResultEntry 33 }

		
		sheMeltTestResultForeignVoltageAcFrequencyBEValid OBJECT-TYPE
			SYNTAX SheMeltTestResultValidType
			MAX-ACCESS read-only
			STATUS current
			DESCRIPTION
				"The valid information for foreignAcVoltageFrequency test b-wire - earth,  if sheMeltTestResultState = testSucceeded.
				"
			DEFVAL { invalid }
			::= { sheMeltTestResultEntry 34 }

		
		sheMeltTestResultForeignCurrentAB OBJECT-TYPE
			SYNTAX SheMeltTestResultForeignCurrentType
			UNITS "uA"
			MAX-ACCESS read-only
			STATUS current
			DESCRIPTION
				"The MELT result for foreign current test  a-wire - b-wire (ring - tip)."
			DEFVAL { 0 }
			::= { sheMeltTestResultEntry 35 }

		
		sheMeltTestResultForeignCurrentABValid OBJECT-TYPE
			SYNTAX SheMeltTestResultValidType
			MAX-ACCESS read-only
			STATUS current
			DESCRIPTION
				"The valid information for foreignCurrenttest a-wire - b-wire,  if sheMeltTestResultState = testSucceeded.
				"
			DEFVAL { invalid }
			::= { sheMeltTestResultEntry 36 }

		
		sheMeltTestResultForeignCurrentAE OBJECT-TYPE
			SYNTAX SheMeltTestResultForeignCurrentType
			UNITS "uA"
			MAX-ACCESS read-only
			STATUS current
			DESCRIPTION
				"The MELT result for foreign current test  a-wire - E (ring - earth)."
			DEFVAL { 0 }
			::= { sheMeltTestResultEntry 37 }

		
		sheMeltTestResultForeignCurrentAEValid OBJECT-TYPE
			SYNTAX SheMeltTestResultValidType
			MAX-ACCESS read-only
			STATUS current
			DESCRIPTION
				"The valid information for foreignCurrenttest a-wire - earth,  if sheMeltTestResultState = testSucceeded.
				"
			DEFVAL { invalid }
			::= { sheMeltTestResultEntry 38 }

		
		sheMeltTestResultForeignCurrentBE OBJECT-TYPE
			SYNTAX SheMeltTestResultForeignCurrentType
			UNITS "uA"
			MAX-ACCESS read-only
			STATUS current
			DESCRIPTION
				"The MELT result for foreign current test  b-wire - E (tip - earth)."
			DEFVAL { 0 }
			::= { sheMeltTestResultEntry 39 }

		
		sheMeltTestResultForeignCurrentBEValid OBJECT-TYPE
			SYNTAX SheMeltTestResultValidType
			MAX-ACCESS read-only
			STATUS current
			DESCRIPTION
				"The valid information for foreignCurrenttest b-wire - earth,  if sheMeltTestResultState = testSucceeded.
				"
			DEFVAL { invalid }
			::= { sheMeltTestResultEntry 40 }

		
		sheMeltTestResultConductanceAB OBJECT-TYPE
			SYNTAX SheMeltTestResultConductanceType
			UNITS "100 nS"
			MAX-ACCESS read-only
			STATUS current
			DESCRIPTION
				"The MELT result for conductance test  a-wire - b-wire (ring - tip)."
			DEFVAL { 0 }
			::= { sheMeltTestResultEntry 41 }

		
		sheMeltTestResultConductanceABValid OBJECT-TYPE
			SYNTAX SheMeltTestResultValidType
			MAX-ACCESS read-only
			STATUS current
			DESCRIPTION
				"The valid information for conductancetest a-wire - b-wire,  if sheMeltTestResultState = testSucceeded.
				"
			DEFVAL { invalid }
			::= { sheMeltTestResultEntry 42 }

		
		sheMeltTestResultConductanceAE OBJECT-TYPE
			SYNTAX SheMeltTestResultConductanceType
			UNITS "100 nS"
			MAX-ACCESS read-only
			STATUS current
			DESCRIPTION
				"The MELT result for conductance test  a-wire - earth (ring - earth)."
			DEFVAL { 0 }
			::= { sheMeltTestResultEntry 43 }

		
		sheMeltTestResultConductanceAEValid OBJECT-TYPE
			SYNTAX SheMeltTestResultValidType
			MAX-ACCESS read-only
			STATUS current
			DESCRIPTION
				"The valid information for conductancetest a-wire - earth,  if sheMeltTestResultState = testSucceeded.
				"
			DEFVAL { invalid }
			::= { sheMeltTestResultEntry 44 }

		
		sheMeltTestResultConductanceBE OBJECT-TYPE
			SYNTAX SheMeltTestResultConductanceType
			UNITS "100 nS"
			MAX-ACCESS read-only
			STATUS current
			DESCRIPTION
				"The MELT result for conductance test  b-wire - earth (tip - earth)."
			DEFVAL { 0 }
			::= { sheMeltTestResultEntry 45 }

		
		sheMeltTestResultConductanceBEValid OBJECT-TYPE
			SYNTAX SheMeltTestResultValidType
			MAX-ACCESS read-only
			STATUS current
			DESCRIPTION
				"The valid information for conductancetest b-wire - earth,  if sheMeltTestResultState = testSucceeded.
				"
			DEFVAL { invalid }
			::= { sheMeltTestResultEntry 46 }

		
		sheMeltTestResultSusceptanceAB OBJECT-TYPE
			SYNTAX SheMeltTestResultConductanceType
			UNITS "100 nS"
			MAX-ACCESS read-only
			STATUS current
			DESCRIPTION
				"The MELT result for susceptance test  a-wire - b-wire (ring - tip)."
			DEFVAL { 0 }
			::= { sheMeltTestResultEntry 47 }

		
		sheMeltTestResultSusceptanceABValid OBJECT-TYPE
			SYNTAX SheMeltTestResultValidType
			MAX-ACCESS read-only
			STATUS current
			DESCRIPTION
				"The valid information for susceptancetest a-wire - b-wire,  if sheMeltTestResultState = testSucceeded.
				"
			DEFVAL { invalid }
			::= { sheMeltTestResultEntry 48 }

		
		sheMeltTestResultSusceptanceAE OBJECT-TYPE
			SYNTAX SheMeltTestResultConductanceType
			UNITS "100 nS"
			MAX-ACCESS read-only
			STATUS current
			DESCRIPTION
				"The MELT result for susceptance test  a-wire - earth (ring - earth)."
			DEFVAL { 0 }
			::= { sheMeltTestResultEntry 49 }

		
		sheMeltTestResultSusceptanceAEValid OBJECT-TYPE
			SYNTAX SheMeltTestResultValidType
			MAX-ACCESS read-only
			STATUS current
			DESCRIPTION
				"The valid information for susceptancetest a-wire - earth,  if sheMeltTestResultState = testSucceeded.
				"
			DEFVAL { invalid }
			::= { sheMeltTestResultEntry 50 }

		
		sheMeltTestResultSusceptanceBE OBJECT-TYPE
			SYNTAX SheMeltTestResultConductanceType
			UNITS "100 nS"
			MAX-ACCESS read-only
			STATUS current
			DESCRIPTION
				"The MELT result for susceptance test  b-wire - earth (tip - earth)."
			DEFVAL { 0 }
			::= { sheMeltTestResultEntry 51 }

		
		sheMeltTestResultSusceptanceBEValid OBJECT-TYPE
			SYNTAX SheMeltTestResultValidType
			MAX-ACCESS read-only
			STATUS current
			DESCRIPTION
				"The valid information for susceptancetest b-wire - earth,  if sheMeltTestResultState = testSucceeded.
				"
			DEFVAL { invalid }
			::= { sheMeltTestResultEntry 52 }

		
		sheMeltTestResultCheckPPA OBJECT-TYPE
			SYNTAX SheMeltTestResultCheckPpaType
			MAX-ACCESS read-only
			STATUS current
			DESCRIPTION
				"The MELT result for PPA test.
				"
			DEFVAL { notTested }
			::= { sheMeltTestResultEntry 53 }

		
		sheMeltTestResultCheckSplitter OBJECT-TYPE
			SYNTAX SheMeltTestResultCheckType
			MAX-ACCESS read-only
			STATUS current
			DESCRIPTION
				"The MELT result for Splitter test.
				"
			DEFVAL { notTested }
			::= { sheMeltTestResultEntry 54 }

		
		sheMeltTestResultCheckIAD OBJECT-TYPE
			SYNTAX SheMeltTestResultCheckType
			MAX-ACCESS read-only
			STATUS current
			DESCRIPTION
				"The MELT result for IAD test.
				"
			DEFVAL { notTested }
			::= { sheMeltTestResultEntry 55 }

		
--  End: Add some parameters.
-- -----------------------------------------------------------------
--       Single End Loop Test Notifications for ADSL
-- -----------------------------------------------------------------
-- 
		sheMeltNotifications OBJECT IDENTIFIER ::= { sheMelt 10 }

		
		sheMeltTestRequestParametersModified NOTIFICATION-TYPE
			OBJECTS { sheMeltTestRequestControlReqTimeStamp,  sheMeltTestParameterFreq1 }
			STATUS current
			DESCRIPTION 
				"The MELT testparameters are modified."
			::= { sheMeltNotifications 1 }

		
		sheMeltTestRequestStateModified NOTIFICATION-TYPE
			OBJECTS { sheMeltTestRequestControlReqTimeStamp,  sheMeltTestRequestIfState,  sheMeltTestRequestIuState }
			STATUS current
			DESCRIPTION 
				"The MELT state of an interface was modified by command or by NE."
			::= { sheMeltNotifications 2 }

		
		sheMeltTestRequestIfTestToneIndexModified NOTIFICATION-TYPE
			OBJECTS { sheMeltTestRequestControlReqTimeStamp,  sheMeltTestRequestTestToneIndex }
			STATUS current
			DESCRIPTION 
				"The used test tone set of an interface (assignment  interface - test tone index) was modified."
			::= { sheMeltNotifications 3 }

		
		sheMeltTestToneEntryCreated NOTIFICATION-TYPE
			OBJECTS { sheMeltTestToneControlIndex,  sheMeltTestToneControlReqTimeStamp,  sheMeltTestToneControlFreq1,  sheMeltTestToneControlFreq2,  sheMeltTestToneControlLevel
				 }
			STATUS current
			DESCRIPTION 
				"Configuration trap for new created MELT testTone set."
			::= { sheMeltNotifications 4 }

		
		sheMeltTestToneEntryModified NOTIFICATION-TYPE
			OBJECTS { sheMeltTestToneControlIndex,  sheMeltTestToneControlReqTimeStamp,  sheMeltTestToneControlFreq1,  sheMeltTestToneControlFreq2,  sheMeltTestToneControlLevel
				 }
			STATUS current
			DESCRIPTION 
				"Configuration trap for modified MELT testTone set."
			::= { sheMeltNotifications 5 }

		
		sheMeltTestToneEntryDeleted NOTIFICATION-TYPE
			OBJECTS { sheMeltTestToneControlIndex,  sheMeltTestToneControlReqTimeStamp }
			STATUS current
			DESCRIPTION 
				"Configuration trap for delete a MELT testTone set."
			::= { sheMeltNotifications 6 }

		
		sheMeltConformance OBJECT IDENTIFIER ::= { sheMelt 100 }

		
		sheMeltCompliances OBJECT IDENTIFIER ::= { sheMeltConformance 1 }

		
		sheMeltMibCompliance MODULE-COMPLIANCE
			STATUS current
			DESCRIPTION 
				"Description."
			MODULE -- this module
				MANDATORY-GROUPS { sheMeltGroup,  sheMeltControlGroup,  sheMeltNotificationGroup }
			::= { sheMeltCompliances 1 }

		
		sheMeltGroups OBJECT IDENTIFIER ::= { sheMeltConformance 2 }

		
		sheMeltGroup OBJECT-GROUP
			OBJECTS { sheMeltTestParameterFreq1,  sheMeltTestRequestIfState,  sheMeltTestRequestIuState,  sheMeltTestRequestTestToneIndex,  sheMeltTestToneIndex,  
				sheMeltTestToneFreq1,  sheMeltTestToneFreq2,  sheMeltTestToneLevel,  sheMeltTestResultState,  sheMeltTestResultTimeStamp,  
				sheMeltTestResultCapacityAB,  sheMeltTestResultCapacityABValid,  sheMeltTestResultCapacityAE,  sheMeltTestResultCapacityAEValid,  sheMeltTestResultCapacityBE,  
				sheMeltTestResultCapacityBEValid,  sheMeltTestResultResistanceAB,  sheMeltTestResultResistanceABValid,  sheMeltTestResultResistanceBA,  sheMeltTestResultResistanceBAValid,  
				sheMeltTestResultResistanceAE,  sheMeltTestResultResistanceAEValid,  sheMeltTestResultResistanceBE,  sheMeltTestResultResistanceBEValid,  sheMeltTestResultForeignVoltageDcAB,  
				sheMeltTestResultForeignVoltageDcABValid,  sheMeltTestResultForeignVoltageDcAE,  sheMeltTestResultForeignVoltageDcAEValid,  sheMeltTestResultForeignVoltageDcBE,  sheMeltTestResultForeignVoltageDcBEValid,  
				sheMeltTestResultForeignVoltageAcAB,  sheMeltTestResultForeignVoltageAcABValid,  sheMeltTestResultForeignVoltageAcAE,  sheMeltTestResultForeignVoltageAcAEValid,  sheMeltTestResultForeignVoltageAcBE,  
				sheMeltTestResultForeignVoltageAcBEValid,  sheMeltTestResultForeignCurrentAB,  sheMeltTestResultForeignCurrentABValid,  sheMeltTestResultForeignCurrentAE,  sheMeltTestResultForeignCurrentAEValid,  
				sheMeltTestResultForeignCurrentBE,  sheMeltTestResultForeignCurrentBEValid,  sheMeltTestResultConductanceAB,  sheMeltTestResultConductanceABValid,  sheMeltTestResultConductanceAE,  
				sheMeltTestResultConductanceAEValid,  sheMeltTestResultConductanceBE,  sheMeltTestResultConductanceBEValid,  sheMeltTestResultSusceptanceAB,  sheMeltTestResultSusceptanceABValid,  
				sheMeltTestResultSusceptanceAE,  sheMeltTestResultSusceptanceAEValid,  sheMeltTestResultSusceptanceBE,  sheMeltTestResultSusceptanceBEValid,  sheMeltTestResultCheckPPA,  
				sheMeltTestResultCheckSplitter,  sheMeltTestResultCheckIAD,  sheMeltTestResultForeignVoltageAcFrequencyAB,  sheMeltTestResultForeignVoltageAcFrequencyABValid,  sheMeltTestResultForeignVoltageAcFrequencyAE,  
				sheMeltTestResultForeignVoltageAcFrequencyAEValid,  sheMeltTestResultForeignVoltageAcFrequencyBE,  sheMeltTestResultForeignVoltageAcFrequencyBEValid }
			STATUS current
			DESCRIPTION 
				" "
			::= { sheMeltGroups 1 }

		
		sheMeltControlGroup OBJECT-GROUP
			OBJECTS { sheMeltTestRequestControlReq,  sheMeltTestRequestControlIndex,  sheMeltTestRequestControlStatus,  sheMeltTestRequestControlTimer,  sheMeltTestRequestControlReqResult,  
				sheMeltTestRequestControlReqTimeStamp,  sheMeltTestRequestControlTestToneIndex,  sheMeltTestRequestControlParameterFreq1,  sheMeltTestToneControlReq,  sheMeltTestToneControlIndex,  
				sheMeltTestToneControlStatus,  sheMeltTestToneControlTimer,  sheMeltTestToneControlReqResult,  sheMeltTestToneControlReqTimeStamp,  sheMeltTestToneControlFreq1,  
				sheMeltTestToneControlFreq2,  sheMeltTestToneControlLevel }
			STATUS current
			DESCRIPTION 
				"Description."
			::= { sheMeltGroups 2 }

		
		sheMeltNotificationGroup NOTIFICATION-GROUP
			NOTIFICATIONS { sheMeltTestRequestParametersModified,  sheMeltTestRequestStateModified,  sheMeltTestRequestIfTestToneIndexModified,  sheMeltTestToneEntryCreated,  sheMeltTestToneEntryModified,  
				sheMeltTestToneEntryDeleted }
			STATUS current
			DESCRIPTION 
				" "
			::= { sheMeltGroups 3 }

		
	
	END

--
-- she-melt-mib.mib
--
