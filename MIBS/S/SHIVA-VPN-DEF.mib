SHIVA-VPN-DEF DEFINITIONS ::= BEGIN

-- This MIB contains OID definitions for Shiva VPN products.

IMPORTS
  shivaVpn
      FROM SHIVA-MIB;

  vpnProducts           OBJECT IDENTIFIER ::= { shivaVpn 1 }
  vpnCapabilities       OBJECT IDENTIFIER ::= { shivaVpn 2 }
  vpnRequirements       OBJECT IDENTIFIER ::= { shivaVpn 3 }
  vpnExperimental       OBJECT IDENTIFIER ::= { shivaVpn 4 }
  vpnRel6Products       OBJECT IDENTIFIER ::= { shivaVpn 6 }

  vpnGateways           OBJECT IDENTIFIER ::= { vpnProducts 1 }

  vpnSystem             OBJECT IDENTIFIER ::= { vpnGateways 1 }
  vpnMemory             OBJECT IDENTIFIER ::= { vpnGateways 2 }
  vpnUtilization        OBJECT IDENTIFIER ::= { vpnGateways 3 }
  vpnConfig             OBJECT IDENTIFIER ::= { vpnGateways 4 }
  vpnArp                OBJECT IDENTIFIER ::= { vpnGateways 5 }
  vpnIp                 OBJECT IDENTIFIER ::= { vpnGateways 6 }
  vpnTunnel             OBJECT IDENTIFIER ::= { vpnGateways 7 }

  -- The following OBJECT IDENTIFIER versions are used as the
  -- value of sysObjectID IN THE ShivICE software for the VPN products.
  -- They were used by both the LanRover VPN Gateway and LanRover VPN Express.
  -- Note that the sysObjectID is being used to represent the software release,
  -- not the hardware platform.

  vpnGateway65     OBJECT IDENTIFIER ::= { vpnRel6Products 50 } -- 6.5
  vpnGateway66     OBJECT IDENTIFIER ::= { vpnRel6Products 60 } -- 6.6
  vpnGateway67     OBJECT IDENTIFIER ::= { vpnRel6Products 70 } -- 6.7
  vpnGateway68     OBJECT IDENTIFIER ::= { vpnRel6Products 80 } -- 6.8


  vpnLanRoverVPNGatewayCapabilities
                   OBJECT IDENTIFIER ::= { vpnCapabilities 1 }
END
