-- 	$Id: shiva-time.asn,v 1.4 1996/01/16 17:05:37 dfox Exp $

--
-- 	Copyright 1992, 1993, 1995, 1996 Shiva Corporation
--

SHIVA-TIME-MIB DEFINITIONS ::= BEGIN

IMPORTS
    	OBJECT-TYPE
    		FROM RFC-1212		-- Concise MIB Definitions
    	time
    		FROM SHIVA-MIB;

    timeRTC OBJECT-TYPE
  	SYNTAX  INTEGER
  	ACCESS  read-write
  	STATUS  mandatory
	DESCRIPTION
		"The date and time, as kept by the device's Real
		Time Clock hardware, represented as the number of
		seconds elapsed since Midnight on January 1st, 1970
		GMT.  This value may be zero if the device has no
		RTC, or the RTC is halted."
	::= { time 1 }

    timeZone OBJECT-TYPE
  	SYNTAX  INTEGER
  	ACCESS  read-write
  	STATUS  mandatory
	DESCRIPTION
		"The timezone in which the device is located,
		represented as an offset from GMT in seconds."
	::= { time 2 }

    timeOfDay OBJECT-TYPE
  	SYNTAX  INTEGER
  	ACCESS  read-write
  	STATUS  mandatory
	DESCRIPTION
		"This device's notion of the date and time,
		represented as the number of seconds elapsed since
		Midnight on January 1st, 1970 GMT.  This may differ
		from timeRTC if the device is using an external time
		server."
	::= { time 3 }


END
