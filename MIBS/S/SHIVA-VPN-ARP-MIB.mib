SHIVA-VPN-ARP-MIB DEFINITIONS ::= BEGIN

IMPORTS
  Counter
      FROM RFC1155-SMI
  OBJECT-TYPE
      FROM RFC-1212
  ifIndex
      FROM RFC1213-MIB
  vpnArp
      FROM SHIVA-VPN-DEF;

  arpConfig OBJECT IDENTIFIER ::= { vpnArp 1 }
  arpStatus OBJECT IDENTIFIER ::= { vpnArp 2 }

  arpIfTable OBJECT-TYPE
      SYNTAX SEQUENCE OF ArpIfEntry
      ACCESS not-accessible
      STATUS mandatory
      DESCRIPTION
          "The (conceptual) table containing information
           on configured interfaces running the ARP protocol.
           This table augments the ifTable for non-tunnel
           interfaces."
      ::= { arpStatus 50 }

  arpIfEntry OBJECT-TYPE
      SYNTAX ArpIfEntry
      ACCESS not-accessible
      STATUS mandatory
      DESCRIPTION
          "An entry (conceptual row) containing the information
           on a particular ARP interface."
      INDEX { ifIndex }
      ::= { arpIfTable 1 }

  ArpIfEntry ::=
      SEQUENCE {
            arpIfInPkts
                Counter,
            arpIfOutPkts
                Counter,
            arpIfInOctets
                Counter,
            arpIfOutOctets
                Counter
        }

  arpIfInPkts OBJECT-TYPE
      SYNTAX Counter
      ACCESS read-only
      STATUS mandatory
      DESCRIPTION
          "The number of packets passed in to the ARP
           layer on this interface."
      ::= { arpIfEntry 1 }

  arpIfOutPkts OBJECT-TYPE
      SYNTAX Counter
      ACCESS read-only
      STATUS mandatory
      DESCRIPTION
          "The number of packets passed out from the ARP
           layer on this interface."
      ::= { arpIfEntry 2 }

  arpIfInOctets OBJECT-TYPE
      SYNTAX Counter
      ACCESS read-only
      STATUS mandatory
      DESCRIPTION
          "The number of bytes passed in to the ARP
           layer on this interface.  This includes
           only the length of the ARP packets proper,
           not any encapsulation from lower layers or
           tunnels."
      ::= { arpIfEntry 3 }

  arpIfOutOctets OBJECT-TYPE
      SYNTAX Counter
      ACCESS read-only
      STATUS mandatory
      DESCRIPTION
          "The number of bytes passed out from the ARP
           layer on this interface.  This includes
           only the length of the ARP packets proper,
           not any encapsulation for lower layers or
           tunnels."
      ::= { arpIfEntry 4 }

END
