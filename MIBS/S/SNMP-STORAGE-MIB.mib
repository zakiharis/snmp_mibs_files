-- extracted from draft-schoenw-storage-type-00.txt
-- at Sun Jun 24 06:04:48 2001

   SNMP-STORAGE-MIB DEFINITIONS ::= BEGIN

   IMPORTS
       MODULE-IDENTITY, OBJECT-TYPE, snmpModules, Unsigned32
   	FROM SNMPv2-SMI

       DateAndTime, AutonomousType
           FROM SNMPv2-TC

       MODULE-COMPLIANCE, OBJECT-GROUP
           FROM SNMPv2-CONF

       SnmpAdminString
           FROM SNMP-FRAMEWORK-MIB;

   snmpStorageMIB MODULE-IDENTITY
       LAST-UPDATED "200106210000Z"
       ORGANIZATION "IETF"
       CONTACT-INFO
           "Juergen Schoenwaelder (Editor)
            TU Braunschweig
            Bueltenweg 74/75
            38106 Braunschweig, Germany

            Phone: +49 531 391-3289
            EMail: schoenw@ibr.cs.tu-bs.de

            Send comments to <mibs@ops.ietf.org>."
       DESCRIPTION
   	"This MIB modules provides objects that allow management
            applications to commit non-volatile conceptual rows to
            stable storage."
       REVISION    "200106210000Z"
       DESCRIPTION "The initial revision, published as RFC XXXX."
       ::= { snmpModules 1 }

   snmpStorageObjects     OBJECT IDENTIFIER ::= { snmpStorageMIB 1 }
   snmpStorageConformance OBJECT IDENTIFIER ::= { snmpStorageMIB 2 }

   snmpStorageGlobControl OBJECT-TYPE
       SYNTAX	INTEGER { nop(1), write(2) }
       MAX-ACCESS	read-write
       STATUS	current
       DESCRIPTION
   	"Setting this object to write(2) causes the agent to sync
            not yet committed non-volatile MIB data to stable storage.

            Setting this object to write(2) while the value of the
            snmpStorageGlobStatus object is writing(3) leads to an
            inconsitent value error.

            Setting this object to nop(1) always succeeds and has no
            effect.

            Management applications are advised to make use of the
            snmpSetSerialNo object defined in the SNMPv2-MIB to
            coordinate their use of this object."
       ::= { snmpStorageObjects 1 }

   snmpStorageGlobStatus OBJECT-TYPE
       SYNTAX	INTEGER {
   		    other(1),
   		    dirty(2),		-- can probably not be implemented ?
   		    writing(3),		-- perhaps we only need 'idle' and
   		    finished(4),	-- 'inProgress'?
                       error(5)
   		}
       MAX-ACCESS	read-only
       STATUS	current
       DESCRIPTION
   	"This object reports the current status of the write operation."
       ::= { snmpStorageObjects 2 }

   snmpStorageGlobError OBJECT-TYPE
       SYNTAX	SnmpAdminString
       MAX-ACCESS	read-only
       STATUS	current
       DESCRIPTION
   	"This object contains a descriptive error message if the
   	 last attempt to write global stable storage has failed."
       ::= { snmpStorageObjects 3 }

   snmpStorageGlobErrorTime OBJECT-TYPE
       SYNTAX	DateAndTime
       MAX-ACCESS	read-only
       STATUS	current
       DESCRIPTION
   	"The data and time when the snmpStorageGlobError was last
   	 updated. The value '0000000000000000'H is returned if
   	 snmpStorageGlobError has not yet been updated after the
   	 initialization."
       ::= { snmpStorageObjects 4 }

   snmpStorageTable OBJECT-TYPE
       SYNTAX	SEQUENCE OF SnmpStorageEntry
       MAX-ACCESS	not-accessible
       STATUS	current
       DESCRIPTION
   	""
       ::= { snmpStorageObjects 5 }

   snmpStorageEntry OBJECT-TYPE
       SYNTAX	SnmpStorageEntry
       MAX-ACCESS	not-accessible
       STATUS	current
       DESCRIPTION
   	""
       INDEX { snmpStorageIndex }
       ::= { snmpStorageTable 1 }

   SnmpStorageEntry ::= SEQUENCE {
       snmpStorageIndex		Unsigned32,
       snmpStorageDescr		SnmpAdminString,
       snmpStorageID		AutonomousType,
       snmpStorageControl		INTEGER,
       snmpStorageStatus		INTEGER,
       snmpStorageError		SnmpAdminString,
       snmpStorageErrorTime	DateAndTime
   }

   snmpStorageIndex OBJECT-TYPE
       SYNTAX	Unsigned32 (1..4294967295)
       MAX-ACCESS	not-accessible
       STATUS	current
       DESCRIPTION
   	"The index which uniquely identifies a row in the
   	 snmpStorageTable."
       ::= { snmpStorageEntry 1 }

   snmpStorageDescr OBJECT-TYPE
       SYNTAX	SnmpAdminString
       MAX-ACCESS	read-only
       STATUS	current
       DESCRIPTION
   	"A textual description which explains the scope of
            MIB data which is controlled by this row."
       ::= { snmpStorageEntry 2 }

   snmpStorageID OBJECT-TYPE
       SYNTAX	AutonomousType
       MAX-ACCESS	read-only
       STATUS	current
       DESCRIPTION
   	""
       ::= { snmpStorageEntry 3 }

   snmpStorageControl OBJECT-TYPE
       SYNTAX	INTEGER { nop(1), write(2) }
       MAX-ACCESS	read-write
       STATUS	current
       DESCRIPTION
   	"Setting this object to write(2) causes the agent to sync
            not yet committed non-volatile MIB data to stable storage.

            Setting this object to write(2) while the value of the
            snmpStorageStatus object is writing(3) leads to an
            inconsitent value error.

            Setting this object to nop(1) always succeeds and has no
            effect.

            Management applications are advised to make use of the
            snmpSetSerialNo object defined in the SNMPv2-MIB to
            coordinate their use of this object."
       ::= { snmpStorageEntry 4 }

   snmpStorageStatus OBJECT-TYPE
       SYNTAX	INTEGER {
                       other(1),
                       dirty(2),
                       writing(3),
                       finished(4),
                       error(5)
                   }
       MAX-ACCESS	read-only
       STATUS	current
       DESCRIPTION
   	"This object reports the current status of the write operation."
       ::= { snmpStorageEntry 5 }

   snmpStorageError OBJECT-TYPE
       SYNTAX	SnmpAdminString
       MAX-ACCESS	read-only
       STATUS	current
       DESCRIPTION
   	"This object contains a descriptive error message if the
   	 last attempt to write into stable storage has failed."
       ::= { snmpStorageEntry 6 }

   snmpStorageErrorTime OBJECT-TYPE
       SYNTAX	DateAndTime
       MAX-ACCESS	read-only
       STATUS	current
       DESCRIPTION
   	"The data and time when the snmpStorageError was last
   	 updated. The value '0000000000000000'H is returned if
   	 snmpStorageError has not yet been updated after the
   	 initialization."
       ::= { snmpStorageEntry 7 }

   snmpStorageCompliances OBJECT IDENTIFIER ::= { snmpStorageConformance 1 }
   snmpStorageGroups      OBJECT IDENTIFIER ::= { snmpStorageConformance 2 }

   snmpStorageCompliance MODULE-COMPLIANCE
       STATUS      current
       DESCRIPTION
           ""
       MODULE      -- this module
       MANDATORY-GROUPS { snmpStorageGlobalGroup }
       GROUP       snmpStorageGroup
       DESCRIPTION
           "Implementation of this group is only mandatory for
            systems that support multiple write buttons for
            different sets of MIB objects."
       ::= { snmpStorageCompliances 1 }

   snmpStorageGlobalGroup OBJECT-GROUP
       OBJECTS { snmpStorageGlobControl, snmpStorageGlobStatus,
                 snmpStorageGlobError, snmpStorageGlobErrorTime }
       STATUS      current
       DESCRIPTION
           ""
       ::= { snmpStorageGroups 1 }

   snmpStorageGroup OBJECT-GROUP
       OBJECTS { snmpStorageDescr, snmpStorageID,
                 snmpStorageControl, snmpStorageStatus,
                 snmpStorageError, snmpStorageErrorTime }
       STATUS      current
       DESCRIPTION
           ""
       ::= { snmpStorageGroups 2 }

   END

-- 
--    Copyright (C) The Internet Society (2001).  All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
--
