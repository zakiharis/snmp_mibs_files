SHIVA-VPN-MEMORY-MIB DEFINITIONS ::= BEGIN

-- This MIB contains objects for managing memory use on Shiva VPN
-- products.

IMPORTS
  Gauge
      FROM RFC1155-SMI
  OBJECT-TYPE
      FROM RFC-1212
  vpnMemory
      FROM SHIVA-VPN-DEF;

  freeMem OBJECT-TYPE
      SYNTAX Gauge
      ACCESS read-only
      STATUS mandatory
      DESCRIPTION
          "The number of bytes of unused memory in
           this VPN Gateway."
      ::= { vpnMemory 1 }    

  totalMem OBJECT-TYPE
      SYNTAX Gauge
      ACCESS read-only
      STATUS mandatory
      DESCRIPTION
          "The total number of bytes of memory available
           in this VPN Gateway."
      ::= { vpnMemory 2 }

END
