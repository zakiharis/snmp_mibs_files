--
-- Copyright 1996, 1997, 1998 Shiva Corporation
-- Copyright 1999, 2000 Intel Network Systems, Inc.  All Rights Reserved
--
-- Conformance statements for Shiva LanRover Access Switch
--

-- These conformance statements note what IETF MIBs, defined in the
-- SNMPv2-SMI syntax are implemented, are implemented.
-- The agent itself is an SNMPv1 agent.

-- Note that the conformance statements may be a bit off in older
-- software releases that implement obsolete Internet Draft versions of
-- MIBs.  This is because we have to test compilation of this MIB against the
-- latest versions of the MIB, which may have different OBJECT-GROUPS
-- and NOTIFICATION-GROUPS, or may have obsoleted variables.


SHIVA-LANROVER-ACCESS-SWITCH-CAP DEFINITIONS ::= BEGIN

IMPORTS
    MODULE-IDENTITY
        FROM SNMPv2-SMI
    AGENT-CAPABILITIES
        FROM SNMPv2-CONF
    conformance
        FROM SHIVA-MIB;

shivaLanRoverAccessSwitchCapabilities MODULE-IDENTITY
    LAST-UPDATED	"0005012130Z"
    ORGANIZATION	"Intel Network Systems Inc"
    CONTACT-INFO	"Intel Network Systems Inc
			28 Crosby Drive
			Bedford, MA  01730"
    DESCRIPTION		"The Shiva LanRover Access Switch Capabilities module"
    REVISION		"9811061830Z"
    DESCRIPTION		"The initial revision of this module."
    REVISION		"9811111830Z"
    DESCRIPTION		"Correct DESCRIPTION in MODULE-IDENTITY."
    REVISION            "0005012130Z"
    DESCRIPTION         "Add release 6.1.1p1"
    ::= { conformance 4 }

shivaLanRoverAccessSwitchAgent457 AGENT-CAPABILITIES
    PRODUCT-RELEASE	"LanRover Access Switch 4.5.7"
    STATUS		current
    DESCRIPTION		"SNMP Agent in LanRover Access Switch 4.5.7 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover Access Switch/E.

    SUPPORTS		EtherLike-MIB	-- RFC 1650
	INCLUDES	{ etherStatsGroup, etherCollisionTableGroup }


    -- RS-232-MIB supported FOR UART1, UART2, and all modems
    -- on the Digital Modem Card.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    SUPPORTS		RIPv2-MIB	-- RFC 1724
	INCLUDES	{ rip2GlobalGroup, rip2IfStatGroup,
			  rip2IfConfGroup }

	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
	                    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."


    SUPPORTS		FRAME-RELAY-DTE-MIB	
			-- draft-ietf-iplpdn-frmib-dte-05.asn,
			-- which is a superset of RFC 1315 but in SMIv2.
	INCLUDES	{ frPortGroup, frCircuitGroup, frErrGroup, 
			  frTrapGroup, frNotificationGroup }

	VARIATION	frDlcmiState
	    ACCESS	read-only
	    DESCRIPTION	"Row creation is not required for the frDlcmiTable."

	VARIATION	frDlcmiAddress
	    ACCESS	read-only
	    DESCRIPTION	"Row creation is not required for the frDlcmiTable."

	VARIATION	frDlcmiAddressLen
	    ACCESS	read-only
	    DESCRIPTION	"Row creation is not required for the frDlcmiTable."

	VARIATION	frDlcmiPollingInterval
	    ACCESS	read-only
	    DESCRIPTION	"Row creation is not required for the frDlcmiTable."

	VARIATION	frDlcmiFullEnquiryInterval
	    ACCESS	read-only
	    DESCRIPTION	"Row creation is not required for the frDlcmiTable."

	VARIATION	frDlcmiErrorThreshold
	    ACCESS	read-only
	    DESCRIPTION	"Row creation is not required for the frDlcmiTable."

	VARIATION	frDlcmiMonitoredEvents
	    ACCESS	read-only
	    DESCRIPTION	"Row creation is not required for the frDlcmiTable."

	VARIATION	frDlcmiMaxSupportedVCs
	    ACCESS	read-only
	    DESCRIPTION	"Row creation is not required for the frDlcmiTable."

	VARIATION	frDlcmiMulticast
	    ACCESS	read-only
	    DESCRIPTION	"Row creation is not required for the frDlcmiTable."

	VARIATION	frDlcmiRowStatus
	    ACCESS	read-only
	    DESCRIPTION	"Row creation is not required for the frDlcmiTable."

	VARIATION	frCircuitState
	    ACCESS	read-only
	    DESCRIPTION	"Row creation is not required for the frCircuitTable."

	VARIATION	frCircuitCommittedBurst
	    ACCESS	read-only
	    DESCRIPTION	"Row creation is not required for the frCircuitTable."

	VARIATION	frCircuitExcessBurst
	    ACCESS	read-only
	    DESCRIPTION	"Row creation is not required for the frCircuitTable."

	VARIATION	frCircuitThroughput
	    ACCESS	read-only
	    DESCRIPTION	"Row creation is not required for the frCircuitTable."

	VARIATION	frCircuitMulticast
	    ACCESS	read-only
	    DESCRIPTION	"Row creation is not required for the frCircuitTable."

	VARIATION	frCircuitLogicalIfIndex
	    ACCESS	read-only
	    DESCRIPTION	"Row creation is not required for the frCircuitTable."

	VARIATION	frCircuitRowStatus
	    ACCESS	read-only
	    DESCRIPTION	"Row creation is not required for the frCircuitTable."


    SUPPORTS		ISDN-MIB -- draft-ietf-isdnmib-snmp-isdn-mib-04.txt
	INCLUDES	{ isdnMibBasicRateGroup, isdnMibSignalingGroup,
			  isdnMibEndpointGroup }

	VARIATION	isdnBasicTblIfType
	    ACCESS	read-only
	    DESCRIPTION	"No write access via SNMP."

	VARIATION	isdnBasicTblLineTopology
	    ACCESS	read-only
	    DESCRIPTION	"No write access via SNMP."

	VARIATION	isdnBasicTblIfMode
	    ACCESS	read-only
	    DESCRIPTION	"No write access via SNMP."

	VARIATION	isdnBasicTblSignalMode
	    ACCESS	read-only
	    DESCRIPTION	"No write access via SNMP."

	VARIATION	isdnSigTblSignalingProtocol
	    ACCESS	read-only
	    DESCRIPTION	"No write access via SNMP."

	VARIATION	isdnSigTblCallingAddress
	    ACCESS	read-only
	    DESCRIPTION	"No write access via SNMP."

	VARIATION	isdnSigTblSubAddress
	    ACCESS	read-only
	    DESCRIPTION	"No write access via SNMP."

	VARIATION	isdnSigTblBchannelCount
	    ACCESS	read-only
	    DESCRIPTION	"No write access via SNMP."

	VARIATION	isdnSigTblStatus
	    ACCESS	read-only
	    DESCRIPTION	"No write access via SNMP."

	VARIATION	isdnEndpointIfType
	    ACCESS	read-only
	    DESCRIPTION	"No write access via SNMP."

	VARIATION	isdnEndpointTeiType
	    ACCESS	read-only
	    DESCRIPTION	"No write access via SNMP."

	VARIATION	isdnEndpointTeiValue
	    ACCESS	read-only
	    DESCRIPTION	"No write access via SNMP."

	VARIATION	isdnEndpointSpid
	    ACCESS	read-only
	    DESCRIPTION	"No write access via SNMP."

	VARIATION	isdnEndpointStatus
	    ACCESS	read-only
	    DESCRIPTION	"No write access via SNMP."


    SUPPORTS		DS0-MIB		 -- draft-ietf-trunkmib-ds0-mib-02.txt
	INCLUDES	{ ds0ConfigGroup }

	VARIATION	dsx0Ds0Number
	    ACCESS	read-only
	    DESCRIPTION	"No write access via SNMP."

	VARIATION	dsx0RobbedBitSignalling
	    ACCESS	read-only
	    DESCRIPTION	"No write access via SNMP."


    SUPPORTS		DS1-MIB		 -- draft-ietf-trunkmib-ds1-mib-03.txt
	INCLUDES	{ ds1NearEndConfigGroup
			  -- ds1FracGroup ---- implemented, but can't compile
			}

	VARIATION	dsx1LineType
	    ACCESS	read-only
	    DESCRIPTION	"No write access via SNMP."

	VARIATION	dsx1LineCoding
	    ACCESS	read-only
	    DESCRIPTION	"No write access via SNMP."

	VARIATION	dsx1SendCode
	    ACCESS	read-only
	    DESCRIPTION	"No write access via SNMP."

--	This variable was deprecated in later Internet-Drafts...
--	VARIATION	dsx1CircuitIdentifier
--	    ACCESS	read-only
--	    DESCRIPTION	"No write access via SNMP.  Always null string,
--			no way to configure this parameter."

	VARIATION	dsx1LoopbackConfig
	    ACCESS	read-only
	    DESCRIPTION	"No write access via SNMP."

	VARIATION	dsx1SignalMode
	    ACCESS	read-only
	    DESCRIPTION	"No write access via SNMP."

	VARIATION	dsx1TransmitClockSource
	    ACCESS	read-only
	    DESCRIPTION	"No write access via SNMP."

	VARIATION	dsx1Fdl
	    ACCESS	read-only
	    DESCRIPTION	"No write access via SNMP."

	VARIATION	dsx1LineLength
	    ACCESS	read-only
	    DESCRIPTION	"No write access via SNMP."

--	This variable was deprecated in later Internet-Drafts...
--	VARIATION	dsx1FracIfIndex
--	    ACCESS	read-only
--	    DESCRIPTION	"No write access via SNMP."


-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMediaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover
--		Access Switch/T.  Variables dot5Commands, dot5RingSpeed,
--		dot5ActMonParticipate, and dot5FunctionalAddress read-only.
-- RFC 1243	AppleTalk Management Information Base.  The LLAP group is
--		not implemented (no LocalTalk hardware).  The variables
--		atportType and atportIfIndex are read-only.  The KIP group
--		is not implemented (protocol not supported).
-- RFC 1315	RFC1315-MIB, SMIv1 MIB for Frame Relay DTE's.  Implemented
--		in that it's a subset of draft-ietf-iplpdn-frmib-dte-05.asn.
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
--		The pppLqr group is not implemented (LQR is not implemented).
-- RFC 1473	PPP-IP-NCP-MIB.  Instantiated for each PPP Multilink bundle.
--		Variables pppIpConfigAdminStatus and pppIpConfigCompression
--		are read-only (inconsistent with configuration model).

-- Other notes on SHIVA MIBs:

-- SHIVA-LINE-MIB
-- For LanRover Access Switch 4.5.7, the serialLineTable is only
-- for UART1 and UART2.  

    ::= { shivaLanRoverAccessSwitchCapabilities 457 }

shivaLanRoverAccessSwitchAgent520 AGENT-CAPABILITIES
    PRODUCT-RELEASE	"LanRover Access Switch 5.2"
    STATUS		current
    DESCRIPTION		"SNMP Agent in LanRover Access Switch 5.2 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover Access Switch/E.

    SUPPORTS		EtherLike-MIB	-- RFC 1650
	INCLUDES	{ etherStatsGroup, etherCollisionTableGroup }


    -- RS-232-MIB supported FOR UART1, UART2, and all modems
    -- on the Digital Modem Card.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    -- Modem MIB supported on all modems on the Digital Modem Card.

    SUPPORTS		Modem-MIB	-- RFC 1696
	INCLUDES	{ mdmCallControlGroup,
			  mdmSignalConvertorGroup,
			  mdmStatisticsGroup } -- subset of required

	VARIATION	mdmCCRingsBeforeAnswer
	    ACCESS	not-implemented
	    DESCRIPTION	"Modem doesn't do answering."

	VARIATION	mdmCCCallSetUpFailTimer
	    ACCESS	not-implemented
	    DESCRIPTION	"Not implemented."

	VARIATION	mdmCCResultCodeEnable
	    ACCESS	not-implemented
	    DESCRIPTION	"Modem not interfaced this way."

	VARIATION	mdmCCEscapeAction
	    ACCESS	not-implemented
	    DESCRIPTION	"Modem not interfaced this way."

	VARIATION	mdmCCCallDuration
	    ACCESS	not-implemented
	    DESCRIPTION	"Not implemented."

	VARIATION	mdmCCStoredDialString
	    ACCESS	not-implemented
	    DESCRIPTION	"Not implemented."


    SUPPORTS		RIPv2-MIB	-- RFC 1724
	INCLUDES	{ rip2GlobalGroup, rip2IfStatGroup,
			  rip2IfConfGroup }

	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
	                    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."


    SUPPORTS		FRAME-RELAY-DTE-MIB	
			-- draft-ietf-iplpdn-frmib-dte-05.asn,
			-- which is a superset of RFC 1315 but in SMIv2.
	INCLUDES	{ frPortGroup, frCircuitGroup, frErrGroup, 
			  frTrapGroup, frNotificationGroup }

	VARIATION	frDlcmiState
	    ACCESS	read-only
	    DESCRIPTION	"Row creation is not required for the frDlcmiTable."

	VARIATION	frDlcmiAddress
	    ACCESS	read-only
	    DESCRIPTION	"Row creation is not required for the frDlcmiTable."

	VARIATION	frDlcmiAddressLen
	    ACCESS	read-only
	    DESCRIPTION	"Row creation is not required for the frDlcmiTable."

	VARIATION	frDlcmiPollingInterval
	    ACCESS	read-only
	    DESCRIPTION	"Row creation is not required for the frDlcmiTable."

	VARIATION	frDlcmiFullEnquiryInterval
	    ACCESS	read-only
	    DESCRIPTION	"Row creation is not required for the frDlcmiTable."

	VARIATION	frDlcmiErrorThreshold
	    ACCESS	read-only
	    DESCRIPTION	"Row creation is not required for the frDlcmiTable."

	VARIATION	frDlcmiMonitoredEvents
	    ACCESS	read-only
	    DESCRIPTION	"Row creation is not required for the frDlcmiTable."

	VARIATION	frDlcmiMaxSupportedVCs
	    ACCESS	read-only
	    DESCRIPTION	"Row creation is not required for the frDlcmiTable."

	VARIATION	frDlcmiMulticast
	    ACCESS	read-only
	    DESCRIPTION	"Row creation is not required for the frDlcmiTable."

	VARIATION	frDlcmiRowStatus
	    ACCESS	read-only
	    DESCRIPTION	"Row creation is not required for the frDlcmiTable."

	VARIATION	frCircuitState
	    ACCESS	read-only
	    DESCRIPTION	"Row creation is not required for the frCircuitTable."

	VARIATION	frCircuitCommittedBurst
	    ACCESS	read-only
	    DESCRIPTION	"Row creation is not required for the frCircuitTable."

	VARIATION	frCircuitExcessBurst
	    ACCESS	read-only
	    DESCRIPTION	"Row creation is not required for the frCircuitTable."

	VARIATION	frCircuitThroughput
	    ACCESS	read-only
	    DESCRIPTION	"Row creation is not required for the frCircuitTable."

	VARIATION	frCircuitMulticast
	    ACCESS	read-only
	    DESCRIPTION	"Row creation is not required for the frCircuitTable."

	VARIATION	frCircuitLogicalIfIndex
	    ACCESS	read-only
	    DESCRIPTION	"Row creation is not required for the frCircuitTable."

	VARIATION	frCircuitRowStatus
	    ACCESS	read-only
	    DESCRIPTION	"Row creation is not required for the frCircuitTable."


    SUPPORTS		ISDN-MIB -- draft-ietf-isdnmib-snmp-isdn-mib-04.txt
	INCLUDES	{ isdnMibBasicRateGroup, isdnMibSignalingGroup,
			  isdnMibEndpointGroup }

	VARIATION	isdnBasicTblIfType
	    ACCESS	read-only
	    DESCRIPTION	"No write access via SNMP."

	VARIATION	isdnBasicTblLineTopology
	    ACCESS	read-only
	    DESCRIPTION	"No write access via SNMP."

	VARIATION	isdnBasicTblIfMode
	    ACCESS	read-only
	    DESCRIPTION	"No write access via SNMP."

	VARIATION	isdnBasicTblSignalMode
	    ACCESS	read-only
	    DESCRIPTION	"No write access via SNMP."

	VARIATION	isdnSigTblSignalingProtocol
	    ACCESS	read-only
	    DESCRIPTION	"No write access via SNMP."

	VARIATION	isdnSigTblCallingAddress
	    ACCESS	read-only
	    DESCRIPTION	"No write access via SNMP."

	VARIATION	isdnSigTblSubAddress
	    ACCESS	read-only
	    DESCRIPTION	"No write access via SNMP."

	VARIATION	isdnSigTblBchannelCount
	    ACCESS	read-only
	    DESCRIPTION	"No write access via SNMP."

	VARIATION	isdnSigTblStatus
	    ACCESS	read-only
	    DESCRIPTION	"No write access via SNMP."

	VARIATION	isdnEndpointIfType
	    ACCESS	read-only
	    DESCRIPTION	"No write access via SNMP."

	VARIATION	isdnEndpointTeiType
	    ACCESS	read-only
	    DESCRIPTION	"No write access via SNMP."

	VARIATION	isdnEndpointTeiValue
	    ACCESS	read-only
	    DESCRIPTION	"No write access via SNMP."

	VARIATION	isdnEndpointSpid
	    ACCESS	read-only
	    DESCRIPTION	"No write access via SNMP."

	VARIATION	isdnEndpointStatus
	    ACCESS	read-only
	    DESCRIPTION	"No write access via SNMP."


    SUPPORTS		DS0-MIB		 -- draft-ietf-trunkmib-ds0-mib-04.txt
	INCLUDES	{ ds0ConfigGroup }

	VARIATION	dsx0Ds0Number
	    ACCESS	read-only
	    DESCRIPTION	"No write access via SNMP."

	VARIATION	dsx0RobbedBitSignalling
	    ACCESS	read-only
	    DESCRIPTION	"No write access via SNMP."


    SUPPORTS		DS1-MIB		 -- draft-ietf-trunkmib-ds1-mib-06.txt
	INCLUDES	{ ds1NearEndConfigGroup,
			  ds1NearEndStatisticsGroup,
			  -- ds1DeprecatedGroup,  ---- is implemented
			  ds1NearEndOptionalConfigGroup,
			  ds1NearEndOptionalTrapGroup
			}

	VARIATION	dsx1LineType
	    ACCESS	read-only
	    DESCRIPTION	"No write access via SNMP."

	VARIATION	dsx1LineCoding
	    ACCESS	read-only
	    DESCRIPTION	"No write access via SNMP."

	VARIATION	dsx1SendCode
	    ACCESS	read-only
	    DESCRIPTION	"No write access via SNMP."

	VARIATION	dsx1LoopbackConfig
	    ACCESS	read-only
	    DESCRIPTION	"No write access via SNMP."

	VARIATION	dsx1SignalMode
	    ACCESS	read-only
	    DESCRIPTION	"No write access via SNMP."

	VARIATION	dsx1TransmitClockSource
	    ACCESS	read-only
	    DESCRIPTION	"No write access via SNMP."

	VARIATION	dsx1Fdl
	    ACCESS	read-only
	    DESCRIPTION	"No write access via SNMP."

	VARIATION	dsx1LineLength
	    ACCESS	read-only
	    DESCRIPTION	"No write access via SNMP."

	VARIATION	dsx1LoopbackStatus
	    ACCESS	not-implemented
	    DESCRIPTION	"Loopbacks not presently supported."


    SUPPORTS		RADIUS-ACC-CLIENT-MIB
			-- draft-ietf-radius-acc-clientmib-00.txt
	INCLUDES	{ radiusAccClientMIBGroup }


    SUPPORTS		RADIUS-AUTH-CLIENT-MIB
			-- draft-ietf-radius-auth-clientmib-00.txt
	INCLUDES	{ radiusAuthClientMIBGroup }

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMediaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover
--		Access Switch/T.  Variables dot5Commands, dot5RingSpeed,
--		dot5ActMonParticipate, and dot5FunctionalAddress read-only.
-- RFC 1243	AppleTalk Management Information Base.  The LLAP group is
--		not implemented (no LocalTalk hardware).  The variables
--		atportType and atportIfIndex are read-only.  The KIP group
--		is not implemented (protocol not supported).
-- RFC 1315	RFC1315-MIB, SMIv1 MIB for Frame Relay DTE's.  Implemented
--		in that it's a subset of draft-ietf-iplpdn-frmib-dte-05.asn.
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
--		The pppLqr group is not implemented (LQR is not implemented).
-- RFC 1473	PPP-IP-NCP-MIB.  Instantiated for each PPP Multilink bundle.
--		Variables pppIpConfigAdminStatus and pppIpConfigCompression
--		are read-only (inconsistent with configuration model).

-- Other notes on SHIVA MIBs:

-- SHIVA-LINE-MIB
-- For LanRover Access Switch 5.2, the serialLineTable is only
-- for UART1 and UART2.  

    ::= { shivaLanRoverAccessSwitchCapabilities 520 }

shivaLanRoverAccessSwitchAgent540 AGENT-CAPABILITIES
    PRODUCT-RELEASE	"LanRover Access Switch 5.4"
    STATUS		current
    DESCRIPTION		"SNMP Agent in LanRover Access Switch 5.4, 5.4.1,
			and 5.4.2 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover Access Switch/E.

    SUPPORTS		EtherLike-MIB	-- RFC 1650
	INCLUDES	{ etherStatsGroup, etherCollisionTableGroup }


    -- RS-232-MIB supported FOR UART1, UART2, and all modems
    -- on the Digital Modem Card.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    -- Modem MIB supported on all modems on the Digital Modem Card.

    SUPPORTS		Modem-MIB	-- RFC 1696
	INCLUDES	{ mdmCallControlGroup,
			  mdmSignalConvertorGroup,
			  mdmStatisticsGroup } -- subset of required

	VARIATION	mdmCCRingsBeforeAnswer
	    ACCESS	not-implemented
	    DESCRIPTION	"Modem doesn't do answering."

	VARIATION	mdmCCCallSetUpFailTimer
	    ACCESS	not-implemented
	    DESCRIPTION	"Not implemented."

	VARIATION	mdmCCResultCodeEnable
	    ACCESS	not-implemented
	    DESCRIPTION	"Modem not interfaced this way."

	VARIATION	mdmCCEscapeAction
	    ACCESS	not-implemented
	    DESCRIPTION	"Modem not interfaced this way."

	VARIATION	mdmCCCallDuration
	    ACCESS	not-implemented
	    DESCRIPTION	"Not implemented."

	VARIATION	mdmCCStoredDialString
	    ACCESS	not-implemented
	    DESCRIPTION	"Not implemented."


    SUPPORTS		RIPv2-MIB	-- RFC 1724
	INCLUDES	{ rip2GlobalGroup, rip2IfStatGroup,
			  rip2IfConfGroup }

	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
	                    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."


    SUPPORTS		FRAME-RELAY-DTE-MIB	-- RFC 2115
	INCLUDES	{ frPortGroup, frCircuitGroup, frErrGroup, 
			  frTrapGroup, frNotificationGroup }

	VARIATION	frDlcmiState
	    ACCESS	read-only
	    DESCRIPTION	"Row creation is not required for the frDlcmiTable."

	VARIATION	frDlcmiAddress
	    ACCESS	read-only
	    DESCRIPTION	"Row creation is not required for the frDlcmiTable."

	VARIATION	frDlcmiAddressLen
	    ACCESS	read-only
	    DESCRIPTION	"Row creation is not required for the frDlcmiTable."

	VARIATION	frDlcmiPollingInterval
	    ACCESS	read-only
	    DESCRIPTION	"Row creation is not required for the frDlcmiTable."

	VARIATION	frDlcmiFullEnquiryInterval
	    ACCESS	read-only
	    DESCRIPTION	"Row creation is not required for the frDlcmiTable."

	VARIATION	frDlcmiErrorThreshold
	    ACCESS	read-only
	    DESCRIPTION	"Row creation is not required for the frDlcmiTable."

	VARIATION	frDlcmiMonitoredEvents
	    ACCESS	read-only
	    DESCRIPTION	"Row creation is not required for the frDlcmiTable."

	VARIATION	frDlcmiMaxSupportedVCs
	    ACCESS	read-only
	    DESCRIPTION	"Row creation is not required for the frDlcmiTable."

	VARIATION	frDlcmiMulticast
	    ACCESS	read-only
	    DESCRIPTION	"Row creation is not required for the frDlcmiTable."

	VARIATION	frDlcmiRowStatus
	    ACCESS	read-only
	    DESCRIPTION	"Row creation is not required for the frDlcmiTable."

	VARIATION	frCircuitState
	    ACCESS	read-only
	    DESCRIPTION	"Row creation is not required for the frCircuitTable."

	VARIATION	frCircuitCommittedBurst
	    ACCESS	read-only
	    DESCRIPTION	"Row creation is not required for the frCircuitTable."

	VARIATION	frCircuitExcessBurst
	    ACCESS	read-only
	    DESCRIPTION	"Row creation is not required for the frCircuitTable."

	VARIATION	frCircuitThroughput
	    ACCESS	read-only
	    DESCRIPTION	"Row creation is not required for the frCircuitTable."

	VARIATION	frCircuitMulticast
	    ACCESS	read-only
	    DESCRIPTION	"Row creation is not required for the frCircuitTable."

	VARIATION	frCircuitLogicalIfIndex
	    ACCESS	read-only
	    DESCRIPTION	"Row creation is not required for the frCircuitTable."

	VARIATION	frCircuitRowStatus
	    ACCESS	read-only
	    DESCRIPTION	"Row creation is not required for the frCircuitTable."


    SUPPORTS		ISDN-MIB -- draft-ietf-isdnmib-snmp-isdn-mib-04.txt
	INCLUDES	{ isdnMibBasicRateGroup, isdnMibSignalingGroup,
			  isdnMibEndpointGroup }

	VARIATION	isdnBasicTblIfType
	    ACCESS	read-only
	    DESCRIPTION	"No write access via SNMP."

	VARIATION	isdnBasicTblLineTopology
	    ACCESS	read-only
	    DESCRIPTION	"No write access via SNMP."

	VARIATION	isdnBasicTblIfMode
	    ACCESS	read-only
	    DESCRIPTION	"No write access via SNMP."

	VARIATION	isdnBasicTblSignalMode
	    ACCESS	read-only
	    DESCRIPTION	"No write access via SNMP."

	VARIATION	isdnSigTblSignalingProtocol
	    ACCESS	read-only
	    DESCRIPTION	"No write access via SNMP."

	VARIATION	isdnSigTblCallingAddress
	    ACCESS	read-only
	    DESCRIPTION	"No write access via SNMP."

	VARIATION	isdnSigTblSubAddress
	    ACCESS	read-only
	    DESCRIPTION	"No write access via SNMP."

	VARIATION	isdnSigTblBchannelCount
	    ACCESS	read-only
	    DESCRIPTION	"No write access via SNMP."

	VARIATION	isdnSigTblStatus
	    ACCESS	read-only
	    DESCRIPTION	"No write access via SNMP."

	VARIATION	isdnEndpointIfType
	    ACCESS	read-only
	    DESCRIPTION	"No write access via SNMP."

	VARIATION	isdnEndpointTeiType
	    ACCESS	read-only
	    DESCRIPTION	"No write access via SNMP."

	VARIATION	isdnEndpointTeiValue
	    ACCESS	read-only
	    DESCRIPTION	"No write access via SNMP."

	VARIATION	isdnEndpointSpid
	    ACCESS	read-only
	    DESCRIPTION	"No write access via SNMP."

	VARIATION	isdnEndpointStatus
	    ACCESS	read-only
	    DESCRIPTION	"No write access via SNMP."


    SUPPORTS		DS0-MIB		 -- draft-ietf-trunkmib-ds0-mib-04.txt
	INCLUDES	{ ds0ConfigGroup }

	VARIATION	dsx0Ds0Number
	    ACCESS	read-only
	    DESCRIPTION	"No write access via SNMP."

	VARIATION	dsx0RobbedBitSignalling
	    ACCESS	read-only
	    DESCRIPTION	"No write access via SNMP."


    SUPPORTS		DS1-MIB		 -- draft-ietf-trunkmib-ds1-mib-06.txt
	INCLUDES	{ ds1NearEndConfigGroup,
			  ds1NearEndStatisticsGroup,
			  -- ds1DeprecatedGroup,  ---- is implemented
			  ds1NearEndOptionalConfigGroup,
			  ds1NearEndOptionalTrapGroup
			}

	VARIATION	dsx1LineType
	    ACCESS	read-only
	    DESCRIPTION	"No write access via SNMP."

	VARIATION	dsx1LineCoding
	    ACCESS	read-only
	    DESCRIPTION	"No write access via SNMP."

	VARIATION	dsx1SendCode
	    ACCESS	read-only
	    DESCRIPTION	"No write access via SNMP."

	VARIATION	dsx1LoopbackConfig
	    ACCESS	read-only
	    DESCRIPTION	"No write access via SNMP."

	VARIATION	dsx1SignalMode
	    ACCESS	read-only
	    DESCRIPTION	"No write access via SNMP."

	VARIATION	dsx1TransmitClockSource
	    ACCESS	read-only
	    DESCRIPTION	"No write access via SNMP."

	VARIATION	dsx1Fdl
	    ACCESS	read-only
	    DESCRIPTION	"No write access via SNMP."

	VARIATION	dsx1LineLength
	    ACCESS	read-only
	    DESCRIPTION	"No write access via SNMP."

	VARIATION	dsx1LoopbackStatus
	    ACCESS	not-implemented
	    DESCRIPTION	"Loopbacks not presently supported."


    SUPPORTS		RADIUS-ACC-CLIENT-MIB
			-- draft-ietf-radius-acc-clientmib-00.txt
	INCLUDES	{ radiusAccClientMIBGroup }


    SUPPORTS		RADIUS-AUTH-CLIENT-MIB
			-- draft-ietf-radius-auth-clientmib-00.txt
	INCLUDES	{ radiusAuthClientMIBGroup }

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMediaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover
--		Access Switch/T.  Variables dot5Commands, dot5RingSpeed,
--		dot5ActMonParticipate, and dot5FunctionalAddress read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
--		The pppLqr group is not implemented (LQR is not implemented).
-- RFC 1473	PPP-IP-NCP-MIB.  Instantiated for each PPP Multilink bundle.
--		Variables pppIpConfigAdminStatus and pppIpConfigCompression
--		are read-only (inconsistent with configuration model).

-- Other notes on SHIVA MIBs:

-- SHIVA-LINE-MIB
-- For LanRover Access Switch 5.4, the serialLineTable is only
-- for UART1 and UART2.  

    ::= { shivaLanRoverAccessSwitchCapabilities 540 }

shivaLanRoverAccessSwitchAgent605 AGENT-CAPABILITIES
    PRODUCT-RELEASE	"LanRover Access Switch 6.0.5"
    STATUS		current
    DESCRIPTION		"SNMP Agent in LanRover Access Switch 6.0.5 firmware.
			Describes only those MIBs which have
			SMIv2 MODULE-COMPLIANCE macro."

    SUPPORTS		IF-MIB		-- RFC 1573
	INCLUDES	{ ifGeneralGroup, ifPacketGroup, ifTestGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover Access Switch/E.

    SUPPORTS		EtherLike-MIB	-- RFC 1650
	INCLUDES	{ etherStatsGroup, etherCollisionTableGroup }


    -- RS-232-MIB supported FOR UART1, UART2, and all modems
    -- on the Digital Modem Card.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    -- Modem MIB supported on all modems on the Digital Modem Card.

    SUPPORTS		Modem-MIB	-- RFC 1696
	INCLUDES	{ mdmCallControlGroup,
			  mdmSignalConvertorGroup,
			  mdmStatisticsGroup } -- subset of required

	VARIATION	mdmCCRingsBeforeAnswer
	    ACCESS	not-implemented
	    DESCRIPTION	"Modem doesn't do answering."

	VARIATION	mdmCCCallSetUpFailTimer
	    ACCESS	not-implemented
	    DESCRIPTION	"Not implemented."

	VARIATION	mdmCCResultCodeEnable
	    ACCESS	not-implemented
	    DESCRIPTION	"Modem not interfaced this way."

	VARIATION	mdmCCEscapeAction
	    ACCESS	not-implemented
	    DESCRIPTION	"Modem not interfaced this way."

	VARIATION	mdmCCCallDuration
	    ACCESS	not-implemented
	    DESCRIPTION	"Not implemented."

	VARIATION	mdmCCStoredDialString
	    ACCESS	not-implemented
	    DESCRIPTION	"Not implemented."


    SUPPORTS		RIPv2-MIB	-- RFC 1724
	INCLUDES	{ rip2GlobalGroup, rip2IfStatGroup,
			  rip2IfConfGroup }

	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
	                    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."


    SUPPORTS		FRAME-RELAY-DTE-MIB	-- RFC 2115
	INCLUDES	{ frPortGroup, frCircuitGroup, frErrGroup, 
			  frTrapGroup, frNotificationGroup }

	VARIATION	frDlcmiState
	    ACCESS	read-only
	    DESCRIPTION	"Row creation is not required for the frDlcmiTable."

	VARIATION	frDlcmiAddress
	    ACCESS	read-only
	    DESCRIPTION	"Row creation is not required for the frDlcmiTable."

	VARIATION	frDlcmiAddressLen
	    ACCESS	read-only
	    DESCRIPTION	"Row creation is not required for the frDlcmiTable."

	VARIATION	frDlcmiPollingInterval
	    ACCESS	read-only
	    DESCRIPTION	"Row creation is not required for the frDlcmiTable."

	VARIATION	frDlcmiFullEnquiryInterval
	    ACCESS	read-only
	    DESCRIPTION	"Row creation is not required for the frDlcmiTable."

	VARIATION	frDlcmiErrorThreshold
	    ACCESS	read-only
	    DESCRIPTION	"Row creation is not required for the frDlcmiTable."

	VARIATION	frDlcmiMonitoredEvents
	    ACCESS	read-only
	    DESCRIPTION	"Row creation is not required for the frDlcmiTable."

	VARIATION	frDlcmiMaxSupportedVCs
	    ACCESS	read-only
	    DESCRIPTION	"Row creation is not required for the frDlcmiTable."

	VARIATION	frDlcmiMulticast
	    ACCESS	read-only
	    DESCRIPTION	"Row creation is not required for the frDlcmiTable."

	VARIATION	frDlcmiRowStatus
	    ACCESS	read-only
	    DESCRIPTION	"Row creation is not required for the frDlcmiTable."

	VARIATION	frCircuitState
	    ACCESS	read-only
	    DESCRIPTION	"Row creation is not required for the frCircuitTable."

	VARIATION	frCircuitCommittedBurst
	    ACCESS	read-only
	    DESCRIPTION	"Row creation is not required for the frCircuitTable."

	VARIATION	frCircuitExcessBurst
	    ACCESS	read-only
	    DESCRIPTION	"Row creation is not required for the frCircuitTable."

	VARIATION	frCircuitThroughput
	    ACCESS	read-only
	    DESCRIPTION	"Row creation is not required for the frCircuitTable."

	VARIATION	frCircuitMulticast
	    ACCESS	read-only
	    DESCRIPTION	"Row creation is not required for the frCircuitTable."

	VARIATION	frCircuitLogicalIfIndex
	    ACCESS	read-only
	    DESCRIPTION	"Row creation is not required for the frCircuitTable."

	VARIATION	frCircuitRowStatus
	    ACCESS	read-only
	    DESCRIPTION	"Row creation is not required for the frCircuitTable."


    SUPPORTS		ISDN-MIB -- draft-ietf-isdnmib-snmp-isdn-mib-04.txt
	INCLUDES	{ isdnMibBasicRateGroup, isdnMibSignalingGroup,
			  isdnMibEndpointGroup }

	VARIATION	isdnBasicTblIfType
	    ACCESS	read-only
	    DESCRIPTION	"No write access via SNMP."

	VARIATION	isdnBasicTblLineTopology
	    ACCESS	read-only
	    DESCRIPTION	"No write access via SNMP."

	VARIATION	isdnBasicTblIfMode
	    ACCESS	read-only
	    DESCRIPTION	"No write access via SNMP."

	VARIATION	isdnBasicTblSignalMode
	    ACCESS	read-only
	    DESCRIPTION	"No write access via SNMP."

	VARIATION	isdnSigTblSignalingProtocol
	    ACCESS	read-only
	    DESCRIPTION	"No write access via SNMP."

	VARIATION	isdnSigTblCallingAddress
	    ACCESS	read-only
	    DESCRIPTION	"No write access via SNMP."

	VARIATION	isdnSigTblSubAddress
	    ACCESS	read-only
	    DESCRIPTION	"No write access via SNMP."

	VARIATION	isdnSigTblBchannelCount
	    ACCESS	read-only
	    DESCRIPTION	"No write access via SNMP."

	VARIATION	isdnSigTblStatus
	    ACCESS	read-only
	    DESCRIPTION	"No write access via SNMP."

	VARIATION	isdnEndpointIfType
	    ACCESS	read-only
	    DESCRIPTION	"No write access via SNMP."

	VARIATION	isdnEndpointTeiType
	    ACCESS	read-only
	    DESCRIPTION	"No write access via SNMP."

	VARIATION	isdnEndpointTeiValue
	    ACCESS	read-only
	    DESCRIPTION	"No write access via SNMP."

	VARIATION	isdnEndpointSpid
	    ACCESS	read-only
	    DESCRIPTION	"No write access via SNMP."

	VARIATION	isdnEndpointStatus
	    ACCESS	read-only
	    DESCRIPTION	"No write access via SNMP."


    SUPPORTS		DS0-MIB		 -- draft-ietf-trunkmib-ds0-mib-04.txt
	INCLUDES	{ ds0ConfigGroup }

	VARIATION	dsx0Ds0Number
	    ACCESS	read-only
	    DESCRIPTION	"No write access via SNMP."

	VARIATION	dsx0RobbedBitSignalling
	    ACCESS	read-only
	    DESCRIPTION	"No write access via SNMP."


    SUPPORTS		DS1-MIB		 -- draft-ietf-trunkmib-ds1-mib-06.txt
	INCLUDES	{ ds1NearEndConfigGroup,
			  ds1NearEndStatisticsGroup,
			  -- ds1DeprecatedGroup,  ---- is implemented
			  ds1NearEndOptionalConfigGroup,
			  ds1NearEndOptionalTrapGroup
			}

	VARIATION	dsx1LineType
	    ACCESS	read-only
	    DESCRIPTION	"No write access via SNMP."

	VARIATION	dsx1LineCoding
	    ACCESS	read-only
	    DESCRIPTION	"No write access via SNMP."

	VARIATION	dsx1SendCode
	    ACCESS	read-only
	    DESCRIPTION	"No write access via SNMP."

	VARIATION	dsx1LoopbackConfig
	    ACCESS	read-only
	    DESCRIPTION	"No write access via SNMP."

	VARIATION	dsx1SignalMode
	    ACCESS	read-only
	    DESCRIPTION	"No write access via SNMP."

	VARIATION	dsx1TransmitClockSource
	    ACCESS	read-only
	    DESCRIPTION	"No write access via SNMP."

	VARIATION	dsx1Fdl
	    ACCESS	read-only
	    DESCRIPTION	"No write access via SNMP."

	VARIATION	dsx1LineLength
	    ACCESS	read-only
	    DESCRIPTION	"No write access via SNMP."

	VARIATION	dsx1LoopbackStatus
	    ACCESS	not-implemented
	    DESCRIPTION	"Loopbacks not presently supported."


    SUPPORTS		RADIUS-ACC-CLIENT-MIB
			-- draft-ietf-radius-acc-clientmib-00.txt
	INCLUDES	{ radiusAccClientMIBGroup }


    SUPPORTS		RADIUS-AUTH-CLIENT-MIB
			-- draft-ietf-radius-auth-clientmib-00.txt
	INCLUDES	{ radiusAuthClientMIBGroup }

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMediaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover
--		Access Switch/T.  Variables dot5Commands, dot5RingSpeed,
--		dot5ActMonParticipate, and dot5FunctionalAddress read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
--		The pppLqr group is not implemented (LQR is not implemented).
-- RFC 1473	PPP-IP-NCP-MIB.  Instantiated for each PPP Multilink bundle.
--		Variables pppIpConfigAdminStatus and pppIpConfigCompression
--		are read-only (inconsistent with configuration model).

-- Other notes on SHIVA MIBs:

-- SHIVA-LINE-MIB
-- For LanRover Access Switch 6.0.5, the serialLineTable is only
-- for UART1 and UART2.  

    ::= { shivaLanRoverAccessSwitchCapabilities 605 }

shivaLanRoverAccessSwitchAgent611p1 AGENT-CAPABILITIES
    PRODUCT-RELEASE	"LanRover Access Switch 6.1.1p1"
    STATUS		current
    DESCRIPTION		"SNMP Agent in LanRover Access Switch 6.1.1 firmware.
			Describes only those MIBs which have
			SMIv2 MODULE-COMPLIANCE macro."

    SUPPORTS		IF-MIB		-- RFC 1573
	INCLUDES	{ ifGeneralGroup, ifPacketGroup, ifTestGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover Access Switch/E.

    SUPPORTS		EtherLike-MIB	-- RFC 1650
	INCLUDES	{ etherStatsGroup, etherCollisionTableGroup }


    -- RS-232-MIB supported FOR UART1, UART2, and all modems
    -- on the Digital Modem Card.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    -- Modem MIB supported on all modems on the Digital Modem Card.

    SUPPORTS		Modem-MIB	-- RFC 1696
	INCLUDES	{ mdmCallControlGroup,
			  mdmSignalConvertorGroup,
			  mdmStatisticsGroup } -- subset of required

	VARIATION	mdmCCRingsBeforeAnswer
	    ACCESS	not-implemented
	    DESCRIPTION	"Modem doesn't do answering."

	VARIATION	mdmCCCallSetUpFailTimer
	    ACCESS	not-implemented
	    DESCRIPTION	"Not implemented."

	VARIATION	mdmCCResultCodeEnable
	    ACCESS	not-implemented
	    DESCRIPTION	"Modem not interfaced this way."

	VARIATION	mdmCCEscapeAction
	    ACCESS	not-implemented
	    DESCRIPTION	"Modem not interfaced this way."

	VARIATION	mdmCCCallDuration
	    ACCESS	not-implemented
	    DESCRIPTION	"Not implemented."

	VARIATION	mdmCCStoredDialString
	    ACCESS	not-implemented
	    DESCRIPTION	"Not implemented."


    SUPPORTS		RIPv2-MIB	-- RFC 1724
	INCLUDES	{ rip2GlobalGroup, rip2IfStatGroup,
			  rip2IfConfGroup }

	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
	                    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."


    SUPPORTS		FRAME-RELAY-DTE-MIB	-- RFC 2115
	INCLUDES	{ frPortGroup, frCircuitGroup, frErrGroup, 
			  frTrapGroup, frNotificationGroup }

	VARIATION	frDlcmiState
	    ACCESS	read-only
	    DESCRIPTION	"Row creation is not required for the frDlcmiTable."

	VARIATION	frDlcmiAddress
	    ACCESS	read-only
	    DESCRIPTION	"Row creation is not required for the frDlcmiTable."

	VARIATION	frDlcmiAddressLen
	    ACCESS	read-only
	    DESCRIPTION	"Row creation is not required for the frDlcmiTable."

	VARIATION	frDlcmiPollingInterval
	    ACCESS	read-only
	    DESCRIPTION	"Row creation is not required for the frDlcmiTable."

	VARIATION	frDlcmiFullEnquiryInterval
	    ACCESS	read-only
	    DESCRIPTION	"Row creation is not required for the frDlcmiTable."

	VARIATION	frDlcmiErrorThreshold
	    ACCESS	read-only
	    DESCRIPTION	"Row creation is not required for the frDlcmiTable."

	VARIATION	frDlcmiMonitoredEvents
	    ACCESS	read-only
	    DESCRIPTION	"Row creation is not required for the frDlcmiTable."

	VARIATION	frDlcmiMaxSupportedVCs
	    ACCESS	read-only
	    DESCRIPTION	"Row creation is not required for the frDlcmiTable."

	VARIATION	frDlcmiMulticast
	    ACCESS	read-only
	    DESCRIPTION	"Row creation is not required for the frDlcmiTable."

	VARIATION	frDlcmiRowStatus
	    ACCESS	read-only
	    DESCRIPTION	"Row creation is not required for the frDlcmiTable."

	VARIATION	frCircuitState
	    ACCESS	read-only
	    DESCRIPTION	"Row creation is not required for the frCircuitTable."

	VARIATION	frCircuitCommittedBurst
	    ACCESS	read-only
	    DESCRIPTION	"Row creation is not required for the frCircuitTable."

	VARIATION	frCircuitExcessBurst
	    ACCESS	read-only
	    DESCRIPTION	"Row creation is not required for the frCircuitTable."

	VARIATION	frCircuitThroughput
	    ACCESS	read-only
	    DESCRIPTION	"Row creation is not required for the frCircuitTable."

	VARIATION	frCircuitMulticast
	    ACCESS	read-only
	    DESCRIPTION	"Row creation is not required for the frCircuitTable."

	VARIATION	frCircuitLogicalIfIndex
	    ACCESS	read-only
	    DESCRIPTION	"Row creation is not required for the frCircuitTable."

	VARIATION	frCircuitRowStatus
	    ACCESS	read-only
	    DESCRIPTION	"Row creation is not required for the frCircuitTable."


    SUPPORTS		ISDN-MIB -- draft-ietf-isdnmib-snmp-isdn-mib-04.txt
	INCLUDES	{ isdnMibBasicRateGroup, isdnMibSignalingGroup,
			  isdnMibEndpointGroup }

	VARIATION	isdnBasicTblIfType
	    ACCESS	read-only
	    DESCRIPTION	"No write access via SNMP."

	VARIATION	isdnBasicTblLineTopology
	    ACCESS	read-only
	    DESCRIPTION	"No write access via SNMP."

	VARIATION	isdnBasicTblIfMode
	    ACCESS	read-only
	    DESCRIPTION	"No write access via SNMP."

	VARIATION	isdnBasicTblSignalMode
	    ACCESS	read-only
	    DESCRIPTION	"No write access via SNMP."

	VARIATION	isdnSigTblSignalingProtocol
	    ACCESS	read-only
	    DESCRIPTION	"No write access via SNMP."

	VARIATION	isdnSigTblCallingAddress
	    ACCESS	read-only
	    DESCRIPTION	"No write access via SNMP."

	VARIATION	isdnSigTblSubAddress
	    ACCESS	read-only
	    DESCRIPTION	"No write access via SNMP."

	VARIATION	isdnSigTblBchannelCount
	    ACCESS	read-only
	    DESCRIPTION	"No write access via SNMP."

	VARIATION	isdnSigTblStatus
	    ACCESS	read-only
	    DESCRIPTION	"No write access via SNMP."

	VARIATION	isdnEndpointIfType
	    ACCESS	read-only
	    DESCRIPTION	"No write access via SNMP."

	VARIATION	isdnEndpointTeiType
	    ACCESS	read-only
	    DESCRIPTION	"No write access via SNMP."

	VARIATION	isdnEndpointTeiValue
	    ACCESS	read-only
	    DESCRIPTION	"No write access via SNMP."

	VARIATION	isdnEndpointSpid
	    ACCESS	read-only
	    DESCRIPTION	"No write access via SNMP."

	VARIATION	isdnEndpointStatus
	    ACCESS	read-only
	    DESCRIPTION	"No write access via SNMP."


    SUPPORTS		DS0-MIB		 -- draft-ietf-trunkmib-ds0-mib-04.txt
	INCLUDES	{ ds0ConfigGroup }

	VARIATION	dsx0Ds0Number
	    ACCESS	read-only
	    DESCRIPTION	"No write access via SNMP."

	VARIATION	dsx0RobbedBitSignalling
	    ACCESS	read-only
	    DESCRIPTION	"No write access via SNMP."


    SUPPORTS		DS1-MIB		 -- draft-ietf-trunkmib-ds1-mib-06.txt
	INCLUDES	{ ds1NearEndConfigGroup,
			  ds1NearEndStatisticsGroup,
			  -- ds1DeprecatedGroup,  ---- is implemented
			  ds1NearEndOptionalConfigGroup,
			  ds1NearEndOptionalTrapGroup
			}

	VARIATION	dsx1LineType
	    ACCESS	read-only
	    DESCRIPTION	"No write access via SNMP."

	VARIATION	dsx1LineCoding
	    ACCESS	read-only
	    DESCRIPTION	"No write access via SNMP."

	VARIATION	dsx1SendCode
	    ACCESS	read-only
	    DESCRIPTION	"No write access via SNMP."

	VARIATION	dsx1LoopbackConfig
	    ACCESS	read-only
	    DESCRIPTION	"No write access via SNMP."

	VARIATION	dsx1SignalMode
	    ACCESS	read-only
	    DESCRIPTION	"No write access via SNMP."

	VARIATION	dsx1TransmitClockSource
	    ACCESS	read-only
	    DESCRIPTION	"No write access via SNMP."

	VARIATION	dsx1Fdl
	    ACCESS	read-only
	    DESCRIPTION	"No write access via SNMP."

	VARIATION	dsx1LineLength
	    ACCESS	read-only
	    DESCRIPTION	"No write access via SNMP."

	VARIATION	dsx1LoopbackStatus
	    ACCESS	not-implemented
	    DESCRIPTION	"Loopbacks not presently supported."


    SUPPORTS		RADIUS-ACC-CLIENT-MIB
			-- draft-ietf-radius-acc-clientmib-00.txt
	INCLUDES	{ radiusAccClientMIBGroup }


    SUPPORTS		RADIUS-AUTH-CLIENT-MIB
			-- draft-ietf-radius-auth-clientmib-00.txt
	INCLUDES	{ radiusAuthClientMIBGroup }

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMediaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover
--		Access Switch/T.  Variables dot5Commands, dot5RingSpeed,
--		dot5ActMonParticipate, and dot5FunctionalAddress read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
--		The pppLqr group is not implemented (LQR is not implemented).
-- RFC 1473	PPP-IP-NCP-MIB.  Instantiated for each PPP Multilink bundle.
--		Variables pppIpConfigAdminStatus and pppIpConfigCompression
--		are read-only (inconsistent with configuration model).

-- Other notes on SHIVA MIBs:

-- SHIVA-LINE-MIB
-- For LanRover Access Switch 6.1.1, the serialLineTable is only
-- for UART1 and UART2.  

    ::= { shivaLanRoverAccessSwitchCapabilities 611 }
END
