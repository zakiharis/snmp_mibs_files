-- Revision 1.0.0
-- Copyright 1999 D-Link, Inc.
-- All rights reserved.

SW-VLAN-MIB     DEFINITIONS ::= BEGIN
    IMPORTS
        OBJECT-TYPE     FROM RFC-1212
        DisplayString   FROM RFC1213-MIB
        enterprises     FROM RFC1155-SMI;

    MacAddress  ::= OCTET STRING(SIZE(6))
    VlanIndex   ::= INTEGER (1..4094)
    PortList    ::= OCTET STRING(SIZE(12))

    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }              

    marconi-mgmt    OBJECT IDENTIFIER ::= { golfcommon 2 }

    es2000Mgmt      OBJECT IDENTIFIER ::= { marconi-mgmt 28 }

    swL2Mgmt        OBJECT IDENTIFIER ::= { es2000Mgmt 2 }

    swVlan          OBJECT IDENTIFIER ::= { swL2Mgmt 8 }

    swVlanCtrl      OBJECT IDENTIFIER ::= { swVlan 1 }

    swMacBaseVlan   OBJECT IDENTIFIER ::= { swVlan 2 }

    swPortBaseVlan  OBJECT IDENTIFIER ::= { swVlan 3 }

-- *****************************************************************************
--  swVlanCtrl
-- *****************************************************************************
    swVlanCtrlMode OBJECT-TYPE
        SYNTAX  INTEGER {
            other(1),
            disabled(2),    -- Vlan function be disable
            mac-base(3),    -- proprietary mac base Vlan
-- +updated by Jemy 2000/2/10 04:02PM B14            
            ieee8021q(4),    -- 802.1q gvrp base Vlan
            port-base(5)   -- proprietary port base Vlan
-- -            
        }
        ACCESS  read-write
        STATUS  mandatory
        DESCRIPTION
            "This object controls which Vlan function will be enable (or disable)
             when the switch hub restart at the startup (power on) or warm
             start."
        ::= { swVlanCtrl 1 }

    swVlanInfoStatus OBJECT-TYPE
        SYNTAX  INTEGER {
            other(1),
            disabled(2),    -- Vlan function be disable
            mac-base(3),    -- proprietary mac base Vlan
-- +updated by Jemy 2000/2/10 04:02PM B14            
            ieee8021q(4),    -- 802.1q gvrp base Vlan
            port-base(5)   -- proprietary port base Vlan
-- -            
        }
        ACCESS  read-only
        STATUS  mandatory
        DESCRIPTION
            "This object indicates which Vlan function be enable (or disable)
             in mandatoryly stage. There are no effect when change swVlanCtrlMode
             vlaue in the system running."
        ::= { swVlanCtrl 2 }

    swVlanSnmpPortVlan OBJECT-TYPE
        SYNTAX  VlanIndex
        ACCESS  read-only -- updated by Jemy 2000/2/25 10:42AM B19
        STATUS  mandatory
        DESCRIPTION
            "Indicates the Vlan which the SNMP port belongs to.
             The value range is 1 to 4094."
        ::= { swVlanCtrl 3 }

-- *****************************************************************************
--  swMacBaseVlan
-- *****************************************************************************
    swMacBaseVlanInfo   OBJECT IDENTIFIER ::= { swMacBaseVlan 1 }

    swMacBaseVlanMaxNum OBJECT-TYPE
        SYNTAX  INTEGER
        ACCESS  read-only
        STATUS  mandatory
        DESCRIPTION
            "The maximum number of Mac base Vlan allowed by the system."
        ::= { swMacBaseVlanInfo 1 }

    swMacBaseVlanAddrMaxNum OBJECT-TYPE
        SYNTAX  INTEGER
        ACCESS  read-only
        STATUS  mandatory
        DESCRIPTION
            "The maximum number of entries in Mac-based Vlan address table."
        ::= { swMacBaseVlanInfo 2 }

    swMacBaseVlanCtrlTable OBJECT-TYPE
        SYNTAX  SEQUENCE OF SwMacBaseVlanCtrlEntry
        ACCESS  not-accessible
        STATUS  mandatory
        DESCRIPTION
            "A table that contains information about MAC base Vlan
             entries for which the switch has forwarding and/or filtering
             information. This information is used by the transparent switching
             function in determining how to propagate a received frame."
        ::= { swMacBaseVlan 2 }

    swMacBaseVlanCtrlEntry OBJECT-TYPE
        SYNTAX  SwMacBaseVlanCtrlEntry
        ACCESS  not-accessible
        STATUS  mandatory
        DESCRIPTION
            "A list of information about a specific MAC base Vlan configuration
             portlist for which the switch has some forwarding and/or filtering
             information."
        INDEX   { swMacBaseVlanDesc }
        ::= { swMacBaseVlanCtrlTable 1 }

    SwMacBaseVlanCtrlEntry ::=
        SEQUENCE {
            swMacBaseVlanDesc
                DisplayString (SIZE (1..12)),
            swMacBaseVlanMacMember
                INTEGER,
            swMacBaseVlanCtrlState
                INTEGER
        }

    swMacBaseVlanDesc OBJECT-TYPE
        SYNTAX  DisplayString (SIZE (1..12))
        ACCESS  read-only
        STATUS  mandatory
        DESCRIPTION
            "A textual description of the Mac Base Vlan for memorization.
             The string cannot set to empty string. There is a default value for this string."
        ::= { swMacBaseVlanCtrlEntry 1 }

    swMacBaseVlanMacMember OBJECT-TYPE
        SYNTAX  INTEGER
        ACCESS  read-only
        STATUS  mandatory
        DESCRIPTION
            "This object indicates the total number of MAC addresses contained
             in the VLAN entry."
        ::= { swMacBaseVlanCtrlEntry 2 }

    swMacBaseVlanCtrlState OBJECT-TYPE
        SYNTAX  INTEGER {
            other(1),
            disabled(2),
            enabled(3)
        }
        ACCESS  read-write
        STATUS  mandatory
        DESCRIPTION
            "This object indicates the MacBase Vlan state."
        ::= { swMacBaseVlanCtrlEntry 3 }

    swMacBaseVlanAddrTable OBJECT-TYPE
        SYNTAX  SEQUENCE OF SwMacBaseVlanAddrEntry
        ACCESS  not-accessible
        STATUS  mandatory
        DESCRIPTION
            "A table that contains information about unicast or multicast
             entries for which the switch has forwarding and/or filtering
             information. This information is used by the transparent switching
             function in determining how to propagate a received frame. Note that
             the priority of MacBaseVlanAddr table entries is lowest than Filtering
             Table and FDB Table, i.e. if there is a table hash collision between
             the entries of MacBaseVlanAddr Table and Filtering Table inside the
             switch H/W address table, then Filtering Table entry overwrite the
             colliding entry of MacBaseVlanAddr Table. This state is same of FDB
             table. See swFdbFilterTable and swFdbStaticTable description also."
        ::= { swMacBaseVlan 3 }

    swMacBaseVlanAddrEntry OBJECT-TYPE
        SYNTAX  SwMacBaseVlanAddrEntry
        ACCESS  not-accessible
        STATUS  mandatory
        DESCRIPTION
            "A list of information about a specific unicast or multicast MAC
             address for which the switch has some forwarding and/or filtering
             information."
        INDEX   { swMacBaseVlanAddr }
        ::= { swMacBaseVlanAddrTable 1 }

    SwMacBaseVlanAddrEntry ::=
        SEQUENCE {
            swMacBaseVlanAddr
                MacAddress,
            swMacBaseVlanAddrVlanDesc
                DisplayString (SIZE (1..64)),
            swMacBaseVlanAddrState
                INTEGER,
            swMacBaseVlanAddrStatus
                INTEGER
        }

    swMacBaseVlanAddr OBJECT-TYPE
        SYNTAX  MacAddress
        ACCESS  read-only
        STATUS  mandatory
        DESCRIPTION
            "This object indictaes a unicast or multicast MAC address for which
             the bridge has forwarding and/or filtering information."
        ::= { swMacBaseVlanAddrEntry 1 }

    swMacBaseVlanAddrVlanDesc OBJECT-TYPE
        SYNTAX  DisplayString (SIZE (1..64))
        ACCESS  read-write
        STATUS  mandatory
        DESCRIPTION
            "A textual description of the Mac Base Vlan for memorization."
        ::= { swMacBaseVlanAddrEntry 2 }

    swMacBaseVlanAddrState OBJECT-TYPE
        SYNTAX  INTEGER {
            other(1),
            invalid(2),
            valid(3)
        }
        ACCESS  read-write
        STATUS  mandatory
        DESCRIPTION
            "This object indicates the MacBase Vlan Address entry state.
             other(1) - this entry is currently in use but the conditions under
                        which it will remain so are different from each of the
                        following values.
             invalid(2) - writing this value to the object, and then the corresponding
                          entry will be removed from the table.
             valid(3) - this entry is reside in the table."
        ::= { swMacBaseVlanAddrEntry 3 }

    swMacBaseVlanAddrStatus OBJECT-TYPE
        SYNTAX  INTEGER {
            other(1),
            apply(2),
            not-apply(3)
        }
        ACCESS  read-only
        STATUS  mandatory
        DESCRIPTION
            "This object indicates the MacBase Vlan Address entry state.
             other(1) - this entry is currently in use but the conditions under
                        which it will remain so are different from each of the
                        following values.
             apply(2) - this entry is currently in use and reside in the table.
             not-apply(3) - this entry is reside in the table but currently not
                            in use due to conflict with filter table."
        ::= { swMacBaseVlanAddrEntry 4 }

-- *****************************************************************************
--  swPortBaseVlan
-- *****************************************************************************
    swPortBaseVlanTotalNum OBJECT-TYPE
        SYNTAX  INTEGER
        ACCESS  read-only
        STATUS  mandatory
        DESCRIPTION
            "The total number of Port-Base Vlan which is in enabled state
             within this switch hub."
        ::= { swPortBaseVlan 1 }

    swPortBaseVlanDefaultVlanTable OBJECT-TYPE
        SYNTAX  SEQUENCE OF SwPortBaseVlanDefaultVlanEntry
        ACCESS  not-accessible
        STATUS  mandatory
        DESCRIPTION
            "A table that contains default Port-Based VLAN list entries for the 
             switch. The entry (Vid = 1,i.e. swPortBaseVlanDefaultPvid = 1) is 
             defalut Port-Based VLAN , maintained by system."
        ::= { swPortBaseVlan 2 }

    swPortBaseVlanDefaultVlanEntry OBJECT-TYPE
        SYNTAX  SwPortBaseVlanDefaultVlanEntry
        ACCESS  not-accessible
        STATUS  mandatory
        DESCRIPTION
            "A list of default Port-Based VLAN information in 
             swPortBaseVlanDefaultVlanTable."
        INDEX   { swPortBaseVlanDefaultPvid }
        ::= { swPortBaseVlanDefaultVlanTable 1 }

    SwPortBaseVlanDefaultVlanEntry ::= 
        SEQUENCE {
            swPortBaseVlanDefaultPvid
                INTEGER,
            swPortBaseVlanDefaultDesc
                DisplayString,
            swPortBaseVlanDefaultPortList
                PortList,
            swPortBaseVlanDefaultPortNumber
                INTEGER
        }

    swPortBaseVlanDefaultPvid OBJECT-TYPE
        SYNTAX  INTEGER
        ACCESS  read-only
        STATUS  mandatory
        DESCRIPTION
            "This object indicates the default Port-Base Vlan ID. It occupies only 
             1 entry in VLAN table, with VID=1."
        ::= { swPortBaseVlanDefaultVlanEntry 1 }

    swPortBaseVlanDefaultDesc OBJECT-TYPE
        SYNTAX  DisplayString (SIZE (1..12))
        ACCESS  read-only
        STATUS  mandatory
        DESCRIPTION
            "A textual description of the Port-Base Vlan."
        ::= { swPortBaseVlanDefaultVlanEntry 2 }

    swPortBaseVlanDefaultPortList OBJECT-TYPE
        SYNTAX  PortList
        ACCESS  read-only
        STATUS  mandatory
        DESCRIPTION
            "This object indicates the port member set of the specified Vlan.
             Each Vlan has a octect string to indicate the port map. The most
             significant bit represents the lowest numbered port, and the
             least significant bit represents the highest numbered port."
        ::= { swPortBaseVlanDefaultVlanEntry 3 }

    swPortBaseVlanDefaultPortNumber OBJECT-TYPE
        SYNTAX  INTEGER
        ACCESS  read-only
        STATUS  mandatory
        DESCRIPTION
            "This object indicates the number of ports of the entry."
        ::= { swPortBaseVlanDefaultVlanEntry 4 }

    swPortBaseVlanConfigTable OBJECT-TYPE
        SYNTAX  SEQUENCE OF SwPortBaseVlanConfigEntry
        ACCESS  not-accessible
        STATUS  mandatory
        DESCRIPTION
            "A table that contains Port-Based VLAN list entries for the switch.
             The device can't support port overlapping in Port-Based VLAN."
        ::= { swPortBaseVlan 3 }

    swPortBaseVlanConfigEntry OBJECT-TYPE
        SYNTAX  SwPortBaseVlanConfigEntry
        ACCESS  not-accessible
        STATUS  mandatory
        DESCRIPTION
            "A list of information about a specific Port-Based VLAN configuration
             in swPortBaseVlanConfigTable."
        INDEX   { swPortBaseVlanConfigPvid }
        ::= { swPortBaseVlanConfigTable 1 }

    SwPortBaseVlanConfigEntry ::= 
        SEQUENCE {
            swPortBaseVlanConfigPvid
                INTEGER,
            swPortBaseVlanConfigDesc
                DisplayString,
            swPortBaseVlanConfigPortList
                PortList,
            swPortBaseVlanConfigPortNumber
                INTEGER
-- +deleted by Jemy 2000/2/10 06:37PM B14                
--            swPortBaseVlanConfigState
--                INTEGER
-- -
        }

    swPortBaseVlanConfigPvid OBJECT-TYPE
        SYNTAX  INTEGER (2..12)
        ACCESS  read-only
        STATUS  mandatory
        DESCRIPTION
            "This object indicates the Port-Base Vlan ID. There are up to 11 entries
             for current product now. The object range varies from 2 to 12."
        ::= { swPortBaseVlanConfigEntry 1 }

    swPortBaseVlanConfigDesc OBJECT-TYPE
        SYNTAX  DisplayString (SIZE (1..12))
        ACCESS  read-write
        STATUS  mandatory
        DESCRIPTION
            "A textual description of the Port-Base Vlan. It cannot be a null string.
             And each description must be unique in the table."
        ::= { swPortBaseVlanConfigEntry 2 }

    swPortBaseVlanConfigPortList OBJECT-TYPE
        SYNTAX  PortList
        ACCESS  read-write
        STATUS  mandatory
        DESCRIPTION
            "This object indicates which ports are belong to the Vlan. Each Vlan
             has a octect string to indicate with port map. The most significant
             bit represents the lowest numbered port, and the least significant 
             bit represents the highest numbered port."
        ::= { swPortBaseVlanConfigEntry 3 }

    swPortBaseVlanConfigPortNumber OBJECT-TYPE
        SYNTAX  INTEGER
        ACCESS  read-only
        STATUS  mandatory
        DESCRIPTION
            "This object indicates the number of ports of the entry."
        ::= { swPortBaseVlanConfigEntry 4 }

-- +deleted by Jemy 2000/2/10 06:08PM B14
--    swPortBaseVlanConfigState OBJECT-TYPE
--        SYNTAX  INTEGER {
--            other(1),
--            disabled(2),
--            enabled(3)
--        }
--        ACCESS  read-write
--        STATUS  mandatory
--        DESCRIPTION
--            "This object indicates the Port-Base Vlan state.
--             other(1) - this entry is currently in use but the conditions under
--                        which it will remain so are different from each of the
--                        following values.
--             disabled(2) - writing this value to the object, and then the
--                          corresponding entry will be removed from the table.
--             enabled(3) - this entry is reside in the table."
--       ::= { swPortBaseVlanConfigEntry 5 }
-- -

END
