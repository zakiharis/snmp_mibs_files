-- extracted from draft-ietf-ops-rowpointer-tc-01.txt
-- at Wed Mar  7 06:04:48 2001

   SNMP-REUSABLE-ROW-TC-MIB DEFINITIONS ::= BEGIN


      IMPORTS
        MODULE-IDENTITY, mib-2 FROM SNMPv2-SMI
        TEXTUAL-CONVENTION     FROM SNMPv2-TC;

      snmpReusableRowTCMIB MODULE-IDENTITY
        LAST-UPDATED "200103020000Z" -- March 2, 2001
        ORGANIZATION
            "IETF Operations & Management Area"
        CONTACT-INFO
            "Bob Moore
             IBM Corporation, BRQA/502
             PO Box 12195
             Research Triangle Park, NC 27709, USA
             Phone: +1 919 254 4436
             EMail: remoore@us.ibm.com

             Kwok Ho Chan
             Nortel Networks
             600 Technology Park Drive
             Billerica, MA 01821, USA
             E-mail: khchan@nortelnetworks.com

             Send comments to mibs@ops.ietf.org."

      DESCRIPTION
        "This MIB module defines a textual convention that indicates
         whether a conceptual row is reusable."

      REVISION     "200103020000Z" -- March 2, 2001
      DESCRIPTION
          "Initial version, published as RFCnnnn."
      ::= { mib-2 67890 } -- to be assigned by IANA


   ReusableRow ::= TEXTUAL-CONVENTION
       STATUS       current
       DESCRIPTION
               "This textual convention characerizes a
               conceptual row as reusable or not reusable
               for the purposes of cloning a configuration
               template.  The objects being cloned may
               either be special ones that express
               configuration information at the
               mechanism-specific level, or simply
               instance-specific ones that already exist at
               the time the cloning is done.

               The following values are defined:
                 - other(1)
                 - reusable(2): the conceptual row is
                   available to be pointed to by mulitple
                   RowPointer objects.
                 - singleUse(3): a separate copy of the
                   conceptual row is needed for each
                   RowPointer object that points to it.

               Because it represents a capability of the
               managed sytsem, rather than something that
               is configurable, an object having this syntax
               SHOULD have MAX-ACCESS of 'read-only'."

       SYNTAX  INTEGER {
                 other(1),
                 reusable(2),
                 singleUse(3)
               }

   END

-- 
--    Copyright (C) The Internet Society (2001).  All Rights Reserved.
-- 
--    This document and translations of it may be copied and furnished to
--    others, and derivative works that comment on or otherwise explain it
--    or assist in its implementation may be prepared, copied, published and
--    distributed, in whole or in part, without restriction of any kind,
--    provided that the above copyright notice and this paragraph are
--    included on all such copies and derivative works.  However, this
--    document itself may not be modified in any way, such as by removing
--    the copyright notice or references to the Internet Society or other
--    Internet organizations, except as needed for the purpose of developing
--    Internet standards in which case the procedures for copyrights defined
--    in the Internet Standards process must be followed, or as required to
--    translate it into languages other than English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING BUT
--    NOT LIMITED TO ANY WARRANTY THAT THE USE OF THE INFORMATION HEREIN
--    WILL NOT INFRINGE ANY RIGHTS OR ANY IMPLIED WARRANTIES OF
--    MERCHANTABILITY OR FITNESS FOR A PARTICULAR PURPOSE.
