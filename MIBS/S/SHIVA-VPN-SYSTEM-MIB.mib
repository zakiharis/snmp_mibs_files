SHIVA-VPN-SYSTEM-MIB DEFINITIONS ::= BEGIN

IMPORTS
  Counter
      FROM RFC1155-SMI
  OBJECT-TYPE
      FROM RFC-1212
  DisplayString
      FROM RFC1213-MIB
  vpnSystem
      FROM SHIVA-VPN-DEF;

  systemSerialNumber OBJECT-TYPE
      SYNTAX DisplayString
      ACCESS read-only
      STATUS mandatory
      DESCRIPTION
          "The serial number of the system."
      ::= { vpnSystem 1 }

  systemRestarts OBJECT-TYPE
      SYNTAX Counter
      ACCESS read-only
      STATUS mandatory
      DESCRIPTION
          "The number of times that the system has restarted."
      ::= { vpnSystem 2 }

END
