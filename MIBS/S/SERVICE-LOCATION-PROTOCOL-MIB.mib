-- extracted from draft-mcdonald-svrloc-mib-04.txt
-- at Fri May 14 06:21:04 2004

SERVICE-LOCATION-PROTOCOL-MIB DEFINITIONS ::= BEGIN

IMPORTS
    MODULE-IDENTITY,
        OBJECT-TYPE,
        Integer32,
        mib-2
            FROM SNMPv2-SMI             -- IETF RFC 2578
    TEXTUAL-CONVENTION,
        TruthValue
            FROM SNMPv2-TC              -- IETF RFC 2579
    MODULE-COMPLIANCE,
        OBJECT-GROUP
            FROM SNMPv2-CONF            -- IETF RFC 2580
    SnmpAdminString
            FROM SNMP-FRAMEWORK-MIB;    -- IETF RFC 2571

slpMIB MODULE-IDENTITY
    LAST-UPDATED   "200203010000Z" -- 1 March 2002
    ORGANIZATION   "SLP Project (at Source Forge)"
    CONTACT-INFO
        "           SLP Project (at Source Forge)
        Email:      srvloc-discuss@lists.sourceforge.net

        Editor:     Mark Bakke
        Postal:     Cisco Systems Inc
                    6450 Wedgwood Road, Suite 130
                    Maple Grove, MN  55311
                    USA
        Tel:        +1 763-398-1000
        Email:      mbakke@cisco.com

        Editor:     Ira McDonald
        Postal:     High North Inc
                    221 Ridge Ave
                    Grand Marais, MI  49839
                    USA
        Tel:        +1 906-494-2434
        Email:      imcdonald@sharplabs.com"
    DESCRIPTION
        "The MIB module for monitoring (but not configuration) of
        SLP (Service Location Protocol) directory agents (DAs), service
        agents (SAs), and/or user agents (UAs) on managed systems."
    ::= { mib-2 999 }                   -- [to be assigned by IANA]
                                        -- [standards track module]

slpMIBObjects           OBJECT IDENTIFIER ::= { slpMIB 1 }
slpMIBConformance       OBJECT IDENTIFIER ::= { slpMIB 2 }
slpMIBObjectGroups      OBJECT IDENTIFIER ::= { slpMIBConformance 2 }


--
-- Textual Conventions
--

SlpAgentTypeTC ::= TEXTUAL-CONVENTION
    STATUS      current
    DESCRIPTION
        "The type of this SLP agent.

        See:    'net.slp.isDA' in SLP API (RFC 2614)."
    SYNTAX      INTEGER {
        da(1),                          -- directory agent
        sa(2),                          -- service agent
        ua(3)                           -- user agent
    }

SlpScopeSourceTC ::= TEXTUAL-CONVENTION
    STATUS      current
    DESCRIPTION
        "The source (DHCP, etc) of this SLP scope or scope list.

        See:    Section 2 'Introduction' in RFC 2610."
    SYNTAX      INTEGER {
        static(1),                      -- from static local config info
        staticDA(2),                    -- from static local config DA
        dhcp(3),                        -- from DHCP config info
        dhcpDA(4),                      -- from DHCP config DA
        dynamicDA(5),                   -- from dynamic DA (DAAdvert)
        dynamicSA(6),                   -- from dynamic SA (SAAdvert)
        default(7)                      -- use of scope 'DEFAULT'
    }

SlpAttributeTypeTC ::= TEXTUAL-CONVENTION
    STATUS      current
    DESCRIPTION
        "The type of this SLP attribute.

        See:    Section 5 'Service Attributes' in SLPv2 (RFC 2608)."
    SYNTAX      INTEGER {
        attrBoolean(1),                 -- Boolean ('true' or 'false')
        attrInteger(2),                 -- Integer (32-bit string)
        attrString(3),                  -- String (UTF-8 string)
        attrOpaque(4),                  -- Opaque (sequence of bytes)
        attrKeyword(5)                  -- Keyword (name only, no value)
    }

--
-- Agent Group (Mandatory) Objects
--

slpAgent                OBJECT IDENTIFIER ::= { slpMIBObjects 1 }

slpAgentTable OBJECT-TYPE
    SYNTAX      SEQUENCE OF SlpAgentEntry
    MAX-ACCESS  not-accessible
    STATUS      current
    DESCRIPTION
        "A table containing SLP (Service Location Protocol) objects for
        all of the SLP directory agents (DAs), service agents (SAs),
        or user agents (UAs) currently installed and (possibly) active
        on this managed system."
    ::= { slpAgent 1 }

slpAgentEntry OBJECT-TYPE
    SYNTAX      SlpAgentEntry
    MAX-ACCESS  not-accessible
    STATUS      current
    DESCRIPTION
        "An entry containing SLP (Service Location Protocol) objects for
        one of the SLP directory agents (DAs), service agents (SAs),
        or user agents (UAs) currently installed and (possibly) active
        on this managed system."
    INDEX     { slpAgentIndex }
    ::= { slpAgentTable 1 }


SlpAgentEntry ::= SEQUENCE {
        slpAgentIndex                   Integer32,
        slpAgentSWInstalledIndexOrZero  Integer32,
        slpAgentName                    SnmpAdminString,
        slpAgentType                    SlpAgentTypeTC,
        slpAgentIsBroadcastOnly         TruthValue,
        slpAgentActiveDADiscovery       TruthValue,
        slpAgentPassiveDADiscovery      TruthValue,
        slpAgentMessageTypesSupported   OCTET STRING,
        slpAgentExtensionsSupported     OCTET STRING
    }

slpAgentIndex OBJECT-TYPE
    SYNTAX      Integer32 (1..2147483647)
    MAX-ACCESS  not-accessible
    STATUS      current
    DESCRIPTION
        "Ordinal of this conceptual row in 'slpAgentTable'."
    ::= { slpAgentEntry 1 }

slpAgentSWInstalledIndexOrZero OBJECT-TYPE
    SYNTAX      Integer32 (0..2147483647)
    MAX-ACCESS  read-only
    STATUS      current
    DESCRIPTION
        "The value of 'hrSWInstalledIndex' in the Host Resources MIB
        (RFC 2790) for the executable software for this SLP agent,
        or zero if none.

        See:    'hrSWInstalledIndex' in Host Resources MIB (RFC 2790)."
    ::= { slpAgentEntry 2 }

slpAgentName OBJECT-TYPE
    SYNTAX      SnmpAdminString (SIZE (0..64))
    MAX-ACCESS  read-only
    STATUS      current
    DESCRIPTION
        "The friendly locally unique name for this SLP agent,
        for use with remote network management scripts and GUIs
        For example 'daNewYork'."
    ::= { slpAgentEntry 3 }

slpAgentType OBJECT-TYPE
    SYNTAX      SlpAgentTypeTC
    MAX-ACCESS  read-only
    STATUS      current
    DESCRIPTION
        "The type of this SLP agent (DA, SA, or UA).

        See:    'net.slp.isDA' in SLP API (RFC 2614)."
    ::= { slpAgentEntry 4 }

slpAgentIsBroadcastOnly OBJECT-TYPE
    SYNTAX      TruthValue
    MAX-ACCESS  read-only
    STATUS      current
    DESCRIPTION
        "Broadcast only network enabled for this SLP agent.
        If 'true', SLP agent MUST send only broadcast messages.
        If 'false', SLP agent MAY send multicast messages.

        See:    'Broadcast Only' in section 14 of SLPv2 (RFC 2608).

        See:    'net.slp.isBroadcastOnly' in SLP API (RFC 2614)."
    DEFVAL      { false }               -- multicast allowed
    ::= { slpAgentEntry 5 }

slpAgentActiveDADiscovery OBJECT-TYPE
    SYNTAX      TruthValue
    MAX-ACCESS  read-only
    STATUS      current
    DESCRIPTION
        "Active DA discovery allowed for this SLP agent.
        If 'true', SLP agent MAY actively discover DAs,
        If 'false', SLP agent MUST NOT actively discover DAs.

        See:    'Active DA Discovery' in SLPv2 (RFC 2608).

        See:    'net.slp.DAActiveDiscoveryInterval' in SLP API
                (RFC2614)."
    DEFVAL      { true }                -- active DA discovery allowed
    ::= { slpAgentEntry 6 }

slpAgentPassiveDADiscovery OBJECT-TYPE
    SYNTAX      TruthValue
    MAX-ACCESS  read-only
    STATUS      current
    DESCRIPTION
        "Passive DA discovery allowed for this SLP agent.
        If 'true', SLP agent MAY passively discover DAs,
        If 'false', SLP agent MUST NOT passively discover DAs.

        See:    'Passive DA Advertising' in SLPv2 (RFC 2608).

        See:    'net.slp.passiveDADetection' in SLP API (RFC2614)."
    DEFVAL      { true }                -- passive DA discovery allowed
    ::= { slpAgentEntry 7 }

slpAgentMessageTypesSupported OBJECT-TYPE
    SYNTAX      OCTET STRING (SIZE (0..64))
    MAX-ACCESS  read-only
    STATUS      current
    DESCRIPTION
        "The SLP message types supported by this SLP agent,
        expressed as an array of binary Function-ID values (RFC 2608).
        For example '0102'H means 'SrvRqst, SrvRply'.

        See:    Section 8 'Required SLP Messages' in SLPv2 (RFC 2608)."
    ::= { slpAgentEntry 8 }

slpAgentExtensionsSupported OBJECT-TYPE
    SYNTAX      OCTET STRING (SIZE (0..64))
    MAX-ACCESS  read-only
    STATUS      current
    DESCRIPTION
        "The SLP extensions supported by this SLP agent,
        expressed as an array of binary Extension ID values (RFC 2608),
        in network byte order (i.e., big-endian representation).
        For example '00020003'H  means 'AttributeList, VendorOpaque'.

        See:    Section 9.1 'SLP Extensions' in SLPv2 (RFC 2608)."

    DEFVAL      { ''H }                 -- no extensions supported
    ::= { slpAgentEntry 9 }


--
-- Scope Group (Mandatory) Objects
--

slpScope                OBJECT IDENTIFIER ::= { slpMIBObjects 2 }

slpScopeTable OBJECT-TYPE
    SYNTAX      SEQUENCE OF SlpScopeEntry
    MAX-ACCESS  not-accessible
    STATUS      current
    DESCRIPTION
        "A table containing SLP (Service Location Protocol) objects for
        scope lists on this managed system.

        Usage:  This table sparsely augments the 'slpAgentTable'.

        Usage:  Scope lists consist of one or more rows in the
        'slpScopeTable' (one row per scope value) for each SLP agent."
    ::= { slpScope 1 }

slpScopeEntry OBJECT-TYPE
    SYNTAX      SlpScopeEntry
    MAX-ACCESS  not-accessible
    STATUS      current
    DESCRIPTION
        "An entry containing SLP (Service Location Protocol) objects for
        one scope value on this managed system."
    INDEX     { slpAgentIndex, slpScopeIndex }
    ::= { slpScopeTable 1 }


SlpScopeEntry ::= SEQUENCE {
        slpScopeIndex                   Integer32,
        slpScopeSource                  SlpScopeSourceTC,
        slpScopeValue                   SnmpAdminString
    }

slpScopeIndex OBJECT-TYPE
    SYNTAX      Integer32 (1..2147483647)
    MAX-ACCESS  not-accessible
    STATUS      current
    DESCRIPTION
        "Ordinal of this conceptual single row in 'slpScopeTable',
        subordinate to 'slpAgentIndex'."
    ::= { slpScopeEntry 1 }

slpScopeSource OBJECT-TYPE
    SYNTAX      SlpScopeSourceTC
    MAX-ACCESS  read-only
    STATUS      current
    DESCRIPTION
        "The source (DHCP, etc) of this SLP scope.

        See:    Section 2 'Introduction' in RFC 2610."
    ::= { slpScopeEntry 2 }

slpScopeValue OBJECT-TYPE
    SYNTAX      SnmpAdminString (SIZE (0..255))
    MAX-ACCESS  read-only
    STATUS      current
    DESCRIPTION
        "One scope configured or discovered for this SLP agent.

        Note:   The default (and lowest preference) scope value for any
        SLP agent is the string 'DEFAULT' verbatim in uppercase, per
        SLPv2 (RFC 2608).

        See:    'net.slp.useScopes' in SLP API (RFC 2614)."
    DEFVAL      { ''H }                 -- no scope configured
    ::= { slpScopeEntry 3 }


--
-- Address Group (Optional) Objects
--

slpAddress              OBJECT IDENTIFIER ::= { slpMIBObjects 3 }

slpAddressTable OBJECT-TYPE
    SYNTAX      SEQUENCE OF SlpAddressEntry
    MAX-ACCESS  not-accessible
    STATUS      current
    DESCRIPTION
        "A table containing SLP (Service Location Protocol) objects for
        remote DA/SA address lists known to this managed system.

        Usage:  This table sparsely augments the 'slpAgentTable'.

        Usage:  DA/SA address lists consist of one or more rows in the
        'slpAddressTable' (one row per address) for each SLP agent."
    ::= { slpAddress 1 }

slpAddressEntry OBJECT-TYPE
    SYNTAX      SlpAddressEntry
    MAX-ACCESS  not-accessible
    STATUS      current
    DESCRIPTION
        "An entry containing SLP (Service Location Protocol) objects for
        one remote DA or SA address known to this managed system."
    INDEX     { slpAgentIndex, slpAddressIndex }
    ::= { slpAddressTable 1 }


SlpAddressEntry ::= SEQUENCE {
        slpAddressIndex                 Integer32,
        slpAddressAgentType             SlpAgentTypeTC,
        slpAddressSource                SlpScopeSourceTC,
        slpAddressOrName                SnmpAdminString
    }

slpAddressIndex OBJECT-TYPE
    SYNTAX      Integer32 (1..2147483647)
    MAX-ACCESS  not-accessible
    STATUS      current
    DESCRIPTION
        "Ordinal of this conceptual single row in 'slpAddressTable',
        subordinate to 'slpAgentIndex'."
    ::= { slpAddressEntry 1 }

slpAddressAgentType OBJECT-TYPE
    SYNTAX      SlpAgentTypeTC
    MAX-ACCESS  read-only
    STATUS      current
    DESCRIPTION
        "The type of this remote SLP agent (DA or SA).

        See:    'net.slp.isDA' in SLP API (RFC 2614)."
    ::= { slpAddressEntry 2 }

slpAddressSource OBJECT-TYPE
    SYNTAX      SlpScopeSourceTC
    MAX-ACCESS  read-only
    STATUS      current
    DESCRIPTION
        "The source (DHCP, etc) of this remote SLP agent address.
        For example 'static(1)'.

        See:    'slpScopeSource' above in this SLP MIB."
    ::= { slpAddressEntry 3 }

slpAddressOrName OBJECT-TYPE
    SYNTAX      SnmpAdminString (SIZE (0..64))
    MAX-ACCESS  read-only
    STATUS      current
    DESCRIPTION
        "Text formatted (dotted decimal) IPv4 address; or (per RFC 2373)
        text formatted (colon-delimited hexadecimal) IPv6 address; or
        a fully qualifed DNS name for this remote SLP agent (DA or SA).
        For example '13.281.11.12' or '3FFE:2A00:100:7031::1'.
        See:    IP Version 6 Addressing Architecture (RFC 2373).

        See:    Format for Literal IPv6 Addresses in URLs (RFC 2732).

        See:    'net.slp.DAAddresses' in SLP API (RFC 2614)."
    ::= { slpAddressEntry 4 }


--
-- Attribute Group (Optional) Objects
--

slpAttribute            OBJECT IDENTIFIER ::= { slpMIBObjects 4 }

slpAttributeTable OBJECT-TYPE
    SYNTAX      SEQUENCE OF SlpAttributeEntry
    MAX-ACCESS  not-accessible
    STATUS      current
    DESCRIPTION
        "A table containing SLP (Service Location Protocol) objects for
        SLP agent (DA or SA) attribute lists on this managed system.

        Usage:  This table sparsely augments the 'slpAgentTable' (UAs
        do not have attribute lists - DAs/SAs should have attribute
        lists with at least the SLP standard DA/SA attributes).

        Usage:  Attribute lists consist of one or more rows in the
        'slpAttributeTable' (one row per attribute) for each SLP agent."
    ::= { slpAttribute 1 }

slpAttributeEntry OBJECT-TYPE
    SYNTAX      SlpAttributeEntry
    MAX-ACCESS  not-accessible
    STATUS      current
    DESCRIPTION
        "An entry containing SLP (Service Location Protocol) objects for
        one SLP agent (DA or SA) attribute on this managed system.

        See:    'net.slp.DAAttributes' in SLP API (RFC 2614).
        See:    'net.slp.SAAttributes' in SLP API (RFC 2614)."
    INDEX     { slpAgentIndex, slpAttributeIndex }
    ::= { slpAttributeTable 1 }


SlpAttributeEntry ::= SEQUENCE {
        slpAttributeIndex               Integer32,
        slpAttributeName                SnmpAdminString,
        slpAttributeType                SlpAttributeTypeTC,
        slpAttributeValue               SnmpAdminString
    }

slpAttributeIndex OBJECT-TYPE
    SYNTAX      Integer32 (1..2147483647)
    MAX-ACCESS  not-accessible
    STATUS      current
    DESCRIPTION
        "Ordinal of this conceptual single row in 'slpAttributeTable',
        subordinate to 'slpAgentIndex'."
    ::= { slpAttributeEntry 1 }

slpAttributeName OBJECT-TYPE
    SYNTAX      SnmpAdminString (SIZE (0..64))
    MAX-ACCESS  read-only
    STATUS      current
    DESCRIPTION
        "The name of this SLP attribute.
        For example 'printer-resolution-supported' in the
        'service:printer' IANA registered service template.

        See:    Section 5 'Service Attributes' in SLPv2 (RFC 2608)."
    ::= { slpAttributeEntry 2 }

slpAttributeType OBJECT-TYPE
    SYNTAX      SlpAttributeTypeTC
    MAX-ACCESS  read-only
    STATUS      current
    DESCRIPTION
        "The type of this SLP attribute.
        For example 'attrBoolean' for a string formatted boolean.

        See:    Section 5 'Service Attributes' in SLPv2 (RFC 2608)."
    ::= { slpAttributeEntry 3 }

slpAttributeValue OBJECT-TYPE
    SYNTAX      SnmpAdminString (SIZE (0..255))
    MAX-ACCESS  read-only
    STATUS      current
    DESCRIPTION
        "The value of this SLP attribute:

        a)  A UTF-8 string if 'slpAttributeType' is 'attrBoolean',
            'attrInteger', or 'attrString'
        b)  an escaped string if 'slpAttributeType' is 'attrOpaque'; or
        c)  an empty string if 'slpAttributeType' is 'attrKeyword'.

        See:    Section 5 'Service Attributes' in SLPv2 (RFC 2608)."
    ::= { slpAttributeEntry 4 }

--
-- Conformance Statements
--

slpMIBCompliance MODULE-COMPLIANCE
    STATUS      current
    DESCRIPTION
        "The compliance statements for SNMP Command Responders that
        implement the Service Location Protocol MIB."
    MODULE -- this module
    MANDATORY-GROUPS {
        slpAgentGroup,
        slpScopeGroup
    }

    GROUP   slpAddressGroup
    DESCRIPTION
            "Address Group"

    GROUP   slpAttributeGroup
    DESCRIPTION
            "Attribute Group"

    ::= { slpMIBConformance 1 }


--
-- Conformance Groups
--

slpAgentGroup OBJECT-GROUP
    OBJECTS {
        slpAgentSWInstalledIndexOrZero,
        slpAgentName,
        slpAgentType,
        slpAgentIsBroadcastOnly,
        slpAgentActiveDADiscovery,
        slpAgentPassiveDADiscovery,
        slpAgentMessageTypesSupported,
        slpAgentExtensionsSupported
    }
    STATUS      current
    DESCRIPTION
        "The Agent object group in the SLP MIB"
    ::= { slpMIBObjectGroups 1 }

slpScopeGroup OBJECT-GROUP
    OBJECTS {
        slpScopeSource,
        slpScopeValue
    }
    STATUS      current
    DESCRIPTION
        "The Scope object group in the SLP MIB"
    ::= { slpMIBObjectGroups 2 }

slpAddressGroup OBJECT-GROUP
    OBJECTS {
        slpAddressAgentType,
        slpAddressSource,
        slpAddressOrName
    }
    STATUS      current
    DESCRIPTION
        "The Address object group in the SLP MIB"
    ::= { slpMIBObjectGroups 3 }

slpAttributeGroup OBJECT-GROUP
    OBJECTS {
        slpAttributeName,
        slpAttributeType,
        slpAttributeValue
    }
    STATUS      current
    DESCRIPTION
        "The Attribute object group in the SLP MIB"
    ::= { slpMIBObjectGroups 4 }

END

-- 
--    Copyright (C) The Internet Society (2003).  All Rights Reserved.  
--    
--    This document and translations of it may be copied and furnished to
--    others, and derivative works that comment on or otherwise explain it 
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.  
--    
--    The limited permissions granted above are perpetual and will not be
--    revoked by the Internet Society or its successors or assigns.  
--    
--    This document and the information contained herein is provided on an 
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE."
