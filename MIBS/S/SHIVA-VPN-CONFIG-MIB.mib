SHIVA-VPN-CONFIG-MIB DEFINITIONS ::= BEGIN

-- This MIB contains definitions for managing configuration storage
-- on Shiva VPN products.

IMPORTS
  TimeTicks
      FROM RFC1155-SMI
  OBJECT-TYPE
      FROM RFC-1212
  vpnConfig
      FROM SHIVA-VPN-DEF;

  configConfig OBJECT IDENTIFIER ::= { vpnConfig 1 }
  configStatus OBJECT IDENTIFIER ::= { vpnConfig 2 }
  configActions OBJECT IDENTIFIER ::= { vpnConfig 3 }

  configFileLastWritten OBJECT-TYPE
      SYNTAX TimeTicks
      ACCESS read-only
      STATUS mandatory
      DESCRIPTION
          "If the non-volatile configuration file has
           been written since the last restart of the 
           system, this is the value of sysUpTime at
           the time that it was written.  If the
           non-volatile configuration file has not
           been written since the last restart, the
           value is 0."
      ::= { configStatus 1 }

END
