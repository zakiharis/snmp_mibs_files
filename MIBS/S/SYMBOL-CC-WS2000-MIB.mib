--
-- SYMBOL-CC-WS2000-MIB-2.0.mib
-- MIB generated by MG-SOFT Visual MIB Builder Version 6.0  Build 88
-- Saturday, April 24, 2010 at 09:38:04
--

-- MIB version = 08b35
-- 
-- Notes for WS2000 MIB:
-- 
-- === v2.0, (MIB='08b'):
-- 
-- (no notes at this time).
-- 
-- === v1.5, (MIB='08a'):
-- 
-- One 'incompatible' change was made: all MIB groups were
-- moved from their v1.0 locations to a new group called
-- 'ccGroupsV1dot0' under 'ccGroups'.  Since the switch does
-- not actually implement such groups, no NMS should be able
-- to detect this change, and so while technically an
-- 'incompatible' change, it should not matter to anyone.
-- 
-- Value 'ccLoadFtpPassword' has been obsoleted;  use the new
-- value 'ccLoadFtpPasswordNoRead' which is the same, except
-- that GETs return a 0-length string.  Had to remove the old
-- value from the ccAdminGroup, since all items in a group
-- must be of the same type, (in this case 'current').
-- 
-- Note that OIDs declared in this MIB, (except for values 
-- under group 'sysoids'), are reserved for future expansion.
-- They may be redefined in the future without causing an 
-- 'incompatible' change.
-- 
-- === v1.0, (MIB='07a'):
-- 
-- (no notes at this time).
-- 
-- 
-- 
-- 
-- 

	SYMBOL-CC-WS2000-MIB DEFINITIONS ::= BEGIN
 
		IMPORTS
			OBJECT-GROUP, NOTIFICATION-GROUP			
				FROM SNMPv2-CONF			
			enterprises, TimeTicks, IpAddress, Integer32, Unsigned32, 
			Counter32, Counter64, OBJECT-TYPE, MODULE-IDENTITY, 
			OBJECT-IDENTITY, NOTIFICATION-TYPE			
				FROM SNMPv2-SMI			
			DisplayString, TruthValue, TestAndIncr, PhysAddress, TEXTUAL-CONVENTION			
				FROM SNMPv2-TC;
	
	
		-- 1.3.6.1.4.1.388.11.2.1
		moduleid MODULE-IDENTITY 
			LAST-UPDATED "201004242137Z"		-- April 24, 2010 at 21:37 GMT
			ORGANIZATION 
				"Symbol WSD (Wireless Infrastructure Division, San Jose)"
			CONTACT-INFO 
				"Carl Mower
				cmower@symbol.com"
			DESCRIPTION 
				" "
			REVISION "201004240937Z"		-- April 24, 2010 at 09:37 GMT
			DESCRIPTION 
				"DNS Relay Mode added"
			REVISION "200912301325Z"		-- December 30, 2009 at 13:25 GMT
			DESCRIPTION 
				"ccLoadFw and ccLoadCfg modified to add SFTP support"
			REVISION "200412101649Z"		-- December 10, 2004 at 16:49 GMT
			DESCRIPTION 
				"09a00: Initial clean-up for WS2000 v2.0 release."
			REVISION "200410281632Z"		-- October 28, 2004 at 16:32 GMT
			DESCRIPTION 
				"08a43: Final clean-up for WS2000 v1.5 release candidate:
				Adopted new mib versioning scheme.  Details can be found
				in the description of ccIdMibVersion.
				"
			REVISION "200409081207Z"		-- September 08, 2004 at 12:07 GMT
			DESCRIPTION 
				"8a: Final clean-up for WS2000 v1.5 beta release:
				Added RF utilization, efficiency & health and system stats 
				at the Mu, Portal, Wlan and Switch level.
				Enabled config files up/down via TFTP
				Added 4 static and 4 stats traps"
			REVISION "200402041532Z"		-- February 04, 2004 at 15:32 GMT
			DESCRIPTION 
				"7a: Final clean-up for WS2000 v1.0 release:
				Removed -07A from MIB name, (can't chg after MIB locked).
				Rename ccPortalType to ccPortalRadioType.
				New RadioType; used in ccPortalRadioType & ccMuRadioType.
				Moved ccAp: Name, Location, & LastReset to ccPortal_.
				Delete ccAssociation: LastUnAssociate, CountUnAssociates.
				Change ccMuSymbolRogueApEna from int to TruthValue.
				Change ccPortalLastReason & ccMuLastReason: int to enum.
				Some items OIDs changed.
				Locked MIB after these chgs; (no prior diffs possible);
				   all chgs after this shall be backward compatible.
				"
			REVISION "200401060000Z"		-- January 06, 2004 at 00:00 GMT
			DESCRIPTION 
				"6a: Change a few items from RW to RO.
				Added ranges to all RW values.
				Added descriptions to all items.
				Some items OIDs changed.
				"
			REVISION "200312110100Z"		-- December 11, 2003 at 01:00 GMT
			DESCRIPTION 
				"5a: First release of WS2000 MIB (aside from development team).
				"
			REVISION "200312110000Z"		-- December 11, 2003 at 00:00 GMT
			DESCRIPTION 
				"4a: Forth preliminary draft of WS2000 MIB.
				"
			REVISION "200312020000Z"		-- December 02, 2003 at 00:00 GMT
			DESCRIPTION 
				"3a: Third preliminary draft of WS2000 MIB.
				"
			REVISION "200311260000Z"		-- November 26, 2003 at 00:00 GMT
			DESCRIPTION 
				"2a: Second preliminary draft of WS2000 MIB.
				"
			REVISION "200311250000Z"		-- November 25, 2003 at 00:00 GMT
			DESCRIPTION 
				"1a: First preliminary draft of WS2000 MIB.
				MIB naming include 2-digits & 1-letter;
				   digits increase for substantive chgs;
				   letter chgs for non-substantive chgs:
				      -- chgs to comments
				      -- chgs to descriptions
				      -- any other chg that person with
				           MIB browser could not detect.
				
				"
			::= { ws2k 1 }

		
	
--
-- Type definitions
--
	
--  
-- 
		SinglePointer ::= INTEGER (0..255)

		MultiPointer63 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63)
			}

		MultiPointer255 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63),
			referToEntry064(64),
			referToEntry065(65),
			referToEntry066(66),
			referToEntry067(67),
			referToEntry068(68),
			referToEntry069(69),
			referToEntry070(70),
			referToEntry071(71),
			referToEntry072(72),
			referToEntry073(73),
			referToEntry074(74),
			referToEntry075(75),
			referToEntry076(76),
			referToEntry077(77),
			referToEntry078(78),
			referToEntry079(79),
			referToEntry080(80),
			referToEntry081(81),
			referToEntry082(82),
			referToEntry083(83),
			referToEntry084(84),
			referToEntry085(85),
			referToEntry086(86),
			referToEntry087(87),
			referToEntry088(88),
			referToEntry089(89),
			referToEntry090(90),
			referToEntry091(91),
			referToEntry092(92),
			referToEntry093(93),
			referToEntry094(94),
			referToEntry095(95),
			referToEntry096(96),
			referToEntry097(97),
			referToEntry098(98),
			referToEntry099(99),
			referToEntry100(100),
			referToEntry101(101),
			referToEntry102(102),
			referToEntry103(103),
			referToEntry104(104),
			referToEntry105(105),
			referToEntry106(106),
			referToEntry107(107),
			referToEntry108(108),
			referToEntry109(109),
			referToEntry110(110),
			referToEntry111(111),
			referToEntry112(112),
			referToEntry113(113),
			referToEntry114(114),
			referToEntry115(115),
			referToEntry116(116),
			referToEntry117(117),
			referToEntry118(118),
			referToEntry119(119),
			referToEntry120(120),
			referToEntry121(121),
			referToEntry122(122),
			referToEntry123(123),
			referToEntry124(124),
			referToEntry125(125),
			referToEntry126(126),
			referToEntry127(127),
			referToEntry128(128),
			referToEntry129(129),
			referToEntry130(130),
			referToEntry131(131),
			referToEntry132(132),
			referToEntry133(133),
			referToEntry134(134),
			referToEntry135(135),
			referToEntry136(136),
			referToEntry137(137),
			referToEntry138(138),
			referToEntry139(139),
			referToEntry140(140),
			referToEntry141(141),
			referToEntry142(142),
			referToEntry143(143),
			referToEntry144(144),
			referToEntry145(145),
			referToEntry146(146),
			referToEntry147(147),
			referToEntry148(148),
			referToEntry149(149),
			referToEntry150(150),
			referToEntry151(151),
			referToEntry152(152),
			referToEntry153(153),
			referToEntry154(154),
			referToEntry155(155),
			referToEntry156(156),
			referToEntry157(157),
			referToEntry158(158),
			referToEntry159(159),
			referToEntry160(160),
			referToEntry161(161),
			referToEntry162(162),
			referToEntry163(163),
			referToEntry164(164),
			referToEntry165(165),
			referToEntry166(166),
			referToEntry167(167),
			referToEntry168(168),
			referToEntry169(169),
			referToEntry170(170),
			referToEntry171(171),
			referToEntry172(172),
			referToEntry173(173),
			referToEntry174(174),
			referToEntry175(175),
			referToEntry176(176),
			referToEntry177(177),
			referToEntry178(178),
			referToEntry179(179),
			referToEntry180(180),
			referToEntry181(181),
			referToEntry182(182),
			referToEntry183(183),
			referToEntry184(184),
			referToEntry185(185),
			referToEntry186(186),
			referToEntry187(187),
			referToEntry188(188),
			referToEntry189(189),
			referToEntry190(190),
			referToEntry191(191),
			referToEntry192(192),
			referToEntry193(193),
			referToEntry194(194),
			referToEntry195(195),
			referToEntry196(196),
			referToEntry197(197),
			referToEntry198(198),
			referToEntry199(199),
			referToEntry200(200),
			referToEntry201(201),
			referToEntry202(202),
			referToEntry203(203),
			referToEntry204(204),
			referToEntry205(205),
			referToEntry206(206),
			referToEntry207(207),
			referToEntry208(208),
			referToEntry209(209),
			referToEntry210(210),
			referToEntry211(211),
			referToEntry212(212),
			referToEntry213(213),
			referToEntry214(214),
			referToEntry215(215),
			referToEntry216(216),
			referToEntry217(217),
			referToEntry218(218),
			referToEntry219(219),
			referToEntry220(220),
			referToEntry221(221),
			referToEntry222(222),
			referToEntry223(223),
			referToEntry224(224),
			referToEntry225(225),
			referToEntry226(226),
			referToEntry227(227),
			referToEntry228(228),
			referToEntry229(229),
			referToEntry230(230),
			referToEntry231(231),
			referToEntry232(232),
			referToEntry233(233),
			referToEntry234(234),
			referToEntry235(235),
			referToEntry236(236),
			referToEntry237(237),
			referToEntry238(238),
			referToEntry239(239),
			referToEntry240(240),
			referToEntry241(241),
			referToEntry242(242),
			referToEntry243(243),
			referToEntry244(244),
			referToEntry245(245),
			referToEntry246(246),
			referToEntry247(247),
			referToEntry248(248),
			referToEntry249(249),
			referToEntry250(250),
			referToEntry251(251),
			referToEntry252(252),
			referToEntry253(253),
			referToEntry254(254),
			referToEntry255(255)
			}

-- This datatype always means that the MIB variable is
-- a simple ENUM that when written to 'doActionRightNow', 
-- causes the described action to take place, (much like 
-- a button pressed in a UI).
-- 
-- Such a value does NOT remain in state 'doActionRightNow'
-- while the operation is in-process, but instead when read 
-- always returns 'idleState'.
		DoActionNow ::= INTEGER
			{
			doActionRightNow(1),
			idleState(2)
			}

		RadioType ::= INTEGER
			{
			radio802dot11A(1),
			radio802dot11B(2),
			radio802dot11G(3),
			radio802dot11FH(4)
			}

-- Values of this type are passwords.  They can be written,
-- but when read, they return a 0-length string.
		Password ::= OCTET STRING (SIZE (0..255))

-- In order to make the switch's implementation of 
-- numerous tables simpler, tables using this datatype
-- have a fixed number of entries with fixed indices.
-- In such tables, no entries may be added or deleted, 
-- but the pre-existing rows can be enabled or disabled 
-- using the value declared with this datatype.
		StaticRowEnable ::= INTEGER
			{
			enable(1),
			disable(2)
			}

		PartsPer10k ::= Unsigned32 (0..10000)
-- This datatype is used for all percentage values that have
-- interesting tenths and hundreths, (such as 1.37%).  SNMP
-- cannot report decimals, only whole numbers.  Values of 
-- this datatype are expressed not as parts-per-100, (percent),
-- but as parts-per-10000.
-- 
-- Said another way, values of this type are percent 
-- multiplied by 100.
-- 
-- For example, 1.37% would be reported as 137.
-- 
		ScaleBy100 ::= Unsigned32
-- This datatype is used for all values that have interesting 
-- tenths and hundreths, (such as 2.48).  SNMP cannot report 
-- decimals, only whole numbers.  Values of this datatype are 
-- scaled (muliplied) by 100.
-- 
-- For example, 2.48 would be reported as 248.
-- In order to make the switch's implementation of some
-- dynamic tables simpler, tables using this datatype
-- use an abbreviated form of RowStatus.
-- 
-- Only CreateAndGo and Destroy states are supported.
-- 
-- On row creation, a single SET-PDU must contain all
-- the required values, including this value set to
-- createAndGo.  (This greatly simplifies row validation
-- for the switch).
-- 
-- Setting this value to Destroy causes the corresponding
-- row to be deleted.
-- 
		AbbrevRowStatus ::= INTEGER
			{
			createAndGo(4),
			destroy(6)
			}

-- This datatype always means that the MIB variable is
-- a simple ENUM that when written to 'doActionRightNow', 
-- causes the described action to take place, (much like 
-- a button pressed in a UI).
-- 
-- Such a value DOES remain in state 'doActionRightNow'
-- while the operation is in-process;  when the operation is
-- completed, it will then return the value 'idleState'.
		DoActionShowProgress ::= INTEGER
			{
			doActionRightNow(1),
			idleState(2)
			}

-- Values of this type are keys, expressed in hexadecimal as
-- a sequence of characters '0'..'9' plus 'A'..'F'.
-- 
-- Unless otherwise noted, the default value for variables of
-- this type is all-0s.
-- 
-- Values of this type are passwords.  They can be written,
-- but when read, they return a 0-length string.
		HexPassword ::= OCTET STRING (SIZE (0..255))

		TransmitRate ::= BITS
			{
			null(0),
			rate1Mb(1),
			rate2Mb(2),
			rate5pt5Mb(3),
			rate6Mb(4),
			rate9Mb(5),
			rate11Mb(6),
			rate12Mb(7),
			rate18Mb(8),
			rate22Mb(9),
			rate24Mb(10),
			rate36Mb(11),
			rate48Mb(12),
			rate54Mb(13)
			}

	
--
-- Textual conventions
--
	
		RowStatus ::= TEXTUAL-CONVENTION
			STATUS current
			DESCRIPTION 
				"The RowStatus textual convention is used to manage the
				creation and deletion of conceptual rows, and is used as the
				value of the SYNTAX clause for the status column of a
				conceptual row (as described in Section 7.7.1 of [2].)
				
				The status column has six defined values:
				
				     - `active', which indicates that the conceptual row is
				     available for use by the managed device;
				
				     - `notInService', which indicates that the conceptual
				     row exists in the agent, but is unavailable for use by
				     the managed device (see NOTE below);
				
				     - `notReady', which indicates that the conceptual row
				     exists in the agent, but is missing information
				     necessary in order to be available for use by the
				     managed device;
				
				     - `createAndGo', which is supplied by a management
				     station wishing to create a new instance of a
				     conceptual row and to have its status automatically set
				     to active, making it available for use by the managed
				     device;
				
				     - `createAndWait', which is supplied by a management
				     station wishing to create a new instance of a
				     conceptual row (but not make it available for use by
				     the managed device); and,
				
				     - `destroy', which is supplied by a management station
				     wishing to delete all of the instances associated with
				     an existing conceptual row.
				
				Whereas five of the six values (all except `notReady') may
				be specified in a management protocol set operation, only
				three values will be returned in response to a management
				protocol retrieval operation:  `notReady', `notInService' or
				`active'.  That is, when queried, an existing conceptual row
				has only three states:  it is either available for use by
				the managed device (the status column has value `active');
				it is not available for use by the managed device, though
				the agent has sufficient information to make it so (the
				status column has value `notInService'); or, it is not
				available for use by the managed device, and an attempt to
				make it so would fail because the agent has insufficient
				information (the state column has value `notReady').
				
				                         NOTE WELL
				
				     This textual convention may be used for a MIB table,
				     irrespective of whether the values of that table's
				     conceptual rows are able to be modified while it is
				     active, or whether its conceptual rows must be taken
				     out of service in order to be modified.  That is, it is
				     the responsibility of the DESCRIPTION clause of the
				     status column to specify whether the status column must
				     not be `active' in order for the value of some other
				     column of the same conceptual row to be modified.  If
				     such a specification is made, affected columns may be
				     changed by an SNMP set PDU if the RowStatus would not
				     be equal to `active' either immediately before or after
				     processing the PDU.  In other words, if the PDU also
				     contained a varbind that would change the RowStatus
				     value, the column in question may be changed if the
				     RowStatus was not equal to `active' as the PDU was
				     received, or if the varbind sets the status to a value
				     other than 'active'.
				
				
				Also note that whenever any elements of a row exist, the
				RowStatus column must also exist.
				
				To summarize the effect of having a conceptual row with a
				status column having a SYNTAX clause value of RowStatus,
				consider the following state diagram:
				
				
				                                           STATE
				                +--------------+-----------+-------------+-------------
				                |      A       |     B     |      C      |      D
				                |              |status col.|status column|
				                |status column |    is     |      is     |status column
				      ACTION    |does not exist|  notReady | notInService|  is active
				  --------------+--------------+-----------+-------------+-------------
				  set status    |noError    ->D|inconsist- |inconsistent-|inconsistent-
				  column to     |       or     |   entValue|        Value|        Value
				  createAndGo   |inconsistent- |           |             |
				                |         Value|           |             |
				  --------------+--------------+-----------+-------------+-------------
				  set status    |noError  see 1|inconsist- |inconsistent-|inconsistent-
				  column to     |       or     |   entValue|        Value|        Value
				  createAndWait |wrongValue    |           |             |
				  --------------+--------------+-----------+-------------+-------------
				  set status    |inconsistent- |inconsist- |noError      |noError
				  column to     |         Value|   entValue|             |
				  active        |              |           |             |
				                |              |     or    |             |
				                |              |           |             |
				                |              |see 2   ->D|          ->D|          ->D
				  --------------+--------------+-----------+-------------+-------------
				  set status    |inconsistent- |inconsist- |noError      |noError   ->C
				  column to     |         Value|   entValue|             |
				  notInService  |              |           |             |
				                |              |     or    |             |      or
				                |              |           |             |
				                |              |see 3   ->C|          ->C|wrongValue
				  --------------+--------------+-----------+-------------+-------------
				  set status    |noError       |noError    |noError      |noError
				  column to     |              |           |             |
				  destroy       |           ->A|        ->A|          ->A|          ->A
				  --------------+--------------+-----------+-------------+-------------
				  set any other |see 4         |noError    |noError      |see 5
				  column to some|              |           |             |
				  value         |              |      see 1|          ->C|          ->D
				  --------------+--------------+-----------+-------------+-------------
				  
				(1) goto B or C, depending on information available to the
				agent.
				
				(2) if other variable bindings included in the same PDU,
				provide values for all columns which are missing but
				required, then return noError and goto D.
				
				(3) if other variable bindings included in the same PDU,
				provide values for all columns which are missing but
				required, then return noError and goto C.
				
				(4) at the discretion of the agent, the return value may be
				either:
				
				     inconsistentName:  because the agent does not choose to
				     create such an instance when the corresponding
				     RowStatus instance does not exist, or
				
				     inconsistentValue:  if the supplied value is
				     inconsistent with the state of some other MIB object's
				     value, or
				
				     noError: because the agent chooses to create the
				     instance.
				
				If noError is returned, then the instance of the status
				column must also be created, and the new state is B or C,
				depending on the information available to the agent.  If
				inconsistentName or inconsistentValue is returned, the row
				remains in state A.
				
				(5) depending on the MIB definition for the column/table,
				either noError or inconsistentValue may be returned.
				
				NOTE: Other processing of the set request may result in a
				response other than noError being returned, e.g.,
				wrongValue, noCreation, etc.
				
				
				                  Conceptual Row Creation
				
				There are four potential interactions when creating a
				conceptual row:  selecting an instance-identifier which is
				not in use; creating the conceptual row; initializing any
				objects for which the agent does not supply a default; and,
				making the conceptual row available for use by the managed
				device.
				
				Interaction 1: Selecting an Instance-Identifier
				
				The algorithm used to select an instance-identifier varies
				for each conceptual row.  In some cases, the instance-
				identifier is semantically significant, e.g., the
				destination address of a route, and a management station
				selects the instance-identifier according to the semantics.
				
				In other cases, the instance-identifier is used solely to
				distinguish conceptual rows, and a management station
				without specific knowledge of the conceptual row might
				examine the instances present in order to determine an
				unused instance-identifier.  (This approach may be used, but
				it is often highly sub-optimal; however, it is also a
				questionable practice for a naive management station to
				attempt conceptual row creation.)
				
				Alternately, the MIB module which defines the conceptual row
				might provide one or more objects which provide assistance
				in determining an unused instance-identifier.  For example,
				if the conceptual row is indexed by an integer-value, then
				an object having an integer-valued SYNTAX clause might be
				defined for such a purpose, allowing a management station to
				issue a management protocol retrieval operation.  In order
				to avoid unnecessary collisions between competing management
				stations, `adjacent' retrievals of this object should be
				different.
				
				Finally, the management station could select a pseudo-random
				number to use as the index.  In the event that this index
				was already in use and an inconsistentValue was returned in
				response to the management protocol set operation, the
				management station should simply select a new pseudo-random
				number and retry the operation.
				
				A MIB designer should choose between the two latter
				algorithms based on the size of the table (and therefore the
				efficiency of each algorithm).  For tables in which a large
				number of entries are expected, it is recommended that a MIB
				object be defined that returns an acceptable index for
				creation.  For tables with small numbers of entries, it is
				recommended that the latter pseudo-random index mechanism be
				used.
				
				
				Interaction 2: Creating the Conceptual Row
				
				Once an unused instance-identifier has been selected, the
				management station determines if it wishes to create and
				activate the conceptual row in one transaction or in a
				negotiated set of interactions.
				
				Interaction 2a: Creating and Activating the Conceptual Row
				
				The management station must first determine the column
				requirements, i.e., it must determine those columns for
				which it must or must not provide values.  Depending on the
				complexity of the table and the management station's
				knowledge of the agent's capabilities, this determination
				can be made locally by the management station.  Alternately,
				the management station issues a management protocol get
				operation to examine all columns in the conceptual row that
				it wishes to create.  In response, for each column, there
				are three possible outcomes:
				
				     - a value is returned, indicating that some other
				     management station has already created this conceptual
				     row.  We return to interaction 1.
				
				     - the exception `noSuchInstance' is returned,
				     indicating that the agent implements the object-type
				     associated with this column, and that this column in at
				     least one conceptual row would be accessible in the MIB
				     view used by the retrieval were it to exist. For those
				     columns to which the agent provides read-create access,
				     the `noSuchInstance' exception tells the management
				     station that it should supply a value for this column
				     when the conceptual row is to be created.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				Once the column requirements have been determined, a
				management protocol set operation is accordingly issued.
				This operation also sets the new instance of the status
				column to `createAndGo'.
				
				When the agent processes the set operation, it verifies that
				it has sufficient information to make the conceptual row
				available for use by the managed device.  The information
				available to the agent is provided by two sources:  the
				management protocol set operation which creates the
				conceptual row, and, implementation-specific defaults
				supplied by the agent (note that an agent must provide
				implementation-specific defaults for at least those objects
				which it implements as read-only).  If there is sufficient
				information available, then the conceptual row is created, a
				`noError' response is returned, the status column is set to
				`active', and no further interactions are necessary (i.e.,
				interactions 3 and 4 are skipped).  If there is insufficient
				information, then the conceptual row is not created, and the
				set operation fails with an error of `inconsistentValue'.
				On this error, the management station can issue a management
				protocol retrieval operation to determine if this was
				because it failed to specify a value for a required column,
				or, because the selected instance of the status column
				already existed.  In the latter case, we return to
				interaction 1.  In the former case, the management station
				can re-issue the set operation with the additional
				information, or begin interaction 2 again using
				`createAndWait' in order to negotiate creation of the
				conceptual row.
				
				                         NOTE WELL
				
				     Regardless of the method used to determine the column
				     requirements, it is possible that the management
				     station might deem a column necessary when, in fact,
				     the agent will not allow that particular columnar
				     instance to be created or written.  In this case, the
				     management protocol set operation will fail with an
				     error such as `noCreation' or `notWritable'.  In this
				     case, the management station decides whether it needs
				     to be able to set a value for that particular columnar
				     instance.  If not, the management station re-issues the
				     management protocol set operation, but without setting
				     a value for that particular columnar instance;
				     otherwise, the management station aborts the row
				     creation algorithm.
				
				Interaction 2b: Negotiating the Creation of the Conceptual
				Row
				
				The management station issues a management protocol set
				operation which sets the desired instance of the status
				column to `createAndWait'.  If the agent is unwilling to
				process a request of this sort, the set operation fails with
				an error of `wrongValue'.  (As a consequence, such an agent
				must be prepared to accept a single management protocol set
				operation, i.e., interaction 2a above, containing all of the
				columns indicated by its column requirements.)  Otherwise,
				the conceptual row is created, a `noError' response is
				returned, and the status column is immediately set to either
				`notInService' or `notReady', depending on whether it has
				sufficient information to make the conceptual row available
				for use by the managed device.  If there is sufficient
				information available, then the status column is set to
				`notInService'; otherwise, if there is insufficient
				information, then the status column is set to `notReady'.
				Regardless, we proceed to interaction 3.
				
				Interaction 3: Initializing non-defaulted Objects
				
				The management station must now determine the column
				requirements.  It issues a management protocol get operation
				to examine all columns in the created conceptual row.  In
				the response, for each column, there are three possible
				outcomes:
				
				     - a value is returned, indicating that the agent
				     implements the object-type associated with this column
				     and had sufficient information to provide a value.  For
				     those columns to which the agent provides read-create
				     access (and for which the agent allows their values to
				     be changed after their creation), a value return tells
				     the management station that it may issue additional
				     management protocol set operations, if it desires, in
				     order to change the value associated with this column.
				
				     - the exception `noSuchInstance' is returned,
				     indicating that the agent implements the object-type
				     associated with this column, and that this column in at
				     least one conceptual row would be accessible in the MIB
				     view used by the retrieval were it to exist. However,
				     the agent does not have sufficient information to
				     provide a value, and until a value is provided, the
				     conceptual row may not be made available for use by the
				     managed device.  For those columns to which the agent
				     provides read-create access, the `noSuchInstance'
				     exception tells the management station that it must
				     issue additional management protocol set operations, in
				     order to provide a value associated with this column.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				If the value associated with the status column is
				`notReady', then the management station must first deal with
				all `noSuchInstance' columns, if any.  Having done so, the
				value of the status column becomes `notInService', and we
				proceed to interaction 4.
				
				Interaction 4: Making the Conceptual Row Available
				
				Once the management station is satisfied with the values
				associated with the columns of the conceptual row, it issues
				a management protocol set operation to set the status column
				to `active'.  If the agent has sufficient information to
				make the conceptual row available for use by the managed
				device, the management protocol set operation succeeds (a
				`noError' response is returned).  Otherwise, the management
				protocol set operation fails with an error of
				`inconsistentValue'.
				
				
				                         NOTE WELL
				
				     A conceptual row having a status column with value
				     `notInService' or `notReady' is unavailable to the
				     managed device.  As such, it is possible for the
				     managed device to create its own instances during the
				     time between the management protocol set operation
				     which sets the status column to `createAndWait' and the
				     management protocol set operation which sets the status
				     column to `active'.  In this case, when the management
				     protocol set operation is issued to set the status
				     column to `active', the values held in the agent
				     supersede those used by the managed device.
				
				If the management station is prevented from setting the
				status column to `active' (e.g., due to management station
				or network failure) the conceptual row will be left in the
				`notInService' or `notReady' state, consuming resources
				indefinitely.  The agent must detect conceptual rows that
				have been in either state for an abnormally long period of
				time and remove them.  It is the responsibility of the
				DESCRIPTION clause of the status column to indicate what an
				abnormally long period of time would be.  This period of
				time should be long enough to allow for human response time
				(including `think time') between the creation of the
				conceptual row and the setting of the status to `active'.
				In the absense of such information in the DESCRIPTION
				clause, it is suggested that this period be approximately 5
				minutes in length.  This removal action applies not only to
				newly-created rows, but also to previously active rows which
				are set to, and left in, the notInService state for a
				prolonged period exceeding that which is considered normal
				for such a conceptual row.
				
				
				                 Conceptual Row Suspension
				
				When a conceptual row is `active', the management station
				may issue a management protocol set operation which sets the
				instance of the status column to `notInService'.  If the
				agent is unwilling to do so, the set operation fails with an
				error of `wrongValue'.  Otherwise, the conceptual row is
				taken out of service, and a `noError' response is returned.
				It is the responsibility of the DESCRIPTION clause of the
				status column to indicate under what circumstances the
				status column should be taken out of service (e.g., in order
				for the value of some other column of the same conceptual
				row to be modified).
				
				
				                  Conceptual Row Deletion
				
				For deletion of conceptual rows, a management protocol set
				operation is issued which sets the instance of the status
				column to `destroy'.  This request may be made regardless of
				the current value of the status column (e.g., it is possible
				to delete conceptual rows which are either `notReady',
				`notInService' or `active'.)  If the operation succeeds,
				then all instances associated with the conceptual row are
				immediately removed."
			SYNTAX INTEGER
				{
				active(1),
				notInService(2),
				notReady(3),
				createAndGo(4),
				createAndWait(5),
				destroy(6)
				}

		DateAndTime ::= TEXTUAL-CONVENTION
			STATUS current
			DESCRIPTION 
				"A date-time specification.
				
				field  octets  contents                  range
				-----  ------  --------                  -----
				  1      1-2   year                      0..65536
				  2       3    month                     1..12
				  3       4    day                       1..31
				  4       5    hour                      0..23
				  5       6    minutes                   0..59
				  6       7    seconds                   0..60
				               (use 60 for leap-second)
				  7       8    deci-seconds              0..9
				  8       9    direction from UTC        '+' / '-'
				  9      10    hours from UTC            0..11
				 10      11    minutes from UTC          0..59
				
				For example, Tuesday May 26, 1992 at 1:30:15 PM EDT would be
				displayed as:
				
				                1992-5-26,13:30:15.0,-4:0
				
				Note that if only local time is known, then timezone
				information (fields 8-10) is not present."
			SYNTAX OCTET STRING (SIZE (0..255))

	
--
-- Node definitions
--
	
-- Node definitions
-- 
		-- 1.3.6.1.4.1.388
		symbol OBJECT IDENTIFIER ::= { enterprises 388 }

		
-- !!- OID: .11 - as specified by Symbol MIB Admin.
-- 
-- This sub-tree used for MIBs and sysOIDs produced 
-- by WSD, (Wireless Infrastructure Division, 
-- San Jose).
-- 
		-- 1.3.6.1.4.1.388.11
		wsd OBJECT IDENTIFIER ::= { symbol 11 }

		
-- This node reserved for sysOIDs of devices produced 
-- by WSD.
-- 
		-- 1.3.6.1.4.1.388.11.1
		sysoids OBJECT IDENTIFIER ::= { wsd 1 }

		
		-- 1.3.6.1.4.1.388.11.1.1
		ws2000 OBJECT-IDENTITY
			STATUS current
			DESCRIPTION 
				"WS2000 with 1 WAN port, 6 LAN ports."
			::= { sysoids 1 }

		
-- MIBs implemented by WS2000 devices.
-- 
-- All counter variables, under this tree node wrap in no less
-- than 5.8 minutes, EXCEPT as noted below.  (Be advised that
-- all values referred to here as 'counters' are not 
-- necessarily of type Counter32 or Counter64;  some are
-- Unsigned32, and some Signal & Noise values are Integer32).
-- 
-- Exception #1: for all values that count the number
-- of tx/rx/both octets when the MAX number of Portals (12)
-- are all running at a full 54Mb.  In such cases, those
-- counters could theoretically wrap in 0.8min.  But, since
-- 54Mb does not practically achieve 54Mb, this wrap time
-- is more realistically at least 1-2min.  If the switch does
-- not have all 12 Portals, that wrap time would be even 
-- longer.
-- 
-- Exception #2: there are three _SignalSum values, (Portal,
-- MU, and WLAN);  since Signal values range up to around
-- -90dBm, they could theoretically wrap in 0.5min if the MAX
-- number of Portals all had a full 54Mb of short packets 
-- flowing, all with _Signal values of around -100.  Since you
-- generally cannot communicate at 54Mb at -100dBm, this is
-- not practially realistic.  At more realistic levels, these
-- values would wrap no faster than 1-2min, and verly likely
-- no faster than 5min.
-- 
-- (It was considered to increase the affected counters to
-- 64bits, but given the difficulty implementing larger 
-- counters and the large number of values to change, as
-- weighed against the REALISTIC wrap risk did not suggest
-- doing this work).
-- 
-- Given all this, a poll time of 5min, (or less), will
-- basically ensure that no data is lost due to counter wrap.
-- 
-- 
-- 
-- Numerous tables include _SumSquares values.  These MIB
-- variables are always the summation of the square of each
-- individual value.  These _SumSquares values can be used,
-- (in conjunction with 'N' and _Sum), to calculate standard
-- deviation, (a statistical measure of the variance of the
-- data points).
		-- 1.3.6.1.4.1.388.11.2
		ws2k OBJECT IDENTIFIER ::= { wsd 2 }

		
-- Miscelaneous administrative functions.
		-- 1.3.6.1.4.1.388.11.2.2
		ccAdmin OBJECT IDENTIFIER ::= { ws2k 2 }

		
-- Information about the switch not otherwise
-- provided in MIB-2.
		-- 1.3.6.1.4.1.388.11.2.2.1
		ccInfo OBJECT IDENTIFIER ::= { ccAdmin 1 }

		
		-- 1.3.6.1.4.1.388.11.2.2.1.1
		ccInfoSerialNumber OBJECT-TYPE
			SYNTAX DisplayString
			MAX-ACCESS read-only
			STATUS current
			DESCRIPTION
				"The serial number of the switch.  This value is
				unique for each instance of the WS2000 switch."
			::= { ccInfo 1 }

		
		-- 1.3.6.1.4.1.388.11.2.2.1.2
		ccInfoCountrySelection OBJECT-TYPE
			SYNTAX DisplayString
			MAX-ACCESS read-write
			STATUS current
			DESCRIPTION
				"This value is a two-character representation of the country
				code.
				
				Note: when changing this _CountrySelection, the current
				channel and power levels are NOT changed.  The prior 
				settings for these values may or may not be valid/legal 
				for the new country selected.  It is up to the network 
				management software to ensure that channel and/or power
				settings are changed BEFORE changing the country selection
				so that no such invalid/illegal state is reached, even for
				a short interim.
						
						
				country code:
						
					Argentina:            ar 
					Australia:            au 
					Austria:              at
					Bahrain:              bh
					Belarus:              by
					Belgium:              be
					Botswana:             bw
					Brazil:               br
					Bulgaria:             bg
					Canada:               ca
					Chile:                cl
					China:                cn
					Colombia:             co
					Costa Rica:           cr
					Croatia:              hr
					Czech Republic:       cz
					Denmark:              dk
					Ecuador:              ec
					Egypt:                eg
					Estonia:              ee
					Finland:              fi
					France:               fr
					Germany:              de
					Greece:               gr
					Hong Kong:            hk
					Hungary:              hu
					Iceland:              is
					India:                in
					Indonesia:            id
					Ireland:              ie
					Israel:               il
					Italy:                it
					Japan:                jp
					Jordan:               jo
					Kazakhstan:           kz
					Kuwait:               kw
					Latvia:               lv
					Liechtenstein:        li
					Lithuania:            lt
					Luxembourg:           lu
					Malaysia:             my
					Mexico:               mx
					Morocco:              ma
					Namibia:              na
					Netherlands:          nl
					New Zealand:          nz
					Norway:               no
					Oman:                 om
					Peru:                 pe
					Philippines:          ph
					Poland:               pl
					Portugal:             pt
					Qatar:                qa
					Romania:              ro
					Russia:               ru
					Saudi Arabia:         sa
					Singapore:            sg
					Slovak Republic:      sk
					Slovenia:             si
					South Africa:         za
					South Korea:          kr
					Spain:                es
					Sri Lanka:            lk
					Sweden:               se
					Switzerland:          ch
					Taiwan:               tw
					Thailand:             th
					Turkey:               tr
					Ukraine:              ua
					United Arab Emirates: ae
					United Kingdom:       uk
					United States:        us
					Uruguay:              uy
					Venezuela:            ve
					Vietnam:              vn
				"
			::= { ccInfo 2 }

		
-- This group contains MIB variables that identify the versions
-- of various components of the switch.
-- 
-- sysDescr is ALSO overloaded for this purpose.  The 'terms'
-- reported in sysDescr occur in the same order as the MIB
-- values in this group.
-- 
-- (Separate MIB scalars report each term separately to make
-- it easy for SNMP scripts to find the given information.  The
-- infomation is also retained in an overloaded sysDescr since
-- many NMS platforms show this one value prominently).
-- 
-- In sysDescr, each term is marked with a 'label':
--   'HW=', 'FW=', 'SW=', 'MIB=', 'CLI=', 'XML='.
-- Each label in sysDescr is followed, (without a space), by
-- a sub-string (which itself contains no spaces), that 
-- describes the version of that entity.  Each term, (except 
-- the last), is followed by a ',' and a space before the next
-- term.
-- 
-- If a device does not have a particular item, (for
-- example no XML interface), that term and its lablel 
-- will be entirely missing from sysDescr, and the 
-- corresponding MIB scalar will be either a zero-length 
-- string, or will return a NO-SUCH.
-- 
-- The MIB version substring is a two-digit number (with a
-- leading zero if needed), followed by a lower-case letter.  
-- The letter is increased if only comments or descriptions 
-- are changed.  If any other change is made, the number 
-- increases.
-- 
-- The CLI version substring is a three-digit number,  (with 
-- leading zeros if needed).  There is no letter.  Any change
-- in CLI commands, parameters, or outputs results in this
-- value incrementing.
-- 
-- The XML version substring has the same format as the MIB
-- version sub-string.
-- 
-- SerialNumber is included here for convenience;  it is not
-- displayed in sysDescr.
		-- 1.3.6.1.4.1.388.11.2.2.1.3
		ccIdentfication OBJECT IDENTIFIER ::= { ccInfo 3 }

		
		-- 1.3.6.1.4.1.388.11.2.2.1.3.1
		ccIdHwVersion OBJECT-TYPE
			SYNTAX DisplayString
			MAX-ACCESS read-only
			STATUS current
			DESCRIPTION
				"The same text that follows 'HW=' in sysDescr, EXCLUDING the
				'HW='."
			::= { ccIdentfication 1 }

		
		-- 1.3.6.1.4.1.388.11.2.2.1.3.2
		ccIdFwVersion OBJECT-TYPE
			SYNTAX DisplayString
			MAX-ACCESS read-only
			STATUS current
			DESCRIPTION
				"The same text that follows 'FW=' in sysDescr, EXCLUDING the
				'FW='.  (The bootcode version)."
			::= { ccIdentfication 2 }

		
		-- 1.3.6.1.4.1.388.11.2.2.1.3.3
		ccIdSwVersion OBJECT-TYPE
			SYNTAX DisplayString
			MAX-ACCESS read-only
			STATUS current
			DESCRIPTION
				"The same text that follows 'SW=' in sysDescr, EXCLUDING the
				'SW='."
			::= { ccIdentfication 3 }

		
		-- 1.3.6.1.4.1.388.11.2.2.1.3.4
		ccIdMibVersion OBJECT-TYPE
			SYNTAX DisplayString
			MAX-ACCESS read-only
			STATUS current
			DESCRIPTION
				"The same text that follows 'MIB=' in sysDescr, EXCLUDING the
				'MIB='.
				
				The MIB version is identified by a two-digit major version 
				number (with a leading zero if needed), followed by a 
				lower-case letter minor version and 0 or more character info 
				number.
								
				The major MIB version is changed whenever it becomes 
				incompatible to its previous version; i.e., some variables 
				have been deleted or the behavior/meaning has been changed. 
								
				Minor version number is changed when new features have been 
				added, but existing behavior is completely unchanged.
				"
			::= { ccIdentfication 4 }

		
		-- 1.3.6.1.4.1.388.11.2.2.1.3.5
		ccIdCliVersion OBJECT-TYPE
			SYNTAX DisplayString
			MAX-ACCESS read-only
			STATUS current
			DESCRIPTION
				"The same text that follows 'CLI=' in sysDescr, EXCLUDING the
				'CLI='."
			::= { ccIdentfication 5 }

		
		-- 1.3.6.1.4.1.388.11.2.2.1.3.6
		ccIdXmlVersion OBJECT-TYPE
			SYNTAX DisplayString
			MAX-ACCESS read-only
			STATUS current
			DESCRIPTION
				"Version of XML template implemented on this switch.  (Much 
				like MIB version - read details there)."
			::= { ccIdentfication 6 }

		
		-- 1.3.6.1.4.1.388.11.2.2.1.3.7
		ccIdSerialNumber OBJECT-TYPE
			SYNTAX DisplayString
			MAX-ACCESS read-only
			STATUS current
			DESCRIPTION
				"The serial number of the switch.  This value is unique for each
				instance of a given switch type."
			::= { ccIdentfication 7 }

		
		-- 1.3.6.1.4.1.388.11.2.2.1.4
		ccSysDNSRelayMode OBJECT-TYPE
			SYNTAX TruthValue
			MAX-ACCESS read-write
			STATUS current
			DESCRIPTION
				"Enable/Disable DNS Relay Mode"
			DEFVAL { false }
			::= { ccInfo 4 }


		-- 1.3.6.1.4.1.388.11.2.2.1.5
                ccApSslv2Mode OBJECT-TYPE
                        SYNTAX TruthValue
                        MAX-ACCESS read-write
                        STATUS current
                        DESCRIPTION
                                "Enable/Disable SSLV2 Support"
                        DEFVAL { false }
                        ::= { ccInfo 5 }


                -- 1.3.6.1.4.1.388.11.2.2.1.6
                ccApSshv1Mode OBJECT-TYPE
                        SYNTAX TruthValue
                        MAX-ACCESS read-write
                        STATUS current
                        DESCRIPTION
                                "Enable/Disable SSHV1 Support"
                        DEFVAL { false }
                        ::= { ccInfo 6 }


                -- 1.3.6.1.4.1.388.11.2.2.1.7
                ccApSslWeakCipherSupport OBJECT-TYPE
                        SYNTAX TruthValue
                        MAX-ACCESS read-write
                        STATUS current
                        DESCRIPTION
                                "Enable/Disable SSL Weak Cipher Support"
                        DEFVAL { false }
                        ::= { ccInfo 7 }



		
-- Values that can be used to reset portions of the 
-- switch.
-- 
-- Reading any of the items in this group will always
-- return a value of 'false'.
		-- 1.3.6.1.4.1.388.11.2.2.2
		ccReset OBJECT IDENTIFIER ::= { ccAdmin 2 }

		
		-- 1.3.6.1.4.1.388.11.2.2.2.1
		ccResetFactory OBJECT-TYPE
			SYNTAX TruthValue
			MAX-ACCESS read-write
			STATUS current
			DESCRIPTION
				"Writing this value causes the switch to reset to
				factory conditions.  NOTHING is retained, NOT the
				static IP address assignments (if any), NOR any 
				non-factory-default SNMP settings, nor any other
				non-factory-default settings.
				
				Given this, be warned that setting this value may
				very well cause all communication paths to the 
				WS2000 to be lost.  (However, if DHCP is used to
				obtain an IP addr on the WAN port, and only 
				default SNMP settings are used, communications may
				be possible after the factory reset)."
			::= { ccReset 1 }

		
		-- 1.3.6.1.4.1.388.11.2.2.2.2
		ccResetSwitch OBJECT-TYPE
			SYNTAX TruthValue
			MAX-ACCESS read-write
			STATUS current
			DESCRIPTION
				"Writing this value causes the switch to reset in
				the same fashion as a common, (non-factory) reset."
			::= { ccReset 2 }

		
		-- 1.3.6.1.4.1.388.11.2.2.2.3
		ccResetMuCounters OBJECT-TYPE
			SYNTAX TruthValue
			MAX-ACCESS read-write
			STATUS obsolete
			DESCRIPTION
				"Writing this value resets all counters in the
				ccRf > ccMus sub-tree.
				
				Obsolete in WS2000 v1.5"
			::= { ccReset 3 }

		
		-- 1.3.6.1.4.1.388.11.2.2.2.4
		ccResetFactoryExceptIpSnmp OBJECT-TYPE
			SYNTAX DoActionNow
			MAX-ACCESS read-write
			STATUS current
			DESCRIPTION
				"Performs a factory reset, EXCEPT that Wan IP and SNMP access settings
				are retained across the reset.  Specifically:
				
				Wan Ip + related settings
				Pppoe settings
				WS2000 wan access SNMP setting
				SNMP v1/v2/v3 access settings
				
				
				"
			::= { ccReset 4 }

		
		-- 1.3.6.1.4.1.388.11.2.2.2.5
		ccResetStatCounters OBJECT-TYPE
			SYNTAX TruthValue
			MAX-ACCESS read-write
			STATUS current
			DESCRIPTION
				"Writing this value resets all counters in the
				ccRf sub-tree except for the ccPortalSystemStatsTable and 
				ccPortalTable
				"
			::= { ccReset 5 }

		
-- Values used to initiate, (via TFTP or FTP), a 
-- firmware update of the switch remotely via SNMP.
-- 
-- All items in this group persist across reboots,
-- except: _FwOperation and _FwStart.
		-- 1.3.6.1.4.1.388.11.2.2.3
		ccLoadFw OBJECT IDENTIFIER ::= { ccAdmin 3 }

		
		-- 1.3.6.1.4.1.388.11.2.2.3.1
		ccLoadFwOperation OBJECT-TYPE
			SYNTAX INTEGER
				{
				unspecified(1),
				ftpFirmwareServerToSwitch(2),
				tftpFirmwareServerToSwitch(3),
				cfFirmwareToSwitch(4),
				sftpFirmwareServerToSwitch(5)
				}
			MAX-ACCESS read-write
			STATUS current
			DESCRIPTION
				"Specifies if the firmware is to be loaded to the
				switch via FTP or TFTP or SFTP or CF Card."
			::= { ccLoadFw 1 }

		
		-- 1.3.6.1.4.1.388.11.2.2.3.2
		ccLoadFwInterface OBJECT-TYPE
			SYNTAX INTEGER
				{
				unspecified(1),
				wan(2),
				subnet1(11),
				subnet2(12),
				subnet3(13),
				subnet4(14)
				}
			MAX-ACCESS read-write
			STATUS current
			DESCRIPTION
				"The interface to use in contacting the FTP or TFTP 
				or SFTP server. This is required since the actual 
				firmware load is accomplished via boot code that 
				does not contain routing logic."
			::= { ccLoadFw 2 }

		
		-- 1.3.6.1.4.1.388.11.2.2.3.3
		ccLoadFwServerPath OBJECT-TYPE
			SYNTAX DisplayString (SIZE (0..39))
			MAX-ACCESS read-write
			STATUS current
			DESCRIPTION
				"The path to the firmware on the SFTP/TFTP/FTP 
				server.
				
				Remember that the type of separator varies 
				depending on the operating system of the server.
				For Windows, use '\', for Unix use '/'.
				
				No path need be specified, (in which case the 
				default directory for the TFTP/FTP/SFTP server 
				will be used);  if a path is specified, remember
				to terminate it with a trailing '/' or '\'."
			::= { ccLoadFw 3 }

		
		-- 1.3.6.1.4.1.388.11.2.2.3.4
		ccLoadFwServerFilename OBJECT-TYPE
			SYNTAX DisplayString (SIZE (0..39))
			MAX-ACCESS read-write
			STATUS current
			DESCRIPTION
				"The name, (on the server), of the firmware file 
				to load.
				
				If operation is set to cfFirmwareToSwitch, this 
				variable is the file name on the compact flash card."
			::= { ccLoadFw 4 }

		
		-- 1.3.6.1.4.1.388.11.2.2.3.5
		ccLoadFwStart OBJECT-TYPE
			SYNTAX TruthValue
			MAX-ACCESS read-write
			STATUS current
			DESCRIPTION
				"Set this value to start the firmware load
				operation.
				
				Note that the actual SFTP/TFTP/FTP does not begin
				immediately, as first the 'operational' firmware
				shuts-down, and returns to low-level boot code,
				which actually starts the transfer."
			::= { ccLoadFw 5 }

		
		-- 1.3.6.1.4.1.388.11.2.2.3.6
		ccLoadFwResult OBJECT-TYPE
			SYNTAX DisplayString
			MAX-ACCESS read-only
			STATUS current
			DESCRIPTION
				"This value reflects the result of the most-recent
				firmware load since reboot, (if any)."
			::= { ccLoadFw 6 }

		
		-- 1.3.6.1.4.1.388.11.2.2.3.7
		ccLoadFwSuccess OBJECT-TYPE
			SYNTAX TruthValue
			MAX-ACCESS read-only
			STATUS current
			DESCRIPTION
				"The success/failure status of the most recent
				firmware load."
			::= { ccLoadFw 7 }

		
-- Values used to initiate (via FTP only), a 
-- download of a configuration file to the switch, 
-- or an upload of a configuration file from the 
-- switch.
-- 
-- All items in this group persist across reboots,
-- except: _CfgOperation and _CfgStart.
		-- 1.3.6.1.4.1.388.11.2.2.4
		ccLoadCfg OBJECT IDENTIFIER ::= { ccAdmin 4 }

		
		-- 1.3.6.1.4.1.388.11.2.2.4.1
		ccLoadCfgOperation OBJECT-TYPE
			SYNTAX INTEGER
				{
				unspecified(1),
				ftpConfigServerToSwitch(2),
				ftpConfigSwitchToServer(3),
				tftpConfigServerToSwitch(4),
				tftpConfigSwitchToServer(5),
				sftpConfigServerToSwitch(6),
				sftpConfigSwitchToServer(7)
				}
			MAX-ACCESS read-write
			STATUS current
			DESCRIPTION
				"Specifies the type and direction of the transfer to 
				perform involving the configuration file."
			::= { ccLoadCfg 1 }

		
		-- 1.3.6.1.4.1.388.11.2.2.4.2
		ccLoadCfgServerPath OBJECT-TYPE
			SYNTAX DisplayString (SIZE (0..39))
			MAX-ACCESS read-write
			STATUS current
			DESCRIPTION
				"The path to the firmware on the SFTP/TFTP/FTP 
				server.
				
				Remember that the type of separator varies 
				depending on the operating system of the server.
				For Windows, use '\', for Unix use '/'.
				
				No path need be specified, (in which case the 
				default directory for the SFTP/TFTP/FTP server 
				will be used);  if a path is specified, remember 
				to terminate it with a trailing '/' or '\'."
			::= { ccLoadCfg 2 }

		
		-- 1.3.6.1.4.1.388.11.2.2.4.3
		ccLoadCfgServerFilename OBJECT-TYPE
			SYNTAX DisplayString (SIZE (0..39))
			MAX-ACCESS read-write
			STATUS current
			DESCRIPTION
				"The name, (on the server), of the configuration 
				file to load/store from/to the server."
			::= { ccLoadCfg 3 }

		
		-- 1.3.6.1.4.1.388.11.2.2.4.4
		ccLoadCfgStart OBJECT-TYPE
			SYNTAX TruthValue
			MAX-ACCESS read-write
			STATUS current
			DESCRIPTION
				"Set this value to start the configuration file 
				operation.
				
				Note that unlike a firmware load, the actual 
				FTP/TFTP/SFTP transfer does begin virtually 
				immediately."
			::= { ccLoadCfg 4 }

		
		-- 1.3.6.1.4.1.388.11.2.2.4.5
		ccLoadCfgOperationsDone OBJECT-TYPE
			SYNTAX Counter32
			MAX-ACCESS read-only
			STATUS current
			DESCRIPTION
				"This value counts the total number of configuration
				file transfers completed, (whether they succeed or
				fail).
				
				The SNMP manager should save the value of this
				counter just before starting a LoadCfg operation,
				and then wait for this value to increment before
				checking the Result and/or Success values."
			::= { ccLoadCfg 5 }

		
		-- 1.3.6.1.4.1.388.11.2.2.4.6
		ccLoadCfgResult OBJECT-TYPE
			SYNTAX DisplayString
			MAX-ACCESS read-only
			STATUS current
			DESCRIPTION
				"This value reflects the result of the most-recent
				configuration file load/store."
			::= { ccLoadCfg 6 }

		
		-- 1.3.6.1.4.1.388.11.2.2.4.7
		ccLoadCfgSuccess OBJECT-TYPE
			SYNTAX TruthValue
			MAX-ACCESS read-only
			STATUS current
			DESCRIPTION
				"The success/failure status of the most recent
				configuration file load/store."
			::= { ccLoadCfg 7 }

		
-- Values that indicate if the configuration of the 
-- switch has changed.
		-- 1.3.6.1.4.1.388.11.2.2.5
		ccCfgHist OBJECT IDENTIFIER ::= { ccAdmin 5 }

		
		-- 1.3.6.1.4.1.388.11.2.2.5.1
		ccCfgHistChangeCount OBJECT-TYPE
			SYNTAX Unsigned32
			MAX-ACCESS read-write
			STATUS current
			DESCRIPTION
				"This value will increment by 1 or more for each
				config change.  It persists across reboots.
				
				This variable can only be SET with the same value
				that it currently contains.  Any other value will
				cause a SET-FAILED.
				
				Note that this is NOT a TEST-AND-INCREMENT
				semaphore, as this value does not immediately
				increment after a config change, but only after
				a short, though non-zero, delay.  Because of this
				non-zero delay, it is not suitable as a semaphore.
				
				Note also that this value counts the number of
				times that Flash memory has been written, which
				may be greater than the number of config changes."
			::= { ccCfgHist 1 }

		
		-- 1.3.6.1.4.1.388.11.2.2.5.2
		ccCfgHistChangeTime OBJECT-TYPE
			SYNTAX TimeTicks
			MAX-ACCESS read-only
			STATUS current
			DESCRIPTION
				"A snapshot of sysUpTime as of the last config 
				change."
			::= { ccCfgHist 2 }

		
		-- 1.3.6.1.4.1.388.11.2.2.5.3
		ccCfgHistSemaphore OBJECT-TYPE
			SYNTAX TestAndIncr
			MAX-ACCESS read-write
			STATUS current
			DESCRIPTION
				"Can be used to solve the multiple-manager problem.
				Before performing any SETs, the manager reads this
				value.  As a VAR-BIND of the only/last SET PDU,
				this value is written with that value read.  If
				some other manager had made changes, this value 
				would have incremented, and the SET to it will 
				fail.
				
				Note that this only guards against other managers
				that use this semaphore.  Changes made without
				using this value will NOT be protected against.
				For this reason, it is suggested that
				ccCfgHistChangeCount also be SET - though that is
				not a perfectly fail-safe semaphore, it will in
				most cases protect even against this latter case."
			::= { ccCfgHist 3 }

		
-- This group contains items that are common between
-- ccLoadFw and ccLoadCfg.  This is not done just to
-- eliminate duplication, but also because the
-- values in this group are actually implemented only
-- once on the device.
-- 
-- (If these items were implemented in both ccLoadFw 
-- and ccLoadCfg, setting a value in one group would 
-- also be reflected in the corresponding variable in
-- the other group).
-- 
-- All items in this group persist across reboots.
		-- 1.3.6.1.4.1.388.11.2.2.6
		ccLoad OBJECT IDENTIFIER ::= { ccAdmin 6 }

		
		-- 1.3.6.1.4.1.388.11.2.2.6.1
		ccLoadServerIpAddr OBJECT-TYPE
			SYNTAX IpAddress
			MAX-ACCESS read-write
			STATUS current
			DESCRIPTION
				"IP address of the server used for a firmware load,
				or configuration file load/store operation."
			::= { ccLoad 1 }

		
		-- 1.3.6.1.4.1.388.11.2.2.6.2
		ccLoadFtpUsername OBJECT-TYPE
			SYNTAX DisplayString (SIZE (0..39))
			MAX-ACCESS read-write
			STATUS current
			DESCRIPTION
				"Username for FTP LoadFw or LoadCfg operations."
			::= { ccLoad 2 }

		
		-- 1.3.6.1.4.1.388.11.2.2.6.3
		ccLoadFtpPassword OBJECT-TYPE
			SYNTAX DisplayString (SIZE (0..39))
			MAX-ACCESS read-write
			STATUS current
			DESCRIPTION
				"Password for FTP LoadFw or LoadCfg operations."
			::= { ccLoad 3 }

		
-- Miscellaneous values not implemented in MIB-2 SNMP
-- group.
		-- 1.3.6.1.4.1.388.11.2.2.7
		ccSnmp OBJECT IDENTIFIER ::= { ccAdmin 7 }

		
		-- 1.3.6.1.4.1.388.11.2.2.7.1
		ccSnmpAclViolations OBJECT-TYPE
			SYNTAX Counter32
			MAX-ACCESS read-only
			STATUS current
			DESCRIPTION
				"Counts the total number of SNMP requests rejected
				due to ACL violations since boot."
			::= { ccSnmp 1 }

		
		-- 1.3.6.1.4.1.388.11.2.2.7.2
		ccSnmpLastDeniedIpAddr OBJECT-TYPE
			SYNTAX IpAddress
			MAX-ACCESS read-only
			STATUS current
			DESCRIPTION
				"The IP address of the last SNMP request to be 
				denied due to ACL violation."
			::= { ccSnmp 2 }

		
		-- 1.3.6.1.4.1.388.11.2.2.7.3
		ccSnmpV3EngineId OBJECT-TYPE
			SYNTAX DisplayString (SIZE (1..64))
			MAX-ACCESS read-only
			STATUS current
			DESCRIPTION
				"SNMPv3 Engine ID"
			::= { ccSnmp 3 }

		
		-- 1.3.6.1.4.1.388.11.2.2.7.4
		ccSnmpAccess OBJECT IDENTIFIER ::= { ccSnmp 4 }

		
		-- 1.3.6.1.4.1.388.11.2.2.7.4.1
		ccSnmpAccessV12Table OBJECT-TYPE
			SYNTAX SEQUENCE OF CcSnmpAccessV12Entry
			MAX-ACCESS not-accessible
			STATUS current
			DESCRIPTION
				"Table of SNMP v1/v2 access entries."
			::= { ccSnmpAccess 1 }

		
		-- 1.3.6.1.4.1.388.11.2.2.7.4.1.1
		ccSnmpAccessV12Entry OBJECT-TYPE
			SYNTAX CcSnmpAccessV12Entry
			MAX-ACCESS not-accessible
			STATUS current
			DESCRIPTION
				"Description."
			INDEX { ccSnmpAccessV12Index }
			::= { ccSnmpAccessV12Table 1 }

		
		CcSnmpAccessV12Entry ::=
			SEQUENCE { 
				ccSnmpAccessV12Index
					Integer32,
				ccSnmpAccessV12Community
					DisplayString,
				ccSnmpAccessV12CustomOid
					OBJECT IDENTIFIER,
				ccSnmpAccessV12OidLimit
					INTEGER,
				ccSnmpAccessV12Access
					INTEGER,
				ccSnmpAccessV12Enable
					AbbrevRowStatus
			 }

		-- 1.3.6.1.4.1.388.11.2.2.7.4.1.1.1
		ccSnmpAccessV12Index OBJECT-TYPE
			SYNTAX Integer32 (1..20)
			MAX-ACCESS accessible-for-notify
			STATUS current
			DESCRIPTION
				"Simple Index."
			::= { ccSnmpAccessV12Entry 1 }

		
		-- 1.3.6.1.4.1.388.11.2.2.7.4.1.1.2
		ccSnmpAccessV12Community OBJECT-TYPE
			SYNTAX DisplayString
			MAX-ACCESS read-write
			STATUS current
			DESCRIPTION
				"Community Name of the SNMP manager."
			::= { ccSnmpAccessV12Entry 2 }

		
		-- 1.3.6.1.4.1.388.11.2.2.7.4.1.1.3
		ccSnmpAccessV12CustomOid OBJECT-TYPE
			SYNTAX OBJECT IDENTIFIER
			MAX-ACCESS read-write
			STATUS current
			DESCRIPTION
				"Starting OID."
			::= { ccSnmpAccessV12Entry 3 }

		
		-- 1.3.6.1.4.1.388.11.2.2.7.4.1.1.4
		ccSnmpAccessV12OidLimit OBJECT-TYPE
			SYNTAX INTEGER
				{
				all(1),
				custom(2)
				}
			MAX-ACCESS read-write
			STATUS current
			DESCRIPTION
				"OID Limit whether the entire MIB tree or 
				a specific OID set."
			::= { ccSnmpAccessV12Entry 4 }

		
		-- 1.3.6.1.4.1.388.11.2.2.7.4.1.1.5
		ccSnmpAccessV12Access OBJECT-TYPE
			SYNTAX INTEGER
				{
				readOnly(1),
				readWrite(2)
				}
			MAX-ACCESS read-write
			STATUS current
			DESCRIPTION
				"Access type whether RO or RW."
			::= { ccSnmpAccessV12Entry 5 }

		
		-- 1.3.6.1.4.1.388.11.2.2.7.4.1.1.6
		ccSnmpAccessV12Enable OBJECT-TYPE
			SYNTAX AbbrevRowStatus
			MAX-ACCESS read-write
			STATUS current
			DESCRIPTION
				"Row Status."
			::= { ccSnmpAccessV12Entry 6 }

		
		-- 1.3.6.1.4.1.388.11.2.2.7.4.2
		ccSnmpAccessV3Table OBJECT-TYPE
			SYNTAX SEQUENCE OF CcSnmpAccessV3Entry
			MAX-ACCESS not-accessible
			STATUS current
			DESCRIPTION
				"Table of SNMP v3 access entries."
			::= { ccSnmpAccess 2 }

		
		-- 1.3.6.1.4.1.388.11.2.2.7.4.2.1
		ccSnmpAccessV3Entry OBJECT-TYPE
			SYNTAX CcSnmpAccessV3Entry
			MAX-ACCESS not-accessible
			STATUS current
			DESCRIPTION
				"Description."
			INDEX { ccSnmpAccessV3Index }
			::= { ccSnmpAccessV3Table 1 }

		
		CcSnmpAccessV3Entry ::=
			SEQUENCE { 
				ccSnmpAccessV3Index
					Integer32,
				ccSnmpAccessV3User
					DisplayString,
				ccSnmpAccessV3SecurityLevel
					INTEGER,
				ccSnmpAccessV3CustomOid
					OBJECT IDENTIFIER,
				ccSnmpAccessV3OidLimit
					INTEGER,
				ccSnmpAccessV3Access
					INTEGER,
				ccSnmpAccessV3AuthAlgorithm
					INTEGER,
				ccSnmpAccessV3AuthPassword
					Password,
				ccSnmpAccessV3PrivacyAlgorithm
					INTEGER,
				ccSnmpAccessV3PrivacyPassword
					Password,
				ccSnmpAccessV3Enable
					AbbrevRowStatus
			 }

		-- 1.3.6.1.4.1.388.11.2.2.7.4.2.1.1
		ccSnmpAccessV3Index OBJECT-TYPE
			SYNTAX Integer32 (1..20)
			MAX-ACCESS accessible-for-notify
			STATUS current
			DESCRIPTION
				"Simple Index."
			::= { ccSnmpAccessV3Entry 1 }

		
		-- 1.3.6.1.4.1.388.11.2.2.7.4.2.1.2
		ccSnmpAccessV3User OBJECT-TYPE
			SYNTAX DisplayString (SIZE (1..32))
			MAX-ACCESS read-write
			STATUS current
			DESCRIPTION
				"v3 User Name."
			::= { ccSnmpAccessV3Entry 2 }

		
		-- 1.3.6.1.4.1.388.11.2.2.7.4.2.1.3
		ccSnmpAccessV3SecurityLevel OBJECT-TYPE
			SYNTAX INTEGER
				{
				noAuth(1),
				authNoPriv(2),
				authPriv(3)
				}
			MAX-ACCESS read-write
			STATUS current
			DESCRIPTION
				"Security Level."
			::= { ccSnmpAccessV3Entry 3 }

		
		-- 1.3.6.1.4.1.388.11.2.2.7.4.2.1.4
		ccSnmpAccessV3CustomOid OBJECT-TYPE
			SYNTAX OBJECT IDENTIFIER
			MAX-ACCESS read-write
			STATUS current
			DESCRIPTION
				"Starting OID."
			::= { ccSnmpAccessV3Entry 4 }

		
		-- 1.3.6.1.4.1.388.11.2.2.7.4.2.1.5
		ccSnmpAccessV3OidLimit OBJECT-TYPE
			SYNTAX INTEGER
				{
				all(1),
				custom(2)
				}
			MAX-ACCESS read-write
			STATUS current
			DESCRIPTION
				"OID Limit whether the entire MIB tree or 
				a specific OID set."
			::= { ccSnmpAccessV3Entry 5 }

		
		-- 1.3.6.1.4.1.388.11.2.2.7.4.2.1.6
		ccSnmpAccessV3Access OBJECT-TYPE
			SYNTAX INTEGER
				{
				readOnly(1),
				readWrite(2)
				}
			MAX-ACCESS read-write
			STATUS current
			DESCRIPTION
				"Access type whether RO or RW."
			::= { ccSnmpAccessV3Entry 6 }

		
		-- 1.3.6.1.4.1.388.11.2.2.7.4.2.1.7
		ccSnmpAccessV3AuthAlgorithm OBJECT-TYPE
			SYNTAX INTEGER
				{
				md5(1),
				sha(2)
				}
			MAX-ACCESS read-write
			STATUS current
			DESCRIPTION
				"Authentication Algorithm used."
			::= { ccSnmpAccessV3Entry 7 }

		
		-- 1.3.6.1.4.1.388.11.2.2.7.4.2.1.8
		ccSnmpAccessV3AuthPassword OBJECT-TYPE
			SYNTAX Password (SIZE (8..31))
			MAX-ACCESS read-write
			STATUS current
			DESCRIPTION
				"Authentication Password."
			::= { ccSnmpAccessV3Entry 8 }

		
		-- 1.3.6.1.4.1.388.11.2.2.7.4.2.1.9
		ccSnmpAccessV3PrivacyAlgorithm OBJECT-TYPE
			SYNTAX INTEGER
				{
				des(1),
				aes128(2)
				}
			MAX-ACCESS read-write
			STATUS current
			DESCRIPTION
				"Privacy Algorithm used."
			::= { ccSnmpAccessV3Entry 9 }

		
		-- 1.3.6.1.4.1.388.11.2.2.7.4.2.1.10
		ccSnmpAccessV3PrivacyPassword OBJECT-TYPE
			SYNTAX Password (SIZE (8..31))
			MAX-ACCESS read-write
			STATUS current
			DESCRIPTION
				"Privacy Password."
			::= { ccSnmpAccessV3Entry 10 }

		
		-- 1.3.6.1.4.1.388.11.2.2.7.4.2.1.11
		ccSnmpAccessV3Enable OBJECT-TYPE
			SYNTAX AbbrevRowStatus
			MAX-ACCESS read-write
			STATUS current
			DESCRIPTION
				"Row Status."
			::= { ccSnmpAccessV3Entry 11 }

		
		-- 1.3.6.1.4.1.388.11.2.2.7.4.3
		ccSnmpAccessControlTable OBJECT-TYPE
			SYNTAX SEQUENCE OF CcSnmpAccessControlEntry
			MAX-ACCESS not-accessible
			STATUS current
			DESCRIPTION
				"Table of SNMP access control entries."
			::= { ccSnmpAccess 3 }

		
		-- 1.3.6.1.4.1.388.11.2.2.7.4.3.1
		ccSnmpAccessControlEntry OBJECT-TYPE
			SYNTAX CcSnmpAccessControlEntry
			MAX-ACCESS not-accessible
			STATUS current
			DESCRIPTION
				"Description."
			INDEX { ccSnmpAccessControlIndex }
			::= { ccSnmpAccessControlTable 1 }

		
		CcSnmpAccessControlEntry ::=
			SEQUENCE { 
				ccSnmpAccessControlIndex
					Integer32,
				ccSnmpAccessControlStartIp
					IpAddress,
				ccSnmpAccessControlEndIp
					IpAddress,
				ccSnmpAccessControlEnable
					AbbrevRowStatus
			 }

		-- 1.3.6.1.4.1.388.11.2.2.7.4.3.1.1
		ccSnmpAccessControlIndex OBJECT-TYPE
			SYNTAX Integer32 (1..20)
			MAX-ACCESS accessible-for-notify
			STATUS current
			DESCRIPTION
				"Simple Index."
			::= { ccSnmpAccessControlEntry 1 }

		
		-- 1.3.6.1.4.1.388.11.2.2.7.4.3.1.2
		ccSnmpAccessControlStartIp OBJECT-TYPE
			SYNTAX IpAddress
			MAX-ACCESS read-write
			STATUS current
			DESCRIPTION
				"Starting IP range of the SNMP manager
				allowed to access the switch."
			::= { ccSnmpAccessControlEntry 2 }

		
		-- 1.3.6.1.4.1.388.11.2.2.7.4.3.1.3
		ccSnmpAccessControlEndIp OBJECT-TYPE
			SYNTAX IpAddress
			MAX-ACCESS read-write
			STATUS current
			DESCRIPTION
				"Ending IP range of the SNMP manager
				allowed to access the switch."
			::= { ccSnmpAccessControlEntry 3 }

		
		-- 1.3.6.1.4.1.388.11.2.2.7.4.3.1.4
		ccSnmpAccessControlEnable OBJECT-TYPE
			SYNTAX AbbrevRowStatus
			MAX-ACCESS read-write
			STATUS current
			DESCRIPTION
				"Row Status."
			::= { ccSnmpAccessControlEntry 4 }

		
		-- 1.3.6.1.4.1.388.11.2.2.7.5
		ccSnmpTraps OBJECT IDENTIFIER ::= { ccSnmp 5 }

		
		-- 1.3.6.1.4.1.388.11.2.2.7.5.1
		ccSnmpTrapSinkV12Table OBJECT-TYPE
			SYNTAX SEQUENCE OF CcSnmpTrapSinkV12Entry
			MAX-ACCESS not-accessible
			STATUS current
			DESCRIPTION
				"Table of SNMP v1/v2 trap configuration entries."
			::= { ccSnmpTraps 1 }

		
		-- 1.3.6.1.4.1.388.11.2.2.7.5.1.1
		ccSnmpTrapSinkV12Entry OBJECT-TYPE
			SYNTAX CcSnmpTrapSinkV12Entry
			MAX-ACCESS not-accessible
			STATUS current
			DESCRIPTION
				"Description."
			INDEX { ccSnmpTrapSinkV12Index }
			::= { ccSnmpTrapSinkV12Table 1 }

		
		CcSnmpTrapSinkV12Entry ::=
			SEQUENCE { 
				ccSnmpTrapSinkV12Index
					Integer32,
				ccSnmpTrapSinkV12DestinationIp
					IpAddress,
				ccSnmpTrapSinkV12Port
					Integer32,
				ccSnmpTrapSinkV12Community
					DisplayString,
				ccSnmpTrapSinkV12Version
					INTEGER,
				ccSnmpTrapSinkV12Enable
					AbbrevRowStatus
			 }

		-- 1.3.6.1.4.1.388.11.2.2.7.5.1.1.1
		ccSnmpTrapSinkV12Index OBJECT-TYPE
			SYNTAX Integer32 (1..20)
			MAX-ACCESS accessible-for-notify
			STATUS current
			DESCRIPTION
				"Simple Index."
			::= { ccSnmpTrapSinkV12Entry 1 }

		
		-- 1.3.6.1.4.1.388.11.2.2.7.5.1.1.2
		ccSnmpTrapSinkV12DestinationIp OBJECT-TYPE
			SYNTAX IpAddress
			MAX-ACCESS read-write
			STATUS current
			DESCRIPTION
				"Destination IP of Trap Manager."
			::= { ccSnmpTrapSinkV12Entry 2 }

		
		-- 1.3.6.1.4.1.388.11.2.2.7.5.1.1.3
		ccSnmpTrapSinkV12Port OBJECT-TYPE
			SYNTAX Integer32
			MAX-ACCESS read-write
			STATUS current
			DESCRIPTION
				"Destination Port of Trap Manager."
			::= { ccSnmpTrapSinkV12Entry 3 }

		
		-- 1.3.6.1.4.1.388.11.2.2.7.5.1.1.4
		ccSnmpTrapSinkV12Community OBJECT-TYPE
			SYNTAX DisplayString
			MAX-ACCESS read-write
			STATUS current
			DESCRIPTION
				"Community Name."
			::= { ccSnmpTrapSinkV12Entry 4 }

		
		-- 1.3.6.1.4.1.388.11.2.2.7.5.1.1.5
		ccSnmpTrapSinkV12Version OBJECT-TYPE
			SYNTAX INTEGER
				{
				snmpV1(1),
				snmpV2(2)
				}
			MAX-ACCESS read-write
			STATUS current
			DESCRIPTION
				"SNMP protocol version."
			::= { ccSnmpTrapSinkV12Entry 5 }

		
		-- 1.3.6.1.4.1.388.11.2.2.7.5.1.1.6
		ccSnmpTrapSinkV12Enable OBJECT-TYPE
			SYNTAX AbbrevRowStatus
			MAX-ACCESS read-write
			STATUS current
			DESCRIPTION
				"Row Status."
			::= { ccSnmpTrapSinkV12Entry 6 }

		
		-- 1.3.6.1.4.1.388.11.2.2.7.5.2
		ccSnmpTrapSinkV3Table OBJECT-TYPE
			SYNTAX SEQUENCE OF CcSnmpTrapSinkV3Entry
			MAX-ACCESS not-accessible
			STATUS current
			DESCRIPTION
				"Table of SNMP v3 trap configuration entries."
			::= { ccSnmpTraps 2 }

		
		-- 1.3.6.1.4.1.388.11.2.2.7.5.2.1
		ccSnmpTrapSinkV3Entry OBJECT-TYPE
			SYNTAX CcSnmpTrapSinkV3Entry
			MAX-ACCESS not-accessible
			STATUS current
			DESCRIPTION
				"Description."
			INDEX { ccSnmpTrapSinkV3Index }
			::= { ccSnmpTrapSinkV3Table 1 }

		
		CcSnmpTrapSinkV3Entry ::=
			SEQUENCE { 
				ccSnmpTrapSinkV3Index
					Integer32,
				ccSnmpTrapSinkV3DestinationIp
					IpAddress,
				ccSnmpTrapSinkV3Port
					Integer32,
				ccSnmpTrapSinkV3Username
					DisplayString,
				ccSnmpTrapSinkV3SecurityLevel
					INTEGER,
				ccSnmpTrapSinkV3AuthAlgorithm
					INTEGER,
				ccSnmpTrapSinkV3AuthPassword
					Password,
				ccSnmpTrapSinkV3PrivacyAlgorithm
					INTEGER,
				ccSnmpTrapSinkV3PrivacyPassword
					Password,
				ccSnmpTrapSinkV3Enable
					AbbrevRowStatus
			 }

		-- 1.3.6.1.4.1.388.11.2.2.7.5.2.1.1
		ccSnmpTrapSinkV3Index OBJECT-TYPE
			SYNTAX Integer32 (1..20)
			MAX-ACCESS accessible-for-notify
			STATUS current
			DESCRIPTION
				"Simple Index."
			::= { ccSnmpTrapSinkV3Entry 1 }

		
		-- 1.3.6.1.4.1.388.11.2.2.7.5.2.1.2
		ccSnmpTrapSinkV3DestinationIp OBJECT-TYPE
			SYNTAX IpAddress
			MAX-ACCESS read-write
			STATUS current
			DESCRIPTION
				"Destination IP of Trap Manager."
			::= { ccSnmpTrapSinkV3Entry 2 }

		
		-- 1.3.6.1.4.1.388.11.2.2.7.5.2.1.3
		ccSnmpTrapSinkV3Port OBJECT-TYPE
			SYNTAX Integer32
			MAX-ACCESS read-write
			STATUS current
			DESCRIPTION
				"Destination Port of Trap Manager."
			::= { ccSnmpTrapSinkV3Entry 3 }

		
		-- 1.3.6.1.4.1.388.11.2.2.7.5.2.1.4
		ccSnmpTrapSinkV3Username OBJECT-TYPE
			SYNTAX DisplayString
			MAX-ACCESS read-write
			STATUS current
			DESCRIPTION
				"User name of SNMP v3 user."
			::= { ccSnmpTrapSinkV3Entry 4 }

		
		-- 1.3.6.1.4.1.388.11.2.2.7.5.2.1.5
		ccSnmpTrapSinkV3SecurityLevel OBJECT-TYPE
			SYNTAX INTEGER
				{
				auth(1),
				authNoPriv(2),
				authPriv(3)
				}
			MAX-ACCESS read-write
			STATUS current
			DESCRIPTION
				"Security Level."
			::= { ccSnmpTrapSinkV3Entry 5 }

		
		-- 1.3.6.1.4.1.388.11.2.2.7.5.2.1.6
		ccSnmpTrapSinkV3AuthAlgorithm OBJECT-TYPE
			SYNTAX INTEGER
				{
				md5(1),
				sha(2)
				}
			MAX-ACCESS read-write
			STATUS current
			DESCRIPTION
				"SNMP v3 Authentication Algorithm."
			::= { ccSnmpTrapSinkV3Entry 6 }

		
		-- 1.3.6.1.4.1.388.11.2.2.7.5.2.1.7
		ccSnmpTrapSinkV3AuthPassword OBJECT-TYPE
			SYNTAX Password (SIZE (8..31))
			MAX-ACCESS read-write
			STATUS current
			DESCRIPTION
				"SNMP v3 Authentication Password."
			::= { ccSnmpTrapSinkV3Entry 7 }

		
		-- 1.3.6.1.4.1.388.11.2.2.7.5.2.1.8
		ccSnmpTrapSinkV3PrivacyAlgorithm OBJECT-TYPE
			SYNTAX INTEGER
				{
				des(1),
				aes128(2)
				}
			MAX-ACCESS read-write
			STATUS current
			DESCRIPTION
				"SNMP v3 Privacy Algorithm."
			::= { ccSnmpTrapSinkV3Entry 8 }

		
		-- 1.3.6.1.4.1.388.11.2.2.7.5.2.1.9
		ccSnmpTrapSinkV3PrivacyPassword OBJECT-TYPE
			SYNTAX Password (SIZE (8..31))
			MAX-ACCESS read-write
			STATUS current
			DESCRIPTION
				"SNMP v3 Privacy Password."
			::= { ccSnmpTrapSinkV3Entry 9 }

		
		-- 1.3.6.1.4.1.388.11.2.2.7.5.2.1.10
		ccSnmpTrapSinkV3Enable OBJECT-TYPE
			SYNTAX AbbrevRowStatus
			MAX-ACCESS read-write
			STATUS current
			DESCRIPTION
				"Row Status."
			::= { ccSnmpTrapSinkV3Entry 10 }

		
		-- 1.3.6.1.4.1.388.11.2.2.8
		ccCompactFlash OBJECT IDENTIFIER ::= { ccAdmin 8 }

		
		-- 1.3.6.1.4.1.388.11.2.2.8.1
		ccCompactFlashCapacity OBJECT-TYPE
			SYNTAX Integer32
			MAX-ACCESS read-only
			STATUS current
			DESCRIPTION
				"Capacity of the Compact Flash card in Kbyte.
				"
			::= { ccCompactFlash 1 }
-- The capacity of the flash used in the WS2000 system
		
		-- 1.3.6.1.4.1.388.11.2.2.8.2
		ccCompactFlashUsed OBJECT-TYPE
			SYNTAX Integer32
			MAX-ACCESS read-only
			STATUS current
			DESCRIPTION
				"Number of Kbyte in use on the Compact Flash card."
			::= { ccCompactFlash 2 }
-- The amount of cosumed space in flash card.
		
-- For MUs, PORTALs, and WLANs, there are two tables (each), 
-- that describe the highest-level summary values.  (Those
-- 3*2 tables are found in their respective groups, not here
-- in this group).
-- 
-- Unlike the other various tables of statistics for MUs, 
-- PORTALs, and WLANs, (which are true counters - ever 
-- increasing since switch reboot), the values in these tables
-- are all rates/percentages as measured over a finite period 
-- of time, called here a 'window'.
-- 
-- There are two different 'windows': 'Short' and 'Long'.
-- The 'Short' window extends generally over seconds;  the 
-- 'Long' window generally extends over minutes.  (Both are
-- explicitly specified via scalars in this group).
-- 
-- Additionally, these windows are updated at an 
-- 'update interval' that is typically a fraction of the 
-- window time.  (Also specified via scalars in this group).
-- 
-- For example, (see scalars for actual values):
--       window  update-interval
-- Short  30sec   5sec
-- Long   60min   5min
-- 
-- Using the example values above, the 'Short' window shows 
-- average rates / percentages for the prior 30sec, and is
-- updated every 5sec.
-- 
-- These values are intended to match the same values reported
-- in the Web UI summary screens.
-- 
-- Descriptions of each data item are only provided in the
-- ccPortalSumStatsShortTable, (since it occurs first in the
-- MIB, and because unlike the corresponding MU tables, it
-- has the union of all possible columns).  For all other 
-- values, (ccMuSumStats_, ccPortalSumStatsLong and 
-- ccWlanSumStats_), refer to these descriptions.  
-- (Did this to avoid massive cut-and-paste which later 
-- leads to discrepencies when changes are made to the 
-- descriptions).
		-- 1.3.6.1.4.1.388.11.2.2.9
		ccSumStats OBJECT IDENTIFIER ::= { ccAdmin 9 }

		
		-- 1.3.6.1.4.1.388.11.2.2.9.1
		ccSumStatsShortWindow OBJECT-TYPE
			SYNTAX Integer32
			UNITS "seconds"
			MAX-ACCESS read-only
			STATUS current
			DESCRIPTION
				"The number of seconds backwards from the specified 
				timestamp that the the 'Short' window extends backwards in
				time."
			::= { ccSumStats 1 }

		
		-- 1.3.6.1.4.1.388.11.2.2.9.2
		ccSumStatsShortUpdateInterval OBJECT-TYPE
			SYNTAX Integer32
			UNITS "seconds"
			MAX-ACCESS read-only
			STATUS current
			DESCRIPTION
				"The frequency at which the 'Short' summary stats are 
				updated."
			::= { ccSumStats 2 }

		
		-- 1.3.6.1.4.1.388.11.2.2.9.3
		ccSumStatsLongWindow OBJECT-TYPE
			SYNTAX Integer32
			UNITS "minutes"
			MAX-ACCESS read-only
			STATUS current
			DESCRIPTION
				"Same as corresponding 'Short' value, for the 'Long' window."
			::= { ccSumStats 3 }

		
		-- 1.3.6.1.4.1.388.11.2.2.9.4
		ccSumStatsLongUpdateInterval OBJECT-TYPE
			SYNTAX Integer32
			UNITS "minutes"
			MAX-ACCESS read-only
			STATUS current
			DESCRIPTION
				"Same as corresponding 'Short' value, for the 'Long' window."
			::= { ccSumStats 4 }

		
-- MIB values to control network management access to the
-- switch.
		-- 1.3.6.1.4.1.388.11.2.2.10
		ccMgmtAccess OBJECT IDENTIFIER ::= { ccAdmin 10 }

		
		-- 1.3.6.1.4.1.388.11.2.2.10.1
		ccMgmtAccessToAllow OBJECT-TYPE
			SYNTAX BITS
				{
				fromLanAppletHttp(0),
				fromLanAppletHttps(1),
				fromLanCliTelnet(2),
				fromLanSsh(3),
				fromLanSnmp(4),
				fromWanAppletHttp(5),
				fromWanAppletHttps(6),
				fromWanCliTelnet(7),
				fromWanSsh(8),
				fromWanSnmp(9),
				fromWanFtp(10)
				}
			MAX-ACCESS read-write
			STATUS current
			DESCRIPTION
				"Types of network management access to permit."
			::= { ccMgmtAccess 1 }

		
		-- 1.3.6.1.4.1.388.11.2.2.10.2
		ccMgmtAccessAirbeam OBJECT IDENTIFIER ::= { ccMgmtAccess 2 }

		
		-- 1.3.6.1.4.1.388.11.2.2.10.2.1
		ccMgmtAccessAirbeamAllow OBJECT-TYPE
			SYNTAX TruthValue
			MAX-ACCESS read-write
			STATUS current
			DESCRIPTION
				"Allow Airbeam smart.
				
				(If enabled, Airbeam access is only allowed from the LAN
				interfaces)."
			::= { ccMgmtAccessAirbeam 1 }

		
		-- 1.3.6.1.4.1.388.11.2.2.10.2.2
		ccMgmtAccessAirbeamPassword OBJECT-TYPE
			SYNTAX Password
			MAX-ACCESS read-write
			STATUS current
			DESCRIPTION
				"Airbeam password.  (username is 'airbeam')."
			::= { ccMgmtAccessAirbeam 2 }

		
		-- 1.3.6.1.4.1.388.11.2.2.10.3
		ccMgmtAccessAdmin OBJECT IDENTIFIER ::= { ccMgmtAccess 3 }

		
		-- 1.3.6.1.4.1.388.11.2.2.10.3.1
		ccMgmtAccessAdminAuth OBJECT-TYPE
			SYNTAX INTEGER
				{
				local(1),
				radius(2)
				}
			MAX-ACCESS read-write
			STATUS current
			DESCRIPTION
				"The type of authentication used to authenticate the 
				administrator.It can be a local database or a radius server.
				
				"
			::= { ccMgmtAccessAdmin 1 }
-- T
		
		-- 1.3.6.1.4.1.388.11.2.2.10.3.2
		ccMgmtAccessAdminPassword OBJECT-TYPE
			SYNTAX Password (SIZE (1..11))
			MAX-ACCESS read-write
			STATUS current
			DESCRIPTION
				"Administrator password.
				
				Can only be read, (via GET), using a community string
				capable of writing, (via SET), the value.  If an otherwise
				valid community string is used, a string of length 0 is
				returned."
			::= { ccMgmtAccessAdmin 2 }

		
		-- 1.3.6.1.4.1.388.11.2.2.10.3.4
		ccMgmtAccessAdminAuthRadiusServerIp OBJECT-TYPE
			SYNTAX IpAddress
			MAX-ACCESS read-write
			STATUS current
			DESCRIPTION
				"The IP address of the radius server which is used to
				authenticate the administrator
				"
			::= { ccMgmtAccessAdmin 4 }
-- ??-CSM: can there be more than one?  if so, change to a table.
		
		-- 1.3.6.1.4.1.388.11.2.2.10.3.5
		ccMgmtAccessAdminAuthRadiusServerPort OBJECT-TYPE
			SYNTAX Unsigned32
			MAX-ACCESS read-write
			STATUS current
			DESCRIPTION
				"The port of the radius server which is used to
				authenticate the administrator"
			::= { ccMgmtAccessAdmin 5 }

		
		-- 1.3.6.1.4.1.388.11.2.2.10.3.6
		ccMgmtAccessAdminAuthRadiusSharedSecret OBJECT-TYPE
			SYNTAX Password
			MAX-ACCESS read-write
			STATUS current
			DESCRIPTION
				"The shared secret the radius server which is used to
				authenticate the administrator"
			::= { ccMgmtAccessAdmin 6 }

		
		-- 1.3.6.1.4.1.388.11.2.2.10.4
		ccMgmtAccessSsh OBJECT IDENTIFIER ::= { ccMgmtAccess 4 }

		
		-- 1.3.6.1.4.1.388.11.2.2.10.4.1
		ccMgmtAccessSshAuthTimeout OBJECT-TYPE
			SYNTAX Unsigned32
			MAX-ACCESS read-write
			STATUS current
			DESCRIPTION
				"The duration within which the user can enter the password
				after providing the user id."
			::= { ccMgmtAccessSsh 1 }

		
		-- 1.3.6.1.4.1.388.11.2.2.10.4.2
		ccMgmtAccessSshInactivityTimeout OBJECT-TYPE
			SYNTAX Unsigned32
			MAX-ACCESS read-write
			STATUS current
			DESCRIPTION
				"The duration within which the server should receive the 
				keep alive responses from the client.
				In SSH v2, the server shall timeout if does not receive 
				Keep alive responses from the client. "
			::= { ccMgmtAccessSsh 2 }

		
		-- 1.3.6.1.4.1.388.11.2.2.10.5
		ccMgmtAccessHttpsTimeout OBJECT-TYPE
			SYNTAX Unsigned32
			MAX-ACCESS read-write
			STATUS current
			DESCRIPTION
				"HTTP/HTTPS connection timeout."
			::= { ccMgmtAccess 5 }

		
-- Logging configuration.
		-- 1.3.6.1.4.1.388.11.2.2.11
		ccLogging OBJECT IDENTIFIER ::= { ccAdmin 11 }

		
		-- 1.3.6.1.4.1.388.11.2.2.11.1
		ccLoggingLevel OBJECT-TYPE
			SYNTAX INTEGER
				{
				level0Emergency(0),
				level1Alert(1),
				level2Critical(2),
				level3Errors(3),
				level4Warnings(4),
				level5Notice(5),
				level6Info(6),
				level7Debug(7)
				}
			MAX-ACCESS read-write
			STATUS current
			DESCRIPTION
				"Level of logging to perform."
			::= { ccLogging 1 }

		
		-- 1.3.6.1.4.1.388.11.2.2.11.2
		ccLoggingToSyslog OBJECT-TYPE
			SYNTAX TruthValue
			MAX-ACCESS read-write
			STATUS current
			DESCRIPTION
				"Send logs to external syslog."
			::= { ccLogging 2 }

		
		-- 1.3.6.1.4.1.388.11.2.2.11.3
		ccLoggingSyslogServer OBJECT-TYPE
			SYNTAX IpAddress
			MAX-ACCESS read-write
			STATUS current
			DESCRIPTION
				"IP addr of syslog server."
			::= { ccLogging 3 }

		
		-- 1.3.6.1.4.1.388.11.2.2.11.4
		ccLoggingDeleteCoreFile OBJECT-TYPE
			SYNTAX DoActionNow
			MAX-ACCESS read-write
			STATUS current
			DESCRIPTION
				"Delete the Core File."
			::= { ccLogging 4 }

		
		-- 1.3.6.1.4.1.388.11.2.2.11.5
		ccLoggingTransferCoreFile OBJECT-TYPE
			SYNTAX DoActionNow
			MAX-ACCESS read-write
			STATUS current
			DESCRIPTION
				"Transfer the core file to external FTP server."
			::= { ccLogging 5 }

		
-- Configure NTP on switch.
		-- 1.3.6.1.4.1.388.11.2.2.12
		ccNtp OBJECT IDENTIFIER ::= { ccAdmin 12 }

		
		-- 1.3.6.1.4.1.388.11.2.2.12.1
		ccNtpEnable OBJECT-TYPE
			SYNTAX TruthValue
			MAX-ACCESS read-write
			STATUS current
			DESCRIPTION
				"Enable NTP."
			::= { ccNtp 1 }

		
		-- 1.3.6.1.4.1.388.11.2.2.12.2
		ccNtp0Server OBJECT-TYPE
			SYNTAX IpAddress
			MAX-ACCESS read-write
			STATUS current
			DESCRIPTION
				"Preferred NTP server IPaddr."
			::= { ccNtp 2 }

		
		-- 1.3.6.1.4.1.388.11.2.2.12.3
		ccNtp0Port OBJECT-TYPE
			SYNTAX Integer32
			MAX-ACCESS read-write
			STATUS current
			DESCRIPTION
				"Preferred NTP server port number."
			::= { ccNtp 3 }

		
		-- 1.3.6.1.4.1.388.11.2.2.12.4
		ccNtp1Server OBJECT-TYPE
			SYNTAX IpAddress
			MAX-ACCESS read-write
			STATUS current
			DESCRIPTION
				"1st alternate NTP server IPaddr."
			::= { ccNtp 4 }

		
		-- 1.3.6.1.4.1.388.11.2.2.12.5
		ccNtp1Port OBJECT-TYPE
			SYNTAX Integer32
			MAX-ACCESS read-write
			STATUS current
			DESCRIPTION
				"1st alternate NTP server port number."
			::= { ccNtp 5 }

		
		-- 1.3.6.1.4.1.388.11.2.2.12.6
		ccNtp2Server OBJECT-TYPE
			SYNTAX IpAddress
			MAX-ACCESS read-write
			STATUS current
			DESCRIPTION
				"2nd alternate NTP server IPaddr."
			::= { ccNtp 6 }

		
		-- 1.3.6.1.4.1.388.11.2.2.12.7
		ccNtp2Port OBJECT-TYPE
			SYNTAX Integer32
			MAX-ACCESS read-write
			STATUS current
			DESCRIPTION
				"2nd alternate NTP server port number."
			::= { ccNtp 7 }

		
		-- 1.3.6.1.4.1.388.11.2.2.12.8
		ccNtpGmtHourOffset OBJECT-TYPE
			SYNTAX Integer32
			MAX-ACCESS read-only
			STATUS current
			DESCRIPTION
				"GMT Hour Offset.
				
				Not implemented in WS2000 2.0"
			::= { ccNtp 8 }

		
		-- 1.3.6.1.4.1.388.11.2.2.12.9
		ccNtpGmtMinuteOffset OBJECT-TYPE
			SYNTAX Integer32
			MAX-ACCESS read-only
			STATUS current
			DESCRIPTION
				"GMT Minute Offset.
				
				Not implemented in WS2000 2.0"
			::= { ccNtp 9 }

		
		-- 1.3.6.1.4.1.388.11.2.2.12.10
		ccNtpCurrentDateTime OBJECT-TYPE
			SYNTAX DateAndTime
			MAX-ACCESS read-only
			STATUS current
			DESCRIPTION
				"Current date/time.
				
				If NTP is not running, or has not yet synchronized the
				time, this value will be 0.
				"
			::= { ccNtp 10 }

		
		-- 1.3.6.1.4.1.388.11.2.2.12.11
		ccNtpSyncInterval OBJECT-TYPE
			SYNTAX Integer32
			MAX-ACCESS read-write
			STATUS current
			DESCRIPTION
				"Synchronization Interval (in minutes)"
			::= { ccNtp 11 }

		
		-- 1.3.6.1.4.1.388.11.2.2.14
		ccDhcpOptions OBJECT IDENTIFIER ::= { ccAdmin 14 }

		
		-- 1.3.6.1.4.1.388.11.2.2.14.1
		ccDhcpOptionsUpdateFwEna OBJECT-TYPE
			SYNTAX TruthValue
			MAX-ACCESS read-write
			STATUS current
			DESCRIPTION
				"Enable updating of firmware using DHCP vendor options
				"
			::= { ccDhcpOptions 1 }

		
		-- 1.3.6.1.4.1.388.11.2.2.14.2
		ccDhcpOptionsUpdateCfgEna OBJECT-TYPE
			SYNTAX TruthValue
			MAX-ACCESS read-write
			STATUS current
			DESCRIPTION
				"Enable updating of configuration using DHCP vendor options"
			::= { ccDhcpOptions 2 }

		
		-- 1.3.6.1.4.1.388.11.2.2.14.3
		ccDhcpOptionsUpdateInterface OBJECT-TYPE
			SYNTAX INTEGER
				{
				wan(1),
				subnet1(2),
				subnet2(3),
				subnet3(4),
				subnet4(5)
				}
			MAX-ACCESS read-write
			STATUS current
			DESCRIPTION
				"The interface to use in contacting the FTP or TFTP 
				server.  This is required since the actual firmware 
				load is accomplished via boot code that does not 
				contain routing logic."
			::= { ccDhcpOptions 3 }

		
		-- 1.3.6.1.4.1.388.11.2.2.14.4
		ccDhcpOptionsUpdateFwFilename OBJECT-TYPE
			SYNTAX DisplayString
			MAX-ACCESS read-only
			STATUS current
			DESCRIPTION
				"The firmware filename most recently provided
				via DHCP options.
				
				The success/failure of actually fetching that
				file via TFTP is reported in ccLoadFwSuccess
				and ccLoadFwResult.
				"
			::= { ccDhcpOptions 4 }

		
		-- 1.3.6.1.4.1.388.11.2.2.14.5
		ccDhcpOptionsUpdateCfgFilename OBJECT-TYPE
			SYNTAX DisplayString
			MAX-ACCESS read-only
			STATUS current
			DESCRIPTION
				"The config filename most recently provided
				via DHCP options.
				
				The success/failure of actually fetching that
				file via TFTP is reported in ccLoadCfgSuccess
				and ccLoadCfgResult.
				"
			::= { ccDhcpOptions 5 }

		
		-- 1.3.6.1.4.1.388.11.2.2.15
		ccRedundancy OBJECT IDENTIFIER ::= { ccAdmin 15 }

		
		-- 1.3.6.1.4.1.388.11.2.2.15.1
		ccRedundancyAdminState OBJECT-TYPE
			SYNTAX INTEGER
				{
				primary(1),
				standby(2)
				}
			MAX-ACCESS read-write
			STATUS current
			DESCRIPTION
				"The desired state of redundancy for this switch.
				
				'standAlone' is for a switch with no redundancy.
				
				'redundantPrimary' and 'redundantStandby' for 
				when the switch is desired to be part of a pair 
				of switches for redundancy.
				
				'redundantUpgrade' is used to update the firmware 
				of one switch of a pair configured for redundancy.
				This mode is just like 'standAlone' except that
				switch will not adopt portals.
				
				Note that when configuring two switches, both
				starting in 'standAlone' state, configure the
				primary first.  (If you configure the desired
				standby first, it will NOT hear heartbeats from
				the primary, and will quickly transition to 
				_OperState = 'redundantPrimary').
				"
			::= { ccRedundancy 1 }

		
		-- 1.3.6.1.4.1.388.11.2.2.15.2
		ccRedundancyOperState OBJECT-TYPE
			SYNTAX INTEGER
				{
				redundancy(1),
				upgrade(2),
				standAlone(3)
				}
			MAX-ACCESS read-write
			STATUS current
			DESCRIPTION
				"The actual state of redundancy for this switch."
			::= { ccRedundancy 2 }

		
		-- 1.3.6.1.4.1.388.11.2.2.15.3
		ccRedundancyHeartbeatInterface OBJECT-TYPE
			SYNTAX INTEGER
				{
				port1(1),
				port2(2),
				port3(3),
				port4(4),
				port5(5),
				port6(6)
				}
			MAX-ACCESS read-write
			STATUS current
			DESCRIPTION
				"The interface to use in contacting the FTP or TFTP 
				server.  This is required since the actual firmware 
				load is accomplished via boot code that does not 
				contain routing logic."
			::= { ccRedundancy 3 }

		
		-- 1.3.6.1.4.1.388.11.2.2.15.4
		ccRedundancyHeartbeatInterval OBJECT-TYPE
			SYNTAX Unsigned32
			UNITS "seconds"
			MAX-ACCESS read-write
			STATUS current
			DESCRIPTION
				"The duration in seconds between consecutive heartbeats. User can control the
				frequency of hearbeats by tuning this parameter."
			::= { ccRedundancy 4 }

		
		-- 1.3.6.1.4.1.388.11.2.2.15.5
		ccRedundancyRevertDelay OBJECT-TYPE
			SYNTAX Unsigned32
			UNITS "minutes"
			MAX-ACCESS read-write
			STATUS current
			DESCRIPTION
				"The duration which the master WS2000 shall wait before 
				taking over from a backup WS2000."
			::= { ccRedundancy 5 }

		
		-- 1.3.6.1.4.1.388.11.2.2.15.6
		ccRedundancyOperMode OBJECT-TYPE
			SYNTAX DisplayString
			MAX-ACCESS read-only
			STATUS current
			DESCRIPTION
				"Current Operational Mode of the switch."
			::= { ccRedundancy 6 }

		
		-- 1.3.6.1.4.1.388.11.2.2.16
		ccCertMgnt OBJECT IDENTIFIER ::= { ccAdmin 16 }

		
-- The ccSelfCerts group allows the admin to create a 
-- certificate request, send it off to a Certificate
-- Authority(CA) to be signed, and then import the signed 
-- certificate. 
-- 
-- The process can be broken down into the following steps:
-- 1. Create a row in the ccCertMgntSelfCertsReqTable.
-- 2. Fill out ccCertMgntSelfCertsReqKeyId and 
--    ccCertMgntSelfCertsReqSubject and any optional fields
-- 3. Set ccCertMgntSelfCertsReqGenReq to true
-- 4. Read certificate request from 
--    ccCertMgntSelfCertsReqCertReqStr
-- 5. Get the certificate signed by a CA
-- 6. Write the signed certificate string to 
--    ccCertMgntSelfCertsSignedStr
-- 7. Set ccCertMgntSelfCertsSignedImport to true and pull
--    for progress. This step will create a row in 
--    ccCertMgntSelfCertsSignedTable.
-- 
		-- 1.3.6.1.4.1.388.11.2.2.16.1
		ccCertMgntSelfCerts OBJECT IDENTIFIER ::= { ccCertMgnt 1 }

		
		-- 1.3.6.1.4.1.388.11.2.2.16.1.1
		ccCertMgntSelfCertsReqTable OBJECT-TYPE
			SYNTAX SEQUENCE OF CcCertMgntSelfCertsReqEntry
			MAX-ACCESS not-accessible
			STATUS current
			DESCRIPTION
				"This table allows the admin to create and store up to 
				three certificate signature requests.  The required 
				fields are ccSelfCertsReqKeyId and ccSelfCertReqSubject.
				
				"
			::= { ccCertMgntSelfCerts 1 }

		
		-- 1.3.6.1.4.1.388.11.2.2.16.1.1.1
		ccCertMgntSelfCertsReqEntry OBJECT-TYPE
			SYNTAX CcCertMgntSelfCertsReqEntry
			MAX-ACCESS not-accessible
			STATUS current
			DESCRIPTION
				" "
			INDEX { ccCertMgntSelfCertsReqIndex }
			::= { ccCertMgntSelfCertsReqTable 1 }

		
		CcCertMgntSelfCertsReqEntry ::=
			SEQUENCE { 
				ccCertMgntSelfCertsReqIndex
					Integer32,
				ccCertMgntSelfCertsReqKeyId
					DisplayString,
				ccCertMgntSelfCertsReqSubject
					DisplayString,
				ccCertMgntSelfCertsReqDept
					DisplayString,
				ccCertMgntSelfCertsReqOrg
					DisplayString,
				ccCertMgntSelfCertsReqCity
					DisplayString,
				ccCertMgntSelfCertsReqState
					DisplayString,
				ccCertMgntSelfCertsReqPostal
					DisplayString,
				ccCertMgntSelfCertsReqCountry
					DisplayString,
				ccCertMgntSelfCertsReqEmail
					DisplayString,
				ccCertMgntSelfCertsReqDomain
					DisplayString,
				ccCertMgntSelfCertsReqIp
					IpAddress,
				ccCertMgntSelfCertsReqSigAlgo
					INTEGER,
				ccCertMgntSelfCertsReqKeyLen
					INTEGER,
				ccCertMgntSelfCertsReqGenReq
					DoActionShowProgress,
				ccCertMgntSelfCertsReqCertReqStr
					DisplayString,
				ccCertMgntSelfCertsReqRowStatus
					AbbrevRowStatus
			 }

		-- 1.3.6.1.4.1.388.11.2.2.16.1.1.1.1
		ccCertMgntSelfCertsReqIndex OBJECT-TYPE
			SYNTAX Integer32 (1..3)
			MAX-ACCESS accessible-for-notify
			STATUS current
			DESCRIPTION
				"Simple index."
			::= { ccCertMgntSelfCertsReqEntry 1 }

		
		-- 1.3.6.1.4.1.388.11.2.2.16.1.1.1.2
		ccCertMgntSelfCertsReqKeyId OBJECT-TYPE
			SYNTAX DisplayString (SIZE (1..7))
			MAX-ACCESS read-write
			STATUS current
			DESCRIPTION
				"The ID for the certificate. Use this field to distinguish 
				between certificates. 
				
				This is a required field.
				"
			::= { ccCertMgntSelfCertsReqEntry 2 }

		
		-- 1.3.6.1.4.1.388.11.2.2.16.1.1.1.3
		ccCertMgntSelfCertsReqSubject OBJECT-TYPE
			SYNTAX DisplayString (SIZE (1..49))
			MAX-ACCESS read-write
			STATUS current
			DESCRIPTION
				"The subject of the certificate.  
				
				This is a required field.
				"
			::= { ccCertMgntSelfCertsReqEntry 3 }

		
		-- 1.3.6.1.4.1.388.11.2.2.16.1.1.1.4
		ccCertMgntSelfCertsReqDept OBJECT-TYPE
			SYNTAX DisplayString (SIZE (0..49))
			MAX-ACCESS read-write
			STATUS current
			DESCRIPTION
				"The department that is making the request.  
				
				Contact your CA to determine whether this field is required."
			::= { ccCertMgntSelfCertsReqEntry 4 }

		
		-- 1.3.6.1.4.1.388.11.2.2.16.1.1.1.5
		ccCertMgntSelfCertsReqOrg OBJECT-TYPE
			SYNTAX DisplayString (SIZE (0..49))
			MAX-ACCESS read-write
			STATUS current
			DESCRIPTION
				"The name of the organization or company that is making the 
				request.  
				
				Contact your CA to determine whether this field is required."
			::= { ccCertMgntSelfCertsReqEntry 5 }

		
		-- 1.3.6.1.4.1.388.11.2.2.16.1.1.1.6
		ccCertMgntSelfCertsReqCity OBJECT-TYPE
			SYNTAX DisplayString (SIZE (0..49))
			MAX-ACCESS read-write
			STATUS current
			DESCRIPTION
				"The name of the city where the organization resides. 
				
				Contact your CA to determine whether this field is required."
			::= { ccCertMgntSelfCertsReqEntry 6 }

		
		-- 1.3.6.1.4.1.388.11.2.2.16.1.1.1.7
		ccCertMgntSelfCertsReqState OBJECT-TYPE
			SYNTAX DisplayString (SIZE (0..49))
			MAX-ACCESS read-write
			STATUS current
			DESCRIPTION
				"The name of the state where the organzation resides.
				
				Contact your CA to determine whether this field is required."
			::= { ccCertMgntSelfCertsReqEntry 7 }

		
		-- 1.3.6.1.4.1.388.11.2.2.16.1.1.1.8
		ccCertMgntSelfCertsReqPostal OBJECT-TYPE
			SYNTAX DisplayString (SIZE (0..9))
			MAX-ACCESS read-write
			STATUS current
			DESCRIPTION
				"The postal code (zip code in US) for the organization.
				
				Contact your CA to determine whether this field is required."
			::= { ccCertMgntSelfCertsReqEntry 8 }

		
		-- 1.3.6.1.4.1.388.11.2.2.16.1.1.1.9
		ccCertMgntSelfCertsReqCountry OBJECT-TYPE
			SYNTAX DisplayString (SIZE (0..2))
			MAX-ACCESS read-write
			STATUS current
			DESCRIPTION
				"The two-letter ISO code for the country where the 
				organization resides. 
				
				Contact your CA to determine whether this field is required."
			::= { ccCertMgntSelfCertsReqEntry 9 }

		
		-- 1.3.6.1.4.1.388.11.2.2.16.1.1.1.10
		ccCertMgntSelfCertsReqEmail OBJECT-TYPE
			SYNTAX DisplayString (SIZE (0..49))
			MAX-ACCESS read-write
			STATUS current
			DESCRIPTION
				"The email address to be used for identification purposes. 
				
				Contact your CA to determine whether this field is required."
			::= { ccCertMgntSelfCertsReqEntry 10 }

		
		-- 1.3.6.1.4.1.388.11.2.2.16.1.1.1.11
		ccCertMgntSelfCertsReqDomain OBJECT-TYPE
			SYNTAX DisplayString (SIZE (0..49))
			MAX-ACCESS read-write
			STATUS current
			DESCRIPTION
				"The domain name to associate with the certificate. 
				
				Contact your CA to determine whether this field is required."
			::= { ccCertMgntSelfCertsReqEntry 11 }

		
		-- 1.3.6.1.4.1.388.11.2.2.16.1.1.1.12
		ccCertMgntSelfCertsReqIp OBJECT-TYPE
			SYNTAX IpAddress
			MAX-ACCESS read-write
			STATUS current
			DESCRIPTION
				"The WAN IP of the WS 2000 Wireless Switch.
				
				Contact your CA to determine whether this field is required."
			::= { ccCertMgntSelfCertsReqEntry 12 }

		
		-- 1.3.6.1.4.1.388.11.2.2.16.1.1.1.13
		ccCertMgntSelfCertsReqSigAlgo OBJECT-TYPE
			SYNTAX INTEGER
				{
				cryptoMd5Rsa(1),
				cryptoSha1Rsa(2)
				}
			MAX-ACCESS read-write
			STATUS current
			DESCRIPTION
				"The signature algorithm you want used for the certificate. 
				The options are:
				
				MD5-RSA: This option uses the Message Digest 5 algorithm in 
				         combination with RSA encryption.
				SHA1-RSA: This options uses the Secure Hash Algorithm 1 in 
				          combination with RSA encryption.
				
				This is a required field.
				
				"
			::= { ccCertMgntSelfCertsReqEntry 13 }

		
		-- 1.3.6.1.4.1.388.11.2.2.16.1.1.1.14
		ccCertMgntSelfCertsReqKeyLen OBJECT-TYPE
			SYNTAX INTEGER
				{
				keylen512(1),
				keylen1024(2),
				keylen2048(3)
				}
			MAX-ACCESS read-write
			STATUS current
			DESCRIPTION
				"The desired length of the key. Possible values are 512, 
				1024, and 2048. Select a lower number to enhance 
				performance. Select a large number to enhance security."
			::= { ccCertMgntSelfCertsReqEntry 14 }

		
		-- 1.3.6.1.4.1.388.11.2.2.16.1.1.1.15
		ccCertMgntSelfCertsReqGenReq OBJECT-TYPE
			SYNTAX DoActionShowProgress
			MAX-ACCESS read-write
			STATUS current
			DESCRIPTION
				"Start generating certificate request."
			::= { ccCertMgntSelfCertsReqEntry 15 }

		
		-- 1.3.6.1.4.1.388.11.2.2.16.1.1.1.16
		ccCertMgntSelfCertsReqCertReqStr OBJECT-TYPE
			SYNTAX DisplayString
			MAX-ACCESS read-only
			STATUS current
			DESCRIPTION
				"The generated certificate request string."
			::= { ccCertMgntSelfCertsReqEntry 16 }

		
		-- 1.3.6.1.4.1.388.11.2.2.16.1.1.1.17
		ccCertMgntSelfCertsReqRowStatus OBJECT-TYPE
			SYNTAX AbbrevRowStatus
			MAX-ACCESS read-write
			STATUS current
			DESCRIPTION
				"Row status."
			::= { ccCertMgntSelfCertsReqEntry 17 }

		
		-- 1.3.6.1.4.1.388.11.2.2.16.1.2
		ccCertMgntSelfCertsIdName OBJECT-TYPE
			SYNTAX DisplayString
			MAX-ACCESS read-write
			STATUS current
			DESCRIPTION
				"ID Name of the signed certificate."
			::= { ccCertMgntSelfCerts 2 }

		
		-- 1.3.6.1.4.1.388.11.2.2.16.1.3
		ccCertMgntSelfCertsSignedStr OBJECT-TYPE
			SYNTAX DisplayString
			MAX-ACCESS read-write
			STATUS current
			DESCRIPTION
				"The signed certificate."
			::= { ccCertMgntSelfCerts 3 }

		
		-- 1.3.6.1.4.1.388.11.2.2.16.1.4
		ccCertMgntSelfCertsSignedImport OBJECT-TYPE
			SYNTAX DoActionShowProgress
			MAX-ACCESS read-write
			STATUS current
			DESCRIPTION
				"Start importing the signed certificate from
				ccCertMgntSelfCertsSignedStr to a new row in 
				ccCertMgntSelfCertsSignedTable.  "
			::= { ccCertMgntSelfCerts 4 }

		
		-- 1.3.6.1.4.1.388.11.2.2.16.1.5
		ccCertMgntSelfCertsSignedTable OBJECT-TYPE
			SYNTAX SEQUENCE OF CcCertMgntSelfCertsSignedEntry
			MAX-ACCESS not-accessible
			STATUS current
			DESCRIPTION
				"This table allows the admin to store up to three signed 
				certificates. 
				
				This table supports a max size of three rows."
			::= { ccCertMgntSelfCerts 5 }

		
		-- 1.3.6.1.4.1.388.11.2.2.16.1.5.1
		ccCertMgntSelfCertsSignedEntry OBJECT-TYPE
			SYNTAX CcCertMgntSelfCertsSignedEntry
			MAX-ACCESS not-accessible
			STATUS current
			DESCRIPTION
				" "
			INDEX { ccCertMgntSelfCertsSignedIndex }
			::= { ccCertMgntSelfCertsSignedTable 1 }

		
		CcCertMgntSelfCertsSignedEntry ::=
			SEQUENCE { 
				ccCertMgntSelfCertsSignedIndex
					Integer32,
				ccCertMgntSelfCertsSignedKeyId
					DisplayString,
				ccCertMgntSelfCertsSignedIssuerName
					DisplayString,
				ccCertMgntSelfCertsSignedSubject
					DisplayString,
				ccCertMgntSelfCertsSignedSerialNumber
					DisplayString,
				ccCertMgntSelfCertsSignedExpiry
					DateAndTime,
				ccCertMgntSelfCertsSignedDeleteRow
					TruthValue
			 }

		-- 1.3.6.1.4.1.388.11.2.2.16.1.5.1.1
		ccCertMgntSelfCertsSignedIndex OBJECT-TYPE
			SYNTAX Integer32 (1..3)
			MAX-ACCESS accessible-for-notify
			STATUS current
			DESCRIPTION
				"Simple index."
			::= { ccCertMgntSelfCertsSignedEntry 1 }

		
		-- 1.3.6.1.4.1.388.11.2.2.16.1.5.1.2
		ccCertMgntSelfCertsSignedKeyId OBJECT-TYPE
			SYNTAX DisplayString (SIZE (1..7))
			MAX-ACCESS read-only
			STATUS current
			DESCRIPTION
				"The ID for the certificate. Use this field to distinguish 
				between certificates. "
			::= { ccCertMgntSelfCertsSignedEntry 2 }

		
		-- 1.3.6.1.4.1.388.11.2.2.16.1.5.1.3
		ccCertMgntSelfCertsSignedIssuerName OBJECT-TYPE
			SYNTAX DisplayString
			MAX-ACCESS read-only
			STATUS current
			DESCRIPTION
				"The name of the certificate authority who signed the 
				certificate."
			::= { ccCertMgntSelfCertsSignedEntry 3 }

		
		-- 1.3.6.1.4.1.388.11.2.2.16.1.5.1.4
		ccCertMgntSelfCertsSignedSubject OBJECT-TYPE
			SYNTAX DisplayString
			MAX-ACCESS read-only
			STATUS current
			DESCRIPTION
				"The subject of the certificate."
			::= { ccCertMgntSelfCertsSignedEntry 4 }

		
		-- 1.3.6.1.4.1.388.11.2.2.16.1.5.1.5
		ccCertMgntSelfCertsSignedSerialNumber OBJECT-TYPE
			SYNTAX DisplayString
			MAX-ACCESS read-only
			STATUS current
			DESCRIPTION
				"The serial number of the certificate."
			::= { ccCertMgntSelfCertsSignedEntry 5 }

		
		-- 1.3.6.1.4.1.388.11.2.2.16.1.5.1.6
		ccCertMgntSelfCertsSignedExpiry OBJECT-TYPE
			SYNTAX DateAndTime
			MAX-ACCESS read-only
			STATUS current
			DESCRIPTION
				"The date when the certificate expires."
			::= { ccCertMgntSelfCertsSignedEntry 6 }

		
		-- 1.3.6.1.4.1.388.11.2.2.16.1.5.1.7
		ccCertMgntSelfCertsSignedDeleteRow OBJECT-TYPE
			SYNTAX TruthValue
			MAX-ACCESS read-write
			STATUS current
			DESCRIPTION
				"Delete row."
			::= { ccCertMgntSelfCertsSignedEntry 7 }

		
-- The ccCACerts group allows the admin to import CA 
-- certificates.
-- 
-- The process can be broken down into the following steps:
-- 1. Write the certificate text to ccCACertsStr
-- 2. Set ccCACertsImport to true and pull for progress. This 
--    step will create a row in ccCACertsTable.
-- 
-- 
-- 
-- 
		-- 1.3.6.1.4.1.388.11.2.2.16.2
		ccCACerts OBJECT IDENTIFIER ::= { ccCertMgnt 2 }

		
		-- 1.3.6.1.4.1.388.11.2.2.16.2.1
		ccCACertsStr OBJECT-TYPE
			SYNTAX DisplayString
			MAX-ACCESS read-write
			STATUS current
			DESCRIPTION
				"The CA certificate to be imported."
			::= { ccCACerts 1 }

		
		-- 1.3.6.1.4.1.388.11.2.2.16.2.2
		ccCACertsImport OBJECT-TYPE
			SYNTAX DoActionShowProgress
			MAX-ACCESS read-write
			STATUS current
			DESCRIPTION
				"Start import operation for the CA certificate stored in
				ccCACertsStr.  This operation adds a row in ccCACertsTable."
			::= { ccCACerts 2 }

		
		-- 1.3.6.1.4.1.388.11.2.2.16.2.3
		ccCACertsTable OBJECT-TYPE
			SYNTAX SEQUENCE OF CcCACertsEntry
			MAX-ACCESS not-accessible
			STATUS current
			DESCRIPTION
				"This table allows the admin to store up to three CA
				certificates. 
				
				This table supports a max size of three rows."
			::= { ccCACerts 3 }

		
		-- 1.3.6.1.4.1.388.11.2.2.16.2.3.1
		ccCACertsEntry OBJECT-TYPE
			SYNTAX CcCACertsEntry
			MAX-ACCESS not-accessible
			STATUS current
			DESCRIPTION
				" "
			INDEX { ccCACertsIndex }
			::= { ccCACertsTable 1 }

		
		CcCACertsEntry ::=
			SEQUENCE { 
				ccCACertsIndex
					Integer32,
				ccCACertsKeyId
					DisplayString,
				ccCACertsIssuerName
					DisplayString,
				ccCACertsSubject
					DisplayString,
				ccCACertsSerialNumber
					DisplayString,
				ccCACertsExpiry
					DateAndTime,
				ccCACertsDeleteRow
					TruthValue
			 }

		-- 1.3.6.1.4.1.388.11.2.2.16.2.3.1.1
		ccCACertsIndex OBJECT-TYPE
			SYNTAX Integer32 (1..3)
			MAX-ACCESS accessible-for-notify
			STATUS current
			DESCRIPTION
				"Simple index."
			::= { ccCACertsEntry 1 }

		
		-- 1.3.6.1.4.1.388.11.2.2.16.2.3.1.2
		ccCACertsKeyId OBJECT-TYPE
			SYNTAX DisplayString (SIZE (1..7))
			MAX-ACCESS read-only
			STATUS current
			DESCRIPTION
				"The ID for the certificate. Use this field to distinguish 
				between certificates. "
			::= { ccCACertsEntry 2 }

		
		-- 1.3.6.1.4.1.388.11.2.2.16.2.3.1.3
		ccCACertsIssuerName OBJECT-TYPE
			SYNTAX DisplayString
			MAX-ACCESS read-only
			STATUS current
			DESCRIPTION
				"The name of the certificate authority."
			::= { ccCACertsEntry 3 }

		
		-- 1.3.6.1.4.1.388.11.2.2.16.2.3.1.4
		ccCACertsSubject OBJECT-TYPE
			SYNTAX DisplayString
			MAX-ACCESS read-only
			STATUS current
			DESCRIPTION
				"The subject of the certificate."
			::= { ccCACertsEntry 4 }

		
		-- 1.3.6.1.4.1.388.11.2.2.16.2.3.1.5
		ccCACertsSerialNumber OBJECT-TYPE
			SYNTAX DisplayString
			MAX-ACCESS read-only
			STATUS current
			DESCRIPTION
				"The serial number of the certificate."
			::= { ccCACertsEntry 5 }

		
		-- 1.3.6.1.4.1.388.11.2.2.16.2.3.1.6
		ccCACertsExpiry OBJECT-TYPE
			SYNTAX DateAndTime
			MAX-ACCESS read-only
			STATUS current
			DESCRIPTION
				"The date when the certificate expires."
			::= { ccCACertsEntry 6 }

		
		-- 1.3.6.1.4.1.388.11.2.2.16.2.3.1.7
		ccCACertsDeleteRow OBJECT-TYPE
			SYNTAX TruthValue
			MAX-ACCESS read-write
			STATUS current
			DESCRIPTION
				"Delete Row."
			::= { ccCACertsEntry 7 }

		
-- Notifications implemented on the switch.
-- 
-- For each notification, a 'pseudo printf' is shown to 
-- illustrate how the var-binds sent with the notification
-- make for an informative notification message.  
-- 
-- The notation '%s1' is used to denote the first [optional]
-- var-bind in the notification.  '%i1' is used to denote the
-- instance of the first [optional] var-bind in the 
-- notification.
		-- 1.3.6.1.4.1.388.11.2.3
		ccNotifications OBJECT IDENTIFIER ::= { ws2k 3 }

		
		-- 1.3.6.1.4.1.388.11.2.3.1
		ccPortalAdopted NOTIFICATION-TYPE
			OBJECTS { ccPortalLastMac }
			STATUS current
			DESCRIPTION 
				"A Portal has been adopted by the switch.
				
				Example:
				Portal MAC=%s1 has been adopted."
			::= { ccNotifications 1 }

		
		-- 1.3.6.1.4.1.388.11.2.3.2
		ccPortalUnAdopted NOTIFICATION-TYPE
			OBJECTS { ccPortalLastMac, ccPortalLastReason }
			STATUS current
			DESCRIPTION 
				"A Portal has been un-adopted by the switch.
				
				Example:
				Portal MAC=%s1 has been UN-adopted for reason %s2."
			::= { ccNotifications 2 }

		
		-- 1.3.6.1.4.1.388.11.2.3.3
		ccPortalDenied NOTIFICATION-TYPE
			OBJECTS { ccPortalLastMac, ccPortalLastReason }
			STATUS current
			DESCRIPTION 
				"A Portal has been denied adoption by the switch.
				
				Example:
				Portal MAC=%s1 has been denied adopted for reason %s2."
			::= { ccNotifications 3 }

		
		-- 1.3.6.1.4.1.388.11.2.3.4
		ccMuAssociated NOTIFICATION-TYPE
			OBJECTS { ccMuLastMac, ccMuLastPortal }
			STATUS current
			DESCRIPTION 
				"An MU has been associated to a Portal adopted 
				by this switch.
				
				Example:
				MU MAC=%s1 has associated to Portal MAC=%s2."
			::= { ccNotifications 4 }

		
		-- 1.3.6.1.4.1.388.11.2.3.5
		ccMuUnAssociated NOTIFICATION-TYPE
			OBJECTS { ccMuLastMac, ccMuLastPortal, ccMuLastReason }
			STATUS current
			DESCRIPTION 
				"An MU has been un-associated to a Portal adopted 
				by this switch.
				
				Example:
				MU MAC=%s1 has UN-associated from Portal MAC=%s2 for
				reason %s3."
			::= { ccNotifications 5 }

		
		-- 1.3.6.1.4.1.388.11.2.3.6
		ccMuDenied NOTIFICATION-TYPE
			OBJECTS { ccMuLastMac, ccMuLastPortal, ccMuLastReason }
			STATUS current
			DESCRIPTION 
				"An MU has been denied association to a Portal 
				adopted by this switch.
				
				Example:
				MU MAC=%s1 has been denied association to Portal MAC=%s2
				for reason %s3."
			::= { ccNotifications 6 }

		
		-- 1.3.6.1.4.1.388.11.2.3.7
		ccConfigChange NOTIFICATION-TYPE
			OBJECTS { ccCfgHistChangeTime, ccCfgHistChangeCount }
			STATUS current
			DESCRIPTION 
				"The configuration of this switch has changed.
				
				Example:
				The configuration of the switch changed as of 
				sysUpTime=%s1;  the total number of config changes
				since reboot is now %s2."
			::= { ccNotifications 7 }

		
		-- 1.3.6.1.4.1.388.11.2.3.8
		ccSnmpAclViolation NOTIFICATION-TYPE
			OBJECTS { ccSnmpLastDeniedIpAddr, ccSnmpAclViolations }
			STATUS current
			DESCRIPTION 
				"An attempt to communicate via SNMP to the switch
				has been denied based on configured ACLs.
				
				Example:
				IP-addr %s1 has attempted, but been prohibited, from 
				communicating with the switch via SNMP;  total number
				of such ACL violations = %s2."
			::= { ccNotifications 8 }

		
		-- 1.3.6.1.4.1.388.11.2.3.9
		ccPortStatusChange NOTIFICATION-TYPE
			OBJECTS { ccPortStatus }
			STATUS current
			DESCRIPTION 
				"A [physical] port's state has changed from up-->down, or
				down-->up.
				
				Example:
				Port %i1 has changed state to %s1."
			::= { ccNotifications 9 }

		
		-- 1.3.6.1.4.1.388.11.2.3.10
		ccCfAlmostFull NOTIFICATION-TYPE
			OBJECTS { ccCompactFlashCapacity, ccCompactFlashUsed, ccTrapCtrlCfAlmostFullThreshold }
			STATUS current
			DESCRIPTION 
				"The compact flash is almost full;  (it has crossed the
				threshold defined by ccTrapCtrlCfAlmostFullThreshold).
				
				Example:
				The compact flash is almost full;
				Used=%s1, Capacity=%s2, Threshold=%s3."
			::= { ccNotifications 10 }

		
		-- 1.3.6.1.4.1.388.11.2.3.11
		ccFirewallUnderAttack NOTIFICATION-TYPE
			OBJECTS { ccTrapCtrlFirewallUnderAttackDescription }
			STATUS current
			DESCRIPTION 
				"The firewall has detected an attack in progress.
				
				Example:
				The WAN firewall is being attached by method %s1."
			::= { ccNotifications 11 }

		
		-- 1.3.6.1.4.1.388.11.2.3.12
		ccRadarDetected NOTIFICATION-TYPE
			OBJECTS { ccTrapCtrlRadarDetectedPortalMac, ccTrapCtrlRadarDetectedChannel }
			STATUS current
			DESCRIPTION 
				"Radar has been detected on a Portal channel.
				
				Example:
				Radar has been detected on Portal MAC=%s1, on channel %s2."
			::= { ccNotifications 12 }

		
-- ??-TW/CM: add 1 UINT32 to show the current/live value for
-- the variable that this trap is saying crossed a threshold.
-- Fortunately, UINT32 works for every single SumStat data
-- item, (even Signal and Noise, which for traps are reported
-- and configured as POSITIVE values not negative).
-- 
-- Also, add 3-9 more on top of that to show the recent 
-- history?  If so, beware: the threshold trap is calculated
-- on the SHORT items, but is it calculated on 5sec interval,
-- or on a 30sec interval.  If the former, can show the less
-- fresh 5sec-by-5sec values.  If the latter, showing those
-- values might look bad - see this example:
-- 
-- threshold=15
-- Tnow T-minus-5sec T-10 T-15 T-20 T-25 T-30
--  17       13       14   17    14  13   11
-- 
-- This shows that the value peaked above the threshold 15sec
-- earlier, but it was not 'caught'.  Worse yet, that may
-- bring to the customer's attention that in some cases it is
-- quite possible that such a peak between 30sec threshold
-- checks might be entirely missed.
-- 
-- If trap thresholds are only checked every 30sec, the 
-- 'history' values reported, (if any), should probably be
-- the 10min LONG sub-buckets.
-- 
-- Ideally, (if performance permits), the threshold trap
-- checking should occur at the 5sec interval, and the history
-- values reported are the SHORT sub-buckets, PLUS the LONG
-- sub-buckets.
-- 
-- Decided 5/20 to wait to see how Tina's implementation 
-- works-out and then maybe add the 1 current value and/or
-- several history values.
-- 
-- This comment applies equally to the Portal, WLAN, and 
-- switch ccSumStats_ traps.
		-- 1.3.6.1.4.1.388.11.2.3.13
		ccSumStatsMu NOTIFICATION-TYPE
			OBJECTS { ccTrapCtrlSumStatsDescr, ccTrapCtrlSumStatsThresholdMu, ccTrapCtrlSumStatsUnits, ccMuMac, ccMuIpAddr
				 }
			STATUS current
			DESCRIPTION 
				"A summary statistic has crossed the prescribed threshold 
				by an MU.
				
				Example:
				Threshold '%s1' of value %s2 (units:%s3) has been crossed
				by MU MAC=%s4 with IP-addr=%s5."
			::= { ccNotifications 13 }

		
		-- 1.3.6.1.4.1.388.11.2.3.14
		ccSumStatsPortal NOTIFICATION-TYPE
			OBJECTS { ccTrapCtrlSumStatsIndex, ccTrapCtrlSumStatsThresholdPortals, ccTrapCtrlSumStatsUnits, ccPortalIndex, ccPortalMac, 
				ccPortalName, ccPortalLocation }
			STATUS current
			DESCRIPTION 
				"A summary statistic has crossed the prescribed threshold 
				by a Portal.
				
				Example:
				Threshold #%s1 of value %s2 (units:%s3) has been crossed
				by Portal index=%s4 with MAC=%s5."
			::= { ccNotifications 14 }

		
		-- 1.3.6.1.4.1.388.11.2.3.15
		ccSumStatsWlan NOTIFICATION-TYPE
			OBJECTS { ccTrapCtrlSumStatsDescr, ccTrapCtrlSumStatsThresholdWlans, ccTrapCtrlSumStatsUnits, ccWlanIndex, ccWlanName, 
				ccWlanEssid }
			STATUS current
			DESCRIPTION 
				"A summary statistic has crossed the prescribed threshold 
				by a WLAN.
				
				Example:
				Threshold #%s1 of value %s2 (units:%s3) has been crossed
				by WLAN index=%s4 with name=%s5."
			::= { ccNotifications 15 }

		
		-- 1.3.6.1.4.1.388.11.2.3.16
		ccSumStatsSwitch NOTIFICATION-TYPE
			OBJECTS { ccTrapCtrlSumStatsDescr, ccTrapCtrlSumStatsThresholdSwitch, ccTrapCtrlSumStatsUnits }
			STATUS current
			DESCRIPTION 
				"A summary statistic has crossed the prescribed threshold 
				by the entire Switch.
				
				Example:
				Threshold %s1 of value %s2 (units:%s3) has been crossed
				by the entire switch."
			::= { ccNotifications 16 }

		
		-- 1.3.6.1.4.1.388.11.2.3.17
		ccLanVlanActivated NOTIFICATION-TYPE
			OBJECTS { ccTrapCtrlLanVlanActivatedVlanId }
			STATUS current
			DESCRIPTION 
				"A Vlan is activated. When ever a MU is associated with
				the switch, and it receives a VLAN attribute from the 
				radius server, the specified VLAN is activated.
				"
			::= { ccNotifications 17 }

		
		-- 1.3.6.1.4.1.388.11.2.3.18
		ccDhcpOptionsFileTransferStatus NOTIFICATION-TYPE
			OBJECTS { ccTrapCtrlDhcpOptionsFileTransferStatusRequested, ccLoadFwServerFilename, ccLoadFwSuccess, ccLoadFwResult, ccLoadCfgServerFilename, 
				ccLoadCfgSuccess, ccLoadCfgResult }
			STATUS current
			DESCRIPTION 
				"Trap to say that the device received DHCP
				options instructing it to load a new fw or
				cnfg file, and that it has completed the
				transfer.  The varbinds tell if the transfer
				was successful.
				
				Note that this trap will NOT be issued if the
				DHCP options specify the same file as was
				most recently loaded.
				
				Example:
				(if FW bit set in _Requested):
				The switch was instructed to load firmware %s2,
				and success=%s3 with result=%s4.
				
				(if CFG bit set in _Requested):
				The switch was instructed to load config %s5,
				and success=%s6 with result=%s7.
				"
			::= { ccNotifications 18 }

		
		-- 1.3.6.1.4.1.388.11.2.3.19
		ccRedundancyStateChange NOTIFICATION-TYPE
			OBJECTS { ccRedundancyOperState, ccTrapCtrlRedundancyPreviousOperState }
			STATUS current
			DESCRIPTION 
				"The state of this switch's ccRedundancyOperState
				has changed.
				
				Example:
				The switch has changed it's redundancy state to %s1.
				"
			::= { ccNotifications 19 }

		
-- !!- OID: .1000 - to save room above for notifications.
		-- 1.3.6.1.4.1.388.11.2.3.1000
		ccTrapCtrl OBJECT IDENTIFIER ::= { ccNotifications 1000 }

		
		-- 1.3.6.1.4.1.388.11.2.3.1000.1
		ccTrapCtrlEnableTable OBJECT-TYPE
			SYNTAX SEQUENCE OF CcTrapCtrlEnableEntry
			MAX-ACCESS not-accessible
			STATUS current
			DESCRIPTION
				"Table of Trap Enable entries."
			::= { ccTrapCtrl 1 }

		
		-- 1.3.6.1.4.1.388.11.2.3.1000.1.1
		ccTrapCtrlEnableEntry OBJECT-TYPE
			SYNTAX CcTrapCtrlEnableEntry
			MAX-ACCESS not-accessible
			STATUS current
			DESCRIPTION
				"Description."
			INDEX { ccTrapCtrlEnableIndex }
			::= { ccTrapCtrlEnableTable 1 }

		
		CcTrapCtrlEnableEntry ::=
			SEQUENCE { 
				ccTrapCtrlEnableIndex
					INTEGER,
				ccTrapCtrlEnableName
					DisplayString,
				ccTrapCtrlEnable
					TruthValue
			 }

		-- 1.3.6.1.4.1.388.11.2.3.1000.1.1.1
		ccTrapCtrlEnableIndex OBJECT-TYPE
			SYNTAX INTEGER
				{
				trapCtrlPortalAdopted(1),
				trapCtrlPortalUnAdopted(2),
				trapCtrlPortalDeniedAdoption(3),
				trapCtrlMuAssociated(4),
				trapCtrlMuUnAssociated(5),
				trapCtrlMuDeniedAssociation(6),
				trapCtrlSnmpAuthFailure(7),
				trapCtrlSnmpAclViolation(8),
				trapCtrlSnmpColdStart(9),
				trapCtrlSnmpConfigChanged(10),
				trapCtrlCfAlmostFull(11),
				trapCtrlPortStatusChange(12),
				trapCtrlDenialofService(13),
				trapCtrlMuAuthDenied(14),
				trapCtrlRadarDetected(15),
				trapCtrlRogueApDetected(16)
				}
			MAX-ACCESS accessible-for-notify
			STATUS current
			DESCRIPTION
				"Simple Index."
			::= { ccTrapCtrlEnableEntry 1 }
-- ??-India: add the other 18 enum values.
		
		-- 1.3.6.1.4.1.388.11.2.3.1000.1.1.2
		ccTrapCtrlEnableName OBJECT-TYPE
			SYNTAX DisplayString
			MAX-ACCESS read-only
			STATUS current
			DESCRIPTION
				"Name of the Trap."
			::= { ccTrapCtrlEnableEntry 2 }

		
		-- 1.3.6.1.4.1.388.11.2.3.1000.1.1.3
		ccTrapCtrlEnable OBJECT-TYPE
			SYNTAX TruthValue
			MAX-ACCESS read-write
			STATUS current
			DESCRIPTION
				"Enable/Disbale a particular Trap."
			::= { ccTrapCtrlEnableEntry 3 }

		
		-- 1.3.6.1.4.1.388.11.2.3.1000.2
		ccTrapCtrlDetails OBJECT IDENTIFIER ::= { ccTrapCtrl 2 }

		
		-- 1.3.6.1.4.1.388.11.2.3.1000.2.1
		ccTrapCtrlPortalAdopted OBJECT-IDENTITY
			STATUS current
			DESCRIPTION 
				"(place-holder for future use and to keep the last OID of
				each ccTrapCtrl_ item here to match the last OID of the
				corresponding notification)."
			::= { ccTrapCtrlDetails 1 }

		
		-- 1.3.6.1.4.1.388.11.2.3.1000.2.2
		ccTrapCtrlPortalUnAdopted OBJECT-IDENTITY
			STATUS current
			DESCRIPTION 
				"(place-holder for future use and to keep the last OID of
				each ccTrapCtrl_ item here to match the last OID of the
				corresponding notification)."
			::= { ccTrapCtrlDetails 2 }

		
		-- 1.3.6.1.4.1.388.11.2.3.1000.2.3
		ccTrapCtrlPortalDenied OBJECT-IDENTITY
			STATUS current
			DESCRIPTION 
				"(place-holder for future use and to keep the last OID of
				each ccTrapCtrl_ item here to match the last OID of the
				corresponding notification)."
			::= { ccTrapCtrlDetails 3 }

		
		-- 1.3.6.1.4.1.388.11.2.3.1000.2.4
		ccTrapCtrlMuAssociated OBJECT-IDENTITY
			STATUS current
			DESCRIPTION 
				"(place-holder for future use and to keep the last OID of
				each ccTrapCtrl_ item here to match the last OID of the
				corresponding notification)."
			::= { ccTrapCtrlDetails 4 }

		
		-- 1.3.6.1.4.1.388.11.2.3.1000.2.5
		ccTrapCtrlMuUnAssociated OBJECT-IDENTITY
			STATUS current
			DESCRIPTION 
				"(place-holder for future use and to keep the last OID of
				each ccTrapCtrl_ item here to match the last OID of the
				corresponding notification)."
			::= { ccTrapCtrlDetails 5 }

		
		-- 1.3.6.1.4.1.388.11.2.3.1000.2.6
		ccTrapCtrlMuDenied OBJECT-IDENTITY
			STATUS current
			DESCRIPTION 
				"(place-holder for future use and to keep the last OID of
				each ccTrapCtrl_ item here to match the last OID of the
				corresponding notification)."
			::= { ccTrapCtrlDetails 6 }

		
		-- 1.3.6.1.4.1.388.11.2.3.1000.2.7
		ccTrapCtrlConfigChange OBJECT-IDENTITY
			STATUS current
			DESCRIPTION 
				"(place-holder for future use and to keep the last OID of
				each ccTrapCtrl_ item here to match the last OID of the
				corresponding notification)."
			::= { ccTrapCtrlDetails 7 }

		
		-- 1.3.6.1.4.1.388.11.2.3.1000.2.8
		ccTrapCtrlSnmpAclViolation OBJECT-IDENTITY
			STATUS current
			DESCRIPTION 
				"(place-holder for future use and to keep the last OID of
				each ccTrapCtrl_ item here to match the last OID of the
				corresponding notification)."
			::= { ccTrapCtrlDetails 8 }

		
		-- 1.3.6.1.4.1.388.11.2.3.1000.2.9
		ccTrapCtrlPortStatusChange OBJECT-IDENTITY
			STATUS current
			DESCRIPTION 
				"(place-holder for future use and to keep the last OID of
				each ccTrapCtrl_ item here to match the last OID of the
				corresponding notification)."
			::= { ccTrapCtrlDetails 9 }

		
		-- 1.3.6.1.4.1.388.11.2.3.1000.2.10
		ccTrapCtrlCfAlmostFull OBJECT IDENTIFIER ::= { ccTrapCtrlDetails 10 }

		
		-- 1.3.6.1.4.1.388.11.2.3.1000.2.10.1
		ccTrapCtrlCfAlmostFullThreshold OBJECT-TYPE
			SYNTAX Unsigned32
			MAX-ACCESS read-write
			STATUS current
			DESCRIPTION
				"A ccCfAlmostFull trap will be sent when less than this 
				number of bytes are remained on the Compact Flash card.
								
				The trap is currently scheduled to fire every 5 minutes 
				when the condition is met. 
				"
			::= { ccTrapCtrlCfAlmostFull 1 }

		
		-- 1.3.6.1.4.1.388.11.2.3.1000.2.11
		ccTrapCtrlFirewallUnderAttack OBJECT IDENTIFIER ::= { ccTrapCtrlDetails 11 }

		
		-- 1.3.6.1.4.1.388.11.2.3.1000.2.11.1
		ccTrapCtrlFirewallUnderAttackDescription OBJECT-TYPE
			SYNTAX OCTET STRING (SIZE (0..255))
			MAX-ACCESS accessible-for-notify
			STATUS current
			DESCRIPTION
				"Description of Firewall Under Attack."
			::= { ccTrapCtrlFirewallUnderAttack 1 }

		
		-- 1.3.6.1.4.1.388.11.2.3.1000.2.11.2
		ccTrapCtrlFirewallUnderAttackRateLimit OBJECT-TYPE
			SYNTAX Unsigned32
			UNITS "seconds"
			MAX-ACCESS read-write
			STATUS current
			DESCRIPTION
				"The max rate at which ccFirewallUnderAttack
				traps/notifications will be sent from the switch.
				
				If the switch detects a FirewallUnderAttack condition and
				it has NOT been at least this many seconds since the
				last ccFirewallUnderAttack trap/notification, this current
				event will NOT result in a trap/notification.
				
				If this value is set to 0, every such event results in a
				trap/notification.
				
				Factory-default state is 1 [second].
				"
			::= { ccTrapCtrlFirewallUnderAttack 2 }

		
		-- 1.3.6.1.4.1.388.11.2.3.1000.2.12
		ccTrapCtrlRadarDetected OBJECT IDENTIFIER ::= { ccTrapCtrlDetails 12 }

		
		-- 1.3.6.1.4.1.388.11.2.3.1000.2.12.1
		ccTrapCtrlRadarDetectedPortalMac OBJECT-TYPE
			SYNTAX PhysAddress
			MAX-ACCESS accessible-for-notify
			STATUS current
			DESCRIPTION
				"MAC address of the Portal that has detected Radar.
				(Note that this variable is accessible-for-notify only)."
			::= { ccTrapCtrlRadarDetected 1 }

		
		-- 1.3.6.1.4.1.388.11.2.3.1000.2.12.2
		ccTrapCtrlRadarDetectedChannel OBJECT-TYPE
			SYNTAX Unsigned32
			MAX-ACCESS accessible-for-notify
			STATUS current
			DESCRIPTION
				"Channel on which Radar has been detected.
				(Note that this variable is accessible-for-notify only)."
			::= { ccTrapCtrlRadarDetected 2 }

		
		-- 1.3.6.1.4.1.388.11.2.3.1000.2.13
		ccTrapCtrlSumStats OBJECT IDENTIFIER ::= { ccTrapCtrlDetails 13 }

		
		-- 1.3.6.1.4.1.388.11.2.3.1000.2.13.1
		ccTrapCtrlSumStatsTable OBJECT-TYPE
			SYNTAX SEQUENCE OF CcTrapCtrlSumStatsEntry
			MAX-ACCESS not-accessible
			STATUS current
			DESCRIPTION
				"This table configures thresholds that can be monitored for
				- all MUs      and/or 
				- all Portals  and/or 
				- all WLANs    and/or 
				- for the entire switch
				
				When a given threshold is crossed, it generates the 
				appropriate corresponding notification, (ccSumStats_:
				_MU, _Portal, _WLAN, or _Switch).
				
				Some thresholds result in notifications when exceeded, and
				some when the current value sinks below the threshold.  
				This is indicated by the wording of the entry in
				the entry's _Descr value.
				
				In all cases, the summary stat being monitored is the Short
				value, never the Long value.
				
				Note that for thresholds of type thresholdsAvgMuSignal & 
				thresholdsAvgMuNoise, the values being 'watched' are 
				actually negative.  In these cases the threshold is 
				specified as a Unsigned32.  For example, if you wish to
				trap on Signal being worse than -75dBm, enter '70'.  This
				works since a user would never want to trap on a threshold
				of Sinal worse than +10dBm.  (SNR is not an issue, since
				that is a positive value).
				
				Any values reported as var-binds in the resultant trap(s)
				are likewise reported as positive values."
			::= { ccTrapCtrlSumStats 1 }

		
		-- 1.3.6.1.4.1.388.11.2.3.1000.2.13.1.1
		ccTrapCtrlSumStatsEntry OBJECT-TYPE
			SYNTAX CcTrapCtrlSumStatsEntry
			MAX-ACCESS not-accessible
			STATUS current
			DESCRIPTION
				"The rows/instances in this table occur at the exact same
				indices as the corresponding monitored data occurs in the
				_SumStats tables.
				
				For example, row #2 / instance .2 represents the
				threshold(s) for the _PktsPerSec values for MU, Portal,
				WLAN, and Switch.
				
				If a given threshold does not make sense for one of those
				4 entities, its corresponding TruthValue will be false."
			INDEX { ccTrapCtrlSumStatsIndex }
			::= { ccTrapCtrlSumStatsTable 1 }

		
		CcTrapCtrlSumStatsEntry ::=
			SEQUENCE { 
				ccTrapCtrlSumStatsIndex
					INTEGER,
				ccTrapCtrlSumStatsDescr
					DisplayString,
				ccTrapCtrlSumStatsUnits
					DisplayString,
				ccTrapCtrlSumStatsCanBeSetMu
					TruthValue,
				ccTrapCtrlSumStatsThresholdMu
					Unsigned32,
				ccTrapCtrlSumStatsCanBeSetPortal
					TruthValue,
				ccTrapCtrlSumStatsThresholdPortals
					Unsigned32,
				ccTrapCtrlSumStatsCanBeSetWlan
					TruthValue,
				ccTrapCtrlSumStatsThresholdWlans
					Unsigned32,
				ccTrapCtrlSumStatsCanBeSetSwitch
					TruthValue,
				ccTrapCtrlSumStatsThresholdSwitch
					Unsigned32
			 }

		-- 1.3.6.1.4.1.388.11.2.3.1000.2.13.1.1.1
		ccTrapCtrlSumStatsIndex OBJECT-TYPE
			SYNTAX INTEGER
				{
				unusedTimestamp(1),
				unusedNumPkts(2),
				thresholdsPktsPerSec(3),
				unusedPktsPerSecTx(4),
				unusedPktsPerSecRx(5),
				thresholdsThroughput(6),
				unusedThroughputTx(7),
				unusedThroughputRx(8),
				thresholdsAvgBitSpeed(9),
				thresholdsAvgMuSignal(10),
				thresholdsAvgMuNoise(11),
				thresholdsAvgMuSnr(12),
				thresholdsPctNUcastPkts(13),
				thresholdsPpmTxWithRetires(14),
				thresholdsPpmTxDropped(15),
				thresholdsTxAvgRetries(16),
				thresholdsPpmRxUndecrypt(17),
				thresholdsTotalMus(18),
				thresholdsPctRfUtil(19),
				thresholdsPctDropped(20)
				}
			MAX-ACCESS accessible-for-notify
			STATUS current
			DESCRIPTION
				"Index into table.  Note that specific thresholds occur at
				specific instance values as denoted by the enumeration
				values assigned to this variable."
			::= { ccTrapCtrlSumStatsEntry 1 }

		
		-- 1.3.6.1.4.1.388.11.2.3.1000.2.13.1.1.2
		ccTrapCtrlSumStatsDescr OBJECT-TYPE
			SYNTAX DisplayString
			MAX-ACCESS read-only
			STATUS current
			DESCRIPTION
				"Description of the threshold."
			::= { ccTrapCtrlSumStatsEntry 2 }

		
		-- 1.3.6.1.4.1.388.11.2.3.1000.2.13.1.1.3
		ccTrapCtrlSumStatsUnits OBJECT-TYPE
			SYNTAX DisplayString
			MAX-ACCESS read-only
			STATUS current
			DESCRIPTION
				"Units of the the threshold."
			::= { ccTrapCtrlSumStatsEntry 3 }

		
		-- 1.3.6.1.4.1.388.11.2.3.1000.2.13.1.1.4
		ccTrapCtrlSumStatsCanBeSetMu OBJECT-TYPE
			SYNTAX TruthValue
			MAX-ACCESS read-only
			STATUS current
			DESCRIPTION
				"If true, the threshold can be set for MUs.
				If false, attempting the threshold will return a READ-ONLY."
			::= { ccTrapCtrlSumStatsEntry 4 }

		
		-- 1.3.6.1.4.1.388.11.2.3.1000.2.13.1.1.5
		ccTrapCtrlSumStatsThresholdMu OBJECT-TYPE
			SYNTAX Unsigned32
			MAX-ACCESS read-write
			STATUS current
			DESCRIPTION
				"The threshold for all MUs.
				If 0, no threshold checking is performed."
			::= { ccTrapCtrlSumStatsEntry 5 }

		
		-- 1.3.6.1.4.1.388.11.2.3.1000.2.13.1.1.6
		ccTrapCtrlSumStatsCanBeSetPortal OBJECT-TYPE
			SYNTAX TruthValue
			MAX-ACCESS read-only
			STATUS current
			DESCRIPTION
				"If true, the threshold can be set for Portals.
				If false, attempting the threshold will return a READ-ONLY."
			::= { ccTrapCtrlSumStatsEntry 6 }

		
		-- 1.3.6.1.4.1.388.11.2.3.1000.2.13.1.1.7
		ccTrapCtrlSumStatsThresholdPortals OBJECT-TYPE
			SYNTAX Unsigned32
			MAX-ACCESS read-write
			STATUS current
			DESCRIPTION
				"The threshold for all Portals.  
				If 0, no threshold checking is performed."
			::= { ccTrapCtrlSumStatsEntry 7 }

		
		-- 1.3.6.1.4.1.388.11.2.3.1000.2.13.1.1.8
		ccTrapCtrlSumStatsCanBeSetWlan OBJECT-TYPE
			SYNTAX TruthValue
			MAX-ACCESS read-only
			STATUS current
			DESCRIPTION
				"If true, the threshold can be set for Wlans.
				If false, attempting the threshold will return a READ-ONLY."
			::= { ccTrapCtrlSumStatsEntry 8 }

		
		-- 1.3.6.1.4.1.388.11.2.3.1000.2.13.1.1.9
		ccTrapCtrlSumStatsThresholdWlans OBJECT-TYPE
			SYNTAX Unsigned32
			MAX-ACCESS read-write
			STATUS current
			DESCRIPTION
				"The threshold for all Wlans.  
				If 0, no threshold checking is performed."
			::= { ccTrapCtrlSumStatsEntry 9 }

		
		-- 1.3.6.1.4.1.388.11.2.3.1000.2.13.1.1.10
		ccTrapCtrlSumStatsCanBeSetSwitch OBJECT-TYPE
			SYNTAX TruthValue
			MAX-ACCESS read-only
			STATUS current
			DESCRIPTION
				"If true, the threshold can be set for the entire switch.
				If false, attempting the threshold will return a READ-ONLY."
			::= { ccTrapCtrlSumStatsEntry 10 }

		
		-- 1.3.6.1.4.1.388.11.2.3.1000.2.13.1.1.11
		ccTrapCtrlSumStatsThresholdSwitch OBJECT-TYPE
			SYNTAX Unsigned32
			MAX-ACCESS read-write
			STATUS current
			DESCRIPTION
				"The threshold for the entire Switch.  
				If 0, no threshold checking is performed."
			::= { ccTrapCtrlSumStatsEntry 11 }

		
		-- 1.3.6.1.4.1.388.11.2.3.1000.2.13.2
		ccTrapCtrlSumStatsMinPktsForTrap OBJECT-TYPE
			SYNTAX Unsigned32
			MAX-ACCESS read-write
			STATUS current
			DESCRIPTION
				"The minimum number of packets that must be in a
				window/dataset before any of the threshold traps 
				will 'fire'."
			::= { ccTrapCtrlSumStats 2 }

		
		-- 1.3.6.1.4.1.388.11.2.3.1000.2.14
		ccTrapCtrlSumStatsPortal OBJECT-IDENTITY
			STATUS current
			DESCRIPTION 
				"(place-holder for future use and to keep the last OID of
				each ccTrapCtrl_ item here to match the last OID of the
				corresponding notification)."
			::= { ccTrapCtrlDetails 14 }

		
		-- 1.3.6.1.4.1.388.11.2.3.1000.2.15
		ccTrapCtrlSumStatsWlan OBJECT-IDENTITY
			STATUS current
			DESCRIPTION 
				"(place-holder for future use and to keep the last OID of
				each ccTrapCtrl_ item here to match the last OID of the
				corresponding notification)."
			::= { ccTrapCtrlDetails 15 }

		
		-- 1.3.6.1.4.1.388.11.2.3.1000.2.16
		ccTrapCtrlSumStatsSwitch OBJECT-IDENTITY
			STATUS current
			DESCRIPTION 
				"(place-holder for future use and to keep the last OID of
				each ccTrapCtrl_ item here to match the last OID of the
				corresponding notification)."
			::= { ccTrapCtrlDetails 16 }

		
		-- 1.3.6.1.4.1.388.11.2.3.1000.2.17
		ccTrapCtrlLanVlanActivated OBJECT IDENTIFIER ::= { ccTrapCtrlDetails 17 }

		
		-- 1.3.6.1.4.1.388.11.2.3.1000.2.17.1
		ccTrapCtrlLanVlanActivatedVlanId OBJECT-TYPE
			SYNTAX Unsigned32 (1..31)
			MAX-ACCESS accessible-for-notify
			STATUS current
			DESCRIPTION
				"VLAN ID to which MU has been associated.
				(Note that this variable is accessible-for-notify only)."
			::= { ccTrapCtrlLanVlanActivated 1 }

		
		-- 1.3.6.1.4.1.388.11.2.3.1000.2.18
		ccTrapCtrlDhcpOptionsFileTransferStatus OBJECT IDENTIFIER ::= { ccTrapCtrlDetails 18 }

		
		-- 1.3.6.1.4.1.388.11.2.3.1000.2.18.1
		ccTrapCtrlDhcpOptionsFileTransferStatusRequested OBJECT-TYPE
			SYNTAX BITS
				{
				dhcpRequestedFwLoad(0),
				dhcpRequestedCfgLoad(1)
				}
			MAX-ACCESS accessible-for-notify
			STATUS current
			DESCRIPTION
				"DHCP request received.
				(Note that this variable is accessible-for-notify only)."
			::= { ccTrapCtrlDhcpOptionsFileTransferStatus 1 }

		
		-- 1.3.6.1.4.1.388.11.2.3.1000.2.19
		ccTrapCtrlRedundancyStateChange OBJECT IDENTIFIER ::= { ccTrapCtrlDetails 19 }

		
		-- 1.3.6.1.4.1.388.11.2.3.1000.2.19.1
		ccTrapCtrlRedundancyPreviousOperState OBJECT-TYPE
			SYNTAX INTEGER
				{
				standAlone(1),
				redundantPrimary(2),
				redundantStandby(3),
				redundantUpgrade(4)
				}
			MAX-ACCESS accessible-for-notify
			STATUS current
			DESCRIPTION
				"The actual state of redundancy for this switch."
			::= { ccTrapCtrlRedundancyStateChange 1 }

		
-- Values for the radio (RF) side of the switch.
		-- 1.3.6.1.4.1.388.11.2.4
		ccRf OBJECT IDENTIFIER ::= { ws2k 4 }

		
-- This group contains MIB values that describe the
-- Access Ports known to this WS2000.
		-- 1.3.6.1.4.1.388.11.2.4.1
		ccAp OBJECT IDENTIFIER ::= { ccRf 1 }

		
		-- 1.3.6.1.4.1.388.11.2.4.1.1
		ccApTable OBJECT-TYPE
			SYNTAX SEQUENCE OF CcApEntry
			MAX-ACCESS not-accessible
			STATUS current
			DESCRIPTION
				"This table lists all Access Ports that contain
				at least one Portal that has been adopted by this
				WS2000."
			::= { ccAp 1 }

		
		-- 1.3.6.1.4.1.388.11.2.4.1.1.1
		ccApEntry OBJECT-TYPE
			SYNTAX CcApEntry
			MAX-ACCESS not-accessible
			STATUS current
			DESCRIPTION
				" "
			INDEX { ccApIndex }
			::= { ccApTable 1 }

		
		CcApEntry ::=
			SEQUENCE { 
				ccApIndex
					INTEGER,
				ccApNicMac
					PhysAddress,
				ccApModelNumber
					DisplayString,
				ccApSerialNumber
					DisplayString,
				ccApPcbRevision
					DisplayString,
				ccApBootLoaderRev
					DisplayString,
				ccApWispVersion
					DisplayString,
				ccApRuntimeFwVersion
					DisplayString,
				ccApNumPortals
					Unsigned32,
				ccApPointersToPortals
					MultiPointer255
			 }

		-- 1.3.6.1.4.1.388.11.2.4.1.1.1.1
		ccApIndex OBJECT-TYPE
			SYNTAX INTEGER (1..255)
			MAX-ACCESS accessible-for-notify
			STATUS current
			DESCRIPTION
				"Small, arbitrary integer index."
			::= { ccApEntry 1 }

		
		-- 1.3.6.1.4.1.388.11.2.4.1.1.1.2
		ccApNicMac OBJECT-TYPE
			SYNTAX PhysAddress
			MAX-ACCESS read-only
			STATUS current
			DESCRIPTION
				"MAC address of this Access Port."
			::= { ccApEntry 2 }

		
		-- 1.3.6.1.4.1.388.11.2.4.1.1.1.3
		ccApModelNumber OBJECT-TYPE
			SYNTAX DisplayString
			MAX-ACCESS read-only
			STATUS current
			DESCRIPTION
				"Model number of the Access Port."
			::= { ccApEntry 3 }

		
		-- 1.3.6.1.4.1.388.11.2.4.1.1.1.4
		ccApSerialNumber OBJECT-TYPE
			SYNTAX DisplayString
			MAX-ACCESS read-only
			STATUS current
			DESCRIPTION
				"Serial Number of this Access Port."
			::= { ccApEntry 4 }

		
		-- 1.3.6.1.4.1.388.11.2.4.1.1.1.5
		ccApPcbRevision OBJECT-TYPE
			SYNTAX DisplayString
			MAX-ACCESS read-only
			STATUS current
			DESCRIPTION
				"Revision of the printed circuit board for this
				Access Port."
			::= { ccApEntry 5 }

		
		-- 1.3.6.1.4.1.388.11.2.4.1.1.1.6
		ccApBootLoaderRev OBJECT-TYPE
			SYNTAX DisplayString
			MAX-ACCESS read-only
			STATUS current
			DESCRIPTION
				"Revision of the boot loader code in this Access
				Port."
			::= { ccApEntry 6 }

		
		-- 1.3.6.1.4.1.388.11.2.4.1.1.1.7
		ccApWispVersion OBJECT-TYPE
			SYNTAX DisplayString
			MAX-ACCESS read-only
			STATUS current
			DESCRIPTION
				"Version of the WISP (AP-switch) protocol
				implemented by this Access Port."
			::= { ccApEntry 7 }

		
		-- 1.3.6.1.4.1.388.11.2.4.1.1.1.8
		ccApRuntimeFwVersion OBJECT-TYPE
			SYNTAX DisplayString
			MAX-ACCESS read-only
			STATUS current
			DESCRIPTION
				"Version of run-time code on this Access Port."
			::= { ccApEntry 8 }

		
-- ??-CM: this should be Uint32 - would chaning this be an
-- incompatible change?  Any diff on wire Int32 vs Unit32 ?
		-- 1.3.6.1.4.1.388.11.2.4.1.1.1.9
		ccApNumPortals OBJECT-TYPE
			SYNTAX Unsigned32
			MAX-ACCESS read-only
			STATUS current
			DESCRIPTION
				"The number of Portals implemented on this
				Access Port."
			::= { ccApEntry 9 }

		
		-- 1.3.6.1.4.1.388.11.2.4.1.1.1.10
		ccApPointersToPortals OBJECT-TYPE
			SYNTAX MultiPointer255
			MAX-ACCESS read-only
			STATUS current
			DESCRIPTION
				"If bit <n> of this value is set, this ApTable
				entry 'points' to entry <n> in the Portal Table.
				
				Such a reference conveys that the Portal entry
				pointed-to represents a Portal contained in the 
				Access Port represented by this entry.
				
				Note that since one Access Port can implement 1,
				2, (and in the future possibly more), Portals,
				this 'pointer' field had to be a bit-mask."
			::= { ccApEntry 10 }

		
-- This group contains MIB values that describe the
-- Portals known to and adopted by this WS2000.
-- 
-- An Access Port will contain 1, 2, (and in the 
-- future, possibly more), 'Portals'.  Such Portals
-- may be thought of as the radio portion of an
-- Access Port.
-- 
-- Descriptions of each data item are only provided here in 
-- the Portal tables, (since it occurs first in the MIB).
-- For the nearly identical values in the MU and WLAN tables,
-- refer back to the descriptions found here.  (Did this to 
-- avoid massive cut-and-paste which later leads to 
-- discrepencies and inconsistencies when changes are 
-- incorrectly made to the descriptions in one location but 
-- not the others).
		-- 1.3.6.1.4.1.388.11.2.4.2
		ccPortal OBJECT IDENTIFIER ::= { ccRf 2 }

		
		-- 1.3.6.1.4.1.388.11.2.4.2.1
		ccPortalTable OBJECT-TYPE
			SYNTAX SEQUENCE OF CcPortalEntry
			MAX-ACCESS not-accessible
			STATUS current
			DESCRIPTION
				"This table lists all Portals that have been
				adopted or have failed adoption (by this WS2000)."
			::= { ccPortal 1 }

		
		-- 1.3.6.1.4.1.388.11.2.4.2.1.1
		ccPortalEntry OBJECT-TYPE
			SYNTAX CcPortalEntry
			MAX-ACCESS not-accessible
			STATUS current
			DESCRIPTION
				" "
			INDEX { ccPortalIndex }
			::= { ccPortalTable 1 }

		
		CcPortalEntry ::=
			SEQUENCE { 
				ccPortalIndex
					INTEGER,
				ccPortalPointerToAp
					SinglePointer,
				ccPortalPointersToWlans
					MultiPointer63,
				ccPortalName
					DisplayString,
				ccPortalLocation
					DisplayString,
				ccPortalOptions
					BITS,
				ccPortalMac
					PhysAddress,
				ccPortalNumberOfEss
					Integer32,
				ccPortalNumberOfBss
					Integer32,
				ccPortalAssociatedMus
					Integer32,
				ccPortalRadioType
					RadioType,
				ccPortalChannel
					INTEGER,
				ccPortalTxPowerLevel
					Integer32,
				ccPortalLastAdoption
					TimeTicks,
				ccPortalState
					INTEGER,
				ccPortalBackgroundNoiseNumSamples
					Counter32,
				ccPortalBackgroundNoiseBest
					Integer32,
				ccPortalBackgroundNoiseWorst
					Integer32,
				ccPortalBackgroundNoiseSum
					Integer32,
				ccPortalBackgroundNoiseSumSquares
					Counter64
			 }

		-- 1.3.6.1.4.1.388.11.2.4.2.1.1.1
		ccPortalIndex OBJECT-TYPE
			SYNTAX INTEGER (1..255)
			MAX-ACCESS accessible-for-notify
			STATUS current
			DESCRIPTION
				"Small, arbitrary integer index."
			::= { ccPortalEntry 1 }

		
		-- 1.3.6.1.4.1.388.11.2.4.2.1.1.2
		ccPortalPointerToAp OBJECT-TYPE
			SYNTAX SinglePointer
			MAX-ACCESS read-only
			STATUS current
			DESCRIPTION
				"This value is the index in the ApTable for the 
				entry representing the Access Port that contains
				this Portal.
				
				Since each Portal has one and only one Access Port
				as 'parent', this value is a simple integer, not a
				bit-mask."
			::= { ccPortalEntry 2 }

		
		-- 1.3.6.1.4.1.388.11.2.4.2.1.1.3
		ccPortalPointersToWlans OBJECT-TYPE
			SYNTAX MultiPointer63
			MAX-ACCESS read-only
			STATUS current
			DESCRIPTION
				"(Reserved for future implementation)."
			::= { ccPortalEntry 3 }

		
		-- 1.3.6.1.4.1.388.11.2.4.2.1.1.4
		ccPortalName OBJECT-TYPE
			SYNTAX DisplayString
			MAX-ACCESS read-only
			STATUS current
			DESCRIPTION
				"Name of this Portal, as assigned by the Web UI 
				or CLI."
			::= { ccPortalEntry 4 }

		
		-- 1.3.6.1.4.1.388.11.2.4.2.1.1.5
		ccPortalLocation OBJECT-TYPE
			SYNTAX DisplayString
			MAX-ACCESS read-only
			STATUS current
			DESCRIPTION
				"Location string for this Portal, as assigned by
				the Web UI or CLI."
			::= { ccPortalEntry 5 }

		
		-- 1.3.6.1.4.1.388.11.2.4.2.1.1.6
		ccPortalOptions OBJECT-TYPE
			SYNTAX BITS
				{
				undefined00(0),
				undefined01(1),
				undefined02(2),
				undefined03(3),
				undefined04(4),
				undefined05(5),
				undefined06(6),
				undefined07(7),
				undefined08(8),
				undefined09(9),
				undefined10(10),
				undefined11(11),
				externalSecondaryAntInstalled(12),
				internalSecondaryAntInstalled(13),
				externalPrimaryAntInstalled(14),
				internalPrimaryAntInstalled(15)
				}
			MAX-ACCESS read-only
			STATUS current
			DESCRIPTION
				"This value describes the presence/absence of 
				internal and/or external primary and/or secondary
				antennas."
			::= { ccPortalEntry 6 }

		
		-- 1.3.6.1.4.1.388.11.2.4.2.1.1.7
		ccPortalMac OBJECT-TYPE
			SYNTAX PhysAddress
			MAX-ACCESS read-only
			STATUS current
			DESCRIPTION
				"MAC address of the Portal."
			::= { ccPortalEntry 7 }

		
-- ??-CM: this should be Uint32 - would chaning this be an
-- incompatible change?  Any diff on wire Int32 vs Unit32 ?
		-- 1.3.6.1.4.1.388.11.2.4.2.1.1.8
		ccPortalNumberOfEss OBJECT-TYPE
			SYNTAX Integer32
			MAX-ACCESS read-only
			STATUS current
			DESCRIPTION
				"The number of ESSs implemented by this Portal."
			::= { ccPortalEntry 8 }

		
-- ??-CM: this should be Uint32 - would chaning this be an
-- incompatible change?  Any diff on wire Int32 vs Unit32 ?
		-- 1.3.6.1.4.1.388.11.2.4.2.1.1.9
		ccPortalNumberOfBss OBJECT-TYPE
			SYNTAX Integer32
			MAX-ACCESS read-only
			STATUS current
			DESCRIPTION
				"The number of BSSs implemented by this Portal."
			::= { ccPortalEntry 9 }

		
-- ??-CM: this should be Uint32 - would chaning this be an
-- incompatible change?  Any diff on wire Int32 vs Unit32 ?
		-- 1.3.6.1.4.1.388.11.2.4.2.1.1.10
		ccPortalAssociatedMus OBJECT-TYPE
			SYNTAX Integer32
			MAX-ACCESS read-only
			STATUS current
			DESCRIPTION
				"The number of MUs currently associated to this
				Portal."
			::= { ccPortalEntry 10 }

		
		-- 1.3.6.1.4.1.388.11.2.4.2.1.1.11
		ccPortalRadioType OBJECT-TYPE
			SYNTAX RadioType
			MAX-ACCESS read-only
			STATUS current
			DESCRIPTION
				"Radio type of the Portal."
			::= { ccPortalEntry 11 }

		
-- ??-CM: this should be Uint32 - would chaning this be an
-- incompatible change?  Any diff on wire Int32 vs Unit32 ?
		-- 1.3.6.1.4.1.388.11.2.4.2.1.1.12
		ccPortalChannel OBJECT-TYPE
			SYNTAX INTEGER
				{
				ieee802dot11bChannel01(1),
				ieee802dot11bChannel02(2),
				ieee802dot11bChannel03(3),
				ieee802dot11bChannel04(4),
				ieee802dot11bChannel05(5),
				ieee802dot11bChannel06(6),
				ieee802dot11bChannel07(7),
				ieee802dot11bChannel08(8),
				ieee802dot11bChannel09(9),
				ieee802dot11bChannel10(10),
				ieee802dot11bChannel11(11),
				ieee802dot11bChannel12(12),
				ieee802dot11bChannel13(13),
				ieee802dot11bChannel14(14),
				ieee802dot11aChannel036(36),
				ieee802dot11aChannel040(40),
				ieee802dot11aChannel044(44),
				ieee802dot11aChannel048(48),
				ieee802dot11aChannel052(52),
				ieee802dot11aChannel056(56),
				ieee802dot11aChannel060(60),
				ieee802dot11aChannel064(64),
				ieee802dot11aChannel149(149),
				ieee802dot11aChannel153(153),
				ieee802dot11aChannel157(157),
				ieee802dot11aChannel161(161)
				}
			MAX-ACCESS read-only
			STATUS current
			DESCRIPTION
				"The value describes the channel the Portal is
				currently operating on.
				"
			::= { ccPortalEntry 12 }

		
-- ??-CM: this should be Uint32 - would chaning this be an
-- incompatible change?  Any diff on wire Int32 vs Unit32 ?
		-- 1.3.6.1.4.1.388.11.2.4.2.1.1.13
		ccPortalTxPowerLevel OBJECT-TYPE
			SYNTAX Integer32 (0..255)
			UNITS "milli-Watts"
			MAX-ACCESS read-only
			STATUS current
			DESCRIPTION
				"Output power level for the Portal.
				"
			::= { ccPortalEntry 13 }

		
		-- 1.3.6.1.4.1.388.11.2.4.2.1.1.14
		ccPortalLastAdoption OBJECT-TYPE
			SYNTAX TimeTicks
			MAX-ACCESS read-only
			STATUS current
			DESCRIPTION
				"A snapshot of the WS2000's sysUpTime when this
				Portal was last adopted."
			::= { ccPortalEntry 14 }

		
		-- 1.3.6.1.4.1.388.11.2.4.2.1.1.15
		ccPortalState OBJECT-TYPE
			SYNTAX INTEGER
				{
				portalUpAndWaitingForConfig(1),
				portalReceivingConfig(2),
				portalUpAndAdopted(3),
				portalDeniedAdoptionDueToAcl(4),
				portalBroken(5)
				}
			MAX-ACCESS read-only
			STATUS current
			DESCRIPTION
				"This value describes the state of the Portal.
				
				A healthy Portal would power-on, and quickly advance from
				  portalUpAndWaitingForConfig and then on to
				  portalReceivingConfig and then on to
				  portalUpAndAdopted.
				
				A Portal that is denied adoption due to ACLs would show:
				  portalDeniedAdoptionDueToAcl.
				
				A Portal that does not 'handshake' with the switch properly
				would be found in state:
				  portalBroken."
			::= { ccPortalEntry 15 }

		
		-- 1.3.6.1.4.1.388.11.2.4.2.1.1.16
		ccPortalBackgroundNoiseNumSamples OBJECT-TYPE
			SYNTAX Counter32
			MAX-ACCESS read-only
			STATUS current
			DESCRIPTION
				"Total packets received via the Portal included in
				all the other counters reported in this row."
			::= { ccPortalEntry 16 }

		
		-- 1.3.6.1.4.1.388.11.2.4.2.1.1.17
		ccPortalBackgroundNoiseBest OBJECT-TYPE
			SYNTAX Integer32
			UNITS "dBm"
			MAX-ACCESS read-only
			STATUS current
			DESCRIPTION
				"The best Signal value seen from the Portal so far.
				(Remember that a -20dBm Signal is better than -60dBm).
				
				This value is initialized to 500dBm.
				"
			::= { ccPortalEntry 17 }

		
		-- 1.3.6.1.4.1.388.11.2.4.2.1.1.18
		ccPortalBackgroundNoiseWorst OBJECT-TYPE
			SYNTAX Integer32
			UNITS "dBm"
			MAX-ACCESS read-only
			STATUS current
			DESCRIPTION
				"The worst Signal value seen from the Portal so far.
				(Remember that a -80dBm Signal is worse than -60dBm).
				
				This value is initialized to -500dBm.
				"
			::= { ccPortalEntry 18 }

		
		-- 1.3.6.1.4.1.388.11.2.4.2.1.1.19
		ccPortalBackgroundNoiseSum OBJECT-TYPE
			SYNTAX Integer32
			UNITS "dBm"
			MAX-ACCESS read-only
			STATUS current
			DESCRIPTION
				"A running sum of all Signal values calculated by the
				switch (using reported RSSI values), for packets 
				received via this Portal.
				
				Note that this value is normally a negative value
				ranging from -10dBm to -80dBm.  It is possible for this
				value to be positive, but that would be rare, and would
				signal an exceptionally strong signal.
				
				(This value divided by ccPortalRxRssiNumPkts yields
				the average Signal value for all packets received
				from this Portal)."
			::= { ccPortalEntry 19 }

		
		-- 1.3.6.1.4.1.388.11.2.4.2.1.1.20
		ccPortalBackgroundNoiseSumSquares OBJECT-TYPE
			SYNTAX Counter64
			UNITS "dBm"
			MAX-ACCESS read-only
			STATUS current
			DESCRIPTION
				"A sum of the squares of each Signal value calculated
				for packets received via this Portal.
				
				Unlike _SignalSum, this value is never negative, since
				the square of a negative number is a positive.
				
				(This value can be used to calculate the standard
				deviation for Signal values calculated for packets
				from this Portal)."
			::= { ccPortalEntry 20 }

		
		-- 1.3.6.1.4.1.388.11.2.4.2.2
		ccPortalLastMac OBJECT-TYPE
			SYNTAX PhysAddress
			MAX-ACCESS read-only
			STATUS current
			DESCRIPTION
				"This scalar records the MAC address of the most 
				recent Portal to be Adopted, UnAdopted, or Denied."
			::= { ccPortal 2 }

		
		-- 1.3.6.1.4.1.388.11.2.4.2.3
		ccPortalLastReason OBJECT-TYPE
			SYNTAX INTEGER
				{
				success(1),
				aclViolation(2),
				timeout(3)
				}
			MAX-ACCESS read-only
			STATUS current
			DESCRIPTION
				"This value notes the reason for the most-recent 
				Portal UnAdoption or Denial."
			::= { ccPortal 3 }

		
		-- 1.3.6.1.4.1.388.11.2.4.2.4
		ccPortalAdoptionTable OBJECT-TYPE
			SYNTAX SEQUENCE OF CcPortalAdoptionEntry
			MAX-ACCESS not-accessible
			STATUS current
			DESCRIPTION
				"Table describing which WLANs are eligible to adopt a
				new portal.
				
				The illegal MAC address value of 'FF:FF:FF:FF:FF:FF'
				is used in both _StartMac and _EndMac fields to 
				indicate the special row used to declare 'default' 
				behavior.  That is, if no other row in the
				table applies, which WLANs are eligible to adopt the
				portal.  
				
				This one special row cannot be deleted."
			::= { ccPortal 4 }

		
		-- 1.3.6.1.4.1.388.11.2.4.2.4.1
		ccPortalAdoptionEntry OBJECT-TYPE
			SYNTAX CcPortalAdoptionEntry
			MAX-ACCESS not-accessible
			STATUS current
			DESCRIPTION
				" "
			INDEX { ccPortalAdoptionIndex }
			::= { ccPortalAdoptionTable 1 }

		
		CcPortalAdoptionEntry ::=
			SEQUENCE { 
				ccPortalAdoptionIndex
					Integer32,
				ccPortalAdoptionStartMac
					PhysAddress,
				ccPortalAdoptionEndMac
					PhysAddress,
				ccPortalAdoptionWlanPointers
					SinglePointer,
				ccPortalAdoptionRowStatus
					AbbrevRowStatus
			 }

-- Simple index.
-- 
-- ??- it appears that 'start MAC' is not required in
-- the UI to be unique, so it would not suffice as the
-- index.
		-- 1.3.6.1.4.1.388.11.2.4.2.4.1.1
		ccPortalAdoptionIndex OBJECT-TYPE
			SYNTAX Integer32 (1..127)
			MAX-ACCESS accessible-for-notify
			STATUS current
			DESCRIPTION
				"Table that describes which portals can be adopted by
				which WLANs."
			::= { ccPortalAdoptionEntry 1 }

		
		-- 1.3.6.1.4.1.388.11.2.4.2.4.1.2
		ccPortalAdoptionStartMac OBJECT-TYPE
			SYNTAX PhysAddress
			MAX-ACCESS read-write
			STATUS current
			DESCRIPTION
				"Starting MAC address of range of MAC addresses."
			::= { ccPortalAdoptionEntry 2 }

		
		-- 1.3.6.1.4.1.388.11.2.4.2.4.1.3
		ccPortalAdoptionEndMac OBJECT-TYPE
			SYNTAX PhysAddress
			MAX-ACCESS read-write
			STATUS current
			DESCRIPTION
				"Ending MAC address of range of MAC addresses."
			::= { ccPortalAdoptionEntry 3 }

		
		-- 1.3.6.1.4.1.388.11.2.4.2.4.1.4
		ccPortalAdoptionWlanPointers OBJECT-TYPE
			SYNTAX SinglePointer
			MAX-ACCESS read-write
			STATUS current
			DESCRIPTION
				"Pointer to zero or more WLANs which are eligible
				to adopt portals whose MAC address falls within the
				specified range.
				
				Any WLAN selected by this value must first be removed
				from the 'default' row first.
				
				Note that to make an adoption rule apply to more
				than one WLAN, you must create multiple rows in 
				this table.  (This is due to the way the adoption
				rules are stored inside the switch).
				"
			::= { ccPortalAdoptionEntry 4 }

		
		-- 1.3.6.1.4.1.388.11.2.4.2.4.1.5
		ccPortalAdoptionRowStatus OBJECT-TYPE
			SYNTAX AbbrevRowStatus
			MAX-ACCESS read-write
			STATUS current
			DESCRIPTION
				"Simple row status."
			::= { ccPortalAdoptionEntry 5 }

		
-- ??-TW: all the stats in this table are reported in WISP
-- 'Status' messages reported from the Portal to the switch
-- every 5sec.  Note that these are counters newly added to
-- the Portals.  In each case, they are cumulative counters,
-- (since Portal reset), so the swith should NOT add them up.
		-- 1.3.6.1.4.1.388.11.2.4.2.5
		ccPortalSystemStatsTable OBJECT-TYPE
			SYNTAX SEQUENCE OF CcPortalSystemStatsEntry
			MAX-ACCESS not-accessible
			STATUS current
			DESCRIPTION
				"This table includes statistics for 802.11 system packets
				transmitted/received at each Portal."
			::= { ccPortal 5 }

		
		-- 1.3.6.1.4.1.388.11.2.4.2.5.1
		ccPortalSystemStatsEntry OBJECT-TYPE
			SYNTAX CcPortalSystemStatsEntry
			MAX-ACCESS not-accessible
			STATUS current
			DESCRIPTION
				" "
			INDEX { ccPortalIndex }
			::= { ccPortalSystemStatsTable 1 }

		
		CcPortalSystemStatsEntry ::=
			SEQUENCE { 
				ccPortalSystemStatsBeaconsTx
					Unsigned32,
				ccPortalSystemStatsBeaconsTxOctets
					Unsigned32,
				ccPortalSystemStatsProbeReqRx
					Unsigned32,
				ccPortalSystemStatsProbeReqRxOctets
					Unsigned32,
				ccPortalSystemStatsProbeRespRetriesNone
					Unsigned32,
				ccPortalSystemStatsProbeRespRetries1
					Unsigned32,
				ccPortalSystemStatsProbeRespRetries2
					Unsigned32,
				ccPortalSystemStatsProbeRespRetries3OrMore
					Unsigned32,
				ccPortalSystemStatsProbeRespRetriesFailed
					Unsigned32,
				ccPortalSystemStatsProbeRespTxOctets
					Unsigned32
			 }

		-- 1.3.6.1.4.1.388.11.2.4.2.5.1.1
		ccPortalSystemStatsBeaconsTx OBJECT-TYPE
			SYNTAX Unsigned32
			MAX-ACCESS read-only
			STATUS current
			DESCRIPTION
				"The number of Beacons sent."
			::= { ccPortalSystemStatsEntry 1 }

		
		-- 1.3.6.1.4.1.388.11.2.4.2.5.1.2
		ccPortalSystemStatsBeaconsTxOctets OBJECT-TYPE
			SYNTAX Unsigned32
			MAX-ACCESS read-only
			STATUS current
			DESCRIPTION
				"The number of octets sent in Beacons."
			::= { ccPortalSystemStatsEntry 2 }

		
		-- 1.3.6.1.4.1.388.11.2.4.2.5.1.3
		ccPortalSystemStatsProbeReqRx OBJECT-TYPE
			SYNTAX Unsigned32
			MAX-ACCESS read-only
			STATUS current
			DESCRIPTION
				"The number of Probe Request packets received."
			::= { ccPortalSystemStatsEntry 3 }

		
		-- 1.3.6.1.4.1.388.11.2.4.2.5.1.4
		ccPortalSystemStatsProbeReqRxOctets OBJECT-TYPE
			SYNTAX Unsigned32
			MAX-ACCESS read-only
			STATUS current
			DESCRIPTION
				"The number of octets received in Probe Request packets."
			::= { ccPortalSystemStatsEntry 4 }

		
		-- 1.3.6.1.4.1.388.11.2.4.2.5.1.5
		ccPortalSystemStatsProbeRespRetriesNone OBJECT-TYPE
			SYNTAX Unsigned32
			MAX-ACCESS read-only
			STATUS current
			DESCRIPTION
				"The number of Probe Response packets sent with no retries."
			::= { ccPortalSystemStatsEntry 5 }

		
		-- 1.3.6.1.4.1.388.11.2.4.2.5.1.6
		ccPortalSystemStatsProbeRespRetries1 OBJECT-TYPE
			SYNTAX Unsigned32
			MAX-ACCESS read-only
			STATUS current
			DESCRIPTION
				"The number of Probe Response packets sent with exactly
				1 retry."
			::= { ccPortalSystemStatsEntry 6 }

		
		-- 1.3.6.1.4.1.388.11.2.4.2.5.1.7
		ccPortalSystemStatsProbeRespRetries2 OBJECT-TYPE
			SYNTAX Unsigned32
			MAX-ACCESS read-only
			STATUS current
			DESCRIPTION
				"The number of Probe Response packets sent with exactly
				2 retries."
			::= { ccPortalSystemStatsEntry 7 }

		
		-- 1.3.6.1.4.1.388.11.2.4.2.5.1.8
		ccPortalSystemStatsProbeRespRetries3OrMore OBJECT-TYPE
			SYNTAX Unsigned32
			MAX-ACCESS read-only
			STATUS current
			DESCRIPTION
				"The number of Probe Response packets sent with exactly
				3 retries or more retries.
				"
			::= { ccPortalSystemStatsEntry 8 }

		
		-- 1.3.6.1.4.1.388.11.2.4.2.5.1.9
		ccPortalSystemStatsProbeRespRetriesFailed OBJECT-TYPE
			SYNTAX Unsigned32
			MAX-ACCESS read-only
			STATUS current
			DESCRIPTION
				"The number of Probe Response packets that were never
				successfully transmitted because the max retry count was
				reached."
			::= { ccPortalSystemStatsEntry 9 }

		
		-- 1.3.6.1.4.1.388.11.2.4.2.5.1.10
		ccPortalSystemStatsProbeRespTxOctets OBJECT-TYPE
			SYNTAX Unsigned32
			MAX-ACCESS read-only
			STATUS current
			DESCRIPTION
				"The number of octets successfully transmitted in Probe 
				Response packets.  (For example, the octets in a Probe 
				Response that is transmitted twice - one retry - only 
				counts once in this sum)."
			::= { ccPortalSystemStatsEntry 10 }

		
		-- 1.3.6.1.4.1.388.11.2.4.2.6
		ccPortalSettingsTable OBJECT-TYPE
			SYNTAX SEQUENCE OF CcPortalSettingsEntry
			MAX-ACCESS not-accessible
			STATUS current
			DESCRIPTION
				"Use ccPortalSettingsTable to view and set the properties of 
				the Access Ports.
				
				"
			::= { ccPortal 6 }

		
		-- 1.3.6.1.4.1.388.11.2.4.2.6.1
		ccPortalSettingsEntry OBJECT-TYPE
			SYNTAX CcPortalSettingsEntry
			MAX-ACCESS not-accessible
			STATUS current
			DESCRIPTION
				" "
			INDEX { ccPortalIndex }
			::= { ccPortalSettingsTable 1 }

		
		CcPortalSettingsEntry ::=
			SEQUENCE { 
				ccPortalSettingsName
					DisplayString,
				ccPortalSettingsLocation
					DisplayString,
				ccPortalSettingsAntenna
					INTEGER,
				ccPortalSettingsShortPreamble
					TruthValue,
				ccPortalSettingsUniSpread
					TruthValue,
				ccPortalSettingsRtsThresh
					Integer32,
				ccPortalSettingsBeaconInt
					Integer32,
				ccPortalSettingsDtimPrd
					Integer32,
				ccPortalSettingsSecBeacon
					TruthValue,
				ccPortalSettingsPriWlan
					SinglePointer,
				ccPortalSettingsBasicRates
					TransmitRate,
				ccPortalSettingsSupportedRates
					TransmitRate,
				ccPortalSettingsBGMode
					INTEGER,
				ccPortalSettingsAdoptedWlan
					MultiPointer63,
				ccPortalSettingsDetector
					TruthValue
			 }

		-- 1.3.6.1.4.1.388.11.2.4.2.6.1.1
		ccPortalSettingsName OBJECT-TYPE
			SYNTAX DisplayString
			MAX-ACCESS read-write
			STATUS current
			DESCRIPTION
				"Name of Access Port."
			::= { ccPortalSettingsEntry 1 }

		
		-- 1.3.6.1.4.1.388.11.2.4.2.6.1.2
		ccPortalSettingsLocation OBJECT-TYPE
			SYNTAX DisplayString
			MAX-ACCESS read-write
			STATUS current
			DESCRIPTION
				"Site location of Access Port."
			::= { ccPortalSettingsEntry 2 }

		
		-- 1.3.6.1.4.1.388.11.2.4.2.6.1.3
		ccPortalSettingsAntenna OBJECT-TYPE
			SYNTAX INTEGER
				{
				fullDiversity(1),
				primaryOnly(2),
				secondaryOnly(3)
				}
			MAX-ACCESS read-write
			STATUS current
			DESCRIPTION
				"The antenna diversity setting for the access port."
			::= { ccPortalSettingsEntry 3 }

		
		-- 1.3.6.1.4.1.388.11.2.4.2.6.1.4
		ccPortalSettingsShortPreamble OBJECT-TYPE
			SYNTAX TruthValue
			MAX-ACCESS read-write
			STATUS current
			DESCRIPTION
				"Enable support for Short Preamble when MUs 
				associate with the Access Port.  Enabling Short
				Preamble may cause incompatibility with some older
				clients."
			::= { ccPortalSettingsEntry 4 }

		
		-- 1.3.6.1.4.1.388.11.2.4.2.6.1.5
		ccPortalSettingsUniSpread OBJECT-TYPE
			SYNTAX TruthValue
			MAX-ACCESS read-write
			STATUS current
			DESCRIPTION
				"Eable the Uniform Spreading feature of the AP300.
				To comply with Dynamic Frequency Selection(DFS) 
				requirements in the European Union, the 802.11a
				radio on AP300 Access Ports will come up on a random
				channel each time it is powered on."
			::= { ccPortalSettingsEntry 5 }

		
		-- 1.3.6.1.4.1.388.11.2.4.2.6.1.6
		ccPortalSettingsRtsThresh OBJECT-TYPE
			SYNTAX Integer32
			MAX-ACCESS read-write
			STATUS current
			DESCRIPTION
				"The Request To Send(RTS) threshold(in bytes) for use
				by the WLAN's adopted Access Port."
			::= { ccPortalSettingsEntry 6 }

		
		-- 1.3.6.1.4.1.388.11.2.4.2.6.1.7
		ccPortalSettingsBeaconInt OBJECT-TYPE
			SYNTAX Integer32 (50..200)
			MAX-ACCESS read-write
			STATUS current
			DESCRIPTION
				"Specify a beacon interval in units of 1,000 
				microseconds (K-us). This is a multiple of the DTIM 
				(ccPortalCfgDefaultADtimPrd) value, for example, 
				100 : 10. "
			::= { ccPortalSettingsEntry 7 }

		
		-- 1.3.6.1.4.1.388.11.2.4.2.6.1.8
		ccPortalSettingsDtimPrd OBJECT-TYPE
			SYNTAX Integer32 (1..50)
			MAX-ACCESS read-write
			STATUS current
			DESCRIPTION
				"Specify a period for the Delivery Traffic Indication 
				Message (DTIM). This is a divisor of the beacon 
				interval (in milliseconds), for example, 10 : 100. "
			::= { ccPortalSettingsEntry 8 }

		
		-- 1.3.6.1.4.1.388.11.2.4.2.6.1.9
		ccPortalSettingsSecBeacon OBJECT-TYPE
			SYNTAX TruthValue
			MAX-ACCESS read-write
			STATUS current
			DESCRIPTION
				"Enable the Secure Beacon checkbox to disallow the 
				Access Port from broadcasting an ESSID in its 
				beacons. This is a safeguard to prevent intruders 
				from tapping into the WLAN. Consider this security 
				measure for a private, corporate network."
			::= { ccPortalSettingsEntry 9 }

		
		-- 1.3.6.1.4.1.388.11.2.4.2.6.1.10
		ccPortalSettingsPriWlan OBJECT-TYPE
			SYNTAX SinglePointer
			MAX-ACCESS read-write
			STATUS current
			DESCRIPTION
				"Associate a primary WLAN with the Access Port for 
				broadcast of the Extended Service Set Identification 
				(ESSID). The purpose of such broadcasting is to allow
				mobile units to identify Access Ports that are 
				associated with the WLAN."
			::= { ccPortalSettingsEntry 10 }

		
		-- 1.3.6.1.4.1.388.11.2.4.2.6.1.11
		ccPortalSettingsBasicRates OBJECT-TYPE
			SYNTAX TransmitRate
			MAX-ACCESS read-write
			STATUS current
			DESCRIPTION
				"List of basic rates for the radio."
			::= { ccPortalSettingsEntry 11 }

		
		-- 1.3.6.1.4.1.388.11.2.4.2.6.1.12
		ccPortalSettingsSupportedRates OBJECT-TYPE
			SYNTAX TransmitRate
			MAX-ACCESS read-write
			STATUS current
			DESCRIPTION
				"List of supported rates for the radio."
			::= { ccPortalSettingsEntry 12 }

		
		-- 1.3.6.1.4.1.388.11.2.4.2.6.1.13
		ccPortalSettingsBGMode OBJECT-TYPE
			SYNTAX INTEGER
				{
				modeBandG(1),
				modeG(2),
				modeB(3)
				}
			MAX-ACCESS read-write
			STATUS current
			DESCRIPTION
				"Radio mode."
			::= { ccPortalSettingsEntry 13 }

		
		-- 1.3.6.1.4.1.388.11.2.4.2.6.1.14
		ccPortalSettingsAdoptedWlan OBJECT-TYPE
			SYNTAX MultiPointer63
			MAX-ACCESS read-only
			STATUS current
			DESCRIPTION
				"Enable the bits for the WLANs you wish to associate the 
				Access Port with."
			::= { ccPortalSettingsEntry 14 }

		
		-- 1.3.6.1.4.1.388.11.2.4.2.6.1.15
		ccPortalSettingsDetector OBJECT-TYPE
			SYNTAX TruthValue
			MAX-ACCESS read-write
			STATUS current
			DESCRIPTION
				"Description."
			::= { ccPortalSettingsEntry 15 }

		
		-- 1.3.6.1.4.1.388.11.2.4.2.7
		ccPortalCfgRadioTable OBJECT-TYPE
			SYNTAX SEQUENCE OF CcPortalCfgRadioEntry
			MAX-ACCESS not-accessible
			STATUS current
			DESCRIPTION
				"Use ccPortalCfgRadioTable to view and set the radio 
				properties of the Access Ports.
				
				
				The process can be broken down into the following steps:
				1. Set ccPortalCfgRadioReset to TRUE.
				2. Set ccPortalCfgRadioDesPlacement
				3. Get ccPortalCfgRadioPosChannel
				4. Set ccPortalCfgRadioDesChannel
				5. Get ccPortalCfgRadioPosPowerLevel
				6. Set ccPortalCfgRadioDesPowerLevel
				7. Get ccPortalCfgRadioPowerInMW
				8. Set and pull progress of ccPortalCfgRadioSet 
				9. Validate the configuration has been set by getting
				     ccPortalCfgRadioPlacement
				     ccPortalCfgRadioChannel
				     ccPortalCfgRadioPowerLevel
				
				"
			::= { ccPortal 7 }

		
		-- 1.3.6.1.4.1.388.11.2.4.2.7.1
		ccPortalCfgRadioEntry OBJECT-TYPE
			SYNTAX CcPortalCfgRadioEntry
			MAX-ACCESS not-accessible
			STATUS current
			DESCRIPTION
				" "
			INDEX { ccPortalIndex }
			::= { ccPortalCfgRadioTable 1 }

		
		CcPortalCfgRadioEntry ::=
			SEQUENCE { 
				ccPortalCfgRadioDesPlacement
					INTEGER,
				ccPortalCfgRadioPosChannel
					BITS,
				ccPortalCfgRadioDesChannel
					INTEGER,
				ccPortalCfgRadioPosPowerLevel
					Integer32,
				ccPortalCfgRadioDesPowerLevel
					Integer32,
				ccPortalCfgRadioDesPowerInMW
					Integer32,
				ccPortalCfgRadioSet
					DoActionShowProgress,
				ccPortalCfgRadioReset
					DoActionShowProgress,
				ccPortalCfgRadioPlacement
					INTEGER,
				ccPortalCfgRadioChannel
					INTEGER,
				ccPortalCfgRadioPowerLevel
					Unsigned32,
				ccPortalCfgRadioPowerInMW
					Unsigned32
			 }

		-- 1.3.6.1.4.1.388.11.2.4.2.7.1.1
		ccPortalCfgRadioDesPlacement OBJECT-TYPE
			SYNTAX INTEGER
				{
				indoor(1),
				outdoor(2)
				}
			MAX-ACCESS read-write
			STATUS current
			DESCRIPTION
				"The desired placement for radio."
			::= { ccPortalCfgRadioEntry 1 }

		
		-- 1.3.6.1.4.1.388.11.2.4.2.7.1.2
		ccPortalCfgRadioPosChannel OBJECT-TYPE
			SYNTAX BITS
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(12),
				achannel40(13),
				achannel44(14),
				achannel48(15),
				achannel52(16),
				achannel56(17),
				achannel60(18),
				achannel64(19),
				achannel149(20),
				achannel153(21),
				achannel157(22),
				achannel161(23)
				}
			MAX-ACCESS read-only
			STATUS current
			DESCRIPTION
				"The possible channels that can be set when placement = 
				ccPortalCfgRadioDesPlacement."
			::= { ccPortalCfgRadioEntry 2 }

		
		-- 1.3.6.1.4.1.388.11.2.4.2.7.1.3
		ccPortalCfgRadioDesChannel OBJECT-TYPE
			SYNTAX INTEGER
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(36),
				achannel40(40),
				achannel44(44),
				achannel48(48),
				achannel52(52),
				achannel56(56),
				achannel60(60),
				achannel64(64),
				achannel149(149),
				achannel153(153),
				achannel157(157),
				achannel161(161)
				}
			MAX-ACCESS read-write
			STATUS current
			DESCRIPTION
				"The desired channel for radio."
			::= { ccPortalCfgRadioEntry 3 }

		
		-- 1.3.6.1.4.1.388.11.2.4.2.7.1.4
		ccPortalCfgRadioPosPowerLevel OBJECT-TYPE
			SYNTAX Integer32
			MAX-ACCESS read-only
			STATUS current
			DESCRIPTION
				"The max possible power level (dBm) that can be set when 
				channel= ccPortalCfgRadioDesChannel."
			::= { ccPortalCfgRadioEntry 4 }

		
		-- 1.3.6.1.4.1.388.11.2.4.2.7.1.5
		ccPortalCfgRadioDesPowerLevel OBJECT-TYPE
			SYNTAX Integer32
			MAX-ACCESS read-write
			STATUS current
			DESCRIPTION
				"The desired power level (dBm) for radio."
			::= { ccPortalCfgRadioEntry 5 }

		
		-- 1.3.6.1.4.1.388.11.2.4.2.7.1.6
		ccPortalCfgRadioDesPowerInMW OBJECT-TYPE
			SYNTAX Integer32
			MAX-ACCESS read-only
			STATUS current
			DESCRIPTION
				"ccPortalCfgRadioDesPowerLevel in mW."
			::= { ccPortalCfgRadioEntry 6 }

		
		-- 1.3.6.1.4.1.388.11.2.4.2.7.1.7
		ccPortalCfgRadioSet OBJECT-TYPE
			SYNTAX DoActionShowProgress
			MAX-ACCESS read-write
			STATUS current
			DESCRIPTION
				"Validate values in ccPortalCfgRadioDes_ fields.  If it is
				a valid combination, configure the switch with this 
				combination and set ccPortalCfgRadio_ to these values."
			::= { ccPortalCfgRadioEntry 7 }

		
		-- 1.3.6.1.4.1.388.11.2.4.2.7.1.8
		ccPortalCfgRadioReset OBJECT-TYPE
			SYNTAX DoActionShowProgress
			MAX-ACCESS read-write
			STATUS current
			DESCRIPTION
				"Reset the following OIDs.
				
				ccPortalCfgRadioDesPlacement
				ccPortalCfgRadioDesChannel
				ccPortalCfgRadioDesPowerLevel
				ccPortalCfgRadioPosChannel
				ccPortalCfgRadioPosPowerLevel
				ccPortalCfgRadioPowerInMW
				"
			::= { ccPortalCfgRadioEntry 8 }

		
		-- 1.3.6.1.4.1.388.11.2.4.2.7.1.9
		ccPortalCfgRadioPlacement OBJECT-TYPE
			SYNTAX INTEGER
				{
				indoor(1),
				outdoor(2)
				}
			MAX-ACCESS read-only
			STATUS current
			DESCRIPTION
				"The placement configuration for radio."
			::= { ccPortalCfgRadioEntry 9 }

		
		-- 1.3.6.1.4.1.388.11.2.4.2.7.1.10
		ccPortalCfgRadioChannel OBJECT-TYPE
			SYNTAX INTEGER
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(36),
				achannel40(40),
				achannel44(44),
				achannel48(48),
				achannel52(52),
				achannel56(56),
				achannel60(60),
				achannel64(64),
				achannel149(149),
				achannel153(153),
				achannel157(157),
				achannel161(161)
				}
			MAX-ACCESS read-only
			STATUS current
			DESCRIPTION
				"The channel configuration for radio."
			::= { ccPortalCfgRadioEntry 10 }

		
		-- 1.3.6.1.4.1.388.11.2.4.2.7.1.11
		ccPortalCfgRadioPowerLevel OBJECT-TYPE
			SYNTAX Unsigned32
			MAX-ACCESS read-only
			STATUS current
			DESCRIPTION
				"The power level (dBm) configuration for radio."
			::= { ccPortalCfgRadioEntry 11 }

		
		-- 1.3.6.1.4.1.388.11.2.4.2.7.1.12
		ccPortalCfgRadioPowerInMW OBJECT-TYPE
			SYNTAX Unsigned32
			MAX-ACCESS read-only
			STATUS current
			DESCRIPTION
				"ccPortalCfgRadioPowerLevel in mW."
			::= { ccPortalCfgRadioEntry 12 }

		
		-- 1.3.6.1.4.1.388.11.2.4.2.8
		ccPortalSettingsDefaultTable OBJECT-TYPE
			SYNTAX SEQUENCE OF CcPortalSettingsDefaultEntry
			MAX-ACCESS not-accessible
			STATUS current
			DESCRIPTION
				"The ccPortalSettingsDefaultsTable contains the initial 
				settings for the Access Ports.
				"
			::= { ccPortal 8 }

		
		-- 1.3.6.1.4.1.388.11.2.4.2.8.1
		ccPortalSettingsDefaultEntry OBJECT-TYPE
			SYNTAX CcPortalSettingsDefaultEntry
			MAX-ACCESS not-accessible
			STATUS current
			DESCRIPTION
				" "
			INDEX { ccPortalSettingsDefaultIndex }
			::= { ccPortalSettingsDefaultTable 1 }

		
		CcPortalSettingsDefaultEntry ::=
			SEQUENCE { 
				ccPortalSettingsDefaultIndex
					INTEGER,
				ccPortalSettingsDefaultAntenna
					INTEGER,
				ccPortalSettingsDefaultShortPreamble
					TruthValue,
				ccPortalSettingsDefaultUniSpread
					TruthValue,
				ccPortalSettingsDefaultRtsThresh
					Integer32,
				ccPortalSettingsDefaultBeaconInt
					Integer32,
				ccPortalSettingsDefaultDtimPrd
					Integer32,
				ccPortalSettingsDefaultSecBeacon
					TruthValue,
				ccPortalSettingsDefaultPriWlan
					SinglePointer,
				ccPortalSettingsDefaultBasicRates
					TransmitRate,
				ccPortalSettingsDefaultSupportedRates
					TransmitRate,
				ccPortalSettingsDefaultBGMode
					INTEGER
			 }

		-- 1.3.6.1.4.1.388.11.2.4.2.8.1.1
		ccPortalSettingsDefaultIndex OBJECT-TYPE
			SYNTAX INTEGER
				{
				radioA(1),
				radioB(2),
				radioG(3)
				}
			MAX-ACCESS accessible-for-notify
			STATUS current
			DESCRIPTION
				"The type of the radio"
			::= { ccPortalSettingsDefaultEntry 1 }

		
		-- 1.3.6.1.4.1.388.11.2.4.2.8.1.2
		ccPortalSettingsDefaultAntenna OBJECT-TYPE
			SYNTAX INTEGER
				{
				fullDiversity(1),
				primaryOnly(2),
				secondaryOnly(3)
				}
			MAX-ACCESS read-write
			STATUS current
			DESCRIPTION
				"The antenna diversity setting for the access port."
			::= { ccPortalSettingsDefaultEntry 2 }

		
		-- 1.3.6.1.4.1.388.11.2.4.2.8.1.3
		ccPortalSettingsDefaultShortPreamble OBJECT-TYPE
			SYNTAX TruthValue
			MAX-ACCESS read-write
			STATUS current
			DESCRIPTION
				"Enable support for Short Preamble when MUs 
				associate with the Access Port.  Enabling Short
				Preamble may cause incompatibility with some older
				clients."
			::= { ccPortalSettingsDefaultEntry 3 }

		
		-- 1.3.6.1.4.1.388.11.2.4.2.8.1.4
		ccPortalSettingsDefaultUniSpread OBJECT-TYPE
			SYNTAX TruthValue
			MAX-ACCESS read-write
			STATUS current
			DESCRIPTION
				"Eable the Uniform Spreading feature of the AP300.
				To comply with Dynamic Frequency Selection(DFS) 
				requirements in the European Union, the 802.11a
				radio on AP300 Access Ports will come up on a random
				channel each time it is powered on."
			::= { ccPortalSettingsDefaultEntry 4 }

		
		-- 1.3.6.1.4.1.388.11.2.4.2.8.1.5
		ccPortalSettingsDefaultRtsThresh OBJECT-TYPE
			SYNTAX Integer32
			MAX-ACCESS read-write
			STATUS current
			DESCRIPTION
				"The Request To Send(RTS) threshold(in bytes) for use
				by the WLAN's adopted Access Port."
			::= { ccPortalSettingsDefaultEntry 5 }

		
		-- 1.3.6.1.4.1.388.11.2.4.2.8.1.6
		ccPortalSettingsDefaultBeaconInt OBJECT-TYPE
			SYNTAX Integer32 (50..200)
			MAX-ACCESS read-write
			STATUS current
			DESCRIPTION
				"Specify a beacon interval in units of 1,000 
				microseconds (K-us). This is a multiple of the DTIM 
				(ccPortalCfgDefaultADtimPrd) value, for example, 
				100 : 10. "
			::= { ccPortalSettingsDefaultEntry 6 }

		
		-- 1.3.6.1.4.1.388.11.2.4.2.8.1.7
		ccPortalSettingsDefaultDtimPrd OBJECT-TYPE
			SYNTAX Integer32 (1..50)
			MAX-ACCESS read-write
			STATUS current
			DESCRIPTION
				"Specify a period for the Delivery Traffic Indication 
				Message (DTIM). This is a divisor of the beacon 
				interval (in milliseconds), for example, 10 : 100. "
			::= { ccPortalSettingsDefaultEntry 7 }

		
		-- 1.3.6.1.4.1.388.11.2.4.2.8.1.8
		ccPortalSettingsDefaultSecBeacon OBJECT-TYPE
			SYNTAX TruthValue
			MAX-ACCESS read-write
			STATUS current
			DESCRIPTION
				"Enable the Secure Beacon checkbox to disallow the 
				Access Port from broadcasting an ESSID in its 
				beacons. This is a safeguard to prevent intruders 
				from tapping into the WLAN. Consider this security 
				measure for a private, corporate network."
			::= { ccPortalSettingsDefaultEntry 8 }

		
		-- 1.3.6.1.4.1.388.11.2.4.2.8.1.9
		ccPortalSettingsDefaultPriWlan OBJECT-TYPE
			SYNTAX SinglePointer
			MAX-ACCESS read-write
			STATUS current
			DESCRIPTION
				"Associate a primary WLAN with the Access Port for 
				broadcast of the Extended Service Set Identification 
				(ESSID). The purpose of such broadcasting is to allow
				mobile units to identify Access Ports that are 
				associated with the WLAN."
			::= { ccPortalSettingsDefaultEntry 9 }

		
		-- 1.3.6.1.4.1.388.11.2.4.2.8.1.10
		ccPortalSettingsDefaultBasicRates OBJECT-TYPE
			SYNTAX TransmitRate
			MAX-ACCESS read-write
			STATUS current
			DESCRIPTION
				"List of basic rates for the radio."
			::= { ccPortalSettingsDefaultEntry 10 }

		
		-- 1.3.6.1.4.1.388.11.2.4.2.8.1.11
		ccPortalSettingsDefaultSupportedRates OBJECT-TYPE
			SYNTAX TransmitRate
			MAX-ACCESS read-write
			STATUS current
			DESCRIPTION
				"List of supported rates for the radio."
			::= { ccPortalSettingsDefaultEntry 11 }

		
		-- 1.3.6.1.4.1.388.11.2.4.2.8.1.12
		ccPortalSettingsDefaultBGMode OBJECT-TYPE
			SYNTAX INTEGER
				{
				modeBandG(1),
				modeG(2),
				modeB(3)
				}
			MAX-ACCESS read-write
			STATUS current
			DESCRIPTION
				"Radio mode."
			::= { ccPortalSettingsDefaultEntry 12 }

		
		-- 1.3.6.1.4.1.388.11.2.4.2.9
		ccPortalCfgRadioDefaultTable OBJECT-TYPE
			SYNTAX SEQUENCE OF CcPortalCfgRadioDefaultEntry
			MAX-ACCESS not-accessible
			STATUS current
			DESCRIPTION
				"The ccPortalCfgRadioDefaultTable contains the initial 
				settings for the radio settings of the Access Ports.
				
				Please refer to descriptions in ccPortalCfgRadioTable.
				"
			::= { ccPortal 9 }

		
		-- 1.3.6.1.4.1.388.11.2.4.2.9.1
		ccPortalCfgRadioDefaultEntry OBJECT-TYPE
			SYNTAX CcPortalCfgRadioDefaultEntry
			MAX-ACCESS not-accessible
			STATUS current
			DESCRIPTION
				" "
			INDEX { ccPortalSettingsDefaultIndex }
			::= { ccPortalCfgRadioDefaultTable 1 }

		
		CcPortalCfgRadioDefaultEntry ::=
			SEQUENCE { 
				ccPortalCfgRadioDefaultDesPlacement
					INTEGER,
				ccPortalCfgRadioDefaultPosChannel
					BITS,
				ccPortalCfgRadioDefaultDesChannel
					INTEGER,
				ccPortalCfgRadioDefaultPosPowerLevel
					Integer32,
				ccPortalCfgRadioDefaultDesPowerLevel
					Integer32,
				ccPortalCfgRadioDefaultDesPowerInMW
					Integer32,
				ccPortalCfgRadioDefaultSet
					DoActionShowProgress,
				ccPortalCfgRadioDefaultReset
					DoActionShowProgress,
				ccPortalCfgRadioDefaultPlacement
					INTEGER,
				ccPortalCfgRadioDefaultChannel
					INTEGER,
				ccPortalCfgRadioDefaultPowerLevel
					Unsigned32,
				ccPortalCfgRadioDefaultPowerInMW
					Unsigned32
			 }

		-- 1.3.6.1.4.1.388.11.2.4.2.9.1.1
		ccPortalCfgRadioDefaultDesPlacement OBJECT-TYPE
			SYNTAX INTEGER
				{
				indoor(1),
				outdoor(2)
				}
			MAX-ACCESS read-write
			STATUS current
			DESCRIPTION
				"The default desired placement for radio type."
			::= { ccPortalCfgRadioDefaultEntry 1 }

		
		-- 1.3.6.1.4.1.388.11.2.4.2.9.1.2
		ccPortalCfgRadioDefaultPosChannel OBJECT-TYPE
			SYNTAX BITS
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(12),
				achannel40(13),
				achannel44(14),
				achannel48(15),
				achannel52(16),
				achannel56(17),
				achannel60(18),
				achannel64(19),
				achannel149(20),
				achannel153(21),
				achannel157(22),
				achannel161(23)
				}
			MAX-ACCESS read-only
			STATUS current
			DESCRIPTION
				"The possible channels that can be set when placement = 
				ccPortalCfgRadioDefaultDesPlacement."
			::= { ccPortalCfgRadioDefaultEntry 2 }

		
		-- 1.3.6.1.4.1.388.11.2.4.2.9.1.3
		ccPortalCfgRadioDefaultDesChannel OBJECT-TYPE
			SYNTAX INTEGER
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(36),
				achannel40(40),
				achannel44(44),
				achannel48(48),
				achannel52(52),
				achannel56(56),
				achannel60(60),
				achannel64(64),
				achannel149(149),
				achannel153(153),
				achannel157(157),
				achannel161(161)
				}
			MAX-ACCESS read-write
			STATUS current
			DESCRIPTION
				"The default desired channel for radio type."
			::= { ccPortalCfgRadioDefaultEntry 3 }

		
		-- 1.3.6.1.4.1.388.11.2.4.2.9.1.4
		ccPortalCfgRadioDefaultPosPowerLevel OBJECT-TYPE
			SYNTAX Integer32
			MAX-ACCESS read-only
			STATUS current
			DESCRIPTION
				"The max possible power level (dBm) that can be set when 
				channel= ccPortalCfgRadioDefaultDesChannel."
			::= { ccPortalCfgRadioDefaultEntry 4 }

		
		-- 1.3.6.1.4.1.388.11.2.4.2.9.1.5
		ccPortalCfgRadioDefaultDesPowerLevel OBJECT-TYPE
			SYNTAX Integer32
			MAX-ACCESS read-write
			STATUS current
			DESCRIPTION
				"The desired power level (dBm) for radio."
			::= { ccPortalCfgRadioDefaultEntry 5 }

		
		-- 1.3.6.1.4.1.388.11.2.4.2.9.1.6
		ccPortalCfgRadioDefaultDesPowerInMW OBJECT-TYPE
			SYNTAX Integer32
			MAX-ACCESS read-only
			STATUS current
			DESCRIPTION
				"ccPortalCfgRadioDefaultDesPowerLevel in mW."
			::= { ccPortalCfgRadioDefaultEntry 6 }

		
		-- 1.3.6.1.4.1.388.11.2.4.2.9.1.7
		ccPortalCfgRadioDefaultSet OBJECT-TYPE
			SYNTAX DoActionShowProgress
			MAX-ACCESS read-write
			STATUS current
			DESCRIPTION
				"Validate values in ccPortalCfgRadioDefaultDes_ fields.  If it is
				a valid combination, configure the switch with this 
				combination and set ccPortalCfgRadioDefault_ to these values."
			::= { ccPortalCfgRadioDefaultEntry 7 }

		
		-- 1.3.6.1.4.1.388.11.2.4.2.9.1.8
		ccPortalCfgRadioDefaultReset OBJECT-TYPE
			SYNTAX DoActionShowProgress
			MAX-ACCESS read-write
			STATUS current
			DESCRIPTION
				"Reset the following OIDs.
				
				ccPortalCfgRadioDefaultDesPlacement
				ccPortalCfgRadioDefaultDesChannel
				ccPortalCfgRadioDefaultDesPowerLevel
				ccPortalCfgRadioDefaultPosChannel
				ccPortalCfgRadioDefaultPosPowerLevel
				ccPortalCfgRadioDefaultPowerInMW
				"
			::= { ccPortalCfgRadioDefaultEntry 8 }

		
		-- 1.3.6.1.4.1.388.11.2.4.2.9.1.9
		ccPortalCfgRadioDefaultPlacement OBJECT-TYPE
			SYNTAX INTEGER
				{
				indoor(1),
				outdoor(2)
				}
			MAX-ACCESS read-only
			STATUS current
			DESCRIPTION
				"The default placement configuration for radio type."
			::= { ccPortalCfgRadioDefaultEntry 9 }

		
		-- 1.3.6.1.4.1.388.11.2.4.2.9.1.10
		ccPortalCfgRadioDefaultChannel OBJECT-TYPE
			SYNTAX INTEGER
				{
				null(0),
				bchannel01(1),
				bchannel02(2),
				bchannel03(3),
				bchannel04(4),
				bchannel05(5),
				bchannel06(6),
				bchannel07(7),
				bchannel08(8),
				bchannel09(9),
				bchannel10(10),
				bchannel11(11),
				achannel36(36),
				achannel40(40),
				achannel44(44),
				achannel48(48),
				achannel52(52),
				achannel56(56),
				achannel60(60),
				achannel64(64),
				achannel149(149),
				achannel153(153),
				achannel157(157),
				achannel161(161)
				}
			MAX-ACCESS read-only
			STATUS current
			DESCRIPTION
				"The default channel configuration for radio type."
			::= { ccPortalCfgRadioDefaultEntry 10 }

		
		-- 1.3.6.1.4.1.388.11.2.4.2.9.1.11
		ccPortalCfgRadioDefaultPowerLevel OBJECT-TYPE
			SYNTAX Unsigned32
			MAX-ACCESS read-only
			STATUS current
			DESCRIPTION
				"The default power level (dBm) configuration for radio type."
			::= { ccPortalCfgRadioDefaultEntry 11 }

		
		-- 1.3.6.1.4.1.388.11.2.4.2.9.1.12
		ccPortalCfgRadioDefaultPowerInMW OBJECT-TYPE
			SYNTAX Unsigned32
			MAX-ACCESS read-only
			STATUS current
			DESCRIPTION
				"ccPortalCfgRadioDefaultPowerLevel in mW."
			::= { ccPortalCfgRadioDefaultEntry 12 }

		
-- 802.1x Port Authentication is used to provide 
-- security and authentication of all wired clients on 
-- a network. The WS 2000 supports 802.1x port 
-- authentication for the AP 300 Access Ports connected 
-- to it. It uses a username and password for all ports 
-- that can be configured from the wireless switch.
		-- 1.3.6.1.4.1.388.11.2.4.2.10
		cc802dt1xPortAuth OBJECT IDENTIFIER ::= { ccPortal 10 }

		
		-- 1.3.6.1.4.1.388.11.2.4.2.10.1
		cc802dt1xPortAuthLogin OBJECT-TYPE
			SYNTAX DisplayString (SIZE (1..64))
			MAX-ACCESS read-write
			STATUS current
			DESCRIPTION
				"802.1x Port Authentication username."
			::= { cc802dt1xPortAuth 1 }

		
		-- 1.3.6.1.4.1.388.11.2.4.2.10.2
		cc802dt1xPortAuthPass OBJECT-TYPE
			SYNTAX Password
			MAX-ACCESS read-write
			STATUS current
			DESCRIPTION
				"802.1x Port Authentication password."
			::= { cc802dt1xPortAuth 2 }

		
		-- 1.3.6.1.4.1.388.11.2.4.2.10.3
		cc802dt1xPortAuthSetAp300 OBJECT-TYPE
			SYNTAX DoActionShowProgress
			MAX-ACCESS read-write
			STATUS current
			DESCRIPTION
				"Set the username and password stored in 
				cc802dt1xPortAuthLogin and cc802dt1xPortAuthPass
				on all AP 300 Access Ports adopted by the switch."
			::= { cc802dt1xPortAuth 3 }

		
-- !!- OID: .100
		-- 1.3.6.1.4.1.388.11.2.4.2.100
		ccPortalRfSum OBJECT IDENTIFIER ::= { ccPortal 100 }

		
		-- 1.3.6.1.4.1.388.11.2.4.2.100.1
		ccPortalStatsTable OBJECT-TYPE
			SYNTAX SEQUENCE OF CcPortalStatsEntry
			MAX-ACCESS not-accessible
			STATUS current
			DESCRIPTION
				"This table describes general statistics about
				packets sent/recieved via each Portal on the switch."
			::= { ccPortalRfSum 1 }

		
		-- 1.3.6.1.4.1.388.11.2.4.2.100.1.1
		ccPortalStatsEntry OBJECT-TYPE
			SYNTAX CcPortalStatsEntry
			MAX-ACCESS not-accessible
			STATUS current
			DESCRIPTION
				" "
			INDEX { ccPortalIndex }
			::= { ccPortalStatsTable 1 }

		
		CcPortalStatsEntry ::=
			SEQUENCE { 
				ccPortalTxPktsUcast
					Counter32,
				ccPortalRxPktsUcast
					Counter32,
				ccPortalRxPktsNUcast
					Counter32,
				ccPortalTxOctetsUcast
					Counter32,
				ccPortalRxOctetsUcast
					Counter32,
				ccPortalRxOctetsNUcast
					Counter32,
				ccPortalRxUndecryptablePkts
					Counter32,
				ccPortalLastActivity
					TimeTicks
			 }

		-- 1.3.6.1.4.1.388.11.2.4.2.100.1.1.1
		ccPortalTxPktsUcast OBJECT-TYPE
			SYNTAX Counter32
			MAX-ACCESS read-only
			STATUS current
			DESCRIPTION
				"Count of unicast packets sent via the Portal."
			::= { ccPortalStatsEntry 1 }

		
		-- 1.3.6.1.4.1.388.11.2.4.2.100.1.1.2
		ccPortalRxPktsUcast OBJECT-TYPE
			SYNTAX Counter32
			MAX-ACCESS read-only
			STATUS current
			DESCRIPTION
				"Count of unicast packets received via the Portal."
			::= { ccPortalStatsEntry 2 }

		
		-- 1.3.6.1.4.1.388.11.2.4.2.100.1.1.3
		ccPortalRxPktsNUcast OBJECT-TYPE
			SYNTAX Counter32
			MAX-ACCESS read-only
			STATUS current
			DESCRIPTION
				"Count of non-unicast (broadcast & multicast) 
				packets received via the Portal."
			::= { ccPortalStatsEntry 3 }

		
		-- 1.3.6.1.4.1.388.11.2.4.2.100.1.1.4
		ccPortalTxOctetsUcast OBJECT-TYPE
			SYNTAX Counter32
			MAX-ACCESS read-only
			STATUS current
			DESCRIPTION
				"Count of unicast octets sent via the Portal."
			::= { ccPortalStatsEntry 4 }

		
		-- 1.3.6.1.4.1.388.11.2.4.2.100.1.1.5
		ccPortalRxOctetsUcast OBJECT-TYPE
			SYNTAX Counter32
			MAX-ACCESS read-only
			STATUS current
			DESCRIPTION
				"Count of unicast octets received via the Portal."
			::= { ccPortalStatsEntry 5 }

		
		-- 1.3.6.1.4.1.388.11.2.4.2.100.1.1.6
		ccPortalRxOctetsNUcast OBJECT-TYPE
			SYNTAX Counter32
			MAX-ACCESS read-only
			STATUS current
			DESCRIPTION
				"Count of non-unicast (broadcast & multicast) 
				octets received via the Portal."
			::= { ccPortalStatsEntry 6 }

		
		-- 1.3.6.1.4.1.388.11.2.4.2.100.1.1.7
		ccPortalRxUndecryptablePkts OBJECT-TYPE
			SYNTAX Counter32
			MAX-ACCESS read-only
			STATUS current
			DESCRIPTION
				"Count of packets received via the Portal that could
				not be decrypted."
			::= { ccPortalStatsEntry 7 }

		
		-- 1.3.6.1.4.1.388.11.2.4.2.100.1.1.8
		ccPortalLastActivity OBJECT-TYPE
			SYNTAX TimeTicks
			MAX-ACCESS read-only
			STATUS current
			DESCRIPTION
				"A snapshot of the switch's sysUpTime at the time
				of the last activity (packet sent or received)
				via the Portal."
			::= { ccPortalStatsEntry 8 }

		
		-- 1.3.6.1.4.1.388.11.2.4.2.100.2
		ccPortalRxPktsTable OBJECT-TYPE
			SYNTAX SEQUENCE OF CcPortalRxPktsEntry
			MAX-ACCESS not-accessible
			STATUS current
			DESCRIPTION
				"For each Portal on the switch, this table 
				describes counts of packets received at each 
				possible speed, (1Mb, 2Mb, 5.5Mb, 6Mb...)."
			::= { ccPortalRfSum 2 }

		
		-- 1.3.6.1.4.1.388.11.2.4.2.100.2.1
		ccPortalRxPktsEntry OBJECT-TYPE
			SYNTAX CcPortalRxPktsEntry
			MAX-ACCESS not-accessible
			STATUS current
			DESCRIPTION
				" "
			INDEX { ccPortalIndex }
			::= { ccPortalRxPktsTable 1 }

		
		CcPortalRxPktsEntry ::=
			SEQUENCE { 
				ccPortalRxPktsAt1Mb
					Counter32,
				ccPortalRxPktsAt2Mb
					Counter32,
				ccPortalRxPktsAt5pt5Mb
					Counter32,
				ccPortalRxPktsAt6Mb
					Counter32,
				ccPortalRxPktsAt9Mb
					Counter32,
				ccPortalRxPktsAt11Mb
					Counter32,
				ccPortalRxPktsAt12Mb
					Counter32,
				ccPortalRxPktsAt18Mb
					Counter32,
				ccPortalRxPktsAt22Mb
					Counter32,
				ccPortalRxPktsAt24Mb
					Counter32,
				ccPortalRxPktsAt36Mb
					Counter32,
				ccPortalRxPktsAt48Mb
					Counter32,
				ccPortalRxPktsAt54Mb
					Counter32
			 }

		-- 1.3.6.1.4.1.388.11.2.4.2.100.2.1.1
		ccPortalRxPktsAt1Mb OBJECT-TYPE
			SYNTAX Counter32
			MAX-ACCESS read-only
			STATUS current
			DESCRIPTION
				"Number of pkts received via this Portal at 1 Mb."
			::= { ccPortalRxPktsEntry 1 }

		
		-- 1.3.6.1.4.1.388.11.2.4.2.100.2.1.2
		ccPortalRxPktsAt2Mb OBJECT-TYPE
			SYNTAX Counter32
			MAX-ACCESS read-only
			STATUS current
			DESCRIPTION
				"Number of pkts received via this Portal at 2 Mb."
			::= { ccPortalRxPktsEntry 2 }

		
		-- 1.3.6.1.4.1.388.11.2.4.2.100.2.1.3
		ccPortalRxPktsAt5pt5Mb OBJECT-TYPE
			SYNTAX Counter32
			MAX-ACCESS read-only
			STATUS current
			DESCRIPTION
				"Number of pkts received via this Portal at 5.5 Mb."
			::= { ccPortalRxPktsEntry 3 }

		
		-- 1.3.6.1.4.1.388.11.2.4.2.100.2.1.4
		ccPortalRxPktsAt6Mb OBJECT-TYPE
			SYNTAX Counter32
			MAX-ACCESS read-only
			STATUS current
			DESCRIPTION
				"Number of pkts received via this Portal at 6 Mb."
			::= { ccPortalRxPktsEntry 4 }

		
		-- 1.3.6.1.4.1.388.11.2.4.2.100.2.1.5
		ccPortalRxPktsAt9Mb OBJECT-TYPE
			SYNTAX Counter32
			MAX-ACCESS read-only
			STATUS current
			DESCRIPTION
				"Number of pkts received via this Portal at 9 Mb."
			::= { ccPortalRxPktsEntry 5 }

		
		-- 1.3.6.1.4.1.388.11.2.4.2.100.2.1.6
		ccPortalRxPktsAt11Mb OBJECT-TYPE
			SYNTAX Counter32
			MAX-ACCESS read-only
			STATUS current
			DESCRIPTION
				"Number of pkts received via this Portal at 11 Mb."
			::= { ccPortalRxPktsEntry 6 }

		
		-- 1.3.6.1.4.1.388.11.2.4.2.100.2.1.7
		ccPortalRxPktsAt12Mb OBJECT-TYPE
			SYNTAX Counter32
			MAX-ACCESS read-only
			STATUS current
			DESCRIPTION
				"Number of pkts received via this Portal at 12 Mb."
			::= { ccPortalRxPktsEntry 7 }

		
		-- 1.3.6.1.4.1.388.11.2.4.2.100.2.1.8
		ccPortalRxPktsAt18Mb OBJECT-TYPE
			SYNTAX Counter32
			MAX-ACCESS read-only
			STATUS current
			DESCRIPTION
				"Number of pkts received via this Portal at 18 Mb."
			::= { ccPortalRxPktsEntry 8 }

		
		-- 1.3.6.1.4.1.388.11.2.4.2.100.2.1.9
		ccPortalRxPktsAt22Mb OBJECT-TYPE
			SYNTAX Counter32
			MAX-ACCESS read-only
			STATUS current
			DESCRIPTION
				"Number of pkts received via this Portal at 22 Mb."
			::= { ccPortalRxPktsEntry 9 }

		
		-- 1.3.6.1.4.1.388.11.2.4.2.100.2.1.10
		ccPortalRxPktsAt24Mb OBJECT-TYPE
			SYNTAX Counter32
			MAX-ACCESS read-only
			STATUS current
			DESCRIPTION
				"Number of pkts received via this Portal at 24 Mb."
			::= { ccPortalRxPktsEntry 10 }

		
		-- 1.3.6.1.4.1.388.11.2.4.2.100.2.1.11
		ccPortalRxPktsAt36Mb OBJECT-TYPE
			SYNTAX Counter32
			MAX-ACCESS read-only
			STATUS current
			DESCRIPTION
				"Number of pkts received via this Portal at 36 Mb."
			::= { ccPortalRxPktsEntry 11 }

		
		-- 1.3.6.1.4.1.388.11.2.4.2.100.2.1.12
		ccPortalRxPktsAt48Mb OBJECT-TYPE
			SYNTAX Counter32
			MAX-ACCESS read-only
			STATUS current
			DESCRIPTION
				"Number of pkts received via this Portal at 48 Mb."
			::= { ccPortalRxPktsEntry 12 }

		
		-- 1.3.6.1.4.1.388.11.2.4.2.100.2.1.13
		ccPortalRxPktsAt54Mb OBJECT-TYPE
			SYNTAX Counter32
			MAX-ACCESS read-only
			STATUS current
			DESCRIPTION
				"Number of pkts received via this Portal at 54 Mb."
			::= { ccPortalRxPktsEntry 13 }

		
		-- 1.3.6.1.4.1.388.11.2.4.2.100.3
		ccPortalTxPktsTable OBJECT-TYPE
			SYNTAX SEQUENCE OF CcPortalTxPktsEntry
			MAX-ACCESS not-accessible
			STATUS current
			DESCRIPTION
				"For each Portal on the switch, this table 
				describes counts of packets transmitted at each 
				possible speed, (1Mb, 2Mb, 5.5Mb, 6Mb...)."
			::= { ccPortalRfSum 3 }

		
		-- 1.3.6.1.4.1.388.11.2.4.2.100.3.1
		ccPortalTxPktsEntry OBJECT-TYPE
			SYNTAX CcPortalTxPktsEntry
			MAX-ACCESS not-accessible
			STATUS current
			DESCRIPTION
				" "
			INDEX { ccPortalIndex }
			::= { ccPortalTxPktsTable 1 }

		
		CcPortalTxPktsEntry ::=
			SEQUENCE { 
				ccPortalTxPktsAt1Mb
					Counter32,
				ccPortalTxPktsAt2Mb
					Counter32,
				ccPortalTxPktsAt5pt5Mb
					Counter32,
				ccPortalTxPktsAt6Mb
					Counter32,
				ccPortalTxPktsAt9Mb
					Counter32,
				ccPortalTxPktsAt11Mb
					Counter32,
				ccPortalTxPktsAt12Mb
					Counter32,
				ccPortalTxPktsAt18Mb
					Counter32,
				ccPortalTxPktsAt22Mb
					Counter32,
				ccPortalTxPktsAt24Mb
					Counter32,
				ccPortalTxPktsAt36Mb
					Counter32,
				ccPortalTxPktsAt48Mb
					Counter32,
				ccPortalTxPktsAt54Mb
					Counter32
			 }

		-- 1.3.6.1.4.1.388.11.2.4.2.100.3.1.1
		ccPortalTxPktsAt1Mb OBJECT-TYPE
			SYNTAX Counter32
			MAX-ACCESS read-only
			STATUS current
			DESCRIPTION
				"Number of pkts transmitted via this Portal at 1 Mb."
			::= { ccPortalTxPktsEntry 1 }

		
		-- 1.3.6.1.4.1.388.11.2.4.2.100.3.1.2
		ccPortalTxPktsAt2Mb OBJECT-TYPE
			SYNTAX Counter32
			MAX-ACCESS read-only
			STATUS current
			DESCRIPTION
				"Number of pkts transmitted via this Portal at 2 Mb."
			::= { ccPortalTxPktsEntry 2 }

		
		-- 1.3.6.1.4.1.388.11.2.4.2.100.3.1.3
		ccPortalTxPktsAt5pt5Mb OBJECT-TYPE
			SYNTAX Counter32
			MAX-ACCESS read-only
			STATUS current
			DESCRIPTION
				"Number of pkts transmitted via this Portal at 5.5 Mb."
			::= { ccPortalTxPktsEntry 3 }

		
		-- 1.3.6.1.4.1.388.11.2.4.2.100.3.1.4
		ccPortalTxPktsAt6Mb OBJECT-TYPE
			SYNTAX Counter32
			MAX-ACCESS read-only
			STATUS current
			DESCRIPTION
				"Number of pkts transmitted via this Portal at 6 Mb."
			::= { ccPortalTxPktsEntry 4 }

		
		-- 1.3.6.1.4.1.388.11.2.4.2.100.3.1.5
		ccPortalTxPktsAt9Mb OBJECT-TYPE
			SYNTAX Counter32
			MAX-ACCESS read-only
			STATUS current
			DESCRIPTION
				"Number of pkts transmitted via this Portal at 9 Mb."
			::= { ccPortalTxPktsEntry 5 }

		
		-- 1.3.6.1.4.1.388.11.2.4.2.100.3.1.6
		ccPortalTxPktsAt11Mb OBJECT-TYPE
			SYNTAX Counter32
			MAX-ACCESS read-only
			STATUS current
			DESCRIPTION
				"Number of pkts transmitted via this Portal at 11 Mb."
			::= { ccPortalTxPktsEntry 6 }

		
		-- 1.3.6.1.4.1.388.11.2.4.2.100.3.1.7
		ccPortalTxPktsAt12Mb OBJECT-TYPE
			SYNTAX Counter32
			MAX-ACCESS read-only
			STATUS current
			DESCRIPTION
				"Number of pkts transmitted via this Portal at 12 Mb."
			::= { ccPortalTxPktsEntry 7 }

		
		-- 1.3.6.1.4.1.388.11.2.4.2.100.3.1.8
		ccPortalTxPktsAt18Mb OBJECT-TYPE
			SYNTAX Counter32
			MAX-ACCESS read-only
			STATUS current
			DESCRIPTION
				"Number of pkts transmitted via this Portal at 18 Mb."
			::= { ccPortalTxPktsEntry 8 }

		
		-- 1.3.6.1.4.1.388.11.2.4.2.100.3.1.9
		ccPortalTxPktsAt22Mb OBJECT-TYPE
			SYNTAX Counter32
			MAX-ACCESS read-only
			STATUS current
			DESCRIPTION
				"Number of pkts transmitted via this Portal at 22 Mb."
			::= { ccPortalTxPktsEntry 9 }

		
		-- 1.3.6.1.4.1.388.11.2.4.2.100.3.1.10
		ccPortalTxPktsAt24Mb OBJECT-TYPE
			SYNTAX Counter32
			MAX-ACCESS read-only
			STATUS current
			DESCRIPTION
				"Number of pkts transmitted via this Portal at 24 Mb."
			::= { ccPortalTxPktsEntry 10 }

		
		-- 1.3.6.1.4.1.388.11.2.4.2.100.3.1.11
		ccPortalTxPktsAt36Mb OBJECT-TYPE
			SYNTAX Counter32
			MAX-ACCESS read-only
			STATUS current
			DESCRIPTION
				"Number of pkts transmitted via this Portal at 36 Mb."
			::= { ccPortalTxPktsEntry 11 }

		
		-- 1.3.6.1.4.1.388.11.2.4.2.100.3.1.12
		ccPortalTxPktsAt48Mb OBJECT-TYPE
			SYNTAX Counter32
			MAX-ACCESS read-only
			STATUS current
			DESCRIPTION
				"Number of pkts transmitted via this Portal at 48 Mb."
			::= { ccPortalTxPktsEntry 12 }

		
		-- 1.3.6.1.4.1.388.11.2.4.2.100.3.1.13
		ccPortalTxPktsAt54Mb OBJECT-TYPE
			SYNTAX Counter32
			MAX-ACCESS read-only
			STATUS current
			DESCRIPTION
				"Number of pkts transmitted via this Portal at 54 Mb."
			::= { ccPortalTxPktsEntry 13 }

		
		-- 1.3.6.1.4.1.388.11.2.4.2.100.4
		ccPortalRxOctetsTable OBJECT-TYPE
			SYNTAX SEQUENCE OF CcPortalRxOctetsEntry
			MAX-ACCESS not-accessible
			STATUS current
			DESCRIPTION
				"For each Portal on this switch, this table 
				describes counts of octets received at each 
				possible speed, (1Mb, 2Mb, 5.5Mb, 6Mb...)."
			::= { ccPortalRfSum 4 }

		
		-- 1.3.6.1.4.1.388.11.2.4.2.100.4.1
		ccPortalRxOctetsEntry OBJECT-TYPE
			SYNTAX CcPortalRxOctetsEntry
			MAX-ACCESS not-accessible
			STATUS current
			DESCRIPTION
				" "
			INDEX { ccPortalIndex }
			::= { ccPortalRxOctetsTable 1 }

		
		CcPortalRxOctetsEntry ::=
			SEQUENCE { 
				ccPortalRxOctetsAt1Mb
					Counter32,
				ccPortalRxOctetsAt2Mb
					Counter32,
				ccPortalRxOctetsAt5pt5Mb
					Counter32,
				ccPortalRxOctetsAt6Mb
					Counter32,
				ccPortalRxOctetsAt9Mb
					Counter32,
				ccPortalRxOctetsAt11Mb
					Counter32,
				ccPortalRxOctetsAt12Mb
					Counter32,
				ccPortalRxOctetsAt18Mb
					Counter32,
				ccPortalRxOctetsAt22Mb
					Counter32,
				ccPortalRxOctetsAt24Mb
					Counter32,
				ccPortalRxOctetsAt36Mb
					Counter32,
				ccPortalRxOctetsAt48Mb
					Counter32,
				ccPortalRxOctetsAt54Mb
					Counter32
			 }

		-- 1.3.6.1.4.1.388.11.2.4.2.100.4.1.1
		ccPortalRxOctetsAt1Mb OBJECT-TYPE
			SYNTAX Counter32
			MAX-ACCESS read-only
			STATUS current
			DESCRIPTION
				"Number of octets received via this Portal at 1 Mb."
			::= { ccPortalRxOctetsEntry 1 }

		
		-- 1.3.6.1.4.1.388.11.2.4.2.100.4.1.2
		ccPortalRxOctetsAt2Mb OBJECT-TYPE
			SYNTAX Counter32
			MAX-ACCESS read-only
			STATUS current
			DESCRIPTION
				"Number of octets received via this Portal at 2 Mb."
			::= { ccPortalRxOctetsEntry 2 }

		
		-- 1.3.6.1.4.1.388.11.2.4.2.100.4.1.3
		ccPortalRxOctetsAt5pt5Mb OBJECT-TYPE
			SYNTAX Counter32
			MAX-ACCESS read-only
			STATUS current
			DESCRIPTION
				"Number of octets received via this Portal at 5.5 Mb."
			::= { ccPortalRxOctetsEntry 3 }

		
		-- 1.3.6.1.4.1.388.11.2.4.2.100.4.1.4
		ccPortalRxOctetsAt6Mb OBJECT-TYPE
			SYNTAX Counter32
			MAX-ACCESS read-only
			STATUS current
			DESCRIPTION
				"Number of octets received via this Portal at 6 Mb."
			::= { ccPortalRxOctetsEntry 4 }

		
		-- 1.3.6.1.4.1.388.11.2.4.2.100.4.1.5
		ccPortalRxOctetsAt9Mb OBJECT-TYPE
			SYNTAX Counter32
			MAX-ACCESS read-only
			STATUS current
			DESCRIPTION
				"Number of octets received via this Portal at 9 Mb."
			::= { ccPortalRxOctetsEntry 5 }

		
		-- 1.3.6.1.4.1.388.11.2.4.2.100.4.1.6
		ccPortalRxOctetsAt11Mb OBJECT-TYPE
			SYNTAX Counter32
			MAX-ACCESS read-only
			STATUS current
			DESCRIPTION
				"Number of octets received via this Portal at 11 Mb."
			::= { ccPortalRxOctetsEntry 6 }

		
		-- 1.3.6.1.4.1.388.11.2.4.2.100.4.1.7
		ccPortalRxOctetsAt12Mb OBJECT-TYPE
			SYNTAX Counter32
			MAX-ACCESS read-only
			STATUS current
			DESCRIPTION
				"Number of octets received via this Portal at 12 Mb."
			::= { ccPortalRxOctetsEntry 7 }

		
		-- 1.3.6.1.4.1.388.11.2.4.2.100.4.1.8
		ccPortalRxOctetsAt18Mb OBJECT-TYPE
			SYNTAX Counter32
			MAX-ACCESS read-only
			STATUS current
			DESCRIPTION
				"Number of octets received via this Portal at 18 Mb."
			::= { ccPortalRxOctetsEntry 8 }

		
		-- 1.3.6.1.4.1.388.11.2.4.2.100.4.1.9
		ccPortalRxOctetsAt22Mb OBJECT-TYPE
			SYNTAX Counter32
			MAX-ACCESS read-only
			STATUS current
			DESCRIPTION
				"Number of octets received via this Portal at 22 Mb."
			::= { ccPortalRxOctetsEntry 9 }

		
		-- 1.3.6.1.4.1.388.11.2.4.2.100.4.1.10
		ccPortalRxOctetsAt24Mb OBJECT-TYPE
			SYNTAX Counter32
			MAX-ACCESS read-only
			STATUS current
			DESCRIPTION
				"Number of octets received via this Portal at 24 Mb."
			::= { ccPortalRxOctetsEntry 10 }

		
		-- 1.3.6.1.4.1.388.11.2.4.2.100.4.1.11
		ccPortalRxOctetsAt36Mb OBJECT-TYPE
			SYNTAX Counter32
			MAX-ACCESS read-only
			STATUS current
			DESCRIPTION
				"Number of octets received via this Portal at 36 Mb."
			::= { ccPortalRxOctetsEntry 11 }

		
		-- 1.3.6.1.4.1.388.11.2.4.2.100.4.1.12
		ccPortalRxOctetsAt48Mb OBJECT-TYPE
			SYNTAX Counter32
			MAX-ACCESS read-only
			STATUS current
			DESCRIPTION
				"Number of octets received via this Portal at 48 Mb."
			::= { ccPortalRxOctetsEntry 12 }

		
		-- 1.3.6.1.4.1.388.11.2.4.2.100.4.1.13
		ccPortalRxOctetsAt54Mb OBJECT-TYPE
			SYNTAX Counter32
			MAX-ACCESS read-only
			STATUS current
			DESCRIPTION
				"Number of octets received via this Portal at 54 Mb."
			::= { ccPortalRxOctetsEntry 13 }

		
		-- 1.3.6.1.4.1.388.11.2.4.2.100.5
		ccPortalTxOctetsTable OBJECT-TYPE
			SYNTAX SEQUENCE OF CcPortalTxOctetsEntry
			MAX-ACCESS not-accessible
			STATUS current
			DESCRIPTION
				"For each Portal on this switch, this table 
				describes counts of octets transmitted at each 
				possible speed, (1Mb, 2Mb, 5.5Mb, 6Mb...)."
			::= { ccPortalRfSum 5 }

		
		-- 1.3.6.1.4.1.388.11.2.4.2.100.5.1
		ccPortalTxOctetsEntry OBJECT-TYPE
			SYNTAX CcPortalTxOctetsEntry
			MAX-ACCESS not-accessible
			STATUS current
			DESCRIPTION
				" "
			INDEX { ccPortalIndex }
			::= { ccPortalTxOctetsTable 1 }

		
		CcPortalTxOctetsEntry ::=
			SEQUENCE { 
				ccPortalTxOctetsAt1Mb
					Counter32,
				ccPortalTxOctetsAt2Mb
					Counter32,
				ccPortalTxOctetsAt5pt5Mb
					Counter32,
				ccPortalTxOctetsAt6Mb
					Counter32,
				ccPortalTxOctetsAt9Mb
					Counter32,
				ccPortalTxOctetsAt11Mb
					Counter32,
				ccPortalTxOctetsAt12Mb
					Counter32,
				ccPortalTxOctetsAt18Mb
					Counter32,
				ccPortalTxOctetsAt22Mb
					Counter32,
				ccPortalTxOctetsAt24Mb
					Counter32,
				ccPortalTxOctetsAt36Mb
					Counter32,
				ccPortalTxOctetsAt48Mb
					Counter32,
				ccPortalTxOctetsAt54Mb
					Counter32
			 }

		-- 1.3.6.1.4.1.388.11.2.4.2.100.5.1.1
		ccPortalTxOctetsAt1Mb OBJECT-TYPE
			SYNTAX Counter32
			MAX-ACCESS read-only
			STATUS current
			DESCRIPTION
				"Number octets transmitted via this Portal at 1 Mb."
			::= { ccPortalTxOctetsEntry 1 }

		
		-- 1.3.6.1.4.1.388.11.2.4.2.100.5.1.2
		ccPortalTxOctetsAt2Mb OBJECT-TYPE
			SYNTAX Counter32
			MAX-ACCESS read-only
			STATUS current
			DESCRIPTION
				"Number octets transmitted via this Portal at 2 Mb."
			::= { ccPortalTxOctetsEntry 2 }

		
		-- 1.3.6.1.4.1.388.11.2.4.2.100.5.1.3
		ccPortalTxOctetsAt5pt5Mb OBJECT-TYPE
			SYNTAX Counter32
			MAX-ACCESS read-only
			STATUS current
			DESCRIPTION
				"Number octets transmitted via this Portal at 5.5 Mb."
			::= { ccPortalTxOctetsEntry 3 }

		
		-- 1.3.6.1.4.1.388.11.2.4.2.100.5.1.4
		ccPortalTxOctetsAt6Mb OBJECT-TYPE
			SYNTAX Counter32
			MAX-ACCESS read-only
			STATUS current
			DESCRIPTION
				"Number octets transmitted via this Portal at 6 Mb."
			::= { ccPortalTxOctetsEntry 4 }

		
		-- 1.3.6.1.4.1.388.11.2.4.2.100.5.1.5
		ccPortalTxOctetsAt9Mb OBJECT-TYPE
			SYNTAX Counter32
			MAX-ACCESS read-only
			STATUS current
			DESCRIPTION
				"Number octets transmitted via this Portal at 9 Mb."
			::= { ccPortalTxOctetsEntry 5 }

		
		-- 1.3.6.1.4.1.388.11.2.4.2.100.5.1.6
		ccPortalTxOctetsAt11Mb OBJECT-TYPE
			SYNTAX Counter32
			MAX-ACCESS read-only
			STATUS current
			DESCRIPTION
				"Number octets transmitted via this Portal at 11 Mb."
			::= { ccPortalTxOctetsEntry 6 }

		
		-- 1.3.6.1.4.1.388.11.2.4.2.100.5.1.7
		ccPortalTxOctetsAt12Mb OBJECT-TYPE
			SYNTAX Counter32
			MAX-ACCESS read-only
			STATUS current
			DESCRIPTION
				"Number octets transmitted via this Portal at 12 Mb."
			::= { ccPortalTxOctetsEntry 7 }

		
		-- 1.3.6.1.4.1.388.11.2.4.2.100.5.1.8
		ccPortalTxOctetsAt18Mb OBJECT-TYPE
			SYNTAX Counter32
			MAX-ACCESS read-only
			STATUS current
			DESCRIPTION
				"Number octets transmitted via this Portal at 18 Mb."
			::= { ccPortalTxOctetsEntry 8 }

		
		-- 1.3.6.1.4.1.388.11.2.4.2.100.5.1.9
		ccPortalTxOctetsAt22Mb OBJECT-TYPE
			SYNTAX Counter32
			MAX-ACCESS read-only
			STATUS current
			DESCRIPTION
				"Number octets transmitted via this Portal at 22 Mb."
			::= { ccPortalTxOctetsEntry 9 }

		
		-- 1.3.6.1.4.1.388.11.2.4.2.100.5.1.10
		ccPortalTxOctetsAt24Mb OBJECT-TYPE
			SYNTAX Counter32
			MAX-ACCESS read-only
			STATUS current
			DESCRIPTION
				"Number octets transmitted via this Portal at 24 Mb."
			::= { ccPortalTxOctetsEntry 10 }

		
		-- 1.3.6.1.4.1.388.11.2.4.2.100.5.1.11
		ccPortalTxOctetsAt36Mb OBJECT-TYPE
			SYNTAX Counter32
			MAX-ACCESS read-only
			STATUS current
			DESCRIPTION
				"Number octets transmitted via this Portal at 36 Mb."
			::= { ccPortalTxOctetsEntry 11 }

		
		-- 1.3.6.1.4.1.388.11.2.4.2.100.5.1.12
		ccPortalTxOctetsAt48Mb OBJECT-TYPE
			SYNTAX Counter32
			MAX-ACCESS read-only
			STATUS current
			DESCRIPTION
				"Number octets transmitted via this Portal at 48 Mb."
			::= { ccPortalTxOctetsEntry 12 }

		
		-- 1.3.6.1.4.1.388.11.2.4.2.100.5.1.13
		ccPortalTxOctetsAt54Mb OBJECT-TYPE
			SYNTAX Counter32
			MAX-ACCESS read-only
			STATUS current
			DESCRIPTION
				"Number octets transmitted via this Portal at 54 Mb."
			::= { ccPortalTxOctetsEntry 13 }

		
		-- 1.3.6.1.4.1.388.11.2.4.2.100.6
		ccPortalTxRetriesPktsTable OBJECT-TYPE
			SYNTAX SEQUENCE OF CcPortalTxRetriesPktsEntry
			MAX-ACCESS not-accessible
			STATUS current
			DESCRIPTION
				"For each Portal on the switch, this table describes 
				counts of the number of packets affected by transmit 
				retries, (no retries, 1 retry, 2 retries,... gave-up)."
			::= { ccPortalRfSum 6 }

		
		-- 1.3.6.1.4.1.388.11.2.4.2.100.6.1
		ccPortalTxRetriesPktsEntry OBJECT-TYPE
			SYNTAX CcPortalTxRetriesPktsEntry
			MAX-ACCESS not-accessible
			STATUS current
			DESCRIPTION
				" "
			INDEX { ccPortalIndex }
			::= { ccPortalTxRetriesPktsTable 1 }

		
		CcPortalTxRetriesPktsEntry ::=
			SEQUENCE { 
				ccPortalTxRetriesPktsNone
					Counter32,
				ccPortalTxRetriesPkts01
					Counter32,
				ccPortalTxRetriesPkts02
					Counter32,
				ccPortalTxRetriesPkts03
					Counter32,
				ccPortalTxRetriesPkts04
					Counter32,
				ccPortalTxRetriesPkts05
					Counter32,
				ccPortalTxRetriesPkts06
					Counter32,
				ccPortalTxRetriesPkts07
					Counter32,
				ccPortalTxRetriesPkts08
					Counter32,
				ccPortalTxRetriesPkts09
					Counter32,
				ccPortalTxRetriesPkts10
					Counter32,
				ccPortalTxRetriesPkts11
					Counter32,
				ccPortalTxRetriesPkts12
					Counter32,
				ccPortalTxRetriesPkts13
					Counter32,
				ccPortalTxRetriesPkts14
					Counter32,
				ccPortalTxRetriesPkts15
					Counter32,
				ccPortalTxRetriesPktsFailed
					Counter32
			 }

		-- 1.3.6.1.4.1.388.11.2.4.2.100.6.1.1
		ccPortalTxRetriesPktsNone OBJECT-TYPE
			SYNTAX Counter32
			MAX-ACCESS read-only
			STATUS current
			DESCRIPTION
				"Number of pkts successfully transmitted via this
				Portal with no retries."
			::= { ccPortalTxRetriesPktsEntry 1 }

		
		-- 1.3.6.1.4.1.388.11.2.4.2.100.6.1.2
		ccPortalTxRetriesPkts01 OBJECT-TYPE
			SYNTAX Counter32
			MAX-ACCESS read-only
			STATUS current
			DESCRIPTION
				"Number of pkts successfully transmitted via this
				Portal with exactly 1 retry."
			::= { ccPortalTxRetriesPktsEntry 2 }

		
		-- 1.3.6.1.4.1.388.11.2.4.2.100.6.1.3
		ccPortalTxRetriesPkts02 OBJECT-TYPE
			SYNTAX Counter32
			MAX-ACCESS read-only
			STATUS current
			DESCRIPTION
				"Number of pkts successfully transmitted via this
				Portal with exactly 2 retries."
			::= { ccPortalTxRetriesPktsEntry 3 }

		
		-- 1.3.6.1.4.1.388.11.2.4.2.100.6.1.4
		ccPortalTxRetriesPkts03 OBJECT-TYPE
			SYNTAX Counter32
			MAX-ACCESS read-only
			STATUS current
			DESCRIPTION
				"Number of pkts successfully transmitted via this
				Portal with exactly 3 retries."
			::= { ccPortalTxRetriesPktsEntry 4 }

		
		-- 1.3.6.1.4.1.388.11.2.4.2.100.6.1.5
		ccPortalTxRetriesPkts04 OBJECT-TYPE
			SYNTAX Counter32
			MAX-ACCESS read-only
			STATUS current
			DESCRIPTION
				"Number of pkts successfully transmitted via this
				Portal with exactly 4 retries."
			::= { ccPortalTxRetriesPktsEntry 5 }

		
		-- 1.3.6.1.4.1.388.11.2.4.2.100.6.1.6
		ccPortalTxRetriesPkts05 OBJECT-TYPE
			SYNTAX Counter32
			MAX-ACCESS read-only
			STATUS current
			DESCRIPTION
				"Number of pkts successfully transmitted via this
				Portal with exactly 5 retries."
			::= { ccPortalTxRetriesPktsEntry 6 }

		
		-- 1.3.6.1.4.1.388.11.2.4.2.100.6.1.7
		ccPortalTxRetriesPkts06 OBJECT-TYPE
			SYNTAX Counter32
			MAX-ACCESS read-only
			STATUS current
			DESCRIPTION
				"Number of pkts successfully transmitted via this
				Portal with exactly 6 retries."
			::= { ccPortalTxRetriesPktsEntry 7 }

		
		-- 1.3.6.1.4.1.388.11.2.4.2.100.6.1.8
		ccPortalTxRetriesPkts07 OBJECT-TYPE
			SYNTAX Counter32
			MAX-ACCESS read-only
			STATUS current
			DESCRIPTION
				"Number of pkts successfully transmitted via this
				Portal with exactly 7 retries."
			::= { ccPortalTxRetriesPktsEntry 8 }

		
		-- 1.3.6.1.4.1.388.11.2.4.2.100.6.1.9
		ccPortalTxRetriesPkts08 OBJECT-TYPE
			SYNTAX Counter32
			MAX-ACCESS read-only
			STATUS current
			DESCRIPTION
				"Number of pkts successfully transmitted via this
				Portal with exactly 8 retries."
			::= { ccPortalTxRetriesPktsEntry 9 }

		
		-- 1.3.6.1.4.1.388.11.2.4.2.100.6.1.10
		ccPortalTxRetriesPkts09 OBJECT-TYPE
			SYNTAX Counter32
			MAX-ACCESS read-only
			STATUS current
			DESCRIPTION
				"Number of pkts successfully transmitted via this
				Portal with exactly 9 retries."
			::= { ccPortalTxRetriesPktsEntry 10 }

		
		-- 1.3.6.1.4.1.388.11.2.4.2.100.6.1.11
		ccPortalTxRetriesPkts10 OBJECT-TYPE
			SYNTAX Counter32
			MAX-ACCESS read-only
			STATUS current
			DESCRIPTION
				"Number of pkts successfully transmitted via this
				Portal with exactly 10 retries."
			::= { ccPortalTxRetriesPktsEntry 11 }

		
		-- 1.3.6.1.4.1.388.11.2.4.2.100.6.1.12
		ccPortalTxRetriesPkts11 OBJECT-TYPE
			SYNTAX Counter32
			MAX-ACCESS read-only
			STATUS current
			DESCRIPTION
				"Number of pkts successfully transmitted via this
				Portal with exactly 11 retries."
			::= { ccPortalTxRetriesPktsEntry 12 }

		
		-- 1.3.6.1.4.1.388.11.2.4.2.100.6.1.13
		ccPortalTxRetriesPkts12 OBJECT-TYPE
			SYNTAX Counter32
			MAX-ACCESS read-only
			STATUS current
			DESCRIPTION
				"Number of pkts successfully transmitted via this
				Portal with exactly 12 retries."
			::= { ccPortalTxRetriesPktsEntry 13 }

		
		-- 1.3.6.1.4.1.388.11.2.4.2.100.6.1.14
		ccPortalTxRetriesPkts13 OBJECT-TYPE
			SYNTAX Counter32
			MAX-ACCESS read-only
			STATUS current
			DESCRIPTION
				"Number of pkts successfully transmitted via this
				Portal with exactly 13 retries."
			::= { ccPortalTxRetriesPktsEntry 14 }

		
		-- 1.3.6.1.4.1.388.11.2.4.2.100.6.1.15
		ccPortalTxRetriesPkts14 OBJECT-TYPE
			SYNTAX Counter32
			MAX-ACCESS read-only
			STATUS current
			DESCRIPTION
				"Number of pkts successfully transmitted via this
				Portal with exactly 14 retries."
			::= { ccPortalTxRetriesPktsEntry 15 }

		
		-- 1.3.6.1.4.1.388.11.2.4.2.100.6.1.16
		ccPortalTxRetriesPkts15 OBJECT-TYPE
			SYNTAX Counter32
			MAX-ACCESS read-only
			STATUS current
			DESCRIPTION
				"Number of pkts successfully transmitted via this
				Portal with exactly 15 retries."
			::= { ccPortalTxRetriesPktsEntry 16 }

		
		-- 1.3.6.1.4.1.388.11.2.4.2.100.6.1.17
		ccPortalTxRetriesPktsFailed OBJECT-TYPE
			SYNTAX Counter32
			MAX-ACCESS read-only
			STATUS current
			DESCRIPTION
				"Number of pkts that never were successfully 
				transmitted to via this Portal because the max retry
				count was exceeded."
			::= { ccPortalTxRetriesPktsEntry 17 }

		
		-- 1.3.6.1.4.1.388.11.2.4.2.100.7
		ccPortalTxRetriesOctetsTable OBJECT-TYPE
			SYNTAX SEQUENCE OF CcPortalTxRetriesOctetsEntry
			MAX-ACCESS not-accessible
			STATUS current
			DESCRIPTION
				"For each Portal on the switch, this table describes 
				counts of the number of octets affected by transmit 
				retries, (no retries, 1 retry, 2 retries,... gave-up)."
			::= { ccPortalRfSum 7 }

		
		-- 1.3.6.1.4.1.388.11.2.4.2.100.7.1
		ccPortalTxRetriesOctetsEntry OBJECT-TYPE
			SYNTAX CcPortalTxRetriesOctetsEntry
			MAX-ACCESS not-accessible
			STATUS current
			DESCRIPTION
				" "
			INDEX { ccPortalIndex }
			::= { ccPortalTxRetriesOctetsTable 1 }

		
		CcPortalTxRetriesOctetsEntry ::=
			SEQUENCE { 
				ccPortalTxRetriesOctetsNone
					Counter32,
				ccPortalTxRetriesOctets01
					Counter32,
				ccPortalTxRetriesOctets02
					Counter32,
				ccPortalTxRetriesOctets03
					Counter32,
				ccPortalTxRetriesOctets04
					Counter32,
				ccPortalTxRetriesOctets05
					Counter32,
				ccPortalTxRetriesOctets06
					Counter32,
				ccPortalTxRetriesOctets07
					Counter32,
				ccPortalTxRetriesOctets08
					Counter32,
				ccPortalTxRetriesOctets09
					Counter32,
				ccPortalTxRetriesOctets10
					Counter32,
				ccPortalTxRetriesOctets11
					Counter32,
				ccPortalTxRetriesOctets12
					Counter32,
				ccPortalTxRetriesOctets13
					Counter32,
				ccPortalTxRetriesOctets14
					Counter32,
				ccPortalTxRetriesOctets15
					Counter32,
				ccPortalTxRetriesOctetsFailed
					Counter32
			 }

		-- 1.3.6.1.4.1.388.11.2.4.2.100.7.1.1
		ccPortalTxRetriesOctetsNone OBJECT-TYPE
			SYNTAX Counter32
			MAX-ACCESS read-only
			STATUS current
			DESCRIPTION
				"Number of octets successfully transmitted via this
				Portal with no retries."
			::= { ccPortalTxRetriesOctetsEntry 1 }

		
		-- 1.3.6.1.4.1.388.11.2.4.2.100.7.1.2
		ccPortalTxRetriesOctets01 OBJECT-TYPE
			SYNTAX Counter32
			MAX-ACCESS read-only
			STATUS current
			DESCRIPTION
				"Number of octets successfully transmitted via this
				Portal with exactly 1 retry."
			::= { ccPortalTxRetriesOctetsEntry 2 }

		
		-- 1.3.6.1.4.1.388.11.2.4.2.100.7.1.3
		ccPortalTxRetriesOctets02 OBJECT-TYPE
			SYNTAX Counter32
			MAX-ACCESS read-only
			STATUS current
			DESCRIPTION
				"Number of octets successfully transmitted via this
				Portal with exactly 2 retries."
			::= { ccPortalTxRetriesOctetsEntry 3 }

		
		-- 1.3.6.1.4.1.388.11.2.4.2.100.7.1.4
		ccPortalTxRetriesOctets03 OBJECT-TYPE
			SYNTAX Counter32
			MAX-ACCESS read-only
			STATUS current
			DESCRIPTION
				"Number of octets successfully transmitted via this
				Portal with exactly 3 retries."
			::= { ccPortalTxRetriesOctetsEntry 4 }

		
		-- 1.3.6.1.4.1.388.11.2.4.2.100.7.1.5
		ccPortalTxRetriesOctets04 OBJECT-TYPE
			SYNTAX Counter32
			MAX-ACCESS read-only
			STATUS current
			DESCRIPTION
				"Number of octets successfully transmitted via this
				Portal with exactly 4 retries."
			::= { ccPortalTxRetriesOctetsEntry 5 }

		
		-- 1.3.6.1.4.1.388.11.2.4.2.100.7.1.6
		ccPortalTxRetriesOctets05 OBJECT-TYPE
			SYNTAX Counter32
			MAX-ACCESS read-only
			STATUS current
			DESCRIPTION
				"Number of octets successfully transmitted via this
				Portal with exactly 5 retries."
			::= { ccPortalTxRetriesOctetsEntry 6 }

		
		-- 1.3.6.1.4.1.388.11.2.4.2.100.7.1.7
		ccPortalTxRetriesOctets06 OBJECT-TYPE
			SYNTAX Counter32
			MAX-ACCESS read-only
			STATUS current
			DESCRIPTION
				"Number of octets successfully transmitted via this
				Portal with exactly 6 retries."
			::= { ccPortalTxRetriesOctetsEntry 7 }

		
		-- 1.3.6.1.4.1.388.11.2.4.2.100.7.1.8
		ccPortalTxRetriesOctets07 OBJECT-TYPE
			SYNTAX Counter32
			MAX-ACCESS read-only
			STATUS current
			DESCRIPTION
				"Number of octets successfully transmitted via this
				Portal with exactly 7 retries."
			::= { ccPortalTxRetriesOctetsEntry 8 }

		
		-- 1.3.6.1.4.1.388.11.2.4.2.100.7.1.9
		ccPortalTxRetriesOctets08 OBJECT-TYPE
			SYNTAX Counter32
			MAX-ACCESS read-only
			STATUS current
			DESCRIPTION
				"Number of octets successfully transmitted via this
				Portal with exactly 8 retries."
			::= { ccPortalTxRetriesOctetsEntry 9 }

		
		-- 1.3.6.1.4.1.388.11.2.4.2.100.7.1.10
		ccPortalTxRetriesOctets09 OBJECT-TYPE
			SYNTAX Counter32
			MAX-ACCESS read-only
			STATUS current
			DESCRIPTION
				"Number of octets successfully transmitted via this
				Portal with exactly 9 retries."
			::= { ccPortalTxRetriesOctetsEntry 10 }

		
		-- 1.3.6.1.4.1.388.11.2.4.2.100.7.1.11
		ccPortalTxRetriesOctets10 OBJECT-TYPE
			SYNTAX Counter32
			MAX-ACCESS read-only
			STATUS current
			DESCRIPTION
				"Number of octets successfully transmitted via this
				Portal with exactly 10 retries."
			::= { ccPortalTxRetriesOctetsEntry 11 }

		
		-- 1.3.6.1.4.1.388.11.2.4.2.100.7.1.12
		ccPortalTxRetriesOctets11 OBJECT-TYPE
			SYNTAX Counter32
			MAX-ACCESS read-only
			STATUS current
			DESCRIPTION
				"Number of octets successfully transmitted via this
				Portal with exactly 11 retries."
			::= { ccPortalTxRetriesOctetsEntry 12 }

		
		-- 1.3.6.1.4.1.388.11.2.4.2.100.7.1.13
		ccPortalTxRetriesOctets12 OBJECT-TYPE
			SYNTAX Counter32
			MAX-ACCESS read-only
			STATUS current
			DESCRIPTION
				"Number of octets successfully transmitted via this
				Portal with exactly 12 retries."
			::= { ccPortalTxRetriesOctetsEntry 13 }

		
		-- 1.3.6.1.4.1.388.11.2.4.2.100.7.1.14
		ccPortalTxRetriesOctets13 OBJECT-TYPE
			SYNTAX Counter32
			MAX-ACCESS read-only
			STATUS current
			DESCRIPTION
				"Number of octets successfully transmitted via this
				Portal with exactly 13 retries."
			::= { ccPortalTxRetriesOctetsEntry 14 }

		
		-- 1.3.6.1.4.1.388.11.2.4.2.100.7.1.15
		ccPortalTxRetriesOctets14 OBJECT-TYPE
			SYNTAX Counter32
			MAX-ACCESS read-only
			STATUS current
			DESCRIPTION
				"Number of octets successfully transmitted via this
				Portal with exactly 14 retries."
			::= { ccPortalTxRetriesOctetsEntry 15 }

		
		-- 1.3.6.1.4.1.388.11.2.4.2.100.7.1.16
		ccPortalTxRetriesOctets15 OBJECT-TYPE
			SYNTAX Counter32
			MAX-ACCESS read-only
			STATUS current
			DESCRIPTION
				"Number of octets successfully transmitted via this
				Portal with exactly 15 retries."
			::= { ccPortalTxRetriesOctetsEntry 16 }

		
		-- 1.3.6.1.4.1.388.11.2.4.2.100.7.1.17
		ccPortalTxRetriesOctetsFailed OBJECT-TYPE
			SYNTAX Counter32
			MAX-ACCESS read-only
			STATUS current
			DESCRIPTION
				"Number of octets that never were successfully 
				transmitted to via this Portal because the max retry
				count was exceeded."
			::= { ccPortalTxRetriesOctetsEntry 17 }

		
-- ??-TW: Note that these values have been split-out from the
-- _StatsTable for Portal/MU/WLAN.  The resulting new tables
-- _SigStatsTable for Portal/MU/WLAN are symmetrical, but they
-- have been added before other v1.5 tables, and so have 
-- caused their location to move.
-- 
-- Also, note that the four RSSI values still remain in the 
-- ccMuStats table, since to delete them would be an 
-- inconsistant change.  For symmetry, they have been 
-- duplicated.
		-- 1.3.6.1.4.1.388.11.2.4.2.100.8
		ccPortalSigStatsTable OBJECT-TYPE
			SYNTAX SEQUENCE OF CcPortalSigStatsEntry
			MAX-ACCESS not-accessible
			STATUS current
			DESCRIPTION
				"This table describes statistics about RSSI, Signal, Noise,
				and SNR for packets recieved via each Portal on the switch."
			::= { ccPortalRfSum 8 }

		
		-- 1.3.6.1.4.1.388.11.2.4.2.100.8.1
		ccPortalSigStatsEntry OBJECT-TYPE
			SYNTAX CcPortalSigStatsEntry
			MAX-ACCESS not-accessible
			STATUS current
			DESCRIPTION
				" "
			INDEX { ccPortalIndex }
			::= { ccPortalSigStatsTable 1 }

		
		CcPortalSigStatsEntry ::=
			SEQUENCE { 
				ccPortalSigStatsNumPkts
					Counter32,
				ccPortalSigStatsSignalBest
					Integer32,
				ccPortalSigStatsSignalWorst
					Integer32,
				ccPortalSigStatsSignalSum
					Integer32,
				ccPortalSigStatsSignalSumSquares
					Counter64,
				ccPortalSigStatsSignalMostRecent
					Integer32,
				ccPortalSigStatsNoiseBest
					Integer32,
				ccPortalSigStatsNoiseWorst
					Integer32,
				ccPortalSigStatsNoiseSum
					Integer32,
				ccPortalSigStatsNoiseSumSquares
					Counter64,
				ccPortalSigStatsNoiseMostRecent
					Integer32,
				ccPortalSigStatsSnrBest
					Integer32,
				ccPortalSigStatsSnrWorst
					Integer32,
				ccPortalSigStatsSnrSum
					Integer32,
				ccPortalSigStatsSnrSumSquares
					Counter64,
				ccPortalSigStatsSnrMostRecent
					Integer32
			 }

		-- 1.3.6.1.4.1.388.11.2.4.2.100.8.1.1
		ccPortalSigStatsNumPkts OBJECT-TYPE
			SYNTAX Counter32
			MAX-ACCESS read-only
			STATUS current
			DESCRIPTION
				"Total packets received via the Portal included in
				all the other counters reported in this row."
			::= { ccPortalSigStatsEntry 1 }

		
		-- 1.3.6.1.4.1.388.11.2.4.2.100.8.1.2
		ccPortalSigStatsSignalBest OBJECT-TYPE
			SYNTAX Integer32
			UNITS "dBm"
			MAX-ACCESS read-only
			STATUS current
			DESCRIPTION
				"The best Signal value seen from the Portal so far.
				(Remember that a -20dBm Signal is better than -60dBm).
				
				This value is initialized to -500dBm.
				"
			::= { ccPortalSigStatsEntry 2 }

		
		-- 1.3.6.1.4.1.388.11.2.4.2.100.8.1.3
		ccPortalSigStatsSignalWorst OBJECT-TYPE
			SYNTAX Integer32
			UNITS "dBm"
			MAX-ACCESS read-only
			STATUS current
			DESCRIPTION
				"The worst Signal value seen from the Portal so far.
				(Remember that a -80dBm Signal is worse than -60dBm).
				
				This value is initialized to 500dBm."
			::= { ccPortalSigStatsEntry 3 }

		
		-- 1.3.6.1.4.1.388.11.2.4.2.100.8.1.4
		ccPortalSigStatsSignalSum OBJECT-TYPE
			SYNTAX Integer32
			UNITS "dBm"
			MAX-ACCESS read-only
			STATUS current
			DESCRIPTION
				"A running sum of all Signal values calculated by the
				switch (using reported RSSI values), for packets 
				received via this Portal.
				
				Note that this value is normally a negative value
				ranging from -10dBm to -80dBm.  It is possible for this
				value to be positive, but that would be rare, and would
				signal an exceptionally strong signal.
				
				(This value divided by ccPortalSigStatsNumPkts yields
				the average Signal value for all packets received
				from this MU)."
			::= { ccPortalSigStatsEntry 4 }

		
		-- 1.3.6.1.4.1.388.11.2.4.2.100.8.1.5
		ccPortalSigStatsSignalSumSquares OBJECT-TYPE
			SYNTAX Counter64
			UNITS "dBm"
			MAX-ACCESS read-only
			STATUS current
			DESCRIPTION
				"A sum of the squares of each Signal value calculated
				for packets received via this Portal.
				
				Unlike _SignalSum, this value is never negative, since
				the square of a negative number is a positive.
				
				(This value can be used to calculate the standard
				deviation for Signal values calculated for packets
				from this Portal)."
			::= { ccPortalSigStatsEntry 5 }

		
		-- 1.3.6.1.4.1.388.11.2.4.2.100.8.1.6
		ccPortalSigStatsSignalMostRecent OBJECT-TYPE
			SYNTAX Integer32
			UNITS "dBm"
			MAX-ACCESS read-only
			STATUS current
			DESCRIPTION
				"The best Signal value seen from the Portal so far.
				(Remember that a -20dBm Signal is better than -60dBm).
				
				This value does not make sense when ccPortalSigStatsNumPkts 
				equals to 0."
			::= { ccPortalSigStatsEntry 6 }

		
		-- 1.3.6.1.4.1.388.11.2.4.2.100.8.1.7
		ccPortalSigStatsNoiseBest OBJECT-TYPE
			SYNTAX Integer32
			UNITS "dBm"
			MAX-ACCESS read-only
			STATUS current
			DESCRIPTION
				"The best Noise value seen from the Portal so far.
				(Remember that -80dBm Noise is better than -70dBm).
				
				This value is initialized to 500dBm."
			::= { ccPortalSigStatsEntry 7 }

		
		-- 1.3.6.1.4.1.388.11.2.4.2.100.8.1.8
		ccPortalSigStatsNoiseWorst OBJECT-TYPE
			SYNTAX Integer32
			UNITS "dBm"
			MAX-ACCESS read-only
			STATUS current
			DESCRIPTION
				"The worst Noise value seen from the Portal so far.
				(Remember that -50dBm Noise is worse than -60dBm).
				
				This value is initialized to -500dBm."
			::= { ccPortalSigStatsEntry 8 }

		
		-- 1.3.6.1.4.1.388.11.2.4.2.100.8.1.9
		ccPortalSigStatsNoiseSum OBJECT-TYPE
			SYNTAX Integer32
			UNITS "dBm"
			MAX-ACCESS read-only
			STATUS current
			DESCRIPTION
				"A running sum of all Noise values calculated by the
				switch (using reported RSSI values), for packets
				received via this Portal.
				
				Like _SignalSum, this value is normally a negative value.
				
				(This value divided by ccPortalSigStatsNumPkts yields
				the average Noise value for all packets received
				from this MU)."
			::= { ccPortalSigStatsEntry 9 }

		
		-- 1.3.6.1.4.1.388.11.2.4.2.100.8.1.10
		ccPortalSigStatsNoiseSumSquares OBJECT-TYPE
			SYNTAX Counter64
			UNITS "dBm"
			MAX-ACCESS read-only
			STATUS current
			DESCRIPTION
				"A sum of the squares of each Noise value calculated
				for packets received via this Portal.
				
				As with _SignalSumSquares, this value is never negative.
				
				(This value can be used to calculate the standard
				deviation for Noise values calculated for packets
				from this Portal)."
			::= { ccPortalSigStatsEntry 10 }

		
		-- 1.3.6.1.4.1.388.11.2.4.2.100.8.1.11
		ccPortalSigStatsNoiseMostRecent OBJECT-TYPE
			SYNTAX Integer32
			UNITS "dBm"
			MAX-ACCESS read-only
			STATUS current
			DESCRIPTION
				"The best Noise value seen from the Portal so far.
				(Remember that -80dBm Noise is better than -70dBm).
				
				This value does not make sense when ccPortalSigStatsNumPkts 
				equals to 0."
			::= { ccPortalSigStatsEntry 11 }

		
		-- 1.3.6.1.4.1.388.11.2.4.2.100.8.1.12
		ccPortalSigStatsSnrBest OBJECT-TYPE
			SYNTAX Integer32
			UNITS "dB"
			MAX-ACCESS read-only
			STATUS current
			DESCRIPTION
				"The best SNR value seen from the Portal so far.
				(Remember that +30dBm SNR is better than +20dBm).
				
				This value is initialized to -500dB."
			::= { ccPortalSigStatsEntry 12 }

		
		-- 1.3.6.1.4.1.388.11.2.4.2.100.8.1.13
		ccPortalSigStatsSnrWorst OBJECT-TYPE
			SYNTAX Integer32
			UNITS "dB"
			MAX-ACCESS read-only
			STATUS current
			DESCRIPTION
				"The worst SNR value seen from the Portal so far.
				(Remember that +10dBm SNR is worse than +20dBm).
				
				This value is initialized to 500dB."
			::= { ccPortalSigStatsEntry 13 }

		
		-- 1.3.6.1.4.1.388.11.2.4.2.100.8.1.14
		ccPortalSigStatsSnrSum OBJECT-TYPE
			SYNTAX Integer32
			UNITS "dB"
			MAX-ACCESS read-only
			STATUS current
			DESCRIPTION
				"A running sum of all SNR values calculated by the
				switch (using reported RSSI values), for packets 
				received via this Portal.
				
				Unlike _Signal and _Noise, this value is never negative.
				
				(This value divided by ccPortalSigStatsNumPkts yields
				the average SNR value for all packets received
				from this MU)."
			::= { ccPortalSigStatsEntry 14 }

		
		-- 1.3.6.1.4.1.388.11.2.4.2.100.8.1.15
		ccPortalSigStatsSnrSumSquares OBJECT-TYPE
			SYNTAX Counter64
			UNITS "dB"
			MAX-ACCESS read-only
			STATUS current
			DESCRIPTION
				"A sum of the squares of each SNR value calculated
				for packets received via this Portal.
				
				This value is never negative.
				
				(This value can be used to calculate the standard
				deviation for SNR values calculated for packets
				from this Portal)."
			::= { ccPortalSigStatsEntry 15 }

		
		-- 1.3.6.1.4.1.388.11.2.4.2.100.8.1.16
		ccPortalSigStatsSnrMostRecent OBJECT-TYPE
			SYNTAX Integer32
			UNITS "dB"
			MAX-ACCESS read-only
			STATUS current
			DESCRIPTION
				"The best SNR value seen from the Portal so far.
				(Remember that +30dBm SNR is better than +20dBm).
				
				This value does not make sense when ccPortalSigStatsNumPkts 
				equals to 0."
			::= { ccPortalSigStatsEntry 16 }

		
		-- 1.3.6.1.4.1.388.11.2.4.2.100.9
		ccPortalSumStatsShortTable OBJECT-TYPE
			SYNTAX SEQUENCE OF CcPortalSumStatsShortEntry
			MAX-ACCESS not-accessible
			STATUS current
			DESCRIPTION
				"Averages and rates calculated over the SHORT window for
				each Portal."
			::= { ccPortalRfSum 9 }

		
		-- 1.3.6.1.4.1.388.11.2.4.2.100.9.1
		ccPortalSumStatsShortEntry OBJECT-TYPE
			SYNTAX CcPortalSumStatsShortEntry
			MAX-ACCESS not-accessible
			STATUS current
			DESCRIPTION
				" "
			INDEX { ccPortalIndex }
			::= { ccPortalSumStatsShortTable 1 }

		
		CcPortalSumStatsShortEntry ::=
			SEQUENCE { 
				ccPortalSumStatsShortTimestamp
					TimeTicks,
				ccPortalSumStatsShortNumPkts
					Unsigned32,
				ccPortalSumStatsShortPktsPerSec100
					ScaleBy100,
				ccPortalSumStatsShortPktsPerSecTx100
					ScaleBy100,
				ccPortalSumStatsShortPktsPerSecRx100
					ScaleBy100,
				ccPortalSumStatsShortThroughput
					Unsigned32,
				ccPortalSumStatsShortThroughputTx
					Unsigned32,
				ccPortalSumStatsShortThroughputRx
					Unsigned32,
				ccPortalSumStatsShortAvgBitSpeed
					Unsigned32,
				ccPortalSumStatsShortAvgMuSignal
					Integer32,
				ccPortalSumStatsShortAvgMuNoise
					Integer32,
				ccPortalSumStatsShortAvgMuSnr
					Integer32,
				ccPortalSumStatsShortPp10kNUcastPkts
					PartsPer10k,
				ccPortalSumStatsShortPp10kTxWithRetries
					PartsPer10k,
				ccPortalSumStatsShortPp10kTxMaxRetries
					PartsPer10k,
				ccPortalSumStatsShortTxAvgRetries100
					ScaleBy100,
				ccPortalSumStatsShortPp10kRxUndecrypt
					PartsPer10k,
				ccPortalSumStatsShortTotalMus
					Unsigned32,
				ccPortalSumStatsShortPp10kRfUtil
					PartsPer10k
			 }

		-- 1.3.6.1.4.1.388.11.2.4.2.100.9.1.1
		ccPortalSumStatsShortTimestamp OBJECT-TYPE
			SYNTAX TimeTicks
			MAX-ACCESS read-only
			STATUS current
			DESCRIPTION
				"Snapshot of sysUpTime as of the END of the 'window' of 
				time that this entry of values represents."
			::= { ccPortalSumStatsShortEntry 1 }

		
		-- 1.3.6.1.4.1.388.11.2.4.2.100.9.1.2
		ccPortalSumStatsShortNumPkts OBJECT-TYPE
			SYNTAX Unsigned32
			UNITS "packets"
			MAX-ACCESS read-only
			STATUS current
			DESCRIPTION
				"The number of packets used to calculate the statistics in
				this window."
			::= { ccPortalSumStatsShortEntry 2 }

		
		-- 1.3.6.1.4.1.388.11.2.4.2.100.9.1.3
		ccPortalSumStatsShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { ccPortalSumStatsShortEntry 3 }

		
		-- 1.3.6.1.4.1.388.11.2.4.2.100.9.1.4
		ccPortalSumStatsShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { ccPortalSumStatsShortEntry 4 }

		
		-- 1.3.6.1.4.1.388.11.2.4.2.100.9.1.5
		ccPortalSumStatsShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { ccPortalSumStatsShortEntry 5 }

		
		-- 1.3.6.1.4.1.388.11.2.4.2.100.9.1.6
		ccPortalSumStatsShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { ccPortalSumStatsShortEntry 6 }

		
		-- 1.3.6.1.4.1.388.11.2.4.2.100.9.1.7
		ccPortalSumStatsShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { ccPortalSumStatsShortEntry 7 }

		
		-- 1.3.6.1.4.1.388.11.2.4.2.100.9.1.8
		ccPortalSumStatsShortThroughputRx OBJECT-TYPE
			SYNTAX Unsigned32
			UNITS "bits per second"
			MAX-ACCESS read-only
			STATUS current
			DESCRIPTION
				"Actual number of bits RX over the window,
				divided by the number of seconds in the window."
			::= { ccPortalSumStatsShortEntry 8 }

		
		-- 1.3.6.1.4.1.388.11.2.4.2.100.9.1.9
		ccPortalSumStatsShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { ccPortalSumStatsShortEntry 9 }

		
		-- 1.3.6.1.4.1.388.11.2.4.2.100.9.1.10
		ccPortalSumStatsShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { ccPortalSumStatsShortEntry 10 }

		
		-- 1.3.6.1.4.1.388.11.2.4.2.100.9.1.11
		ccPortalSumStatsShortAvgMuNoise OBJECT-TYPE
			SYNTAX Integer32
			UNITS "dBm"
			MAX-ACCESS read-only
			STATUS current
			DESCRIPTION
				"The average of all noise values over the window."
			::= { ccPortalSumStatsShortEntry 11 }

		
		-- 1.3.6.1.4.1.388.11.2.4.2.100.9.1.12
		ccPortalSumStatsShortAvgMuSnr OBJECT-TYPE
			SYNTAX Integer32
			UNITS "dB"
			MAX-ACCESS read-only
			STATUS current
			DESCRIPTION
				"The average of all SNR values over the window."
			::= { ccPortalSumStatsShortEntry 12 }

		
		-- 1.3.6.1.4.1.388.11.2.4.2.100.9.1.13
		ccPortalSumStatsShortPp10kNUcastPkts OBJECT-TYPE
			SYNTAX PartsPer10k
			UNITS "parts-per-10000"
			MAX-ACCESS read-only
			STATUS current
			DESCRIPTION
				"Ratio of packets that were NOT unicast.
				
				Expressed as parts-per-10000.
				"
			::= { ccPortalSumStatsShortEntry 13 }

		
		-- 1.3.6.1.4.1.388.11.2.4.2.100.9.1.14
		ccPortalSumStatsShortPp10kTxWithRetries OBJECT-TYPE
			SYNTAX PartsPer10k
			UNITS "parts-per-10000"
			MAX-ACCESS read-only
			STATUS current
			DESCRIPTION
				"Ratio of TX packets that experienced one or more retries.
				
				Expressed as parts-per-10000.
				"
			::= { ccPortalSumStatsShortEntry 14 }

		
		-- 1.3.6.1.4.1.388.11.2.4.2.100.9.1.15
		ccPortalSumStatsShortPp10kTxMaxRetries OBJECT-TYPE
			SYNTAX PartsPer10k
			UNITS "parts-per-10000"
			MAX-ACCESS read-only
			STATUS current
			DESCRIPTION
				"Ratio of TX packets that were dropped due to excessive.
				
				Expressed as parts-per-10000.
				"
			::= { ccPortalSumStatsShortEntry 15 }

		
		-- 1.3.6.1.4.1.388.11.2.4.2.100.9.1.16
		ccPortalSumStatsShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { ccPortalSumStatsShortEntry 16 }

		
		-- 1.3.6.1.4.1.388.11.2.4.2.100.9.1.17
		ccPortalSumStatsShortPp10kRxUndecrypt OBJECT-TYPE
			SYNTAX PartsPer10k
			UNITS "parts-per-10000"
			MAX-ACCESS read-only
			STATUS current
			DESCRIPTION
				"Ratio of RX packets that were undecryptable.
				
				Expressed as parts-per-10000.
				"
			::= { ccPortalSumStatsShortEntry 17 }

		
		-- 1.3.6.1.4.1.388.11.2.4.2.100.9.1.18
		ccPortalSumStatsShortTotalMus OBJECT-TYPE
			SYNTAX Unsigned32 (0..100)
			UNITS "number of MUs"
			MAX-ACCESS read-only
			STATUS current
			DESCRIPTION
				"The total number of MUs associated to the given Portal."
			::= { ccPortalSumStatsShortEntry 18 }

		
		-- 1.3.6.1.4.1.388.11.2.4.2.100.9.1.19
		ccPortalSumStatsShortPp10kRfUtil OBJECT-TYPE
			SYNTAX PartsPer10k
			UNITS "parts-per-10000"
			MAX-ACCESS read-only
			STATUS current
			DESCRIPTION
				"The approximate utilization of the Portal's RF port.  
				Calculated as Throughput divided by AvgBitSpeed.
				
				Expressed as parts-per-10000.
				"
			::= { ccPortalSumStatsShortEntry 19 }

		
		-- 1.3.6.1.4.1.388.11.2.4.2.100.10
		ccPortalSumStatsLongTable OBJECT-TYPE
			SYNTAX SEQUENCE OF CcPortalSumStatsLongEntry
			MAX-ACCESS not-accessible
			STATUS current
			DESCRIPTION
				"Averages and rates calculated over the LONG window for
				each Portal.
				
				(Refer to ccPortalSumStatsShortTable for descriptions)."
			::= { ccPortalRfSum 10 }

		
		-- 1.3.6.1.4.1.388.11.2.4.2.100.10.1
		ccPortalSumStatsLongEntry OBJECT-TYPE
			SYNTAX CcPortalSumStatsLongEntry
			MAX-ACCESS not-accessible
			STATUS current
			DESCRIPTION
				" "
			INDEX { ccPortalIndex }
			::= { ccPortalSumStatsLongTable 1 }

		
		CcPortalSumStatsLongEntry ::=
			SEQUENCE { 
				ccPortalSumStatsLongTimestamp
					TimeTicks,
				ccPortalSumStatsLongNumPkts
					Unsigned32,
				ccPortalSumStatsLongPktsPerSec100
					ScaleBy100,
				ccPortalSumStatsLongPktsPerSecTx100
					ScaleBy100,
				ccPortalSumStatsLongPktsPerSecRx100
					ScaleBy100,
				ccPortalSumStatsLongThroughput
					Unsigned32,
				ccPortalSumStatsLongThroughputTx
					Unsigned32,
				ccPortalSumStatsLongThroughputRx
					Unsigned32,
				ccPortalSumStatsLongAvgBitSpeed
					Unsigned32,
				ccPortalSumStatsLongAvgMuSignal
					Integer32,
				ccPortalSumStatsLongAvgMuNoise
					Integer32,
				ccPortalSumStatsLongAvgMuSnr
					Integer32,
				ccPortalSumStatsLongPp10kNUcastPkts
					PartsPer10k,
				ccPortalSumStatsLongPp10kTxWithRetries
					PartsPer10k,
				ccPortalSumStatsLongPp10kTxMaxRetries
					PartsPer10k,
				ccPortalSumStatsLongTxAvgRetries100
					ScaleBy100,
				ccPortalSumStatsLongPp10kRxUndecrypt
					PartsPer10k,
				ccPortalSumStatsLongTotalMus
					Unsigned32,
				ccPortalSumStatsLongPp10kRfUtil
					PartsPer10k
			 }

		-- 1.3.6.1.4.1.388.11.2.4.2.100.10.1.1
		ccPortalSumStatsLongTimestamp OBJECT-TYPE
			SYNTAX TimeTicks
			MAX-ACCESS read-only
			STATUS current
			DESCRIPTION
				" "
			::= { ccPortalSumStatsLongEntry 1 }

		
		-- 1.3.6.1.4.1.388.11.2.4.2.100.10.1.2
		ccPortalSumStatsLongNumPkts OBJECT-TYPE
			SYNTAX Unsigned32
			UNITS "packets"
			MAX-ACCESS read-only
			STATUS current
			DESCRIPTION
				" "
			::= { ccPortalSumStatsLongEntry 2 }

		
		-- 1.3.6.1.4.1.388.11.2.4.2.100.10.1.3
		ccPortalSumStatsLongPktsPerSec100 OBJECT-TYPE
			SYNTAX ScaleBy100
			UNITS "pkts per sec x100"
			MAX-ACCESS read-only
			STATUS current
			DESCRIPTION
				" "
			::= { ccPortalSumStatsLongEntry 3 }

		
		-- 1.3.6.1.4.1.388.11.2.4.2.100.10.1.4
		ccPortalSumStatsLongPktsPerSecTx100 OBJECT-TYPE
			SYNTAX ScaleBy100
			UNITS "pkts per sec x100"
			MAX-ACCESS read-only
			STATUS current
			DESCRIPTION
				" "
			::= { ccPortalSumStatsLongEntry 4 }

		
		-- 1.3.6.1.4.1.388.11.2.4.2.100.10.1.5
		ccPortalSumStatsLongPktsPerSecRx100 OBJECT-TYPE
			SYNTAX ScaleBy100
			UNITS "pkts per sec x100"
			MAX-ACCESS read-only
			STATUS current
			DESCRIPTION
				" "
			::= { ccPortalSumStatsLongEntry 5 }

		
		-- 1.3.6.1.4.1.388.11.2.4.2.100.10.1.6
		ccPortalSumStatsLongThroughput OBJECT-TYPE
			SYNTAX Unsigned32
			UNITS "bits per second"
			MAX-ACCESS read-only
			STATUS current
			DESCRIPTION
				" "
			::= { ccPortalSumStatsLongEntry 6 }

		
		-- 1.3.6.1.4.1.388.11.2.4.2.100.10.1.7
		ccPortalSumStatsLongThroughputTx OBJECT-TYPE
			SYNTAX Unsigned32
			UNITS "bits per second"
			MAX-ACCESS read-only
			STATUS current
			DESCRIPTION
				" "
			::= { ccPortalSumStatsLongEntry 7 }

		
		-- 1.3.6.1.4.1.388.11.2.4.2.100.10.1.8
		ccPortalSumStatsLongThroughputRx OBJECT-TYPE
			SYNTAX Unsigned32
			UNITS "bits per second"
			MAX-ACCESS read-only
			STATUS current
			DESCRIPTION
				" "
			::= { ccPortalSumStatsLongEntry 8 }

		
		-- 1.3.6.1.4.1.388.11.2.4.2.100.10.1.9
		ccPortalSumStatsLongAvgBitSpeed OBJECT-TYPE
			SYNTAX Unsigned32
			UNITS "bits per second"
			MAX-ACCESS read-only
			STATUS current
			DESCRIPTION
				" "
			::= { ccPortalSumStatsLongEntry 9 }

		
		-- 1.3.6.1.4.1.388.11.2.4.2.100.10.1.10
		ccPortalSumStatsLongAvgMuSignal OBJECT-TYPE
			SYNTAX Integer32
			UNITS "dBm"
			MAX-ACCESS read-only
			STATUS current
			DESCRIPTION
				" "
			::= { ccPortalSumStatsLongEntry 10 }

		
		-- 1.3.6.1.4.1.388.11.2.4.2.100.10.1.11
		ccPortalSumStatsLongAvgMuNoise OBJECT-TYPE
			SYNTAX Integer32
			UNITS "dBm"
			MAX-ACCESS read-only
			STATUS current
			DESCRIPTION
				" "
			::= { ccPortalSumStatsLongEntry 11 }

		
		-- 1.3.6.1.4.1.388.11.2.4.2.100.10.1.12
		ccPortalSumStatsLongAvgMuSnr OBJECT-TYPE
			SYNTAX Integer32
			UNITS "dB"
			MAX-ACCESS read-only
			STATUS current
			DESCRIPTION
				" "
			::= { ccPortalSumStatsLongEntry 12 }

		
		-- 1.3.6.1.4.1.388.11.2.4.2.100.10.1.13
		ccPortalSumStatsLongPp10kNUcastPkts OBJECT-TYPE
			SYNTAX PartsPer10k
			UNITS "parts-per-10000"
			MAX-ACCESS read-only
			STATUS current
			DESCRIPTION
				" "
			::= { ccPortalSumStatsLongEntry 13 }

		
		-- 1.3.6.1.4.1.388.11.2.4.2.100.10.1.14
		ccPortalSumStatsLongPp10kTxWithRetries OBJECT-TYPE
			SYNTAX PartsPer10k
			UNITS "parts-per-10000"
			MAX-ACCESS read-only
			STATUS current
			DESCRIPTION
				" "
			::= { ccPortalSumStatsLongEntry 14 }

		
		-- 1.3.6.1.4.1.388.11.2.4.2.100.10.1.15
		ccPortalSumStatsLongPp10kTxMaxRetries OBJECT-TYPE
			SYNTAX PartsPer10k
			UNITS "parts-per-10000"
			MAX-ACCESS read-only
			STATUS current
			DESCRIPTION
				" "
			::= { ccPortalSumStatsLongEntry 15 }

		
		-- 1.3.6.1.4.1.388.11.2.4.2.100.10.1.16
		ccPortalSumStatsLongTxAvgRetries100 OBJECT-TYPE
			SYNTAX ScaleBy100
			UNITS "average x100"
			MAX-ACCESS read-only
			STATUS current
			DESCRIPTION
				" "
			::= { ccPortalSumStatsLongEntry 16 }

		
		-- 1.3.6.1.4.1.388.11.2.4.2.100.10.1.17
		ccPortalSumStatsLongPp10kRxUndecrypt OBJECT-TYPE
			SYNTAX PartsPer10k
			UNITS "parts-per-10000"
			MAX-ACCESS read-only
			STATUS current
			DESCRIPTION
				" "
			::= { ccPortalSumStatsLongEntry 17 }

		
		-- 1.3.6.1.4.1.388.11.2.4.2.100.10.1.18
		ccPortalSumStatsLongTotalMus OBJECT-TYPE
			SYNTAX Unsigned32 (0..100)
			UNITS "number of MUs"
			MAX-ACCESS read-only
			STATUS current
			DESCRIPTION
				" "
			::= { ccPortalSumStatsLongEntry 18 }

		
		-- 1.3.6.1.4.1.388.11.2.4.2.100.10.1.19
		ccPortalSumStatsLongPp10kRfUtil OBJECT-TYPE
			SYNTAX PartsPer10k
			UNITS "parts-per-10000"
			MAX-ACCESS read-only
			STATUS current
			DESCRIPTION
				" "
			::= { ccPortalSumStatsLongEntry 19 }

		
-- This group contains MIB values that describe the
-- MUs (Mobile Units) currently associated with each
-- Portal adopted by this WS2000.
		-- 1.3.6.1.4.1.388.11.2.4.3
		ccAssociation OBJECT IDENTIFIER ::= { ccRf 3 }

		
		-- 1.3.6.1.4.1.388.11.2.4.3.1
		ccAssociationTable OBJECT-TYPE
			SYNTAX SEQUENCE OF CcAssociationEntry
			MAX-ACCESS not-accessible
			STATUS current
			DESCRIPTION
				"This table contains one entry for each Portal-MU
				association."
			::= { ccAssociation 1 }

		
		-- 1.3.6.1.4.1.388.11.2.4.3.1.1
		ccAssociationEntry OBJECT-TYPE
			SYNTAX CcAssociationEntry
			MAX-ACCESS not-accessible
			STATUS current
			DESCRIPTION
				" "
			INDEX { ccPortalIndex, ccMuMac }
			::= { ccAssociationTable 1 }

		
		CcAssociationEntry ::=
			SEQUENCE { 
				ccAssociationFirstAssociate
					TimeTicks,
				ccAssociationLastAssociate
					TimeTicks,
				ccAssociationCountAssociates
					Counter32
			 }

		-- 1.3.6.1.4.1.388.11.2.4.3.1.1.1
		ccAssociationFirstAssociate OBJECT-TYPE
			SYNTAX TimeTicks
			MAX-ACCESS read-only
			STATUS current
			DESCRIPTION
				"A snapshot of the switch's sysUpTime at the time
				of the first time this MU associated to this
				Portal."
			::= { ccAssociationEntry 1 }

		
		-- 1.3.6.1.4.1.388.11.2.4.3.1.1.2
		ccAssociationLastAssociate OBJECT-TYPE
			SYNTAX TimeTicks
			MAX-ACCESS read-only
			STATUS current
			DESCRIPTION
				"A snapshot of the switch's sysUpTime at the time
				of the time this MU most recently associated to 
				this Portal."
			::= { ccAssociationEntry 2 }

		
		-- 1.3.6.1.4.1.388.11.2.4.3.1.1.3
		ccAssociationCountAssociates OBJECT-TYPE
			SYNTAX Counter32
			MAX-ACCESS read-only
			STATUS current
			DESCRIPTION
				"A count of the total number of times this MU has
				associated to this Portal."
			::= { ccAssociationEntry 3 }

		
-- This group contains MIB values that describe the
-- MUs (Mobile Units) known to this WS2000.
		-- 1.3.6.1.4.1.388.11.2.4.4
		ccMus OBJECT IDENTIFIER ::= { ccRf 4 }

		
		-- 1.3.6.1.4.1.388.11.2.4.4.1
		ccMuInfoTable OBJECT-TYPE
			SYNTAX SEQUENCE OF CcMuInfoEntry
			MAX-ACCESS not-accessible
			STATUS current
			DESCRIPTION
				"This table describes general information about
				each MU serviced by the switch."
			::= { ccMus 1 }

		
		-- 1.3.6.1.4.1.388.11.2.4.4.1.1
		ccMuInfoEntry OBJECT-TYPE
			SYNTAX CcMuInfoEntry
			MAX-ACCESS not-accessible
			STATUS current
			DESCRIPTION
				" "
			INDEX { ccMuMac }
			::= { ccMuInfoTable 1 }

		
		CcMuInfoEntry ::=
			SEQUENCE { 
				ccMuMac
					PhysAddress,
				ccMuWlanIndex
					Integer32,
				ccMuWlanName
					DisplayString,
				ccMuIsDataReady
					TruthValue,
				ccMuPortalIndex
					Integer32,
				ccMuPortalMac
					PhysAddress,
				ccMuSymbolRogueApEna
					TruthValue,
				ccMuIpAddr
					IpAddress,
				ccMuType
					INTEGER,
				ccMuRadioType
					RadioType,
				ccMuSupportedRates
					BITS,
				ccMuPowerMode
					INTEGER,
				ccMuAuthenticationMethod
					INTEGER,
				ccMuEncryptionMethod
					INTEGER,
				ccMuVlanId
					Unsigned32
			 }

		-- 1.3.6.1.4.1.388.11.2.4.4.1.1.1
		ccMuMac OBJECT-TYPE
			SYNTAX PhysAddress
			MAX-ACCESS read-only
			STATUS current
			DESCRIPTION
				"MAC address of the MU."
			::= { ccMuInfoEntry 1 }

		
		-- 1.3.6.1.4.1.388.11.2.4.4.1.1.2
		ccMuWlanIndex OBJECT-TYPE
			SYNTAX Integer32 (0..63)
			MAX-ACCESS read-only
			STATUS current
			DESCRIPTION
				"(Reserved for future implementation)."
			::= { ccMuInfoEntry 2 }

		
		-- 1.3.6.1.4.1.388.11.2.4.4.1.1.3
		ccMuWlanName OBJECT-TYPE
			SYNTAX DisplayString
			MAX-ACCESS read-only
			STATUS current
			DESCRIPTION
				"The name of the WLAN this MU is associated to."
			::= { ccMuInfoEntry 3 }

		
		-- 1.3.6.1.4.1.388.11.2.4.4.1.1.4
		ccMuIsDataReady OBJECT-TYPE
			SYNTAX TruthValue
			MAX-ACCESS read-only
			STATUS current
			DESCRIPTION
				"This value is true if the WS2000 is ready to
				forward/switch packets to/from this MU,
				(internally called the 'data ready' state).
				Otherwise this value is false."
			::= { ccMuInfoEntry 4 }

		
		-- 1.3.6.1.4.1.388.11.2.4.4.1.1.5
		ccMuPortalIndex OBJECT-TYPE
			SYNTAX Integer32 (0..63)
			MAX-ACCESS read-only
			STATUS current
			DESCRIPTION
				"The index of the entry in the PortalTable to
				which this MU is associated."
			::= { ccMuInfoEntry 5 }

		
		-- 1.3.6.1.4.1.388.11.2.4.4.1.1.6
		ccMuPortalMac OBJECT-TYPE
			SYNTAX PhysAddress
			MAX-ACCESS read-only
			STATUS current
			DESCRIPTION
				"The MAC address of the Portal to which this MU is
				associated."
			::= { ccMuInfoEntry 6 }

		
		-- 1.3.6.1.4.1.388.11.2.4.4.1.1.7
		ccMuSymbolRogueApEna OBJECT-TYPE
			SYNTAX TruthValue
			MAX-ACCESS read-only
			STATUS current
			DESCRIPTION
				"If true, this MU supports Symbol's Rogue AP
				detection assist algorithm."
			::= { ccMuInfoEntry 7 }

		
		-- 1.3.6.1.4.1.388.11.2.4.4.1.1.8
		ccMuIpAddr OBJECT-TYPE
			SYNTAX IpAddress
			MAX-ACCESS read-only
			STATUS current
			DESCRIPTION
				"IP address of the MU."
			::= { ccMuInfoEntry 8 }

		
		-- 1.3.6.1.4.1.388.11.2.4.4.1.1.9
		ccMuType OBJECT-TYPE
			SYNTAX INTEGER
				{
				data(1),
				voice(2),
				accessPoint(3)
				}
			MAX-ACCESS read-only
			STATUS current
			DESCRIPTION
				"Type of the MU."
			::= { ccMuInfoEntry 9 }

		
		-- 1.3.6.1.4.1.388.11.2.4.4.1.1.10
		ccMuRadioType OBJECT-TYPE
			SYNTAX RadioType
			MAX-ACCESS read-only
			STATUS current
			DESCRIPTION
				"Radio type of the MU."
			::= { ccMuInfoEntry 10 }

		
		-- 1.3.6.1.4.1.388.11.2.4.4.1.1.11
		ccMuSupportedRates OBJECT-TYPE
			SYNTAX BITS
				{
				supports1Mb(0),
				supports2Mb(1),
				supports5dot5Mb(2),
				supports6Mb(3),
				supports9Mb(4),
				supports11Mb(5),
				supports12Mb(6),
				supports18Mb(7),
				supports22Mb(8),
				supports24Mb(9),
				supports36Mb(10),
				supports48Mb(11),
				supports54Mb(12)
				}
			MAX-ACCESS read-only
			STATUS current
			DESCRIPTION
				"A bit-mask of rates supported by this MU."
			::= { ccMuInfoEntry 11 }

		
		-- 1.3.6.1.4.1.388.11.2.4.4.1.1.12
		ccMuPowerMode OBJECT-TYPE
			SYNTAX INTEGER
				{
				continuousAccessMode(1),
				powerSavePolling(2)
				}
			MAX-ACCESS read-only
			STATUS current
			DESCRIPTION
				"Power-mode implemented by the MU.
				
				A MU's status will constantly switch between PSP and 
				CAM mode when it is in PSP mode.  
				 "
			::= { ccMuInfoEntry 12 }

		
		-- 1.3.6.1.4.1.388.11.2.4.4.1.1.13
		ccMuAuthenticationMethod OBJECT-TYPE
			SYNTAX INTEGER
				{
				none(1),
				eap802dot1x(2),
				kerberos(3)
				}
			MAX-ACCESS read-only
			STATUS current
			DESCRIPTION
				"Authentication method implemented by the MU."
			::= { ccMuInfoEntry 13 }

		
		-- 1.3.6.1.4.1.388.11.2.4.4.1.1.14
		ccMuEncryptionMethod OBJECT-TYPE
			SYNTAX INTEGER
				{
				none(1),
				wep40(2),
				wep128(3),
				keyGuardMCM(4),
				wpaTKIP(5),
				wpa2AesCcmp(6)
				}
			MAX-ACCESS read-only
			STATUS current
			DESCRIPTION
				"Encryption method implemented by the MU."
			::= { ccMuInfoEntry 14 }

		
		-- 1.3.6.1.4.1.388.11.2.4.4.1.1.15
		ccMuVlanId OBJECT-TYPE
			SYNTAX Unsigned32 (1..31)
			MAX-ACCESS read-only
			STATUS current
			DESCRIPTION
				"The VLAN that this MU is assigned to.
				"
			::= { ccMuInfoEntry 15 }

		
		-- 1.3.6.1.4.1.388.11.2.4.4.2
		ccMuStatsTable OBJECT-TYPE
			SYNTAX SEQUENCE OF CcMuStatsEntry
			MAX-ACCESS not-accessible
			STATUS current
			DESCRIPTION
				"This table describes general statistics about
				packets sent/recieved via each MU serviced by the switch."
			::= { ccMus 2 }
-- All 
		
		-- 1.3.6.1.4.1.388.11.2.4.4.2.1
		ccMuStatsEntry OBJECT-TYPE
			SYNTAX CcMuStatsEntry
			MAX-ACCESS not-accessible
			STATUS current
			DESCRIPTION
				" "
			INDEX { ccMuMac }
			::= { ccMuStatsTable 1 }

		
		CcMuStatsEntry ::=
			SEQUENCE { 
				ccMuTxPktsUcast
					Counter32,
				ccMuRxPktsUcast
					Counter32,
				ccMuRxPktsNUcast
					Counter32,
				ccMuTxOctetsUcast
					Counter32,
				ccMuRxOctetsUcast
					Counter32,
				ccMuRxOctetsNUcast
					Counter32,
				ccMuRxUndecryptablePkts
					Counter32,
				ccMuRxRssiNumPkts
					Counter32,
				ccMuRxRssiSum
					Counter32,
				ccMuRxRssiSumSquares
					Counter64,
				ccMuRxRssiMostRecent
					INTEGER,
				ccMuLastActivity
					TimeTicks
			 }

		-- 1.3.6.1.4.1.388.11.2.4.4.2.1.1
		ccMuTxPktsUcast OBJECT-TYPE
			SYNTAX Counter32
			MAX-ACCESS read-only
			STATUS current
			DESCRIPTION
				"Count of unicast packets sent."
			::= { ccMuStatsEntry 1 }

		
		-- 1.3.6.1.4.1.388.11.2.4.4.2.1.2
		ccMuRxPktsUcast OBJECT-TYPE
			SYNTAX Counter32
			MAX-ACCESS read-only
			STATUS current
			DESCRIPTION
				"Count of unicast packets received."
			::= { ccMuStatsEntry 2 }

		
		-- 1.3.6.1.4.1.388.11.2.4.4.2.1.3
		ccMuRxPktsNUcast OBJECT-TYPE
			SYNTAX Counter32
			MAX-ACCESS read-only
			STATUS obsolete
			DESCRIPTION
				"Count of non-unicast (broadcast & multicast) 
				packets received."
			::= { ccMuStatsEntry 3 }
-- This value existed in WS2000 v1.0, but never incremented
-- from 0.  This variable should never have been defined,
-- since there is no such thing as a non-unicast packet 
-- moving from a MU to a Portal, (Rx at the Portal).
		
		-- 1.3.6.1.4.1.388.11.2.4.4.2.1.4
		ccMuTxOctetsUcast OBJECT-TYPE
			SYNTAX Counter32
			MAX-ACCESS read-only
			STATUS current
			DESCRIPTION
				"Count of unicast octets sent."
			::= { ccMuStatsEntry 4 }

		
		-- 1.3.6.1.4.1.388.11.2.4.4.2.1.5
		ccMuRxOctetsUcast OBJECT-TYPE
			SYNTAX Counter32
			MAX-ACCESS read-only
			STATUS current
			DESCRIPTION
				"Count of unicast octets received."
			::= { ccMuStatsEntry 5 }

		
		-- 1.3.6.1.4.1.388.11.2.4.4.2.1.6
		ccMuRxOctetsNUcast OBJECT-TYPE
			SYNTAX Counter32
			MAX-ACCESS read-only
			STATUS obsolete
			DESCRIPTION
				"Count of non-unicast (broadcast & multicast) 
				octets received."
			::= { ccMuStatsEntry 6 }
-- This value existed in WS2000 v1.0, but never incremented
-- from 0.  This variable should never have been defined,
-- since there is no such thing as a non-unicast packet 
-- moving from a MU to a Portal, (Rx at the Portal).
		
		-- 1.3.6.1.4.1.388.11.2.4.4.2.1.7
		ccMuRxUndecryptablePkts OBJECT-TYPE
			SYNTAX Counter32
			MAX-ACCESS read-only
			STATUS current
			DESCRIPTION
				"Count of packets received that could
				not be decrypted."
			::= { ccMuStatsEntry 7 }

		
-- This value is duplicated by ccMuSigStatsNumPkts, but this
-- one is retained for backwards-compatibility.
		-- 1.3.6.1.4.1.388.11.2.4.4.2.1.8
		ccMuRxRssiNumPkts OBJECT-TYPE
			SYNTAX Counter32
			MAX-ACCESS read-only
			STATUS current
			DESCRIPTION
				"Total RSSI packets received."
			::= { ccMuStatsEntry 8 }

		
-- This value is duplicated by ccMuSigStatsRssiSum, but this
-- one is retained for backwards-compatibility.
		-- 1.3.6.1.4.1.388.11.2.4.4.2.1.9
		ccMuRxRssiSum OBJECT-TYPE
			SYNTAX Counter32
			MAX-ACCESS read-only
			STATUS current
			DESCRIPTION
				"A running sum of all RSSI values calculated by the
				switch for packets."
			::= { ccMuStatsEntry 9 }

		
-- This value is duplicated by ccMuSigStatsRssiSumSquares, 
-- but this one is retained for backwards-compatibility.
		-- 1.3.6.1.4.1.388.11.2.4.4.2.1.10
		ccMuRxRssiSumSquares OBJECT-TYPE
			SYNTAX Counter64
			MAX-ACCESS read-only
			STATUS current
			DESCRIPTION
				"A sum of the squares of each RSSI value calculated
				for packets received.
				
				This value is never negative."
			::= { ccMuStatsEntry 10 }

		
-- This value is duplicated by ccMuSigStatsRssiMostRecent, 
-- but this one is retained for backwards-compatibility.
-- 
-- ??-CM: this should be Uint32 - would chaning this be an
-- incompatible change?  Any diff on wire Int32 vs Unit32 ?
		-- 1.3.6.1.4.1.388.11.2.4.4.2.1.11
		ccMuRxRssiMostRecent OBJECT-TYPE
			SYNTAX INTEGER (0..255)
			MAX-ACCESS read-only
			STATUS current
			DESCRIPTION
				"The best RSSI value seen so far.
				(Remember that -80dBm Noise is better than -70dBm).
				
				This value does not make sense when ccMuRxRssiNumPkts 
				equals to 0."
			::= { ccMuStatsEntry 11 }

		
		-- 1.3.6.1.4.1.388.11.2.4.4.2.1.12
		ccMuLastActivity OBJECT-TYPE
			SYNTAX TimeTicks
			MAX-ACCESS read-only
			STATUS current
			DESCRIPTION
				"A snapshot of the switch's sysUpTime at the time
				of the last activity (packet sent or received)."
			::= { ccMuStatsEntry 12 }

		
		-- 1.3.6.1.4.1.388.11.2.4.4.3
		ccMuRxPktsTable OBJECT-TYPE
			SYNTAX SEQUENCE OF CcMuRxPktsEntry
			MAX-ACCESS not-accessible
			STATUS current
			DESCRIPTION
				"For each MU serviced by the switch, this table 
				describes counts of packets received at each 
				possible speed, (1Mb, 2Mb, 5.5Mb, 6Mb...)."
			::= { ccMus 3 }

		
		-- 1.3.6.1.4.1.388.11.2.4.4.3.1
		ccMuRxPktsEntry OBJECT-TYPE
			SYNTAX CcMuRxPktsEntry
			MAX-ACCESS not-accessible
			STATUS current
			DESCRIPTION
				" "
			INDEX { ccMuMac }
			::= { ccMuRxPktsTable 1 }

		
		CcMuRxPktsEntry ::=
			SEQUENCE { 
				ccMuRxPktsAt1Mb
					Counter32,
				ccMuRxPktsAt2Mb
					Counter32,
				ccMuRxPktsAt5pt5Mb
					Counter32,
				ccMuRxPktsAt6Mb
					Counter32,
				ccMuRxPktsAt9Mb
					Counter32,
				ccMuRxPktsAt11Mb
					Counter32,
				ccMuRxPktsAt12Mb
					Counter32,
				ccMuRxPktsAt18Mb
					Counter32,
				ccMuRxPktsAt22Mb
					Counter32,
				ccMuRxPktsAt24Mb
					Counter32,
				ccMuRxPktsAt36Mb
					Counter32,
				ccMuRxPktsAt48Mb
					Counter32,
				ccMuRxPktsAt54Mb
					Counter32
			 }

		-- 1.3.6.1.4.1.388.11.2.4.4.3.1.1
		ccMuRxPktsAt1Mb OBJECT-TYPE
			SYNTAX Counter32
			MAX-ACCESS read-only
			STATUS current
			DESCRIPTION
				"Number of pkts received at 1 Mb."
			::= { ccMuRxPktsEntry 1 }

		
		-- 1.3.6.1.4.1.388.11.2.4.4.3.1.2
		ccMuRxPktsAt2Mb OBJECT-TYPE
			SYNTAX Counter32
			MAX-ACCESS read-only
			STATUS current
			DESCRIPTION
				"Number of pkts received at 2 Mb."
			::= { ccMuRxPktsEntry 2 }

		
		-- 1.3.6.1.4.1.388.11.2.4.4.3.1.3
		ccMuRxPktsAt5pt5Mb OBJECT-TYPE
			SYNTAX Counter32
			MAX-ACCESS read-only
			STATUS current
			DESCRIPTION
				"Number of pkts received at 5.5 Mb."
			::= { ccMuRxPktsEntry 3 }

		
		-- 1.3.6.1.4.1.388.11.2.4.4.3.1.4
		ccMuRxPktsAt6Mb OBJECT-TYPE
			SYNTAX Counter32
			MAX-ACCESS read-only
			STATUS current
			DESCRIPTION
				"Number of pkts received at 6 Mb."
			::= { ccMuRxPktsEntry 4 }

		
		-- 1.3.6.1.4.1.388.11.2.4.4.3.1.5
		ccMuRxPktsAt9Mb OBJECT-TYPE
			SYNTAX Counter32
			MAX-ACCESS read-only
			STATUS current
			DESCRIPTION
				"Number of pkts received at 9 Mb."
			::= { ccMuRxPktsEntry 5 }

		
		-- 1.3.6.1.4.1.388.11.2.4.4.3.1.6
		ccMuRxPktsAt11Mb OBJECT-TYPE
			SYNTAX Counter32
			MAX-ACCESS read-only
			STATUS current
			DESCRIPTION
				"Number of pkts received at 11 Mb."
			::= { ccMuRxPktsEntry 6 }

		
		-- 1.3.6.1.4.1.388.11.2.4.4.3.1.7
		ccMuRxPktsAt12Mb OBJECT-TYPE
			SYNTAX Counter32
			MAX-ACCESS read-only
			STATUS current
			DESCRIPTION
				"Number of pkts received at 12 Mb."
			::= { ccMuRxPktsEntry 7 }

		
		-- 1.3.6.1.4.1.388.11.2.4.4.3.1.8
		ccMuRxPktsAt18Mb OBJECT-TYPE
			SYNTAX Counter32
			MAX-ACCESS read-only
			STATUS current
			DESCRIPTION
				"Number of pkts received at 18 Mb."
			::= { ccMuRxPktsEntry 8 }

		
		-- 1.3.6.1.4.1.388.11.2.4.4.3.1.9
		ccMuRxPktsAt22Mb OBJECT-TYPE
			SYNTAX Counter32
			MAX-ACCESS read-only
			STATUS current
			DESCRIPTION
				"Number of pkts received at 22 Mb."
			::= { ccMuRxPktsEntry 9 }

		
		-- 1.3.6.1.4.1.388.11.2.4.4.3.1.10
		ccMuRxPktsAt24Mb OBJECT-TYPE
			SYNTAX Counter32
			MAX-ACCESS read-only
			STATUS current
			DESCRIPTION
				"Number of pkts received at 24 Mb."
			::= { ccMuRxPktsEntry 10 }

		
		-- 1.3.6.1.4.1.388.11.2.4.4.3.1.11
		ccMuRxPktsAt36Mb OBJECT-TYPE
			SYNTAX Counter32
			MAX-ACCESS read-only
			STATUS current
			DESCRIPTION
				"Number of pkts received at 36 Mb."
			::= { ccMuRxPktsEntry 11 }

		
		-- 1.3.6.1.4.1.388.11.2.4.4.3.1.12
		ccMuRxPktsAt48Mb OBJECT-TYPE
			SYNTAX Counter32
			MAX-ACCESS read-only
			STATUS current
			DESCRIPTION
				"Number of pkts received at 48 Mb."
			::= { ccMuRxPktsEntry 12 }

		
		-- 1.3.6.1.4.1.388.11.2.4.4.3.1.13
		ccMuRxPktsAt54Mb OBJECT-TYPE
			SYNTAX Counter32
			MAX-ACCESS read-only
			STATUS current
			DESCRIPTION
				"Number of pkts received at 54 Mb."
			::= { ccMuRxPktsEntry 13 }

		
		-- 1.3.6.1.4.1.388.11.2.4.4.4
		ccMuTxPktsTable OBJECT-TYPE
			SYNTAX SEQUENCE OF CcMuTxPktsEntry
			MAX-ACCESS not-accessible
			STATUS current
			DESCRIPTION
				"For each MU serviced by the switch, this table 
				describes counts of packets transmitted at each 
				possible speed, (1Mb, 2Mb, 5.5Mb, 6Mb...)."
			::= { ccMus 4 }

		
		-- 1.3.6.1.4.1.388.11.2.4.4.4.1
		ccMuTxPktsEntry OBJECT-TYPE
			SYNTAX CcMuTxPktsEntry
			MAX-ACCESS not-accessible
			STATUS current
			DESCRIPTION
				" "
			INDEX { ccMuMac }
			::= { ccMuTxPktsTable 1 }

		
		CcMuTxPktsEntry ::=
			SEQUENCE { 
				ccMuTxPktsAt1Mb
					Counter32,
				ccMuTxPktsAt2Mb
					Counter32,
				ccMuTxPktsAt5pt5Mb
					Counter32,
				ccMuTxPktsAt6Mb
					Counter32,
				ccMuTxPktsAt9Mb
					Counter32,
				ccMuTxPktsAt11Mb
					Counter32,
				ccMuTxPktsAt12Mb
					Counter32,
				ccMuTxPktsAt18Mb
					Counter32,
				ccMuTxPktsAt22Mb
					Counter32,
				ccMuTxPktsAt24Mb
					Counter32,
				ccMuTxPktsAt36Mb
					Counter32,
				ccMuTxPktsAt48Mb
					Counter32,
				ccMuTxPktsAt54Mb
					Counter32
			 }

		-- 1.3.6.1.4.1.388.11.2.4.4.4.1.1
		ccMuTxPktsAt1Mb OBJECT-TYPE
			SYNTAX Counter32
			MAX-ACCESS read-only
			STATUS current
			DESCRIPTION
				"Number of pkts transmitted at 1 Mb."
			::= { ccMuTxPktsEntry 1 }

		
		-- 1.3.6.1.4.1.388.11.2.4.4.4.1.2
		ccMuTxPktsAt2Mb OBJECT-TYPE
			SYNTAX Counter32
			MAX-ACCESS read-only
			STATUS current
			DESCRIPTION
				"Number of pkts transmitted at 2 Mb."
			::= { ccMuTxPktsEntry 2 }

		
		-- 1.3.6.1.4.1.388.11.2.4.4.4.1.3
		ccMuTxPktsAt5pt5Mb OBJECT-TYPE
			SYNTAX Counter32
			MAX-ACCESS read-only
			STATUS current
			DESCRIPTION
				"Number of pkts transmitted at 5.5 Mb."
			::= { ccMuTxPktsEntry 3 }

		
		-- 1.3.6.1.4.1.388.11.2.4.4.4.1.4
		ccMuTxPktsAt6Mb OBJECT-TYPE
			SYNTAX Counter32
			MAX-ACCESS read-only
			STATUS current
			DESCRIPTION
				"Number of pkts transmitted at 6 Mb."
			::= { ccMuTxPktsEntry 4 }

		
		-- 1.3.6.1.4.1.388.11.2.4.4.4.1.5
		ccMuTxPktsAt9Mb OBJECT-TYPE
			SYNTAX Counter32
			MAX-ACCESS read-only
			STATUS current
			DESCRIPTION
				"Number of pkts transmitted at 9 Mb."
			::= { ccMuTxPktsEntry 5 }

		
		-- 1.3.6.1.4.1.388.11.2.4.4.4.1.6
		ccMuTxPktsAt11Mb OBJECT-TYPE
			SYNTAX Counter32
			MAX-ACCESS read-only
			STATUS current
			DESCRIPTION
				"Number of pkts transmitted at 11 Mb."
			::= { ccMuTxPktsEntry 6 }

		
		-- 1.3.6.1.4.1.388.11.2.4.4.4.1.7
		ccMuTxPktsAt12Mb OBJECT-TYPE
			SYNTAX Counter32
			MAX-ACCESS read-only
			STATUS current
			DESCRIPTION
				"Number of pkts transmitted at 12 Mb."
			::= { ccMuTxPktsEntry 7 }

		
		-- 1.3.6.1.4.1.388.11.2.4.4.4.1.8
		ccMuTxPktsAt18Mb OBJECT-TYPE
			SYNTAX Counter32
			MAX-ACCESS read-only
			STATUS current
			DESCRIPTION
				"Number of pkts transmitted at 18 Mb."
			::= { ccMuTxPktsEntry 8 }

		
		-- 1.3.6.1.4.1.388.11.2.4.4.4.1.9
		ccMuTxPktsAt22Mb OBJECT-TYPE
			SYNTAX Counter32
			MAX-ACCESS read-only
			STATUS current
			DESCRIPTION
				"Number of pkts transmitted at 22 Mb."
			::= { ccMuTxPktsEntry 9 }

		
		-- 1.3.6.1.4.1.388.11.2.4.4.4.1.10
		ccMuTxPktsAt24Mb OBJECT-TYPE
			SYNTAX Counter32
			MAX-ACCESS read-only
			STATUS current
			DESCRIPTION
				"Number of pkts transmitted at 24 Mb."
			::= { ccMuTxPktsEntry 10 }

		
		-- 1.3.6.1.4.1.388.11.2.4.4.4.1.11
		ccMuTxPktsAt36Mb OBJECT-TYPE
			SYNTAX Counter32
			MAX-ACCESS read-only
			STATUS current
			DESCRIPTION
				"Number of pkts transmitted at 36 Mb."
			::= { ccMuTxPktsEntry 11 }

		
		-- 1.3.6.1.4.1.388.11.2.4.4.4.1.12
		ccMuTxPktsAt48Mb OBJECT-TYPE
			SYNTAX Counter32
			MAX-ACCESS read-only
			STATUS current
			DESCRIPTION
				"Number of pkts transmitted at 48 Mb."
			::= { ccMuTxPktsEntry 12 }

		
		-- 1.3.6.1.4.1.388.11.2.4.4.4.1.13
		ccMuTxPktsAt54Mb OBJECT-TYPE
			SYNTAX Counter32
			MAX-ACCESS read-only
			STATUS current
			DESCRIPTION
				"Number of pkts transmitted at 54 Mb."
			::= { ccMuTxPktsEntry 13 }

		
		-- 1.3.6.1.4.1.388.11.2.4.4.5
		ccMuRxOctetsTable OBJECT-TYPE
			SYNTAX SEQUENCE OF CcMuRxOctetsEntry
			MAX-ACCESS not-accessible
			STATUS current
			DESCRIPTION
				"For each MU serviced by this switch, this table 
				describes counts of octets received at each 
				possible speed, (1Mb, 2Mb, 5.5Mb, 6Mb...)."
			::= { ccMus 5 }

		
		-- 1.3.6.1.4.1.388.11.2.4.4.5.1
		ccMuRxOctetsEntry OBJECT-TYPE
			SYNTAX CcMuRxOctetsEntry
			MAX-ACCESS not-accessible
			STATUS current
			DESCRIPTION
				" "
			INDEX { ccMuMac }
			::= { ccMuRxOctetsTable 1 }

		
		CcMuRxOctetsEntry ::=
			SEQUENCE { 
				ccMuRxOctetsAt1Mb
					Counter32,
				ccMuRxOctetsAt2Mb
					Counter32,
				ccMuRxOctetsAt5pt5Mb
					Counter32,
				ccMuRxOctetsAt6Mb
					Counter32,
				ccMuRxOctetsAt9Mb
					Counter32,
				ccMuRxOctetsAt11Mb
					Counter32,
				ccMuRxOctetsAt12Mb
					Counter32,
				ccMuRxOctetsAt18Mb
					Counter32,
				ccMuRxOctetsAt22Mb
					Counter32,
				ccMuRxOctetsAt24Mb
					Counter32,
				ccMuRxOctetsAt36Mb
					Counter32,
				ccMuRxOctetsAt48Mb
					Counter32,
				ccMuRxOctetsAt54Mb
					Counter32
			 }

		-- 1.3.6.1.4.1.388.11.2.4.4.5.1.1
		ccMuRxOctetsAt1Mb OBJECT-TYPE
			SYNTAX Counter32
			MAX-ACCESS read-only
			STATUS current
			DESCRIPTION
				"Number of octets received at 1 Mb."
			::= { ccMuRxOctetsEntry 1 }

		
		-- 1.3.6.1.4.1.388.11.2.4.4.5.1.2
		ccMuRxOctetsAt2Mb OBJECT-TYPE
			SYNTAX Counter32
			MAX-ACCESS read-only
			STATUS current
			DESCRIPTION
				"Number of octets received at 2 Mb."
			::= { ccMuRxOctetsEntry 2 }

		
		-- 1.3.6.1.4.1.388.11.2.4.4.5.1.3
		ccMuRxOctetsAt5pt5Mb OBJECT-TYPE
			SYNTAX Counter32
			MAX-ACCESS read-only
			STATUS current
			DESCRIPTION
				"Number of octets received at 5.5 Mb."
			::= { ccMuRxOctetsEntry 3 }

		
		-- 1.3.6.1.4.1.388.11.2.4.4.5.1.4
		ccMuRxOctetsAt6Mb OBJECT-TYPE
			SYNTAX Counter32
			MAX-ACCESS read-only
			STATUS current
			DESCRIPTION
				"Number of octets received at 6 Mb."
			::= { ccMuRxOctetsEntry 4 }

		
		-- 1.3.6.1.4.1.388.11.2.4.4.5.1.5
		ccMuRxOctetsAt9Mb OBJECT-TYPE
			SYNTAX Counter32
			MAX-ACCESS read-only
			STATUS current
			DESCRIPTION
				"Number of octets received at 9 Mb."
			::= { ccMuRxOctetsEntry 5 }

		
		-- 1.3.6.1.4.1.388.11.2.4.4.5.1.6
		ccMuRxOctetsAt11Mb OBJECT-TYPE
			SYNTAX Counter32
			MAX-ACCESS read-only
			STATUS current
			DESCRIPTION
				"Number of octets received at 11 Mb."
			::= { ccMuRxOctetsEntry 6 }

		
		-- 1.3.6.1.4.1.388.11.2.4.4.5.1.7
		ccMuRxOctetsAt12Mb OBJECT-TYPE
			SYNTAX Counter32
			MAX-ACCESS read-only
			STATUS current
			DESCRIPTION
				"Number of octets received at 12 Mb."
			::= { ccMuRxOctetsEntry 7 }

		
		-- 1.3.6.1.4.1.388.11.2.4.4.5.1.8
		ccMuRxOctetsAt18Mb OBJECT-TYPE
			SYNTAX Counter32
			MAX-ACCESS read-only
			STATUS current
			DESCRIPTION
				"Number of octets received at 18 Mb."
			::= { ccMuRxOctetsEntry 8 }

		
		-- 1.3.6.1.4.1.388.11.2.4.4.5.1.9
		ccMuRxOctetsAt22Mb OBJECT-TYPE
			SYNTAX Counter32
			MAX-ACCESS read-only
			STATUS current
			DESCRIPTION
				"Number of octets received at 22 Mb."
			::= { ccMuRxOctetsEntry 9 }

		
		-- 1.3.6.1.4.1.388.11.2.4.4.5.1.10
		ccMuRxOctetsAt24Mb OBJECT-TYPE
			SYNTAX Counter32
			MAX-ACCESS read-only
			STATUS current
			DESCRIPTION
				"Number of octets received at 24 Mb."
			::= { ccMuRxOctetsEntry 10 }

		
		-- 1.3.6.1.4.1.388.11.2.4.4.5.1.11
		ccMuRxOctetsAt36Mb OBJECT-TYPE
			SYNTAX Counter32
			MAX-ACCESS read-only
			STATUS current
			DESCRIPTION
				"Number of octets received at 36 Mb."
			::= { ccMuRxOctetsEntry 11 }

		
		-- 1.3.6.1.4.1.388.11.2.4.4.5.1.12
		ccMuRxOctetsAt48Mb OBJECT-TYPE
			SYNTAX Counter32
			MAX-ACCESS read-only
			STATUS current
			DESCRIPTION
				"Number of octets received at 48 Mb."
			::= { ccMuRxOctetsEntry 12 }

		
		-- 1.3.6.1.4.1.388.11.2.4.4.5.1.13
		ccMuRxOctetsAt54Mb OBJECT-TYPE
			SYNTAX Counter32
			MAX-ACCESS read-only
			STATUS current
			DESCRIPTION
				"Number of octets received at 54 Mb."
			::= { ccMuRxOctetsEntry 13 }

		
		-- 1.3.6.1.4.1.388.11.2.4.4.6
		ccMuTxOctetsTable OBJECT-TYPE
			SYNTAX SEQUENCE OF CcMuTxOctetsEntry
			MAX-ACCESS not-accessible
			STATUS current
			DESCRIPTION
				"For each MU serviced by this switch, this table 
				describes counts of octets transmitted at each 
				possible speed, (1Mb, 2Mb, 5.5Mb, 6Mb...)."
			::= { ccMus 6 }

		
		-- 1.3.6.1.4.1.388.11.2.4.4.6.1
		ccMuTxOctetsEntry OBJECT-TYPE
			SYNTAX CcMuTxOctetsEntry
			MAX-ACCESS not-accessible
			STATUS current
			DESCRIPTION
				" "
			INDEX { ccMuMac }
			::= { ccMuTxOctetsTable 1 }

		
		CcMuTxOctetsEntry ::=
			SEQUENCE { 
				ccMuTxOctetsAt1Mb
					Counter32,
				ccMuTxOctetsAt2Mb
					Counter32,
				ccMuTxOctetsAt5pt5Mb
					Counter32,
				ccMuTxOctetsAt6Mb
					Counter32,
				ccMuTxOctetsAt9Mb
					Counter32,
				ccMuTxOctetsAt11Mb
					Counter32,
				ccMuTxOctetsAt12Mb
					Counter32,
				ccMuTxOctetsAt18Mb
					Counter32,
				ccMuTxOctetsAt22Mb
					Counter32,
				ccMuTxOctetsAt24Mb
					Counter32,
				ccMuTxOctetsAt36Mb
					Counter32,
				ccMuTxOctetsAt48Mb
					Counter32,
				ccMuTxOctetsAt54Mb
					Counter32
			 }

		-- 1.3.6.1.4.1.388.11.2.4.4.6.1.1
		ccMuTxOctetsAt1Mb OBJECT-TYPE
			SYNTAX Counter32
			MAX-ACCESS read-only
			STATUS current
			DESCRIPTION
				"Number of octets transmitted at 1 Mb."
			::= { ccMuTxOctetsEntry 1 }

		
		-- 1.3.6.1.4.1.388.11.2.4.4.6.1.2
		ccMuTxOctetsAt2Mb OBJECT-TYPE
			SYNTAX Counter32
			MAX-ACCESS read-only
			STATUS current
			DESCRIPTION
				"Number of octets transmitted at 2 Mb."
			::= { ccMuTxOctetsEntry 2 }

		
		-- 1.3.6.1.4.1.388.11.2.4.4.6.1.3
		ccMuTxOctetsAt5pt5Mb OBJECT-TYPE
			SYNTAX Counter32
			MAX-ACCESS read-only
			STATUS current
			DESCRIPTION
				"Number of octets transmitted at 5.5 Mb."
			::= { ccMuTxOctetsEntry 3 }

		
		-- 1.3.6.1.4.1.388.11.2.4.4.6.1.4
		ccMuTxOctetsAt6Mb OBJECT-TYPE
			SYNTAX Counter32
			MAX-ACCESS read-only
			STATUS current
			DESCRIPTION
				"Number of octets transmitted at 6 Mb."
			::= { ccMuTxOctetsEntry 4 }

		
		-- 1.3.6.1.4.1.388.11.2.4.4.6.1.5
		ccMuTxOctetsAt9Mb OBJECT-TYPE
			SYNTAX Counter32
			MAX-ACCESS read-only
			STATUS current
			DESCRIPTION
				"Number of octets transmitted at 9 Mb."
			::= { ccMuTxOctetsEntry 5 }

		
		-- 1.3.6.1.4.1.388.11.2.4.4.6.1.6
		ccMuTxOctetsAt11Mb OBJECT-TYPE
			SYNTAX Counter32
			MAX-ACCESS read-only
			STATUS current
			DESCRIPTION
				"Number of octets transmitted at 11 Mb."
			::= { ccMuTxOctetsEntry 6 }

		
		-- 1.3.6.1.4.1.388.11.2.4.4.6.1.7
		ccMuTxOctetsAt12Mb OBJECT-TYPE
			SYNTAX Counter32
			MAX-ACCESS read-only
			STATUS current
			DESCRIPTION
				"Number of octets transmitted at 12 Mb."
			::= { ccMuTxOctetsEntry 7 }

		
		-- 1.3.6.1.4.1.388.11.2.4.4.6.1.8
		ccMuTxOctetsAt18Mb OBJECT-TYPE
			SYNTAX Counter32
			MAX-ACCESS read-only
			STATUS current
			DESCRIPTION
				"Number of octets transmitted at 18 Mb."
			::= { ccMuTxOctetsEntry 8 }

		
		-- 1.3.6.1.4.1.388.11.2.4.4.6.1.9
		ccMuTxOctetsAt22Mb OBJECT-TYPE
			SYNTAX Counter32
			MAX-ACCESS read-only
			STATUS current
			DESCRIPTION
				"Number of octets transmitted at 22 Mb."
			::= { ccMuTxOctetsEntry 9 }

		
		-- 1.3.6.1.4.1.388.11.2.4.4.6.1.10
		ccMuTxOctetsAt24Mb OBJECT-TYPE
			SYNTAX Counter32
			MAX-ACCESS read-only
			STATUS current
			DESCRIPTION
				"Number of octets transmitted at 24 Mb."
			::= { ccMuTxOctetsEntry 10 }

		
		-- 1.3.6.1.4.1.388.11.2.4.4.6.1.11
		ccMuTxOctetsAt36Mb OBJECT-TYPE
			SYNTAX Counter32
			MAX-ACCESS read-only
			STATUS current
			DESCRIPTION
				"Number of octets transmitted at 36 Mb."
			::= { ccMuTxOctetsEntry 11 }

		
		-- 1.3.6.1.4.1.388.11.2.4.4.6.1.12
		ccMuTxOctetsAt48Mb OBJECT-TYPE
			SYNTAX Counter32
			MAX-ACCESS read-only
			STATUS current
			DESCRIPTION
				"Number of octets transmitted at 48 Mb."
			::= { ccMuTxOctetsEntry 12 }

		
		-- 1.3.6.1.4.1.388.11.2.4.4.6.1.13
		ccMuTxOctetsAt54Mb OBJECT-TYPE
			SYNTAX Counter32
			MAX-ACCESS read-only
			STATUS current
			DESCRIPTION
				"Number of octets transmitted at 54 Mb."
			::= { ccMuTxOctetsEntry 13 }

		
		-- 1.3.6.1.4.1.388.11.2.4.4.7
		ccMuTxRetriesTable OBJECT-TYPE
			SYNTAX SEQUENCE OF CcMuTxRetriesEntry
			MAX-ACCESS not-accessible
			STATUS current
			DESCRIPTION
				"For each MU serviced by the switch, this table describes 
				counts of the number of packets affected by transmit 
				retries, (no retries, 1 retry, 2 retries,... gave-up)."
			::= { ccMus 7 }

		
		-- 1.3.6.1.4.1.388.11.2.4.4.7.1
		ccMuTxRetriesEntry OBJECT-TYPE
			SYNTAX CcMuTxRetriesEntry
			MAX-ACCESS not-accessible
			STATUS current
			DESCRIPTION
				" "
			INDEX { ccMuMac }
			::= { ccMuTxRetriesTable 1 }

		
		CcMuTxRetriesEntry ::=
			SEQUENCE { 
				ccMuTxRetriesNone
					Counter32,
				ccMuTxRetries01
					Counter32,
				ccMuTxRetries02
					Counter32,
				ccMuTxRetries03
					Counter32,
				ccMuTxRetries04
					Counter32,
				ccMuTxRetries05
					Counter32,
				ccMuTxRetries06
					Counter32,
				ccMuTxRetries07
					Counter32,
				ccMuTxRetries08
					Counter32,
				ccMuTxRetries09
					Counter32,
				ccMuTxRetries10
					Counter32,
				ccMuTxRetries11
					Counter32,
				ccMuTxRetries12
					Counter32,
				ccMuTxRetries13
					Counter32,
				ccMuTxRetries14
					Counter32,
				ccMuTxRetries15
					Counter32,
				ccMuTxRetriesFailed
					Counter32,
				ccMuTxRetriesTotal
					Counter32,
				ccMuTxRetriesMostRecent
					INTEGER
			 }

		-- 1.3.6.1.4.1.388.11.2.4.4.7.1.1
		ccMuTxRetriesNone OBJECT-TYPE
			SYNTAX Counter32
			MAX-ACCESS read-only
			STATUS current
			DESCRIPTION
				"Number of pkts successfully transmitted with no retries."
			::= { ccMuTxRetriesEntry 1 }

		
		-- 1.3.6.1.4.1.388.11.2.4.4.7.1.2
		ccMuTxRetries01 OBJECT-TYPE
			SYNTAX Counter32
			MAX-ACCESS read-only
			STATUS current
			DESCRIPTION
				"Number of pkts successfully transmitted with exactly 1 retries."
			::= { ccMuTxRetriesEntry 2 }

		
		-- 1.3.6.1.4.1.388.11.2.4.4.7.1.3
		ccMuTxRetries02 OBJECT-TYPE
			SYNTAX Counter32
			MAX-ACCESS read-only
			STATUS current
			DESCRIPTION
				"Number of pkts successfully transmitted with exactly 2 retries."
			::= { ccMuTxRetriesEntry 3 }

		
		-- 1.3.6.1.4.1.388.11.2.4.4.7.1.4
		ccMuTxRetries03 OBJECT-TYPE
			SYNTAX Counter32
			MAX-ACCESS read-only
			STATUS current
			DESCRIPTION
				"Number of pkts successfully transmitted with exactly 3 retries."
			::= { ccMuTxRetriesEntry 4 }

		
		-- 1.3.6.1.4.1.388.11.2.4.4.7.1.5
		ccMuTxRetries04 OBJECT-TYPE
			SYNTAX Counter32
			MAX-ACCESS read-only
			STATUS current
			DESCRIPTION
				"Number of pkts successfully transmitted with exactly 4 retries."
			::= { ccMuTxRetriesEntry 5 }

		
		-- 1.3.6.1.4.1.388.11.2.4.4.7.1.6
		ccMuTxRetries05 OBJECT-TYPE
			SYNTAX Counter32
			MAX-ACCESS read-only
			STATUS current
			DESCRIPTION
				"Number of pkts successfully transmitted with exactly 5 retries."
			::= { ccMuTxRetriesEntry 6 }

		
		-- 1.3.6.1.4.1.388.11.2.4.4.7.1.7
		ccMuTxRetries06 OBJECT-TYPE
			SYNTAX Counter32
			MAX-ACCESS read-only
			STATUS current
			DESCRIPTION
				"Number of pkts successfully transmitted with exactly 6 retries."
			::= { ccMuTxRetriesEntry 7 }

		
		-- 1.3.6.1.4.1.388.11.2.4.4.7.1.8
		ccMuTxRetries07 OBJECT-TYPE
			SYNTAX Counter32
			MAX-ACCESS read-only
			STATUS current
			DESCRIPTION
				"Number of pkts successfully transmitted with exactly 7 retries."
			::= { ccMuTxRetriesEntry 8 }

		
		-- 1.3.6.1.4.1.388.11.2.4.4.7.1.9
		ccMuTxRetries08 OBJECT-TYPE
			SYNTAX Counter32
			MAX-ACCESS read-only
			STATUS current
			DESCRIPTION
				"Number of pkts successfully transmitted with exactly 8 retries."
			::= { ccMuTxRetriesEntry 9 }

		
		-- 1.3.6.1.4.1.388.11.2.4.4.7.1.10
		ccMuTxRetries09 OBJECT-TYPE
			SYNTAX Counter32
			MAX-ACCESS read-only
			STATUS current
			DESCRIPTION
				"Number of pkts successfully transmitted with exactly 9 retries."
			::= { ccMuTxRetriesEntry 10 }

		
		-- 1.3.6.1.4.1.388.11.2.4.4.7.1.11
		ccMuTxRetries10 OBJECT-TYPE
			SYNTAX Counter32
			MAX-ACCESS read-only
			STATUS current
			DESCRIPTION
				"Number of pkts successfully transmitted with exactly 10 retries."
			::= { ccMuTxRetriesEntry 11 }

		
		-- 1.3.6.1.4.1.388.11.2.4.4.7.1.12
		ccMuTxRetries11 OBJECT-TYPE
			SYNTAX Counter32
			MAX-ACCESS read-only
			STATUS current
			DESCRIPTION
				"Number of pkts successfully transmitted with exactly 11 retries."
			::= { ccMuTxRetriesEntry 12 }

		
		-- 1.3.6.1.4.1.388.11.2.4.4.7.1.13
		ccMuTxRetries12 OBJECT-TYPE
			SYNTAX Counter32
			MAX-ACCESS read-only
			STATUS current
			DESCRIPTION
				"Number of pkts successfully transmitted with exactly 12 retries."
			::= { ccMuTxRetriesEntry 13 }

		
		-- 1.3.6.1.4.1.388.11.2.4.4.7.1.14
		ccMuTxRetries13 OBJECT-TYPE
			SYNTAX Counter32
			MAX-ACCESS read-only
			STATUS current
			DESCRIPTION
				"Number of pkts successfully transmitted with exactly 13 retries."
			::= { ccMuTxRetriesEntry 14 }

		
		-- 1.3.6.1.4.1.388.11.2.4.4.7.1.15
		ccMuTxRetries14 OBJECT-TYPE
			SYNTAX Counter32
			MAX-ACCESS read-only
			STATUS current
			DESCRIPTION
				"Number of pkts successfully transmitted with exactly 14 retries."
			::= { ccMuTxRetriesEntry 15 }

		
		-- 1.3.6.1.4.1.388.11.2.4.4.7.1.16
		ccMuTxRetries15 OBJECT-TYPE
			SYNTAX Counter32
			MAX-ACCESS read-only
			STATUS current
			DESCRIPTION
				"Number of pkts successfully transmitted with exactly 15 retries."
			::= { ccMuTxRetriesEntry 16 }

		
		-- 1.3.6.1.4.1.388.11.2.4.4.7.1.17
		ccMuTxRetriesFailed OBJECT-TYPE
			SYNTAX Counter32
			MAX-ACCESS read-only
			STATUS current
			DESCRIPTION
				"Number of pkts that never were successfully 
				transmitted to because the max retry count was exceeded."
			::= { ccMuTxRetriesEntry 17 }

		
		-- 1.3.6.1.4.1.388.11.2.4.4.7.1.18
		ccMuTxRetriesTotal OBJECT-TYPE
			SYNTAX Counter32
			MAX-ACCESS read-only
			STATUS current
			DESCRIPTION
				"A total sum of all retries across all packets sent
				to this MU.
				
				For example, if 4 packets have been sent, with the
				following number of retires: 2, 0, 5, gave-up,
				this value would be 2+0+5+16 = 23."
			::= { ccMuTxRetriesEntry 18 }

		
		-- 1.3.6.1.4.1.388.11.2.4.4.7.1.19
		ccMuTxRetriesMostRecent OBJECT-TYPE
			SYNTAX INTEGER (0..16)
			MAX-ACCESS read-only
			STATUS current
			DESCRIPTION
				"Most recent retry done by MU."
			::= { ccMuTxRetriesEntry 19 }

		
		-- 1.3.6.1.4.1.388.11.2.4.4.8
		ccMuLastMac OBJECT-TYPE
			SYNTAX PhysAddress
			MAX-ACCESS read-only
			STATUS current
			DESCRIPTION
				"This scalar records the MAC address of the most 
				recent MU to be Adopted, UnAdopted, or Denied."
			::= { ccMus 8 }

		
		-- 1.3.6.1.4.1.388.11.2.4.4.9
		ccMuLastReason OBJECT-TYPE
			SYNTAX INTEGER
				{
				success(1),
				aclViolation(2),
				timeout(3),
				associationFailed(4),
				authenticationFailedOn802dot1x(5),
				kerberosWrongUsername(6)
				}
			MAX-ACCESS read-only
			STATUS current
			DESCRIPTION
				"This value notes the reason for the most-recent 
				MU UnAdoption or Denial.
				
				Enum item associationFailed indicates that a key
				association field was missing, or a mismatch of
				supported rates, etc."
			::= { ccMus 9 }

		
		-- 1.3.6.1.4.1.388.11.2.4.4.10
		ccMuLastPortal OBJECT-TYPE
			SYNTAX PhysAddress
			MAX-ACCESS read-only
			STATUS current
			DESCRIPTION
				"This value notes the reason for the most-recent 
				MU UnAdoption or Denial."
			::= { ccMus 10 }

		
-- !!- OID: .100
-- 
-- (This group would have contained all the stats tables,
-- except that they were located above, before I created
-- matching groups and tables in ccPortal and ccWlan).
		-- 1.3.6.1.4.1.388.11.2.4.4.100
		ccMuRfSum OBJECT IDENTIFIER ::= { ccMus 100 }

		
		-- 1.3.6.1.4.1.388.11.2.4.4.100.1
		ccMuTxRetriesOctetsTable OBJECT-TYPE
			SYNTAX SEQUENCE OF CcMuTxRetriesOctetsEntry
			MAX-ACCESS not-accessible
			STATUS current
			DESCRIPTION
				"For each MU serviced by the switch, this table describes 
				counts of the number of octets affected by transmit 
				retries, (no retries, 1 retry, 2 retries,... gave-up)."
			::= { ccMuRfSum 1 }

		
		-- 1.3.6.1.4.1.388.11.2.4.4.100.1.1
		ccMuTxRetriesOctetsEntry OBJECT-TYPE
			SYNTAX CcMuTxRetriesOctetsEntry
			MAX-ACCESS not-accessible
			STATUS current
			DESCRIPTION
				" "
			INDEX { ccMuMac }
			::= { ccMuTxRetriesOctetsTable 1 }

		
		CcMuTxRetriesOctetsEntry ::=
			SEQUENCE { 
				ccMuTxRetriesOctetsNone
					Counter32,
				ccMuTxRetriesOctets01
					Counter32,
				ccMuTxRetriesOctets02
					Counter32,
				ccMuTxRetriesOctets03
					Counter32,
				ccMuTxRetriesOctets04
					Counter32,
				ccMuTxRetriesOctets05
					Counter32,
				ccMuTxRetriesOctets06
					Counter32,
				ccMuTxRetriesOctets07
					Counter32,
				ccMuTxRetriesOctets08
					Counter32,
				ccMuTxRetriesOctets09
					Counter32,
				ccMuTxRetriesOctets10
					Counter32,
				ccMuTxRetriesOctets11
					Counter32,
				ccMuTxRetriesOctets12
					Counter32,
				ccMuTxRetriesOctets13
					Counter32,
				ccMuTxRetriesOctets14
					Counter32,
				ccMuTxRetriesOctets15
					Counter32,
				ccMuTxRetriesOctetsFailed
					Counter32
			 }

		-- 1.3.6.1.4.1.388.11.2.4.4.100.1.1.1
		ccMuTxRetriesOctetsNone OBJECT-TYPE
			SYNTAX Counter32
			MAX-ACCESS read-only
			STATUS current
			DESCRIPTION
				"Number of octets successfully transmitted with no retries."
			::= { ccMuTxRetriesOctetsEntry 1 }

		
		-- 1.3.6.1.4.1.388.11.2.4.4.100.1.1.2
		ccMuTxRetriesOctets01 OBJECT-TYPE
			SYNTAX Counter32
			MAX-ACCESS read-only
			STATUS current
			DESCRIPTION
				"Number of octets successfully transmitted with exactly 1 retries."
			::= { ccMuTxRetriesOctetsEntry 2 }

		
		-- 1.3.6.1.4.1.388.11.2.4.4.100.1.1.3
		ccMuTxRetriesOctets02 OBJECT-TYPE
			SYNTAX Counter32
			MAX-ACCESS read-only
			STATUS current
			DESCRIPTION
				"Number of octets successfully transmitted with exactly 2 retries."
			::= { ccMuTxRetriesOctetsEntry 3 }

		
		-- 1.3.6.1.4.1.388.11.2.4.4.100.1.1.4
		ccMuTxRetriesOctets03 OBJECT-TYPE
			SYNTAX Counter32
			MAX-ACCESS read-only
			STATUS current
			DESCRIPTION
				"Number of octets successfully transmitted with exactly 3 retries."
			::= { ccMuTxRetriesOctetsEntry 4 }

		
		-- 1.3.6.1.4.1.388.11.2.4.4.100.1.1.5
		ccMuTxRetriesOctets04 OBJECT-TYPE
			SYNTAX Counter32
			MAX-ACCESS read-only
			STATUS current
			DESCRIPTION
				"Number of octets successfully transmitted with exactly 4 retries."
			::= { ccMuTxRetriesOctetsEntry 5 }

		
		-- 1.3.6.1.4.1.388.11.2.4.4.100.1.1.6
		ccMuTxRetriesOctets05 OBJECT-TYPE
			SYNTAX Counter32
			MAX-ACCESS read-only
			STATUS current
			DESCRIPTION
				"Number of octets successfully transmitted with exactly 5 retries."
			::= { ccMuTxRetriesOctetsEntry 6 }

		
		-- 1.3.6.1.4.1.388.11.2.4.4.100.1.1.7
		ccMuTxRetriesOctets06 OBJECT-TYPE
			SYNTAX Counter32
			MAX-ACCESS read-only
			STATUS current
			DESCRIPTION
				"Number of octets successfully transmitted with exactly 6 retries."
			::= { ccMuTxRetriesOctetsEntry 7 }

		
		-- 1.3.6.1.4.1.388.11.2.4.4.100.1.1.8
		ccMuTxRetriesOctets07 OBJECT-TYPE
			SYNTAX Counter32
			MAX-ACCESS read-only
			STATUS current
			DESCRIPTION
				"Number of octets successfully transmitted with exactly 7 retries."
			::= { ccMuTxRetriesOctetsEntry 8 }

		
		-- 1.3.6.1.4.1.388.11.2.4.4.100.1.1.9
		ccMuTxRetriesOctets08 OBJECT-TYPE
			SYNTAX Counter32
			MAX-ACCESS read-only
			STATUS current
			DESCRIPTION
				"Number of octets successfully transmitted with exactly 8 retries."
			::= { ccMuTxRetriesOctetsEntry 9 }

		
		-- 1.3.6.1.4.1.388.11.2.4.4.100.1.1.10
		ccMuTxRetriesOctets09 OBJECT-TYPE
			SYNTAX Counter32
			MAX-ACCESS read-only
			STATUS current
			DESCRIPTION
				"Number of octets successfully transmitted with exactly 9 retries."
			::= { ccMuTxRetriesOctetsEntry 10 }

		
		-- 1.3.6.1.4.1.388.11.2.4.4.100.1.1.11
		ccMuTxRetriesOctets10 OBJECT-TYPE
			SYNTAX Counter32
			MAX-ACCESS read-only
			STATUS current
			DESCRIPTION
				"Number of octets successfully transmitted with exactly 10 retries."
			::= { ccMuTxRetriesOctetsEntry 11 }

		
		-- 1.3.6.1.4.1.388.11.2.4.4.100.1.1.12
		ccMuTxRetriesOctets11 OBJECT-TYPE
			SYNTAX Counter32
			MAX-ACCESS read-only
			STATUS current
			DESCRIPTION
				"Number of octets successfully transmitted with exactly 11 retries."
			::= { ccMuTxRetriesOctetsEntry 12 }

		
		-- 1.3.6.1.4.1.388.11.2.4.4.100.1.1.13
		ccMuTxRetriesOctets12 OBJECT-TYPE
			SYNTAX Counter32
			MAX-ACCESS read-only
			STATUS current
			DESCRIPTION
				"Number of octets successfully transmitted with exactly 12 retries."
			::= { ccMuTxRetriesOctetsEntry 13 }

		
		-- 1.3.6.1.4.1.388.11.2.4.4.100.1.1.14
		ccMuTxRetriesOctets13 OBJECT-TYPE
			SYNTAX Counter32
			MAX-ACCESS read-only
			STATUS current
			DESCRIPTION
				"Number of octets successfully transmitted with exactly 13 retries."
			::= { ccMuTxRetriesOctetsEntry 14 }

		
		-- 1.3.6.1.4.1.388.11.2.4.4.100.1.1.15
		ccMuTxRetriesOctets14 OBJECT-TYPE
			SYNTAX Counter32
			MAX-ACCESS read-only
			STATUS current
			DESCRIPTION
				"Number of octets successfully transmitted with exactly 14 retries."
			::= { ccMuTxRetriesOctetsEntry 15 }

		
		-- 1.3.6.1.4.1.388.11.2.4.4.100.1.1.16
		ccMuTxRetriesOctets15 OBJECT-TYPE
			SYNTAX Counter32
			MAX-ACCESS read-only
			STATUS current
			DESCRIPTION
				"Number of octets successfully transmitted with exactly 15 retries."
			::= { ccMuTxRetriesOctetsEntry 16 }

		
		-- 1.3.6.1.4.1.388.11.2.4.4.100.1.1.17
		ccMuTxRetriesOctetsFailed OBJECT-TYPE
			SYNTAX Counter32
			MAX-ACCESS read-only
			STATUS current
			DESCRIPTION
				"Number of octets that never were successfully 
				transmitted to because the max retry count was exceeded."
			::= { ccMuTxRetriesOctetsEntry 17 }

		
		-- 1.3.6.1.4.1.388.11.2.4.4.100.2
		ccMuSigStatsTable OBJECT-TYPE
			SYNTAX SEQUENCE OF CcMuSigStatsEntry
			MAX-ACCESS not-accessible
			STATUS current
			DESCRIPTION
				"This table describes statistics about RSSI, Signal, Noise,
				and SNR for packets recieved via each MU serviced by the switch."
			::= { ccMuRfSum 2 }

		
		-- 1.3.6.1.4.1.388.11.2.4.4.100.2.1
		ccMuSigStatsEntry OBJECT-TYPE
			SYNTAX CcMuSigStatsEntry
			MAX-ACCESS not-accessible
			STATUS current
			DESCRIPTION
				" "
			INDEX { ccMuMac }
			::= { ccMuSigStatsTable 1 }

		
		CcMuSigStatsEntry ::=
			SEQUENCE { 
				ccMuSigStatsNumPkts
					Counter32,
				ccMuSigStatsSignalBest
					Integer32,
				ccMuSigStatsSignalWorst
					Integer32,
				ccMuSigStatsSignalSum
					Integer32,
				ccMuSigStatsSignalSumSquares
					Counter64,
				ccMuSigStatsSignalMostRecent
					Integer32,
				ccMuSigStatsNoiseBest
					Integer32,
				ccMuSigStatsNoiseWorst
					Integer32,
				ccMuSigStatsNoiseSum
					Integer32,
				ccMuSigStatsNoiseSumSquares
					Counter64,
				ccMuSigStatsNoiseMostRecent
					Integer32,
				ccMuSigStatsSnrBest
					Integer32,
				ccMuSigStatsSnrWorst
					Integer32,
				ccMuSigStatsSnrSum
					Integer32,
				ccMuSigStatsSnrSumSquares
					Counter64,
				ccMuSigStatsSnrMostRecent
					Integer32
			 }

		-- 1.3.6.1.4.1.388.11.2.4.4.100.2.1.1
		ccMuSigStatsNumPkts OBJECT-TYPE
			SYNTAX Counter32
			MAX-ACCESS read-only
			STATUS current
			DESCRIPTION
				"Total packets received included in
				all the other counters reported in this row."
			::= { ccMuSigStatsEntry 1 }

		
		-- 1.3.6.1.4.1.388.11.2.4.4.100.2.1.2
		ccMuSigStatsSignalBest OBJECT-TYPE
			SYNTAX Integer32
			UNITS "dBm"
			MAX-ACCESS read-only
			STATUS current
			DESCRIPTION
				"The best Signal value seen so far.
				(Remember that a -20dBm Signal is better than -60dBm).
				
				This value is initialized to -500dBm.
				"
			::= { ccMuSigStatsEntry 2 }

		
		-- 1.3.6.1.4.1.388.11.2.4.4.100.2.1.3
		ccMuSigStatsSignalWorst OBJECT-TYPE
			SYNTAX Integer32
			UNITS "dBm"
			MAX-ACCESS read-only
			STATUS current
			DESCRIPTION
				"The worst Signal value seen so far.
				(Remember that a -80dBm Signal is worse than -60dBm).
				
				This value is initialized to 500dBm."
			::= { ccMuSigStatsEntry 3 }

		
		-- 1.3.6.1.4.1.388.11.2.4.4.100.2.1.4
		ccMuSigStatsSignalSum OBJECT-TYPE
			SYNTAX Integer32
			UNITS "dBm"
			MAX-ACCESS read-only
			STATUS current
			DESCRIPTION
				"A running sum of all Signal values calculated by the
				switch (using reported RSSI values), for packets received.
				
				Note that this value is normally a negative value
				ranging from -10dBm to -80dBm.  It is possible for this
				value to be positive, but that would be rare, and would
				signal an exceptionally strong signal."
			::= { ccMuSigStatsEntry 4 }

		
		-- 1.3.6.1.4.1.388.11.2.4.4.100.2.1.5
		ccMuSigStatsSignalSumSquares OBJECT-TYPE
			SYNTAX Counter64
			UNITS "dBm"
			MAX-ACCESS read-only
			STATUS current
			DESCRIPTION
				"A sum of the squares of each Signal value calculated
				for packets received.
				
				Unlike _SignalSum, this value is never negative, since
				the square of a negative number is a positive."
			::= { ccMuSigStatsEntry 5 }

		
		-- 1.3.6.1.4.1.388.11.2.4.4.100.2.1.6
		ccMuSigStatsSignalMostRecent OBJECT-TYPE
			SYNTAX Integer32
			UNITS "dBm"
			MAX-ACCESS read-only
			STATUS current
			DESCRIPTION
				"The best Signal value seen so far.
				(Remember that a -20dBm Signal is better than -60dBm).
				
				This value does not make sense when ccMuSigStatsNumPkts 
				equals to 0."
			::= { ccMuSigStatsEntry 6 }

		
		-- 1.3.6.1.4.1.388.11.2.4.4.100.2.1.7
		ccMuSigStatsNoiseBest OBJECT-TYPE
			SYNTAX Integer32
			UNITS "dBm"
			MAX-ACCESS read-only
			STATUS current
			DESCRIPTION
				"The best Noise value seen so far.
				(Remember that -80dBm Noise is better than -70dBm).
				
				This value is initialized to 500dBm."
			::= { ccMuSigStatsEntry 7 }

		
		-- 1.3.6.1.4.1.388.11.2.4.4.100.2.1.8
		ccMuSigStatsNoiseWorst OBJECT-TYPE
			SYNTAX Integer32
			UNITS "dBm"
			MAX-ACCESS read-only
			STATUS current
			DESCRIPTION
				"The worst Noise value seen so far.
				(Remember that -50dBm Noise is worse than -60dBm).
				
				This value is initialized to -500dBm."
			::= { ccMuSigStatsEntry 8 }

		
		-- 1.3.6.1.4.1.388.11.2.4.4.100.2.1.9
		ccMuSigStatsNoiseSum OBJECT-TYPE
			SYNTAX Integer32
			UNITS "dBm"
			MAX-ACCESS read-only
			STATUS current
			DESCRIPTION
				"A running sum of all Noise values calculated by the
				switch (using reported RSSI values), for packets.
				
				Like _SignalSum, this value is normally a negative value."
			::= { ccMuSigStatsEntry 9 }

		
		-- 1.3.6.1.4.1.388.11.2.4.4.100.2.1.10
		ccMuSigStatsNoiseSumSquares OBJECT-TYPE
			SYNTAX Counter64
			UNITS "dBm"
			MAX-ACCESS read-only
			STATUS current
			DESCRIPTION
				"A sum of the squares of each Noise value calculated
				for packets received.
				
				As with _SignalSumSquares, this value is never negative."
			::= { ccMuSigStatsEntry 10 }

		
		-- 1.3.6.1.4.1.388.11.2.4.4.100.2.1.11
		ccMuSigStatsNoiseMostRecent OBJECT-TYPE
			SYNTAX Integer32
			UNITS "dBm"
			MAX-ACCESS read-only
			STATUS current
			DESCRIPTION
				"The best Noise value seen so far.
				(Remember that -80dBm Noise is better than -70dBm).
				
				This value does not make sense when ccMuSigStatsNumPkts 
				equals to 0."
			::= { ccMuSigStatsEntry 11 }

		
		-- 1.3.6.1.4.1.388.11.2.4.4.100.2.1.12
		ccMuSigStatsSnrBest OBJECT-TYPE
			SYNTAX Integer32
			UNITS "dB"
			MAX-ACCESS read-only
			STATUS current
			DESCRIPTION
				"The best SNR value seen so far.
				(Remember that +30dBm SNR is better than +20dBm).
				
				This value is initialized to -500dB."
			::= { ccMuSigStatsEntry 12 }

		
		-- 1.3.6.1.4.1.388.11.2.4.4.100.2.1.13
		ccMuSigStatsSnrWorst OBJECT-TYPE
			SYNTAX Integer32
			UNITS "dB"
			MAX-ACCESS read-only
			STATUS current
			DESCRIPTION
				"The worst SNR value seen so far.
				(Remember that +10dBm SNR is worse than +20dBm).
				
				This value is initialized to 500dB."
			::= { ccMuSigStatsEntry 13 }

		
		-- 1.3.6.1.4.1.388.11.2.4.4.100.2.1.14
		ccMuSigStatsSnrSum OBJECT-TYPE
			SYNTAX Integer32
			UNITS "dB"
			MAX-ACCESS read-only
			STATUS current
			DESCRIPTION
				"A running sum of all SNR values calculated by the
				switch (using reported RSSI values), for packets received.
				
				Unlike _Signal and _Noise, this value is never negative."
			::= { ccMuSigStatsEntry 14 }

		
		-- 1.3.6.1.4.1.388.11.2.4.4.100.2.1.15
		ccMuSigStatsSnrSumSquares OBJECT-TYPE
			SYNTAX Counter64
			UNITS "dB"
			MAX-ACCESS read-only
			STATUS current
			DESCRIPTION
				"A sum of the squares of each SNR value calculated
				for packets received.
				
				This value is never negative."
			::= { ccMuSigStatsEntry 15 }

		
		-- 1.3.6.1.4.1.388.11.2.4.4.100.2.1.16
		ccMuSigStatsSnrMostRecent OBJECT-TYPE
			SYNTAX Integer32
			UNITS "dB"
			MAX-ACCESS read-only
			STATUS current
			DESCRIPTION
				"The best SNR value seen so far.
				(Remember that +30dBm SNR is better than +20dBm).
				
				This value does not make sense when ccMuSigStatsNumPkts 
				equals to 0."
			::= { ccMuSigStatsEntry 16 }

		
		-- 1.3.6.1.4.1.388.11.2.4.4.100.3
		ccMuSumStatsShortTable OBJECT-TYPE
			SYNTAX SEQUENCE OF CcMuSumStatsShortEntry
			MAX-ACCESS not-accessible
			STATUS current
			DESCRIPTION
				"Averages and rates calculated over the SHORT window for
				each MU."
			::= { ccMuRfSum 3 }

		
		-- 1.3.6.1.4.1.388.11.2.4.4.100.3.1
		ccMuSumStatsShortEntry OBJECT-TYPE
			SYNTAX CcMuSumStatsShortEntry
			MAX-ACCESS not-accessible
			STATUS current
			DESCRIPTION
				" "
			INDEX { ccMuMac }
			::= { ccMuSumStatsShortTable 1 }

		
		CcMuSumStatsShortEntry ::=
			SEQUENCE { 
				ccMuSumStatsShortTimestamp
					TimeTicks,
				ccMuSumStatsShortNumPkts
					Unsigned32,
				ccMuSumStatsShortPktsPerSec100
					ScaleBy100,
				ccMuSumStatsShortPktsPerSecTx100
					ScaleBy100,
				ccMuSumStatsShortPktsPerSecRx100
					ScaleBy100,
				ccMuSumStatsShortThroughput
					Unsigned32,
				ccMuSumStatsShortThroughputTx
					Unsigned32,
				ccMuSumStatsShortThroughputRx
					Unsigned32,
				ccMuSumStatsShortAvgBitSpeed
					Unsigned32,
				ccMuSumStatsShortAvgMuSignal
					Integer32,
				ccMuSumStatsShortAvgMuNoise
					Integer32,
				ccMuSumStatsShortAvgMuSnr
					Integer32,
				ccMuSumStatsShortPp10kNUcastPkts
					PartsPer10k,
				ccMuSumStatsShortPp10kTxWithRetries
					PartsPer10k,
				ccMuSumStatsShortPp10kDropped
					PartsPer10k,
				ccMuSumStatsShortTxAvgRetries100
					ScaleBy100,
				ccMuSumStatsShortPp10kRxUndecrypt
					PartsPer10k
			 }

		-- 1.3.6.1.4.1.388.11.2.4.4.100.3.1.1
		ccMuSumStatsShortTimestamp OBJECT-TYPE
			SYNTAX TimeTicks
			MAX-ACCESS read-only
			STATUS current
			DESCRIPTION
				"Snapshot of sysUpTime as of the END of the 'window' of 
				time that this entry of values represents."
			::= { ccMuSumStatsShortEntry 1 }

		
		-- 1.3.6.1.4.1.388.11.2.4.4.100.3.1.2
		ccMuSumStatsShortNumPkts OBJECT-TYPE
			SYNTAX Unsigned32
			UNITS "packets"
			MAX-ACCESS read-only
			STATUS current
			DESCRIPTION
				"The number of packets used to calculate the statistics in
				this window."
			::= { ccMuSumStatsShortEntry 2 }

		
		-- 1.3.6.1.4.1.388.11.2.4.4.100.3.1.3
		ccMuSumStatsShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { ccMuSumStatsShortEntry 3 }

		
		-- 1.3.6.1.4.1.388.11.2.4.4.100.3.1.4
		ccMuSumStatsShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { ccMuSumStatsShortEntry 4 }

		
		-- 1.3.6.1.4.1.388.11.2.4.4.100.3.1.5
		ccMuSumStatsShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { ccMuSumStatsShortEntry 5 }

		
		-- 1.3.6.1.4.1.388.11.2.4.4.100.3.1.6
		ccMuSumStatsShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { ccMuSumStatsShortEntry 6 }

		
		-- 1.3.6.1.4.1.388.11.2.4.4.100.3.1.7
		ccMuSumStatsShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { ccMuSumStatsShortEntry 7 }

		
		-- 1.3.6.1.4.1.388.11.2.4.4.100.3.1.8
		ccMuSumStatsShortThroughputRx OBJECT-TYPE
			SYNTAX Unsigned32
			UNITS "bits per second"
			MAX-ACCESS read-only
			STATUS current
			DESCRIPTION
				"Actual number of bits RX over the window,
				divided by the number of seconds in the window."
			::= { ccMuSumStatsShortEntry 8 }

		
		-- 1.3.6.1.4.1.388.11.2.4.4.100.3.1.9
		ccMuSumStatsShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { ccMuSumStatsShortEntry 9 }

		
		-- 1.3.6.1.4.1.388.11.2.4.4.100.3.1.10
		ccMuSumStatsShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { ccMuSumStatsShortEntry 10 }

		
		-- 1.3.6.1.4.1.388.11.2.4.4.100.3.1.11
		ccMuSumStatsShortAvgMuNoise OBJECT-TYPE
			SYNTAX Integer32
			UNITS "dBm"
			MAX-ACCESS read-only
			STATUS current
			DESCRIPTION
				"The average of all noise values over the window."
			::= { ccMuSumStatsShortEntry 11 }

		
		-- 1.3.6.1.4.1.388.11.2.4.4.100.3.1.12
		ccMuSumStatsShortAvgMuSnr OBJECT-TYPE
			SYNTAX Integer32
			UNITS "dB"
			MAX-ACCESS read-only
			STATUS current
			DESCRIPTION
				"The average of all SNR values over the window."
			::= { ccMuSumStatsShortEntry 12 }

		
		-- 1.3.6.1.4.1.388.11.2.4.4.100.3.1.13
		ccMuSumStatsShortPp10kNUcastPkts OBJECT-TYPE
			SYNTAX PartsPer10k
			UNITS "parts-per-10000"
			MAX-ACCESS read-only
			STATUS current
			DESCRIPTION
				"Ratio of packets that were NOT unicast.
				
				Expressed as parts-per-10000."
			::= { ccMuSumStatsShortEntry 13 }

		
		-- 1.3.6.1.4.1.388.11.2.4.4.100.3.1.14
		ccMuSumStatsShortPp10kTxWithRetries OBJECT-TYPE
			SYNTAX PartsPer10k
			UNITS "parts-per-10000"
			MAX-ACCESS read-only
			STATUS current
			DESCRIPTION
				"Ratio of TX packets that experienced one or more retries.
				
				Expressed as parts-per-10000."
			::= { ccMuSumStatsShortEntry 14 }

		
		-- 1.3.6.1.4.1.388.11.2.4.4.100.3.1.15
		ccMuSumStatsShortPp10kDropped OBJECT-TYPE
			SYNTAX PartsPer10k
			UNITS "parts-per-10000"
			MAX-ACCESS read-only
			STATUS current
			DESCRIPTION
				"Packets dropped divided by packets sent.  Dropped here 
				means dropped intentionally due to the appropriate QoS 
				queue being full.  Other reasons for dropped packets are 
				not counted in this ratio.
				
				Calculated as an average for all WLANs implemented on 
				this MU."
			::= { ccMuSumStatsShortEntry 15 }

		
		-- 1.3.6.1.4.1.388.11.2.4.4.100.3.1.16
		ccMuSumStatsShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { ccMuSumStatsShortEntry 16 }

		
		-- 1.3.6.1.4.1.388.11.2.4.4.100.3.1.17
		ccMuSumStatsShortPp10kRxUndecrypt OBJECT-TYPE
			SYNTAX PartsPer10k
			UNITS "parts-per-10000"
			MAX-ACCESS read-only
			STATUS current
			DESCRIPTION
				"Ratio of RX packets that were undecryptable.
				
				Expressed as parts-per-10000.
				"
			::= { ccMuSumStatsShortEntry 17 }

		
		-- 1.3.6.1.4.1.388.11.2.4.4.100.4
		ccMuSumStatsLongTable OBJECT-TYPE
			SYNTAX SEQUENCE OF CcMuSumStatsLongEntry
			MAX-ACCESS not-accessible
			STATUS current
			DESCRIPTION
				"Averages and rates calculated over the LONG window for
				each MU.
				
				(Refer to ccMuSumStatsShortTable for descriptions)."
			::= { ccMuRfSum 4 }

		
		-- 1.3.6.1.4.1.388.11.2.4.4.100.4.1
		ccMuSumStatsLongEntry OBJECT-TYPE
			SYNTAX CcMuSumStatsLongEntry
			MAX-ACCESS not-accessible
			STATUS current
			DESCRIPTION
				" "
			INDEX { ccMuMac }
			::= { ccMuSumStatsLongTable 1 }

		
		CcMuSumStatsLongEntry ::=
			SEQUENCE { 
				ccMuSumStatsLongTimestamp
					TimeTicks,
				ccMuSumStatsLongNumPkts
					Unsigned32,
				ccMuSumStatsLongPktsPerSec100
					ScaleBy100,
				ccMuSumStatsLongPktsPerSecTx100
					ScaleBy100,
				ccMuSumStatsLongPktsPerSecRx100
					ScaleBy100,
				ccMuSumStatsLongThroughput
					Unsigned32,
				ccMuSumStatsLongThroughputTx
					Unsigned32,
				ccMuSumStatsLongThroughputRx
					Unsigned32,
				ccMuSumStatsLongAvgBitSpeed
					Unsigned32,
				ccMuSumStatsLongAvgMuSignal
					Integer32,
				ccMuSumStatsLongAvgMuNoise
					Integer32,
				ccMuSumStatsLongAvgMuSnr
					Integer32,
				ccMuSumStatsLongPp10kNUcastPkts
					PartsPer10k,
				ccMuSumStatsLongPp10kTxWithRetries
					PartsPer10k,
				ccMuSumStatsLongPp10kDropped
					PartsPer10k,
				ccMuSumStatsLongTxAvgRetries100
					ScaleBy100,
				ccMuSumStatsLongPp10kRxUndecrypt
					PartsPer10k
			 }

		-- 1.3.6.1.4.1.388.11.2.4.4.100.4.1.1
		ccMuSumStatsLongTimestamp OBJECT-TYPE
			SYNTAX TimeTicks
			MAX-ACCESS read-only
			STATUS current
			DESCRIPTION
				" "
			::= { ccMuSumStatsLongEntry 1 }

		
		-- 1.3.6.1.4.1.388.11.2.4.4.100.4.1.2
		ccMuSumStatsLongNumPkts OBJECT-TYPE
			SYNTAX Unsigned32
			UNITS "packets"
			MAX-ACCESS read-only
			STATUS current
			DESCRIPTION
				" "
			::= { ccMuSumStatsLongEntry 2 }

		
		-- 1.3.6.1.4.1.388.11.2.4.4.100.4.1.3
		ccMuSumStatsLongPktsPerSec100 OBJECT-TYPE
			SYNTAX ScaleBy100
			UNITS "pkts per sec x100"
			MAX-ACCESS read-only
			STATUS current
			DESCRIPTION
				" "
			::= { ccMuSumStatsLongEntry 3 }

		
		-- 1.3.6.1.4.1.388.11.2.4.4.100.4.1.4
		ccMuSumStatsLongPktsPerSecTx100 OBJECT-TYPE
			SYNTAX ScaleBy100
			UNITS "pkts per sec x100"
			MAX-ACCESS read-only
			STATUS current
			DESCRIPTION
				" "
			::= { ccMuSumStatsLongEntry 4 }

		
		-- 1.3.6.1.4.1.388.11.2.4.4.100.4.1.5
		ccMuSumStatsLongPktsPerSecRx100 OBJECT-TYPE
			SYNTAX ScaleBy100
			UNITS "pkts per sec x100"
			MAX-ACCESS read-only
			STATUS current
			DESCRIPTION
				" "
			::= { ccMuSumStatsLongEntry 5 }

		
		-- 1.3.6.1.4.1.388.11.2.4.4.100.4.1.6
		ccMuSumStatsLongThroughput OBJECT-TYPE
			SYNTAX Unsigned32
			UNITS "bits per second"
			MAX-ACCESS read-only
			STATUS current
			DESCRIPTION
				" "
			::= { ccMuSumStatsLongEntry 6 }

		
		-- 1.3.6.1.4.1.388.11.2.4.4.100.4.1.7
		ccMuSumStatsLongThroughputTx OBJECT-TYPE
			SYNTAX Unsigned32
			UNITS "bits per second"
			MAX-ACCESS read-only
			STATUS current
			DESCRIPTION
				" "
			::= { ccMuSumStatsLongEntry 7 }

		
		-- 1.3.6.1.4.1.388.11.2.4.4.100.4.1.8
		ccMuSumStatsLongThroughputRx OBJECT-TYPE
			SYNTAX Unsigned32
			UNITS "bits per second"
			MAX-ACCESS read-only
			STATUS current
			DESCRIPTION
				" "
			::= { ccMuSumStatsLongEntry 8 }

		
		-- 1.3.6.1.4.1.388.11.2.4.4.100.4.1.9
		ccMuSumStatsLongAvgBitSpeed OBJECT-TYPE
			SYNTAX Unsigned32
			UNITS "bits per second"
			MAX-ACCESS read-only
			STATUS current
			DESCRIPTION
				" "
			::= { ccMuSumStatsLongEntry 9 }

		
		-- 1.3.6.1.4.1.388.11.2.4.4.100.4.1.10
		ccMuSumStatsLongAvgMuSignal OBJECT-TYPE
			SYNTAX Integer32
			UNITS "dBm"
			MAX-ACCESS read-only
			STATUS current
			DESCRIPTION
				" "
			::= { ccMuSumStatsLongEntry 10 }

		
		-- 1.3.6.1.4.1.388.11.2.4.4.100.4.1.11
		ccMuSumStatsLongAvgMuNoise OBJECT-TYPE
			SYNTAX Integer32
			UNITS "dBm"
			MAX-ACCESS read-only
			STATUS current
			DESCRIPTION
				" "
			::= { ccMuSumStatsLongEntry 11 }

		
		-- 1.3.6.1.4.1.388.11.2.4.4.100.4.1.12
		ccMuSumStatsLongAvgMuSnr OBJECT-TYPE
			SYNTAX Integer32
			UNITS "dB"
			MAX-ACCESS read-only
			STATUS current
			DESCRIPTION
				" "
			::= { ccMuSumStatsLongEntry 12 }

		
		-- 1.3.6.1.4.1.388.11.2.4.4.100.4.1.13
		ccMuSumStatsLongPp10kNUcastPkts OBJECT-TYPE
			SYNTAX PartsPer10k
			UNITS "parts-per-10000"
			MAX-ACCESS read-only
			STATUS current
			DESCRIPTION
				" "
			::= { ccMuSumStatsLongEntry 13 }

		
		-- 1.3.6.1.4.1.388.11.2.4.4.100.4.1.14
		ccMuSumStatsLongPp10kTxWithRetries OBJECT-TYPE
			SYNTAX PartsPer10k
			UNITS "parts-per-10000"
			MAX-ACCESS read-only
			STATUS current
			DESCRIPTION
				" "
			::= { ccMuSumStatsLongEntry 14 }

		
		-- 1.3.6.1.4.1.388.11.2.4.4.100.4.1.15
		ccMuSumStatsLongPp10kDropped OBJECT-TYPE
			SYNTAX PartsPer10k
			UNITS "parts-per-10000"
			MAX-ACCESS read-only
			STATUS current
			DESCRIPTION
				" "
			::= { ccMuSumStatsLongEntry 15 }

		
		-- 1.3.6.1.4.1.388.11.2.4.4.100.4.1.16
		ccMuSumStatsLongTxAvgRetries100 OBJECT-TYPE
			SYNTAX ScaleBy100
			UNITS "average x100"
			MAX-ACCESS read-only
			STATUS current
			DESCRIPTION
				" "
			::= { ccMuSumStatsLongEntry 16 }

		
		-- 1.3.6.1.4.1.388.11.2.4.4.100.4.1.17
		ccMuSumStatsLongPp10kRxUndecrypt OBJECT-TYPE
			SYNTAX PartsPer10k
			UNITS "parts-per-10000"
			MAX-ACCESS read-only
			STATUS current
			DESCRIPTION
				" "
			::= { ccMuSumStatsLongEntry 17 }

		
-- This group describes all wireless LANs on the switch,
-- and their corresponding security settings.
		-- 1.3.6.1.4.1.388.11.2.4.5
		ccWlan OBJECT IDENTIFIER ::= { ccRf 5 }

		
		-- 1.3.6.1.4.1.388.11.2.4.5.1
		ccWlanTable OBJECT-TYPE
			SYNTAX SEQUENCE OF CcWlanEntry
			MAX-ACCESS not-accessible
			STATUS current
			DESCRIPTION
				"Table of wireless LANs configured on the switch."
			::= { ccWlan 1 }

		
		-- 1.3.6.1.4.1.388.11.2.4.5.1.1
		ccWlanEntry OBJECT-TYPE
			SYNTAX CcWlanEntry
			MAX-ACCESS not-accessible
			STATUS current
			DESCRIPTION
				" "
			INDEX { ccWlanIndex }
			::= { ccWlanTable 1 }

		
		CcWlanEntry ::=
			SEQUENCE { 
				ccWlanIndex
					Integer32,
				ccWlanName
					DisplayString,
				ccWlanEssid
					DisplayString,
				ccWlanSubnet
					SinglePointer,
				ccWlanPortalsAdopted
					MultiPointer255,
				ccWlanEnable
					StaticRowEnable,
				ccWlanDisallowMuToMu
					TruthValue,
				ccWlanVoicePrioritization
					TruthValue,
				ccWlanAnswerBroadcastEss
					TruthValue,
				ccWlanMulticastAddr1
					PhysAddress,
				ccWlanMulticastAddr2
					PhysAddress,
				ccWlanMuAclDefault
					INTEGER,
				ccWlanAuthentication
					INTEGER,
				ccWlanEncryption
					INTEGER,
				ccWlanWeight
					Integer32
			 }

		-- 1.3.6.1.4.1.388.11.2.4.5.1.1.1
		ccWlanIndex OBJECT-TYPE
			SYNTAX Integer32 (1..1001)
			MAX-ACCESS accessible-for-notify
			STATUS current
			DESCRIPTION
				"Simple index.
				
				(In the ccRfSum tables, entry 1001 is used to 
				represent the roll-up of all RF communications on 
				this switch).
				"
			::= { ccWlanEntry 1 }

		
		-- 1.3.6.1.4.1.388.11.2.4.5.1.1.2
		ccWlanName OBJECT-TYPE
			SYNTAX DisplayString
			MAX-ACCESS read-write
			STATUS current
			DESCRIPTION
				"Name of the WLAN."
			::= { ccWlanEntry 2 }

		
		-- 1.3.6.1.4.1.388.11.2.4.5.1.1.3
		ccWlanEssid OBJECT-TYPE
			SYNTAX DisplayString
			MAX-ACCESS read-write
			STATUS current
			DESCRIPTION
				"ESSID of the WLAN."
			::= { ccWlanEntry 3 }

		
		-- 1.3.6.1.4.1.388.11.2.4.5.1.1.4
		ccWlanSubnet OBJECT-TYPE
			SYNTAX SinglePointer
			MAX-ACCESS read-write
			STATUS current
			DESCRIPTION
				"The subnet/LAN this WLAN is associated with.
				
				If not associated with any subnet/LAN, this value
				will be 0."
			::= { ccWlanEntry 4 }

		
		-- 1.3.6.1.4.1.388.11.2.4.5.1.1.5
		ccWlanPortalsAdopted OBJECT-TYPE
			SYNTAX MultiPointer255
			MAX-ACCESS read-only
			STATUS current
			DESCRIPTION
				"Pointer to portal(s) adopted by this WLAN."
			::= { ccWlanEntry 5 }

		
		-- 1.3.6.1.4.1.388.11.2.4.5.1.1.6
		ccWlanEnable OBJECT-TYPE
			SYNTAX StaticRowEnable
			MAX-ACCESS read-write
			STATUS current
			DESCRIPTION
				"Row enable."
			::= { ccWlanEntry 6 }

		
		-- 1.3.6.1.4.1.388.11.2.4.5.1.1.7
		ccWlanDisallowMuToMu OBJECT-TYPE
			SYNTAX TruthValue
			MAX-ACCESS read-write
			STATUS current
			DESCRIPTION
				"Set to true to prohibit MU-to-MU communication."
			::= { ccWlanEntry 7 }

		
		-- 1.3.6.1.4.1.388.11.2.4.5.1.1.8
		ccWlanVoicePrioritization OBJECT-TYPE
			SYNTAX TruthValue
			MAX-ACCESS read-write
			STATUS current
			DESCRIPTION
				"Enable voice prioritization."
			::= { ccWlanEntry 8 }

		
		-- 1.3.6.1.4.1.388.11.2.4.5.1.1.9
		ccWlanAnswerBroadcastEss OBJECT-TYPE
			SYNTAX TruthValue
			MAX-ACCESS read-write
			STATUS current
			DESCRIPTION
				"Answer broadcast ESS."
			::= { ccWlanEntry 9 }

		
		-- 1.3.6.1.4.1.388.11.2.4.5.1.1.10
		ccWlanMulticastAddr1 OBJECT-TYPE
			SYNTAX PhysAddress
			MAX-ACCESS read-write
			STATUS current
			DESCRIPTION
				"Multicast address 1."
			::= { ccWlanEntry 10 }

		
		-- 1.3.6.1.4.1.388.11.2.4.5.1.1.11
		ccWlanMulticastAddr2 OBJECT-TYPE
			SYNTAX PhysAddress
			MAX-ACCESS read-write
			STATUS current
			DESCRIPTION
				"Multicast address 2."
			::= { ccWlanEntry 11 }

		
		-- 1.3.6.1.4.1.388.11.2.4.5.1.1.12
		ccWlanMuAclDefault OBJECT-TYPE
			SYNTAX INTEGER
				{
				allowAllMusExceptThoseMatchingAclRules(1),
				denyAllMusExceptThoseMatchingAclRules(2)
				}
			MAX-ACCESS read-write
			STATUS current
			DESCRIPTION
				"Describes the default behavior if none of this WLAN's
				ccWlanMuAclTable entries match the MAC address of an
				MU attempting to associate with this WLAN."
			::= { ccWlanEntry 12 }

		
		-- 1.3.6.1.4.1.388.11.2.4.5.1.1.13
		ccWlanAuthentication OBJECT-TYPE
			SYNTAX INTEGER
				{
				authNone(1),
				auth802dot1xEap(2),
				authKerberos(3)
				}
			MAX-ACCESS read-write
			STATUS current
			DESCRIPTION
				"If auth802dot1xEap, additional EAP settings for this
				WLAN will be used from the matching entry in the
				ccWlanAuthEapTable.
				
				Likewise, if authKerberos, use the settings in the
				matching entry in the ccWlanAuthKerberosTable."
			::= { ccWlanEntry 13 }

		
		-- 1.3.6.1.4.1.388.11.2.4.5.1.1.14
		ccWlanEncryption OBJECT-TYPE
			SYNTAX INTEGER
				{
				cryptoNone(1),
				cryptoWep40(2),
				cryptoWep104(3),
				cryptoKeyguardMcm(4),
				cryptoWpaTkip(5),
				cryptoWpa2Ccmp(6)
				}
			MAX-ACCESS read-write
			STATUS current
			DESCRIPTION
				"If cryptoWep40 or cryptoWep128, additional WEP 
				settings for this WLAN will be used from the matching
				entry in the ccWlanCryptoWepTable.
				
				Likewise, if cryptoWpaTkip, use the settings in the
				matching entry in the ccWlanCryptoWpaTable.
				
				Likewise, if cryptoKeyguardMcm, use the settings in
				the matching entry in the ccWlanCryptoKeyguardTable."
			::= { ccWlanEntry 14 }

		
		-- 1.3.6.1.4.1.388.11.2.4.5.1.1.15
		ccWlanWeight OBJECT-TYPE
			SYNTAX Integer32
			MAX-ACCESS read-write
			STATUS current
			DESCRIPTION
				"The weight to be used when QoS for all WLANs
				is set to weighted-round-robin.
				
				Note that the sum of all weights across all
				WLANs need not total 100.
				"
			::= { ccWlanEntry 15 }

		
-- This group contains authentication settings for all
-- WLANs.
		-- 1.3.6.1.4.1.388.11.2.4.5.2
		ccWlanAuth OBJECT IDENTIFIER ::= { ccWlan 2 }

		
		-- 1.3.6.1.4.1.388.11.2.4.5.2.1
		ccWlanAuthEapTable OBJECT-TYPE
			SYNTAX SEQUENCE OF CcWlanAuthEapEntry
			MAX-ACCESS not-accessible
			STATUS current
			DESCRIPTION
				"Table of EAP authentication settings for each WLAN."
			::= { ccWlanAuth 1 }

		
		-- 1.3.6.1.4.1.388.11.2.4.5.2.1.1
		ccWlanAuthEapEntry OBJECT-TYPE
			SYNTAX CcWlanAuthEapEntry
			MAX-ACCESS not-accessible
			STATUS current
			DESCRIPTION
				" "
			INDEX { ccWlanIndex }
			::= { ccWlanAuthEapTable 1 }

		
		CcWlanAuthEapEntry ::=
			SEQUENCE { 
				ccWlanAuthEapReauthenticationEnable
					TruthValue,
				ccWlanAuthEapReauthenticationPeriod
					Unsigned32,
				ccWlanAuthEapReauthenticationMaxRetries
					Unsigned32,
				ccWlanAuthEapRadius1Server
					IpAddress,
				ccWlanAuthEapRadius1Port
					Unsigned32,
				ccWlanAuthEapRadius1SharedSecret
					Password,
				ccWlanAuthEapRadius2Server
					IpAddress,
				ccWlanAuthEapRadius2Port
					Unsigned32,
				ccWlanAuthEapRadius2SharedSecret
					Password,
				ccWlanAuthEapMuQuietPeriod
					Unsigned32,
				ccWlanAuthEapMuTimeout
					Unsigned32,
				ccWlanAuthEapMuTxPeriod
					Unsigned32,
				ccWlanAuthEapMuMaxRetries
					Unsigned32,
				ccWlanAuthEapServerTimeout
					Unsigned32,
				ccWlanAuthEapServerMaxRetries
					Unsigned32,
				ccWlanAuthEapRadiusAcctMode
					TruthValue,
				ccWlanAuthEapRadiusAcctMuTimeout
					Unsigned32,
				ccWlanAuthEapRadiusAcctMuRetries
					Unsigned32,
				ccWlanAuthEapSyslogMode
					TruthValue,
				ccWlanAuthEapSyslogSeverIp
					IpAddress
			 }

		-- 1.3.6.1.4.1.388.11.2.4.5.2.1.1.1
		ccWlanAuthEapReauthenticationEnable OBJECT-TYPE
			SYNTAX TruthValue
			MAX-ACCESS read-write
			STATUS current
			DESCRIPTION
				"Enable reauthentication."
			::= { ccWlanAuthEapEntry 1 }

		
		-- 1.3.6.1.4.1.388.11.2.4.5.2.1.1.2
		ccWlanAuthEapReauthenticationPeriod OBJECT-TYPE
			SYNTAX Unsigned32 (30..9999)
			UNITS "seconds"
			MAX-ACCESS read-write
			STATUS current
			DESCRIPTION
				"Reauthentication period."
			::= { ccWlanAuthEapEntry 2 }

		
		-- 1.3.6.1.4.1.388.11.2.4.5.2.1.1.3
		ccWlanAuthEapReauthenticationMaxRetries OBJECT-TYPE
			SYNTAX Unsigned32 (1..99)
			MAX-ACCESS read-write
			STATUS current
			DESCRIPTION
				"Reauthentication max retries."
			::= { ccWlanAuthEapEntry 3 }

		
		-- 1.3.6.1.4.1.388.11.2.4.5.2.1.1.4
		ccWlanAuthEapRadius1Server OBJECT-TYPE
			SYNTAX IpAddress
			MAX-ACCESS read-write
			STATUS current
			DESCRIPTION
				"IP address of the primary RADIUS server."
			::= { ccWlanAuthEapEntry 4 }

		
		-- 1.3.6.1.4.1.388.11.2.4.5.2.1.1.5
		ccWlanAuthEapRadius1Port OBJECT-TYPE
			SYNTAX Unsigned32
			MAX-ACCESS read-write
			STATUS current
			DESCRIPTION
				"Port number of the primary RADIUS server."
			::= { ccWlanAuthEapEntry 5 }

		
		-- 1.3.6.1.4.1.388.11.2.4.5.2.1.1.6
		ccWlanAuthEapRadius1SharedSecret OBJECT-TYPE
			SYNTAX Password
			MAX-ACCESS read-write
			STATUS current
			DESCRIPTION
				"Shared secret of the primary RADIUS server."
			::= { ccWlanAuthEapEntry 6 }

		
		-- 1.3.6.1.4.1.388.11.2.4.5.2.1.1.7
		ccWlanAuthEapRadius2Server OBJECT-TYPE
			SYNTAX IpAddress
			MAX-ACCESS read-write
			STATUS current
			DESCRIPTION
				"IP address of the secondary RADIUS server."
			::= { ccWlanAuthEapEntry 7 }

		
		-- 1.3.6.1.4.1.388.11.2.4.5.2.1.1.8
		ccWlanAuthEapRadius2Port OBJECT-TYPE
			SYNTAX Unsigned32
			MAX-ACCESS read-write
			STATUS current
			DESCRIPTION
				"Port number of the secondary RADIUS server."
			::= { ccWlanAuthEapEntry 8 }

		
		-- 1.3.6.1.4.1.388.11.2.4.5.2.1.1.9
		ccWlanAuthEapRadius2SharedSecret OBJECT-TYPE
			SYNTAX Password
			MAX-ACCESS read-write
			STATUS current
			DESCRIPTION
				"Shared secret of the secondary RADIUS server."
			::= { ccWlanAuthEapEntry 9 }

		
		-- 1.3.6.1.4.1.388.11.2.4.5.2.1.1.10
		ccWlanAuthEapMuQuietPeriod OBJECT-TYPE
			SYNTAX Unsigned32 (1..65535)
			UNITS "seconds"
			MAX-ACCESS read-write
			STATUS current
			DESCRIPTION
				"MU quiet period."
			::= { ccWlanAuthEapEntry 10 }

		
		-- 1.3.6.1.4.1.388.11.2.4.5.2.1.1.11
		ccWlanAuthEapMuTimeout OBJECT-TYPE
			SYNTAX Unsigned32 (1..255)
			UNITS "seconds"
			MAX-ACCESS read-write
			STATUS current
			DESCRIPTION
				"MU timeout."
			::= { ccWlanAuthEapEntry 11 }

		
		-- 1.3.6.1.4.1.388.11.2.4.5.2.1.1.12
		ccWlanAuthEapMuTxPeriod OBJECT-TYPE
			SYNTAX Unsigned32 (1..65535)
			UNITS "seconds"
			MAX-ACCESS read-write
			STATUS current
			DESCRIPTION
				"MU Tx period."
			::= { ccWlanAuthEapEntry 12 }

		
		-- 1.3.6.1.4.1.388.11.2.4.5.2.1.1.13
		ccWlanAuthEapMuMaxRetries OBJECT-TYPE
			SYNTAX Unsigned32 (1..10)
			MAX-ACCESS read-write
			STATUS current
			DESCRIPTION
				"MU max retries."
			::= { ccWlanAuthEapEntry 13 }

		
		-- 1.3.6.1.4.1.388.11.2.4.5.2.1.1.14
		ccWlanAuthEapServerTimeout OBJECT-TYPE
			SYNTAX Unsigned32 (1..255)
			UNITS "seconds"
			MAX-ACCESS read-write
			STATUS current
			DESCRIPTION
				"Server timeout."
			::= { ccWlanAuthEapEntry 14 }

		
		-- 1.3.6.1.4.1.388.11.2.4.5.2.1.1.15
		ccWlanAuthEapServerMaxRetries OBJECT-TYPE
			SYNTAX Unsigned32 (1..255)
			MAX-ACCESS read-write
			STATUS current
			DESCRIPTION
				"Server max retries."
			::= { ccWlanAuthEapEntry 15 }

		
		-- 1.3.6.1.4.1.388.11.2.4.5.2.1.1.16
		ccWlanAuthEapRadiusAcctMode OBJECT-TYPE
			SYNTAX TruthValue
			MAX-ACCESS read-write
			STATUS current
			DESCRIPTION
				"Radius Accounting Mode."
			::= { ccWlanAuthEapEntry 16 }

		
		-- 1.3.6.1.4.1.388.11.2.4.5.2.1.1.17
		ccWlanAuthEapRadiusAcctMuTimeout OBJECT-TYPE
			SYNTAX Unsigned32 (1..255)
			MAX-ACCESS read-write
			STATUS current
			DESCRIPTION
				"Radius Accounting MU Timeout."
			::= { ccWlanAuthEapEntry 17 }

		
		-- 1.3.6.1.4.1.388.11.2.4.5.2.1.1.18
		ccWlanAuthEapRadiusAcctMuRetries OBJECT-TYPE
			SYNTAX Unsigned32 (1..10)
			MAX-ACCESS read-write
			STATUS current
			DESCRIPTION
				"Radius Accounting MU Retries."
			::= { ccWlanAuthEapEntry 18 }

		
		-- 1.3.6.1.4.1.388.11.2.4.5.2.1.1.19
		ccWlanAuthEapSyslogMode OBJECT-TYPE
			SYNTAX TruthValue
			MAX-ACCESS read-write
			STATUS current
			DESCRIPTION
				"Logging Mode."
			::= { ccWlanAuthEapEntry 19 }

		
		-- 1.3.6.1.4.1.388.11.2.4.5.2.1.1.20
		ccWlanAuthEapSyslogSeverIp OBJECT-TYPE
			SYNTAX IpAddress
			MAX-ACCESS read-write
			STATUS current
			DESCRIPTION
				"Syslog Server IP Address."
			::= { ccWlanAuthEapEntry 20 }

		
		-- 1.3.6.1.4.1.388.11.2.4.5.2.2
		ccWlanAuthKerberosTable OBJECT-TYPE
			SYNTAX SEQUENCE OF CcWlanAuthKerberosEntry
			MAX-ACCESS not-accessible
			STATUS current
			DESCRIPTION
				"Table of Kerberos authentication settings for each 
				WLAN."
			::= { ccWlanAuth 2 }

		
		-- 1.3.6.1.4.1.388.11.2.4.5.2.2.1
		ccWlanAuthKerberosEntry OBJECT-TYPE
			SYNTAX CcWlanAuthKerberosEntry
			MAX-ACCESS not-accessible
			STATUS current
			DESCRIPTION
				" "
			INDEX { ccWlanIndex }
			::= { ccWlanAuthKerberosTable 1 }

		
		CcWlanAuthKerberosEntry ::=
			SEQUENCE { 
				ccWlanAuthKerberosRealmName
					DisplayString,
				ccWlanAuthKerberosUsername
					DisplayString,
				ccWlanAuthKerberosPassword
					Password,
				ccWlanAuthKerberosKdcServerIp1
					IpAddress,
				ccWlanAuthKerberosKdcPort1
					Unsigned32,
				ccWlanAuthKerberosKdcServerIp2
					IpAddress,
				ccWlanAuthKerberosKdcPort2
					Unsigned32,
				ccWlanAuthKerberosKdcServerIpR
					IpAddress,
				ccWlanAuthKerberosKdcPortR
					Unsigned32
			 }

		-- 1.3.6.1.4.1.388.11.2.4.5.2.2.1.1
		ccWlanAuthKerberosRealmName OBJECT-TYPE
			SYNTAX DisplayString
			MAX-ACCESS read-write
			STATUS current
			DESCRIPTION
				"Realm name."
			::= { ccWlanAuthKerberosEntry 1 }

		
		-- 1.3.6.1.4.1.388.11.2.4.5.2.2.1.2
		ccWlanAuthKerberosUsername OBJECT-TYPE
			SYNTAX DisplayString
			MAX-ACCESS read-write
			STATUS current
			DESCRIPTION
				"Username."
			::= { ccWlanAuthKerberosEntry 2 }

		
		-- 1.3.6.1.4.1.388.11.2.4.5.2.2.1.3
		ccWlanAuthKerberosPassword OBJECT-TYPE
			SYNTAX Password
			MAX-ACCESS read-write
			STATUS current
			DESCRIPTION
				"Password."
			::= { ccWlanAuthKerberosEntry 3 }

		
		-- 1.3.6.1.4.1.388.11.2.4.5.2.2.1.4
		ccWlanAuthKerberosKdcServerIp1 OBJECT-TYPE
			SYNTAX IpAddress
			MAX-ACCESS read-write
			STATUS current
			DESCRIPTION
				"Primary KDC server IP addr."
			::= { ccWlanAuthKerberosEntry 4 }

		
		-- 1.3.6.1.4.1.388.11.2.4.5.2.2.1.5
		ccWlanAuthKerberosKdcPort1 OBJECT-TYPE
			SYNTAX Unsigned32
			MAX-ACCESS read-write
			STATUS current
			DESCRIPTION
				"Primary KDC port."
			::= { ccWlanAuthKerberosEntry 5 }

		
		-- 1.3.6.1.4.1.388.11.2.4.5.2.2.1.6
		ccWlanAuthKerberosKdcServerIp2 OBJECT-TYPE
			SYNTAX IpAddress
			MAX-ACCESS read-write
			STATUS current
			DESCRIPTION
				"Backup KDC server IP addr."
			::= { ccWlanAuthKerberosEntry 6 }

		
		-- 1.3.6.1.4.1.388.11.2.4.5.2.2.1.7
		ccWlanAuthKerberosKdcPort2 OBJECT-TYPE
			SYNTAX Unsigned32
			MAX-ACCESS read-write
			STATUS current
			DESCRIPTION
				"Backup KDC port."
			::= { ccWlanAuthKerberosEntry 7 }

		
		-- 1.3.6.1.4.1.388.11.2.4.5.2.2.1.8
		ccWlanAuthKerberosKdcServerIpR OBJECT-TYPE
			SYNTAX IpAddress
			MAX-ACCESS read-write
			STATUS current
			DESCRIPTION
				"Remote KDC server IP addr."
			::= { ccWlanAuthKerberosEntry 8 }

		
		-- 1.3.6.1.4.1.388.11.2.4.5.2.2.1.9
		ccWlanAuthKerberosKdcPortR OBJECT-TYPE
			SYNTAX Unsigned32
			MAX-ACCESS read-write
			STATUS current
			DESCRIPTION
				"Remote KDC port."
			::= { ccWlanAuthKerberosEntry 9 }

		
-- This group contains encryption settings for all WLANs.
		-- 1.3.6.1.4.1.388.11.2.4.5.3
		ccWlanCrypto OBJECT IDENTIFIER ::= { ccWlan 3 }

		
		-- 1.3.6.1.4.1.388.11.2.4.5.3.1
		ccWlanCryptoWepTable OBJECT-TYPE
			SYNTAX SEQUENCE OF CcWlanCryptoWepEntry
			MAX-ACCESS not-accessible
			STATUS current
			DESCRIPTION
				"Table of WEP encryption settings for each WLAN."
			::= { ccWlanCrypto 1 }

		
		-- 1.3.6.1.4.1.388.11.2.4.5.3.1.1
		ccWlanCryptoWepEntry OBJECT-TYPE
			SYNTAX CcWlanCryptoWepEntry
			MAX-ACCESS not-accessible
			STATUS current
			DESCRIPTION
				" "
			INDEX { ccWlanIndex }
			::= { ccWlanCryptoWepTable 1 }

		
		CcWlanCryptoWepEntry ::=
			SEQUENCE { 
				ccWlanCryptoWepPassKey
					Password,
				ccWlanCryptoWepKey1
					OCTET STRING,
				ccWlanCryptoWepKey2
					OCTET STRING,
				ccWlanCryptoWepKey3
					OCTET STRING,
				ccWlanCryptoWepKey4
					OCTET STRING,
				ccWlanCryptoWepKeyToUse
					Integer32
			 }

		-- 1.3.6.1.4.1.388.11.2.4.5.3.1.1.1
		ccWlanCryptoWepPassKey OBJECT-TYPE
			SYNTAX Password (SIZE (4..32))
			MAX-ACCESS read-write
			STATUS current
			DESCRIPTION
				"Pass key.
				
				If this value is written, the four WepKey1..4 will
				be overwritten."
			::= { ccWlanCryptoWepEntry 1 }

		
		-- 1.3.6.1.4.1.388.11.2.4.5.3.1.1.2
		ccWlanCryptoWepKey1 OBJECT-TYPE
			SYNTAX OCTET STRING (SIZE (0..13))
			MAX-ACCESS read-write
			STATUS current
			DESCRIPTION
				"WEP key #1
				
				exactly 13 octets for WEP-128 (104-bit key);
				exactly  5 octets for WEP-64 (40-bit key)."
			::= { ccWlanCryptoWepEntry 2 }

		
		-- 1.3.6.1.4.1.388.11.2.4.5.3.1.1.3
		ccWlanCryptoWepKey2 OBJECT-TYPE
			SYNTAX OCTET STRING (SIZE (0..13))
			MAX-ACCESS read-write
			STATUS current
			DESCRIPTION
				"WEP key #2
				
				exactly 13 octets for WEP-128 (104-bit key);
				exactly  5 octets for WEP-64 (40-bit key)."
			::= { ccWlanCryptoWepEntry 3 }

		
		-- 1.3.6.1.4.1.388.11.2.4.5.3.1.1.4
		ccWlanCryptoWepKey3 OBJECT-TYPE
			SYNTAX OCTET STRING (SIZE (0..13))
			MAX-ACCESS read-write
			STATUS current
			DESCRIPTION
				"WEP key #3
				
				exactly 13 octets for WEP-128 (104-bit key);
				exactly  5 octets for WEP-64 (40-bit key)."
			::= { ccWlanCryptoWepEntry 4 }

		
		-- 1.3.6.1.4.1.388.11.2.4.5.3.1.1.5
		ccWlanCryptoWepKey4 OBJECT-TYPE
			SYNTAX OCTET STRING (SIZE (0..13))
			MAX-ACCESS read-write
			STATUS current
			DESCRIPTION
				"WEP key #4
				
				exactly 13 octets for WEP-128 (104-bit key);
				exactly  5 octets for WEP-64 (40-bit key)."
			::= { ccWlanCryptoWepEntry 5 }

		
		-- 1.3.6.1.4.1.388.11.2.4.5.3.1.1.6
		ccWlanCryptoWepKeyToUse OBJECT-TYPE
			SYNTAX Integer32 (1..4)
			MAX-ACCESS read-write
			STATUS current
			DESCRIPTION
				"Specifies which WEP key to use."
			::= { ccWlanCryptoWepEntry 6 }

		
		-- 1.3.6.1.4.1.388.11.2.4.5.3.2
		ccWlanCryptoWpaTable OBJECT-TYPE
			SYNTAX SEQUENCE OF CcWlanCryptoWpaEntry
			MAX-ACCESS not-accessible
			STATUS current
			DESCRIPTION
				"Table of WPA-TKIP encryption settings for each WLAN."
			::= { ccWlanCrypto 2 }

		
		-- 1.3.6.1.4.1.388.11.2.4.5.3.2.1
		ccWlanCryptoWpaEntry OBJECT-TYPE
			SYNTAX CcWlanCryptoWpaEntry
			MAX-ACCESS not-accessible
			STATUS current
			DESCRIPTION
				" "
			INDEX { ccWlanIndex }
			::= { ccWlanCryptoWpaTable 1 }

		
		CcWlanCryptoWpaEntry ::=
			SEQUENCE { 
				ccWlanCryptoWpaBcastKeyRotation
					TruthValue,
				ccWlanCryptoWpaKeyRotationInterval
					Unsigned32,
				ccWlanCryptoWpaKeyToUse
					INTEGER,
				ccWlanCryptoWpaPassphrase
					OCTET STRING,
				ccWlanCryptoWpaKey
					OCTET STRING
			 }

		-- 1.3.6.1.4.1.388.11.2.4.5.3.2.1.1
		ccWlanCryptoWpaBcastKeyRotation OBJECT-TYPE
			SYNTAX TruthValue
			MAX-ACCESS read-write
			STATUS current
			DESCRIPTION
				"Use broadcast key rotation."
			::= { ccWlanCryptoWpaEntry 1 }

		
		-- 1.3.6.1.4.1.388.11.2.4.5.3.2.1.2
		ccWlanCryptoWpaKeyRotationInterval OBJECT-TYPE
			SYNTAX Unsigned32 (300..604800)
			UNITS "seconds"
			MAX-ACCESS read-write
			STATUS current
			DESCRIPTION
				"Broadcast key rotation, (if enabled), occurs every 
				this many seconds."
			::= { ccWlanCryptoWpaEntry 2 }

		
		-- 1.3.6.1.4.1.388.11.2.4.5.3.2.1.3
		ccWlanCryptoWpaKeyToUse OBJECT-TYPE
			SYNTAX INTEGER
				{
				use128bitKey(1),
				useAsciiPassPhrase(2)
				}
			MAX-ACCESS read-write
			STATUS current
			DESCRIPTION
				"Specifies which key to use."
			::= { ccWlanCryptoWpaEntry 3 }

		
		-- 1.3.6.1.4.1.388.11.2.4.5.3.2.1.4
		ccWlanCryptoWpaPassphrase OBJECT-TYPE
			SYNTAX OCTET STRING (SIZE (8..63))
			MAX-ACCESS read-write
			STATUS current
			DESCRIPTION
				"Passphrase."
			::= { ccWlanCryptoWpaEntry 4 }

		
		-- 1.3.6.1.4.1.388.11.2.4.5.3.2.1.5
		ccWlanCryptoWpaKey OBJECT-TYPE
			SYNTAX OCTET STRING (SIZE (32))
			MAX-ACCESS read-write
			STATUS current
			DESCRIPTION
				"Key."
			::= { ccWlanCryptoWpaEntry 5 }

		
		-- 1.3.6.1.4.1.388.11.2.4.5.3.3
		ccWlanCryptoKeyguardTable OBJECT-TYPE
			SYNTAX SEQUENCE OF CcWlanCryptoKeyguardEntry
			MAX-ACCESS not-accessible
			STATUS current
			DESCRIPTION
				"Table of KeyGuard-MCM encryption settings for each 
				WLAN."
			::= { ccWlanCrypto 3 }

		
		-- 1.3.6.1.4.1.388.11.2.4.5.3.3.1
		ccWlanCryptoKeyguardEntry OBJECT-TYPE
			SYNTAX CcWlanCryptoKeyguardEntry
			MAX-ACCESS not-accessible
			STATUS current
			DESCRIPTION
				" "
			INDEX { ccWlanIndex }
			::= { ccWlanCryptoKeyguardTable 1 }

		
		CcWlanCryptoKeyguardEntry ::=
			SEQUENCE { 
				ccWlanCryptoKeyguardPasskey
					OCTET STRING,
				ccWlanCryptoKeyguardKey1
					OCTET STRING,
				ccWlanCryptoKeyguardKey2
					OCTET STRING,
				ccWlanCryptoKeyguardKey3
					OCTET STRING,
				ccWlanCryptoKeyguardKey4
					OCTET STRING,
				ccWlanCryptoKeyguardKeyToUse
					Integer32
			 }

		-- 1.3.6.1.4.1.388.11.2.4.5.3.3.1.1
		ccWlanCryptoKeyguardPasskey OBJECT-TYPE
			SYNTAX OCTET STRING (SIZE (4..32))
			MAX-ACCESS read-write
			STATUS current
			DESCRIPTION
				"Pass key."
			::= { ccWlanCryptoKeyguardEntry 1 }

		
		-- 1.3.6.1.4.1.388.11.2.4.5.3.3.1.2
		ccWlanCryptoKeyguardKey1 OBJECT-TYPE
			SYNTAX OCTET STRING (SIZE (13))
			MAX-ACCESS read-write
			STATUS current
			DESCRIPTION
				"Key #1."
			::= { ccWlanCryptoKeyguardEntry 2 }

		
		-- 1.3.6.1.4.1.388.11.2.4.5.3.3.1.3
		ccWlanCryptoKeyguardKey2 OBJECT-TYPE
			SYNTAX OCTET STRING (SIZE (13))
			MAX-ACCESS read-write
			STATUS current
			DESCRIPTION
				"Key #2."
			::= { ccWlanCryptoKeyguardEntry 3 }

		
		-- 1.3.6.1.4.1.388.11.2.4.5.3.3.1.4
		ccWlanCryptoKeyguardKey3 OBJECT-TYPE
			SYNTAX OCTET STRING (SIZE (13))
			MAX-ACCESS read-write
			STATUS current
			DESCRIPTION
				"Key #3."
			::= { ccWlanCryptoKeyguardEntry 4 }

		
		-- 1.3.6.1.4.1.388.11.2.4.5.3.3.1.5
		ccWlanCryptoKeyguardKey4 OBJECT-TYPE
			SYNTAX OCTET STRING (SIZE (13))
			MAX-ACCESS read-write
			STATUS current
			DESCRIPTION
				"Key #4."
			::= { ccWlanCryptoKeyguardEntry 5 }

		
		-- 1.3.6.1.4.1.388.11.2.4.5.3.3.1.6
		ccWlanCryptoKeyguardKeyToUse OBJECT-TYPE
			SYNTAX Integer32 (1..4)
			MAX-ACCESS read-write
			STATUS current
			DESCRIPTION
				"Specifies which WEP key to use."
			::= { ccWlanCryptoKeyguardEntry 6 }

		
		-- 1.3.6.1.4.1.388.11.2.4.5.3.4
		ccWlanCryptoWpaTwoTable OBJECT-TYPE
			SYNTAX SEQUENCE OF CcWlanCryptoWpaTwoEntry
			MAX-ACCESS not-accessible
			STATUS current
			DESCRIPTION
				"Table of WPA-CCMP encryption settings for each WLAN."
			::= { ccWlanCrypto 4 }

		
		-- 1.3.6.1.4.1.388.11.2.4.5.3.4.1
		ccWlanCryptoWpaTwoEntry OBJECT-TYPE
			SYNTAX CcWlanCryptoWpaTwoEntry
			MAX-ACCESS not-accessible
			STATUS current
			DESCRIPTION
				"Description."
			INDEX { ccWlanIndex }
			::= { ccWlanCryptoWpaTwoTable 1 }

		
		CcWlanCryptoWpaTwoEntry ::=
			SEQUENCE { 
				ccWlanCryptoWpaTwoBcastKeyRotation
					TruthValue,
				ccWlanCryptoWpaTwoKeyRotationInterval
					Unsigned32,
				ccWlanCryptoWpaTwoKeyToUse
					INTEGER,
				ccWlanCryptoWpaTwoPassphrase
					Password,
				ccWlanCryptoWpaTwoKey
					OCTET STRING,
				ccWlanCryptoWpaTwoAllowTkipClient
					TruthValue,
				ccWlanCryptoWpaTwoFastRoamPreAuth
					TruthValue,
				ccWlanCryptoWpaTwoFastRoamKeyCache
					TruthValue
			 }

		-- 1.3.6.1.4.1.388.11.2.4.5.3.4.1.1
		ccWlanCryptoWpaTwoBcastKeyRotation OBJECT-TYPE
			SYNTAX TruthValue
			MAX-ACCESS read-write
			STATUS current
			DESCRIPTION
				"Use broadcast key rotation."
			::= { ccWlanCryptoWpaTwoEntry 1 }

		
		-- 1.3.6.1.4.1.388.11.2.4.5.3.4.1.2
		ccWlanCryptoWpaTwoKeyRotationInterval OBJECT-TYPE
			SYNTAX Unsigned32 (300..604800)
			UNITS "seconds"
			MAX-ACCESS read-write
			STATUS current
			DESCRIPTION
				"Broadcast key rotation, (if enabled), occurs every 
				this many seconds."
			::= { ccWlanCryptoWpaTwoEntry 2 }

		
		-- 1.3.6.1.4.1.388.11.2.4.5.3.4.1.3
		ccWlanCryptoWpaTwoKeyToUse OBJECT-TYPE
			SYNTAX INTEGER
				{
				useAsciiPassphrase(1),
				use128bitKey(2)
				}
			MAX-ACCESS read-write
			STATUS current
			DESCRIPTION
				"Specifies which key to use."
			::= { ccWlanCryptoWpaTwoEntry 3 }

		
		-- 1.3.6.1.4.1.388.11.2.4.5.3.4.1.4
		ccWlanCryptoWpaTwoPassphrase OBJECT-TYPE
			SYNTAX Password (SIZE (8..63))
			MAX-ACCESS read-write
			STATUS current
			DESCRIPTION
				"Passphrase."
			::= { ccWlanCryptoWpaTwoEntry 4 }

		
		-- 1.3.6.1.4.1.388.11.2.4.5.3.4.1.5
		ccWlanCryptoWpaTwoKey OBJECT-TYPE
			SYNTAX OCTET STRING (SIZE (32))
			MAX-ACCESS read-write
			STATUS current
			DESCRIPTION
				"Key."
			::= { ccWlanCryptoWpaTwoEntry 5 }

		
		-- 1.3.6.1.4.1.388.11.2.4.5.3.4.1.6
		ccWlanCryptoWpaTwoAllowTkipClient OBJECT-TYPE
			SYNTAX TruthValue
			MAX-ACCESS read-write
			STATUS current
			DESCRIPTION
				"WPA2-CCMP Mixed Mode enables WPA2-CCMP and WPA-TKIP Clients 
				to operate simultaneously on the network. Enabling this 
				option allows backwards compatiblity for clients that 
				support WPA-TKIP but do not support WPA2-CCMP."
			::= { ccWlanCryptoWpaTwoEntry 6 }

		
		-- 1.3.6.1.4.1.388.11.2.4.5.3.4.1.7
		ccWlanCryptoWpaTwoFastRoamPreAuth OBJECT-TYPE
			SYNTAX TruthValue
			MAX-ACCESS read-write
			STATUS current
			DESCRIPTION
				"Enabling this option enables a client associated with one 
				Access Port to carry out an 802.1x authentication with 
				another Access Port before it roams over to it. The WS2000 
				will cache the keying information of the client until it 
				roams to the new Access Port. This enables the roaming the 
				client to start sending and receiving data sooner by not 
				having to do 802.1x authentication after it roams.
				
				Note: This option only works when 802.1x authentication is 
				enabled for the WLAN. "
			::= { ccWlanCryptoWpaTwoEntry 7 }

		
		-- 1.3.6.1.4.1.388.11.2.4.5.3.4.1.8
		ccWlanCryptoWpaTwoFastRoamKeyCache OBJECT-TYPE
			SYNTAX TruthValue
			MAX-ACCESS read-write
			STATUS current
			DESCRIPTION
				"This option enables the WS2000 to use a Pairwise Master Key 
				(PMK) derived with a client on one Access Port, with the 
				same client when it roams over to another Access Port. Upon 
				roaming the client does not have to do 802.1x authentication 
				and can start sending/receiving data sooner.
				
				Note: This option only works when 802.1x authentication is 
				enabled for the WLAN. "
			::= { ccWlanCryptoWpaTwoEntry 8 }

		
		-- 1.3.6.1.4.1.388.11.2.4.5.4
		ccWlanMuAclTable OBJECT-TYPE
			SYNTAX SEQUENCE OF CcWlanMuAclEntry
			MAX-ACCESS not-accessible
			STATUS current
			DESCRIPTION
				"Table describing ACLs for allowing or denying,
				(depending on default behavior for the WLAN
				specified in ccWlanMuAclDefault), MU association with
				each WLAN."
			::= { ccWlan 4 }

		
		-- 1.3.6.1.4.1.388.11.2.4.5.4.1
		ccWlanMuAclEntry OBJECT-TYPE
			SYNTAX CcWlanMuAclEntry
			MAX-ACCESS not-accessible
			STATUS current
			DESCRIPTION
				" "
			INDEX { ccWlanIndex, ccWlanMuAclIndex }
			::= { ccWlanMuAclTable 1 }

		
		CcWlanMuAclEntry ::=
			SEQUENCE { 
				ccWlanMuAclIndex
					Integer32,
				ccWlanMuAclStartingMac
					PhysAddress,
				ccWlanMuAclEndingMac
					PhysAddress,
				ccWlanMuAclRowStatus
					AbbrevRowStatus
			 }

		-- 1.3.6.1.4.1.388.11.2.4.5.4.1.1
		ccWlanMuAclIndex OBJECT-TYPE
			SYNTAX Integer32 (1..127)
			MAX-ACCESS accessible-for-notify
			STATUS current
			DESCRIPTION
				"Simple index."
			::= { ccWlanMuAclEntry 1 }

		
		-- 1.3.6.1.4.1.388.11.2.4.5.4.1.2
		ccWlanMuAclStartingMac OBJECT-TYPE
			SYNTAX PhysAddress
			MAX-ACCESS read-write
			STATUS current
			DESCRIPTION
				"Starting MAC address in a range of addresses."
			::= { ccWlanMuAclEntry 2 }

		
		-- 1.3.6.1.4.1.388.11.2.4.5.4.1.3
		ccWlanMuAclEndingMac OBJECT-TYPE
			SYNTAX PhysAddress
			MAX-ACCESS read-write
			STATUS current
			DESCRIPTION
				"Ending MAC address in a range of addresses."
			::= { ccWlanMuAclEntry 3 }

		
		-- 1.3.6.1.4.1.388.11.2.4.5.4.1.4
		ccWlanMuAclRowStatus OBJECT-TYPE
			SYNTAX AbbrevRowStatus
			MAX-ACCESS read-write
			STATUS current
			DESCRIPTION
				"Row status."
			::= { ccWlanMuAclEntry 4 }

		
		-- 1.3.6.1.4.1.388.11.2.4.5.5
		ccWlanBwShareMode OBJECT-TYPE
			SYNTAX INTEGER
				{
				off(1),
				roundRobin(2),
				weightedRoundRobin(3)
				}
			MAX-ACCESS read-write
			STATUS current
			DESCRIPTION
				"This variable configures the manner in which
				bandwidth is shared among the WLANs.  Only in
				mode 'weightedRoundRobin' are the ccWlanWeight
				values for each WLAN used."
			::= { ccWlan 5 }

		
		-- 1.3.6.1.4.1.388.11.2.4.5.6
		ccWlanQosMonitorTable OBJECT-TYPE
			SYNTAX SEQUENCE OF CcWlanQosMonitorEntry
			MAX-ACCESS not-accessible
			STATUS current
			DESCRIPTION
				"Table of QOS values."
			::= { ccWlan 6 }

		
		-- 1.3.6.1.4.1.388.11.2.4.5.6.1
		ccWlanQosMonitorEntry OBJECT-TYPE
			SYNTAX CcWlanQosMonitorEntry
			MAX-ACCESS not-accessible
			STATUS current
			DESCRIPTION
				"Description."
			INDEX { ccWlanIndex, ccPortalIndex }
			::= { ccWlanQosMonitorTable 1 }

		
		CcWlanQosMonitorEntry ::=
			SEQUENCE { 
				ccWlanQosMonitorSent
					Counter32,
				ccWlanQosMonitorDropped
					Counter32
			 }

		-- 1.3.6.1.4.1.388.11.2.4.5.6.1.1
		ccWlanQosMonitorSent OBJECT-TYPE
			SYNTAX Counter32
			MAX-ACCESS read-only
			STATUS current
			DESCRIPTION
				"Packets Sent."
			::= { ccWlanQosMonitorEntry 1 }

		
		-- 1.3.6.1.4.1.388.11.2.4.5.6.1.2
		ccWlanQosMonitorDropped OBJECT-TYPE
			SYNTAX Counter32
			MAX-ACCESS read-only
			STATUS current
			DESCRIPTION
				"Packets Dropped."
			::= { ccWlanQosMonitorEntry 2 }

		
-- !!- OID: .100
-- 
-- Summary of RF statistics for all RF communications
-- from this switch.
-- 
-- In each table, index 1001 is the roll-up for all RF
-- communications from this switch as a whole.
		-- 1.3.6.1.4.1.388.11.2.4.5.100
		ccWlanRfSum OBJECT IDENTIFIER ::= { ccWlan 100 }

		
		-- 1.3.6.1.4.1.388.11.2.4.5.100.1
		ccWlanStatsTable OBJECT-TYPE
			SYNTAX SEQUENCE OF CcWlanStatsEntry
			MAX-ACCESS not-accessible
			STATUS current
			DESCRIPTION
				"This table describes general statistics about
				packets sent/recieved via each WLAN on the switch."
			::= { ccWlanRfSum 1 }

		
		-- 1.3.6.1.4.1.388.11.2.4.5.100.1.1
		ccWlanStatsEntry OBJECT-TYPE
			SYNTAX CcWlanStatsEntry
			MAX-ACCESS not-accessible
			STATUS current
			DESCRIPTION
				" "
			INDEX { ccWlanIndex }
			::= { ccWlanStatsTable 1 }

		
		CcWlanStatsEntry ::=
			SEQUENCE { 
				ccWlanTxPktsUcast
					Counter32,
				ccWlanRxPktsUcast
					Counter32,
				ccWlanRxPktsNUcast
					Counter32,
				ccWlanTxOctetsUcast
					Counter32,
				ccWlanRxOctetsUcast
					Counter32,
				ccWlanRxOctetsNUcast
					Counter32,
				ccWlanRxUndecryptablePkts
					Counter32,
				ccWlanLastActivity
					TimeTicks
			 }

		-- 1.3.6.1.4.1.388.11.2.4.5.100.1.1.1
		ccWlanTxPktsUcast OBJECT-TYPE
			SYNTAX Counter32
			MAX-ACCESS read-only
			STATUS current
			DESCRIPTION
				"Count of unicast packets sent."
			::= { ccWlanStatsEntry 1 }

		
		-- 1.3.6.1.4.1.388.11.2.4.5.100.1.1.2
		ccWlanRxPktsUcast OBJECT-TYPE
			SYNTAX Counter32
			MAX-ACCESS read-only
			STATUS current
			DESCRIPTION
				"Count of unicast packets received."
			::= { ccWlanStatsEntry 2 }

		
		-- 1.3.6.1.4.1.388.11.2.4.5.100.1.1.3
		ccWlanRxPktsNUcast OBJECT-TYPE
			SYNTAX Counter32
			MAX-ACCESS read-only
			STATUS current
			DESCRIPTION
				"Count of non-unicast (broadcast & multicast) 
				packets received."
			::= { ccWlanStatsEntry 3 }

		
		-- 1.3.6.1.4.1.388.11.2.4.5.100.1.1.4
		ccWlanTxOctetsUcast OBJECT-TYPE
			SYNTAX Counter32
			MAX-ACCESS read-only
			STATUS current
			DESCRIPTION
				"Count of unicast octets sent."
			::= { ccWlanStatsEntry 4 }

		
		-- 1.3.6.1.4.1.388.11.2.4.5.100.1.1.5
		ccWlanRxOctetsUcast OBJECT-TYPE
			SYNTAX Counter32
			MAX-ACCESS read-only
			STATUS current
			DESCRIPTION
				"Count of unicast octets received."
			::= { ccWlanStatsEntry 5 }

		
		-- 1.3.6.1.4.1.388.11.2.4.5.100.1.1.6
		ccWlanRxOctetsNUcast OBJECT-TYPE
			SYNTAX Counter32
			MAX-ACCESS read-only
			STATUS current
			DESCRIPTION
				"Count of non-unicast (broadcast & multicast) 
				octets received."
			::= { ccWlanStatsEntry 6 }

		
		-- 1.3.6.1.4.1.388.11.2.4.5.100.1.1.7
		ccWlanRxUndecryptablePkts OBJECT-TYPE
			SYNTAX Counter32
			MAX-ACCESS read-only
			STATUS current
			DESCRIPTION
				"Count of packets received that could
				not be decrypted."
			::= { ccWlanStatsEntry 7 }

		
		-- 1.3.6.1.4.1.388.11.2.4.5.100.1.1.8
		ccWlanLastActivity OBJECT-TYPE
			SYNTAX TimeTicks
			MAX-ACCESS read-only
			STATUS current
			DESCRIPTION
				"A snapshot of the switch's sysUpTime at the time
				of the last activity (packet sent or received)."
			::= { ccWlanStatsEntry 8 }

		
		-- 1.3.6.1.4.1.388.11.2.4.5.100.2
		ccWlanRxPktsTable OBJECT-TYPE
			SYNTAX SEQUENCE OF CcWlanRxPktsEntry
			MAX-ACCESS not-accessible
			STATUS current
			DESCRIPTION
				"For each WLAN on the switch, this table 
				describes counts of packets received at each 
				possible speed, (1Mb, 2Mb, 5.5Mb, 6Mb...)."
			::= { ccWlanRfSum 2 }

		
		-- 1.3.6.1.4.1.388.11.2.4.5.100.2.1
		ccWlanRxPktsEntry OBJECT-TYPE
			SYNTAX CcWlanRxPktsEntry
			MAX-ACCESS not-accessible
			STATUS current
			DESCRIPTION
				" "
			INDEX { ccWlanIndex }
			::= { ccWlanRxPktsTable 1 }

		
		CcWlanRxPktsEntry ::=
			SEQUENCE { 
				ccWlanRxPktsAt1Mb
					Counter32,
				ccWlanRxPktsAt2Mb
					Counter32,
				ccWlanRxPktsAt5pt5Mb
					Counter32,
				ccWlanRxPktsAt6Mb
					Counter32,
				ccWlanRxPktsAt9Mb
					Counter32,
				ccWlanRxPktsAt11Mb
					Counter32,
				ccWlanRxPktsAt12Mb
					Counter32,
				ccWlanRxPktsAt18Mb
					Counter32,
				ccWlanRxPktsAt22Mb
					Counter32,
				ccWlanRxPktsAt24Mb
					Counter32,
				ccWlanRxPktsAt36Mb
					Counter32,
				ccWlanRxPktsAt48Mb
					Counter32,
				ccWlanRxPktsAt54Mb
					Counter32
			 }

		-- 1.3.6.1.4.1.388.11.2.4.5.100.2.1.1
		ccWlanRxPktsAt1Mb OBJECT-TYPE
			SYNTAX Counter32
			MAX-ACCESS read-only
			STATUS current
			DESCRIPTION
				"Number of pkts received at 1 Mb."
			::= { ccWlanRxPktsEntry 1 }

		
		-- 1.3.6.1.4.1.388.11.2.4.5.100.2.1.2
		ccWlanRxPktsAt2Mb OBJECT-TYPE
			SYNTAX Counter32
			MAX-ACCESS read-only
			STATUS current
			DESCRIPTION
				"Number of pkts received at 2 Mb."
			::= { ccWlanRxPktsEntry 2 }

		
		-- 1.3.6.1.4.1.388.11.2.4.5.100.2.1.3
		ccWlanRxPktsAt5pt5Mb OBJECT-TYPE
			SYNTAX Counter32
			MAX-ACCESS read-only
			STATUS current
			DESCRIPTION
				"Number of pkts received at 5.5 Mb."
			::= { ccWlanRxPktsEntry 3 }

		
		-- 1.3.6.1.4.1.388.11.2.4.5.100.2.1.4
		ccWlanRxPktsAt6Mb OBJECT-TYPE
			SYNTAX Counter32
			MAX-ACCESS read-only
			STATUS current
			DESCRIPTION
				"Number of pkts received at 6 Mb."
			::= { ccWlanRxPktsEntry 4 }

		
		-- 1.3.6.1.4.1.388.11.2.4.5.100.2.1.5
		ccWlanRxPktsAt9Mb OBJECT-TYPE
			SYNTAX Counter32
			MAX-ACCESS read-only
			STATUS current
			DESCRIPTION
				"Number of pkts received at 9 Mb."
			::= { ccWlanRxPktsEntry 5 }

		
		-- 1.3.6.1.4.1.388.11.2.4.5.100.2.1.6
		ccWlanRxPktsAt11Mb OBJECT-TYPE
			SYNTAX Counter32
			MAX-ACCESS read-only
			STATUS current
			DESCRIPTION
				"Number of pkts received at 11 Mb."
			::= { ccWlanRxPktsEntry 6 }

		
		-- 1.3.6.1.4.1.388.11.2.4.5.100.2.1.7
		ccWlanRxPktsAt12Mb OBJECT-TYPE
			SYNTAX Counter32
			MAX-ACCESS read-only
			STATUS current
			DESCRIPTION
				"Number of pkts received at 12 Mb."
			::= { ccWlanRxPktsEntry 7 }

		
		-- 1.3.6.1.4.1.388.11.2.4.5.100.2.1.8
		ccWlanRxPktsAt18Mb OBJECT-TYPE
			SYNTAX Counter32
			MAX-ACCESS read-only
			STATUS current
			DESCRIPTION
				"Number of pkts received at 18 Mb."
			::= { ccWlanRxPktsEntry 8 }

		
		-- 1.3.6.1.4.1.388.11.2.4.5.100.2.1.9
		ccWlanRxPktsAt22Mb OBJECT-TYPE
			SYNTAX Counter32
			MAX-ACCESS read-only
			STATUS current
			DESCRIPTION
				"Number of pkts received at 22 Mb."
			::= { ccWlanRxPktsEntry 9 }

		
		-- 1.3.6.1.4.1.388.11.2.4.5.100.2.1.10
		ccWlanRxPktsAt24Mb OBJECT-TYPE
			SYNTAX Counter32
			MAX-ACCESS read-only
			STATUS current
			DESCRIPTION
				"Number of pkts received at 24 Mb."
			::= { ccWlanRxPktsEntry 10 }

		
		-- 1.3.6.1.4.1.388.11.2.4.5.100.2.1.11
		ccWlanRxPktsAt36Mb OBJECT-TYPE
			SYNTAX Counter32
			MAX-ACCESS read-only
			STATUS current
			DESCRIPTION
				"Number of pkts received at 36 Mb."
			::= { ccWlanRxPktsEntry 11 }

		
		-- 1.3.6.1.4.1.388.11.2.4.5.100.2.1.12
		ccWlanRxPktsAt48Mb OBJECT-TYPE
			SYNTAX Counter32
			MAX-ACCESS read-only
			STATUS current
			DESCRIPTION
				"Number of pkts received at 48 Mb."
			::= { ccWlanRxPktsEntry 12 }

		
		-- 1.3.6.1.4.1.388.11.2.4.5.100.2.1.13
		ccWlanRxPktsAt54Mb OBJECT-TYPE
			SYNTAX Counter32
			MAX-ACCESS read-only
			STATUS current
			DESCRIPTION
				"Number of pkts received at 54 Mb."
			::= { ccWlanRxPktsEntry 13 }

		
		-- 1.3.6.1.4.1.388.11.2.4.5.100.3
		ccWlanTxPktsTable OBJECT-TYPE
			SYNTAX SEQUENCE OF CcWlanTxPktsEntry
			MAX-ACCESS not-accessible
			STATUS current
			DESCRIPTION
				"For each MU serviced by the switch, this table 
				describes counts of packets transmitted at each 
				possible speed, (1Mb, 2Mb, 5.5Mb, 6Mb...)."
			::= { ccWlanRfSum 3 }

		
		-- 1.3.6.1.4.1.388.11.2.4.5.100.3.1
		ccWlanTxPktsEntry OBJECT-TYPE
			SYNTAX CcWlanTxPktsEntry
			MAX-ACCESS not-accessible
			STATUS current
			DESCRIPTION
				" "
			INDEX { ccWlanIndex }
			::= { ccWlanTxPktsTable 1 }

		
		CcWlanTxPktsEntry ::=
			SEQUENCE { 
				ccWlanTxPktsAt1Mb
					Counter32,
				ccWlanTxPktsAt2Mb
					Counter32,
				ccWlanTxPktsAt5pt5Mb
					Counter32,
				ccWlanTxPktsAt6Mb
					Counter32,
				ccWlanTxPktsAt9Mb
					Counter32,
				ccWlanTxPktsAt11Mb
					Counter32,
				ccWlanTxPktsAt12Mb
					Counter32,
				ccWlanTxPktsAt18Mb
					Counter32,
				ccWlanTxPktsAt22Mb
					Counter32,
				ccWlanTxPktsAt24Mb
					Counter32,
				ccWlanTxPktsAt36Mb
					Counter32,
				ccWlanTxPktsAt48Mb
					Counter32,
				ccWlanTxPktsAt54Mb
					Counter32
			 }

		-- 1.3.6.1.4.1.388.11.2.4.5.100.3.1.1
		ccWlanTxPktsAt1Mb OBJECT-TYPE
			SYNTAX Counter32
			MAX-ACCESS read-only
			STATUS current
			DESCRIPTION
				"Number of pkts transmitted at 1 Mb."
			::= { ccWlanTxPktsEntry 1 }

		
		-- 1.3.6.1.4.1.388.11.2.4.5.100.3.1.2
		ccWlanTxPktsAt2Mb OBJECT-TYPE
			SYNTAX Counter32
			MAX-ACCESS read-only
			STATUS current
			DESCRIPTION
				"Number of pkts transmitted at 2 Mb."
			::= { ccWlanTxPktsEntry 2 }

		
		-- 1.3.6.1.4.1.388.11.2.4.5.100.3.1.3
		ccWlanTxPktsAt5pt5Mb OBJECT-TYPE
			SYNTAX Counter32
			MAX-ACCESS read-only
			STATUS current
			DESCRIPTION
				"Number of pkts transmitted at 5.5 Mb."
			::= { ccWlanTxPktsEntry 3 }

		
		-- 1.3.6.1.4.1.388.11.2.4.5.100.3.1.4
		ccWlanTxPktsAt6Mb OBJECT-TYPE
			SYNTAX Counter32
			MAX-ACCESS read-only
			STATUS current
			DESCRIPTION
				"Number of pkts transmitted at 6 Mb."
			::= { ccWlanTxPktsEntry 4 }

		
		-- 1.3.6.1.4.1.388.11.2.4.5.100.3.1.5
		ccWlanTxPktsAt9Mb OBJECT-TYPE
			SYNTAX Counter32
			MAX-ACCESS read-only
			STATUS current
			DESCRIPTION
				"Number of pkts transmitted at 9 Mb."
			::= { ccWlanTxPktsEntry 5 }

		
		-- 1.3.6.1.4.1.388.11.2.4.5.100.3.1.6
		ccWlanTxPktsAt11Mb OBJECT-TYPE
			SYNTAX Counter32
			MAX-ACCESS read-only
			STATUS current
			DESCRIPTION
				"Number of pkts transmitted at 11 Mb."
			::= { ccWlanTxPktsEntry 6 }

		
		-- 1.3.6.1.4.1.388.11.2.4.5.100.3.1.7
		ccWlanTxPktsAt12Mb OBJECT-TYPE
			SYNTAX Counter32
			MAX-ACCESS read-only
			STATUS current
			DESCRIPTION
				"Number of pkts transmitted at 12 Mb."
			::= { ccWlanTxPktsEntry 7 }

		
		-- 1.3.6.1.4.1.388.11.2.4.5.100.3.1.8
		ccWlanTxPktsAt18Mb OBJECT-TYPE
			SYNTAX Counter32
			MAX-ACCESS read-only
			STATUS current
			DESCRIPTION
				"Number of pkts transmitted at 18 Mb."
			::= { ccWlanTxPktsEntry 8 }

		
		-- 1.3.6.1.4.1.388.11.2.4.5.100.3.1.9
		ccWlanTxPktsAt22Mb OBJECT-TYPE
			SYNTAX Counter32
			MAX-ACCESS read-only
			STATUS current
			DESCRIPTION
				"Number of pkts transmitted at 22 Mb."
			::= { ccWlanTxPktsEntry 9 }

		
		-- 1.3.6.1.4.1.388.11.2.4.5.100.3.1.10
		ccWlanTxPktsAt24Mb OBJECT-TYPE
			SYNTAX Counter32
			MAX-ACCESS read-only
			STATUS current
			DESCRIPTION
				"Number of pkts transmitted at 24 Mb."
			::= { ccWlanTxPktsEntry 10 }

		
		-- 1.3.6.1.4.1.388.11.2.4.5.100.3.1.11
		ccWlanTxPktsAt36Mb OBJECT-TYPE
			SYNTAX Counter32
			MAX-ACCESS read-only
			STATUS current
			DESCRIPTION
				"Number of pkts transmitted at 36 Mb."
			::= { ccWlanTxPktsEntry 11 }

		
		-- 1.3.6.1.4.1.388.11.2.4.5.100.3.1.12
		ccWlanTxPktsAt48Mb OBJECT-TYPE
			SYNTAX Counter32
			MAX-ACCESS read-only
			STATUS current
			DESCRIPTION
				"Number of pkts transmitted at 48 Mb."
			::= { ccWlanTxPktsEntry 12 }

		
		-- 1.3.6.1.4.1.388.11.2.4.5.100.3.1.13
		ccWlanTxPktsAt54Mb OBJECT-TYPE
			SYNTAX Counter32
			MAX-ACCESS read-only
			STATUS current
			DESCRIPTION
				"Number of pkts transmitted at 54 Mb."
			::= { ccWlanTxPktsEntry 13 }

		
		-- 1.3.6.1.4.1.388.11.2.4.5.100.4
		ccWlanRxOctetsTable OBJECT-TYPE
			SYNTAX SEQUENCE OF CcWlanRxOctetsEntry
			MAX-ACCESS not-accessible
			STATUS current
			DESCRIPTION
				"For each MU serviced by this switch, this table 
				describes counts of octets received at each 
				possible speed, (1Mb, 2Mb, 5.5Mb, 6Mb...)."
			::= { ccWlanRfSum 4 }

		
		-- 1.3.6.1.4.1.388.11.2.4.5.100.4.1
		ccWlanRxOctetsEntry OBJECT-TYPE
			SYNTAX CcWlanRxOctetsEntry
			MAX-ACCESS not-accessible
			STATUS current
			DESCRIPTION
				" "
			INDEX { ccWlanIndex }
			::= { ccWlanRxOctetsTable 1 }

		
		CcWlanRxOctetsEntry ::=
			SEQUENCE { 
				ccWlanRxOctetsAt1Mb
					Counter32,
				ccWlanRxOctetsAt2Mb
					Counter32,
				ccWlanRxOctetsAt5pt5Mb
					Counter32,
				ccWlanRxOctetsAt6Mb
					Counter32,
				ccWlanRxOctetsAt9Mb
					Counter32,
				ccWlanRxOctetsAt11Mb
					Counter32,
				ccWlanRxOctetsAt12Mb
					Counter32,
				ccWlanRxOctetsAt18Mb
					Counter32,
				ccWlanRxOctetsAt22Mb
					Counter32,
				ccWlanRxOctetsAt24Mb
					Counter32,
				ccWlanRxOctetsAt36Mb
					Counter32,
				ccWlanRxOctetsAt48Mb
					Counter32,
				ccWlanRxOctetsAt54Mb
					Counter32
			 }

		-- 1.3.6.1.4.1.388.11.2.4.5.100.4.1.1
		ccWlanRxOctetsAt1Mb OBJECT-TYPE
			SYNTAX Counter32
			MAX-ACCESS read-only
			STATUS current
			DESCRIPTION
				"Number of octets received at 1 Mb."
			::= { ccWlanRxOctetsEntry 1 }

		
		-- 1.3.6.1.4.1.388.11.2.4.5.100.4.1.2
		ccWlanRxOctetsAt2Mb OBJECT-TYPE
			SYNTAX Counter32
			MAX-ACCESS read-only
			STATUS current
			DESCRIPTION
				"Number of octets received at 2 Mb."
			::= { ccWlanRxOctetsEntry 2 }

		
		-- 1.3.6.1.4.1.388.11.2.4.5.100.4.1.3
		ccWlanRxOctetsAt5pt5Mb OBJECT-TYPE
			SYNTAX Counter32
			MAX-ACCESS read-only
			STATUS current
			DESCRIPTION
				"Number of octets received at 5.5 Mb."
			::= { ccWlanRxOctetsEntry 3 }

		
		-- 1.3.6.1.4.1.388.11.2.4.5.100.4.1.4
		ccWlanRxOctetsAt6Mb OBJECT-TYPE
			SYNTAX Counter32
			MAX-ACCESS read-only
			STATUS current
			DESCRIPTION
				"Number of octets received at 6 Mb."
			::= { ccWlanRxOctetsEntry 4 }

		
		-- 1.3.6.1.4.1.388.11.2.4.5.100.4.1.5
		ccWlanRxOctetsAt9Mb OBJECT-TYPE
			SYNTAX Counter32
			MAX-ACCESS read-only
			STATUS current
			DESCRIPTION
				"Number of octets received at 9 Mb."
			::= { ccWlanRxOctetsEntry 5 }

		
		-- 1.3.6.1.4.1.388.11.2.4.5.100.4.1.6
		ccWlanRxOctetsAt11Mb OBJECT-TYPE
			SYNTAX Counter32
			MAX-ACCESS read-only
			STATUS current
			DESCRIPTION
				"Number of octets received at 11 Mb."
			::= { ccWlanRxOctetsEntry 6 }

		
		-- 1.3.6.1.4.1.388.11.2.4.5.100.4.1.7
		ccWlanRxOctetsAt12Mb OBJECT-TYPE
			SYNTAX Counter32
			MAX-ACCESS read-only
			STATUS current
			DESCRIPTION
				"Number of octets received at 12 Mb."
			::= { ccWlanRxOctetsEntry 7 }

		
		-- 1.3.6.1.4.1.388.11.2.4.5.100.4.1.8
		ccWlanRxOctetsAt18Mb OBJECT-TYPE
			SYNTAX Counter32
			MAX-ACCESS read-only
			STATUS current
			DESCRIPTION
				"Number of octets received at 18 Mb."
			::= { ccWlanRxOctetsEntry 8 }

		
		-- 1.3.6.1.4.1.388.11.2.4.5.100.4.1.9
		ccWlanRxOctetsAt22Mb OBJECT-TYPE
			SYNTAX Counter32
			MAX-ACCESS read-only
			STATUS current
			DESCRIPTION
				"Number of octets received at 22 Mb."
			::= { ccWlanRxOctetsEntry 9 }

		
		-- 1.3.6.1.4.1.388.11.2.4.5.100.4.1.10
		ccWlanRxOctetsAt24Mb OBJECT-TYPE
			SYNTAX Counter32
			MAX-ACCESS read-only
			STATUS current
			DESCRIPTION
				"Number of octets received at 24 Mb."
			::= { ccWlanRxOctetsEntry 10 }

		
		-- 1.3.6.1.4.1.388.11.2.4.5.100.4.1.11
		ccWlanRxOctetsAt36Mb OBJECT-TYPE
			SYNTAX Counter32
			MAX-ACCESS read-only
			STATUS current
			DESCRIPTION
				"Number of octets received at 36 Mb."
			::= { ccWlanRxOctetsEntry 11 }

		
		-- 1.3.6.1.4.1.388.11.2.4.5.100.4.1.12
		ccWlanRxOctetsAt48Mb OBJECT-TYPE
			SYNTAX Counter32
			MAX-ACCESS read-only
			STATUS current
			DESCRIPTION
				"Number of octets received at 48 Mb."
			::= { ccWlanRxOctetsEntry 12 }

		
		-- 1.3.6.1.4.1.388.11.2.4.5.100.4.1.13
		ccWlanRxOctetsAt54Mb OBJECT-TYPE
			SYNTAX Counter32
			MAX-ACCESS read-only
			STATUS current
			DESCRIPTION
				"Number of octets received at 54 Mb."
			::= { ccWlanRxOctetsEntry 13 }

		
		-- 1.3.6.1.4.1.388.11.2.4.5.100.5
		ccWlanTxOctetsTable OBJECT-TYPE
			SYNTAX SEQUENCE OF CcWlanTxOctetsEntry
			MAX-ACCESS not-accessible
			STATUS current
			DESCRIPTION
				"For each WLAN on this switch, this table 
				describes counts of octets transmitted at each 
				possible speed, (1Mb, 2Mb, 5.5Mb, 6Mb...)."
			::= { ccWlanRfSum 5 }

		
		-- 1.3.6.1.4.1.388.11.2.4.5.100.5.1
		ccWlanTxOctetsEntry OBJECT-TYPE
			SYNTAX CcWlanTxOctetsEntry
			MAX-ACCESS not-accessible
			STATUS current
			DESCRIPTION
				" "
			INDEX { ccWlanIndex }
			::= { ccWlanTxOctetsTable 1 }

		
		CcWlanTxOctetsEntry ::=
			SEQUENCE { 
				ccWlanTxOctetsAt1Mb
					Counter32,
				ccWlanTxOctetsAt2Mb
					Counter32,
				ccWlanTxOctetsAt5pt5Mb
					Counter32,
				ccWlanTxOctetsAt6Mb
					Counter32,
				ccWlanTxOctetsAt9Mb
					Counter32,
				ccWlanTxOctetsAt11Mb
					Counter32,
				ccWlanTxOctetsAt12Mb
					Counter32,
				ccWlanTxOctetsAt18Mb
					Counter32,
				ccWlanTxOctetsAt22Mb
					Counter32,
				ccWlanTxOctetsAt24Mb
					Counter32,
				ccWlanTxOctetsAt36Mb
					Counter32,
				ccWlanTxOctetsAt48Mb
					Counter32,
				ccWlanTxOctetsAt54Mb
					Counter32
			 }

		-- 1.3.6.1.4.1.388.11.2.4.5.100.5.1.1
		ccWlanTxOctetsAt1Mb OBJECT-TYPE
			SYNTAX Counter32
			MAX-ACCESS read-only
			STATUS current
			DESCRIPTION
				"Number of octets transmitted at 1 Mb."
			::= { ccWlanTxOctetsEntry 1 }

		
		-- 1.3.6.1.4.1.388.11.2.4.5.100.5.1.2
		ccWlanTxOctetsAt2Mb OBJECT-TYPE
			SYNTAX Counter32
			MAX-ACCESS read-only
			STATUS current
			DESCRIPTION
				"Number of octets transmitted at 2 Mb."
			::= { ccWlanTxOctetsEntry 2 }

		
		-- 1.3.6.1.4.1.388.11.2.4.5.100.5.1.3
		ccWlanTxOctetsAt5pt5Mb OBJECT-TYPE
			SYNTAX Counter32
			MAX-ACCESS read-only
			STATUS current
			DESCRIPTION
				"Number of octets transmitted at 5.5 Mb."
			::= { ccWlanTxOctetsEntry 3 }

		
		-- 1.3.6.1.4.1.388.11.2.4.5.100.5.1.4
		ccWlanTxOctetsAt6Mb OBJECT-TYPE
			SYNTAX Counter32
			MAX-ACCESS read-only
			STATUS current
			DESCRIPTION
				"Number of octets transmitted at 6 Mb."
			::= { ccWlanTxOctetsEntry 4 }

		
		-- 1.3.6.1.4.1.388.11.2.4.5.100.5.1.5
		ccWlanTxOctetsAt9Mb OBJECT-TYPE
			SYNTAX Counter32
			MAX-ACCESS read-only
			STATUS current
			DESCRIPTION
				"Number of octets transmitted at 9 Mb."
			::= { ccWlanTxOctetsEntry 5 }

		
		-- 1.3.6.1.4.1.388.11.2.4.5.100.5.1.6
		ccWlanTxOctetsAt11Mb OBJECT-TYPE
			SYNTAX Counter32
			MAX-ACCESS read-only
			STATUS current
			DESCRIPTION
				"Number of octets transmitted at 11 Mb."
			::= { ccWlanTxOctetsEntry 6 }

		
		-- 1.3.6.1.4.1.388.11.2.4.5.100.5.1.7
		ccWlanTxOctetsAt12Mb OBJECT-TYPE
			SYNTAX Counter32
			MAX-ACCESS read-only
			STATUS current
			DESCRIPTION
				"Number of octets transmitted at 12 Mb."
			::= { ccWlanTxOctetsEntry 7 }

		
		-- 1.3.6.1.4.1.388.11.2.4.5.100.5.1.8
		ccWlanTxOctetsAt18Mb OBJECT-TYPE
			SYNTAX Counter32
			MAX-ACCESS read-only
			STATUS current
			DESCRIPTION
				"Number of octets transmitted at 18 Mb."
			::= { ccWlanTxOctetsEntry 8 }

		
		-- 1.3.6.1.4.1.388.11.2.4.5.100.5.1.9
		ccWlanTxOctetsAt22Mb OBJECT-TYPE
			SYNTAX Counter32
			MAX-ACCESS read-only
			STATUS current
			DESCRIPTION
				"Number of octets transmitted at 22 Mb."
			::= { ccWlanTxOctetsEntry 9 }

		
		-- 1.3.6.1.4.1.388.11.2.4.5.100.5.1.10
		ccWlanTxOctetsAt24Mb OBJECT-TYPE
			SYNTAX Counter32
			MAX-ACCESS read-only
			STATUS current
			DESCRIPTION
				"Number of octets transmitted at 24 Mb."
			::= { ccWlanTxOctetsEntry 10 }

		
		-- 1.3.6.1.4.1.388.11.2.4.5.100.5.1.11
		ccWlanTxOctetsAt36Mb OBJECT-TYPE
			SYNTAX Counter32
			MAX-ACCESS read-only
			STATUS current
			DESCRIPTION
				"Number of octets transmitted at 36 Mb."
			::= { ccWlanTxOctetsEntry 11 }

		
		-- 1.3.6.1.4.1.388.11.2.4.5.100.5.1.12
		ccWlanTxOctetsAt48Mb OBJECT-TYPE
			SYNTAX Counter32
			MAX-ACCESS read-only
			STATUS current
			DESCRIPTION
				"Number of octets transmitted at 48 Mb."
			::= { ccWlanTxOctetsEntry 12 }

		
		-- 1.3.6.1.4.1.388.11.2.4.5.100.5.1.13
		ccWlanTxOctetsAt54Mb OBJECT-TYPE
			SYNTAX Counter32
			MAX-ACCESS read-only
			STATUS current
			DESCRIPTION
				"Number of octets transmitted at 54 Mb."
			::= { ccWlanTxOctetsEntry 13 }

		
		-- 1.3.6.1.4.1.388.11.2.4.5.100.6
		ccWlanTxRetriesPktsTable OBJECT-TYPE
			SYNTAX SEQUENCE OF CcWlanTxRetriesPktsEntry
			MAX-ACCESS not-accessible
			STATUS current
			DESCRIPTION
				"For each WLAN on the switch, this table describes 
				counts of the number of packets affected by transmit 
				retries, (no retries, 1 retry, 2 retries,... gave-up)."
			::= { ccWlanRfSum 6 }

		
		-- 1.3.6.1.4.1.388.11.2.4.5.100.6.1
		ccWlanTxRetriesPktsEntry OBJECT-TYPE
			SYNTAX CcWlanTxRetriesPktsEntry
			MAX-ACCESS not-accessible
			STATUS current
			DESCRIPTION
				" "
			INDEX { ccWlanIndex }
			::= { ccWlanTxRetriesPktsTable 1 }

		
		CcWlanTxRetriesPktsEntry ::=
			SEQUENCE { 
				ccWlanTxRetriesPktsNone
					Counter32,
				ccWlanTxRetriesPkts01
					Counter32,
				ccWlanTxRetriesPkts02
					Counter32,
				ccWlanTxRetriesPkts03
					Counter32,
				ccWlanTxRetriesPkts04
					Counter32,
				ccWlanTxRetriesPkts05
					Counter32,
				ccWlanTxRetriesPkts06
					Counter32,
				ccWlanTxRetriesPkts07
					Counter32,
				ccWlanTxRetriesPkts08
					Counter32,
				ccWlanTxRetriesPkts09
					Counter32,
				ccWlanTxRetriesPkts10
					Counter32,
				ccWlanTxRetriesPkts11
					Counter32,
				ccWlanTxRetriesPkts12
					Counter32,
				ccWlanTxRetriesPkts13
					Counter32,
				ccWlanTxRetriesPkts14
					Counter32,
				ccWlanTxRetriesPkts15
					Counter32,
				ccWlanTxRetriesPktsFailed
					Counter32
			 }

		-- 1.3.6.1.4.1.388.11.2.4.5.100.6.1.1
		ccWlanTxRetriesPktsNone OBJECT-TYPE
			SYNTAX Counter32
			MAX-ACCESS read-only
			STATUS current
			DESCRIPTION
				"Number of pkts successfully transmitted with no retries."
			::= { ccWlanTxRetriesPktsEntry 1 }

		
		-- 1.3.6.1.4.1.388.11.2.4.5.100.6.1.2
		ccWlanTxRetriesPkts01 OBJECT-TYPE
			SYNTAX Counter32
			MAX-ACCESS read-only
			STATUS current
			DESCRIPTION
				"Number of pkts successfully transmitted with exactly 1 retries."
			::= { ccWlanTxRetriesPktsEntry 2 }

		
		-- 1.3.6.1.4.1.388.11.2.4.5.100.6.1.3
		ccWlanTxRetriesPkts02 OBJECT-TYPE
			SYNTAX Counter32
			MAX-ACCESS read-only
			STATUS current
			DESCRIPTION
				"Number of pkts successfully transmitted with exactly 2 retries."
			::= { ccWlanTxRetriesPktsEntry 3 }

		
		-- 1.3.6.1.4.1.388.11.2.4.5.100.6.1.4
		ccWlanTxRetriesPkts03 OBJECT-TYPE
			SYNTAX Counter32
			MAX-ACCESS read-only
			STATUS current
			DESCRIPTION
				"Number of pkts successfully transmitted with exactly 3 retries."
			::= { ccWlanTxRetriesPktsEntry 4 }

		
		-- 1.3.6.1.4.1.388.11.2.4.5.100.6.1.5
		ccWlanTxRetriesPkts04 OBJECT-TYPE
			SYNTAX Counter32
			MAX-ACCESS read-only
			STATUS current
			DESCRIPTION
				"Number of pkts successfully transmitted with exactly 4 retries."
			::= { ccWlanTxRetriesPktsEntry 5 }

		
		-- 1.3.6.1.4.1.388.11.2.4.5.100.6.1.6
		ccWlanTxRetriesPkts05 OBJECT-TYPE
			SYNTAX Counter32
			MAX-ACCESS read-only
			STATUS current
			DESCRIPTION
				"Number of pkts successfully transmitted with exactly 5 retries."
			::= { ccWlanTxRetriesPktsEntry 6 }

		
		-- 1.3.6.1.4.1.388.11.2.4.5.100.6.1.7
		ccWlanTxRetriesPkts06 OBJECT-TYPE
			SYNTAX Counter32
			MAX-ACCESS read-only
			STATUS current
			DESCRIPTION
				"Number of pkts successfully transmitted with exactly 6 retries."
			::= { ccWlanTxRetriesPktsEntry 7 }

		
		-- 1.3.6.1.4.1.388.11.2.4.5.100.6.1.8
		ccWlanTxRetriesPkts07 OBJECT-TYPE
			SYNTAX Counter32
			MAX-ACCESS read-only
			STATUS current
			DESCRIPTION
				"Number of pkts successfully transmitted with exactly 7 retries."
			::= { ccWlanTxRetriesPktsEntry 8 }

		
		-- 1.3.6.1.4.1.388.11.2.4.5.100.6.1.9
		ccWlanTxRetriesPkts08 OBJECT-TYPE
			SYNTAX Counter32
			MAX-ACCESS read-only
			STATUS current
			DESCRIPTION
				"Number of pkts successfully transmitted with exactly 8 retries."
			::= { ccWlanTxRetriesPktsEntry 9 }

		
		-- 1.3.6.1.4.1.388.11.2.4.5.100.6.1.10
		ccWlanTxRetriesPkts09 OBJECT-TYPE
			SYNTAX Counter32
			MAX-ACCESS read-only
			STATUS current
			DESCRIPTION
				"Number of pkts successfully transmitted with exactly 9 retries."
			::= { ccWlanTxRetriesPktsEntry 10 }

		
		-- 1.3.6.1.4.1.388.11.2.4.5.100.6.1.11
		ccWlanTxRetriesPkts10 OBJECT-TYPE
			SYNTAX Counter32
			MAX-ACCESS read-only
			STATUS current
			DESCRIPTION
				"Number of pkts successfully transmitted with exactly 10 retries."
			::= { ccWlanTxRetriesPktsEntry 11 }

		
		-- 1.3.6.1.4.1.388.11.2.4.5.100.6.1.12
		ccWlanTxRetriesPkts11 OBJECT-TYPE
			SYNTAX Counter32
			MAX-ACCESS read-only
			STATUS current
			DESCRIPTION
				"Number of pkts successfully transmitted with exactly 11 retries."
			::= { ccWlanTxRetriesPktsEntry 12 }

		
		-- 1.3.6.1.4.1.388.11.2.4.5.100.6.1.13
		ccWlanTxRetriesPkts12 OBJECT-TYPE
			SYNTAX Counter32
			MAX-ACCESS read-only
			STATUS current
			DESCRIPTION
				"Number of pkts successfully transmitted with exactly 12 retries."
			::= { ccWlanTxRetriesPktsEntry 13 }

		
		-- 1.3.6.1.4.1.388.11.2.4.5.100.6.1.14
		ccWlanTxRetriesPkts13 OBJECT-TYPE
			SYNTAX Counter32
			MAX-ACCESS read-only
			STATUS current
			DESCRIPTION
				"Number of pkts successfully transmitted with exactly 13 retries."
			::= { ccWlanTxRetriesPktsEntry 14 }

		
		-- 1.3.6.1.4.1.388.11.2.4.5.100.6.1.15
		ccWlanTxRetriesPkts14 OBJECT-TYPE
			SYNTAX Counter32
			MAX-ACCESS read-only
			STATUS current
			DESCRIPTION
				"Number of pkts successfully transmitted with exactly 14 retries."
			::= { ccWlanTxRetriesPktsEntry 15 }

		
		-- 1.3.6.1.4.1.388.11.2.4.5.100.6.1.16
		ccWlanTxRetriesPkts15 OBJECT-TYPE
			SYNTAX Counter32
			MAX-ACCESS read-only
			STATUS current
			DESCRIPTION
				"Number of pkts successfully transmitted with exactly 15 retries."
			::= { ccWlanTxRetriesPktsEntry 16 }

		
		-- 1.3.6.1.4.1.388.11.2.4.5.100.6.1.17
		ccWlanTxRetriesPktsFailed OBJECT-TYPE
			SYNTAX Counter32
			MAX-ACCESS read-only
			STATUS current
			DESCRIPTION
				"Number of pkts that never were successfully 
				transmitted to because the max retry count was exceeded."
			::= { ccWlanTxRetriesPktsEntry 17 }

		
		-- 1.3.6.1.4.1.388.11.2.4.5.100.7
		ccWlanTxRetriesOctetsTable OBJECT-TYPE
			SYNTAX SEQUENCE OF CcWlanTxRetriesOctetsEntry
			MAX-ACCESS not-accessible
			STATUS current
			DESCRIPTION
				"For each WLAN on the switch, this table describes 
				counts of the number of octets affected by transmit 
				retries, (no retries, 1 retry, 2 retries,... gave-up)."
			::= { ccWlanRfSum 7 }

		
		-- 1.3.6.1.4.1.388.11.2.4.5.100.7.1
		ccWlanTxRetriesOctetsEntry OBJECT-TYPE
			SYNTAX CcWlanTxRetriesOctetsEntry
			MAX-ACCESS not-accessible
			STATUS current
			DESCRIPTION
				" "
			INDEX { ccWlanIndex }
			::= { ccWlanTxRetriesOctetsTable 1 }

		
		CcWlanTxRetriesOctetsEntry ::=
			SEQUENCE { 
				ccWlanTxRetriesOctetsNone
					Counter32,
				ccWlanTxRetriesOctets01
					Counter32,
				ccWlanTxRetriesOctets02
					Counter32,
				ccWlanTxRetriesOctets03
					Counter32,
				ccWlanTxRetriesOctets04
					Counter32,
				ccWlanTxRetriesOctets05
					Counter32,
				ccWlanTxRetriesOctets06
					Counter32,
				ccWlanTxRetriesOctets07
					Counter32,
				ccWlanTxRetriesOctets08
					Counter32,
				ccWlanTxRetriesOctets09
					Counter32,
				ccWlanTxRetriesOctets10
					Counter32,
				ccWlanTxRetriesOctets11
					Counter32,
				ccWlanTxRetriesOctets12
					Counter32,
				ccWlanTxRetriesOctets13
					Counter32,
				ccWlanTxRetriesOctets14
					Counter32,
				ccWlanTxRetriesOctets15
					Counter32,
				ccWlanTxRetriesOctetsFailed
					Counter32
			 }

		-- 1.3.6.1.4.1.388.11.2.4.5.100.7.1.1
		ccWlanTxRetriesOctetsNone OBJECT-TYPE
			SYNTAX Counter32
			MAX-ACCESS read-only
			STATUS current
			DESCRIPTION
				"Number of octets successfully transmitted with no retries."
			::= { ccWlanTxRetriesOctetsEntry 1 }

		
		-- 1.3.6.1.4.1.388.11.2.4.5.100.7.1.2
		ccWlanTxRetriesOctets01 OBJECT-TYPE
			SYNTAX Counter32
			MAX-ACCESS read-only
			STATUS current
			DESCRIPTION
				"Number of octets successfully transmitted with exactly 1 retries."
			::= { ccWlanTxRetriesOctetsEntry 2 }

		
		-- 1.3.6.1.4.1.388.11.2.4.5.100.7.1.3
		ccWlanTxRetriesOctets02 OBJECT-TYPE
			SYNTAX Counter32
			MAX-ACCESS read-only
			STATUS current
			DESCRIPTION
				"Number of octets successfully transmitted with exactly 2 retries."
			::= { ccWlanTxRetriesOctetsEntry 3 }

		
		-- 1.3.6.1.4.1.388.11.2.4.5.100.7.1.4
		ccWlanTxRetriesOctets03 OBJECT-TYPE
			SYNTAX Counter32
			MAX-ACCESS read-only
			STATUS current
			DESCRIPTION
				"Number of octets successfully transmitted with exactly 3 retries."
			::= { ccWlanTxRetriesOctetsEntry 4 }

		
		-- 1.3.6.1.4.1.388.11.2.4.5.100.7.1.5
		ccWlanTxRetriesOctets04 OBJECT-TYPE
			SYNTAX Counter32
			MAX-ACCESS read-only
			STATUS current
			DESCRIPTION
				"Number of octets successfully transmitted with exactly 4 retries."
			::= { ccWlanTxRetriesOctetsEntry 5 }

		
		-- 1.3.6.1.4.1.388.11.2.4.5.100.7.1.6
		ccWlanTxRetriesOctets05 OBJECT-TYPE
			SYNTAX Counter32
			MAX-ACCESS read-only
			STATUS current
			DESCRIPTION
				"Number of octets successfully transmitted with exactly 5 retries."
			::= { ccWlanTxRetriesOctetsEntry 6 }

		
		-- 1.3.6.1.4.1.388.11.2.4.5.100.7.1.7
		ccWlanTxRetriesOctets06 OBJECT-TYPE
			SYNTAX Counter32
			MAX-ACCESS read-only
			STATUS current
			DESCRIPTION
				"Number of octets successfully transmitted with exactly 6 retries."
			::= { ccWlanTxRetriesOctetsEntry 7 }

		
		-- 1.3.6.1.4.1.388.11.2.4.5.100.7.1.8
		ccWlanTxRetriesOctets07 OBJECT-TYPE
			SYNTAX Counter32
			MAX-ACCESS read-only
			STATUS current
			DESCRIPTION
				"Number of octets successfully transmitted with exactly 7 retries."
			::= { ccWlanTxRetriesOctetsEntry 8 }

		
		-- 1.3.6.1.4.1.388.11.2.4.5.100.7.1.9
		ccWlanTxRetriesOctets08 OBJECT-TYPE
			SYNTAX Counter32
			MAX-ACCESS read-only
			STATUS current
			DESCRIPTION
				"Number of octets successfully transmitted with exactly 8 retries."
			::= { ccWlanTxRetriesOctetsEntry 9 }

		
		-- 1.3.6.1.4.1.388.11.2.4.5.100.7.1.10
		ccWlanTxRetriesOctets09 OBJECT-TYPE
			SYNTAX Counter32
			MAX-ACCESS read-only
			STATUS current
			DESCRIPTION
				"Number of octets successfully transmitted with exactly 9 retries."
			::= { ccWlanTxRetriesOctetsEntry 10 }

		
		-- 1.3.6.1.4.1.388.11.2.4.5.100.7.1.11
		ccWlanTxRetriesOctets10 OBJECT-TYPE
			SYNTAX Counter32
			MAX-ACCESS read-only
			STATUS current
			DESCRIPTION
				"Number of octets successfully transmitted with exactly 10 retries."
			::= { ccWlanTxRetriesOctetsEntry 11 }

		
		-- 1.3.6.1.4.1.388.11.2.4.5.100.7.1.12
		ccWlanTxRetriesOctets11 OBJECT-TYPE
			SYNTAX Counter32
			MAX-ACCESS read-only
			STATUS current
			DESCRIPTION
				"Number of octets successfully transmitted with exactly 11 retries."
			::= { ccWlanTxRetriesOctetsEntry 12 }

		
		-- 1.3.6.1.4.1.388.11.2.4.5.100.7.1.13
		ccWlanTxRetriesOctets12 OBJECT-TYPE
			SYNTAX Counter32
			MAX-ACCESS read-only
			STATUS current
			DESCRIPTION
				"Number of octets successfully transmitted with exactly 12 retries."
			::= { ccWlanTxRetriesOctetsEntry 13 }

		
		-- 1.3.6.1.4.1.388.11.2.4.5.100.7.1.14
		ccWlanTxRetriesOctets13 OBJECT-TYPE
			SYNTAX Counter32
			MAX-ACCESS read-only
			STATUS current
			DESCRIPTION
				"Number of octets successfully transmitted with exactly 13 retries."
			::= { ccWlanTxRetriesOctetsEntry 14 }

		
		-- 1.3.6.1.4.1.388.11.2.4.5.100.7.1.15
		ccWlanTxRetriesOctets14 OBJECT-TYPE
			SYNTAX Counter32
			MAX-ACCESS read-only
			STATUS current
			DESCRIPTION
				"Number of octets successfully transmitted with exactly 14 retries."
			::= { ccWlanTxRetriesOctetsEntry 15 }

		
		-- 1.3.6.1.4.1.388.11.2.4.5.100.7.1.16
		ccWlanTxRetriesOctets15 OBJECT-TYPE
			SYNTAX Counter32
			MAX-ACCESS read-only
			STATUS current
			DESCRIPTION
				"Number of octets successfully transmitted with exactly 15 retries."
			::= { ccWlanTxRetriesOctetsEntry 16 }

		
		-- 1.3.6.1.4.1.388.11.2.4.5.100.7.1.17
		ccWlanTxRetriesOctetsFailed OBJECT-TYPE
			SYNTAX Counter32
			MAX-ACCESS read-only
			STATUS current
			DESCRIPTION
				"Number of octets that never were successfully 
				transmitted to because the max retry count was exceeded."
			::= { ccWlanTxRetriesOctetsEntry 17 }

		
		-- 1.3.6.1.4.1.388.11.2.4.5.100.8
		ccWlanSigStatsTable OBJECT-TYPE
			SYNTAX SEQUENCE OF CcWlanSigStatsEntry
			MAX-ACCESS not-accessible
			STATUS current
			DESCRIPTION
				"This table describes statistics about RSSI, Signal, Noise,
				and SNR for packets recieved via each WLAN on the switch."
			::= { ccWlanRfSum 8 }

		
		-- 1.3.6.1.4.1.388.11.2.4.5.100.8.1
		ccWlanSigStatsEntry OBJECT-TYPE
			SYNTAX CcWlanSigStatsEntry
			MAX-ACCESS not-accessible
			STATUS current
			DESCRIPTION
				" "
			INDEX { ccWlanIndex }
			::= { ccWlanSigStatsTable 1 }

		
		CcWlanSigStatsEntry ::=
			SEQUENCE { 
				ccWlanSigStatsNumPkts
					Counter32,
				ccWlanSigStatsSignalBest
					Integer32,
				ccWlanSigStatsSignalWorst
					Integer32,
				ccWlanSigStatsSignalSum
					Integer32,
				ccWlanSigStatsSignalSumSquares
					Counter64,
				ccWlanSigStatsNoiseBest
					Integer32,
				ccWlanSigStatsNoiseWorst
					Integer32,
				ccWlanSigStatsNoiseSum
					Integer32,
				ccWlanSigStatsNoiseSumSquares
					Counter64,
				ccWlanSigStatsSnrBest
					Integer32,
				ccWlanSigStatsSnrWorst
					Integer32,
				ccWlanSigStatsSnrSum
					Integer32,
				ccWlanSigStatsSnrSumSquares
					Counter64
			 }

		-- 1.3.6.1.4.1.388.11.2.4.5.100.8.1.1
		ccWlanSigStatsNumPkts OBJECT-TYPE
			SYNTAX Counter32
			MAX-ACCESS read-only
			STATUS current
			DESCRIPTION
				"Total packets received included in
				all the other counters reported in this row."
			::= { ccWlanSigStatsEntry 1 }

		
		-- 1.3.6.1.4.1.388.11.2.4.5.100.8.1.2
		ccWlanSigStatsSignalBest OBJECT-TYPE
			SYNTAX Integer32
			UNITS "dBm"
			MAX-ACCESS read-only
			STATUS current
			DESCRIPTION
				"The best Signal value seen so far.
				(Remember that a -20dBm Signal is better than -60dBm).
				
				This value is initialized to -500dBm."
			::= { ccWlanSigStatsEntry 2 }

		
		-- 1.3.6.1.4.1.388.11.2.4.5.100.8.1.3
		ccWlanSigStatsSignalWorst OBJECT-TYPE
			SYNTAX Integer32
			UNITS "dBm"
			MAX-ACCESS read-only
			STATUS current
			DESCRIPTION
				"The worst Signal value seen so far.
				(Remember that a -80dBm Signal is worse than -60dBm).
				
				This value is initialized to 500dBm."
			::= { ccWlanSigStatsEntry 3 }

		
		-- 1.3.6.1.4.1.388.11.2.4.5.100.8.1.4
		ccWlanSigStatsSignalSum OBJECT-TYPE
			SYNTAX Integer32
			UNITS "dBm"
			MAX-ACCESS read-only
			STATUS current
			DESCRIPTION
				"A running sum of all Signal values calculated by the
				switch (using reported RSSI values), for packets received.
				
				Note that this value is normally a negative value
				ranging from -10dBm to -80dBm.  It is possible for this
				value to be positive, but that would be rare, and would
				signal an exceptionally strong signal."
			::= { ccWlanSigStatsEntry 4 }

		
		-- 1.3.6.1.4.1.388.11.2.4.5.100.8.1.5
		ccWlanSigStatsSignalSumSquares OBJECT-TYPE
			SYNTAX Counter64
			UNITS "dBm"
			MAX-ACCESS read-only
			STATUS current
			DESCRIPTION
				"A sum of the squares of each Signal value calculated
				for packets received.
				
				Unlike _SignalSum, this value is never negative, since
				the square of a negative number is a positive."
			::= { ccWlanSigStatsEntry 5 }

		
		-- 1.3.6.1.4.1.388.11.2.4.5.100.8.1.6
		ccWlanSigStatsNoiseBest OBJECT-TYPE
			SYNTAX Integer32
			UNITS "dBm"
			MAX-ACCESS read-only
			STATUS current
			DESCRIPTION
				"The best Noise value seen so far.
				(Remember that -80dBm Noise is better than -70dBm).
				
				This value is initialized to 500dBm."
			::= { ccWlanSigStatsEntry 6 }

		
		-- 1.3.6.1.4.1.388.11.2.4.5.100.8.1.7
		ccWlanSigStatsNoiseWorst OBJECT-TYPE
			SYNTAX Integer32
			UNITS "dBm"
			MAX-ACCESS read-only
			STATUS current
			DESCRIPTION
				"The worst Noise value seen so far.
				(Remember that -50dBm Noise is worse than -60dBm).
				
				This value is initialized to -500dBm."
			::= { ccWlanSigStatsEntry 7 }

		
		-- 1.3.6.1.4.1.388.11.2.4.5.100.8.1.8
		ccWlanSigStatsNoiseSum OBJECT-TYPE
			SYNTAX Integer32
			UNITS "dBm"
			MAX-ACCESS read-only
			STATUS current
			DESCRIPTION
				"A running sum of all Noise values calculated by the
				switch (using reported RSSI values), for packets.
				
				Like _SignalSum, this value is normally a negative value."
			::= { ccWlanSigStatsEntry 8 }

		
		-- 1.3.6.1.4.1.388.11.2.4.5.100.8.1.9
		ccWlanSigStatsNoiseSumSquares OBJECT-TYPE
			SYNTAX Counter64
			UNITS "dBm"
			MAX-ACCESS read-only
			STATUS current
			DESCRIPTION
				"A sum of the squares of each Noise value calculated
				for packets received.
				
				As with _SignalSumSquares, this value is never negative."
			::= { ccWlanSigStatsEntry 9 }

		
		-- 1.3.6.1.4.1.388.11.2.4.5.100.8.1.10
		ccWlanSigStatsSnrBest OBJECT-TYPE
			SYNTAX Integer32
			UNITS "dB"
			MAX-ACCESS read-only
			STATUS current
			DESCRIPTION
				"The best SNR value seen so far.
				(Remember that +30dBm SNR is better than +20dBm).
				
				This value is initialized to -500dB."
			::= { ccWlanSigStatsEntry 10 }

		
		-- 1.3.6.1.4.1.388.11.2.4.5.100.8.1.11
		ccWlanSigStatsSnrWorst OBJECT-TYPE
			SYNTAX Integer32
			UNITS "dB"
			MAX-ACCESS read-only
			STATUS current
			DESCRIPTION
				"The worst SNR value seen so far.
				(Remember that +10dBm SNR is worse than +20dBm).
				
				This value is initialized to 500dB."
			::= { ccWlanSigStatsEntry 11 }

		
		-- 1.3.6.1.4.1.388.11.2.4.5.100.8.1.12
		ccWlanSigStatsSnrSum OBJECT-TYPE
			SYNTAX Integer32
			UNITS "dB"
			MAX-ACCESS read-only
			STATUS current
			DESCRIPTION
				"A running sum of all SNR values calculated by the
				switch (using reported RSSI values), for packets received.
				
				Unlike _Signal and _Noise, this value is never negative."
			::= { ccWlanSigStatsEntry 12 }

		
		-- 1.3.6.1.4.1.388.11.2.4.5.100.8.1.13
		ccWlanSigStatsSnrSumSquares OBJECT-TYPE
			SYNTAX Counter64
			UNITS "dB"
			MAX-ACCESS read-only
			STATUS current
			DESCRIPTION
				"A sum of the squares of each SNR value calculated
				for packets received.
				
				This value is never negative."
			::= { ccWlanSigStatsEntry 13 }

		
-- The switch roll-up values are reported at entry/instance
-- 1001, as with the other ccWlanRfSum tables.  Note, however,
-- that the switch reports very few of the values that WLANs
-- report, and will return NO-SUCH for those values on GET,
-- and will 'skip-over' those columns for GET-NEXT.
		-- 1.3.6.1.4.1.388.11.2.4.5.100.9
		ccWlanSumStatsShortTable OBJECT-TYPE
			SYNTAX SEQUENCE OF CcWlanSumStatsShortEntry
			MAX-ACCESS not-accessible
			STATUS current
			DESCRIPTION
				"Averages and rates calculated over the SHORT window for
				each WLAN."
			::= { ccWlanRfSum 9 }

		
		-- 1.3.6.1.4.1.388.11.2.4.5.100.9.1
		ccWlanSumStatsShortEntry OBJECT-TYPE
			SYNTAX CcWlanSumStatsShortEntry
			MAX-ACCESS not-accessible
			STATUS current
			DESCRIPTION
				" "
			INDEX { ccWlanIndex }
			::= { ccWlanSumStatsShortTable 1 }

		
		CcWlanSumStatsShortEntry ::=
			SEQUENCE { 
				ccWlanSumStatsShortTimestamp
					TimeTicks,
				ccWlanSumStatsShortNumPkts
					Unsigned32,
				ccWlanSumStatsShortPktsPerSec100
					ScaleBy100,
				ccWlanSumStatsShortPktsPerSecTx100
					ScaleBy100,
				ccWlanSumStatsShortPktsPerSecRx100
					ScaleBy100,
				ccWlanSumStatsShortThroughput
					Unsigned32,
				ccWlanSumStatsShortThroughputTx
					Unsigned32,
				ccWlanSumStatsShortThroughputRx
					Unsigned32,
				ccWlanSumStatsShortAvgBitSpeed
					Unsigned32,
				ccWlanSumStatsShortAvgMuSignal
					Integer32,
				ccWlanSumStatsShortAvgMuNoise
					Integer32,
				ccWlanSumStatsShortAvgMuSnr
					Integer32,
				ccWlanSumStatsShortPp10kNUcastPkts
					PartsPer10k,
				ccWlanSumStatsShortPp10kTxWithRetries
					PartsPer10k,
				ccWlanSumStatsShortPp10kDropped
					PartsPer10k,
				ccWlanSumStatsShortTxAvgRetries100
					ScaleBy100,
				ccWlanSumStatsShortPp10kRxUndecrypt
					PartsPer10k,
				ccWlanSumStatsShortTotalMus
					Unsigned32,
				ccWlanSumStatsShortSkip1
					Integer32
			 }

		-- 1.3.6.1.4.1.388.11.2.4.5.100.9.1.1
		ccWlanSumStatsShortTimestamp OBJECT-TYPE
			SYNTAX TimeTicks
			MAX-ACCESS read-only
			STATUS current
			DESCRIPTION
				"Snapshot of sysUpTime as of the END of the 'window' of 
				time that this entry of values represents."
			::= { ccWlanSumStatsShortEntry 1 }

		
		-- 1.3.6.1.4.1.388.11.2.4.5.100.9.1.2
		ccWlanSumStatsShortNumPkts OBJECT-TYPE
			SYNTAX Unsigned32
			UNITS "packets"
			MAX-ACCESS read-only
			STATUS current
			DESCRIPTION
				"The number of packets used to calculate the statistics in
				this window."
			::= { ccWlanSumStatsShortEntry 2 }

		
		-- 1.3.6.1.4.1.388.11.2.4.5.100.9.1.3
		ccWlanSumStatsShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { ccWlanSumStatsShortEntry 3 }

		
		-- 1.3.6.1.4.1.388.11.2.4.5.100.9.1.4
		ccWlanSumStatsShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { ccWlanSumStatsShortEntry 4 }

		
		-- 1.3.6.1.4.1.388.11.2.4.5.100.9.1.5
		ccWlanSumStatsShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { ccWlanSumStatsShortEntry 5 }

		
		-- 1.3.6.1.4.1.388.11.2.4.5.100.9.1.6
		ccWlanSumStatsShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { ccWlanSumStatsShortEntry 6 }

		
		-- 1.3.6.1.4.1.388.11.2.4.5.100.9.1.7
		ccWlanSumStatsShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { ccWlanSumStatsShortEntry 7 }

		
		-- 1.3.6.1.4.1.388.11.2.4.5.100.9.1.8
		ccWlanSumStatsShortThroughputRx OBJECT-TYPE
			SYNTAX Unsigned32
			UNITS "bits per second"
			MAX-ACCESS read-only
			STATUS current
			DESCRIPTION
				"Actual number of bits RX over the window,
				divided by the number of seconds in the window."
			::= { ccWlanSumStatsShortEntry 8 }

		
		-- 1.3.6.1.4.1.388.11.2.4.5.100.9.1.9
		ccWlanSumStatsShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { ccWlanSumStatsShortEntry 9 }

		
		-- 1.3.6.1.4.1.388.11.2.4.5.100.9.1.10
		ccWlanSumStatsShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { ccWlanSumStatsShortEntry 10 }

		
		-- 1.3.6.1.4.1.388.11.2.4.5.100.9.1.11
		ccWlanSumStatsShortAvgMuNoise OBJECT-TYPE
			SYNTAX Integer32
			UNITS "dBm"
			MAX-ACCESS read-only
			STATUS current
			DESCRIPTION
				"The average of all noise values over the window."
			::= { ccWlanSumStatsShortEntry 11 }

		
		-- 1.3.6.1.4.1.388.11.2.4.5.100.9.1.12
		ccWlanSumStatsShortAvgMuSnr OBJECT-TYPE
			SYNTAX Integer32
			UNITS "dB"
			MAX-ACCESS read-only
			STATUS current
			DESCRIPTION
				"The average of all SNR values over the window."
			::= { ccWlanSumStatsShortEntry 12 }

		
		-- 1.3.6.1.4.1.388.11.2.4.5.100.9.1.13
		ccWlanSumStatsShortPp10kNUcastPkts OBJECT-TYPE
			SYNTAX PartsPer10k
			UNITS "parts-per-10000"
			MAX-ACCESS read-only
			STATUS current
			DESCRIPTION
				"Ratio of packets that were NOT unicast.
				
				Expressed as parts-per-10000."
			::= { ccWlanSumStatsShortEntry 13 }

		
		-- 1.3.6.1.4.1.388.11.2.4.5.100.9.1.14
		ccWlanSumStatsShortPp10kTxWithRetries OBJECT-TYPE
			SYNTAX PartsPer10k
			UNITS "parts-per-10000"
			MAX-ACCESS read-only
			STATUS current
			DESCRIPTION
				"Ratio of TX packets that experienced one or more retries.
				
				Expressed as parts-per-10000."
			::= { ccWlanSumStatsShortEntry 14 }

		
		-- 1.3.6.1.4.1.388.11.2.4.5.100.9.1.15
		ccWlanSumStatsShortPp10kDropped OBJECT-TYPE
			SYNTAX PartsPer10k
			UNITS "parts-per-10000"
			MAX-ACCESS read-only
			STATUS current
			DESCRIPTION
				"Packets dropped divided by packets sent.  Dropped here 
				means dropped intentionally due to the appropriate QoS 
				queue being full.  Other reasons for dropped packets are 
				not counted in this ratio."
			::= { ccWlanSumStatsShortEntry 15 }

		
		-- 1.3.6.1.4.1.388.11.2.4.5.100.9.1.16
		ccWlanSumStatsShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { ccWlanSumStatsShortEntry 16 }

		
		-- 1.3.6.1.4.1.388.11.2.4.5.100.9.1.17
		ccWlanSumStatsShortPp10kRxUndecrypt OBJECT-TYPE
			SYNTAX PartsPer10k
			UNITS "parts-per-10000"
			MAX-ACCESS read-only
			STATUS current
			DESCRIPTION
				"Ratio of RX packets that were undecryptable.
				
				Expressed as parts-per-10000."
			::= { ccWlanSumStatsShortEntry 17 }

		
		-- 1.3.6.1.4.1.388.11.2.4.5.100.9.1.18
		ccWlanSumStatsShortTotalMus OBJECT-TYPE
			SYNTAX Unsigned32 (0..100)
			UNITS "number of MUs"
			MAX-ACCESS read-only
			STATUS current
			DESCRIPTION
				"The number of packets used to calculate the statistics in
				this window for all MUs associated with WLAN."
			::= { ccWlanSumStatsShortEntry 18 }

		
		-- 1.3.6.1.4.1.388.11.2.4.5.100.9.1.19
		ccWlanSumStatsShortSkip1 OBJECT-TYPE
			SYNTAX Integer32
			MAX-ACCESS read-write
			STATUS obsolete
			DESCRIPTION
				"Not relevant for WS2000 2.0."
			::= { ccWlanSumStatsShortEntry 19 }
-- place-holder so _Pp10kDropped falls at same OID for
-- both Portal and Wlan summary tables.
-- 
		
-- The switch roll-up values are reported at entry/instance
-- 1001, as with the other ccWlanRfSum tables.  Note, however,
-- that the switch reports very few of the values that WLANs
-- report, and will return NO-SUCH for those values on GET,
-- and will 'skip-over' those columns for GET-NEXT.
		-- 1.3.6.1.4.1.388.11.2.4.5.100.10
		ccWlanSumStatsLongTable OBJECT-TYPE
			SYNTAX SEQUENCE OF CcWlanSumStatsLongEntry
			MAX-ACCESS not-accessible
			STATUS current
			DESCRIPTION
				"Averages and rates calculated over the LONG window for
				each WLAN.
				
				(Refer to ccWlanSumStatsShortTable for descriptions)."
			::= { ccWlanRfSum 10 }

		
		-- 1.3.6.1.4.1.388.11.2.4.5.100.10.1
		ccWlanSumStatsLongEntry OBJECT-TYPE
			SYNTAX CcWlanSumStatsLongEntry
			MAX-ACCESS not-accessible
			STATUS current
			DESCRIPTION
				" "
			INDEX { ccWlanIndex }
			::= { ccWlanSumStatsLongTable 1 }

		
		CcWlanSumStatsLongEntry ::=
			SEQUENCE { 
				ccWlanSumStatsLongTimestamp
					TimeTicks,
				ccWlanSumStatsLongNumPkts
					Unsigned32,
				ccWlanSumStatsLongPktsPerSec100
					ScaleBy100,
				ccWlanSumStatsLongPktsPerSecTx100
					ScaleBy100,
				ccWlanSumStatsLongPktsPerSecRx100
					ScaleBy100,
				ccWlanSumStatsLongThroughput
					Unsigned32,
				ccWlanSumStatsLongThroughputTx
					Unsigned32,
				ccWlanSumStatsLongThroughputRx
					Unsigned32,
				ccWlanSumStatsLongAvgBitSpeed
					Unsigned32,
				ccWlanSumStatsLongAvgMuSignal
					Integer32,
				ccWlanSumStatsLongAvgMuNoise
					Integer32,
				ccWlanSumStatsLongAvgMuSnr
					Integer32,
				ccWlanSumStatsLongPp10kNUcastPkts
					PartsPer10k,
				ccWlanSumStatsLongPp10kTxWithRetries
					PartsPer10k,
				ccWlanSumStatsLongPp10kDropped
					PartsPer10k,
				ccWlanSumStatsLongTxAvgRetries100
					ScaleBy100,
				ccWlanSumStatsLongPp10kRxUndecrypt
					PartsPer10k,
				ccWlanSumStatsLongTotalMus
					Unsigned32,
				ccWlanSumStatsLongSkip1
					Integer32
			 }

		-- 1.3.6.1.4.1.388.11.2.4.5.100.10.1.1
		ccWlanSumStatsLongTimestamp OBJECT-TYPE
			SYNTAX TimeTicks
			MAX-ACCESS read-only
			STATUS current
			DESCRIPTION
				" "
			::= { ccWlanSumStatsLongEntry 1 }

		
		-- 1.3.6.1.4.1.388.11.2.4.5.100.10.1.2
		ccWlanSumStatsLongNumPkts OBJECT-TYPE
			SYNTAX Unsigned32
			UNITS "packets"
			MAX-ACCESS read-only
			STATUS current
			DESCRIPTION
				" "
			::= { ccWlanSumStatsLongEntry 2 }

		
		-- 1.3.6.1.4.1.388.11.2.4.5.100.10.1.3
		ccWlanSumStatsLongPktsPerSec100 OBJECT-TYPE
			SYNTAX ScaleBy100
			UNITS "pkts per sec x100"
			MAX-ACCESS read-only
			STATUS current
			DESCRIPTION
				" "
			::= { ccWlanSumStatsLongEntry 3 }

		
		-- 1.3.6.1.4.1.388.11.2.4.5.100.10.1.4
		ccWlanSumStatsLongPktsPerSecTx100 OBJECT-TYPE
			SYNTAX ScaleBy100
			UNITS "pkts per sec x100"
			MAX-ACCESS read-only
			STATUS current
			DESCRIPTION
				" "
			::= { ccWlanSumStatsLongEntry 4 }

		
		-- 1.3.6.1.4.1.388.11.2.4.5.100.10.1.5
		ccWlanSumStatsLongPktsPerSecRx100 OBJECT-TYPE
			SYNTAX ScaleBy100
			UNITS "pkts per sec x100"
			MAX-ACCESS read-only
			STATUS current
			DESCRIPTION
				" "
			::= { ccWlanSumStatsLongEntry 5 }

		
		-- 1.3.6.1.4.1.388.11.2.4.5.100.10.1.6
		ccWlanSumStatsLongThroughput OBJECT-TYPE
			SYNTAX Unsigned32
			UNITS "bits per second"
			MAX-ACCESS read-only
			STATUS current
			DESCRIPTION
				" "
			::= { ccWlanSumStatsLongEntry 6 }

		
		-- 1.3.6.1.4.1.388.11.2.4.5.100.10.1.7
		ccWlanSumStatsLongThroughputTx OBJECT-TYPE
			SYNTAX Unsigned32
			UNITS "bits per second"
			MAX-ACCESS read-only
			STATUS current
			DESCRIPTION
				" "
			::= { ccWlanSumStatsLongEntry 7 }

		
		-- 1.3.6.1.4.1.388.11.2.4.5.100.10.1.8
		ccWlanSumStatsLongThroughputRx OBJECT-TYPE
			SYNTAX Unsigned32
			UNITS "bits per second"
			MAX-ACCESS read-only
			STATUS current
			DESCRIPTION
				" "
			::= { ccWlanSumStatsLongEntry 8 }

		
		-- 1.3.6.1.4.1.388.11.2.4.5.100.10.1.9
		ccWlanSumStatsLongAvgBitSpeed OBJECT-TYPE
			SYNTAX Unsigned32
			UNITS "bits per second"
			MAX-ACCESS read-only
			STATUS current
			DESCRIPTION
				" "
			::= { ccWlanSumStatsLongEntry 9 }

		
		-- 1.3.6.1.4.1.388.11.2.4.5.100.10.1.10
		ccWlanSumStatsLongAvgMuSignal OBJECT-TYPE
			SYNTAX Integer32
			UNITS "dBm"
			MAX-ACCESS read-only
			STATUS current
			DESCRIPTION
				" "
			::= { ccWlanSumStatsLongEntry 10 }

		
		-- 1.3.6.1.4.1.388.11.2.4.5.100.10.1.11
		ccWlanSumStatsLongAvgMuNoise OBJECT-TYPE
			SYNTAX Integer32
			UNITS "dBm"
			MAX-ACCESS read-only
			STATUS current
			DESCRIPTION
				" "
			::= { ccWlanSumStatsLongEntry 11 }

		
		-- 1.3.6.1.4.1.388.11.2.4.5.100.10.1.12
		ccWlanSumStatsLongAvgMuSnr OBJECT-TYPE
			SYNTAX Integer32
			UNITS "dB"
			MAX-ACCESS read-only
			STATUS current
			DESCRIPTION
				" "
			::= { ccWlanSumStatsLongEntry 12 }

		
		-- 1.3.6.1.4.1.388.11.2.4.5.100.10.1.13
		ccWlanSumStatsLongPp10kNUcastPkts OBJECT-TYPE
			SYNTAX PartsPer10k
			UNITS "parts-per-10000"
			MAX-ACCESS read-only
			STATUS current
			DESCRIPTION
				" "
			::= { ccWlanSumStatsLongEntry 13 }

		
		-- 1.3.6.1.4.1.388.11.2.4.5.100.10.1.14
		ccWlanSumStatsLongPp10kTxWithRetries OBJECT-TYPE
			SYNTAX PartsPer10k
			UNITS "parts-per-10000"
			MAX-ACCESS read-only
			STATUS current
			DESCRIPTION
				" "
			::= { ccWlanSumStatsLongEntry 14 }

		
		-- 1.3.6.1.4.1.388.11.2.4.5.100.10.1.15
		ccWlanSumStatsLongPp10kDropped OBJECT-TYPE
			SYNTAX PartsPer10k
			UNITS "parts-per-10000"
			MAX-ACCESS read-only
			STATUS current
			DESCRIPTION
				" "
			::= { ccWlanSumStatsLongEntry 15 }

		
		-- 1.3.6.1.4.1.388.11.2.4.5.100.10.1.16
		ccWlanSumStatsLongTxAvgRetries100 OBJECT-TYPE
			SYNTAX ScaleBy100
			UNITS "average x100"
			MAX-ACCESS read-only
			STATUS current
			DESCRIPTION
				" "
			::= { ccWlanSumStatsLongEntry 16 }

		
		-- 1.3.6.1.4.1.388.11.2.4.5.100.10.1.17
		ccWlanSumStatsLongPp10kRxUndecrypt OBJECT-TYPE
			SYNTAX PartsPer10k
			UNITS "parts-per-10000"
			MAX-ACCESS read-only
			STATUS current
			DESCRIPTION
				" "
			::= { ccWlanSumStatsLongEntry 17 }

		
		-- 1.3.6.1.4.1.388.11.2.4.5.100.10.1.18
		ccWlanSumStatsLongTotalMus OBJECT-TYPE
			SYNTAX Unsigned32 (0..100)
			UNITS "number of MUs"
			MAX-ACCESS read-only
			STATUS current
			DESCRIPTION
				" "
			::= { ccWlanSumStatsLongEntry 18 }

		
		-- 1.3.6.1.4.1.388.11.2.4.5.100.10.1.19
		ccWlanSumStatsLongSkip1 OBJECT-TYPE
			SYNTAX Integer32
			MAX-ACCESS read-write
			STATUS obsolete
			DESCRIPTION
				"Description."
			::= { ccWlanSumStatsLongEntry 19 }
-- place-holder so _Pp10kDropped falls at same OID for
-- both Portal and Wlan summary tables.
-- 
		
		-- 1.3.6.1.4.1.388.11.2.5
		ccSwitch OBJECT IDENTIFIER ::= { ws2k 5 }

		
		-- 1.3.6.1.4.1.388.11.2.5.1
		ccWan OBJECT IDENTIFIER ::= { ccSwitch 1 }

		
		-- 1.3.6.1.4.1.388.11.2.5.1.1
		ccWanTable OBJECT-TYPE
			SYNTAX SEQUENCE OF CcWanEntry
			MAX-ACCESS not-accessible
			STATUS current
			DESCRIPTION
				"Table of WAN interfaces.
				
				There is only one WAN interface on the WS2000, but we
				show the WAN interface in a table for consistancy and
				to have an entry to point to from other tables, (such
				as the MatrixSrc and MatrixDest tables)."
			::= { ccWan 1 }

		
		-- 1.3.6.1.4.1.388.11.2.5.1.1.1
		ccWanEntry OBJECT-TYPE
			SYNTAX CcWanEntry
			MAX-ACCESS not-accessible
			STATUS current
			DESCRIPTION
				" "
			INDEX { ccWanIndex }
			::= { ccWanTable 1 }

		
		CcWanEntry ::=
			SEQUENCE { 
				ccWanIndex
					Integer32,
				ccWanDhcpEnable
					TruthValue,
				ccWanDhcpIpAddr
					IpAddress,
				ccWanDhcpSubnetMask
					IpAddress,
				ccWanDhcpDefaultGateway
					IpAddress,
				ccWanDhcpPrimaryDnsServer
					IpAddress,
				ccWanDhcpSecondaryDnsServer
					IpAddress,
				ccWanSubnetMask
					IpAddress,
				ccWanDefaultGateway
					IpAddress,
				ccWanPrimaryDnsServer
					IpAddress,
				ccWanSecondaryDnsServer
					IpAddress
			 }

		-- 1.3.6.1.4.1.388.11.2.5.1.1.1.1
		ccWanIndex OBJECT-TYPE
			SYNTAX Integer32 (1..127)
			MAX-ACCESS accessible-for-notify
			STATUS current
			DESCRIPTION
				"Simple index."
			::= { ccWanEntry 1 }

		
		-- 1.3.6.1.4.1.388.11.2.5.1.1.1.2
		ccWanDhcpEnable OBJECT-TYPE
			SYNTAX TruthValue
			MAX-ACCESS read-write
			STATUS current
			DESCRIPTION
				"Enable DHCP on this WAN interface.
				"
			::= { ccWanEntry 2 }

		
		-- 1.3.6.1.4.1.388.11.2.5.1.1.1.3
		ccWanDhcpIpAddr OBJECT-TYPE
			SYNTAX IpAddress
			MAX-ACCESS read-only
			STATUS current
			DESCRIPTION
				"The IP address obtained via DHCP.
				
				If DHCP is disabled or if DHCP has not yet obtained
				values, this value will be 0.0.0.0."
			::= { ccWanEntry 3 }

		
		-- 1.3.6.1.4.1.388.11.2.5.1.1.1.4
		ccWanDhcpSubnetMask OBJECT-TYPE
			SYNTAX IpAddress
			MAX-ACCESS read-only
			STATUS current
			DESCRIPTION
				"The subnet mask address obtained via DHCP.
				
				If DHCP is disabled or if DHCP has not yet obtained
				values, this value will be 0.0.0.0."
			::= { ccWanEntry 4 }

		
		-- 1.3.6.1.4.1.388.11.2.5.1.1.1.5
		ccWanDhcpDefaultGateway OBJECT-TYPE
			SYNTAX IpAddress
			MAX-ACCESS read-only
			STATUS current
			DESCRIPTION
				"The default gateway obtained via DHCP.
				
				If DHCP is disabled or if DHCP has not yet obtained
				values, this value will be 0.0.0.0."
			::= { ccWanEntry 5 }

		
		-- 1.3.6.1.4.1.388.11.2.5.1.1.1.6
		ccWanDhcpPrimaryDnsServer OBJECT-TYPE
			SYNTAX IpAddress
			MAX-ACCESS read-only
			STATUS current
			DESCRIPTION
				"The primary DNS server obtained via DHCP.
				
				If DHCP is disabled or if DHCP has not yet obtained
				values, this value will be 0.0.0.0."
			::= { ccWanEntry 6 }

		
		-- 1.3.6.1.4.1.388.11.2.5.1.1.1.7
		ccWanDhcpSecondaryDnsServer OBJECT-TYPE
			SYNTAX IpAddress
			MAX-ACCESS read-only
			STATUS current
			DESCRIPTION
				"The secondary DNS server obtained via DHCP.
				
				If DHCP is disabled or if DHCP has not yet obtained
				values, this value will be 0.0.0.0."
			::= { ccWanEntry 7 }

		
		-- 1.3.6.1.4.1.388.11.2.5.1.1.1.8
		ccWanSubnetMask OBJECT-TYPE
			SYNTAX IpAddress
			MAX-ACCESS read-write
			STATUS current
			DESCRIPTION
				"The subnet mask to use if DHCP is not enabled.
				
				If DHCP is enabled, this value is still writeable,
				but is not used."
			::= { ccWanEntry 8 }

		
		-- 1.3.6.1.4.1.388.11.2.5.1.1.1.9
		ccWanDefaultGateway OBJECT-TYPE
			SYNTAX IpAddress
			MAX-ACCESS read-write
			STATUS current
			DESCRIPTION
				"The default gateway to use if DHCP is not enabled.
				
				If DHCP is enabled, this value is still writeable,
				but is not used."
			::= { ccWanEntry 9 }

		
		-- 1.3.6.1.4.1.388.11.2.5.1.1.1.10
		ccWanPrimaryDnsServer OBJECT-TYPE
			SYNTAX IpAddress
			MAX-ACCESS read-write
			STATUS current
			DESCRIPTION
				"The primary DNS server to use if DHCP is not enabled.
				
				If DHCP is enabled, this value is still writeable,
				but is not used."
			::= { ccWanEntry 10 }

		
		-- 1.3.6.1.4.1.388.11.2.5.1.1.1.11
		ccWanSecondaryDnsServer OBJECT-TYPE
			SYNTAX IpAddress
			MAX-ACCESS read-write
			STATUS current
			DESCRIPTION
				"The secondary DNS server to use if DHCP is not 
				enabled.
				
				If DHCP is enabled, this value is still writeable,
				but is not used."
			::= { ccWanEntry 11 }

		
		-- 1.3.6.1.4.1.388.11.2.5.1.2
		ccWanPppoeTable OBJECT-TYPE
			SYNTAX SEQUENCE OF CcWanPppoeEntry
			MAX-ACCESS not-accessible
			STATUS current
			DESCRIPTION
				"PPPoE settings for WAN interfaces."
			::= { ccWan 2 }

		
		-- 1.3.6.1.4.1.388.11.2.5.1.2.1
		ccWanPppoeEntry OBJECT-TYPE
			SYNTAX CcWanPppoeEntry
			MAX-ACCESS not-accessible
			STATUS current
			DESCRIPTION
				" "
			INDEX { ccWanIndex }
			::= { ccWanPppoeTable 1 }

		
		CcWanPppoeEntry ::=
			SEQUENCE { 
				ccWanPppoeEnable
					StaticRowEnable,
				ccWanPppoeUsername
					DisplayString,
				ccWanPppoePassword
					DisplayString,
				ccWanPppoeKeepAlive
					TruthValue,
				ccWanPppoeIdleTime
					Unsigned32,
				ccWanPppoeAuthType
					INTEGER
			 }

		-- 1.3.6.1.4.1.388.11.2.5.1.2.1.1
		ccWanPppoeEnable OBJECT-TYPE
			SYNTAX StaticRowEnable
			MAX-ACCESS read-write
			STATUS current
			DESCRIPTION
				"Enable PPPoE for this WAN interface."
			::= { ccWanPppoeEntry 1 }

		
		-- 1.3.6.1.4.1.388.11.2.5.1.2.1.2
		ccWanPppoeUsername OBJECT-TYPE
			SYNTAX DisplayString
			MAX-ACCESS read-write
			STATUS current
			DESCRIPTION
				"PPPoE username."
			::= { ccWanPppoeEntry 2 }

		
		-- 1.3.6.1.4.1.388.11.2.5.1.2.1.3
		ccWanPppoePassword OBJECT-TYPE
			SYNTAX DisplayString
			MAX-ACCESS read-write
			STATUS current
			DESCRIPTION
				"PPPoE password.
				
				When this value is read, the switch returns a 
				DisplayString of zero length."
			::= { ccWanPppoeEntry 3 }

		
		-- 1.3.6.1.4.1.388.11.2.5.1.2.1.4
		ccWanPppoeKeepAlive OBJECT-TYPE
			SYNTAX TruthValue
			MAX-ACCESS read-write
			STATUS current
			DESCRIPTION
				"PPPoE keep-alive."
			::= { ccWanPppoeEntry 4 }

		
		-- 1.3.6.1.4.1.388.11.2.5.1.2.1.5
		ccWanPppoeIdleTime OBJECT-TYPE
			SYNTAX Unsigned32
			UNITS "seconds"
			MAX-ACCESS read-write
			STATUS current
			DESCRIPTION
				"PPPoE idle time."
			::= { ccWanPppoeEntry 5 }

		
		-- 1.3.6.1.4.1.388.11.2.5.1.2.1.6
		ccWanPppoeAuthType OBJECT-TYPE
			SYNTAX INTEGER
				{
				none(1),
				papOrChap(2),
				pap(3),
				chap(4)
				}
			MAX-ACCESS read-write
			STATUS current
			DESCRIPTION
				"PPPoE authentication type.
				
				If no bits are set, no authentication is done.
				If more than one bit is set, any of the selected 
				methods may be used by the switch."
			::= { ccWanPppoeEntry 6 }

		
		-- 1.3.6.1.4.1.388.11.2.5.1.3
		ccWanIpAddrTable OBJECT-TYPE
			SYNTAX SEQUENCE OF CcWanIpAddrEntry
			MAX-ACCESS not-accessible
			STATUS current
			DESCRIPTION
				"Table of IP addresses for the given WAN interface.
				Up to 8 IP addresses per WAN interface."
			::= { ccWan 3 }

		
		-- 1.3.6.1.4.1.388.11.2.5.1.3.1
		ccWanIpAddrEntry OBJECT-TYPE
			SYNTAX CcWanIpAddrEntry
			MAX-ACCESS not-accessible
			STATUS current
			DESCRIPTION
				" "
			INDEX { ccWanIndex, ccWanIpAddrIndex }
			::= { ccWanIpAddrTable 1 }

		
		CcWanIpAddrEntry ::=
			SEQUENCE { 
				ccWanIpAddrIndex
					Integer32,
				ccWanIpAddrEnable
					StaticRowEnable,
				ccWanIpAddr
					IpAddress
			 }

		-- 1.3.6.1.4.1.388.11.2.5.1.3.1.1
		ccWanIpAddrIndex OBJECT-TYPE
			SYNTAX Integer32 (1..127)
			MAX-ACCESS accessible-for-notify
			STATUS current
			DESCRIPTION
				"Simple index 1..8 of entries for each WAN interface."
			::= { ccWanIpAddrEntry 1 }

		
		-- 1.3.6.1.4.1.388.11.2.5.1.3.1.2
		ccWanIpAddrEnable OBJECT-TYPE
			SYNTAX StaticRowEnable
			MAX-ACCESS read-write
			STATUS current
			DESCRIPTION
				"Enable this entry."
			::= { ccWanIpAddrEntry 2 }

		
		-- 1.3.6.1.4.1.388.11.2.5.1.3.1.3
		ccWanIpAddr OBJECT-TYPE
			SYNTAX IpAddress
			MAX-ACCESS read-write
			STATUS current
			DESCRIPTION
				"WAN IP address."
			::= { ccWanIpAddrEntry 3 }

		
-- Variables to control the Firewall function.
		-- 1.3.6.1.4.1.388.11.2.5.1.4
		ccWanFirewall OBJECT IDENTIFIER ::= { ccWan 4 }

		
		-- 1.3.6.1.4.1.388.11.2.5.1.4.1
		ccWanFirewallGlobalEnable OBJECT-TYPE
			SYNTAX TruthValue
			MAX-ACCESS read-write
			STATUS current
			DESCRIPTION
				"This variable enables/disables the global state of the
				firewall.  Note that if the firewall function is disabled,
				NAT, VPN, content filtering and subnet access are also
				disabled.
				
				(Disabling all these functions would only be useful in 
				using the WS2000 in an existing network topology).
				
				Factory-default state is TRUE."
			::= { ccWanFirewall 1 }

		
		-- 1.3.6.1.4.1.388.11.2.5.1.4.2
		ccWanFirewallTable OBJECT-TYPE
			SYNTAX SEQUENCE OF CcWanFirewallEntry
			MAX-ACCESS not-accessible
			STATUS current
			DESCRIPTION
				"Table of Firewall attacks that can be enabled/disabled."
			::= { ccWanFirewall 2 }

		
		-- 1.3.6.1.4.1.388.11.2.5.1.4.2.1
		ccWanFirewallEntry OBJECT-TYPE
			SYNTAX CcWanFirewallEntry
			MAX-ACCESS not-accessible
			STATUS current
			DESCRIPTION
				" "
			INDEX { ccWanIndex }
			::= { ccWanFirewallTable 1 }

		
		CcWanFirewallEntry ::=
			SEQUENCE { 
				ccWanFirewallIndex
					INTEGER,
				ccWanFirewallDescription
					DisplayString,
				ccWanFirewallAlwaysEnabled
					TruthValue,
				ccWanFirewallEnable
					TruthValue
			 }

		-- 1.3.6.1.4.1.388.11.2.5.1.4.2.1.1
		ccWanFirewallIndex OBJECT-TYPE
			SYNTAX INTEGER
				{
				fwIpSpoofing(1),
				fwPingOfDeath(2),
				fwLandAttack(3),
				fwReassemblyAttack(4),
				fwSynFloodAttack(5),
				fwSourceRouting(6),
				fwWinnukeAttack(7),
				fwFtpBounceAttack(8),
				fwIpUnalignedTimestamp(9),
				fwIpSequenceNumberPrediction(10),
				fwMimeFloodAttack(11)
				}
			MAX-ACCESS accessible-for-notify
			STATUS current
			DESCRIPTION
				"Simple index, but with explicitly enumerated values."
			::= { ccWanFirewallEntry 1 }

		
		-- 1.3.6.1.4.1.388.11.2.5.1.4.2.1.2
		ccWanFirewallDescription OBJECT-TYPE
			SYNTAX DisplayString
			MAX-ACCESS read-only
			STATUS current
			DESCRIPTION
				"Short description of the type of attack."
			::= { ccWanFirewallEntry 2 }

		
		-- 1.3.6.1.4.1.388.11.2.5.1.4.2.1.3
		ccWanFirewallAlwaysEnabled OBJECT-TYPE
			SYNTAX TruthValue
			MAX-ACCESS read-only
			STATUS current
			DESCRIPTION
				"A few of the firewall algorithms can NOT be disabled.
				If this value is TRUE, this is one of those algorithms.
				Any attempt to set ccWanFwEnable to FALSE will result in
				a BAD-VALUE error."
			::= { ccWanFirewallEntry 3 }

		
		-- 1.3.6.1.4.1.388.11.2.5.1.4.2.1.4
		ccWanFirewallEnable OBJECT-TYPE
			SYNTAX TruthValue
			MAX-ACCESS read-write
			STATUS current
			DESCRIPTION
				"Set to TRUE to enable this type of firewall check."
			::= { ccWanFirewallEntry 4 }

		
		-- 1.3.6.1.4.1.388.11.2.5.1.4.3
		ccWanFirewallMimeFloodMaxHeaderLength OBJECT-TYPE
			SYNTAX Unsigned32
			UNITS "bytes"
			MAX-ACCESS read-write
			STATUS current
			DESCRIPTION
				"Mime flood attack check max header length."
			::= { ccWanFirewall 3 }

		
		-- 1.3.6.1.4.1.388.11.2.5.1.4.4
		ccWanFirewallMimeFloodMaxHeaders OBJECT-TYPE
			SYNTAX Unsigned32
			MAX-ACCESS read-write
			STATUS current
			DESCRIPTION
				"Mime flood attack check max headers."
			::= { ccWanFirewall 4 }

		
		-- 1.3.6.1.4.1.388.11.2.5.1.4.5
		ccWanNatTimeout OBJECT-TYPE
			SYNTAX Unsigned32
			MAX-ACCESS read-write
			STATUS current
			DESCRIPTION
				"Timeout value for NAT."
			::= { ccWanFirewall 5 }

		
-- Values regarding NAT functions.
		-- 1.3.6.1.4.1.388.11.2.5.1.5
		ccWanNat OBJECT IDENTIFIER ::= { ccWan 5 }

		
		-- 1.3.6.1.4.1.388.11.2.5.1.5.1
		ccWanNatLowestUnusedSlot OBJECT-TYPE
			SYNTAX Unsigned32
			MAX-ACCESS read-only
			STATUS current
			DESCRIPTION
				"Since the ccWanNatTable is actually 
				implemented as a single list of entries,
				the second index of the ccWanNatTable,
				(ccWanNatIndex), must be unique across all
				ccWanNatTable entries.  This scalar tells
				the network management software the
				lowest unused value that is available to be
				used for ccWanNatIndex, when creating a 
				new ccWanNatTable entry.
				"
			::= { ccWanNat 1 }

		
		-- 1.3.6.1.4.1.388.11.2.5.1.5.2
		ccWanNatTable OBJECT-TYPE
			SYNTAX SEQUENCE OF CcWanNatEntry
			MAX-ACCESS not-accessible
			STATUS current
			DESCRIPTION
				"Table of NAT mappings for each IP address assigned to
				each WAN interface.
				
				(The WS2000 currently only has one WAN interface, but
				all MIBs are designed for the possibility of multiple
				WAN interfaces)."
			::= { ccWanNat 2 }

		
		-- 1.3.6.1.4.1.388.11.2.5.1.5.2.1
		ccWanNatEntry OBJECT-TYPE
			SYNTAX CcWanNatEntry
			MAX-ACCESS not-accessible
			STATUS current
			DESCRIPTION
				" "
			INDEX { ccWanNatIndex, ccWanNatWanIpAddress }
			::= { ccWanNatTable 1 }

		
		CcWanNatEntry ::=
			SEQUENCE { 
				ccWanNatIndex
					Integer32,
				ccWanNatWanIpAddress
					IpAddress,
				ccWanNatType
					INTEGER,
				ccWanNat1to1IpAddr
					IpAddress,
				ccWanNatInboundDefaultEna
					TruthValue,
				ccWanNatInboundDefaultIp
					IpAddress
			 }

		-- 1.3.6.1.4.1.388.11.2.5.1.5.2.1.1
		ccWanNatIndex OBJECT-TYPE
			SYNTAX Integer32 (1..127)
			MAX-ACCESS accessible-for-notify
			STATUS current
			DESCRIPTION
				"Simple index matching the simple index in the
				ccWanTable."
			::= { ccWanNatEntry 1 }

		
		-- 1.3.6.1.4.1.388.11.2.5.1.5.2.1.2
		ccWanNatWanIpAddress OBJECT-TYPE
			SYNTAX IpAddress
			MAX-ACCESS accessible-for-notify
			STATUS current
			DESCRIPTION
				"One, (of possibly several), IP addresses assigned to
				this WAN interface.  One entries in this table will 
				appear for each matching entry in the 
				ccWanIpAddrTable."
			::= { ccWanNatEntry 2 }

		
		-- 1.3.6.1.4.1.388.11.2.5.1.5.2.1.3
		ccWanNatType OBJECT-TYPE
			SYNTAX INTEGER
				{
				natNone(1),
				nat1to1(2),
				nat1toMany(3)
				}
			MAX-ACCESS read-write
			STATUS current
			DESCRIPTION
				"Configure the NAT type.
				
				Only if 'nat1to1' is selected is the 
				ccWanNat1to1IpAddr value is used.  In such a case, 
				any corresponding entries in the ccWanNatInboundTable
				and the ccWanNatOutboundTable are ignored.
				
				If 'none' is selected, all the above mentioned values
				are ignored.
				
				If '1toMany' is selected, the ccWanNat1to1IpAddr
				value is ignored, but entries, (if any), in the two
				tables are relevant."
			::= { ccWanNatEntry 3 }

		
		-- 1.3.6.1.4.1.388.11.2.5.1.5.2.1.4
		ccWanNat1to1IpAddr OBJECT-TYPE
			SYNTAX IpAddress
			MAX-ACCESS read-write
			STATUS current
			DESCRIPTION
				"The IP address to use for outbound 1-to-1 mapping.
				
				Only used if ccWanNatType is '1to1'."
			::= { ccWanNatEntry 4 }

		
		-- 1.3.6.1.4.1.388.11.2.5.1.5.2.1.5
		ccWanNatInboundDefaultEna OBJECT-TYPE
			SYNTAX TruthValue
			MAX-ACCESS read-write
			STATUS current
			DESCRIPTION
				"If set, any port that is NOT found in the
				ccWanNatInboundTable entries is forwarded to the
				IP addr specified by ccWanNatInboundDefaultIp."
			::= { ccWanNatEntry 5 }

		
		-- 1.3.6.1.4.1.388.11.2.5.1.5.2.1.6
		ccWanNatInboundDefaultIp OBJECT-TYPE
			SYNTAX IpAddress
			MAX-ACCESS read-write
			STATUS current
			DESCRIPTION
				"IP addr to send ports that do not match any entry in
				the ccWanNatInboundTable."
			::= { ccWanNatEntry 6 }

		
		-- 1.3.6.1.4.1.388.11.2.5.1.5.3
		ccWanNatInboundTable OBJECT-TYPE
			SYNTAX SEQUENCE OF CcWanNatInboundEntry
			MAX-ACCESS not-accessible
			STATUS current
			DESCRIPTION
				"Table of inbound NAT mappings for IP addresses on
				WAN interfaces that are set to ccWanNatType of
				'1to1' or '1toMany'."
			::= { ccWanNat 3 }

		
		-- 1.3.6.1.4.1.388.11.2.5.1.5.3.1
		ccWanNatInboundEntry OBJECT-TYPE
			SYNTAX CcWanNatInboundEntry
			MAX-ACCESS not-accessible
			STATUS current
			DESCRIPTION
				" "
			INDEX { ccWanNatIndex, ccWanNatWanIpAddress, ccWanNatInboundIndex }
			::= { ccWanNatInboundTable 1 }

		
		CcWanNatInboundEntry ::=
			SEQUENCE { 
				ccWanNatInboundIndex
					Integer32,
				ccWanNatInboundName
					DisplayString,
				ccWanNatInboundTransport
					INTEGER,
				ccWanNatInboundStartPort
					Integer32,
				ccWanNatInboundEndPort
					Integer32,
				ccWanNatInboundIpAddr
					IpAddress,
				ccWanNatInboundTranslationPort
					Integer32,
				ccWanNatInboundRowStatus
					AbbrevRowStatus
			 }

		-- 1.3.6.1.4.1.388.11.2.5.1.5.3.1.1
		ccWanNatInboundIndex OBJECT-TYPE
			SYNTAX Integer32 (1..255)
			MAX-ACCESS accessible-for-notify
			STATUS current
			DESCRIPTION
				"A given IP address on a given WAN interface may have
				many inbound NAT mappings.  This (3rd) index numbers
				those many mappings."
			::= { ccWanNatInboundEntry 1 }

		
		-- 1.3.6.1.4.1.388.11.2.5.1.5.3.1.2
		ccWanNatInboundName OBJECT-TYPE
			SYNTAX DisplayString
			MAX-ACCESS read-write
			STATUS current
			DESCRIPTION
				"Name of the inbound mapping."
			::= { ccWanNatInboundEntry 2 }

		
		-- 1.3.6.1.4.1.388.11.2.5.1.5.3.1.3
		ccWanNatInboundTransport OBJECT-TYPE
			SYNTAX INTEGER
				{
				all(1),
				tcp(2),
				udp(3),
				icmp(4),
				ah(5),
				esp(6),
				gre(7)
				}
			MAX-ACCESS read-write
			STATUS current
			DESCRIPTION
				"Transport for which this mapping applies."
			::= { ccWanNatInboundEntry 3 }

		
		-- 1.3.6.1.4.1.388.11.2.5.1.5.3.1.4
		ccWanNatInboundStartPort OBJECT-TYPE
			SYNTAX Integer32
			MAX-ACCESS read-write
			STATUS current
			DESCRIPTION
				"Low-end of the port range."
			::= { ccWanNatInboundEntry 4 }

		
		-- 1.3.6.1.4.1.388.11.2.5.1.5.3.1.5
		ccWanNatInboundEndPort OBJECT-TYPE
			SYNTAX Integer32
			MAX-ACCESS read-write
			STATUS current
			DESCRIPTION
				"High-end of the port range."
			::= { ccWanNatInboundEntry 5 }

		
		-- 1.3.6.1.4.1.388.11.2.5.1.5.3.1.6
		ccWanNatInboundIpAddr OBJECT-TYPE
			SYNTAX IpAddress
			MAX-ACCESS read-write
			STATUS current
			DESCRIPTION
				"IP address to map to."
			::= { ccWanNatInboundEntry 6 }

		
		-- 1.3.6.1.4.1.388.11.2.5.1.5.3.1.7
		ccWanNatInboundTranslationPort OBJECT-TYPE
			SYNTAX Integer32
			MAX-ACCESS read-write
			STATUS current
			DESCRIPTION
				"Description."
			::= { ccWanNatInboundEntry 7 }

		
		-- 1.3.6.1.4.1.388.11.2.5.1.5.3.1.8
		ccWanNatInboundRowStatus OBJECT-TYPE
			SYNTAX AbbrevRowStatus
			MAX-ACCESS read-write
			STATUS current
			DESCRIPTION
				"Simple row status."
			::= { ccWanNatInboundEntry 8 }

		
		-- 1.3.6.1.4.1.388.11.2.5.1.5.4
		ccWanNatOutboundTable OBJECT-TYPE
			SYNTAX SEQUENCE OF CcWanNatOutboundEntry
			MAX-ACCESS not-accessible
			STATUS current
			DESCRIPTION
				"Table of outbound NAT mappings for IP addresses on
				WAN interfaces that are set to ccWanNatType of
				'1toMany'."
			::= { ccWanNat 4 }

		
		-- 1.3.6.1.4.1.388.11.2.5.1.5.4.1
		ccWanNatOutboundEntry OBJECT-TYPE
			SYNTAX CcWanNatOutboundEntry
			MAX-ACCESS not-accessible
			STATUS current
			DESCRIPTION
				" "
			INDEX { ccWanNatIndex, ccWanNatWanIpAddress, ccWanNatOutboundSubnetIndex }
			::= { ccWanNatOutboundTable 1 }

		
		CcWanNatOutboundEntry ::=
			SEQUENCE { 
				ccWanNatOutboundSubnetIndex
					Integer32,
				ccWanNatOutboundEnable
					INTEGER,
				ccWanNatOutboundPossibleIpAddr
					MultiPointer63,
				ccWanNatOutboundIpAddr
					SinglePointer
			 }

		-- 1.3.6.1.4.1.388.11.2.5.1.5.4.1.1
		ccWanNatOutboundSubnetIndex OBJECT-TYPE
			SYNTAX Integer32 (1..255)
			MAX-ACCESS accessible-for-notify
			STATUS current
			DESCRIPTION
				"A different mapping can be set for each subnet.  This
				(3rd) index specifies the subnet.
				
				This index is the same value for a given subnet as in
				the ccLanTable."
			::= { ccWanNatOutboundEntry 1 }

		
		-- 1.3.6.1.4.1.388.11.2.5.1.5.4.1.2
		ccWanNatOutboundEnable OBJECT-TYPE
			SYNTAX INTEGER (1..2)
			MAX-ACCESS read-write
			STATUS current
			DESCRIPTION
				"Enable the Outbound entry."
			::= { ccWanNatOutboundEntry 2 }

		
		-- 1.3.6.1.4.1.388.11.2.5.1.5.4.1.3
		ccWanNatOutboundPossibleIpAddr OBJECT-TYPE
			SYNTAX MultiPointer63
			MAX-ACCESS read-only
			STATUS current
			DESCRIPTION
				"This multi-bit-mask-pointer points to every IP
				address in the ccWanIpAddrTable that is a valid
				outbound NAT mapping for this subnet.
				
				Setting this value to all 0s effectively 
				disables this NAT mapping."
			::= { ccWanNatOutboundEntry 3 }

		
		-- 1.3.6.1.4.1.388.11.2.5.1.5.4.1.4
		ccWanNatOutboundIpAddr OBJECT-TYPE
			SYNTAX SinglePointer
			MAX-ACCESS read-write
			STATUS current
			DESCRIPTION
				"This value points to the ccWanIpAddrTable entry that
				has been selected for the outbound NAT mapping."
			::= { ccWanNatOutboundEntry 4 }

		
		-- 1.3.6.1.4.1.388.11.2.5.1.6
		ccWanVpn OBJECT IDENTIFIER ::= { ccWan 6 }

		
		-- 1.3.6.1.4.1.388.11.2.5.1.6.4
		ccWanVpnTunnelConfig OBJECT IDENTIFIER ::= { ccWanVpn 4 }
-- Tables used to configure VPNs on this switch.
-- 
-- Since there are so many settings for each such tunnel,
-- the values have been divided into three tables.  The 
-- second two tables AUGMENT the first.
-- 
-- Since the number of values to create a VPN that must be
-- SET exceed that which can fit in a single packet, a true
-- RowStatus is used, (not the AbbrevRowStatus).  Given this,
-- default values are specified for each item.
		
		-- 1.3.6.1.4.1.388.11.2.5.1.6.4.1
		ccWanVpnTable OBJECT-TYPE
			SYNTAX SEQUENCE OF CcWanVpnEntry
			MAX-ACCESS not-accessible
			STATUS current
			DESCRIPTION
				"Table of VPN entries."
			::= { ccWanVpnTunnelConfig 1 }

		
		-- 1.3.6.1.4.1.388.11.2.5.1.6.4.1.1
		ccWanVpnEntry OBJECT-TYPE
			SYNTAX CcWanVpnEntry
			MAX-ACCESS not-accessible
			STATUS current
			DESCRIPTION
				"Description."
			INDEX { ccWanVpnIndex }
			::= { ccWanVpnTable 1 }

		
		CcWanVpnEntry ::=
			SEQUENCE { 
				ccWanVpnIndex
					INTEGER,
				ccWanVpnName
					DisplayString,
				ccWanVpnLocalSubnet
					SinglePointer,
				ccWanVpnLocalWanIp
					SinglePointer,
				ccWanVpnRemoteSubnet
					IpAddress,
				ccWanVpnRemoteSubnetMask
					IpAddress,
				ccWanVpnRemoteGateway
					IpAddress,
				ccWanVpnKeyExchange
					INTEGER,
				ccWanVpnRowStatus
					RowStatus
			 }

		-- 1.3.6.1.4.1.388.11.2.5.1.6.4.1.1.1
		ccWanVpnIndex OBJECT-TYPE
			SYNTAX INTEGER (1..25)
			MAX-ACCESS accessible-for-notify
			STATUS current
			DESCRIPTION
				"Simple Index."
			::= { ccWanVpnEntry 1 }

		
		-- 1.3.6.1.4.1.388.11.2.5.1.6.4.1.1.2
		ccWanVpnName OBJECT-TYPE
			SYNTAX DisplayString (SIZE (1..13))
			MAX-ACCESS read-write
			STATUS current
			DESCRIPTION
				"Name of VPN tunnel."
			::= { ccWanVpnEntry 2 }

		
		-- 1.3.6.1.4.1.388.11.2.5.1.6.4.1.1.3
		ccWanVpnLocalSubnet OBJECT-TYPE
			SYNTAX SinglePointer
			MAX-ACCESS read-write
			STATUS current
			DESCRIPTION
				"Points to a ccSubnetTable entry. 1-LAN1, 2-LAN2, 3-WAN"
			::= { ccWanVpnEntry 3 }
-- ??-India: please provide a defval??
		
		-- 1.3.6.1.4.1.388.11.2.5.1.6.4.1.1.4
		ccWanVpnLocalWanIp OBJECT-TYPE
			SYNTAX SinglePointer
			MAX-ACCESS read-write
			STATUS current
			DESCRIPTION
				"Points to a ccWanIpAddr entry."
			::= { ccWanVpnEntry 4 }
-- ??-India: please provide a defval??
		
		-- 1.3.6.1.4.1.388.11.2.5.1.6.4.1.1.5
		ccWanVpnRemoteSubnet OBJECT-TYPE
			SYNTAX IpAddress
			MAX-ACCESS read-write
			STATUS current
			DESCRIPTION
				"IP addr of the remote subnet."
			DEFVAL { '00000000'h }
			::= { ccWanVpnEntry 5 }

		
		-- 1.3.6.1.4.1.388.11.2.5.1.6.4.1.1.6
		ccWanVpnRemoteSubnetMask OBJECT-TYPE
			SYNTAX IpAddress
			MAX-ACCESS read-write
			STATUS current
			DESCRIPTION
				"Mask for remote subnet."
			DEFVAL { '00000000'h }
			::= { ccWanVpnEntry 6 }

		
		-- 1.3.6.1.4.1.388.11.2.5.1.6.4.1.1.7
		ccWanVpnRemoteGateway OBJECT-TYPE
			SYNTAX IpAddress
			MAX-ACCESS read-write
			STATUS current
			DESCRIPTION
				"Gateway IP addr for the remote subnet."
			DEFVAL { '00000000'h }
			::= { ccWanVpnEntry 7 }

		
		-- 1.3.6.1.4.1.388.11.2.5.1.6.4.1.1.8
		ccWanVpnKeyExchange OBJECT-TYPE
			SYNTAX INTEGER
				{
				manual(1),
				automatic(2)
				}
			MAX-ACCESS read-write
			STATUS current
			DESCRIPTION
				"Selects manual or automatic key exchange mechanism."
			DEFVAL { manual }
			::= { ccWanVpnEntry 8 }

		
		-- 1.3.6.1.4.1.388.11.2.5.1.6.4.1.1.9
		ccWanVpnRowStatus OBJECT-TYPE
			SYNTAX RowStatus
			MAX-ACCESS read-write
			STATUS current
			DESCRIPTION
				"Used to create/destroy rows."
			::= { ccWanVpnEntry 9 }
-- Note that unlike so many other WS2000 tables, this is NOT
-- an abbreviated RowStatus.  A full RowStatus is needed in
-- order to have the ability to create a new row with status
-- of UnderCreation, so that the multitude of columns can be
-- filled-in before Activation.
		
		-- 1.3.6.1.4.1.388.11.2.5.1.6.4.2
		ccWanVpnKeyManualTable OBJECT-TYPE
			SYNTAX SEQUENCE OF CcWanVpnKeyManualEntry
			MAX-ACCESS not-accessible
			STATUS current
			DESCRIPTION
				"Table of Manual Key Setting entries."
			::= { ccWanVpnTunnelConfig 2 }

		
		-- 1.3.6.1.4.1.388.11.2.5.1.6.4.2.1
		ccWanVpnKeyManualEntry OBJECT-TYPE
			SYNTAX CcWanVpnKeyManualEntry
			MAX-ACCESS not-accessible
			STATUS current
			DESCRIPTION
				"Description."
			AUGMENTS { ccWanVpnEntry }
			::= { ccWanVpnKeyManualTable 1 }

		
		CcWanVpnKeyManualEntry ::=
			SEQUENCE { 
				ccWanVpnKeyManualAhAuth
					INTEGER,
				ccWanVpnKeyManualInAhAuthKey
					HexPassword,
				ccWanVpnKeyManualOutAhAuthKey
					HexPassword,
				ccWanVpnKeyManualInAhSpi
					Unsigned32,
				ccWanVpnKeyManualOutAhSpi
					Unsigned32,
				ccWanVpnKeyManualEspType
					INTEGER,
				ccWanVpnKeyManualEspEncrypAlg
					INTEGER,
				ccWanVpnKeyManualInEspEncrypKey
					HexPassword,
				ccWanVpnKeyManualOutEspEncrypKey
					HexPassword,
				ccWanVpnKeyManualEspAuthAlg
					INTEGER,
				ccWanVpnKeyManualInEspAuthKey
					HexPassword,
				ccWanVpnKeyManualOutEspAuthKey
					HexPassword,
				ccWanVpnKeyManualInEspSpi
					Unsigned32,
				ccWanVpnKeyManualOutEspSpi
					Unsigned32
			 }

		-- 1.3.6.1.4.1.388.11.2.5.1.6.4.2.1.1
		ccWanVpnKeyManualAhAuth OBJECT-TYPE
			SYNTAX INTEGER
				{
				none(1),
				md5(2),
				sha1(3)
				}
			MAX-ACCESS read-write
			STATUS current
			DESCRIPTION
				"data authentication and anti-replay services for the VPN tunnel.
				
				The following 2 keys have max length:
				  md5  - 32 hex characters
				  sha1 - 40
				"
			DEFVAL { none }
			::= { ccWanVpnKeyManualEntry 1 }

		
		-- 1.3.6.1.4.1.388.11.2.5.1.6.4.2.1.2
		ccWanVpnKeyManualInAhAuthKey OBJECT-TYPE
			SYNTAX HexPassword (SIZE (0..40))
			MAX-ACCESS read-write
			STATUS current
			DESCRIPTION
				"AH Authentication Key for inbound traffic."
			::= { ccWanVpnKeyManualEntry 2 }

		
		-- 1.3.6.1.4.1.388.11.2.5.1.6.4.2.1.3
		ccWanVpnKeyManualOutAhAuthKey OBJECT-TYPE
			SYNTAX HexPassword (SIZE (0..40))
			MAX-ACCESS read-write
			STATUS current
			DESCRIPTION
				"AH Authentication Key for outbound traffic."
			::= { ccWanVpnKeyManualEntry 3 }

		
		-- 1.3.6.1.4.1.388.11.2.5.1.6.4.2.1.4
		ccWanVpnKeyManualInAhSpi OBJECT-TYPE
			SYNTAX Unsigned32 (256..4294967295)
			MAX-ACCESS read-write
			STATUS current
			DESCRIPTION
				"inbound security association created by the AH algorithm."
			DEFVAL { 256 }
			::= { ccWanVpnKeyManualEntry 4 }
-- ??-India: is this range correct?
-- note that it's SET via decimal, not hex.
		
		-- 1.3.6.1.4.1.388.11.2.5.1.6.4.2.1.5
		ccWanVpnKeyManualOutAhSpi OBJECT-TYPE
			SYNTAX Unsigned32 (256..4294967295)
			MAX-ACCESS read-write
			STATUS current
			DESCRIPTION
				"outbound security association created by the AH algorithm."
			DEFVAL { 256 }
			::= { ccWanVpnKeyManualEntry 5 }
-- ??-India: is this range correct?
-- note that it's SET via decimal, not hex.
		
		-- 1.3.6.1.4.1.388.11.2.5.1.6.4.2.1.6
		ccWanVpnKeyManualEspType OBJECT-TYPE
			SYNTAX INTEGER
				{
				none(1),
				esp(2),
				espWithAuthentication(3)
				}
			MAX-ACCESS read-write
			STATUS current
			DESCRIPTION
				"packet encryption and optional data authentication
				and anti-replay services for the VPN tunnel.
				
				Some of the next 6 variables are used depending on:
				  none        - all 6 variables are ignored
				  esp         - first 3 are used, next 3 ignored
				  espWithAuth - all 6 are used
				"
			DEFVAL { esp }
			::= { ccWanVpnKeyManualEntry 6 }

		
		-- 1.3.6.1.4.1.388.11.2.5.1.6.4.2.1.7
		ccWanVpnKeyManualEspEncrypAlg OBJECT-TYPE
			SYNTAX INTEGER
				{
				des(1),
				des3(2),
				aes128bit(3),
				aes192bit(4),
				aes256bit(5)
				}
			MAX-ACCESS read-write
			STATUS current
			DESCRIPTION
				"ESP Encryption Algorithm.
				
				The following 2 keys have max length:
				  des       - 16 hex characters
				  des3      - 48
				  aes128bit - 32
				  aes192bit - 48
				  aes256bit - 64
				"
			DEFVAL { des }
			::= { ccWanVpnKeyManualEntry 7 }

		
		-- 1.3.6.1.4.1.388.11.2.5.1.6.4.2.1.8
		ccWanVpnKeyManualInEspEncrypKey OBJECT-TYPE
			SYNTAX HexPassword (SIZE (0..64))
			MAX-ACCESS read-write
			STATUS current
			DESCRIPTION
				"ESP Encryption Key for inbound traffic."
			::= { ccWanVpnKeyManualEntry 8 }

		
		-- 1.3.6.1.4.1.388.11.2.5.1.6.4.2.1.9
		ccWanVpnKeyManualOutEspEncrypKey OBJECT-TYPE
			SYNTAX HexPassword (SIZE (0..64))
			MAX-ACCESS read-write
			STATUS current
			DESCRIPTION
				"ESP Encryption Key for inbound traffic."
			::= { ccWanVpnKeyManualEntry 9 }

		
		-- 1.3.6.1.4.1.388.11.2.5.1.6.4.2.1.10
		ccWanVpnKeyManualEspAuthAlg OBJECT-TYPE
			SYNTAX INTEGER
				{
				md5(1),
				sha1(2)
				}
			MAX-ACCESS read-write
			STATUS current
			DESCRIPTION
				"ESP Authentication Algorithm.
				
				The following 2 keys have max length:
				  md5  - 32 hex characters
				  sha1 - 40"
			DEFVAL { md5 }
			::= { ccWanVpnKeyManualEntry 10 }

		
		-- 1.3.6.1.4.1.388.11.2.5.1.6.4.2.1.11
		ccWanVpnKeyManualInEspAuthKey OBJECT-TYPE
			SYNTAX HexPassword (SIZE (0..40))
			MAX-ACCESS read-write
			STATUS current
			DESCRIPTION
				"ESP Authentication Key for inbound traffic."
			::= { ccWanVpnKeyManualEntry 11 }

		
		-- 1.3.6.1.4.1.388.11.2.5.1.6.4.2.1.12
		ccWanVpnKeyManualOutEspAuthKey OBJECT-TYPE
			SYNTAX HexPassword (SIZE (0..40))
			MAX-ACCESS read-write
			STATUS current
			DESCRIPTION
				"ESP Authentication Key for outbound traffic."
			::= { ccWanVpnKeyManualEntry 12 }

		
		-- 1.3.6.1.4.1.388.11.2.5.1.6.4.2.1.13
		ccWanVpnKeyManualInEspSpi OBJECT-TYPE
			SYNTAX Unsigned32 (256..4294967295)
			MAX-ACCESS read-write
			STATUS current
			DESCRIPTION
				"inbound security association created by the ESP algorithm."
			DEFVAL { 256 }
			::= { ccWanVpnKeyManualEntry 13 }
-- ??-India: is this range correct?
-- note that it's SET via decimal, not hex.
		
		-- 1.3.6.1.4.1.388.11.2.5.1.6.4.2.1.14
		ccWanVpnKeyManualOutEspSpi OBJECT-TYPE
			SYNTAX Unsigned32 (256..4294967295)
			MAX-ACCESS read-write
			STATUS current
			DESCRIPTION
				"outbound security association created by the ESP algorithm."
			DEFVAL { 256 }
			::= { ccWanVpnKeyManualEntry 14 }
-- ??-India: is this range correct?
-- note that it's SET via decimal, not hex.
		
		-- 1.3.6.1.4.1.388.11.2.5.1.6.4.3
		ccWanVpnKeyAutoTable OBJECT-TYPE
			SYNTAX SEQUENCE OF CcWanVpnKeyAutoEntry
			MAX-ACCESS not-accessible
			STATUS current
			DESCRIPTION
				"Table of Auto Key Setting entries."
			::= { ccWanVpnTunnelConfig 3 }

		
		-- 1.3.6.1.4.1.388.11.2.5.1.6.4.3.1
		ccWanVpnKeyAutoEntry OBJECT-TYPE
			SYNTAX CcWanVpnKeyAutoEntry
			MAX-ACCESS not-accessible
			STATUS current
			DESCRIPTION
				"Description."
			AUGMENTS { ccWanVpnEntry }
			::= { ccWanVpnKeyAutoTable 1 }

		
		CcWanVpnKeyAutoEntry ::=
			SEQUENCE { 
				ccWanVpnKeyAutoUsePerfectSecrecy
					TruthValue,
				ccWanVpnKeyAutoAhAuth
					INTEGER,
				ccWanVpnKeyAutoEspType
					INTEGER,
				ccWanVpnKeyAutoEspEncrypAlg
					INTEGER,
				ccWanVpnKeyAutoEspAuthAlg
					INTEGER,
				ccWanVpnKeyAutoIkeOperationMode
					INTEGER,
				ccWanVpnKeyAutoIkeLocalIdType
					INTEGER,
				ccWanVpnKeyAutoIkeLocalIdData
					DisplayString,
				ccWanVpnKeyAutoIkeRemoteIdType
					INTEGER,
				ccWanVpnKeyAutoIkeRemoteIdData
					DisplayString,
				ccWanVpnKeyAutoIkeAuthType
					INTEGER,
				ccWanVpnKeyAutoIkeAuthAlg
					INTEGER,
				ccWanVpnKeyAutoIkeAuthPassphrase
					Password,
				ccWanVpnKeyAutoIkeEncrypAlg
					INTEGER,
				ccWanVpnKeyAutoIkeXauthMode
					INTEGER,
				ccWanVpnKeyAutoIkeXauthUsername
					DisplayString,
				ccWanVpnKeyAutoIkeXauthPassword
					Password,
				ccWanVpnKeyAutoIkeKeyLifetime
					Unsigned32,
				ccWanVpnKeyAutoIkeDiffieHelmanGroup
					INTEGER
			 }

		-- 1.3.6.1.4.1.388.11.2.5.1.6.4.3.1.1
		ccWanVpnKeyAutoUsePerfectSecrecy OBJECT-TYPE
			SYNTAX TruthValue
			MAX-ACCESS read-write
			STATUS current
			DESCRIPTION
				"enable Perfect Forward Secrecy."
			DEFVAL { false }
			::= { ccWanVpnKeyAutoEntry 1 }

		
		-- 1.3.6.1.4.1.388.11.2.5.1.6.4.3.1.2
		ccWanVpnKeyAutoAhAuth OBJECT-TYPE
			SYNTAX INTEGER
				{
				none(1),
				md5(2),
				sha1(3)
				}
			MAX-ACCESS read-write
			STATUS current
			DESCRIPTION
				"data authentication and anti-replay services for the VPN tunnel."
			DEFVAL { none }
			::= { ccWanVpnKeyAutoEntry 2 }

		
		-- 1.3.6.1.4.1.388.11.2.5.1.6.4.3.1.3
		ccWanVpnKeyAutoEspType OBJECT-TYPE
			SYNTAX INTEGER
				{
				none(1),
				esp(2),
				espWithAuthentication(3)
				}
			MAX-ACCESS read-write
			STATUS current
			DESCRIPTION
				"packet encryption and optional data authentication and
				anti-replay services for the VPN tunnel.
				
				Some of the next 2 variables are used depending on:
				  none        - the 2 variables are ignored
				  esp         - the first is used, the second is ignored
				  espWithAuth - both variables are used"
			DEFVAL { esp }
			::= { ccWanVpnKeyAutoEntry 3 }

		
		-- 1.3.6.1.4.1.388.11.2.5.1.6.4.3.1.4
		ccWanVpnKeyAutoEspEncrypAlg OBJECT-TYPE
			SYNTAX INTEGER
				{
				des(1),
				des3(2),
				aes128bit(3),
				aes196bit(4),
				aes256bit(5)
				}
			MAX-ACCESS read-write
			STATUS current
			DESCRIPTION
				"ESP Encryption Algorithm."
			DEFVAL { des }
			::= { ccWanVpnKeyAutoEntry 4 }

		
		-- 1.3.6.1.4.1.388.11.2.5.1.6.4.3.1.5
		ccWanVpnKeyAutoEspAuthAlg OBJECT-TYPE
			SYNTAX INTEGER
				{
				md5(1),
				sha1(2)
				}
			MAX-ACCESS read-write
			STATUS current
			DESCRIPTION
				"ESP Authentication Algorithm.
				"
			DEFVAL { md5 }
			::= { ccWanVpnKeyAutoEntry 5 }

		
		-- 1.3.6.1.4.1.388.11.2.5.1.6.4.3.1.6
		ccWanVpnKeyAutoIkeOperationMode OBJECT-TYPE
			SYNTAX INTEGER
				{
				main(1),
				aggressive(2)
				}
			MAX-ACCESS read-write
			STATUS current
			DESCRIPTION
				"IKE opreational mode.
				IKE main mode refers to the identity-protection exchange,
				and IKE aggressive mode refers to the aggressive exchange"
			DEFVAL { main }
			::= { ccWanVpnKeyAutoEntry 6 }

		
		-- 1.3.6.1.4.1.388.11.2.5.1.6.4.3.1.7
		ccWanVpnKeyAutoIkeLocalIdType OBJECT-TYPE
			SYNTAX INTEGER
				{
				ip(1),
				fqdn(2),
				ufqdn(3)
				}
			MAX-ACCESS read-write
			STATUS current
			DESCRIPTION
				"type of ID to be used for the WS 2000 end of the SA.
				
				The next variable only applies if this is set to 'fqdn' or 'ufqdn'.
				"
			DEFVAL { ip }
			::= { ccWanVpnKeyAutoEntry 7 }

		
		-- 1.3.6.1.4.1.388.11.2.5.1.6.4.3.1.8
		ccWanVpnKeyAutoIkeLocalIdData OBJECT-TYPE
			SYNTAX DisplayString
			MAX-ACCESS read-write
			STATUS current
			DESCRIPTION
				"Based upon the Local ID type you gave, specify the FQDN or UFQDN,"
			DEFVAL { "?" }
			::= { ccWanVpnKeyAutoEntry 8 }
-- This value ranges in size 0..256 octets.  (This would have
-- been added as a range to the syntax, but when this is done,
-- it causes an error in MG-Soft Builder).
-- 
		
		-- 1.3.6.1.4.1.388.11.2.5.1.6.4.3.1.9
		ccWanVpnKeyAutoIkeRemoteIdType OBJECT-TYPE
			SYNTAX INTEGER
				{
				ip(1),
				fqdn(2),
				ufqdn(3)
				}
			MAX-ACCESS read-write
			STATUS current
			DESCRIPTION
				"type of ID to be used for the remote end of the SA.
				
				The next variable only applies if this is set to 'fqdn' or 'ufqdn'.
				"
			DEFVAL { ip }
			::= { ccWanVpnKeyAutoEntry 9 }

		
		-- 1.3.6.1.4.1.388.11.2.5.1.6.4.3.1.10
		ccWanVpnKeyAutoIkeRemoteIdData OBJECT-TYPE
			SYNTAX DisplayString
			MAX-ACCESS read-write
			STATUS current
			DESCRIPTION
				"Based upon the Remote ID type you gave, specify the FQDN or UFQDN."
			DEFVAL { "?" }
			::= { ccWanVpnKeyAutoEntry 10 }
-- This value ranges in size 0..256 octets.  (This would have
-- been added as a range to the syntax, but when this is done,
-- it causes an error in MG-Soft Builder).
		
		-- 1.3.6.1.4.1.388.11.2.5.1.6.4.3.1.11
		ccWanVpnKeyAutoIkeAuthType OBJECT-TYPE
			SYNTAX INTEGER
				{
				psk(1),
				rsa(2)
				}
			MAX-ACCESS read-write
			STATUS current
			DESCRIPTION
				"IKE Authentication Type."
			DEFVAL { psk }
			::= { ccWanVpnKeyAutoEntry 11 }

		
		-- 1.3.6.1.4.1.388.11.2.5.1.6.4.3.1.12
		ccWanVpnKeyAutoIkeAuthAlg OBJECT-TYPE
			SYNTAX INTEGER
				{
				md5(1),
				sha1(2)
				}
			MAX-ACCESS read-write
			STATUS current
			DESCRIPTION
				"IKE Authentication Algorithm."
			DEFVAL { md5 }
			::= { ccWanVpnKeyAutoEntry 12 }

		
		-- 1.3.6.1.4.1.388.11.2.5.1.6.4.3.1.13
		ccWanVpnKeyAutoIkeAuthPassphrase OBJECT-TYPE
			SYNTAX Password
			MAX-ACCESS read-write
			STATUS current
			DESCRIPTION
				"With Pre-Shared Key as the authentication mode, provide a key.
				MD5  : 32-character hexadecimal key.
				SHA1 : 40-character hexadecimal key.
				"
			DEFVAL { "?" }
			::= { ccWanVpnKeyAutoEntry 13 }
-- ??-India: length?
		
		-- 1.3.6.1.4.1.388.11.2.5.1.6.4.3.1.14
		ccWanVpnKeyAutoIkeEncrypAlg OBJECT-TYPE
			SYNTAX INTEGER
				{
				des(1),
				des3(2),
				aes128bit(3),
				aes196bit(4),
				aes256bit(5)
				}
			MAX-ACCESS read-write
			STATUS current
			DESCRIPTION
				"IKE Encryption Algorithm."
			DEFVAL { des }
			::= { ccWanVpnKeyAutoEntry 14 }

		
		-- 1.3.6.1.4.1.388.11.2.5.1.6.4.3.1.15
		ccWanVpnKeyAutoIkeXauthMode OBJECT-TYPE
			SYNTAX INTEGER
				{
				none(1),
				generic(2)
				}
			MAX-ACCESS read-write
			STATUS current
			DESCRIPTION
				"Currently XAUTH mechanism is not supported by WS2000 version 2.0.
				If 'none', the next 2 variables are ignored.
				"
			DEFVAL { none }
			::= { ccWanVpnKeyAutoEntry 15 }

		
		-- 1.3.6.1.4.1.388.11.2.5.1.6.4.3.1.16
		ccWanVpnKeyAutoIkeXauthUsername OBJECT-TYPE
			SYNTAX DisplayString
			MAX-ACCESS read-write
			STATUS current
			DESCRIPTION
				"Currently XAUTH mechanism is not supported by WS2000 version 2.0."
			DEFVAL { "?" }
			::= { ccWanVpnKeyAutoEntry 16 }
-- ??-India: length?
-- 
		
		-- 1.3.6.1.4.1.388.11.2.5.1.6.4.3.1.17
		ccWanVpnKeyAutoIkeXauthPassword OBJECT-TYPE
			SYNTAX Password
			MAX-ACCESS read-write
			STATUS current
			DESCRIPTION
				"Currently XAUTH mechanism is not supported by WS2000 version 2.0."
			DEFVAL { "?" }
			::= { ccWanVpnKeyAutoEntry 17 }
-- ??-India: length?
-- 
		
		-- 1.3.6.1.4.1.388.11.2.5.1.6.4.3.1.18
		ccWanVpnKeyAutoIkeKeyLifetime OBJECT-TYPE
			SYNTAX Unsigned32 (300..4294967295)
			UNITS "seconds"
			MAX-ACCESS read-write
			STATUS current
			DESCRIPTION
				"The number of seconds that the key is valid."
			::= { ccWanVpnKeyAutoEntry 18 }
-- ??-India: valid range of values?  defval?
		
		-- 1.3.6.1.4.1.388.11.2.5.1.6.4.3.1.19
		ccWanVpnKeyAutoIkeDiffieHelmanGroup OBJECT-TYPE
			SYNTAX INTEGER
				{
				group1length768bit(1),
				group2length1024bit(2)
				}
			MAX-ACCESS read-write
			STATUS current
			DESCRIPTION
				"The Diffie-Hellman key agreement protocol allows two users to exchange
				a secret key over an insecure medium without any prior secrets."
			DEFVAL { group1length768bit }
			::= { ccWanVpnKeyAutoEntry 19 }

		
		-- 1.3.6.1.4.1.388.11.2.5.1.6.5
		ccWanVpnTunnelStatus OBJECT IDENTIFIER ::= { ccWanVpn 5 }

		
		-- 1.3.6.1.4.1.388.11.2.5.1.6.5.1
		ccWanVpnSaTable OBJECT-TYPE
			SYNTAX SEQUENCE OF CcWanVpnSaEntry
			MAX-ACCESS not-accessible
			STATUS current
			DESCRIPTION
				"Status of all tunnels that have been 
				configured on the switch."
			::= { ccWanVpnTunnelStatus 1 }

		
		-- 1.3.6.1.4.1.388.11.2.5.1.6.5.1.1
		ccWanVpnSaEntry OBJECT-TYPE
			SYNTAX CcWanVpnSaEntry
			MAX-ACCESS not-accessible
			STATUS current
			DESCRIPTION
				"Description."
			INDEX { ccWanVpnSaTunnelName }
			::= { ccWanVpnSaTable 1 }
-- ??-India: should this AUGMENT the main VPN table?
		
		CcWanVpnSaEntry ::=
			SEQUENCE { 
				ccWanVpnSaTunnelName
					DisplayString,
				ccWanVpnSaStatus
					INTEGER,
				ccWanVpnSaInSpi
					Unsigned32,
				ccWanVpnSaOutSpi
					Unsigned32,
				ccWanVpnSaLifetime
					Unsigned32,
				ccWanVpnSaTxBytes
					Unsigned32,
				ccWanVpnSaRxBytes
					Unsigned32
			 }

		-- 1.3.6.1.4.1.388.11.2.5.1.6.5.1.1.1
		ccWanVpnSaTunnelName OBJECT-TYPE
			SYNTAX DisplayString (SIZE (1..13))
			MAX-ACCESS read-only
			STATUS current
			DESCRIPTION
				"Tunnel Name."
			::= { ccWanVpnSaEntry 1 }

		
		-- 1.3.6.1.4.1.388.11.2.5.1.6.5.1.1.2
		ccWanVpnSaStatus OBJECT-TYPE
			SYNTAX INTEGER
				{
				active(1),
				nonActive(2)
				}
			MAX-ACCESS read-only
			STATUS current
			DESCRIPTION
				"Status of each of the configured tunnels.
				When the tunnel is not in use the status will read NOT_ACTIVE.
				When the tunnel is connected the status will read ACTIVE."
			::= { ccWanVpnSaEntry 2 }

		
		-- 1.3.6.1.4.1.388.11.2.5.1.6.5.1.1.3
		ccWanVpnSaInSpi OBJECT-TYPE
			SYNTAX Unsigned32 (256..4294967295)
			MAX-ACCESS read-only
			STATUS current
			DESCRIPTION
				"Inbound SPI Security Parameter Index (SPI) for each of the tunnels.
				This is used locally by the switch to identify a security association.
				There are unique outbound and inbound SPIs."
			::= { ccWanVpnSaEntry 3 }

		
		-- 1.3.6.1.4.1.388.11.2.5.1.6.5.1.1.4
		ccWanVpnSaOutSpi OBJECT-TYPE
			SYNTAX Unsigned32 (256..4294967295)
			MAX-ACCESS read-only
			STATUS current
			DESCRIPTION
				"Outbound Security Parameter Index (SPI) for each of the tunnels.
				This is used locally by the switch to identify a security association.
				There are unique outbound and inbound SPIs."
			::= { ccWanVpnSaEntry 4 }

		
		-- 1.3.6.1.4.1.388.11.2.5.1.6.5.1.1.5
		ccWanVpnSaLifetime OBJECT-TYPE
			SYNTAX Unsigned32
			UNITS "seconds"
			MAX-ACCESS read-only
			STATUS current
			DESCRIPTION
				"Lifetime associated with a particular Security Association (SA). "
			::= { ccWanVpnSaEntry 5 }

		
		-- 1.3.6.1.4.1.388.11.2.5.1.6.5.1.1.6
		ccWanVpnSaTxBytes OBJECT-TYPE
			SYNTAX Unsigned32
			MAX-ACCESS read-only
			STATUS current
			DESCRIPTION
				"Total number amount of data (in bytes) transmitted 
				through each of the configured tunnels."
			::= { ccWanVpnSaEntry 6 }

		
		-- 1.3.6.1.4.1.388.11.2.5.1.6.5.1.1.7
		ccWanVpnSaRxBytes OBJECT-TYPE
			SYNTAX Unsigned32
			MAX-ACCESS read-only
			STATUS current
			DESCRIPTION
				"Total number amount of data (in bytes) received 
				through each of the configured tunnels."
			::= { ccWanVpnSaEntry 7 }

		
		-- 1.3.6.1.4.1.388.11.2.5.1.6.5.2
		ccWanVpnIkeTable OBJECT-TYPE
			SYNTAX SEQUENCE OF CcWanVpnIkeEntry
			MAX-ACCESS not-accessible
			STATUS current
			DESCRIPTION
				"Table of tunnels configured to use IKE for automatic key exchange"
			::= { ccWanVpnTunnelStatus 2 }

		
		-- 1.3.6.1.4.1.388.11.2.5.1.6.5.2.1
		ccWanVpnIkeEntry OBJECT-TYPE
			SYNTAX CcWanVpnIkeEntry
			MAX-ACCESS not-accessible
			STATUS current
			DESCRIPTION
				"Description."
			INDEX { ccWanVpnIkeTunnelName }
			::= { ccWanVpnIkeTable 1 }
-- ??-India: should this AUGMENT the main VPN table?
		
		CcWanVpnIkeEntry ::=
			SEQUENCE { 
				ccWanVpnIkeTunnelName
					DisplayString,
				ccWanVpnIkeState
					DisplayString,
				ccWanVpnIkeRemainingLife
					Unsigned32
			 }

		-- 1.3.6.1.4.1.388.11.2.5.1.6.5.2.1.1
		ccWanVpnIkeTunnelName OBJECT-TYPE
			SYNTAX DisplayString (SIZE (1..20))
			MAX-ACCESS read-only
			STATUS current
			DESCRIPTION
				"Tunnel name."
			::= { ccWanVpnIkeEntry 1 }

		
		-- 1.3.6.1.4.1.388.11.2.5.1.6.5.2.1.2
		ccWanVpnIkeState OBJECT-TYPE
			SYNTAX DisplayString
			MAX-ACCESS read-only
			STATUS current
			DESCRIPTION
				"State for each of the tunnels configured
				to use IKE for automatic key exchange.
				When the tunnel is not active this will display NOT_CONNECTED.
				When the tunnel is active this will display CONNECTED.
				"
			::= { ccWanVpnIkeEntry 2 }

		
		-- 1.3.6.1.4.1.388.11.2.5.1.6.5.2.1.3
		ccWanVpnIkeRemainingLife OBJECT-TYPE
			SYNTAX Unsigned32
			UNITS "seconds"
			MAX-ACCESS read-only
			STATUS current
			DESCRIPTION
				"Remaining life for the current IKE key
				for each of the listed tunnels."
			::= { ccWanVpnIkeEntry 3 }

		
		-- 1.3.6.1.4.1.388.11.2.5.1.7
		ccWanContentBlock OBJECT IDENTIFIER ::= { ccWan 7 }

		
		-- 1.3.6.1.4.1.388.11.2.5.1.7.1
		ccWanContentBlockSmtp OBJECT-TYPE
			SYNTAX BITS
				{
				blockSmtpHelo(0),
				blockSmtpMail(1),
				blockSmtpRcpt(2),
				blockSmtpData(3),
				blockSmtpQuit(4),
				blockSmtpSend(5),
				blockSmtpSaml(6),
				blockSmtpReset(7),
				blockSmtpVrfy(8),
				blockSmtpExpn(9)
				}
			MAX-ACCESS read-write
			STATUS current
			DESCRIPTION
				"SMTP content block."
			::= { ccWanContentBlock 1 }

		
		-- 1.3.6.1.4.1.388.11.2.5.1.7.2
		ccWanContentBlockFtp OBJECT-TYPE
			SYNTAX BITS
				{
				blockFtpStoringFiles(0),
				blockFtpRetrievingFiles(1),
				blockFtpDirectoryList(2),
				blockFtpCreateDirectory(3),
				blockFtpChangeDirectory(4),
				blockFtpPassiveOperation(5)
				}
			MAX-ACCESS read-write
			STATUS current
			DESCRIPTION
				"FTP content block."
			::= { ccWanContentBlock 2 }

		
		-- 1.3.6.1.4.1.388.11.2.5.1.7.3
		ccWanContentBlockHttp OBJECT-TYPE
			SYNTAX BITS
				{
				blockHttpWebProxy(0),
				blockHttpActiveX(1)
				}
			MAX-ACCESS read-write
			STATUS current
			DESCRIPTION
				"HTTP content block."
			::= { ccWanContentBlock 3 }

		
		-- 1.3.6.1.4.1.388.11.2.5.1.7.4
		ccWanContentBlockOutUrlTable OBJECT-TYPE
			SYNTAX SEQUENCE OF CcWanContentBlockOutUrlEntry
			MAX-ACCESS not-accessible
			STATUS current
			DESCRIPTION
				"Table of Content Block URL entries."
			::= { ccWanContentBlock 4 }

		
		-- 1.3.6.1.4.1.388.11.2.5.1.7.4.1
		ccWanContentBlockOutUrlEntry OBJECT-TYPE
			SYNTAX CcWanContentBlockOutUrlEntry
			MAX-ACCESS not-accessible
			STATUS current
			DESCRIPTION
				"Description."
			INDEX { ccWanContentBlockOutUrlIndex }
			::= { ccWanContentBlockOutUrlTable 1 }

		
		CcWanContentBlockOutUrlEntry ::=
			SEQUENCE { 
				ccWanContentBlockOutUrlIndex
					Unsigned32,
				ccWanContentBlockOutUrlExtension
					DisplayString,
				ccWanContentBlockOutUrlRowStatus
					StaticRowEnable
			 }

		-- 1.3.6.1.4.1.388.11.2.5.1.7.4.1.1
		ccWanContentBlockOutUrlIndex OBJECT-TYPE
			SYNTAX Unsigned32 (1..100)
			MAX-ACCESS read-only
			STATUS current
			DESCRIPTION
				"Simple Index."
			::= { ccWanContentBlockOutUrlEntry 1 }
-- ??-India: range OK?
		
		-- 1.3.6.1.4.1.388.11.2.5.1.7.4.1.2
		ccWanContentBlockOutUrlExtension OBJECT-TYPE
			SYNTAX DisplayString
			MAX-ACCESS read-write
			STATUS current
			DESCRIPTION
				"URL extension."
			::= { ccWanContentBlockOutUrlEntry 2 }

		
		-- 1.3.6.1.4.1.388.11.2.5.1.7.4.1.3
		ccWanContentBlockOutUrlRowStatus OBJECT-TYPE
			SYNTAX StaticRowEnable
			MAX-ACCESS read-write
			STATUS current
			DESCRIPTION
				"Row Status."
			::= { ccWanContentBlockOutUrlEntry 3 }

		
-- This group describes the physical ports on the unit.
		-- 1.3.6.1.4.1.388.11.2.5.2
		ccPort OBJECT IDENTIFIER ::= { ccSwitch 2 }

		
-- This table contains one entry for each physical port
-- on the switch.
		-- 1.3.6.1.4.1.388.11.2.5.2.1
		ccPortTable OBJECT-TYPE
			SYNTAX SEQUENCE OF CcPortEntry
			MAX-ACCESS not-accessible
			STATUS current
			DESCRIPTION
				"This table contains one entry for each physical port
				on the switch."
			::= { ccPort 1 }

		
		-- 1.3.6.1.4.1.388.11.2.5.2.1.1
		ccPortEntry OBJECT-TYPE
			SYNTAX CcPortEntry
			MAX-ACCESS not-accessible
			STATUS current
			DESCRIPTION
				" "
			INDEX { ccPortIndex }
			::= { ccPortTable 1 }

		
		CcPortEntry ::=
			SEQUENCE { 
				ccPortIndex
					Integer32,
				ccPortType
					INTEGER,
				ccPortPoeEquipped
					TruthValue,
				ccPortStatus
					INTEGER,
				ccPortDuplex
					INTEGER,
				ccPortSpeed
					Unsigned32
			 }

		-- 1.3.6.1.4.1.388.11.2.5.2.1.1.1
		ccPortIndex OBJECT-TYPE
			SYNTAX Integer32 (1..127)
			MAX-ACCESS accessible-for-notify
			STATUS current
			DESCRIPTION
				"Simple index.
				
				Instance/index .1 represents the port labelled '1' on the
				physical unit.
				
				The WAN port will reside after all ports that are numbered
				on the physcial unit."
			::= { ccPortEntry 1 }

		
		-- 1.3.6.1.4.1.388.11.2.5.2.1.1.2
		ccPortType OBJECT-TYPE
			SYNTAX INTEGER
				{
				wanPort(1),
				lanPort(2)
				}
			MAX-ACCESS read-only
			STATUS current
			DESCRIPTION
				"Indicates the type of the port."
			::= { ccPortEntry 2 }

		
		-- 1.3.6.1.4.1.388.11.2.5.2.1.1.3
		ccPortPoeEquipped OBJECT-TYPE
			SYNTAX TruthValue
			MAX-ACCESS read-only
			STATUS current
			DESCRIPTION
				"Indicates the port can provide power-over-ethernet."
			::= { ccPortEntry 3 }

		
		-- 1.3.6.1.4.1.388.11.2.5.2.1.1.4
		ccPortStatus OBJECT-TYPE
			SYNTAX INTEGER
				{
				linkUp(1),
				linkDown(2)
				}
			MAX-ACCESS read-only
			STATUS current
			DESCRIPTION
				"Tells if the port is up/down."
			::= { ccPortEntry 4 }

		
		-- 1.3.6.1.4.1.388.11.2.5.2.1.1.5
		ccPortDuplex OBJECT-TYPE
			SYNTAX INTEGER
				{
				halfDuplex(1),
				fullDuplex(2)
				}
			MAX-ACCESS read-only
			STATUS current
			DESCRIPTION
				"Describes the duplex, (half/full), status of the port."
			::= { ccPortEntry 5 }

		
		-- 1.3.6.1.4.1.388.11.2.5.2.1.1.6
		ccPortSpeed OBJECT-TYPE
			SYNTAX Unsigned32
			MAX-ACCESS read-only
			STATUS current
			DESCRIPTION
				"Link's speed in bits per second."
			::= { ccPortEntry 6 }

		
		-- 1.3.6.1.4.1.388.11.2.5.4
		ccLan OBJECT IDENTIFIER ::= { ccSwitch 4 }

		
		-- 1.3.6.1.4.1.388.11.2.5.4.2
		ccSubnet OBJECT IDENTIFIER ::= { ccLan 2 }

		
		-- 1.3.6.1.4.1.388.11.2.5.4.2.1
		ccSubnetTable OBJECT-TYPE
			SYNTAX SEQUENCE OF CcSubnetEntry
			MAX-ACCESS not-accessible
			STATUS current
			DESCRIPTION
				"Table of Subnets."
			::= { ccSubnet 1 }

		
		-- 1.3.6.1.4.1.388.11.2.5.4.2.1.1
		ccSubnetEntry OBJECT-TYPE
			SYNTAX CcSubnetEntry
			MAX-ACCESS not-accessible
			STATUS current
			DESCRIPTION
				" "
			INDEX { ccSubnetIndex }
			::= { ccSubnetTable 1 }

		
		CcSubnetEntry ::=
			SEQUENCE { 
				ccSubnetIndex
					Integer32,
				ccSubnetEnable
					StaticRowEnable,
				ccSubnetName
					DisplayString,
				ccSubnetIpAddress
					IpAddress,
				ccSubnetIpSubnetMask
					IpAddress,
				ccSubnetPortMembers
					BITS,
				ccSubnetWlanMembers
					BITS,
				ccSubnetDhcpState
					INTEGER,
				ccSubnetDhcpIpAddress
					IpAddress,
				ccSubnetDhcpSubnetMask
					IpAddress
			 }

		-- 1.3.6.1.4.1.388.11.2.5.4.2.1.1.1
		ccSubnetIndex OBJECT-TYPE
			SYNTAX Integer32 (1..127)
			MAX-ACCESS accessible-for-notify
			STATUS current
			DESCRIPTION
				"Simple index, 1..4"
			::= { ccSubnetEntry 1 }

		
		-- 1.3.6.1.4.1.388.11.2.5.4.2.1.1.2
		ccSubnetEnable OBJECT-TYPE
			SYNTAX StaticRowEnable
			MAX-ACCESS read-write
			STATUS current
			DESCRIPTION
				"Enable this Subnet."
			::= { ccSubnetEntry 2 }

		
		-- 1.3.6.1.4.1.388.11.2.5.4.2.1.1.3
		ccSubnetName OBJECT-TYPE
			SYNTAX DisplayString
			MAX-ACCESS read-write
			STATUS current
			DESCRIPTION
				"Subnet name."
			::= { ccSubnetEntry 3 }

		
		-- 1.3.6.1.4.1.388.11.2.5.4.2.1.1.4
		ccSubnetIpAddress OBJECT-TYPE
			SYNTAX IpAddress
			MAX-ACCESS read-write
			STATUS current
			DESCRIPTION
				"Ip address of this Subnet."
			::= { ccSubnetEntry 4 }

		
		-- 1.3.6.1.4.1.388.11.2.5.4.2.1.1.5
		ccSubnetIpSubnetMask OBJECT-TYPE
			SYNTAX IpAddress
			MAX-ACCESS read-write
			STATUS current
			DESCRIPTION
				"IPaddr subnet mask of this Subnet"
			::= { ccSubnetEntry 5 }

		
		-- 1.3.6.1.4.1.388.11.2.5.4.2.1.1.6
		ccSubnetPortMembers OBJECT-TYPE
			SYNTAX BITS
				{
				null(0),
				port1(1),
				port2(2),
				port3(3),
				port4(4),
				port5(5),
				port6(6)
				}
			MAX-ACCESS read-write
			STATUS current
			DESCRIPTION
				"Pointer to zero or more ports that are members of
				this Subnet.
				
				No port can be a member of more than one Subnet at 
				any given time."
			::= { ccSubnetEntry 6 }

		
		-- 1.3.6.1.4.1.388.11.2.5.4.2.1.1.7
		ccSubnetWlanMembers OBJECT-TYPE
			SYNTAX BITS
				{
				null(0),
				wlan1(1),
				wlan2(2),
				wlan3(3),
				wlan4(4)
				}
			MAX-ACCESS read-write
			STATUS current
			DESCRIPTION
				"Pointer to zero or more WLANs that are members of
				this Subnet.
				
				No Subnet can be a member of more than one Subnet at 
				any given time."
			::= { ccSubnetEntry 7 }

		
		-- 1.3.6.1.4.1.388.11.2.5.4.2.1.1.8
		ccSubnetDhcpState OBJECT-TYPE
			SYNTAX INTEGER
				{
				dhcpClient(1),
				dhcpServer(2),
				dhcpNone(3)
				}
			MAX-ACCESS read-write
			STATUS current
			DESCRIPTION
				"Specifies how Subnet gets its IP address/mask."
			::= { ccSubnetEntry 8 }

		
		-- 1.3.6.1.4.1.388.11.2.5.4.2.1.1.9
		ccSubnetDhcpIpAddress OBJECT-TYPE
			SYNTAX IpAddress
			MAX-ACCESS read-only
			STATUS current
			DESCRIPTION
				"The IP address obtained via DHCP if this Subnet is
				configured as a DHCP client.
				
				If this Subnet is configured to not use DHCP, or is a
				DHCP server this value will be 0.0.0.0.  Likewise, if
				this Subnet is configured to be a DHCP client but has
				not yet obtained a value via DHCP, this value will be
				0.0.0.0."
			::= { ccSubnetEntry 9 }

		
		-- 1.3.6.1.4.1.388.11.2.5.4.2.1.1.10
		ccSubnetDhcpSubnetMask OBJECT-TYPE
			SYNTAX IpAddress
			MAX-ACCESS read-only
			STATUS current
			DESCRIPTION
				"The Subnet IPaddr subnet mask obtained via DHCP if 
				this Subnet is configured as a DHCP client.
				
				If this Subnet is configured to not use DHCP, or is a
				DHCP server this value will be 0.0.0.0.  Likewise, if
				this Subnet is configured to be a DHCP client but has 
				not yet obtained a value via DHCP, this value will be 
				0.0.0.0."
			::= { ccSubnetEntry 10 }

		
		-- 1.3.6.1.4.1.388.11.2.5.4.2.2
		ccSubnetDhcpServerTable OBJECT-TYPE
			SYNTAX SEQUENCE OF CcSubnetDhcpServerEntry
			MAX-ACCESS not-accessible
			STATUS current
			DESCRIPTION
				"Configures a DHCP server for a Subnet.  While these 
				values can always be SET, they will only take effect
				if the given Subnet is enabled and configured to be 
				a DHCP server."
			::= { ccSubnet 2 }

		
		-- 1.3.6.1.4.1.388.11.2.5.4.2.2.1
		ccSubnetDhcpServerEntry OBJECT-TYPE
			SYNTAX CcSubnetDhcpServerEntry
			MAX-ACCESS not-accessible
			STATUS current
			DESCRIPTION
				" "
			INDEX { ccSubnetIndex }
			::= { ccSubnetDhcpServerTable 1 }

		
		CcSubnetDhcpServerEntry ::=
			SEQUENCE { 
				ccSubnetDhcpServerEnable
					StaticRowEnable,
				ccSubnetDhcpServerPoolStart
					IpAddress,
				ccSubnetDhcpServerPoolEnd
					IpAddress,
				ccSubnetDhcpServerPrimaryDns
					IpAddress,
				ccSubnetDhcpServerSecondaryDns
					IpAddress,
				ccSubnetDhcpServerDefaultGateway
					IpAddress,
				ccSubnetDhcpServerLeaseTime
					Integer32,
				ccSubnetDhcpServerWinsServer
					IpAddress,
				ccSubnetDhcpServerDomainName
					DisplayString
			 }

		-- 1.3.6.1.4.1.388.11.2.5.4.2.2.1.1
		ccSubnetDhcpServerEnable OBJECT-TYPE
			SYNTAX StaticRowEnable
			MAX-ACCESS read-only
			STATUS current
			DESCRIPTION
				"Enable DHCP Server functionality on this Subnet."
			::= { ccSubnetDhcpServerEntry 1 }

		
		-- 1.3.6.1.4.1.388.11.2.5.4.2.2.1.2
		ccSubnetDhcpServerPoolStart OBJECT-TYPE
			SYNTAX IpAddress
			MAX-ACCESS read-write
			STATUS current
			DESCRIPTION
				"The start/low end of the range of IP addresses to
				give-out."
			::= { ccSubnetDhcpServerEntry 2 }

		
		-- 1.3.6.1.4.1.388.11.2.5.4.2.2.1.3
		ccSubnetDhcpServerPoolEnd OBJECT-TYPE
			SYNTAX IpAddress
			MAX-ACCESS read-write
			STATUS current
			DESCRIPTION
				"The end/high-end of the range of IP addresses to
				give-out."
			::= { ccSubnetDhcpServerEntry 3 }

		
		-- 1.3.6.1.4.1.388.11.2.5.4.2.2.1.4
		ccSubnetDhcpServerPrimaryDns OBJECT-TYPE
			SYNTAX IpAddress
			MAX-ACCESS read-write
			STATUS current
			DESCRIPTION
				"IP address of primary DNS server to assign to DHCP
				clients."
			::= { ccSubnetDhcpServerEntry 4 }

		
		-- 1.3.6.1.4.1.388.11.2.5.4.2.2.1.5
		ccSubnetDhcpServerSecondaryDns OBJECT-TYPE
			SYNTAX IpAddress
			MAX-ACCESS read-write
			STATUS current
			DESCRIPTION
				"IP address of secondary DNS server to assign to DHCP
				clients."
			::= { ccSubnetDhcpServerEntry 5 }

		
		-- 1.3.6.1.4.1.388.11.2.5.4.2.2.1.6
		ccSubnetDhcpServerDefaultGateway OBJECT-TYPE
			SYNTAX IpAddress
			MAX-ACCESS read-write
			STATUS current
			DESCRIPTION
				"IP address of default gateway to assign to DHCP
				clients."
			::= { ccSubnetDhcpServerEntry 6 }

		
		-- 1.3.6.1.4.1.388.11.2.5.4.2.2.1.7
		ccSubnetDhcpServerLeaseTime OBJECT-TYPE
			SYNTAX Integer32
			UNITS "seconds"
			MAX-ACCESS read-write
			STATUS current
			DESCRIPTION
				"DHCP lease time."
			::= { ccSubnetDhcpServerEntry 7 }

		
		-- 1.3.6.1.4.1.388.11.2.5.4.2.2.1.8
		ccSubnetDhcpServerWinsServer OBJECT-TYPE
			SYNTAX IpAddress
			MAX-ACCESS read-write
			STATUS current
			DESCRIPTION
				"DHCP Server WINS server IP Address."
			::= { ccSubnetDhcpServerEntry 8 }

		
		-- 1.3.6.1.4.1.388.11.2.5.4.2.2.1.9
		ccSubnetDhcpServerDomainName OBJECT-TYPE
			SYNTAX DisplayString
			MAX-ACCESS read-write
			STATUS current
			DESCRIPTION
				"DHCP server Domain Name."
			::= { ccSubnetDhcpServerEntry 9 }

		
		-- 1.3.6.1.4.1.388.11.2.5.4.2.3
		ccSubnetDhcpServerStaticMapTable OBJECT-TYPE
			SYNTAX SEQUENCE OF CcSubnetDhcpServerStaticMapEntry
			MAX-ACCESS not-accessible
			STATUS current
			DESCRIPTION
				"Table of static MAC-IPaddr mappings for the given 
				DHCP server."
			::= { ccSubnet 3 }

		
		-- 1.3.6.1.4.1.388.11.2.5.4.2.3.1
		ccSubnetDhcpServerStaticMapEntry OBJECT-TYPE
			SYNTAX CcSubnetDhcpServerStaticMapEntry
			MAX-ACCESS not-accessible
			STATUS current
			DESCRIPTION
				" "
			INDEX { ccSubnetIndex, ccSubnetDhcpServerStaticMapMac }
			::= { ccSubnetDhcpServerStaticMapTable 1 }

		
		CcSubnetDhcpServerStaticMapEntry ::=
			SEQUENCE { 
				ccSubnetDhcpServerStaticMapMac
					PhysAddress,
				ccSubnetDhcpServerStaticMapIpAddr
					IpAddress,
				ccSubnetDhcpServerStaticMapEnable
					AbbrevRowStatus
			 }

		-- 1.3.6.1.4.1.388.11.2.5.4.2.3.1.1
		ccSubnetDhcpServerStaticMapMac OBJECT-TYPE
			SYNTAX PhysAddress
			MAX-ACCESS read-create
			STATUS current
			DESCRIPTION
				"MAC address to be mapped."
			::= { ccSubnetDhcpServerStaticMapEntry 1 }

		
		-- 1.3.6.1.4.1.388.11.2.5.4.2.3.1.2
		ccSubnetDhcpServerStaticMapIpAddr OBJECT-TYPE
			SYNTAX IpAddress
			MAX-ACCESS read-create
			STATUS current
			DESCRIPTION
				"IP address to assign to this MAC address."
			::= { ccSubnetDhcpServerStaticMapEntry 2 }

		
		-- 1.3.6.1.4.1.388.11.2.5.4.2.3.1.3
		ccSubnetDhcpServerStaticMapEnable OBJECT-TYPE
			SYNTAX AbbrevRowStatus
			MAX-ACCESS read-create
			STATUS current
			DESCRIPTION
				"Value to control row creation/deletion."
			::= { ccSubnetDhcpServerStaticMapEntry 3 }

		
-- MIBs to control which entities in the switch can send
-- packets to other entities, and records the amount of
-- traffic conveyed among those entities.
-- 
-- There is no sense to attempt to count packets/octets
-- sent from a source to a dest - linux does not allow this.
-- 
-- ??- These tables all need to be re-worked for the sole
-- purpose of controlling "subnet access".  Most items need
-- to be renamed.
		-- 1.3.6.1.4.1.388.11.2.5.4.2.4
		ccSubnetAccess OBJECT IDENTIFIER ::= { ccSubnet 4 }

		
		-- 1.3.6.1.4.1.388.11.2.5.4.2.4.1
		ccSubnetAccessTable OBJECT-TYPE
			SYNTAX SEQUENCE OF CcSubnetAccessEntry
			MAX-ACCESS not-accessible
			STATUS current
			DESCRIPTION
				"Describes how packets are allowed to flow from different
				sources to different destinations.
				
				Note that since only subnets can be sources for this table,
				the ccSubnetTable:ccSubnetIndex is used as the 1st index to
				this table.
				
				Note that this table never contains entries where src==dest,
				for example, there is no entry with:
				  _SrcPointerToSource points to subnet1
				  _DestPointerToSource points to subnet1
				
				Note also that if a given subnet does not exisit, (because
				it has not been enabled in ccSubnetTable), no entries in this
				table will exist with that subnet as either src or dest.
				"
			::= { ccSubnetAccess 1 }

		
		-- 1.3.6.1.4.1.388.11.2.5.4.2.4.1.1
		ccSubnetAccessEntry OBJECT-TYPE
			SYNTAX CcSubnetAccessEntry
			MAX-ACCESS not-accessible
			STATUS current
			DESCRIPTION
				" "
			INDEX { ccSubnetIndex, ccSubnetAccessDestIndex }
			::= { ccSubnetAccessTable 1 }

		
		CcSubnetAccessEntry ::=
			SEQUENCE { 
				ccSubnetAccessDestIndex
					Unsigned32,
				ccSubnetAccessDestType
					INTEGER,
				ccSubnetAccessDestPtrToDest
					SinglePointer,
				ccSubnetAccessRuleType
					INTEGER,
				ccSubnetAccessPtrToRules
					MultiPointer255
			 }

		-- 1.3.6.1.4.1.388.11.2.5.4.2.4.1.1.1
		ccSubnetAccessDestIndex OBJECT-TYPE
			SYNTAX Unsigned32 (1..255)
			MAX-ACCESS accessible-for-notify
			STATUS current
			DESCRIPTION
				"Simple index for destination."
			::= { ccSubnetAccessEntry 1 }

		
		-- 1.3.6.1.4.1.388.11.2.5.4.2.4.1.1.2
		ccSubnetAccessDestType OBJECT-TYPE
			SYNTAX INTEGER
				{
				destSubnet(1),
				destWan(2)
				}
			MAX-ACCESS read-only
			STATUS current
			DESCRIPTION
				"Type of the destination.
				
				destDrop is a 'virtual' destination that accounts for
				all dropped packets."
			::= { ccSubnetAccessEntry 2 }

		
		-- 1.3.6.1.4.1.388.11.2.5.4.2.4.1.1.3
		ccSubnetAccessDestPtrToDest OBJECT-TYPE
			SYNTAX SinglePointer
			MAX-ACCESS read-only
			STATUS current
			DESCRIPTION
				"A pointer to the corresponding entry in the ccSubnet or 
				ccWan table, (depending on _DestType).
				"
			::= { ccSubnetAccessEntry 3 }

		
		-- 1.3.6.1.4.1.388.11.2.5.4.2.4.1.1.4
		ccSubnetAccessRuleType OBJECT-TYPE
			SYNTAX INTEGER
				{
				allow(1),
				deny(2)
				}
			MAX-ACCESS read-write
			STATUS current
			DESCRIPTION
				"All ccSubnetAccessRuleTable entries for this 
				combination of ccSubnetIndex and 
				ccSubnetAccessDestIndex will be of the same type,
				(accept or deny).
				"
			::= { ccSubnetAccessEntry 4 }

		
		-- 1.3.6.1.4.1.388.11.2.5.4.2.4.1.1.5
		ccSubnetAccessPtrToRules OBJECT-TYPE
			SYNTAX MultiPointer255
			MAX-ACCESS read-only
			STATUS current
			DESCRIPTION
				"Points to the zero or more ccSubnetAccessRuleTable
				entries that correspond to this ccSubnetIndex +
				ccSubnetAccessDestIndex combination/entry.
				
				This value cannot be changed here, but is a
				reflection of the ccSubnetAccessRuleTable entries
				that currently point to this entry via their
				ccSubnetAccessRuleSrcPtr and _DestPtr values.
				"
			::= { ccSubnetAccessEntry 5 }

		
		-- 1.3.6.1.4.1.388.11.2.5.4.2.4.2
		ccSubnetAccessRuleTable OBJECT-TYPE
			SYNTAX SEQUENCE OF CcSubnetAccessRuleEntry
			MAX-ACCESS not-accessible
			STATUS current
			DESCRIPTION
				"Describes how packets are allowed to flow from different
				sources to different destinations.
				
				Note that since only subnets can be sources for this table,
				the ccSubnetTable:ccSubnetIndex is used as the 1st index to
				this table.
				
				Note that this table never contains entries where src==dest,
				for example, there is no entry with:
				  _SrcPointerToSource points to subnet1
				  _DestPointerToSource points to subnet1
				
				Note also that if a given subnet does not exisit, (because
				it has not been enabled in ccSubnetTable), no entries in this
				table will exist with that subnet as either src or dest.
				"
			::= { ccSubnetAccess 2 }

		
		-- 1.3.6.1.4.1.388.11.2.5.4.2.4.2.1
		ccSubnetAccessRuleEntry OBJECT-TYPE
			SYNTAX CcSubnetAccessRuleEntry
			MAX-ACCESS not-accessible
			STATUS current
			DESCRIPTION
				" "
			INDEX { ccSubnetAccessRuleIndex }
			::= { ccSubnetAccessRuleTable 1 }

		
		CcSubnetAccessRuleEntry ::=
			SEQUENCE { 
				ccSubnetAccessRuleIndex
					Unsigned32,
				ccSubnetAccessRuleSrcPtr
					SinglePointer,
				ccSubnetAccessRuleDestPtr
					SinglePointer,
				ccSubnetAccessRuleName
					DisplayString,
				ccSubnetAccessRuleTransport
					INTEGER,
				ccSubnetAccessRuleStartPort
					Integer32,
				ccSubnetAccessRuleEndPort
					Integer32,
				ccSubnetAccessRuleRowStatus
					AbbrevRowStatus
			 }

		-- 1.3.6.1.4.1.388.11.2.5.4.2.4.2.1.1
		ccSubnetAccessRuleIndex OBJECT-TYPE
			SYNTAX Unsigned32 (1..1000)
			MAX-ACCESS accessible-for-notify
			STATUS current
			DESCRIPTION
				"Each src/dest combination can have several rules;
				this value is the index."
			::= { ccSubnetAccessRuleEntry 1 }

		
		-- 1.3.6.1.4.1.388.11.2.5.4.2.4.2.1.2
		ccSubnetAccessRuleSrcPtr OBJECT-TYPE
			SYNTAX SinglePointer
			MAX-ACCESS read-write
			STATUS current
			DESCRIPTION
				"This is the value of ccSubnetIndex corresponding
				to the source for this rule."
			::= { ccSubnetAccessRuleEntry 2 }

		
		-- 1.3.6.1.4.1.388.11.2.5.4.2.4.2.1.3
		ccSubnetAccessRuleDestPtr OBJECT-TYPE
			SYNTAX SinglePointer
			MAX-ACCESS read-write
			STATUS current
			DESCRIPTION
				"This is the value of ccSubnetAccessDestIndex 
				corresponding to the destination for this rule."
			::= { ccSubnetAccessRuleEntry 3 }

		
		-- 1.3.6.1.4.1.388.11.2.5.4.2.4.2.1.4
		ccSubnetAccessRuleName OBJECT-TYPE
			SYNTAX DisplayString
			MAX-ACCESS read-write
			STATUS current
			DESCRIPTION
				"Name of ACL entry."
			::= { ccSubnetAccessRuleEntry 4 }

		
		-- 1.3.6.1.4.1.388.11.2.5.4.2.4.2.1.5
		ccSubnetAccessRuleTransport OBJECT-TYPE
			SYNTAX INTEGER
				{
				all(1),
				tcp(2),
				udp(3),
				icmp(4),
				ah(5),
				esp(6),
				gre(7)
				}
			MAX-ACCESS read-write
			STATUS current
			DESCRIPTION
				"Transport."
			::= { ccSubnetAccessRuleEntry 5 }

		
		-- 1.3.6.1.4.1.388.11.2.5.4.2.4.2.1.6
		ccSubnetAccessRuleStartPort OBJECT-TYPE
			SYNTAX Integer32
			MAX-ACCESS read-write
			STATUS current
			DESCRIPTION
				"Starting port number."
			::= { ccSubnetAccessRuleEntry 6 }

		
		-- 1.3.6.1.4.1.388.11.2.5.4.2.4.2.1.7
		ccSubnetAccessRuleEndPort OBJECT-TYPE
			SYNTAX Integer32
			MAX-ACCESS read-write
			STATUS current
			DESCRIPTION
				"Ending port number."
			::= { ccSubnetAccessRuleEntry 7 }

		
		-- 1.3.6.1.4.1.388.11.2.5.4.2.4.2.1.8
		ccSubnetAccessRuleRowStatus OBJECT-TYPE
			SYNTAX AbbrevRowStatus
			MAX-ACCESS read-write
			STATUS current
			DESCRIPTION
				"Row status."
			::= { ccSubnetAccessRuleEntry 8 }

		
		-- 1.3.6.1.4.1.388.11.2.5.4.2.4.3
		ccSubnetAccessAdvInTable OBJECT-TYPE
			SYNTAX SEQUENCE OF CcSubnetAccessAdvInEntry
			MAX-ACCESS not-accessible
			STATUS current
			DESCRIPTION
				"Table of Advanced Inbound entries."
			::= { ccSubnetAccess 3 }

		
		-- 1.3.6.1.4.1.388.11.2.5.4.2.4.3.1
		ccSubnetAccessAdvInEntry OBJECT-TYPE
			SYNTAX CcSubnetAccessAdvInEntry
			MAX-ACCESS not-accessible
			STATUS current
			DESCRIPTION
				"Description."
			INDEX { ccSubnetAccessAdvInIndex }
			::= { ccSubnetAccessAdvInTable 1 }

		
		CcSubnetAccessAdvInEntry ::=
			SEQUENCE { 
				ccSubnetAccessAdvInIndex
					Unsigned32,
				ccSubnetAccessAdvInSrcIp
					IpAddress,
				ccSubnetAccessAdvInSrcIpLength
					Integer32,
				ccSubnetAccessAdvInDestIp
					IpAddress,
				ccSubnetAccessAdvInDestIpLength
					Integer32,
				ccSubnetAccessAdvInTransport
					INTEGER,
				ccSubnetAccessAdvInSrcPortStart
					Integer32,
				ccSubnetAccessAdvInSrcPortEnd
					Integer32,
				ccSubnetAccessAdvInDestPortStart
					Integer32,
				ccSubnetAccessAdvInDestPortEnd
					Integer32,
				ccSubnetAccessAdvInReverseNatIp
					IpAddress,
				ccSubnetAccessAdvInReverseNatPort
					Integer32,
				ccSubnetAccessAdvInAction
					INTEGER,
				ccSubnetAccessAdvInRowStatus
					AbbrevRowStatus
			 }

		-- 1.3.6.1.4.1.388.11.2.5.4.2.4.3.1.1
		ccSubnetAccessAdvInIndex OBJECT-TYPE
			SYNTAX Unsigned32 (1..1000)
			MAX-ACCESS accessible-for-notify
			STATUS current
			DESCRIPTION
				"Description."
			::= { ccSubnetAccessAdvInEntry 1 }

		
		-- 1.3.6.1.4.1.388.11.2.5.4.2.4.3.1.2
		ccSubnetAccessAdvInSrcIp OBJECT-TYPE
			SYNTAX IpAddress
			MAX-ACCESS read-write
			STATUS current
			DESCRIPTION
				"Source IP address"
			::= { ccSubnetAccessAdvInEntry 2 }

		
		-- 1.3.6.1.4.1.388.11.2.5.4.2.4.3.1.3
		ccSubnetAccessAdvInSrcIpLength OBJECT-TYPE
			SYNTAX Integer32 (0..32)
			MAX-ACCESS read-write
			STATUS current
			DESCRIPTION
				"Mask length for the IP address"
			::= { ccSubnetAccessAdvInEntry 3 }

		
		-- 1.3.6.1.4.1.388.11.2.5.4.2.4.3.1.4
		ccSubnetAccessAdvInDestIp OBJECT-TYPE
			SYNTAX IpAddress
			MAX-ACCESS read-write
			STATUS current
			DESCRIPTION
				"Destination IP address
				"
			::= { ccSubnetAccessAdvInEntry 4 }

		
		-- 1.3.6.1.4.1.388.11.2.5.4.2.4.3.1.5
		ccSubnetAccessAdvInDestIpLength OBJECT-TYPE
			SYNTAX Integer32 (0..32)
			MAX-ACCESS read-write
			STATUS current
			DESCRIPTION
				"mask length for the IP address"
			::= { ccSubnetAccessAdvInEntry 5 }

		
		-- 1.3.6.1.4.1.388.11.2.5.4.2.4.3.1.6
		ccSubnetAccessAdvInTransport OBJECT-TYPE
			SYNTAX INTEGER
				{
				all(1),
				tcp(2),
				udp(3),
				icmp(4),
				ah(5),
				esp(6),
				gre(7)
				}
			MAX-ACCESS read-write
			STATUS current
			DESCRIPTION
				"Type of transport"
			::= { ccSubnetAccessAdvInEntry 6 }

		
		-- 1.3.6.1.4.1.388.11.2.5.4.2.4.3.1.7
		ccSubnetAccessAdvInSrcPortStart OBJECT-TYPE
			SYNTAX Integer32
			MAX-ACCESS read-write
			STATUS current
			DESCRIPTION
				"start of source port list
				"
			::= { ccSubnetAccessAdvInEntry 7 }

		
		-- 1.3.6.1.4.1.388.11.2.5.4.2.4.3.1.8
		ccSubnetAccessAdvInSrcPortEnd OBJECT-TYPE
			SYNTAX Integer32
			MAX-ACCESS read-write
			STATUS current
			DESCRIPTION
				"End of source port list
				"
			::= { ccSubnetAccessAdvInEntry 8 }

		
		-- 1.3.6.1.4.1.388.11.2.5.4.2.4.3.1.9
		ccSubnetAccessAdvInDestPortStart OBJECT-TYPE
			SYNTAX Integer32
			MAX-ACCESS read-write
			STATUS current
			DESCRIPTION
				"start of destination port list
				"
			::= { ccSubnetAccessAdvInEntry 9 }

		
		-- 1.3.6.1.4.1.388.11.2.5.4.2.4.3.1.10
		ccSubnetAccessAdvInDestPortEnd OBJECT-TYPE
			SYNTAX Integer32
			MAX-ACCESS read-write
			STATUS current
			DESCRIPTION
				"End of destination port list
				"
			::= { ccSubnetAccessAdvInEntry 10 }

		
		-- 1.3.6.1.4.1.388.11.2.5.4.2.4.3.1.12
		ccSubnetAccessAdvInReverseNatIp OBJECT-TYPE
			SYNTAX IpAddress
			MAX-ACCESS read-write
			STATUS current
			DESCRIPTION
				"Address to use for reverse NAT.  To disable, use 0.0.0.0."
			::= { ccSubnetAccessAdvInEntry 12 }

		
		-- 1.3.6.1.4.1.388.11.2.5.4.2.4.3.1.13
		ccSubnetAccessAdvInReverseNatPort OBJECT-TYPE
			SYNTAX Integer32
			MAX-ACCESS read-write
			STATUS current
			DESCRIPTION
				"Port to use for reverse NAT."
			::= { ccSubnetAccessAdvInEntry 13 }

		
		-- 1.3.6.1.4.1.388.11.2.5.4.2.4.3.1.14
		ccSubnetAccessAdvInAction OBJECT-TYPE
			SYNTAX INTEGER
				{
				allow(1),
				deny(2)
				}
			MAX-ACCESS read-write
			STATUS current
			DESCRIPTION
				"Action on the acl i.e allow or deny
				"
			::= { ccSubnetAccessAdvInEntry 14 }

		
		-- 1.3.6.1.4.1.388.11.2.5.4.2.4.3.1.15
		ccSubnetAccessAdvInRowStatus OBJECT-TYPE
			SYNTAX AbbrevRowStatus
			MAX-ACCESS read-write
			STATUS current
			DESCRIPTION
				"status of the row
				"
			::= { ccSubnetAccessAdvInEntry 15 }

		
		-- 1.3.6.1.4.1.388.11.2.5.4.2.4.4
		ccSubnetAccessAdvOutTable OBJECT-TYPE
			SYNTAX SEQUENCE OF CcSubnetAccessAdvOutEntry
			MAX-ACCESS not-accessible
			STATUS current
			DESCRIPTION
				"Table of Advanced Outbound entries."
			::= { ccSubnetAccess 4 }

		
		-- 1.3.6.1.4.1.388.11.2.5.4.2.4.4.1
		ccSubnetAccessAdvOutEntry OBJECT-TYPE
			SYNTAX CcSubnetAccessAdvOutEntry
			MAX-ACCESS not-accessible
			STATUS current
			DESCRIPTION
				"Description."
			INDEX { ccSubnetAccessAdvOutIndex }
			::= { ccSubnetAccessAdvOutTable 1 }

		
		CcSubnetAccessAdvOutEntry ::=
			SEQUENCE { 
				ccSubnetAccessAdvOutIndex
					Unsigned32,
				ccSubnetAccessAdvOutSrcIp
					IpAddress,
				ccSubnetAccessAdvOutSrcIpLength
					Integer32,
				ccSubnetAccessAdvOutDestIp
					IpAddress,
				ccSubnetAccessAdvOutDestIpLength
					Integer32,
				ccSubnetAccessAdvOutTransport
					INTEGER,
				ccSubnetAccessAdvOutSrcPortStart
					Integer32,
				ccSubnetAccessAdvOutSrcPortEnd
					Integer32,
				ccSubnetAccessAdvOutDestPortStart
					Integer32,
				ccSubnetAccessAdvOutDestPortEnd
					Integer32,
				ccSubnetAccessAdvOutReverseNat
					SinglePointer,
				ccSubnetAccessAdvOutAction
					INTEGER,
				ccSubnetAccessAdvOutRowStatus
					AbbrevRowStatus
			 }

		-- 1.3.6.1.4.1.388.11.2.5.4.2.4.4.1.1
		ccSubnetAccessAdvOutIndex OBJECT-TYPE
			SYNTAX Unsigned32 (1..1000)
			MAX-ACCESS accessible-for-notify
			STATUS current
			DESCRIPTION
				"Description."
			::= { ccSubnetAccessAdvOutEntry 1 }

		
		-- 1.3.6.1.4.1.388.11.2.5.4.2.4.4.1.2
		ccSubnetAccessAdvOutSrcIp OBJECT-TYPE
			SYNTAX IpAddress
			MAX-ACCESS read-write
			STATUS current
			DESCRIPTION
				"Source IP address"
			::= { ccSubnetAccessAdvOutEntry 2 }

		
		-- 1.3.6.1.4.1.388.11.2.5.4.2.4.4.1.3
		ccSubnetAccessAdvOutSrcIpLength OBJECT-TYPE
			SYNTAX Integer32 (0..32)
			MAX-ACCESS read-write
			STATUS current
			DESCRIPTION
				"Mask length for the IP address"
			::= { ccSubnetAccessAdvOutEntry 3 }

		
		-- 1.3.6.1.4.1.388.11.2.5.4.2.4.4.1.4
		ccSubnetAccessAdvOutDestIp OBJECT-TYPE
			SYNTAX IpAddress
			MAX-ACCESS read-write
			STATUS current
			DESCRIPTION
				"Destination IP address"
			::= { ccSubnetAccessAdvOutEntry 4 }

		
		-- 1.3.6.1.4.1.388.11.2.5.4.2.4.4.1.5
		ccSubnetAccessAdvOutDestIpLength OBJECT-TYPE
			SYNTAX Integer32 (0..32)
			MAX-ACCESS read-write
			STATUS current
			DESCRIPTION
				"mask length for the IP address"
			::= { ccSubnetAccessAdvOutEntry 5 }

		
		-- 1.3.6.1.4.1.388.11.2.5.4.2.4.4.1.6
		ccSubnetAccessAdvOutTransport OBJECT-TYPE
			SYNTAX INTEGER
				{
				all(1),
				tcp(2),
				udp(3),
				icmp(4),
				ah(5),
				esp(6),
				gre(7)
				}
			MAX-ACCESS read-write
			STATUS current
			DESCRIPTION
				"Type of transport"
			::= { ccSubnetAccessAdvOutEntry 6 }

		
		-- 1.3.6.1.4.1.388.11.2.5.4.2.4.4.1.7
		ccSubnetAccessAdvOutSrcPortStart OBJECT-TYPE
			SYNTAX Integer32
			MAX-ACCESS read-write
			STATUS current
			DESCRIPTION
				"start of source port list"
			::= { ccSubnetAccessAdvOutEntry 7 }

		
		-- 1.3.6.1.4.1.388.11.2.5.4.2.4.4.1.8
		ccSubnetAccessAdvOutSrcPortEnd OBJECT-TYPE
			SYNTAX Integer32
			MAX-ACCESS read-write
			STATUS current
			DESCRIPTION
				"End of source port list"
			::= { ccSubnetAccessAdvOutEntry 8 }

		
		-- 1.3.6.1.4.1.388.11.2.5.4.2.4.4.1.9
		ccSubnetAccessAdvOutDestPortStart OBJECT-TYPE
			SYNTAX Integer32
			MAX-ACCESS read-write
			STATUS current
			DESCRIPTION
				"start of destination port list"
			::= { ccSubnetAccessAdvOutEntry 9 }

		
		-- 1.3.6.1.4.1.388.11.2.5.4.2.4.4.1.10
		ccSubnetAccessAdvOutDestPortEnd OBJECT-TYPE
			SYNTAX Integer32
			MAX-ACCESS read-write
			STATUS current
			DESCRIPTION
				"End of destination port list
				"
			::= { ccSubnetAccessAdvOutEntry 10 }

		
		-- 1.3.6.1.4.1.388.11.2.5.4.2.4.4.1.11
		ccSubnetAccessAdvOutReverseNat OBJECT-TYPE
			SYNTAX SinglePointer
			MAX-ACCESS read-write
			STATUS current
			DESCRIPTION
				"Points to a ccWanIpAddrTable entry representing the WAN IP
				addr to be used for NAT.  To disable NAT, set this value to
				0."
			::= { ccSubnetAccessAdvOutEntry 11 }

		
		-- 1.3.6.1.4.1.388.11.2.5.4.2.4.4.1.12
		ccSubnetAccessAdvOutAction OBJECT-TYPE
			SYNTAX INTEGER
				{
				allow(1),
				deny(2)
				}
			MAX-ACCESS read-write
			STATUS current
			DESCRIPTION
				"Action on the acl i.e allow or deny"
			::= { ccSubnetAccessAdvOutEntry 12 }

		
		-- 1.3.6.1.4.1.388.11.2.5.4.2.4.4.1.13
		ccSubnetAccessAdvOutRowStatus OBJECT-TYPE
			SYNTAX AbbrevRowStatus
			MAX-ACCESS read-write
			STATUS current
			DESCRIPTION
				"status of the row"
			::= { ccSubnetAccessAdvOutEntry 13 }

		
		-- 1.3.6.1.4.1.388.11.2.5.4.2.4.5
		ccSubnetAccessAdvOverrideMode OBJECT-TYPE
			SYNTAX TruthValue
			MAX-ACCESS read-write
			STATUS current
			DESCRIPTION
				"Override the Subnet Access and NAT settings."
			::= { ccSubnetAccess 5 }

		
		-- 1.3.6.1.4.1.388.11.2.5.4.2.4.6
		ccSubnetAccessAdvImportRules OBJECT-TYPE
			SYNTAX DoActionNow
			MAX-ACCESS read-write
			STATUS current
			DESCRIPTION
				"When set to 1 the Subnet Access Rules shall
				be imported on top of the Advanced Access rules."
			::= { ccSubnetAccess 6 }

		
		-- 1.3.6.1.4.1.388.11.2.5.4.3
		ccLanVlan OBJECT IDENTIFIER ::= { ccLan 3 }

		
		-- 1.3.6.1.4.1.388.11.2.5.4.3.1
		ccLanVlanType OBJECT-TYPE
			SYNTAX INTEGER
				{
				portBased(1),
				userBased(2)
				}
			MAX-ACCESS read-write
			STATUS current
			DESCRIPTION
				"Type of the VLAN port/user based
				"
			::= { ccLanVlan 1 }

		
		-- 1.3.6.1.4.1.388.11.2.5.4.3.2
		ccLanVlanTrunkPort OBJECT-TYPE
			SYNTAX Unsigned32
			MAX-ACCESS read-write
			STATUS current
			DESCRIPTION
				"Port used for VLAN trunking ( 1-6)
				"
			::= { ccLanVlan 2 }
-- ??-India: can be either the port #,
-- or the index in the PortTable - implementer's choice.
		
		-- 1.3.6.1.4.1.388.11.2.5.4.3.3
		ccLanVlanDefaultTag OBJECT-TYPE
			SYNTAX Unsigned32 (1..31)
			MAX-ACCESS read-write
			STATUS current
			DESCRIPTION
				"Deafult VLAN tag ( default is 1)
				"
			::= { ccLanVlan 3 }

		
		-- 1.3.6.1.4.1.388.11.2.5.4.3.4
		ccLanVlanTrunked OBJECT-TYPE
			SYNTAX BITS
				{
				noVlansAreTrunked(0),
				trunkVlan01(1),
				trunkVlan02(2),
				trunkVlan03(3),
				trunkVlan04(4),
				trunkVlan05(5),
				trunkVlan06(6),
				trunkVlan07(7),
				trunkVlan08(8),
				trunkVlan09(9),
				trunkVlan10(10),
				trunkVlan11(11),
				trunkVlan12(12),
				trunkVlan13(13),
				trunkVlan14(14),
				trunkVlan15(15),
				trunkVlan16(16),
				trunkVlan17(17),
				trunkVlan18(18),
				trunkVlan19(19),
				trunkVlan20(20),
				trunkVlan21(21),
				trunkVlan22(22),
				trunkVlan23(23),
				trunkVlan24(24),
				trunkVlan25(25),
				trunkVlan26(26),
				trunkVlan27(27),
				trunkVlan28(28),
				trunkVlan29(29),
				trunkVlan30(30),
				trunkVlan31(31)
				}
			MAX-ACCESS read-write
			STATUS current
			DESCRIPTION
				"List of VLANs which are trunked.
				"
			::= { ccLanVlan 4 }

		
		-- 1.3.6.1.4.1.388.11.2.5.4.3.5
		ccLanVlanTable OBJECT-TYPE
			SYNTAX SEQUENCE OF CcLanVlanEntry
			MAX-ACCESS not-accessible
			STATUS current
			DESCRIPTION
				"Table of VLAN IDs mapped to Subnets."
			::= { ccLanVlan 5 }

		
		-- 1.3.6.1.4.1.388.11.2.5.4.3.5.1
		ccLanVlanEntry OBJECT-TYPE
			SYNTAX CcLanVlanEntry
			MAX-ACCESS not-accessible
			STATUS current
			DESCRIPTION
				"Description."
			INDEX { ccSubnetIndex }
			::= { ccLanVlanTable 1 }

		
		CcLanVlanEntry ::=
			SEQUENCE { 
				ccLanVlanId
					Unsigned32
			 }

		-- 1.3.6.1.4.1.388.11.2.5.4.3.5.1.1
		ccLanVlanId OBJECT-TYPE
			SYNTAX Unsigned32 (1..31)
			MAX-ACCESS read-write
			STATUS current
			DESCRIPTION
				"Vlan associated with a subnet
				"
			::= { ccLanVlanEntry 1 }

		
-- Router config.
-- 
-- Note that static routes can be seen and added in the
-- MIB-II ip group tables.
		-- 1.3.6.1.4.1.388.11.2.6
		ccRouter OBJECT IDENTIFIER ::= { ws2k 6 }

		
-- RIP config.
		-- 1.3.6.1.4.1.388.11.2.6.1
		ccRouterRip OBJECT IDENTIFIER ::= { ccRouter 1 }

		
		-- 1.3.6.1.4.1.388.11.2.6.1.1
		ccRouterRipType OBJECT-TYPE
			SYNTAX INTEGER
				{
				noRip(1),
				ripV1(2),
				ripV2withV1compatibility(3),
				ripV2(4)
				}
			MAX-ACCESS read-write
			STATUS current
			DESCRIPTION
				"RIP type."
			::= { ccRouterRip 1 }
-- Version of the RIP enabled on the interface
-- 
		
		-- 1.3.6.1.4.1.388.11.2.6.1.2
		ccRouterRipDirection OBJECT-TYPE
			SYNTAX INTEGER
				{
				both(1),
				rxOnly(2),
				txOnly(3)
				}
			MAX-ACCESS read-write
			STATUS current
			DESCRIPTION
				"RIP direction."
			::= { ccRouterRip 2 }
-- Direction of RIP messages
-- 
		
-- RIP v2 config.
		-- 1.3.6.1.4.1.388.11.2.6.1.3
		ccRouterRip2 OBJECT IDENTIFIER ::= { ccRouterRip 3 }

		
		-- 1.3.6.1.4.1.388.11.2.6.1.3.1
		ccRouterRip2AuthType OBJECT-TYPE
			SYNTAX INTEGER
				{
				none(1),
				simple(2),
				md5(3)
				}
			MAX-ACCESS read-write
			STATUS current
			DESCRIPTION
				"RIP v2 authentication type."
			::= { ccRouterRip2 1 }
-- Type of authentication used by RIP
-- 
		
		-- 1.3.6.1.4.1.388.11.2.6.1.3.2
		ccRouterRip2SimplePassword OBJECT-TYPE
			SYNTAX Password
			MAX-ACCESS read-write
			STATUS current
			DESCRIPTION
				"Password used for RIP v2 simple authentication."
			::= { ccRouterRip2 2 }

		
		-- 1.3.6.1.4.1.388.11.2.6.1.3.3
		ccRouterRip2Md5Key1Id OBJECT-TYPE
			SYNTAX Integer32 (1..256)
			MAX-ACCESS read-write
			STATUS current
			DESCRIPTION
				"RIP v2 with MD5 authentication: key #1 - ID."
			::= { ccRouterRip2 3 }

		
		-- 1.3.6.1.4.1.388.11.2.6.1.3.4
		ccRouterRip2Md5Key1AuthKey OBJECT-TYPE
			SYNTAX Password (SIZE (0..16))
			MAX-ACCESS read-write
			STATUS current
			DESCRIPTION
				"RIP v2 with MD5 authentication: key #1 - auth key."
			::= { ccRouterRip2 4 }

		
		-- 1.3.6.1.4.1.388.11.2.6.1.3.5
		ccRouterRip2Md5Key2Id OBJECT-TYPE
			SYNTAX Integer32 (1..256)
			MAX-ACCESS read-write
			STATUS current
			DESCRIPTION
				"RIP v2 with MD5 authentication: key #2 - ID."
			::= { ccRouterRip2 5 }

		
		-- 1.3.6.1.4.1.388.11.2.6.1.3.6
		ccRouterRip2Md5Key2AuthKey OBJECT-TYPE
			SYNTAX Password (SIZE (0..16))
			MAX-ACCESS read-write
			STATUS current
			DESCRIPTION
				"RIP v2 with MD5 authentication: key #2 - auth key."
			::= { ccRouterRip2 6 }

		
		-- 1.3.6.1.4.1.388.11.2.6.2
		ccRouterRoutesTable OBJECT-TYPE
			SYNTAX SEQUENCE OF CcRouterRoutesEntry
			MAX-ACCESS not-accessible
			STATUS current
			DESCRIPTION
				"Description."
			::= { ccRouter 2 }

		
		-- 1.3.6.1.4.1.388.11.2.6.2.1
		ccRouterRoutesEntry OBJECT-TYPE
			SYNTAX CcRouterRoutesEntry
			MAX-ACCESS not-accessible
			STATUS current
			DESCRIPTION
				"Table of Routing entries."
			INDEX { ccRouterRoutesIndex }
			::= { ccRouterRoutesTable 1 }

		
		CcRouterRoutesEntry ::=
			SEQUENCE { 
				ccRouterRoutesIndex
					Unsigned32,
				ccRouterRoutesDest
					IpAddress,
				ccRouterRoutesDestMask
					IpAddress,
				ccRouterRoutesGateway
					IpAddress,
				ccRouterRoutesInterface
					SinglePointer,
				ccRouterRoutesMetric
					Integer32
			 }

		-- 1.3.6.1.4.1.388.11.2.6.2.1.1
		ccRouterRoutesIndex OBJECT-TYPE
			SYNTAX Unsigned32 (1..10000)
			MAX-ACCESS accessible-for-notify
			STATUS current
			DESCRIPTION
				"Simple Index."
			::= { ccRouterRoutesEntry 1 }
-- ??-India: range OK?
		
		-- 1.3.6.1.4.1.388.11.2.6.2.1.2
		ccRouterRoutesDest OBJECT-TYPE
			SYNTAX IpAddress
			MAX-ACCESS read-only
			STATUS current
			DESCRIPTION
				"IP address of the destination
				"
			::= { ccRouterRoutesEntry 2 }

		
		-- 1.3.6.1.4.1.388.11.2.6.2.1.3
		ccRouterRoutesDestMask OBJECT-TYPE
			SYNTAX IpAddress
			MAX-ACCESS read-only
			STATUS current
			DESCRIPTION
				"Mask used to specify the route
				"
			::= { ccRouterRoutesEntry 3 }

		
		-- 1.3.6.1.4.1.388.11.2.6.2.1.4
		ccRouterRoutesGateway OBJECT-TYPE
			SYNTAX IpAddress
			MAX-ACCESS read-only
			STATUS current
			DESCRIPTION
				"Ip address of the gateway for this route
				"
			::= { ccRouterRoutesEntry 4 }

		
		-- 1.3.6.1.4.1.388.11.2.6.2.1.5
		ccRouterRoutesInterface OBJECT-TYPE
			SYNTAX SinglePointer
			MAX-ACCESS read-only
			STATUS current
			DESCRIPTION
				"Interface used for this route
				"
			::= { ccRouterRoutesEntry 5 }
-- ??-CSM: why does label say interfaces?
-- does this need to be a multipointer?
-- 
		
		-- 1.3.6.1.4.1.388.11.2.6.2.1.6
		ccRouterRoutesMetric OBJECT-TYPE
			SYNTAX Integer32
			MAX-ACCESS read-only
			STATUS current
			DESCRIPTION
				"Metric specified for this route."
			::= { ccRouterRoutesEntry 6 }

		
		-- 1.3.6.1.4.1.388.11.2.6.3
		ccRouterUserRoutesTable OBJECT-TYPE
			SYNTAX SEQUENCE OF CcRouterUserRoutesEntry
			MAX-ACCESS not-accessible
			STATUS current
			DESCRIPTION
				"Table of User defined Routes."
			::= { ccRouter 3 }

		
		-- 1.3.6.1.4.1.388.11.2.6.3.1
		ccRouterUserRoutesEntry OBJECT-TYPE
			SYNTAX CcRouterUserRoutesEntry
			MAX-ACCESS not-accessible
			STATUS current
			DESCRIPTION
				"User defined routes
				"
			INDEX { ccRouterUserRoutesIndex }
			::= { ccRouterUserRoutesTable 1 }

		
		CcRouterUserRoutesEntry ::=
			SEQUENCE { 
				ccRouterUserRoutesIndex
					INTEGER,
				ccRouterUserRoutesDest
					IpAddress,
				ccRouterUserRoutesDestMask
					IpAddress,
				ccRouterUserRoutesGateway
					IpAddress,
				ccRouterUserRoutesInterface
					INTEGER,
				ccRouterUserRoutesMetric
					Integer32,
				ccRouterUserRoutesRowStatus
					AbbrevRowStatus
			 }

		-- 1.3.6.1.4.1.388.11.2.6.3.1.1
		ccRouterUserRoutesIndex OBJECT-TYPE
			SYNTAX INTEGER (1..20)
			MAX-ACCESS accessible-for-notify
			STATUS current
			DESCRIPTION
				"Simple Index."
			::= { ccRouterUserRoutesEntry 1 }
-- ??-India: range OK?
		
		-- 1.3.6.1.4.1.388.11.2.6.3.1.2
		ccRouterUserRoutesDest OBJECT-TYPE
			SYNTAX IpAddress
			MAX-ACCESS read-write
			STATUS current
			DESCRIPTION
				"IP address of the destination"
			::= { ccRouterUserRoutesEntry 2 }

		
		-- 1.3.6.1.4.1.388.11.2.6.3.1.3
		ccRouterUserRoutesDestMask OBJECT-TYPE
			SYNTAX IpAddress
			MAX-ACCESS read-write
			STATUS current
			DESCRIPTION
				"Mask used to specify the route"
			::= { ccRouterUserRoutesEntry 3 }

		
		-- 1.3.6.1.4.1.388.11.2.6.3.1.4
		ccRouterUserRoutesGateway OBJECT-TYPE
			SYNTAX IpAddress
			MAX-ACCESS read-write
			STATUS current
			DESCRIPTION
				"Ip address of the gateway for this route"
			::= { ccRouterUserRoutesEntry 4 }

		
		-- 1.3.6.1.4.1.388.11.2.6.3.1.5
		ccRouterUserRoutesInterface OBJECT-TYPE
			SYNTAX INTEGER
				{
				wan(1),
				subnet1(2),
				subnet2(3),
				subnet3(4),
				subnet4(5)
				}
			MAX-ACCESS read-write
			STATUS current
			DESCRIPTION
				"Interface used for this route"
			::= { ccRouterUserRoutesEntry 5 }
-- ??-CSM: why does label say interfaces?
-- does this need to be a multipointer?
-- 
		
		-- 1.3.6.1.4.1.388.11.2.6.3.1.6
		ccRouterUserRoutesMetric OBJECT-TYPE
			SYNTAX Integer32
			MAX-ACCESS read-write
			STATUS current
			DESCRIPTION
				"Metric specified for this route."
			::= { ccRouterUserRoutesEntry 6 }

		
		-- 1.3.6.1.4.1.388.11.2.6.3.1.7
		ccRouterUserRoutesRowStatus OBJECT-TYPE
			SYNTAX AbbrevRowStatus
			MAX-ACCESS read-write
			STATUS current
			DESCRIPTION
				"Status of this row.
				"
			::= { ccRouterUserRoutesEntry 7 }

		
-- All MIBs in this group are related to detection and 
-- location of 'Rogue' APs.
		-- 1.3.6.1.4.1.388.11.2.7
		ccRap OBJECT IDENTIFIER ::= { ws2k 7 }

		
-- This group specifies which Rogue detection algorithm(s)
-- will be employed, and provides necessary controls for
-- each 'sub-algorithm'.
		-- 1.3.6.1.4.1.388.11.2.7.1
		ccRapControl OBJECT IDENTIFIER ::= { ccRap 1 }

		
-- This group contains MIB variables for controlling
-- and reporting the APs heard by Symbol MUs that 
-- support the 'rogue AP detection assist' algorithm.
-- 
-- This is supported in Mobile Companion v?.? and later.
-- 
-- The following is a PARTIAL list of Symbol MUs that
-- support this feature:
-- ???
-- 
-- Note that Symbol MUs running Mobile Companion v?.?
-- only report the first 20 APs heard.  The order in
-- which APs appear in the MU's list is random.  This
-- means that if the total of all APs in the local
-- environment (including rogues) is more than 20, it
-- may take more than one poll cycle to find an MU that
-- has that rogue within the top 20 entries of it's
-- list of heard APs.
-- 
-- Symbol MUs running Mobile Companion v?.? and later
-- do not have this limitation, and report all heard
-- APs on every poll cycle.  A new/rogue AP heard in
-- with such an MU will be reported regardless of the
-- total number of APs in the local environment.
		-- 1.3.6.1.4.1.388.11.2.7.1.3
		ccRapControlPollSymbolMus OBJECT IDENTIFIER ::= { ccRapControl 3 }

		
		-- 1.3.6.1.4.1.388.11.2.7.1.3.1
		ccRapPollSymbolMusEnable OBJECT-TYPE
			SYNTAX TruthValue
			MAX-ACCESS read-write
			STATUS current
			DESCRIPTION
				"Enable/disable polling MUs for their lists of known
				APs.
				
				The state of this variable persists across reboots.
				The factory-default state is disabled."
			::= { ccRapControlPollSymbolMus 1 }

		
		-- 1.3.6.1.4.1.388.11.2.7.1.3.2
		ccRapPollSymbolMusInterval OBJECT-TYPE
			SYNTAX Integer32
			UNITS "minutes"
			MAX-ACCESS read-write
			STATUS current
			DESCRIPTION
				"Amount of time to wait before polling the same MU
				for its known AP list again.
				
				Assuming the MU is disrupted for 3sec when it is
				polled, a value of 5min or more would interrupt MUs
				less than 1% of the time.
				
				The state of this variable persists across reboots.
				The factory-default state is 10 (minutes)."
			::= { ccRapControlPollSymbolMus 2 }

		
-- Rogues can be learned via 'production' Portals if they 
-- happen to be on the same channel.  Such Portals listen for
-- beacons (at a given interval), and report APs heard.
-- 
-- This group controls the learning of new APs via this
-- method.
		-- 1.3.6.1.4.1.388.11.2.7.1.4
		ccRapControlOnChannel OBJECT IDENTIFIER ::= { ccRapControl 4 }

		
		-- 1.3.6.1.4.1.388.11.2.7.1.4.1
		ccRapOnChannelEnable OBJECT-TYPE
			SYNTAX TruthValue
			MAX-ACCESS read-write
			STATUS current
			DESCRIPTION
				"Enable/disable polling MUs for their lists of known
				APs.
				
				The state of this variable persists across reboots.
				The factory-default state is disabled."
			::= { ccRapControlOnChannel 1 }

		
		-- 1.3.6.1.4.1.388.11.2.7.1.4.2
		ccRapOnChannelInterval OBJECT-TYPE
			SYNTAX Integer32
			UNITS "minutes"
			MAX-ACCESS read-write
			STATUS current
			DESCRIPTION
				"Amount of time to wait before polling the same MU
				for its known AP list again.
				
				Assuming the MU is disrupted for 3sec when it is
				polled, a value of 5min or more would interrupt MUs
				less than 1% of the time.
				
				The state of this variable persists across reboots.
				The factory-default state is 10 (minutes)."
			::= { ccRapControlOnChannel 2 }

		
-- One or more Portals can be dedicated for the purpose of
-- detecting Rogues, called 'detectors'.  Such Portals do NOT
-- pass 'production' packets since they are busy scanning many
-- different channels.
-- 
-- This group controls the learning of new APs via this
-- method.
		-- 1.3.6.1.4.1.388.11.2.7.1.5
		ccRapControlDetectors OBJECT IDENTIFIER ::= { ccRapControl 5 }

		
		-- 1.3.6.1.4.1.388.11.2.7.1.5.1
		ccRapDetectorsEnable OBJECT-TYPE
			SYNTAX TruthValue
			MAX-ACCESS read-write
			STATUS current
			DESCRIPTION
				"Enable/disable the entire 'detector' sub-system.
				
				On the true-to-false transition, any portals 
				previously claimed as listeners will be released
				and reset.  Once reset, they will appear to the
				switch as if just newly installed, (and thus
				may or may not be adopted depending on settings
				in the switch).
				
				The state of this variable persists across reboots.
				The factory-default state is disabled."
			::= { ccRapControlDetectors 1 }

		
		-- 1.3.6.1.4.1.388.11.2.7.1.5.2
		ccRapDetectorsInterval OBJECT-TYPE
			SYNTAX Integer32
			UNITS "minutes"
			MAX-ACCESS read-write
			STATUS current
			DESCRIPTION
				"Amount of time to wait before polling the same MU
				for its known AP list again.
				
				Assuming the MU is disrupted for 3sec when it is
				polled, a value of 5min or more would interrupt MUs
				less than 1% of the time.
				
				The state of this variable persists across reboots.
				The factory-default state is 10 (minutes)."
			::= { ccRapControlDetectors 2 }

		
-- This group controls how newly detected APs are 
-- 'authorized', meaning they will be reported as
-- 'approved' rather than 'rogue'.
		-- 1.3.6.1.4.1.388.11.2.7.2
		ccRapAuth OBJECT IDENTIFIER ::= { ccRap 2 }

		
-- MIB values to configure the process of authorizing 
-- newly discovered APs via a specific list of authorized
-- APs, (specified by AP MAC and/or ESSID, wildcarding 
-- permitted).
		-- 1.3.6.1.4.1.388.11.2.7.2.2
		ccRapAuthList OBJECT IDENTIFIER ::= { ccRapAuth 2 }

		
		-- 1.3.6.1.4.1.388.11.2.7.2.2.1
		ccRapAuthAllSymbolMac OBJECT-TYPE
			SYNTAX TruthValue
			MAX-ACCESS read-write
			STATUS current
			DESCRIPTION
				"If TRUE, any newly-discovered AP that has a MAC address
				with a Symbol vendor prefix is authorized, regardless
				of the ESSID."
			::= { ccRapAuthList 1 }

		
		-- 1.3.6.1.4.1.388.11.2.7.2.2.2
		ccRapAuthTable OBJECT-TYPE
			SYNTAX SEQUENCE OF CcRapAuthEntry
			MAX-ACCESS not-accessible
			STATUS current
			DESCRIPTION
				"A list of 'authorized' APs.  There is no need to
				include on this list any APs adopted by the switch.
				Typically, this list will contain APs that are
				located in neighboring stores/buildings that are
				known by some means to NOT be rogue. So this is 
				the List of APs that are Authorized and upon heard
				shall automatically be added to the Approved List
				instead of labelling them as Rogue APs.
				
				Note that this table persists across reboots.
				
				"
			::= { ccRapAuthList 2 }

		
		-- 1.3.6.1.4.1.388.11.2.7.2.2.2.1
		ccRapAuthEntry OBJECT-TYPE
			SYNTAX CcRapAuthEntry
			MAX-ACCESS not-accessible
			STATUS current
			DESCRIPTION
				" "
			INDEX { ccRapAuthIndex }
			::= { ccRapAuthTable 1 }

		
		CcRapAuthEntry ::=
			SEQUENCE { 
				ccRapAuthIndex
					Unsigned32,
				ccRapAuthMacFilter
					PhysAddress,
				ccRapAuthEssidFilter
					DisplayString,
				ccRapAuthRowExists
					TruthValue
			 }

		-- 1.3.6.1.4.1.388.11.2.7.2.2.2.1.1
		ccRapAuthIndex OBJECT-TYPE
			SYNTAX Unsigned32 (1..24)
			MAX-ACCESS accessible-for-notify
			STATUS current
			DESCRIPTION
				"Index."
			::= { ccRapAuthEntry 1 }

		
		-- 1.3.6.1.4.1.388.11.2.7.2.2.2.1.2
		ccRapAuthMacFilter OBJECT-TYPE
			SYNTAX PhysAddress
			MAX-ACCESS read-write
			STATUS current
			DESCRIPTION
				"MAC address of AP to consider 'authorized'.
				
				To specify the entire MAC address as a wildcard, 
				(match any MAC address), use FF:FF:FF:FF:FF:FF.
				
				(While it had been considered, it is NOT possible to
				wildcard just the vendor portion of the MAC)."
			::= { ccRapAuthEntry 2 }

		
		-- 1.3.6.1.4.1.388.11.2.7.2.2.2.1.3
		ccRapAuthEssidFilter OBJECT-TYPE
			SYNTAX DisplayString
			MAX-ACCESS read-write
			STATUS current
			DESCRIPTION
				"ESSID of AP to consider 'authorized'.
				
				Set to 33 '*' characters for wildcard, (to match 
				any ESSID).  (ESSIDs must be 32ch or less)."
			::= { ccRapAuthEntry 3 }

		
		-- 1.3.6.1.4.1.388.11.2.7.2.2.2.1.4
		ccRapAuthRowExists OBJECT-TYPE
			SYNTAX TruthValue
			MAX-ACCESS read-write
			STATUS current
			DESCRIPTION
				"A kludge to avoid RowStatus and save development
				time.
				
				Set this value to true when creating the row.  Set
				this value to false to destroy the row.
				
				??- better name."
			::= { ccRapAuthEntry 4 }

		
		-- 1.3.6.1.4.1.388.11.2.7.2.2.3
		ccRapAuthErase OBJECT-TYPE
			SYNTAX DoActionNow
			MAX-ACCESS read-write
			STATUS current
			DESCRIPTION
				"Setting this value to TRUE erases all AuthTable entries."
			::= { ccRapAuthList 3 }

		
		-- 1.3.6.1.4.1.388.11.2.7.2.2.4
		ccRapAuthCopyAllApproved OBJECT-TYPE
			SYNTAX DoActionNow
			MAX-ACCESS read-write
			STATUS current
			DESCRIPTION
				"Causes all ccRapResultsApprovedTable entries to be
				immediately copied to the ccRapAuthTable."
			::= { ccRapAuthList 4 }

		
		-- 1.3.6.1.4.1.388.11.2.7.2.2.5
		ccRapAuthCopyAllRogue OBJECT-TYPE
			SYNTAX DoActionNow
			MAX-ACCESS read-write
			STATUS current
			DESCRIPTION
				"Causes all ccRapResultsRogueTable entries to be
				immediately copied to the ccRapAuthTable."
			::= { ccRapAuthList 5 }

		
-- This group of MIB values report two tables that 
-- collectively report all APs heard, (except those
-- Portals adopted by this switch).
		-- 1.3.6.1.4.1.388.11.2.7.3
		ccRapResults OBJECT IDENTIFIER ::= { ccRap 3 }

		
-- The APs represented in this group of MIB variables
-- are 'approved', meaning they have been authorized as
-- approved via one of the methods controlled in the
-- ccRapAuth group.
		-- 1.3.6.1.4.1.388.11.2.7.3.1
		ccRapResultsApproved OBJECT IDENTIFIER ::= { ccRapResults 1 }

		
		-- 1.3.6.1.4.1.388.11.2.7.3.1.1
		ccRapResultsApprovedAgeOut OBJECT-TYPE
			SYNTAX Integer32
			UNITS "minutes"
			MAX-ACCESS read-write
			STATUS current
			DESCRIPTION
				"If an entry in the _ResultsApproved table is not heard
				by any means for this number of minutes, is elligable 
				to be removed from the table by the switch;  (the
				switch, however, might not remove the entry until 
				it gets around to it).
				
				A value of 0 indicates that entries will never be
				'aged-out' of the table.
				
				The state of this variable persists across reboots.
				The factory-default state is 1 week, (10080 min)."
			::= { ccRapResultsApproved 1 }

		
		-- 1.3.6.1.4.1.388.11.2.7.3.1.2
		ccRapResultsApprovedTable OBJECT-TYPE
			SYNTAX SEQUENCE OF CcRapResultsApprovedEntry
			MAX-ACCESS not-accessible
			STATUS current
			DESCRIPTION
				"Each AP MAC/ESSID combination heard by any enabled
				detection method will be reported in this table, if it
				has been determined to be 'approved' via one of the
				enabled methods controlled in ccAuth.
				
				Entries persist until that MAC/ESSID combination has
				not been heard for _AgeOut minutes."
			::= { ccRapResultsApproved 2 }

		
		-- 1.3.6.1.4.1.388.11.2.7.3.1.2.1
		ccRapResultsApprovedEntry OBJECT-TYPE
			SYNTAX CcRapResultsApprovedEntry
			MAX-ACCESS not-accessible
			STATUS current
			DESCRIPTION
				" "
			INDEX { ccRapResultsApprovedIndex }
			::= { ccRapResultsApprovedTable 1 }

		
		CcRapResultsApprovedEntry ::=
			SEQUENCE { 
				ccRapResultsApprovedIndex
					Unsigned32,
				ccRapResultsApprovedApMac
					PhysAddress,
				ccRapResultsApprovedEssid
					DisplayString,
				ccRapResultsApprovedCopyToAuthTable
					DoActionNow,
				ccRapResultsApprovedFirstHeard
					TimeTicks,
				ccRapResultsApprovedLastHeard
					TimeTicks,
				ccRapResultsApprovedPortalPtr
					MultiPointer255,
				ccRapResultsApprovedHowFound
					INTEGER,
				ccRapResultsApprovedHowAuth
					INTEGER,
				ccRapResultsApprovedChannel
					Integer32
			 }

		-- 1.3.6.1.4.1.388.11.2.7.3.1.2.1.1
		ccRapResultsApprovedIndex OBJECT-TYPE
			SYNTAX Unsigned32 (1..50)
			MAX-ACCESS accessible-for-notify
			STATUS current
			DESCRIPTION
				"Simple Index."
			::= { ccRapResultsApprovedEntry 1 }

		
		-- 1.3.6.1.4.1.388.11.2.7.3.1.2.1.2
		ccRapResultsApprovedApMac OBJECT-TYPE
			SYNTAX PhysAddress
			MAX-ACCESS read-only
			STATUS current
			DESCRIPTION
				"MAC address of the heard AP."
			::= { ccRapResultsApprovedEntry 2 }

		
		-- 1.3.6.1.4.1.388.11.2.7.3.1.2.1.3
		ccRapResultsApprovedEssid OBJECT-TYPE
			SYNTAX DisplayString
			MAX-ACCESS read-only
			STATUS current
			DESCRIPTION
				"ESSID of the heard AP."
			::= { ccRapResultsApprovedEntry 3 }

		
		-- 1.3.6.1.4.1.388.11.2.7.3.1.2.1.4
		ccRapResultsApprovedCopyToAuthTable OBJECT-TYPE
			SYNTAX DoActionNow
			MAX-ACCESS read-write
			STATUS current
			DESCRIPTION
				"When set to TRUE, this entry is copied to the RuleTable."
			::= { ccRapResultsApprovedEntry 4 }

		
		-- 1.3.6.1.4.1.388.11.2.7.3.1.2.1.5
		ccRapResultsApprovedFirstHeard OBJECT-TYPE
			SYNTAX TimeTicks
			MAX-ACCESS read-only
			STATUS current
			DESCRIPTION
				"Snapshot of sysUpTime the first time this AP 
				MAC/ESSID combination was heard by any Symbol MU."
			::= { ccRapResultsApprovedEntry 5 }

		
		-- 1.3.6.1.4.1.388.11.2.7.3.1.2.1.6
		ccRapResultsApprovedLastHeard OBJECT-TYPE
			SYNTAX TimeTicks
			MAX-ACCESS read-only
			STATUS current
			DESCRIPTION
				"Snapshot of sysUpTime the most recent time this AP 
				MAC/ESSID combination was heard by any Symbol MU."
			::= { ccRapResultsApprovedEntry 6 }

		
		-- 1.3.6.1.4.1.388.11.2.7.3.1.2.1.7
		ccRapResultsApprovedPortalPtr OBJECT-TYPE
			SYNTAX MultiPointer255
			MAX-ACCESS read-only
			STATUS current
			DESCRIPTION
				"A mask of Portal table entries.  Those Portal
				entries indicated by a '1' in this mask were at one
				time the servicing Portal for an MU that reported 
				hearing this AP.
				
				For a rogue of limited range in the parking lot on 
				the north side of a store, it would be expected that
				only the Portals located in the north end of the 
				store would be indicated by this mask, thus giving
				a rough indication of general direction of the
				rogue."
			::= { ccRapResultsApprovedEntry 7 }

		
		-- 1.3.6.1.4.1.388.11.2.7.3.1.2.1.8
		ccRapResultsApprovedHowFound OBJECT-TYPE
			SYNTAX INTEGER
				{
				viaSymbolMuPolling(1),
				viaOnChannelDetection(2),
				viaDetector(3)
				}
			MAX-ACCESS read-only
			STATUS current
			DESCRIPTION
				"Describes the status of this AP.
				
				??- I don't think we would report adoptedAp on the 
				results table, so don't need this enum value."
			::= { ccRapResultsApprovedEntry 8 }

		
		-- 1.3.6.1.4.1.388.11.2.7.3.1.2.1.9
		ccRapResultsApprovedHowAuth OBJECT-TYPE
			SYNTAX INTEGER
				{
				onAuthList(1),
				viaRadius(2)
				}
			MAX-ACCESS read-only
			STATUS current
			DESCRIPTION
				"Describes how this AP was authorized, (or not).
				
				The order in which the various methods of authorizing APs
				is attempted is exactly the numerical order of the enums.
				
				??- I deleted adoptedAp, since it seems to me that there
				is no good reason to report APs that this switch has
				adopted."
			::= { ccRapResultsApprovedEntry 9 }

		
		-- 1.3.6.1.4.1.388.11.2.7.3.1.2.1.10
		ccRapResultsApprovedChannel OBJECT-TYPE
			SYNTAX Integer32
			MAX-ACCESS read-only
			STATUS current
			DESCRIPTION
				"Describes on which channel this AP was found."
			::= { ccRapResultsApprovedEntry 10 }

		
		-- 1.3.6.1.4.1.388.11.2.7.3.1.3
		ccRapResultsApprovedErase OBJECT-TYPE
			SYNTAX DoActionNow
			MAX-ACCESS read-write
			STATUS current
			DESCRIPTION
				"Setting this value to TRUE erases all Results entries.
				
				Any APs heard after that event will be treated as newly
				heard;  (which means they will also generate notifications,
				if enabled).
				
				??- need 2nd scalar."
			::= { ccRapResultsApproved 3 }

		
		-- 1.3.6.1.4.1.388.11.2.7.3.1.4
		ccRapNewApprovedAp NOTIFICATION-TYPE
			OBJECTS { ccRapResultsApprovedPortalPtr, ccRapResultsApprovedHowFound, ccRapResultsApprovedHowAuth }
			STATUS current
			DESCRIPTION 
				"A new AP has been heard that was in some manner
				authorized."
			::= { ccRapResultsApproved 4 }

		
-- The APs represented in this group of MIB variables
-- are 'rogue', meaning they failed to be authorized as
-- approved via one of the methods controlled in the
-- ccRapAuth group.
		-- 1.3.6.1.4.1.388.11.2.7.3.2
		ccRapResultsRogue OBJECT IDENTIFIER ::= { ccRapResults 2 }

		
		-- 1.3.6.1.4.1.388.11.2.7.3.2.1
		ccRapResultsRogueAgeOut OBJECT-TYPE
			SYNTAX Integer32
			UNITS "minutes"
			MAX-ACCESS read-write
			STATUS current
			DESCRIPTION
				"If an entry in the _ResultsRogue table is not heard
				by any means for this number of minutes, is elligable 
				to be removed from the table by the switch;  (the
				switch, however, might not remove the entry until 
				it gets around to it).
				
				A value of 0 indicates that entries will never be
				'aged-out' of the table.
				
				The state of this variable persists across reboots.
				The factory-default state is 1 week, (10080 min)."
			::= { ccRapResultsRogue 1 }

		
		-- 1.3.6.1.4.1.388.11.2.7.3.2.2
		ccRapResultsRogueTable OBJECT-TYPE
			SYNTAX SEQUENCE OF CcRapResultsRogueEntry
			MAX-ACCESS not-accessible
			STATUS current
			DESCRIPTION
				"Each AP MAC/ESSID combination heard by any enabled
				detection method will be reported in this table, if it
				has NOT been determined to be 'approved' via one of 
				the enabled methods controlled in ccAuth.
				
				Entries persist until that MAC/ESSID combination has
				not been heard for _AgeOut minutes."
			::= { ccRapResultsRogue 2 }

		
		-- 1.3.6.1.4.1.388.11.2.7.3.2.2.1
		ccRapResultsRogueEntry OBJECT-TYPE
			SYNTAX CcRapResultsRogueEntry
			MAX-ACCESS not-accessible
			STATUS current
			DESCRIPTION
				" "
			INDEX { ccRapResultsRogueIndex }
			::= { ccRapResultsRogueTable 1 }

		
		CcRapResultsRogueEntry ::=
			SEQUENCE { 
				ccRapResultsRogueIndex
					Unsigned32,
				ccRapResultsRogueApMac
					PhysAddress,
				ccRapResultsRogueEssid
					DisplayString,
				ccRapResultsRogueCopyToAuthTable
					DoActionNow,
				ccRapResultsRogueFirstHeard
					TimeTicks,
				ccRapResultsRogueLastHeard
					TimeTicks,
				ccRapResultsRoguePortalPtr
					MultiPointer255,
				ccRapResultsRogueHowFound
					INTEGER,
				ccRapResultsRogueClosestPortalPtr
					SinglePointer,
				ccRapResultsRogueClosestPortalRssi
					Integer32,
				ccRapResultsRogueChannel
					Integer32
			 }

		-- 1.3.6.1.4.1.388.11.2.7.3.2.2.1.1
		ccRapResultsRogueIndex OBJECT-TYPE
			SYNTAX Unsigned32 (1..50)
			MAX-ACCESS accessible-for-notify
			STATUS current
			DESCRIPTION
				"Simple Index."
			::= { ccRapResultsRogueEntry 1 }

		
		-- 1.3.6.1.4.1.388.11.2.7.3.2.2.1.2
		ccRapResultsRogueApMac OBJECT-TYPE
			SYNTAX PhysAddress
			MAX-ACCESS read-only
			STATUS current
			DESCRIPTION
				"MAC address of the heard AP."
			::= { ccRapResultsRogueEntry 2 }

		
		-- 1.3.6.1.4.1.388.11.2.7.3.2.2.1.3
		ccRapResultsRogueEssid OBJECT-TYPE
			SYNTAX DisplayString
			MAX-ACCESS read-only
			STATUS current
			DESCRIPTION
				"ESSID of the heard AP."
			::= { ccRapResultsRogueEntry 3 }

		
		-- 1.3.6.1.4.1.388.11.2.7.3.2.2.1.4
		ccRapResultsRogueCopyToAuthTable OBJECT-TYPE
			SYNTAX DoActionNow
			MAX-ACCESS read-write
			STATUS current
			DESCRIPTION
				"When set to TRUE, this entry is copied to the RuleTable."
			::= { ccRapResultsRogueEntry 4 }

		
		-- 1.3.6.1.4.1.388.11.2.7.3.2.2.1.5
		ccRapResultsRogueFirstHeard OBJECT-TYPE
			SYNTAX TimeTicks
			MAX-ACCESS read-only
			STATUS current
			DESCRIPTION
				"Snapshot of sysUpTime the first time this AP 
				MAC/ESSID combination was heard by any Symbol MU."
			::= { ccRapResultsRogueEntry 5 }

		
		-- 1.3.6.1.4.1.388.11.2.7.3.2.2.1.6
		ccRapResultsRogueLastHeard OBJECT-TYPE
			SYNTAX TimeTicks
			MAX-ACCESS read-only
			STATUS current
			DESCRIPTION
				"Snapshot of sysUpTime the most recent time this AP 
				MAC/ESSID combination was heard by any Symbol MU."
			::= { ccRapResultsRogueEntry 6 }

		
		-- 1.3.6.1.4.1.388.11.2.7.3.2.2.1.7
		ccRapResultsRoguePortalPtr OBJECT-TYPE
			SYNTAX MultiPointer255
			MAX-ACCESS read-only
			STATUS current
			DESCRIPTION
				"A mask of Portal table entries.  Those Portal
				entries indicated by a '1' in this mask were at one
				time the servicing Portal for an MU that reported 
				hearing this AP.
				
				For a rogue of limited range in the parking lot on 
				the north side of a store, it would be expected that
				only the Portals located in the north end of the 
				store would be indicated by this mask, thus giving
				a rough indication of general direction of the
				rogue."
			::= { ccRapResultsRogueEntry 7 }

		
		-- 1.3.6.1.4.1.388.11.2.7.3.2.2.1.8
		ccRapResultsRogueHowFound OBJECT-TYPE
			SYNTAX INTEGER
				{
				viaSymbolMuPolling(1),
				viaOnChannelDetection(2),
				viaDetector(3)
				}
			MAX-ACCESS read-only
			STATUS current
			DESCRIPTION
				"Describes the status of this AP.
				
				??- I don't think we would report adoptedAp on the 
				results table, so don't need this enum value."
			::= { ccRapResultsRogueEntry 8 }

		
		-- 1.3.6.1.4.1.388.11.2.7.3.2.2.1.9
		ccRapResultsRogueClosestPortalPtr OBJECT-TYPE
			SYNTAX SinglePointer
			MAX-ACCESS read-only
			STATUS current
			DESCRIPTION
				"A pointer to closest reporting Portal to the Rogue AP,
				(where 'closest' is defined as greatest RSSI value
				among all Portals reporting this AP)."
			::= { ccRapResultsRogueEntry 9 }

		
		-- 1.3.6.1.4.1.388.11.2.7.3.2.2.1.10
		ccRapResultsRogueClosestPortalRssi OBJECT-TYPE
			SYNTAX Integer32
			MAX-ACCESS read-only
			STATUS current
			DESCRIPTION
				"RSSI reported by the closest Portal."
			::= { ccRapResultsRogueEntry 10 }

		
		-- 1.3.6.1.4.1.388.11.2.7.3.2.2.1.11
		ccRapResultsRogueChannel OBJECT-TYPE
			SYNTAX Integer32
			MAX-ACCESS read-only
			STATUS current
			DESCRIPTION
				"Describes on which channel this AP was found."
			::= { ccRapResultsRogueEntry 11 }

		
		-- 1.3.6.1.4.1.388.11.2.7.3.2.3
		ccRapResultsRogueErase OBJECT-TYPE
			SYNTAX DoActionNow
			MAX-ACCESS read-write
			STATUS current
			DESCRIPTION
				"Setting this value to TRUE erases all Results entries.
				
				Any APs heard after that event will be treated as newly
				heard;  (which means they will also generate notifications,
				if enabled).
				
				??- need 2nd scalar."
			::= { ccRapResultsRogue 3 }

		
		-- 1.3.6.1.4.1.388.11.2.7.3.2.4
		ccRapNewRogueAp NOTIFICATION-TYPE
			OBJECTS { ccRapResultsRoguePortalPtr, ccRapResultsRogueHowFound }
			STATUS current
			DESCRIPTION 
				"A new AP has been heard that was NOT authorized."
			::= { ccRapResultsRogue 4 }

		
-- The MIBs in this group aid in locating a Rogue AP.
-- 
-- While the Rogue detection algorithms run at prescribed
-- intervals, all methods in this group are 'one-shot' tests.
-- That is, MIB values are written, and the switch immediately
-- performs the specified operation and reports results.  The
-- results are not impacted in any way by the on-going scans
-- configured above, (if any).
		-- 1.3.6.1.4.1.388.11.2.7.4
		ccRapLocate OBJECT IDENTIFIER ::= { ccRap 4 }

		
-- This group allows the user to initiate an immediate scan
-- of all configured Portals for a specified Rogue AP.
		-- 1.3.6.1.4.1.388.11.2.7.4.1
		ccRapPortalResults OBJECT IDENTIFIER ::= { ccRapLocate 1 }

		
		-- 1.3.6.1.4.1.388.11.2.7.4.1.1
		ccRapPortalResultsApMac OBJECT-TYPE
			SYNTAX PhysAddress
			MAX-ACCESS read-write
			STATUS current
			DESCRIPTION
				"The MAC address of the AP to be reported.
				
				(No wildcarding of the AP MAC is allowed.  If it 
				were, several APs could be found that match the
				selection criteria)."
			::= { ccRapPortalResults 1 }

		
		-- 1.3.6.1.4.1.388.11.2.7.4.1.2
		ccRapPortalResultsApEssid OBJECT-TYPE
			SYNTAX DisplayString
			MAX-ACCESS read-write
			STATUS current
			DESCRIPTION
				"The ESSID of the AP to be reported.
				
				(No wildcarding of the AP ESSID is allowed.  If it 
				were, several APs could be found that match the
				selection criteria)."
			::= { ccRapPortalResults 2 }

		
		-- 1.3.6.1.4.1.388.11.2.7.4.1.3
		ccRapPortalResultsInProcess OBJECT-TYPE
			SYNTAX DoActionShowProgress
			MAX-ACCESS read-write
			STATUS current
			DESCRIPTION
				"Setting to true erases the _PortalResultsTable, and 
				immediately initiates a scan of all Portals currently
				enabled in ccRapControlOnChannel and ccRapControlDetectors.
				
				The switch does NOT wait until the next scan interval(s),
				but performs the scan immediately;  (a human is most likely
				waiting for the results in mere seconds).
				
				Once the switch has completed scanning all enabled Portals,
				it sets this value to false."
			::= { ccRapPortalResults 3 }

		
		-- 1.3.6.1.4.1.388.11.2.7.4.1.4
		ccRapPortalResultsTable OBJECT-TYPE
			SYNTAX SEQUENCE OF CcRapPortalResultsEntry
			MAX-ACCESS not-accessible
			STATUS current
			DESCRIPTION
				"Each (enabled/configured) Portal that hears the specified
				AP's MAC/ESSID combination will be reported as one entry
				in this table.
				
				For a rogue of limited range in the parking lot on 
				the north side of a store, it would be expected that
				only the Portals located in the north end of the 
				store would be indicated by this mask, thus giving
				a rough indication of general direction of the
				rogue.
				
				Individual RSSI values combined with exact locations of the
				Portals can be used to triangulate the approximate position
				of the Rogue."
			::= { ccRapPortalResults 4 }

		
		-- 1.3.6.1.4.1.388.11.2.7.4.1.4.1
		ccRapPortalResultsEntry OBJECT-TYPE
			SYNTAX CcRapPortalResultsEntry
			MAX-ACCESS not-accessible
			STATUS current
			DESCRIPTION
				" "
			INDEX { ccRapPortalResultsIndex }
			::= { ccRapPortalResultsTable 1 }

		
		CcRapPortalResultsEntry ::=
			SEQUENCE { 
				ccRapPortalResultsIndex
					Unsigned32,
				ccRapPortalResultsPortalMac
					PhysAddress,
				ccRapPortalResultsRssi
					Integer32
			 }

		-- 1.3.6.1.4.1.388.11.2.7.4.1.4.1.1
		ccRapPortalResultsIndex OBJECT-TYPE
			SYNTAX Unsigned32 (1..1000000000)
			MAX-ACCESS accessible-for-notify
			STATUS current
			DESCRIPTION
				"Simple Index."
			::= { ccRapPortalResultsEntry 1 }

		
		-- 1.3.6.1.4.1.388.11.2.7.4.1.4.1.2
		ccRapPortalResultsPortalMac OBJECT-TYPE
			SYNTAX PhysAddress
			MAX-ACCESS read-only
			STATUS current
			DESCRIPTION
				"MAC address of the Portal reporting having heard the
				specified AP."
			::= { ccRapPortalResultsEntry 2 }

		
		-- 1.3.6.1.4.1.388.11.2.7.4.1.4.1.3
		ccRapPortalResultsRssi OBJECT-TYPE
			SYNTAX Integer32
			MAX-ACCESS read-only
			STATUS current
			DESCRIPTION
				"RSSI value heard by the Portal."
			::= { ccRapPortalResultsEntry 3 }

		
-- This group contains the MIB variables used to
-- initiate an immediate poll of a single Symbol MU, in order
-- to use that MU as a roving agent to find the Rogue.
		-- 1.3.6.1.4.1.388.11.2.7.4.2
		ccRapPollOneMu OBJECT IDENTIFIER ::= { ccRapLocate 2 }

		
		-- 1.3.6.1.4.1.388.11.2.7.4.2.1
		ccRapPollOneMuMac OBJECT-TYPE
			SYNTAX PhysAddress
			MAX-ACCESS read-write
			STATUS current
			DESCRIPTION
				"Writing this value with the MAC address of a MU 
				causes the switch to read that MU's known AP list.
				
				This read is performed just once, (it is not repeated).
				
				This read occurs regardless of the state of 
				ccRapPollSymbolMusEnable.  The read is also performed
				immediately - the switch does NOT wait until the next 
				Sybmol MU poll interval, (as specified in 
				ccRapPollSymbolMusInterval)."
			::= { ccRapPollOneMu 1 }

		
		-- 1.3.6.1.4.1.388.11.2.7.4.2.2
		ccRapPollOneMuInProcess OBJECT-TYPE
			SYNTAX DoActionShowProgress
			MAX-ACCESS read-write
			STATUS current
			DESCRIPTION
				"Setting to true initiates the polling of one 
				specified MU's known AP table.
				
				Once the switch receives a response from the 
				requested MU, it sets this value to false.
				
				If the network management software sets this value
				to false, any future response from the MU will be
				ignored."
			::= { ccRapPollOneMu 2 }

		
		-- 1.3.6.1.4.1.388.11.2.7.4.2.3
		ccRapPollOneMuStatus OBJECT-TYPE
			SYNTAX INTEGER
				{
				notSymbolRogueEnabled(1),
				symbolRogueEnabled(2),
				notAssociated(3)
				}
			MAX-ACCESS read-only
			STATUS current
			DESCRIPTION
				"Describes if the MU is associated or not, and if so,
				if the MU is Symbol Rogue detect enabled or not."
			::= { ccRapPollOneMu 3 }

		
		-- 1.3.6.1.4.1.388.11.2.7.4.2.4
		ccRapPollOneMuResultsTable OBJECT-TYPE
			SYNTAX SEQUENCE OF CcRapPollOneMuResultsEntry
			MAX-ACCESS not-accessible
			STATUS current
			DESCRIPTION
				"Shows the known AP table as read from the specified MU.
				
				This table is NOT cumulative;  that is, it only
				reflects exactly what was read from the most recent
				read of the specified MU's known AP table.
				
				If a non-Symbol MUs is specified, or if the MU is not
				currently associated with any Portal, the resulting table 
				will be empty."
			::= { ccRapPollOneMu 4 }

		
		-- 1.3.6.1.4.1.388.11.2.7.4.2.4.1
		ccRapPollOneMuResultsEntry OBJECT-TYPE
			SYNTAX CcRapPollOneMuResultsEntry
			MAX-ACCESS not-accessible
			STATUS current
			DESCRIPTION
				" "
			INDEX { ccRapPollOneMuResultsIndex }
			::= { ccRapPollOneMuResultsTable 1 }

		
		CcRapPollOneMuResultsEntry ::=
			SEQUENCE { 
				ccRapPollOneMuResultsIndex
					Unsigned32,
				ccRapPollOneMuResultsRssi
					Integer32,
				ccRapPollOneMuResultsEssid
					DisplayString,
				ccRapPollOneMuResultsApMac
					PhysAddress
			 }

		-- 1.3.6.1.4.1.388.11.2.7.4.2.4.1.1
		ccRapPollOneMuResultsIndex OBJECT-TYPE
			SYNTAX Unsigned32 (1..1000000000)
			MAX-ACCESS accessible-for-notify
			STATUS current
			DESCRIPTION
				"Simple index into the table."
			::= { ccRapPollOneMuResultsEntry 1 }

		
		-- 1.3.6.1.4.1.388.11.2.7.4.2.4.1.2
		ccRapPollOneMuResultsRssi OBJECT-TYPE
			SYNTAX Integer32
			MAX-ACCESS read-only
			STATUS current
			DESCRIPTION
				"RSSI reported for that known AP."
			::= { ccRapPollOneMuResultsEntry 2 }

		
		-- 1.3.6.1.4.1.388.11.2.7.4.2.4.1.3
		ccRapPollOneMuResultsEssid OBJECT-TYPE
			SYNTAX DisplayString
			MAX-ACCESS read-only
			STATUS current
			DESCRIPTION
				"ESSID of the heard AP."
			::= { ccRapPollOneMuResultsEntry 3 }

		
		-- 1.3.6.1.4.1.388.11.2.7.4.2.4.1.4
		ccRapPollOneMuResultsApMac OBJECT-TYPE
			SYNTAX PhysAddress
			MAX-ACCESS read-only
			STATUS current
			DESCRIPTION
				"MAC address of the heard AP."
			::= { ccRapPollOneMuResultsEntry 4 }

		
		-- 1.3.6.1.4.1.388.11.2.8
		ccRadiusServer OBJECT IDENTIFIER ::= { ws2k 8 }

		
		-- 1.3.6.1.4.1.388.11.2.8.1
		ccRadius OBJECT IDENTIFIER ::= { ccRadiusServer 1 }
-- ??-CSM: what happens when hit 'server certificate' 
-- and 'CA certificate' buttons?  Add MIBs for these.
-- 
		
		-- 1.3.6.1.4.1.388.11.2.8.1.1
		ccRadiusDataSource OBJECT-TYPE
			SYNTAX INTEGER
				{
				local(1),
				ldap(2)
				}
			MAX-ACCESS read-write
			STATUS current
			DESCRIPTION
				"Source of data for authentication. It can be local database
				on the switch or LDAP database i.e ADS or openLDAP"
			::= { ccRadius 1 }
-- 
-- 
		
		-- 1.3.6.1.4.1.388.11.2.8.1.2
		ccRadiusDefaultEapType OBJECT-TYPE
			SYNTAX INTEGER
				{
				ttls(1),
				peap(2)
				}
			MAX-ACCESS read-write
			STATUS current
			DESCRIPTION
				"Deafult EAP type advertised by the radius server.
				
				"
			::= { ccRadius 2 }
-- EAP type enabled on the switch
-- 
		
-- Type of EAP type within PEAP
-- 
		-- 1.3.6.1.4.1.388.11.2.8.1.4
		ccRadiusAuthTypePeap OBJECT-TYPE
			SYNTAX INTEGER
				{
				gtc(1),
				msChap2(2)
				}
			MAX-ACCESS read-write
			STATUS current
			DESCRIPTION
				"Type of EAP type within PEAP
				"
			::= { ccRadius 4 }

		
-- Type of EAP type within TTLS
		-- 1.3.6.1.4.1.388.11.2.8.1.5
		ccRadiusAuthTypeTtls OBJECT-TYPE
			SYNTAX INTEGER
				{
				md5(1),
				pap(2),
				msChap2(3)
				}
			MAX-ACCESS read-write
			STATUS current
			DESCRIPTION
				"Type of EAP type within TTLS"
			::= { ccRadius 5 }

		
-- Id of the ceritificate used by RADIUS
-- 
		-- 1.3.6.1.4.1.388.11.2.8.1.6
		ccRadiusServerCertificate OBJECT-TYPE
			SYNTAX DisplayString (SIZE (0..10))
			MAX-ACCESS read-write
			STATUS current
			DESCRIPTION
				"Id of the ceritificate used by RADIUS
				"
			::= { ccRadius 6 }

		
-- ID of the CA certificate used by RADIUS
-- 
		-- 1.3.6.1.4.1.388.11.2.8.1.7
		ccRadiusCACertificate OBJECT-TYPE
			SYNTAX DisplayString (SIZE (0..10))
			MAX-ACCESS read-write
			STATUS current
			DESCRIPTION
				"ID of the CA certificate used by RADIUS"
			::= { ccRadius 7 }

		
-- List of client which are authorised by the radius server
-- 
		-- 1.3.6.1.4.1.388.11.2.8.1.8
		ccRadiusClientAuthTable OBJECT-TYPE
			SYNTAX SEQUENCE OF CcRadiusClientAuthEntry
			MAX-ACCESS not-accessible
			STATUS current
			DESCRIPTION
				"Table of Radius Client Entries."
			::= { ccRadius 8 }

		
		-- 1.3.6.1.4.1.388.11.2.8.1.8.1
		ccRadiusClientAuthEntry OBJECT-TYPE
			SYNTAX CcRadiusClientAuthEntry
			MAX-ACCESS not-accessible
			STATUS current
			DESCRIPTION
				"Description."
			INDEX { ccRadiusClientAuthIndex }
			::= { ccRadiusClientAuthTable 1 }

		
		CcRadiusClientAuthEntry ::=
			SEQUENCE { 
				ccRadiusClientAuthIndex
					Unsigned32,
				ccRadiusClientAuthIpAddr
					IpAddress,
				ccRadiusClientAuthMask
					IpAddress,
				ccRadiusClientAuthSharedSecret
					Password,
				ccRadiusClientAuthRowStatus
					AbbrevRowStatus
			 }

		-- 1.3.6.1.4.1.388.11.2.8.1.8.1.1
		ccRadiusClientAuthIndex OBJECT-TYPE
			SYNTAX Unsigned32 (1..100)
			MAX-ACCESS accessible-for-notify
			STATUS current
			DESCRIPTION
				"Simple Index."
			::= { ccRadiusClientAuthEntry 1 }

		
-- IP address
		-- 1.3.6.1.4.1.388.11.2.8.1.8.1.2
		ccRadiusClientAuthIpAddr OBJECT-TYPE
			SYNTAX IpAddress
			MAX-ACCESS read-write
			STATUS current
			DESCRIPTION
				"IP address of the client
				"
			::= { ccRadiusClientAuthEntry 2 }

		
		-- 1.3.6.1.4.1.388.11.2.8.1.8.1.3
		ccRadiusClientAuthMask OBJECT-TYPE
			SYNTAX IpAddress
			MAX-ACCESS read-write
			STATUS current
			DESCRIPTION
				"Mask of the client's IP address
				"
			::= { ccRadiusClientAuthEntry 3 }

		
		-- 1.3.6.1.4.1.388.11.2.8.1.8.1.4
		ccRadiusClientAuthSharedSecret OBJECT-TYPE
			SYNTAX Password
			MAX-ACCESS read-write
			STATUS current
			DESCRIPTION
				"Shared secret between the client and the radius server
				"
			::= { ccRadiusClientAuthEntry 4 }

		
		-- 1.3.6.1.4.1.388.11.2.8.1.8.1.5
		ccRadiusClientAuthRowStatus OBJECT-TYPE
			SYNTAX AbbrevRowStatus
			MAX-ACCESS read-write
			STATUS current
			DESCRIPTION
				"Row Status.
				"
			::= { ccRadiusClientAuthEntry 5 }

		
		-- 1.3.6.1.4.1.388.11.2.8.2
		ccRadiusProxy OBJECT IDENTIFIER ::= { ccRadiusServer 2 }

		
		-- 1.3.6.1.4.1.388.11.2.8.2.1
		ccRadiusProxyRetryCount OBJECT-TYPE
			SYNTAX INTEGER (3..6)
			MAX-ACCESS read-write
			STATUS current
			DESCRIPTION
				"Number of retries for sending messages to a proxy
				"
			::= { ccRadiusProxy 1 }

		
		-- 1.3.6.1.4.1.388.11.2.8.2.2
		ccRadiusProxyTimeout OBJECT-TYPE
			SYNTAX INTEGER (5..10)
			UNITS "seconds"
			MAX-ACCESS read-write
			STATUS current
			DESCRIPTION
				"TImeout in seconds before retrying to a proxy
				"
			::= { ccRadiusProxy 2 }

		
		-- 1.3.6.1.4.1.388.11.2.8.2.3
		ccRadiusProxyServerTable OBJECT-TYPE
			SYNTAX SEQUENCE OF CcRadiusProxyServerEntry
			MAX-ACCESS not-accessible
			STATUS current
			DESCRIPTION
				"Table of Proxy Realm Entries."
			::= { ccRadiusProxy 3 }
-- ??-CSM: limited number of entries?  if not, change to AbbrevRowStatus.
-- 
		
		-- 1.3.6.1.4.1.388.11.2.8.2.3.1
		ccRadiusProxyServerEntry OBJECT-TYPE
			SYNTAX CcRadiusProxyServerEntry
			MAX-ACCESS not-accessible
			STATUS current
			DESCRIPTION
				"Description."
			INDEX { ccRadiusProxyServerIndex }
			::= { ccRadiusProxyServerTable 1 }

		
		CcRadiusProxyServerEntry ::=
			SEQUENCE { 
				ccRadiusProxyServerIndex
					Unsigned32,
				ccRadiusProxyServerPrefixOrSuffix
					DisplayString,
				ccRadiusProxyServerIp
					IpAddress,
				ccRadiusProxyServerPort
					Integer32,
				ccRadiusProxyServerSharedSecret
					Password,
				ccRadiusProxyServerRowStatus
					AbbrevRowStatus
			 }

		-- 1.3.6.1.4.1.388.11.2.8.2.3.1.1
		ccRadiusProxyServerIndex OBJECT-TYPE
			SYNTAX Unsigned32 (1..5)
			MAX-ACCESS accessible-for-notify
			STATUS current
			DESCRIPTION
				"Simple Index."
			::= { ccRadiusProxyServerEntry 1 }

		
		-- 1.3.6.1.4.1.388.11.2.8.2.3.1.2
		ccRadiusProxyServerPrefixOrSuffix OBJECT-TYPE
			SYNTAX DisplayString (SIZE (1..8))
			MAX-ACCESS read-write
			STATUS current
			DESCRIPTION
				"Prefix  of suffix used for proxying radius request to a 
				proxy server
				"
			::= { ccRadiusProxyServerEntry 2 }

		
		-- 1.3.6.1.4.1.388.11.2.8.2.3.1.3
		ccRadiusProxyServerIp OBJECT-TYPE
			SYNTAX IpAddress
			MAX-ACCESS read-write
			STATUS current
			DESCRIPTION
				"IP address of the proxy server
				"
			::= { ccRadiusProxyServerEntry 3 }

		
		-- 1.3.6.1.4.1.388.11.2.8.2.3.1.4
		ccRadiusProxyServerPort OBJECT-TYPE
			SYNTAX Integer32
			MAX-ACCESS read-write
			STATUS current
			DESCRIPTION
				"Port of proxy server
				"
			::= { ccRadiusProxyServerEntry 4 }

		
		-- 1.3.6.1.4.1.388.11.2.8.2.3.1.5
		ccRadiusProxyServerSharedSecret OBJECT-TYPE
			SYNTAX Password
			MAX-ACCESS read-write
			STATUS current
			DESCRIPTION
				"Shared secret between radius server and proxy server
				"
			::= { ccRadiusProxyServerEntry 5 }

		
		-- 1.3.6.1.4.1.388.11.2.8.2.3.1.6
		ccRadiusProxyServerRowStatus OBJECT-TYPE
			SYNTAX AbbrevRowStatus
			MAX-ACCESS read-write
			STATUS current
			DESCRIPTION
				"Row Status.
				"
			::= { ccRadiusProxyServerEntry 6 }

		
		-- 1.3.6.1.4.1.388.11.2.8.3
		ccRadiusLdap OBJECT IDENTIFIER ::= { ccRadiusServer 3 }

		
		-- 1.3.6.1.4.1.388.11.2.8.3.1
		ccRadiusLdapServerIp OBJECT-TYPE
			SYNTAX IpAddress
			MAX-ACCESS read-write
			STATUS current
			DESCRIPTION
				"IP address of the LDAP server
				"
			::= { ccRadiusLdap 1 }

		
		-- 1.3.6.1.4.1.388.11.2.8.3.2
		ccRadiusLdapServerPort OBJECT-TYPE
			SYNTAX INTEGER (1..6)
			MAX-ACCESS read-write
			STATUS current
			DESCRIPTION
				"Port of the LDAP server
				"
			::= { ccRadiusLdap 2 }

		
		-- 1.3.6.1.4.1.388.11.2.8.3.3
		ccRadiusLdapLoginAttribute OBJECT-TYPE
			SYNTAX DisplayString (SIZE (0..16))
			MAX-ACCESS read-write
			STATUS current
			DESCRIPTION
				"Name of the login attribute used by LDAP for authenticating the
				user.
				"
			::= { ccRadiusLdap 3 }

		
		-- 1.3.6.1.4.1.388.11.2.8.3.4
		ccRadiusLdapPasswordAttribute OBJECT-TYPE
			SYNTAX DisplayString
			MAX-ACCESS read-write
			STATUS current
			DESCRIPTION
				"Name of the login attribute used by LDAP for authenticating the
				user.
				"
			::= { ccRadiusLdap 4 }

		
		-- 1.3.6.1.4.1.388.11.2.8.3.5
		ccRadiusLdapBindDistinguishedName OBJECT-TYPE
			SYNTAX DisplayString (SIZE (0..128))
			MAX-ACCESS read-write
			STATUS current
			DESCRIPTION
				"Bind DN used the LDAP client on the WS2000 to connect to
				a LDAP server
				"
			::= { ccRadiusLdap 5 }

		
		-- 1.3.6.1.4.1.388.11.2.8.3.6
		ccRadiusLdapBindDistinguishedPassword OBJECT-TYPE
			SYNTAX Password
			MAX-ACCESS read-write
			STATUS current
			DESCRIPTION
				"Bind password used the LDAP client on the WS2000 to connect to
				a LDAP server"
			::= { ccRadiusLdap 6 }

		
		-- 1.3.6.1.4.1.388.11.2.8.3.7
		ccRadiusLdapBaseDistinguishedName OBJECT-TYPE
			SYNTAX DisplayString (SIZE (0..128))
			MAX-ACCESS read-write
			STATUS current
			DESCRIPTION
				"Base DN used the LDAP client on the WS2000 to connect to
				a LDAP server."
			::= { ccRadiusLdap 7 }

		
		-- 1.3.6.1.4.1.388.11.2.8.3.8
		ccRadiusLdapGroupAttribute OBJECT-TYPE
			SYNTAX DisplayString (SIZE (0..16))
			MAX-ACCESS read-write
			STATUS current
			DESCRIPTION
				"Name of the group attribute used by LDAP for retrieving the
				group associated with a user
				"
			::= { ccRadiusLdap 8 }

		
		-- 1.3.6.1.4.1.388.11.2.8.3.9
		ccRadiusLdapGroupFilter OBJECT-TYPE
			SYNTAX DisplayString (SIZE (0..128))
			MAX-ACCESS read-write
			STATUS current
			DESCRIPTION
				"Filter specification used by the LDAP client to retrieve
				the groups associated with a user
				
				"
			::= { ccRadiusLdap 9 }

		
		-- 1.3.6.1.4.1.388.11.2.8.3.10
		ccRadiusLdapGroupMembershipAttribute OBJECT-TYPE
			SYNTAX DisplayString (SIZE (0..16))
			MAX-ACCESS read-write
			STATUS current
			DESCRIPTION
				"Name  of the attribute in the user schema which specifies
				groups associated with the user. This is used if the
				group filter specified by ccRadiusGroupFilter return 
				an error.
				"
			::= { ccRadiusLdap 10 }

		
		-- 1.3.6.1.4.1.388.11.2.8.4
		ccRadiusUsers OBJECT IDENTIFIER ::= { ccRadiusServer 4 }
-- ??-CSM: who else uses the local user database?
-- depending on that answer, maybe this doesn't go under ccRadius?
		
		-- 1.3.6.1.4.1.388.11.2.8.4.1
		ccRadiusUsersGroupTable OBJECT-TYPE
			SYNTAX SEQUENCE OF CcRadiusUsersGroupEntry
			MAX-ACCESS not-accessible
			STATUS obsolete
			DESCRIPTION
				"Table of Group entries."
			::= { ccRadiusUsers 1 }

		
		-- 1.3.6.1.4.1.388.11.2.8.4.1.1
		ccRadiusUsersGroupEntry OBJECT-TYPE
			SYNTAX CcRadiusUsersGroupEntry
			MAX-ACCESS not-accessible
			STATUS obsolete
			DESCRIPTION
				"Description."
			INDEX { ccRadiusUsersGroup }
			::= { ccRadiusUsersGroupTable 1 }

		
		CcRadiusUsersGroupEntry ::=
			SEQUENCE { 
				ccRadiusUsersGroup
					DisplayString,
				ccRadiusUsersGroupRowStatus
					AbbrevRowStatus,
				ccRadiusUsersGroupId
					Integer32
			 }

		-- 1.3.6.1.4.1.388.11.2.8.4.1.1.1
		ccRadiusUsersGroup OBJECT-TYPE
			SYNTAX DisplayString (SIZE (1..8))
			MAX-ACCESS read-create
			STATUS obsolete
			DESCRIPTION
				"Name of the group
				"
			::= { ccRadiusUsersGroupEntry 1 }

		
		-- 1.3.6.1.4.1.388.11.2.8.4.1.1.2
		ccRadiusUsersGroupRowStatus OBJECT-TYPE
			SYNTAX AbbrevRowStatus
			MAX-ACCESS read-create
			STATUS obsolete
			DESCRIPTION
				"Row status
				"
			::= { ccRadiusUsersGroupEntry 2 }

		
		-- 1.3.6.1.4.1.388.11.2.8.4.1.1.3
		ccRadiusUsersGroupId OBJECT-TYPE
			SYNTAX Integer32
			MAX-ACCESS read-only
			STATUS obsolete
			DESCRIPTION
				"Actual index of that Group in the Configuration.
				
				Added to solve a problem encountered by SEMM
				for resolving the Multipointer ccRadiusUsersGroups."
			::= { ccRadiusUsersGroupEntry 3 }

		
		-- 1.3.6.1.4.1.388.11.2.8.4.2
		ccRadiusUsersTable OBJECT-TYPE
			SYNTAX SEQUENCE OF CcRadiusUsersEntry
			MAX-ACCESS not-accessible
			STATUS current
			DESCRIPTION
				"Table of User entries."
			::= { ccRadiusUsers 2 }

		
		-- 1.3.6.1.4.1.388.11.2.8.4.2.1
		ccRadiusUsersEntry OBJECT-TYPE
			SYNTAX CcRadiusUsersEntry
			MAX-ACCESS not-accessible
			STATUS current
			DESCRIPTION
				"Description."
			INDEX { ccRadiusUsersId }
			::= { ccRadiusUsersTable 1 }

		
		CcRadiusUsersEntry ::=
			SEQUENCE { 
				ccRadiusUsersId
					DisplayString,
				ccRadiusUsersPassword
					Password,
				ccRadiusUsersGroups
					BITS,
				ccRadiusUsersRowStatus
					AbbrevRowStatus
			 }

		-- 1.3.6.1.4.1.388.11.2.8.4.2.1.1
		ccRadiusUsersId OBJECT-TYPE
			SYNTAX DisplayString (SIZE (1..8))
			MAX-ACCESS read-create
			STATUS current
			DESCRIPTION
				"User name."
			::= { ccRadiusUsersEntry 1 }

		
		-- 1.3.6.1.4.1.388.11.2.8.4.2.1.2
		ccRadiusUsersPassword OBJECT-TYPE
			SYNTAX Password (SIZE (1..8))
			MAX-ACCESS read-create
			STATUS current
			DESCRIPTION
				"Password."
			::= { ccRadiusUsersEntry 2 }

		
		-- 1.3.6.1.4.1.388.11.2.8.4.2.1.3
		ccRadiusUsersGroups OBJECT-TYPE
			SYNTAX BITS
				{
				null(0),
				group1(1),
				group2(2),
				group3(3),
				group4(4),
				group5(5),
				group6(6),
				group7(7),
				group8(8),
				group9(9),
				group10(10)
				}
			MAX-ACCESS read-create
			STATUS current
			DESCRIPTION
				"List of groups associated with the user.
				
				Note that if a group is deleted, the
				corresponding bit pointing to that group
				will be cleared in this variable for all
				users that previously had it set."
			::= { ccRadiusUsersEntry 3 }

		
		-- 1.3.6.1.4.1.388.11.2.8.4.2.1.4
		ccRadiusUsersRowStatus OBJECT-TYPE
			SYNTAX AbbrevRowStatus
			MAX-ACCESS read-create
			STATUS current
			DESCRIPTION
				"Row Status."
			::= { ccRadiusUsersEntry 4 }

		
		-- 1.3.6.1.4.1.388.11.2.8.5
		ccRadiusAccess OBJECT IDENTIFIER ::= { ccRadiusServer 5 }

		
		-- 1.3.6.1.4.1.388.11.2.8.5.1
		ccRadiusAccessTable OBJECT-TYPE
			SYNTAX SEQUENCE OF CcRadiusAccessEntry
			MAX-ACCESS not-accessible
			STATUS obsolete
			DESCRIPTION
				"Table of Access Policy entries."
			::= { ccRadiusAccess 1 }

		
		-- 1.3.6.1.4.1.388.11.2.8.5.1.1
		ccRadiusAccessEntry OBJECT-TYPE
			SYNTAX CcRadiusAccessEntry
			MAX-ACCESS not-accessible
			STATUS obsolete
			DESCRIPTION
				"Acess table entry specifying the the WLANs allowed for each 
				group
				"
			INDEX { ccRadiusUsersGroup }
			::= { ccRadiusAccessTable 1 }

		
		CcRadiusAccessEntry ::=
			SEQUENCE { 
				ccRadiusAccessWlanPtrs
					BITS
			 }

		-- 1.3.6.1.4.1.388.11.2.8.5.1.1.2
		ccRadiusAccessWlanPtrs OBJECT-TYPE
			SYNTAX BITS
				{
				null(0),
				wlan1(1),
				wlan2(2),
				wlan3(3),
				wlan4(4)
				}
			MAX-ACCESS read-write
			STATUS obsolete
			DESCRIPTION
				"Points to the zero or more WLANs for which the given
				GroupId is allowed access.
				"
			::= { ccRadiusAccessEntry 2 }

		
-- !!- OID: located at .1000 to save room above.
		-- 1.3.6.1.4.1.388.11.2.1000
		ccGroups OBJECT IDENTIFIER ::= { ws2k 1000 }

		
		-- 1.3.6.1.4.1.388.11.2.1000.1
		ccGroupsV1dot0 OBJECT IDENTIFIER ::= { ccGroups 1 }

		
		-- 1.3.6.1.4.1.388.11.2.1000.1.1
		ccAdminGroup OBJECT-GROUP
			OBJECTS { ccInfoSerialNumber, ccResetFactory, ccResetSwitch, ccLoadFwOperation, ccLoadFwInterface, 
				ccLoadFwServerPath, ccLoadFwServerFilename, ccLoadFwStart, ccLoadFwResult, ccLoadFwSuccess, 
				ccLoadCfgOperation, ccLoadCfgServerPath, ccLoadCfgServerFilename, ccLoadCfgStart, ccLoadCfgOperationsDone, 
				ccLoadCfgResult, ccLoadCfgSuccess, ccCfgHistChangeCount, ccCfgHistChangeTime, ccCfgHistSemaphore, 
				ccSnmpLastDeniedIpAddr, ccSysDNSRelayMode, ccApSslv2Mode, ccApSshv1Mode, ccApSslWeakCipherSupport, ccSnmpAclViolations, ccLoadServerIpAddr, ccLoadFtpUsername
				 }
			STATUS current
			DESCRIPTION 
				" "
			::= { ccGroupsV1dot0 1 }

		
		-- 1.3.6.1.4.1.388.11.2.1000.1.2
		ccNotificationsGroup NOTIFICATION-GROUP
			NOTIFICATIONS { ccPortalAdopted, ccPortalUnAdopted, ccPortalDenied, ccMuAssociated, ccMuUnAssociated, 
				ccMuDenied, ccSnmpAclViolation, ccConfigChange }
			STATUS current
			DESCRIPTION 
				" "
			::= { ccGroupsV1dot0 2 }

		
		-- 1.3.6.1.4.1.388.11.2.1000.1.3
		ccApGroup OBJECT-GROUP
			OBJECTS { ccApIndex, ccApNicMac, ccApModelNumber, ccApSerialNumber, ccApPcbRevision, 
				ccApBootLoaderRev, ccApWispVersion, ccApRuntimeFwVersion, ccApNumPortals, ccApPointersToPortals
				 }
			STATUS current
			DESCRIPTION 
				" "
			::= { ccGroupsV1dot0 3 }

		
		-- 1.3.6.1.4.1.388.11.2.1000.1.4
		ccPortalGroup OBJECT-GROUP
			OBJECTS { ccPortalIndex, ccPortalPointerToAp, ccPortalPointersToWlans, ccPortalOptions, ccPortalMac, 
				ccPortalNumberOfEss, ccPortalNumberOfBss, ccPortalAssociatedMus, ccPortalChannel, ccPortalTxPowerLevel, 
				ccPortalLastMac, ccPortalLastReason, ccPortalName, ccPortalLocation, ccPortalLastAdoption, 
				ccPortalRadioType }
			STATUS current
			DESCRIPTION 
				" "
			::= { ccGroupsV1dot0 4 }

		
		-- 1.3.6.1.4.1.388.11.2.1000.1.5
		ccAssociationGroup OBJECT-GROUP
			OBJECTS { ccAssociationFirstAssociate, ccAssociationLastAssociate, ccAssociationCountAssociates }
			STATUS current
			DESCRIPTION 
				" "
			::= { ccGroupsV1dot0 5 }

		
		-- 1.3.6.1.4.1.388.11.2.1000.1.6
		ccMuGroup OBJECT-GROUP
			OBJECTS { ccMuMac, ccMuWlanIndex, ccMuWlanName, ccMuPortalIndex, ccMuPortalMac, 
				ccMuSymbolRogueApEna, ccMuIpAddr, ccMuType, ccMuRadioType, ccMuSupportedRates, 
				ccMuPowerMode, ccMuAuthenticationMethod, ccMuEncryptionMethod, ccMuRxPktsUcast, ccMuTxPktsUcast, 
				ccMuRxOctetsUcast, ccMuTxOctetsUcast, ccMuRxUndecryptablePkts, ccMuRxRssiNumPkts, ccMuRxRssiSum, 
				ccMuRxRssiSumSquares, ccMuRxRssiMostRecent, ccMuLastActivity, ccMuRxPktsAt1Mb, ccMuRxPktsAt2Mb, 
				ccMuRxPktsAt5pt5Mb, ccMuRxPktsAt6Mb, ccMuRxPktsAt9Mb, ccMuRxPktsAt11Mb, ccMuRxPktsAt12Mb, 
				ccMuRxPktsAt18Mb, ccMuRxPktsAt22Mb, ccMuRxPktsAt24Mb, ccMuRxPktsAt36Mb, ccMuRxPktsAt48Mb, 
				ccMuRxPktsAt54Mb, ccMuTxPktsAt1Mb, ccMuTxPktsAt2Mb, ccMuTxPktsAt5pt5Mb, ccMuTxPktsAt6Mb, 
				ccMuTxPktsAt9Mb, ccMuTxPktsAt11Mb, ccMuTxPktsAt12Mb, ccMuTxPktsAt18Mb, ccMuTxPktsAt22Mb, 
				ccMuTxPktsAt24Mb, ccMuTxPktsAt36Mb, ccMuTxPktsAt48Mb, ccMuTxPktsAt54Mb, ccMuRxOctetsAt1Mb, 
				ccMuRxOctetsAt2Mb, ccMuRxOctetsAt5pt5Mb, ccMuRxOctetsAt6Mb, ccMuRxOctetsAt9Mb, ccMuRxOctetsAt11Mb, 
				ccMuRxOctetsAt12Mb, ccMuRxOctetsAt18Mb, ccMuRxOctetsAt22Mb, ccMuRxOctetsAt24Mb, ccMuRxOctetsAt36Mb, 
				ccMuRxOctetsAt48Mb, ccMuRxOctetsAt54Mb, ccMuTxOctetsAt1Mb, ccMuTxOctetsAt2Mb, ccMuTxOctetsAt5pt5Mb, 
				ccMuTxOctetsAt6Mb, ccMuTxOctetsAt9Mb, ccMuTxOctetsAt11Mb, ccMuTxOctetsAt12Mb, ccMuTxOctetsAt18Mb, 
				ccMuTxOctetsAt22Mb, ccMuTxOctetsAt24Mb, ccMuTxOctetsAt36Mb, ccMuTxOctetsAt48Mb, ccMuTxOctetsAt54Mb, 
				ccMuTxRetries01, ccMuTxRetries02, ccMuTxRetries03, ccMuTxRetries04, ccMuTxRetries05, 
				ccMuTxRetries06, ccMuTxRetries07, ccMuTxRetries08, ccMuTxRetries09, ccMuTxRetries10, 
				ccMuTxRetries11, ccMuTxRetries12, ccMuTxRetries13, ccMuTxRetries14, ccMuTxRetries15, 
				ccMuTxRetriesNone, ccMuTxRetriesFailed, ccMuTxRetriesTotal, ccMuLastPortal, ccMuTxRetriesMostRecent, 
				ccMuLastMac, ccMuLastReason, ccMuIsDataReady }
			STATUS current
			DESCRIPTION 
				" "
			::= { ccGroupsV1dot0 6 }

		
		-- 1.3.6.1.4.1.388.11.2.1000.2
		ccGroupsV1dot5 OBJECT IDENTIFIER ::= { ccGroups 2 }

		
		-- 1.3.6.1.4.1.388.11.2.1000.2.1
		ccGroupsV1dot5variables OBJECT-GROUP
			OBJECTS { ccInfoSerialNumber, ccInfoCountrySelection, ccIdHwVersion, ccIdFwVersion, ccIdSwVersion, 
				ccIdMibVersion, ccIdCliVersion, ccIdXmlVersion, ccIdSerialNumber, ccResetFactory, 
				ccResetSwitch, ccResetFactoryExceptIpSnmp, ccLoadFwOperation, ccLoadFwInterface, ccLoadFwServerPath, 
				ccLoadFwServerFilename, ccLoadFwStart, ccLoadFwResult, ccLoadFwSuccess, ccLoadCfgOperation, 
				ccLoadCfgServerPath, ccLoadCfgServerFilename, ccLoadCfgStart, ccLoadCfgOperationsDone, ccLoadCfgResult, 
				ccLoadCfgSuccess, ccCfgHistChangeCount, ccCfgHistChangeTime, ccCfgHistSemaphore, ccLoadServerIpAddr, 
				ccLoadFtpUsername, ccLoadFtpPassword, ccSnmpAclViolations, ccSnmpLastDeniedIpAddr, ccCompactFlashCapacity, 
				ccCompactFlashUsed, ccSumStatsShortWindow, ccSumStatsShortUpdateInterval, ccSumStatsLongWindow, ccSumStatsLongUpdateInterval, 
				ccTrapCtrlCfAlmostFullThreshold, ccTrapCtrlFirewallUnderAttackDescription, ccTrapCtrlFirewallUnderAttackRateLimit, ccTrapCtrlRadarDetectedPortalMac, ccTrapCtrlRadarDetectedChannel, 
				ccTrapCtrlSumStatsIndex, ccTrapCtrlSumStatsDescr, ccTrapCtrlSumStatsUnits, ccTrapCtrlSumStatsCanBeSetMu, ccTrapCtrlSumStatsThresholdMu, 
				ccTrapCtrlSumStatsCanBeSetPortal, ccTrapCtrlSumStatsThresholdPortals, ccTrapCtrlSumStatsCanBeSetWlan, ccTrapCtrlSumStatsThresholdWlans, ccTrapCtrlSumStatsCanBeSetSwitch, 
				ccTrapCtrlSumStatsThresholdSwitch, ccTrapCtrlSumStatsMinPktsForTrap, ccApIndex, ccApNicMac, ccApModelNumber, 
				ccApSerialNumber, ccApPcbRevision, ccApBootLoaderRev, ccApWispVersion, ccApRuntimeFwVersion, 
				ccApNumPortals, ccApPointersToPortals, ccPortalIndex, ccPortalPointerToAp, ccPortalPointersToWlans, 
				ccPortalName, ccPortalLocation, ccPortalOptions, ccPortalMac, ccPortalNumberOfEss, 
				ccPortalNumberOfBss, ccPortalAssociatedMus, ccPortalRadioType, ccPortalChannel, ccPortalTxPowerLevel, 
				ccPortalLastAdoption, ccPortalState, ccPortalLastMac, ccPortalLastReason, ccPortalSystemStatsBeaconsTx, 
				ccPortalSystemStatsBeaconsTxOctets, ccPortalSystemStatsProbeReqRx, ccPortalSystemStatsProbeReqRxOctets, ccPortalSystemStatsProbeRespRetriesNone, ccPortalSystemStatsProbeRespRetries1, 
				ccPortalSystemStatsProbeRespRetries2, ccPortalSystemStatsProbeRespRetriesFailed, ccPortalSystemStatsProbeRespTxOctets, ccPortalTxPktsUcast, ccPortalRxPktsUcast, 
				ccPortalRxPktsNUcast, ccPortalTxOctetsUcast, ccPortalRxOctetsUcast, ccPortalRxOctetsNUcast, ccPortalRxUndecryptablePkts, 
				ccPortalLastActivity, ccPortalRxPktsAt1Mb, ccPortalRxPktsAt2Mb, ccPortalRxPktsAt5pt5Mb, ccPortalRxPktsAt6Mb, 
				ccPortalRxPktsAt9Mb, ccPortalRxPktsAt11Mb, ccPortalRxPktsAt12Mb, ccPortalRxPktsAt18Mb, ccPortalRxPktsAt22Mb, 
				ccPortalRxPktsAt24Mb, ccPortalRxPktsAt36Mb, ccPortalRxPktsAt48Mb, ccPortalRxPktsAt54Mb, ccPortalTxPktsAt1Mb, 
				ccPortalTxPktsAt2Mb, ccPortalTxPktsAt5pt5Mb, ccPortalTxPktsAt6Mb, ccPortalTxPktsAt9Mb, ccPortalTxPktsAt11Mb, 
				ccPortalTxPktsAt12Mb, ccPortalTxPktsAt18Mb, ccPortalTxPktsAt22Mb, ccPortalTxPktsAt24Mb, ccPortalTxPktsAt36Mb, 
				ccPortalTxPktsAt48Mb, ccPortalTxPktsAt54Mb, ccPortalRxOctetsAt1Mb, ccPortalRxOctetsAt2Mb, ccPortalRxOctetsAt5pt5Mb, 
				ccPortalRxOctetsAt6Mb, ccPortalRxOctetsAt9Mb, ccPortalRxOctetsAt11Mb, ccPortalRxOctetsAt12Mb, ccPortalRxOctetsAt18Mb, 
				ccPortalRxOctetsAt22Mb, ccPortalRxOctetsAt24Mb, ccPortalRxOctetsAt36Mb, ccPortalRxOctetsAt48Mb, ccPortalRxOctetsAt54Mb, 
				ccPortalTxOctetsAt1Mb, ccPortalTxOctetsAt2Mb, ccPortalTxOctetsAt5pt5Mb, ccPortalTxOctetsAt6Mb, ccPortalTxOctetsAt9Mb, 
				ccPortalTxOctetsAt11Mb, ccPortalTxOctetsAt12Mb, ccPortalTxOctetsAt18Mb, ccPortalTxOctetsAt22Mb, ccPortalTxOctetsAt24Mb, 
				ccPortalTxOctetsAt36Mb, ccPortalTxOctetsAt48Mb, ccPortalTxOctetsAt54Mb, ccPortalTxRetriesPktsNone, ccPortalTxRetriesPkts01, 
				ccPortalTxRetriesPkts02, ccPortalTxRetriesPkts03, ccPortalTxRetriesPkts04, ccPortalTxRetriesPkts05, ccPortalTxRetriesPkts06, 
				ccPortalTxRetriesPkts07, ccPortalTxRetriesPkts08, ccPortalTxRetriesPkts09, ccPortalTxRetriesPkts10, ccPortalTxRetriesPkts11, 
				ccPortalTxRetriesPkts12, ccPortalTxRetriesPkts13, ccPortalTxRetriesPkts14, ccPortalTxRetriesPkts15, ccPortalTxRetriesPktsFailed, 
				ccPortalTxRetriesOctetsNone, ccPortalTxRetriesOctets01, ccPortalTxRetriesOctets02, ccPortalTxRetriesOctets03, ccPortalTxRetriesOctets04, 
				ccPortalTxRetriesOctets05, ccPortalTxRetriesOctets06, ccPortalTxRetriesOctets07, ccPortalTxRetriesOctets08, ccPortalTxRetriesOctets09, 
				ccPortalTxRetriesOctets10, ccPortalTxRetriesOctets11, ccPortalTxRetriesOctets12, ccPortalTxRetriesOctets13, ccPortalTxRetriesOctets14, 
				ccPortalTxRetriesOctets15, ccPortalTxRetriesOctetsFailed, ccPortalSigStatsNumPkts, ccPortalSigStatsSignalBest, ccPortalSigStatsSignalWorst, 
				ccPortalSigStatsSignalSum, ccPortalSigStatsSignalSumSquares, ccPortalSigStatsSignalMostRecent, ccPortalSigStatsNoiseBest, ccPortalSigStatsNoiseWorst, 
				ccPortalSigStatsNoiseSum, ccPortalSigStatsNoiseSumSquares, ccPortalSigStatsNoiseMostRecent, ccPortalSigStatsSnrBest, ccPortalSigStatsSnrWorst, 
				ccPortalSigStatsSnrSum, ccPortalSigStatsSnrSumSquares, ccPortalSigStatsSnrMostRecent, ccPortalSumStatsShortTimestamp, ccPortalSumStatsShortNumPkts, 
				ccPortalSumStatsShortPktsPerSec100, ccPortalSumStatsShortPktsPerSecTx100, ccPortalSumStatsShortPktsPerSecRx100, ccPortalSumStatsShortThroughput, ccPortalSumStatsShortThroughputTx, 
				ccPortalSumStatsShortThroughputRx, ccPortalSumStatsShortAvgBitSpeed, ccPortalSumStatsShortAvgMuSignal, ccPortalSumStatsShortAvgMuNoise, ccPortalSumStatsShortAvgMuSnr, 
				ccPortalSumStatsShortPp10kNUcastPkts, ccPortalSumStatsShortPp10kTxWithRetries, ccPortalSumStatsShortTxAvgRetries100, ccPortalSumStatsShortPp10kRxUndecrypt, ccPortalSumStatsShortTotalMus, 
				ccPortalSumStatsShortPp10kRfUtil, ccPortalSumStatsLongTimestamp, ccPortalSumStatsLongNumPkts, ccPortalSumStatsLongPktsPerSec100, ccPortalSumStatsLongPktsPerSecTx100, 
				ccPortalSumStatsLongPktsPerSecRx100, ccPortalSumStatsLongThroughput, ccPortalSumStatsLongThroughputTx, ccPortalSumStatsLongThroughputRx, ccPortalSumStatsLongAvgBitSpeed, 
				ccPortalSumStatsLongAvgMuSignal, ccPortalSumStatsLongAvgMuNoise, ccPortalSumStatsLongAvgMuSnr, ccPortalSumStatsLongPp10kNUcastPkts, ccPortalSumStatsLongPp10kTxWithRetries, 
				ccPortalSumStatsLongTxAvgRetries100, ccPortalSumStatsLongPp10kRxUndecrypt, ccPortalSumStatsLongTotalMus, ccPortalSumStatsLongPp10kRfUtil, ccAssociationFirstAssociate, 
				ccAssociationLastAssociate, ccAssociationCountAssociates, ccMuMac, ccMuWlanIndex, ccMuWlanName, 
				ccMuIsDataReady, ccMuPortalIndex, ccMuPortalMac, ccMuSymbolRogueApEna, ccMuIpAddr, 
				ccMuType, ccMuRadioType, ccMuSupportedRates, ccMuPowerMode, ccMuAuthenticationMethod, 
				ccMuEncryptionMethod, ccMuTxPktsUcast, ccMuRxPktsUcast, ccMuTxOctetsUcast, ccMuRxOctetsUcast, 
				ccMuRxUndecryptablePkts, ccMuRxRssiNumPkts, ccMuRxRssiSum, ccMuRxRssiSumSquares, ccMuRxRssiMostRecent, 
				ccMuLastActivity, ccMuRxPktsAt1Mb, ccMuRxPktsAt2Mb, ccMuRxPktsAt5pt5Mb, ccMuRxPktsAt6Mb, 
				ccMuRxPktsAt9Mb, ccMuRxPktsAt11Mb, ccMuRxPktsAt12Mb, ccMuRxPktsAt18Mb, ccMuRxPktsAt22Mb, 
				ccMuRxPktsAt24Mb, ccMuRxPktsAt36Mb, ccMuRxPktsAt48Mb, ccMuRxPktsAt54Mb, ccMuTxPktsAt1Mb, 
				ccMuTxPktsAt2Mb, ccMuTxPktsAt5pt5Mb, ccMuTxPktsAt6Mb, ccMuTxPktsAt9Mb, ccMuTxPktsAt11Mb, 
				ccMuTxPktsAt12Mb, ccMuTxPktsAt18Mb, ccMuTxPktsAt22Mb, ccMuTxPktsAt24Mb, ccMuTxPktsAt36Mb, 
				ccMuTxPktsAt48Mb, ccMuTxPktsAt54Mb, ccMuRxOctetsAt1Mb, ccMuRxOctetsAt2Mb, ccMuRxOctetsAt5pt5Mb, 
				ccMuRxOctetsAt6Mb, ccMuRxOctetsAt9Mb, ccMuRxOctetsAt11Mb, ccMuRxOctetsAt12Mb, ccMuRxOctetsAt18Mb, 
				ccMuRxOctetsAt22Mb, ccMuRxOctetsAt24Mb, ccMuRxOctetsAt36Mb, ccMuRxOctetsAt48Mb, ccMuRxOctetsAt54Mb, 
				ccMuTxOctetsAt1Mb, ccMuTxOctetsAt2Mb, ccMuTxOctetsAt5pt5Mb, ccMuTxOctetsAt6Mb, ccMuTxOctetsAt9Mb, 
				ccMuTxOctetsAt11Mb, ccMuTxOctetsAt12Mb, ccMuTxOctetsAt18Mb, ccMuTxOctetsAt22Mb, ccMuTxOctetsAt24Mb, 
				ccMuTxOctetsAt36Mb, ccMuTxOctetsAt48Mb, ccMuTxOctetsAt54Mb, ccMuTxRetriesNone, ccMuTxRetries01, 
				ccMuTxRetries02, ccMuTxRetries03, ccMuTxRetries04, ccMuTxRetries05, ccMuTxRetries06, 
				ccMuTxRetries07, ccMuTxRetries08, ccMuTxRetries09, ccMuTxRetries10, ccMuTxRetries11, 
				ccMuTxRetries12, ccMuTxRetries13, ccMuTxRetries14, ccMuTxRetries15, ccMuTxRetriesFailed, 
				ccMuTxRetriesTotal, ccMuTxRetriesMostRecent, ccMuLastMac, ccMuLastReason, ccMuLastPortal, 
				ccMuTxRetriesOctetsNone, ccMuTxRetriesOctets01, ccMuTxRetriesOctets02, ccMuTxRetriesOctets03, ccMuTxRetriesOctets04, 
				ccMuTxRetriesOctets05, ccMuTxRetriesOctets06, ccMuTxRetriesOctets07, ccMuTxRetriesOctets08, ccMuTxRetriesOctets09, 
				ccMuTxRetriesOctets10, ccMuTxRetriesOctets11, ccMuTxRetriesOctets12, ccMuTxRetriesOctets13, ccMuTxRetriesOctets14, 
				ccMuTxRetriesOctets15, ccMuTxRetriesOctetsFailed, ccMuSigStatsNumPkts, ccMuSigStatsSignalBest, ccMuSigStatsSignalWorst, 
				ccMuSigStatsSignalSum, ccMuSigStatsSignalSumSquares, ccMuSigStatsSignalMostRecent, ccMuSigStatsNoiseBest, ccMuSigStatsNoiseWorst, 
				ccMuSigStatsNoiseSum, ccMuSigStatsNoiseSumSquares, ccMuSigStatsNoiseMostRecent, ccMuSigStatsSnrBest, ccMuSigStatsSnrWorst, 
				ccMuSigStatsSnrSum, ccMuSigStatsSnrSumSquares, ccMuSigStatsSnrMostRecent, ccMuSumStatsShortTimestamp, ccMuSumStatsShortNumPkts, 
				ccMuSumStatsShortPktsPerSec100, ccMuSumStatsShortPktsPerSecTx100, ccMuSumStatsShortPktsPerSecRx100, ccMuSumStatsShortThroughput, ccMuSumStatsShortThroughputTx, 
				ccMuSumStatsShortThroughputRx, ccMuSumStatsShortAvgBitSpeed, ccMuSumStatsShortAvgMuSignal, ccMuSumStatsShortAvgMuNoise, ccMuSumStatsShortAvgMuSnr, 
				ccMuSumStatsShortPp10kNUcastPkts, ccMuSumStatsShortPp10kTxWithRetries, ccMuSumStatsShortTxAvgRetries100, ccMuSumStatsShortPp10kRxUndecrypt, ccMuSumStatsLongTimestamp, 
				ccMuSumStatsLongNumPkts, ccMuSumStatsLongPktsPerSec100, ccMuSumStatsLongPktsPerSecTx100, ccMuSumStatsLongPktsPerSecRx100, ccMuSumStatsLongThroughput, 
				ccMuSumStatsLongThroughputTx, ccMuSumStatsLongThroughputRx, ccMuSumStatsLongAvgBitSpeed, ccMuSumStatsLongAvgMuSignal, ccMuSumStatsLongAvgMuNoise, 
				ccMuSumStatsLongAvgMuSnr, ccMuSumStatsLongPp10kNUcastPkts, ccMuSumStatsLongPp10kTxWithRetries, ccMuSumStatsLongTxAvgRetries100, ccMuSumStatsLongPp10kRxUndecrypt, 
				ccWlanIndex, ccWlanName, ccWlanEssid, ccWlanSubnet, ccWlanPortalsAdopted, 
				ccWlanEnable, ccWlanDisallowMuToMu, ccWlanVoicePrioritization, ccWlanAnswerBroadcastEss, ccWlanMulticastAddr1, 
				ccWlanMulticastAddr2, ccWlanMuAclDefault, ccWlanAuthentication, ccWlanEncryption, ccWlanAuthEapReauthenticationEnable, 
				ccWlanAuthEapReauthenticationPeriod, ccWlanAuthEapReauthenticationMaxRetries, ccWlanAuthEapRadius1Server, ccWlanAuthEapRadius1Port, ccWlanAuthEapRadius1SharedSecret, 
				ccWlanAuthEapRadius2Server, ccWlanAuthEapRadius2Port, ccWlanAuthEapRadius2SharedSecret, ccWlanAuthEapMuQuietPeriod, ccWlanAuthEapMuTimeout, 
				ccWlanAuthEapMuTxPeriod, ccWlanAuthEapMuMaxRetries, ccWlanAuthEapServerTimeout, ccWlanAuthEapServerMaxRetries, ccWlanAuthKerberosRealmName, 
				ccWlanAuthKerberosUsername, ccWlanAuthKerberosPassword, ccWlanAuthKerberosKdcServerIp1, ccWlanAuthKerberosKdcPort1, ccWlanAuthKerberosKdcServerIp2, 
				ccWlanAuthKerberosKdcPort2, ccWlanAuthKerberosKdcServerIpR, ccWlanAuthKerberosKdcPortR, ccWlanCryptoWepPassKey, ccWlanCryptoWepKey1, 
				ccWlanCryptoWepKey2, ccWlanCryptoWepKey3, ccWlanCryptoWepKey4, ccWlanCryptoWepKeyToUse, ccWlanCryptoWpaBcastKeyRotation, 
				ccWlanCryptoWpaKeyRotationInterval, ccWlanCryptoWpaKeyToUse, ccWlanCryptoWpaPassphrase, ccWlanCryptoWpaKey, ccWlanCryptoKeyguardPasskey, 
				ccWlanCryptoKeyguardKey1, ccWlanCryptoKeyguardKey2, ccWlanCryptoKeyguardKey3, ccWlanCryptoKeyguardKey4, ccWlanCryptoKeyguardKeyToUse, 
				ccWlanTxPktsUcast, ccWlanRxPktsUcast, ccWlanRxPktsNUcast, ccWlanTxOctetsUcast, ccWlanRxOctetsUcast, 
				ccWlanRxOctetsNUcast, ccWlanRxUndecryptablePkts, ccWlanLastActivity, ccWlanRxPktsAt1Mb, ccWlanRxPktsAt2Mb, 
				ccWlanRxPktsAt5pt5Mb, ccWlanRxPktsAt6Mb, ccWlanRxPktsAt9Mb, ccWlanRxPktsAt11Mb, ccWlanRxPktsAt12Mb, 
				ccWlanRxPktsAt18Mb, ccWlanRxPktsAt22Mb, ccWlanRxPktsAt24Mb, ccWlanRxPktsAt36Mb, ccWlanRxPktsAt48Mb, 
				ccWlanRxPktsAt54Mb, ccWlanTxPktsAt1Mb, ccWlanTxPktsAt2Mb, ccWlanTxPktsAt5pt5Mb, ccWlanTxPktsAt6Mb, 
				ccWlanTxPktsAt9Mb, ccWlanTxPktsAt11Mb, ccWlanTxPktsAt12Mb, ccWlanTxPktsAt18Mb, ccWlanTxPktsAt22Mb, 
				ccWlanTxPktsAt24Mb, ccWlanTxPktsAt36Mb, ccWlanTxPktsAt48Mb, ccWlanTxPktsAt54Mb, ccWlanRxOctetsAt1Mb, 
				ccWlanRxOctetsAt2Mb, ccWlanRxOctetsAt5pt5Mb, ccWlanRxOctetsAt6Mb, ccWlanRxOctetsAt9Mb, ccWlanRxOctetsAt11Mb, 
				ccWlanRxOctetsAt12Mb, ccWlanRxOctetsAt18Mb, ccWlanRxOctetsAt22Mb, ccWlanRxOctetsAt24Mb, ccWlanRxOctetsAt36Mb, 
				ccWlanRxOctetsAt48Mb, ccWlanRxOctetsAt54Mb, ccWlanTxOctetsAt1Mb, ccWlanTxOctetsAt2Mb, ccWlanTxOctetsAt5pt5Mb, 
				ccWlanTxOctetsAt6Mb, ccWlanTxOctetsAt9Mb, ccWlanTxOctetsAt11Mb, ccWlanTxOctetsAt12Mb, ccWlanTxOctetsAt18Mb, 
				ccWlanTxOctetsAt22Mb, ccWlanTxOctetsAt24Mb, ccWlanTxOctetsAt36Mb, ccWlanTxOctetsAt48Mb, ccWlanTxOctetsAt54Mb, 
				ccWlanTxRetriesPktsNone, ccWlanTxRetriesPkts01, ccWlanTxRetriesPkts02, ccWlanTxRetriesPkts03, ccWlanTxRetriesPkts04, 
				ccWlanTxRetriesPkts05, ccWlanTxRetriesPkts06, ccWlanTxRetriesPkts07, ccWlanTxRetriesPkts08, ccWlanTxRetriesPkts09, 
				ccWlanTxRetriesPkts10, ccWlanTxRetriesPkts11, ccWlanTxRetriesPkts12, ccWlanTxRetriesPkts13, ccWlanTxRetriesPkts14, 
				ccWlanTxRetriesPkts15, ccWlanTxRetriesPktsFailed, ccWlanTxRetriesOctetsNone, ccWlanTxRetriesOctets01, ccWlanTxRetriesOctets02, 
				ccWlanTxRetriesOctets03, ccWlanTxRetriesOctets04, ccWlanTxRetriesOctets05, ccWlanTxRetriesOctets06, ccWlanTxRetriesOctets07, 
				ccWlanTxRetriesOctets08, ccWlanTxRetriesOctets09, ccWlanTxRetriesOctets10, ccWlanTxRetriesOctets11, ccWlanTxRetriesOctets12, 
				ccWlanTxRetriesOctets13, ccWlanTxRetriesOctets14, ccWlanTxRetriesOctets15, ccWlanTxRetriesOctetsFailed, ccWlanSigStatsNumPkts, 
				ccWlanSigStatsSignalBest, ccWlanSigStatsSignalWorst, ccWlanSigStatsSignalSum, ccWlanSigStatsSignalSumSquares, ccWlanSigStatsNoiseBest, 
				ccWlanSigStatsNoiseWorst, ccWlanSigStatsNoiseSum, ccWlanSigStatsNoiseSumSquares, ccWlanSigStatsSnrBest, ccWlanSigStatsSnrWorst, 
				ccWlanSigStatsSnrSum, ccWlanSigStatsSnrSumSquares, ccWlanSumStatsShortTimestamp, ccWlanSumStatsShortNumPkts, ccWlanSumStatsShortPktsPerSec100, 
				ccWlanSumStatsShortPktsPerSecTx100, ccWlanSumStatsShortPktsPerSecRx100, ccWlanSumStatsShortThroughput, ccWlanSumStatsShortThroughputTx, ccWlanSumStatsShortThroughputRx, 
				ccWlanSumStatsShortAvgBitSpeed, ccWlanSumStatsShortAvgMuSignal, ccWlanSumStatsShortAvgMuNoise, ccWlanSumStatsShortAvgMuSnr, ccWlanSumStatsShortPp10kNUcastPkts, 
				ccWlanSumStatsShortPp10kTxWithRetries, ccWlanSumStatsShortTxAvgRetries100, ccWlanSumStatsShortPp10kRxUndecrypt, ccWlanSumStatsShortTotalMus, ccWlanSumStatsLongTimestamp, 
				ccWlanSumStatsLongNumPkts, ccWlanSumStatsLongPktsPerSec100, ccWlanSumStatsLongPktsPerSecTx100, ccWlanSumStatsLongPktsPerSecRx100, ccWlanSumStatsLongThroughput, 
				ccWlanSumStatsLongThroughputTx, ccWlanSumStatsLongThroughputRx, ccWlanSumStatsLongAvgBitSpeed, ccWlanSumStatsLongAvgMuSignal, ccWlanSumStatsLongAvgMuNoise, 
				ccWlanSumStatsLongAvgMuSnr, ccWlanSumStatsLongPp10kNUcastPkts, ccWlanSumStatsLongPp10kTxWithRetries, ccWlanSumStatsLongTxAvgRetries100, ccWlanSumStatsLongPp10kRxUndecrypt, 
				ccWlanSumStatsLongTotalMus, ccWanIndex, ccWanDhcpEnable, ccWanDhcpIpAddr, ccWanDhcpSubnetMask, 
				ccWanDhcpDefaultGateway, ccWanDhcpPrimaryDnsServer, ccWanDhcpSecondaryDnsServer, ccWanSubnetMask, ccWanDefaultGateway, 
				ccWanPrimaryDnsServer, ccWanSecondaryDnsServer, ccWanPppoeEnable, ccWanPppoeUsername, ccWanPppoePassword, 
				ccWanPppoeKeepAlive, ccWanPppoeIdleTime, ccWanPppoeAuthType, ccWanIpAddrIndex, ccWanIpAddrEnable, 
				ccWanIpAddr, ccWanFirewallGlobalEnable, ccWanFirewallIndex, ccWanFirewallDescription, ccWanFirewallAlwaysEnabled, 
				ccWanFirewallEnable, ccWanFirewallMimeFloodMaxHeaderLength, ccWanFirewallMimeFloodMaxHeaders, ccPortIndex, ccPortType, 
				ccPortPoeEquipped, ccPortStatus, ccPortDuplex, ccPortalBackgroundNoiseNumSamples, ccPortalBackgroundNoiseBest, 
				ccPortalBackgroundNoiseWorst, ccPortalBackgroundNoiseSum, ccPortalBackgroundNoiseSumSquares, ccMuSumStatsLongPp10kDropped, ccMuSumStatsShortPp10kDropped, 
				ccPortalSystemStatsProbeRespRetries3OrMore, ccPortalSumStatsShortPp10kTxMaxRetries, ccPortSpeed, ccResetStatCounters }
			STATUS current
			DESCRIPTION 
				"variables implemented in v1.5"
			::= { ccGroupsV1dot5 1 }

		
		-- 1.3.6.1.4.1.388.11.2.1000.2.2
		ccGroupsV1dot5obsoleted OBJECT-GROUP
			OBJECTS { ccLoadFtpPassword, ccMuRxPktsNUcast, ccMuRxOctetsNUcast, ccResetMuCounters }
			STATUS obsolete
			DESCRIPTION 
				"variables obsoleted in v1.5"
			::= { ccGroupsV1dot5 2 }

		
		-- 1.3.6.1.4.1.388.11.2.1000.2.3
		ccGroupsV1dot5notifications NOTIFICATION-GROUP
			NOTIFICATIONS { ccPortStatusChange, ccCfAlmostFull, ccFirewallUnderAttack, ccSumStatsMu, ccSumStatsPortal, 
				ccSumStatsWlan, ccSumStatsSwitch, ccRadarDetected, ccPortalAdopted, ccPortalUnAdopted, 
				ccPortalDenied, ccMuAssociated, ccMuUnAssociated, ccMuDenied, ccConfigChange, 
				ccSnmpAclViolation }
			STATUS current
			DESCRIPTION 
				"notifications implemented in v1.5"
			::= { ccGroupsV1dot5 3 }

		
		-- 1.3.6.1.4.1.388.11.2.1000.3
		ccGroupsV2dot0 OBJECT IDENTIFIER ::= { ccGroups 3 }

		
		-- 1.3.6.1.4.1.388.11.2.1000.3.1
		ccGroupsV2dot0variables OBJECT-GROUP
			OBJECTS { ccInfoSerialNumber, ccInfoCountrySelection, ccIdHwVersion, ccIdFwVersion, ccIdSwVersion, 
				ccIdMibVersion, ccIdCliVersion, ccIdXmlVersion, ccIdSerialNumber, ccResetFactory, 
				ccResetSwitch, ccResetFactoryExceptIpSnmp, ccResetStatCounters, ccLoadFwOperation, ccLoadFwInterface, 
				ccLoadFwServerPath, ccLoadFwServerFilename, ccLoadFwStart, ccLoadFwResult, ccLoadFwSuccess, 
				ccLoadCfgOperation, ccLoadCfgServerPath, ccLoadCfgServerFilename, ccLoadCfgStart, ccLoadCfgOperationsDone, 
				ccLoadCfgResult, ccLoadCfgSuccess, ccCfgHistChangeCount, ccCfgHistChangeTime, ccCfgHistSemaphore, 
				ccLoadServerIpAddr, ccLoadFtpUsername, ccLoadFtpPassword, ccSnmpAclViolations, ccSnmpLastDeniedIpAddr, 
				ccSnmpAccessV12Index, ccSnmpAccessV12Community, ccSnmpAccessV12CustomOid, ccSnmpAccessV12OidLimit, ccSnmpAccessV12Access, 
				ccSnmpAccessV12Enable, ccSnmpAccessV3Index, ccSnmpAccessV3SecurityLevel, ccSnmpAccessV3CustomOid, ccSnmpAccessV3OidLimit, 
				ccSnmpAccessV3Access, ccSnmpAccessV3AuthAlgorithm, ccSnmpAccessV3AuthPassword, ccSnmpAccessV3PrivacyAlgorithm, ccSnmpAccessV3PrivacyPassword, 
				ccSnmpAccessV3Enable, ccSnmpAccessControlIndex, ccSnmpAccessControlStartIp, ccSnmpAccessControlEndIp, ccSnmpAccessControlEnable, 
				ccSnmpTrapSinkV12Index, ccSnmpTrapSinkV12DestinationIp, ccSnmpTrapSinkV12Port, ccSnmpTrapSinkV12Community, ccSnmpTrapSinkV12Version, 
				ccSnmpTrapSinkV12Enable, ccSnmpTrapSinkV3Index, ccSnmpTrapSinkV3DestinationIp, ccSnmpTrapSinkV3Port, ccSnmpTrapSinkV3Username, 
				ccSnmpTrapSinkV3SecurityLevel, ccSnmpTrapSinkV3AuthAlgorithm, ccSnmpTrapSinkV3AuthPassword, ccSnmpTrapSinkV3PrivacyAlgorithm, ccSnmpTrapSinkV3PrivacyPassword, 
				ccSnmpTrapSinkV3Enable, ccCompactFlashCapacity, ccCompactFlashUsed, ccSumStatsShortWindow, ccSumStatsShortUpdateInterval, 
				ccSumStatsLongWindow, ccSumStatsLongUpdateInterval, ccMgmtAccessToAllow, ccMgmtAccessAirbeamAllow, ccMgmtAccessAirbeamPassword, 
				ccMgmtAccessAdminAuth, ccMgmtAccessAdminPassword, ccMgmtAccessAdminAuthRadiusServerIp, ccMgmtAccessAdminAuthRadiusServerPort, ccMgmtAccessAdminAuthRadiusSharedSecret, 
				ccMgmtAccessSshAuthTimeout, ccMgmtAccessSshInactivityTimeout, ccLoggingLevel, ccLoggingToSyslog, ccLoggingSyslogServer, 
				ccNtpEnable, ccNtp0Server, ccNtp0Port, ccNtp1Server, ccNtp1Port, 
				ccNtp2Server, ccNtp2Port, ccNtpGmtHourOffset, ccNtpGmtMinuteOffset, ccDhcpOptionsUpdateFwEna, 
				ccDhcpOptionsUpdateCfgEna, ccDhcpOptionsUpdateInterface, ccDhcpOptionsUpdateFwFilename, ccDhcpOptionsUpdateCfgFilename, ccRedundancyAdminState, 
				ccRedundancyOperState, ccRedundancyHeartbeatInterval, ccRedundancyRevertDelay, ccTrapCtrlCfAlmostFullThreshold, ccTrapCtrlFirewallUnderAttackDescription, 
				ccTrapCtrlFirewallUnderAttackRateLimit, ccTrapCtrlRadarDetectedPortalMac, ccTrapCtrlRadarDetectedChannel, ccTrapCtrlSumStatsIndex, ccTrapCtrlSumStatsDescr, 
				ccTrapCtrlSumStatsUnits, ccTrapCtrlSumStatsCanBeSetMu, ccTrapCtrlSumStatsThresholdMu, ccTrapCtrlSumStatsCanBeSetPortal, ccTrapCtrlSumStatsThresholdPortals, 
				ccTrapCtrlSumStatsCanBeSetWlan, ccTrapCtrlSumStatsThresholdWlans, ccTrapCtrlSumStatsCanBeSetSwitch, ccTrapCtrlSumStatsThresholdSwitch, ccTrapCtrlSumStatsMinPktsForTrap, 
				ccTrapCtrlLanVlanActivatedVlanId, ccTrapCtrlDhcpOptionsFileTransferStatusRequested, ccApIndex, ccApNicMac, ccApModelNumber, 
				ccApSerialNumber, ccApPcbRevision, ccApBootLoaderRev, ccApWispVersion, ccApRuntimeFwVersion, 
				ccApNumPortals, ccApPointersToPortals, ccPortalIndex, ccPortalPointerToAp, ccPortalPointersToWlans, 
				ccPortalName, ccPortalLocation, ccPortalOptions, ccPortalMac, ccPortalNumberOfEss, 
				ccPortalNumberOfBss, ccPortalAssociatedMus, ccPortalRadioType, ccPortalChannel, ccPortalTxPowerLevel, 
				ccPortalLastAdoption, ccPortalState, ccPortalBackgroundNoiseNumSamples, ccPortalBackgroundNoiseBest, ccPortalBackgroundNoiseWorst, 
				ccPortalBackgroundNoiseSum, ccPortalBackgroundNoiseSumSquares, ccPortalLastMac, ccPortalLastReason, ccPortalAdoptionIndex, 
				ccPortalAdoptionStartMac, ccPortalAdoptionEndMac, ccPortalAdoptionWlanPointers, ccPortalAdoptionRowStatus, ccPortalSystemStatsBeaconsTx, 
				ccPortalSystemStatsBeaconsTxOctets, ccPortalSystemStatsProbeReqRx, ccPortalSystemStatsProbeReqRxOctets, ccPortalSystemStatsProbeRespRetriesNone, ccPortalSystemStatsProbeRespRetries1, 
				ccPortalSystemStatsProbeRespRetries2, ccPortalSystemStatsProbeRespRetriesFailed, ccPortalSystemStatsProbeRespTxOctets, ccPortalTxPktsUcast, ccPortalRxPktsUcast, 
				ccPortalRxPktsNUcast, ccPortalTxOctetsUcast, ccPortalRxOctetsUcast, ccPortalRxOctetsNUcast, ccPortalRxUndecryptablePkts, 
				ccPortalLastActivity, ccPortalRxPktsAt1Mb, ccPortalRxPktsAt2Mb, ccPortalRxPktsAt5pt5Mb, ccPortalRxPktsAt6Mb, 
				ccPortalRxPktsAt9Mb, ccPortalRxPktsAt11Mb, ccPortalRxPktsAt12Mb, ccPortalRxPktsAt18Mb, ccPortalRxPktsAt22Mb, 
				ccPortalRxPktsAt24Mb, ccPortalRxPktsAt36Mb, ccPortalRxPktsAt48Mb, ccPortalRxPktsAt54Mb, ccPortalTxPktsAt1Mb, 
				ccPortalTxPktsAt2Mb, ccPortalTxPktsAt5pt5Mb, ccPortalTxPktsAt6Mb, ccPortalTxPktsAt9Mb, ccPortalTxPktsAt11Mb, 
				ccPortalTxPktsAt12Mb, ccPortalTxPktsAt18Mb, ccPortalTxPktsAt22Mb, ccPortalTxPktsAt24Mb, ccPortalTxPktsAt36Mb, 
				ccPortalTxPktsAt48Mb, ccPortalTxPktsAt54Mb, ccPortalRxOctetsAt1Mb, ccPortalRxOctetsAt2Mb, ccPortalRxOctetsAt5pt5Mb, 
				ccPortalRxOctetsAt6Mb, ccPortalRxOctetsAt9Mb, ccPortalRxOctetsAt11Mb, ccPortalRxOctetsAt12Mb, ccPortalRxOctetsAt18Mb, 
				ccPortalRxOctetsAt22Mb, ccPortalRxOctetsAt24Mb, ccPortalRxOctetsAt36Mb, ccPortalRxOctetsAt48Mb, ccPortalRxOctetsAt54Mb, 
				ccPortalTxOctetsAt1Mb, ccPortalTxOctetsAt2Mb, ccPortalTxOctetsAt5pt5Mb, ccPortalTxOctetsAt6Mb, ccPortalTxOctetsAt9Mb, 
				ccPortalTxOctetsAt11Mb, ccPortalTxOctetsAt12Mb, ccPortalTxOctetsAt18Mb, ccPortalTxOctetsAt22Mb, ccPortalTxOctetsAt24Mb, 
				ccPortalTxOctetsAt36Mb, ccPortalTxOctetsAt48Mb, ccPortalTxOctetsAt54Mb, ccPortalTxRetriesPktsNone, ccPortalTxRetriesPkts01, 
				ccPortalTxRetriesPkts02, ccPortalTxRetriesPkts03, ccPortalTxRetriesPkts04, ccPortalTxRetriesPkts05, ccPortalTxRetriesPkts06, 
				ccPortalTxRetriesPkts07, ccPortalTxRetriesPkts08, ccPortalTxRetriesPkts09, ccPortalTxRetriesPkts10, ccPortalTxRetriesPkts11, 
				ccPortalTxRetriesPkts12, ccPortalTxRetriesPkts13, ccPortalTxRetriesPkts14, ccPortalTxRetriesPkts15, ccPortalTxRetriesPktsFailed, 
				ccPortalTxRetriesOctetsNone, ccPortalTxRetriesOctets01, ccPortalTxRetriesOctets02, ccPortalTxRetriesOctets03, ccPortalTxRetriesOctets04, 
				ccPortalTxRetriesOctets05, ccPortalTxRetriesOctets06, ccPortalTxRetriesOctets07, ccPortalTxRetriesOctets08, ccPortalTxRetriesOctets09, 
				ccPortalTxRetriesOctets10, ccPortalTxRetriesOctets11, ccPortalTxRetriesOctets12, ccPortalTxRetriesOctets13, ccPortalTxRetriesOctets14, 
				ccPortalTxRetriesOctets15, ccPortalTxRetriesOctetsFailed, ccPortalSigStatsNumPkts, ccPortalSigStatsSignalBest, ccPortalSigStatsSignalWorst, 
				ccPortalSigStatsSignalSum, ccPortalSigStatsSignalSumSquares, ccPortalSigStatsSignalMostRecent, ccPortalSigStatsNoiseBest, ccPortalSigStatsNoiseWorst, 
				ccPortalSigStatsNoiseSum, ccPortalSigStatsNoiseSumSquares, ccPortalSigStatsNoiseMostRecent, ccPortalSigStatsSnrBest, ccPortalSigStatsSnrWorst, 
				ccPortalSigStatsSnrSum, ccPortalSigStatsSnrSumSquares, ccPortalSigStatsSnrMostRecent, ccPortalSumStatsShortTimestamp, ccPortalSumStatsShortNumPkts, 
				ccPortalSumStatsShortPktsPerSec100, ccPortalSumStatsShortPktsPerSecTx100, ccPortalSumStatsShortPktsPerSecRx100, ccPortalSumStatsShortThroughput, ccPortalSumStatsShortThroughputTx, 
				ccPortalSumStatsShortThroughputRx, ccPortalSumStatsShortAvgBitSpeed, ccPortalSumStatsShortAvgMuSignal, ccPortalSumStatsShortAvgMuNoise, ccPortalSumStatsShortAvgMuSnr, 
				ccPortalSumStatsShortPp10kNUcastPkts, ccPortalSumStatsShortPp10kTxWithRetries, ccPortalSumStatsShortTxAvgRetries100, ccPortalSumStatsShortPp10kRxUndecrypt, ccPortalSumStatsShortTotalMus, 
				ccPortalSumStatsShortPp10kRfUtil, ccPortalSumStatsLongTimestamp, ccPortalSumStatsLongNumPkts, ccPortalSumStatsLongPktsPerSec100, ccPortalSumStatsLongPktsPerSecTx100, 
				ccPortalSumStatsLongPktsPerSecRx100, ccPortalSumStatsLongThroughput, ccPortalSumStatsLongThroughputTx, ccPortalSumStatsLongThroughputRx, ccPortalSumStatsLongAvgBitSpeed, 
				ccPortalSumStatsLongAvgMuSignal, ccPortalSumStatsLongAvgMuNoise, ccPortalSumStatsLongAvgMuSnr, ccPortalSumStatsLongPp10kNUcastPkts, ccPortalSumStatsLongPp10kTxWithRetries, 
				ccPortalSumStatsLongTxAvgRetries100, ccPortalSumStatsLongPp10kRxUndecrypt, ccPortalSumStatsLongTotalMus, ccPortalSumStatsLongPp10kRfUtil, ccAssociationFirstAssociate, 
				ccAssociationLastAssociate, ccAssociationCountAssociates, ccMuMac, ccMuWlanIndex, ccMuWlanName, 
				ccMuIsDataReady, ccMuPortalIndex, ccMuPortalMac, ccMuSymbolRogueApEna, ccMuIpAddr, 
				ccMuType, ccMuRadioType, ccMuSupportedRates, ccMuPowerMode, ccMuAuthenticationMethod, 
				ccMuEncryptionMethod, ccMuVlanId, ccMuTxPktsUcast, ccMuRxPktsUcast, ccMuTxOctetsUcast, 
				ccMuRxOctetsUcast, ccMuRxUndecryptablePkts, ccMuRxRssiNumPkts, ccMuRxRssiSum, ccMuRxRssiSumSquares, 
				ccMuRxRssiMostRecent, ccMuLastActivity, ccMuRxPktsAt1Mb, ccMuRxPktsAt2Mb, ccMuRxPktsAt5pt5Mb, 
				ccMuRxPktsAt6Mb, ccMuRxPktsAt9Mb, ccMuRxPktsAt11Mb, ccMuRxPktsAt12Mb, ccMuRxPktsAt18Mb, 
				ccMuRxPktsAt22Mb, ccMuRxPktsAt24Mb, ccMuRxPktsAt36Mb, ccMuRxPktsAt48Mb, ccMuRxPktsAt54Mb, 
				ccMuTxPktsAt1Mb, ccMuTxPktsAt2Mb, ccMuTxPktsAt5pt5Mb, ccMuTxPktsAt6Mb, ccMuTxPktsAt9Mb, 
				ccMuTxPktsAt11Mb, ccMuTxPktsAt12Mb, ccMuTxPktsAt18Mb, ccMuTxPktsAt22Mb, ccMuTxPktsAt24Mb, 
				ccMuTxPktsAt36Mb, ccMuTxPktsAt48Mb, ccMuTxPktsAt54Mb, ccMuRxOctetsAt1Mb, ccMuRxOctetsAt2Mb, 
				ccMuRxOctetsAt5pt5Mb, ccMuRxOctetsAt6Mb, ccMuRxOctetsAt9Mb, ccMuRxOctetsAt11Mb, ccMuRxOctetsAt12Mb, 
				ccMuRxOctetsAt18Mb, ccMuRxOctetsAt22Mb, ccMuRxOctetsAt24Mb, ccMuRxOctetsAt36Mb, ccMuRxOctetsAt48Mb, 
				ccMuRxOctetsAt54Mb, ccMuTxOctetsAt1Mb, ccMuTxOctetsAt2Mb, ccMuTxOctetsAt5pt5Mb, ccMuTxOctetsAt6Mb, 
				ccMuTxOctetsAt9Mb, ccMuTxOctetsAt11Mb, ccMuTxOctetsAt12Mb, ccMuTxOctetsAt18Mb, ccMuTxOctetsAt22Mb, 
				ccMuTxOctetsAt24Mb, ccMuTxOctetsAt36Mb, ccMuTxOctetsAt48Mb, ccMuTxOctetsAt54Mb, ccMuTxRetriesNone, 
				ccMuTxRetries01, ccMuTxRetries02, ccMuTxRetries03, ccMuTxRetries04, ccMuTxRetries05, 
				ccMuTxRetries06, ccMuTxRetries07, ccMuTxRetries08, ccMuTxRetries09, ccMuTxRetries10, 
				ccMuTxRetries11, ccMuTxRetries12, ccMuTxRetries13, ccMuTxRetries14, ccMuTxRetries15, 
				ccMuTxRetriesFailed, ccMuTxRetriesTotal, ccMuTxRetriesMostRecent, ccMuLastMac, ccMuLastReason, 
				ccMuLastPortal, ccMuTxRetriesOctetsNone, ccMuTxRetriesOctets01, ccMuTxRetriesOctets02, ccMuTxRetriesOctets03, 
				ccMuTxRetriesOctets04, ccMuTxRetriesOctets05, ccMuTxRetriesOctets06, ccMuTxRetriesOctets07, ccMuTxRetriesOctets08, 
				ccMuTxRetriesOctets09, ccMuTxRetriesOctets10, ccMuTxRetriesOctets11, ccMuTxRetriesOctets12, ccMuTxRetriesOctets13, 
				ccMuTxRetriesOctets14, ccMuTxRetriesOctets15, ccMuTxRetriesOctetsFailed, ccMuSigStatsNumPkts, ccMuSigStatsSignalBest, 
				ccMuSigStatsSignalWorst, ccMuSigStatsSignalSum, ccMuSigStatsSignalSumSquares, ccMuSigStatsSignalMostRecent, ccMuSigStatsNoiseBest, 
				ccMuSigStatsNoiseWorst, ccMuSigStatsNoiseSum, ccMuSigStatsNoiseSumSquares, ccMuSigStatsNoiseMostRecent, ccMuSigStatsSnrBest, 
				ccMuSigStatsSnrWorst, ccMuSigStatsSnrSum, ccMuSigStatsSnrSumSquares, ccMuSigStatsSnrMostRecent, ccMuSumStatsShortTimestamp, 
				ccMuSumStatsShortNumPkts, ccMuSumStatsShortPktsPerSec100, ccMuSumStatsShortPktsPerSecTx100, ccMuSumStatsShortPktsPerSecRx100, ccMuSumStatsShortThroughput, 
				ccMuSumStatsShortThroughputTx, ccMuSumStatsShortThroughputRx, ccMuSumStatsShortAvgBitSpeed, ccMuSumStatsShortAvgMuSignal, ccMuSumStatsShortAvgMuNoise, 
				ccMuSumStatsShortAvgMuSnr, ccMuSumStatsShortPp10kNUcastPkts, ccMuSumStatsShortPp10kTxWithRetries, ccMuSumStatsShortTxAvgRetries100, ccMuSumStatsShortPp10kRxUndecrypt, 
				ccMuSumStatsLongTimestamp, ccMuSumStatsLongNumPkts, ccMuSumStatsLongPktsPerSec100, ccMuSumStatsLongPktsPerSecTx100, ccMuSumStatsLongPktsPerSecRx100, 
				ccMuSumStatsLongThroughput, ccMuSumStatsLongThroughputTx, ccMuSumStatsLongThroughputRx, ccMuSumStatsLongAvgBitSpeed, ccMuSumStatsLongAvgMuSignal, 
				ccMuSumStatsLongAvgMuNoise, ccMuSumStatsLongAvgMuSnr, ccMuSumStatsLongPp10kNUcastPkts, ccMuSumStatsLongPp10kTxWithRetries, ccMuSumStatsLongTxAvgRetries100, 
				ccMuSumStatsLongPp10kRxUndecrypt, ccWlanIndex, ccWlanName, ccWlanEssid, ccWlanSubnet, 
				ccWlanPortalsAdopted, ccWlanEnable, ccWlanDisallowMuToMu, ccWlanVoicePrioritization, ccWlanAnswerBroadcastEss, 
				ccWlanMulticastAddr1, ccWlanMulticastAddr2, ccWlanMuAclDefault, ccWlanAuthentication, ccWlanEncryption, 
				ccWlanWeight, ccWlanAuthEapReauthenticationEnable, ccWlanAuthEapReauthenticationPeriod, ccWlanAuthEapReauthenticationMaxRetries, ccWlanAuthEapRadius1Server, 
				ccWlanAuthEapRadius1Port, ccWlanAuthEapRadius1SharedSecret, ccWlanAuthEapRadius2Server, ccWlanAuthEapRadius2Port, ccWlanAuthEapRadius2SharedSecret, 
				ccWlanAuthEapMuQuietPeriod, ccWlanAuthEapMuTimeout, ccWlanAuthEapMuTxPeriod, ccWlanAuthEapMuMaxRetries, ccWlanAuthEapServerTimeout, 
				ccWlanAuthEapServerMaxRetries, ccWlanAuthKerberosRealmName, ccWlanAuthKerberosUsername, ccWlanAuthKerberosPassword, ccWlanAuthKerberosKdcServerIp1, 
				ccWlanAuthKerberosKdcPort1, ccWlanAuthKerberosKdcServerIp2, ccWlanAuthKerberosKdcPort2, ccWlanAuthKerberosKdcServerIpR, ccWlanAuthKerberosKdcPortR, 
				ccWlanCryptoWepPassKey, ccWlanCryptoWepKey1, ccWlanCryptoWepKey2, ccWlanCryptoWepKey3, ccWlanCryptoWepKey4, 
				ccWlanCryptoWepKeyToUse, ccWlanCryptoWpaBcastKeyRotation, ccWlanCryptoWpaKeyRotationInterval, ccWlanCryptoWpaKeyToUse, ccWlanCryptoWpaPassphrase, 
				ccWlanCryptoWpaKey, ccWlanCryptoKeyguardPasskey, ccWlanCryptoKeyguardKey1, ccWlanCryptoKeyguardKey2, ccWlanCryptoKeyguardKey3, 
				ccWlanCryptoKeyguardKey4, ccWlanCryptoKeyguardKeyToUse, ccWlanMuAclIndex, ccWlanMuAclStartingMac, ccWlanMuAclEndingMac, 
				ccWlanMuAclRowStatus, ccWlanBwShareMode, ccWlanTxPktsUcast, ccWlanRxPktsUcast, ccWlanRxPktsNUcast, 
				ccWlanTxOctetsUcast, ccWlanRxOctetsUcast, ccWlanRxOctetsNUcast, ccWlanRxUndecryptablePkts, ccWlanLastActivity, 
				ccWlanRxPktsAt1Mb, ccWlanRxPktsAt2Mb, ccWlanRxPktsAt5pt5Mb, ccWlanRxPktsAt6Mb, ccWlanRxPktsAt9Mb, 
				ccWlanRxPktsAt11Mb, ccWlanRxPktsAt12Mb, ccWlanRxPktsAt18Mb, ccWlanRxPktsAt22Mb, ccWlanRxPktsAt24Mb, 
				ccWlanRxPktsAt36Mb, ccWlanRxPktsAt48Mb, ccWlanRxPktsAt54Mb, ccWlanTxPktsAt1Mb, ccWlanTxPktsAt2Mb, 
				ccWlanTxPktsAt5pt5Mb, ccWlanTxPktsAt6Mb, ccWlanTxPktsAt9Mb, ccWlanTxPktsAt11Mb, ccWlanTxPktsAt12Mb, 
				ccWlanTxPktsAt18Mb, ccWlanTxPktsAt22Mb, ccWlanTxPktsAt24Mb, ccWlanTxPktsAt36Mb, ccWlanTxPktsAt48Mb, 
				ccWlanTxPktsAt54Mb, ccWlanRxOctetsAt1Mb, ccWlanRxOctetsAt2Mb, ccWlanRxOctetsAt5pt5Mb, ccWlanRxOctetsAt6Mb, 
				ccWlanRxOctetsAt9Mb, ccWlanRxOctetsAt11Mb, ccWlanRxOctetsAt12Mb, ccWlanRxOctetsAt18Mb, ccWlanRxOctetsAt22Mb, 
				ccWlanRxOctetsAt24Mb, ccWlanRxOctetsAt36Mb, ccWlanRxOctetsAt48Mb, ccWlanRxOctetsAt54Mb, ccWlanTxOctetsAt1Mb, 
				ccWlanTxOctetsAt2Mb, ccWlanTxOctetsAt5pt5Mb, ccWlanTxOctetsAt6Mb, ccWlanTxOctetsAt9Mb, ccWlanTxOctetsAt11Mb, 
				ccWlanTxOctetsAt12Mb, ccWlanTxOctetsAt18Mb, ccWlanTxOctetsAt22Mb, ccWlanTxOctetsAt24Mb, ccWlanTxOctetsAt36Mb, 
				ccWlanTxOctetsAt48Mb, ccWlanTxOctetsAt54Mb, ccWlanTxRetriesPktsNone, ccWlanTxRetriesPkts01, ccWlanTxRetriesPkts02, 
				ccWlanTxRetriesPkts03, ccWlanTxRetriesPkts04, ccWlanTxRetriesPkts05, ccWlanTxRetriesPkts06, ccWlanTxRetriesPkts07, 
				ccWlanTxRetriesPkts08, ccWlanTxRetriesPkts09, ccWlanTxRetriesPkts10, ccWlanTxRetriesPkts11, ccWlanTxRetriesPkts12, 
				ccWlanTxRetriesPkts13, ccWlanTxRetriesPkts14, ccWlanTxRetriesPkts15, ccWlanTxRetriesPktsFailed, ccWlanTxRetriesOctetsNone, 
				ccWlanTxRetriesOctets01, ccWlanTxRetriesOctets02, ccWlanTxRetriesOctets03, ccWlanTxRetriesOctets04, ccWlanTxRetriesOctets05, 
				ccWlanTxRetriesOctets06, ccWlanTxRetriesOctets07, ccWlanTxRetriesOctets08, ccWlanTxRetriesOctets09, ccWlanTxRetriesOctets10, 
				ccWlanTxRetriesOctets11, ccWlanTxRetriesOctets12, ccWlanTxRetriesOctets13, ccWlanTxRetriesOctets14, ccWlanTxRetriesOctets15, 
				ccWlanTxRetriesOctetsFailed, ccWlanSigStatsNumPkts, ccWlanSigStatsSignalBest, ccWlanSigStatsSignalWorst, ccWlanSigStatsSignalSum, 
				ccWlanSigStatsSignalSumSquares, ccWlanSigStatsNoiseBest, ccWlanSigStatsNoiseWorst, ccWlanSigStatsNoiseSum, ccWlanSigStatsNoiseSumSquares, 
				ccWlanSigStatsSnrBest, ccWlanSigStatsSnrWorst, ccWlanSigStatsSnrSum, ccWlanSigStatsSnrSumSquares, ccWlanSumStatsShortTimestamp, 
				ccWlanSumStatsShortNumPkts, ccWlanSumStatsShortPktsPerSec100, ccWlanSumStatsShortPktsPerSecTx100, ccWlanSumStatsShortPktsPerSecRx100, ccWlanSumStatsShortThroughput, 
				ccWlanSumStatsShortThroughputTx, ccWlanSumStatsShortThroughputRx, ccWlanSumStatsShortAvgBitSpeed, ccWlanSumStatsShortAvgMuSignal, ccWlanSumStatsShortAvgMuNoise, 
				ccWlanSumStatsShortAvgMuSnr, ccWlanSumStatsShortPp10kNUcastPkts, ccWlanSumStatsShortPp10kTxWithRetries, ccWlanSumStatsShortTxAvgRetries100, ccWlanSumStatsShortPp10kRxUndecrypt, 
				ccWlanSumStatsShortTotalMus, ccWlanSumStatsLongTimestamp, ccWlanSumStatsLongNumPkts, ccWlanSumStatsLongPktsPerSec100, ccWlanSumStatsLongPktsPerSecTx100, 
				ccWlanSumStatsLongPktsPerSecRx100, ccWlanSumStatsLongThroughput, ccWlanSumStatsLongThroughputTx, ccWlanSumStatsLongThroughputRx, ccWlanSumStatsLongAvgBitSpeed, 
				ccWlanSumStatsLongAvgMuSignal, ccWlanSumStatsLongAvgMuNoise, ccWlanSumStatsLongAvgMuSnr, ccWlanSumStatsLongPp10kNUcastPkts, ccWlanSumStatsLongPp10kTxWithRetries, 
				ccWlanSumStatsLongTxAvgRetries100, ccWlanSumStatsLongPp10kRxUndecrypt, ccWlanSumStatsLongTotalMus, ccWanIndex, ccWanDhcpEnable, 
				ccWanDhcpIpAddr, ccWanDhcpSubnetMask, ccWanDhcpDefaultGateway, ccWanDhcpPrimaryDnsServer, ccWanDhcpSecondaryDnsServer, 
				ccWanSubnetMask, ccWanDefaultGateway, ccWanPrimaryDnsServer, ccWanSecondaryDnsServer, ccWanPppoeEnable, 
				ccWanPppoeUsername, ccWanPppoePassword, ccWanPppoeKeepAlive, ccWanPppoeIdleTime, ccWanPppoeAuthType, 
				ccWanIpAddrIndex, ccWanIpAddrEnable, ccWanIpAddr, ccWanFirewallGlobalEnable, ccWanFirewallIndex, 
				ccWanFirewallDescription, ccWanFirewallAlwaysEnabled, ccWanFirewallEnable, ccWanFirewallMimeFloodMaxHeaderLength, ccWanFirewallMimeFloodMaxHeaders, 
				ccWanNatIndex, ccWanNatWanIpAddress, ccWanNatType, ccWanNat1to1IpAddr, ccWanNatInboundDefaultEna, 
				ccWanNatInboundDefaultIp, ccWanNatInboundIndex, ccWanNatInboundName, ccWanNatInboundTransport, ccWanNatInboundStartPort, 
				ccWanNatInboundEndPort, ccWanNatInboundIpAddr, ccWanNatInboundRowStatus, ccWanNatOutboundSubnetIndex, ccWanNatOutboundPossibleIpAddr, 
				ccWanNatOutboundIpAddr, ccWanVpnName, ccWanVpnLocalSubnet, ccWanVpnLocalWanIp, ccWanVpnRemoteSubnet, 
				ccWanVpnRemoteSubnetMask, ccWanVpnRemoteGateway, ccWanVpnKeyExchange, ccWanVpnRowStatus, ccWanVpnKeyManualAhAuth, 
				ccWanVpnKeyManualInAhAuthKey, ccWanVpnKeyManualOutAhAuthKey, ccWanVpnKeyManualInAhSpi, ccWanVpnKeyManualOutAhSpi, ccWanVpnKeyManualEspType, 
				ccWanVpnKeyManualEspEncrypAlg, ccWanVpnKeyManualInEspEncrypKey, ccWanVpnKeyManualOutEspEncrypKey, ccWanVpnKeyManualEspAuthAlg, ccWanVpnKeyManualInEspAuthKey, 
				ccWanVpnKeyManualOutEspAuthKey, ccWanVpnKeyManualInEspSpi, ccWanVpnKeyManualOutEspSpi, ccWanVpnKeyAutoUsePerfectSecrecy, ccWanVpnKeyAutoAhAuth, 
				ccWanVpnKeyAutoEspType, ccWanVpnKeyAutoEspEncrypAlg, ccWanVpnKeyAutoEspAuthAlg, ccWanVpnKeyAutoIkeOperationMode, ccWanVpnKeyAutoIkeLocalIdType, 
				ccWanVpnKeyAutoIkeLocalIdData, ccWanVpnKeyAutoIkeRemoteIdType, ccWanVpnKeyAutoIkeRemoteIdData, ccWanVpnKeyAutoIkeAuthAlg, ccWanVpnKeyAutoIkeAuthPassphrase, 
				ccWanVpnKeyAutoIkeEncrypAlg, ccWanVpnKeyAutoIkeXauthMode, ccWanVpnKeyAutoIkeXauthUsername, ccWanVpnKeyAutoIkeXauthPassword, ccWanVpnKeyAutoIkeKeyLifetime, 
				ccWanVpnKeyAutoIkeDiffieHelmanGroup, ccWanVpnSaTunnelName, ccWanVpnSaStatus, ccWanVpnSaInSpi, ccWanVpnSaOutSpi, 
				ccWanVpnSaLifetime, ccWanVpnSaTxBytes, ccWanVpnSaRxBytes, ccWanVpnIkeTunnelName, ccWanVpnIkeState, 
				ccWanVpnIkeRemainingLife, ccWanContentBlockSmtp, ccWanContentBlockFtp, ccWanContentBlockHttp, ccWanContentBlockOutUrlIndex, 
				ccWanContentBlockOutUrlExtension, ccWanContentBlockOutUrlRowStatus, ccPortIndex, ccPortType, ccPortPoeEquipped, 
				ccPortStatus, ccPortDuplex, ccPortSpeed, ccSubnetIndex, ccSubnetEnable, 
				ccSubnetName, ccSubnetIpAddress, ccSubnetIpSubnetMask, ccSubnetPortMembers, ccSubnetWlanMembers, 
				ccSubnetDhcpState, ccSubnetDhcpIpAddress, ccSubnetDhcpSubnetMask, ccSubnetDhcpServerEnable, ccSubnetDhcpServerPoolStart, 
				ccSubnetDhcpServerPoolEnd, ccSubnetDhcpServerPrimaryDns, ccSubnetDhcpServerSecondaryDns, ccSubnetDhcpServerDefaultGateway, ccSubnetDhcpServerLeaseTime, 
				ccSubnetDhcpServerStaticMapMac, ccSubnetDhcpServerStaticMapIpAddr, ccSubnetDhcpServerStaticMapEnable, ccSubnetAccessDestIndex, ccSubnetAccessRuleIndex, 
				ccSubnetAccessDestType, ccSubnetAccessDestPtrToDest, ccSubnetAccessRuleName, ccSubnetAccessRuleType, ccSubnetAccessAdvInIndex, 
				ccLanVlanType, ccLanVlanTrunkPort, ccLanVlanDefaultTag, ccLanVlanTrunked, ccLanVlanId, 
				ccRouterRipType, ccRouterRipDirection, ccRouterRip2AuthType, ccRouterRip2SimplePassword, ccRouterRip2Md5Key1Id, 
				ccRouterRip2Md5Key1AuthKey, ccRouterRip2Md5Key2Id, ccRouterRip2Md5Key2AuthKey, ccRouterRoutesIndex, ccRouterRoutesDest, 
				ccRouterRoutesDestMask, ccRouterRoutesGateway, ccRouterRoutesInterface, ccRouterRoutesMetric, ccRouterUserRoutesIndex, 
				ccRouterUserRoutesDest, ccRouterUserRoutesDestMask, ccRouterUserRoutesGateway, ccRouterUserRoutesInterface, ccRouterUserRoutesMetric, 
				ccRouterUserRoutesRowStatus, ccRapPollSymbolMusEnable, ccRapPollSymbolMusInterval, ccRapOnChannelEnable, ccRapOnChannelInterval, 
				ccRapDetectorsEnable, ccRapDetectorsInterval, ccRapAuthAllSymbolMac, ccRapAuthIndex, ccRapAuthMacFilter, 
				ccRapAuthEssidFilter, ccRapAuthRowExists, ccRapAuthErase, ccRapAuthCopyAllApproved, ccRapResultsApprovedAgeOut, 
				ccRapResultsApprovedApMac, ccRapResultsApprovedEssid, ccRapResultsApprovedCopyToAuthTable, ccRapResultsApprovedFirstHeard, ccRapResultsApprovedLastHeard, 
				ccRapResultsApprovedPortalPtr, ccRapResultsApprovedHowFound, ccRapResultsApprovedHowAuth, ccRapResultsApprovedErase, ccRapResultsRogueAgeOut, 
				ccRapResultsRogueApMac, ccRapResultsRogueEssid, ccRapResultsRogueCopyToAuthTable, ccRapResultsRogueFirstHeard, ccRapResultsRogueLastHeard, 
				ccRapResultsRoguePortalPtr, ccRapResultsRogueHowFound, ccRapResultsRogueClosestPortalPtr, ccRapResultsRogueClosestPortalRssi, ccRapResultsRogueErase, 
				ccRapPortalResultsApMac, ccRapPortalResultsApEssid, ccRapPortalResultsInProcess, ccRapPortalResultsPortalMac, ccRapPortalResultsRssi, 
				ccRapPollOneMuMac, ccRapPollOneMuInProcess, ccRapPollOneMuStatus, ccRapPollOneMuResultsIndex, ccRapPollOneMuResultsRssi, 
				ccRapPollOneMuResultsEssid, ccRapPollOneMuResultsApMac, ccRadiusDataSource, ccRadiusDefaultEapType, ccRadiusClientAuthIndex, 
				ccRadiusClientAuthIpAddr, ccRadiusClientAuthMask, ccRadiusClientAuthSharedSecret, ccRadiusProxyRetryCount, ccRadiusProxyTimeout, 
				ccRadiusProxyServerIndex, ccRadiusProxyServerIp, ccRadiusProxyServerPort, ccRadiusProxyServerSharedSecret, ccRadiusLdapServerIp, 
				ccRadiusLdapServerPort, ccRadiusLdapLoginAttribute, ccRadiusLdapPasswordAttribute, ccRadiusLdapBindDistinguishedName, ccRadiusLdapBindDistinguishedPassword, 
				ccRadiusLdapBaseDistinguishedName, ccRadiusLdapGroupAttribute, ccRadiusLdapGroupFilter, ccRadiusLdapGroupMembershipAttribute, ccRadiusUsersId, 
				ccRadiusUsersPassword, ccRadiusUsersGroups, ccRadiusUsersRowStatus, ccNtpCurrentDateTime, ccRadiusAuthTypePeap, 
				ccRadiusAuthTypeTtls, ccRadiusClientAuthRowStatus, ccRadiusProxyServerPrefixOrSuffix, ccSubnetAccessAdvInSrcIp, ccSubnetAccessAdvInSrcIpLength, 
				ccSubnetAccessAdvInDestIp, ccSubnetAccessAdvInDestIpLength, ccSubnetAccessAdvInTransport, ccSubnetAccessAdvInSrcPortStart, ccSubnetAccessAdvInSrcPortEnd, 
				ccSubnetAccessAdvInDestPortStart, ccSubnetAccessAdvInDestPortEnd, ccSubnetAccessAdvInAction, ccSubnetAccessAdvInRowStatus, ccSubnetAccessAdvOutIndex, 
				ccSubnetAccessAdvOutSrcIp, ccSubnetAccessAdvOutSrcIpLength, ccSubnetAccessAdvOutDestIp, ccSubnetAccessAdvOutDestIpLength, ccSubnetAccessAdvOutTransport, 
				ccSubnetAccessAdvOutSrcPortStart, ccSubnetAccessAdvOutSrcPortEnd, ccSubnetAccessAdvOutDestPortStart, ccSubnetAccessAdvOutDestPortEnd, ccSubnetAccessAdvOutReverseNat, 
				ccSubnetAccessAdvOutAction, ccTrapCtrlRedundancyPreviousOperState, ccSubnetAccessAdvOutRowStatus, ccWanNatLowestUnusedSlot, ccSubnetAccessPtrToRules, 
				ccSubnetAccessRuleSrcPtr, ccSubnetAccessRuleDestPtr, ccSubnetAccessRuleTransport, ccSubnetAccessRuleStartPort, ccSubnetAccessRuleEndPort, 
				ccSubnetAccessRuleRowStatus, ccTrapCtrlEnableIndex, ccTrapCtrlEnableName, ccTrapCtrlEnable, ccWlanQosMonitorSent, 
				ccWlanQosMonitorDropped, ccWlanSumStatsShortPp10kDropped, ccRadiusProxyServerRowStatus, ccWanVpnIndex, ccWanNatOutboundEnable, 
				ccRapResultsApprovedIndex, ccRapResultsRogueIndex, ccWlanSumStatsLongPp10kDropped, ccSnmpAccessV3User, ccSnmpV3EngineId, 
				ccCertMgntSelfCertsReqIndex, ccCertMgntSelfCertsReqKeyId, ccCertMgntSelfCertsReqSubject, ccCertMgntSelfCertsReqDept, ccCertMgntSelfCertsReqOrg, 
				ccCertMgntSelfCertsReqCity, ccCertMgntSelfCertsReqState, ccCertMgntSelfCertsReqPostal, ccCertMgntSelfCertsReqCountry, ccCertMgntSelfCertsReqEmail, 
				ccCertMgntSelfCertsReqDomain, ccCertMgntSelfCertsReqIp, ccCertMgntSelfCertsReqSigAlgo, ccCertMgntSelfCertsReqKeyLen, ccCertMgntSelfCertsReqGenReq, 
				ccCertMgntSelfCertsReqCertReqStr, ccCertMgntSelfCertsReqRowStatus, ccCertMgntSelfCertsSignedStr, ccCertMgntSelfCertsSignedImport, ccCertMgntSelfCertsSignedIndex, 
				ccCertMgntSelfCertsSignedKeyId, ccCertMgntSelfCertsSignedIssuerName, ccCertMgntSelfCertsSignedSubject, ccCertMgntSelfCertsSignedSerialNumber, ccCertMgntSelfCertsSignedExpiry, 
				ccCertMgntSelfCertsSignedDeleteRow, ccCACertsStr, ccCACertsImport, ccCACertsIndex, ccCACertsKeyId, 
				ccCACertsIssuerName, ccCACertsSubject, ccCACertsSerialNumber, ccCACertsExpiry, ccCACertsDeleteRow, 
				ccPortalSettingsName, ccPortalSettingsLocation, ccPortalSettingsAntenna, ccPortalSettingsShortPreamble, ccPortalSettingsUniSpread, 
				ccPortalSettingsRtsThresh, ccPortalSettingsBeaconInt, ccPortalSettingsDtimPrd, ccPortalSettingsSecBeacon, ccPortalSettingsPriWlan, 
				ccPortalSettingsBasicRates, ccPortalSettingsSupportedRates, ccPortalSettingsBGMode, ccPortalSettingsAdoptedWlan, ccPortalCfgRadioDesPlacement, 
				ccPortalCfgRadioPosChannel, ccPortalCfgRadioDesChannel, ccPortalCfgRadioPosPowerLevel, ccPortalCfgRadioDesPowerLevel, ccPortalCfgRadioPowerInMW, 
				ccPortalCfgRadioSet, ccPortalCfgRadioReset, ccPortalCfgRadioPlacement, ccPortalCfgRadioChannel, ccPortalCfgRadioPowerLevel, 
				ccPortalSettingsDefaultAntenna, ccPortalSettingsDefaultShortPreamble, ccPortalSettingsDefaultUniSpread, ccPortalSettingsDefaultRtsThresh, ccPortalSettingsDefaultBeaconInt, 
				ccPortalSettingsDefaultDtimPrd, ccPortalSettingsDefaultSecBeacon, ccPortalSettingsDefaultPriWlan, ccPortalSettingsDefaultBasicRates, ccPortalSettingsDefaultSupportedRates, 
				ccPortalSettingsDefaultBGMode, ccPortalCfgRadioDefaultDesPlacement, ccPortalCfgRadioDefaultPosChannel, ccPortalCfgRadioDefaultDesChannel, ccPortalCfgRadioDefaultPosPowerLevel, 
				ccPortalCfgRadioDefaultDesPowerLevel, ccPortalCfgRadioDefaultSet, ccPortalCfgRadioDefaultReset, ccPortalCfgRadioDefaultPlacement, ccPortalCfgRadioDefaultChannel, 
				ccPortalCfgRadioDefaultPowerLevel, cc802dt1xPortAuthLogin, cc802dt1xPortAuthPass, cc802dt1xPortAuthSetAp300, ccPortalSettingsDefaultIndex, 
				ccRapPortalResultsIndex, ccRapAuthCopyAllRogue, ccPortalSettingsDetector, ccRedundancyHeartbeatInterface, ccRadiusCACertificate, 
				ccRadiusServerCertificate, ccSubnetDhcpServerDomainName, ccSubnetDhcpServerWinsServer, ccCertMgntSelfCertsIdName, ccPortalSystemStatsProbeRespRetries3OrMore, 
				ccPortalSumStatsLongPp10kTxMaxRetries, ccWlanCryptoWpaTwoFastRoamKeyCache, ccWlanCryptoWpaTwoFastRoamPreAuth, ccWlanCryptoWpaTwoAllowTkipClient, ccWlanCryptoWpaTwoKey, 
				ccWlanCryptoWpaTwoPassphrase, ccWlanCryptoWpaTwoKeyToUse, ccWlanCryptoWpaTwoKeyRotationInterval, ccWlanCryptoWpaTwoBcastKeyRotation, ccSubnetAccessAdvOverrideMode, 
				ccSubnetAccessAdvImportRules, ccWlanAuthEapSyslogMode, ccWlanAuthEapSyslogSeverIp, ccMgmtAccessHttpsTimeout, ccNtpSyncInterval, 
				ccWanNatTimeout, ccLoggingDeleteCoreFile, ccLoggingTransferCoreFile, ccWlanAuthEapRadiusAcctMuRetries, ccWanVpnKeyAutoIkeAuthType, 
				ccWanNatInboundTranslationPort, ccRedundancyOperMode, ccRapResultsApprovedChannel, ccRapResultsRogueChannel, ccPortalCfgRadioDefaultDesPowerInMW, 
				ccPortalCfgRadioDesPowerInMW, ccPortalCfgRadioDefaultPowerInMW, ccWlanAuthEapRadiusAcctMode, ccWlanAuthEapRadiusAcctMuTimeout, ccSubnetAccessAdvInReverseNatIp, 
				ccSubnetAccessAdvInReverseNatPort }
			STATUS current
			DESCRIPTION 
				"Description."
			::= { ccGroupsV2dot0 1 }

		
		-- 1.3.6.1.4.1.388.11.2.1000.3.2
		ccGroupsV2dot0obsoleted OBJECT-GROUP
			OBJECTS { ccWlanSumStatsShortSkip1, ccWlanSumStatsLongSkip1, ccRadiusAccessWlanPtrs, ccRadiusUsersGroup, ccRadiusUsersGroupRowStatus, 
				ccRadiusUsersGroupId }
			STATUS obsolete
			DESCRIPTION 
				"Description."
			::= { ccGroupsV2dot0 2 }

		
		-- 1.3.6.1.4.1.388.11.2.1000.3.3
		ccGroupsV2dot0notifications NOTIFICATION-GROUP
			NOTIFICATIONS { ccPortalAdopted, ccPortalUnAdopted, ccPortalDenied, ccMuAssociated, ccMuUnAssociated, 
				ccMuDenied, ccConfigChange, ccSnmpAclViolation, ccPortStatusChange, ccCfAlmostFull, 
				ccFirewallUnderAttack, ccRadarDetected, ccSumStatsMu, ccSumStatsPortal, ccSumStatsWlan, 
				ccSumStatsSwitch, ccLanVlanActivated, ccDhcpOptionsFileTransferStatus, ccRapNewApprovedAp, ccRapNewRogueAp, 
				ccRedundancyStateChange }
			STATUS current
			DESCRIPTION 
				"Description."
			::= { ccGroupsV2dot0 3 }

		
	
	END

--
-- SYMBOL-CC-WS2000-MIB-2.0.mib
--
