--
-- 	Copyright 1995, 1996 Shiva Corporation
--

--
--	Shiva Nortel-Specific MIB
--

SHIVA-NORTEL-SMI DEFINITIONS ::= BEGIN

IMPORTS
	nortelSpecific
		FROM SHIVA-MIB;


    inc		OBJECT IDENTIFIER ::= { nortelSpecific 1 }
END
