--
-- Copyright 1996, 1997, 1998 Shiva Corporation
--
-- Conformance statements for Shiva LanRover/E, LanRover/T, LanRover/E PLUS,
-- LanRover/T PLUS, and LanRover/E XP16.
--

-- These conformance statements note what IETF MIBs, defined in the
-- SNMPv2-SMI syntax are implemented, are implemented.
-- The agent itself is an SNMPv1 agent.

SHIVA-LANROVER-CAP DEFINITIONS ::= BEGIN

IMPORTS
    MODULE-IDENTITY
       FROM SNMPv2-SMI
    AGENT-CAPABILITIES
        FROM SNMPv2-CONF
    conformance
        FROM SHIVA-MIB;

shivaLanRoverCapabilities MODULE-IDENTITY
    LAST-UPDATED	"9811061830Z"
    ORGANIZATION	"Shiva Corporation"
    CONTACT-INFO	"Shiva Corporation
			28 Crosby Drive
			Bedford, MA  01730"
    DESCRIPTION		"The Shiva LanRover/E, LanRover/E PLUS,
			LanRover/E XP16, LanRover/T, and LanRover/T PLUS
			Agent Capabilities module."
    REVISION		"9811061830Z"
    DESCRIPTION		"The first revision of this module with
			MODULE-IDENTITY."
    REVISION		"9811232145Z"
    DESCRIPTION		"Added ShivOS 5.1.  Fine-tuned the platform-
			specific stuff and platform names."
    ::= { conformance 3 }

shivaLanRoverAgent45 AGENT-CAPABILITIES
    PRODUCT-RELEASE	"LanRover/E, LanRover/E PLUS,
			LanRover/T, and LanRover/T PLUS 4.5"
    STATUS		current
    DESCRIPTION		"SNMP Agent in LanRover ShivOS 4.5 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover/E and LanRover/E PLUS

    SUPPORTS		EtherLike-MIB	-- RFC 1650
	INCLUDES	{ etherStatsGroup, etherCollisionTableGroup }


    -- RS-232-MIB supported for all serial ports.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    SUPPORTS		RIPv2-MIB	-- RFC 1724
	INCLUDES	{ rip2GlobalGroup, rip2IfStatGroup,
			  rip2IfConfGroup }
	
	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
			    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMegiaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover/T
--		and LanRover/T PLUS.
--		Variables dot5Commands, dot5RingSpeed, dot5ActMonParticipate,
--		and dot5FunctionalAddress read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
-- RFC 1473	PPP-IPCP-MIB.  Instantiated for each PPP Multilink bundle.
--		Variables pppIpConfigAdminStatus and pppIpConfigCompression
--		are read-only (inconsistent with configuration model).

  ::= { shivaLanRoverCapabilities 450 }

shivaLanRoverAgent50 AGENT-CAPABILITIES
    PRODUCT-RELEASE	"LanRover/E, LanRover/E PLUS,
			LanRover/T, and LanRover/T PLUS 5.0"
    STATUS		current
    DESCRIPTION		"SNMP Agent in LanRover ShivOS 5.0 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover/E and LanRover/E PLUS

    SUPPORTS		EtherLike-MIB	-- RFC 1650
	INCLUDES	{ etherStatsGroup, etherCollisionTableGroup }


    -- RS-232-MIB supported for all serial ports.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    SUPPORTS		RIPv2-MIB	-- RFC 1724
	INCLUDES	{ rip2GlobalGroup, rip2IfStatGroup,
			  rip2IfConfGroup }
	
	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
			    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMegiaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover/T
--		and LanRover/T PLUS.
--		Variables dot5Commands, dot5RingSpeed, dot5ActMonParticipate,
--		and dot5FunctionalAddress read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
-- RFC 1473	PPP-IPCP-MIB.  Instantiated for each PPP Multilink bundle.
--		Variables pppIpConfigAdminStatus and pppIpConfigCompression
--		are read-only (inconsistent with configuration model).

    ::= { shivaLanRoverCapabilities 500 }

shivaLanRoverAgent57 AGENT-CAPABILITIES
    PRODUCT-RELEASE	"LanRover/E, LanRover/E PLUS,
			LanRover/T, and LanRover/T PLUS 5.7"
    STATUS		current
    DESCRIPTION		"SNMP Agent in LanRover ShivOS 5.7 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB supported only on LanRover/E and LanRover/E PLUS

    SUPPORTS		EtherLike-MIB	-- RFC 1650
	INCLUDES	{ etherStatsGroup, etherCollisionTableGroup }


    -- RS-232-MIB supported for all serial ports.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    SUPPORTS		RIPv2-MIB	-- RFC 1724
	INCLUDES	{ rip2GlobalGroup, rip2IfStatGroup,
			  rip2IfConfGroup }
	
	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
			    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMegiaPhysAddress, ipNetToMediaNetAddress, and
--		tcpConnState are read-only.
-- RFC 1229	Interface MIB Extensions.  No tests.  Variable 
--		ifExtnsRcvAddrStatus read-only.
-- RFC 1231	IEEE 802.5 Token Ring MIB.  Only implemented on LanRover/T
--		and LanRover/T PLUS.
--		Variables dot5Commands, dot5RingSpeed, dot5ActMonParticipate,
--		and dot5FunctionalAddress read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
-- RFC 1473	PPP-IPCP-MIB.  Instantiated for each PPP Multilink bundle.
--		Variables pppIpConfigAdminStatus and pppIpConfigCompression
--		are read-only (inconsistent with configuration model).

    ::= { shivaLanRoverCapabilities 570 }

shivaLanRoverAgent51 AGENT-CAPABILITIES
    PRODUCT-RELEASE	"LanRover/E XP16 5.1"
    STATUS		current
    DESCRIPTION		"SNMP Agent in LanRover XP16 ShivOS 5.1 firmware.
			Describes only those MIBs which have
			SMIv2 MODULE-COMPLIANCE macro."

    SUPPORTS		IF-MIB		-- RFC 1573
	INCLUDES	{ ifGeneralGroup, ifPacketGroup,
			  ifRcvAddressGroup, ifStackGroup }

	VARIATION	ifAdminStatus
	    SYNTAX	INTEGER { up(1) }
	    ACCESS	read-only
	    DESCRIPTION	"No write access via SNMP, or any other means.
			No administrative method to disable an interface."

	VARIATION	ifOperStatus
	    SYNTAX	INTEGER { up(1), down(2), unknown(4), dormant(5) }
	    DESCRIPTION	"There is no testing state in this system."

	VARIATION	ifLinkUpDownTrapEnable
	    ACCESS	read-only
	    DESCRIPTION	"No write access via SNMP, or any other means."

	VARIATION	ifPromiscuousMode
	    ACCESS	read-only
	    DESCRIPTION	"No write access via SNMP, mode not available."

	VARIATION	ifStackStatus
	    ACCESS	read-only
	    DESCRIPTION	"No write access via SNMP."

	VARIATION	ifRcvAddressStatus
	    ACCESS	read-only
	    DESCRIPTION "No write access via SNMP, or any other
	    means."

    SUPPORTS		DNS-RESOLVER-MIB	-- RFC 1612
	INCLUDES	{ dnsResConfigGroup, dnsResCounterGroup }

        VARIATION	dnsResConfigMaxCnames
	    ACCESS	read-only
	    DESCRIPTION	"This object need not be writable."

        VARIATION	dnsResConfigSbeltName
	    ACCESS	read-only
	    DESCRIPTION	"This object need not be writable."

        VARIATION	dnsResConfigSbeltRecursion
	    ACCESS	read-only
	    DESCRIPTION	"This object need not be writable."

        VARIATION	dnsResConfigSbeltPref
	    ACCESS	read-only
	    DESCRIPTION	"This object need not be writable."

        VARIATION	dnsResConfigReset
	    ACCESS	read-only
	    DESCRIPTION	"This object need not be writable."


    -- Ethernet MIB

    SUPPORTS		EtherLike-MIB	-- RFC 1650
	INCLUDES	{ etherStatsGroup, etherCollisionTableGroup }


    -- RS-232-MIB supported for all serial ports.

    SUPPORTS		RS-232-MIB	-- RFC 1659
	INCLUDES	{ rs232Group, rs232AsyncGroup }

	VARIATION	rs232PortType
	    SYNTAX	INTEGER { other(1), rs232(2) }
	    DESCRIPTION	"Internal modems are described as
			other.  Only other port type is RS-232."

	VARIATION	rs232PortInSpeed
	    ACCESS	read-only
	    DESCRIPTION	"No write access via SNMP."

	VARIATION	rs232PortOutSpeed
	    ACCESS	read-only
	    DESCRIPTION	"No write access via SNMP."

	VARIATION	rs232PortInFlowType
	    ACCESS	read-only
	    DESCRIPTION	"No write access via SNMP."

	VARIATION	rs232PortOutFlowType
	    ACCESS	read-only
	    DESCRIPTION	"No write access via SNMP."

	VARIATION	rs232AsyncPortBits
	    ACCESS	read-only
	    DESCRIPTION	"No write access via SNMP."

	VARIATION	rs232AsyncPortStopBits
	    ACCESS	read-only
	    DESCRIPTION	"No write access via SNMP."

	VARIATION	rs232AsyncPortParity
	    ACCESS	read-only
	    DESCRIPTION	"No write access via SNMP."

	VARIATION	rs232AsyncPortAutobaud
	    SYNTAX	INTEGER { disabled(2) }
	    ACCESS	read-only
	    DESCRIPTION	"No autobaud support.  No write access
			via SNMP, but no options to set."


    SUPPORTS		RIPv2-MIB	-- RFC 1724
	INCLUDES	{ rip2GlobalGroup, rip2IfStatGroup,
			  rip2IfConfGroup }
	
	VARIATION	rip2IfConfAuthType
	    ACCESS	read-only
	    DESCRIPTION	"No write access via SNMP."

	VARIATION	rip2IfConfAuthKey
	    ACCESS	read-only
	    DESCRIPTION	"No write access via SNMP."

	VARIATION	rip2IfConfSend
	    SYNTAX	INTEGER {
			    doNotSend (1),
			    ripVersion1 (2),
			    rip1Compatible (3),
			    ripVersion2 (4)
			}
	    ACCESS	read-only
	    DESCRIPTION	"No write access via SNMP.  No Demand RIP."

	VARIATION	rip2IfConfReceive
	    ACCESS	read-only
	    DESCRIPTION	"No write access via SNMP."

	VARIATION	rip2IfConfDefaultMetric
	    ACCESS	read-only
	    DESCRIPTION	"No write access via SNMP."

	VARIATION	rip2IfConfStatus
	    SYNTAX	INTEGER { active(1) }
	    ACCESS	read-only
	    DESCRIPTION	"No write access via SNMP."

	VARIATION	rip2IfConfSrcAddress
	    ACCESS	read-only
	    DESCRIPTION	"No write access via SNMP."

-- Other SNMPv1-SMI MIBs implemented:
-- RFC 1213	MIB-II, but without EGP group (no EGP).  See RFC 1573 
--		for interfaces section.  Variables atIfIndex, atPhysAddress,
--		atNetAddress, and ipForwarding are read-only.  All variables
--		in ipRouteTable are read-only.  Variables ipNetToMediaIfIndex,
--		ipNetToMegiaPhysAddress, ipNetToMediaNetAddress, and
--		tcpConnState are read-only.
-- RFC 1229	Interface MIB Extensions.  No tests.  Variable 
--		ifExtnsRcvAddrStatus read-only.
-- RFC 1243	AppleTalk Management Information Base.  The LLAP group is
--		not implemented (no LocalTalk hardware).  The variables
--		atportType and atportIfIndex are read-only.  The KIP group
--		is not implemented (protocol not supported).
-- RFC 1471	PPP-LCP-MIB.  Instantiated for each link in
--		a PPP Multlink, and again for the Multilink bundle.
--		Both layers there even if Multilink not in use.
--		Variables pppLinkConfigInitialMTRU,
--		pppLinkConfigReceiveACCMap, pppLinkConfigTransmitACCMap,
--		pppLinkConfigMagicNumber, and pppLinkConfigFcsSize are
--		read-only (inconsistent with configuration model).
-- RFC 1473	PPP-IPCP-MIB.  Instantiated for each PPP Multilink bundle.
--		Variables pppIpConfigAdminStatus and pppIpConfigCompression
--		are read-only (inconsistent with configuration model).

    ::= { shivaLanRoverCapabilities 510 }

END
