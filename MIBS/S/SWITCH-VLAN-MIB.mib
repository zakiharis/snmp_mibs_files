SWITCH-VLAN-MIB
DEFINITIONS ::= BEGIN
	IMPORTS
        MODULE-IDENTITY, OBJECT-TYPE, IpAddress, 
            Integer32                                   FROM SNMPv2-SMI
        TEXTUAL-CONVENTION, RowStatus, 
            DisplayString, MacAddress                   FROM SNMPv2-TC
        InterfaceIndex                                  FROM IF-MIB
        vLanModule                                      FROM TELESYN-ATI-TC
        ;

switchVlanMib MODULE-IDENTITY
    LAST-UPDATED "9704101600Z"
	ORGANIZATION ""
	CONTACT-INFO ""
	DESCRIPTION  
		"This module provides definitions for the Hitachi Computer
		Products, Network System Group (SWITCH), Virtual LAN (VLAN) MIB."
    REVISION "9704101600Z"
    DESCRIPTION
		"Added additional enumerations to PortFuncCode and
		PhyPortMediaTypeCode.
		
		Clarified the description of vRouterProtocol and added
		the object, vRouterRipMode, to vRouterEntry.
		
		Added a new object, pPortCountersStatus, to PPortEntry.
		"
    REVISION "9702121600Z"
    DESCRIPTION
    	"Added pPortSpeed to PPortEntry. Corrected the max-access for
    	pPortMediaType to be read-only."
    REVISION "9611071600Z"
    DESCRIPTION
        "Initial version."
    ::= { vLanModule 2 }
	
	vLanGroup	    OBJECT IDENTIFIER ::= { switchVlanMib 1 }
	vRouterGroup	OBJECT IDENTIFIER ::= { switchVlanMib 2 }
	physicalPortGroup	OBJECT IDENTIFIER ::= { switchVlanMib 3 }
	virtualPortGroup		OBJECT IDENTIFIER ::= { switchVlanMib 4 }
	ipRouteCacheGroup		OBJECT IDENTIFIER ::= { switchVlanMib 5 }
    
    AtmVci ::= TEXTUAL-CONVENTION
        DISPLAY-HINT       "d"
        STATUS             current
        DESCRIPTION
            "ATM VCI." 
        SYNTAX    INTEGER (0..1023)
	
    VlanAdminStatusCode ::= TEXTUAL-CONVENTION
        DISPLAY-HINT       "d"
        STATUS             current
        DESCRIPTION
            "The administrative status codes"
        SYNTAX    INTEGER {
            disable(1),
            enable(2)
        }
    VlanOperStatusCode ::= TEXTUAL-CONVENTION
        DISPLAY-HINT       "d"
        STATUS             current
        DESCRIPTION
            "The operational status codes"
        SYNTAX    INTEGER {
            down(1),
            up(2)
        }
    VlanMode ::= TEXTUAL-CONVENTION
        DISPLAY-HINT       "d"
        STATUS             current
        DESCRIPTION
            "The VLAN mode."
        SYNTAX    INTEGER {
            unknown(1),
            standard(3),
            atmCIP(4)
        }
    PortFuncCode ::= TEXTUAL-CONVENTION
        DISPLAY-HINT       "d"
        STATUS             current
        DESCRIPTION
            "The port function codes"
        SYNTAX    INTEGER {
            unknown(1),
            router(2),
            bridge(3),
            trunk(4),
            atmLane(5),
            atmMux(6),
            cip(7),
            pt2Pt(8)
            
        }
	MACLayerCode ::= TEXTUAL-CONVENTION
        DISPLAY-HINT       "d"
        STATUS             current
        DESCRIPTION
            "The MAC layer type for the port."
        SYNTAX    INTEGER {
            unknown(0),
			none(1),	
            ethernet(2), 
            ieee802d3(3), 
            ieee802d5(4),
            fddi(5)
        }
    PhyPortMediaTypeCode ::= TEXTUAL-CONVENTION
        DISPLAY-HINT       "d"
        STATUS             current
        DESCRIPTION
            "The media types supported for a port"
        SYNTAX    INTEGER {
            unknown(1),     
            other(2),       
            eth10(3),     	
            eth100(4),		
            tr4(5),		    
            tr16(6),		
            fddi(7),		
            cddi(8),		
            atm25(9),		
            atm50(10),		
            ds1(11),		
            ds3(12),		
            oc3(13),		
            oc12(14),		
            oc48(15),		
            wan(16),		
            eth100F(17)		
        }
    vLanTable  OBJECT-TYPE
        SYNTAX      SEQUENCE OF VLanEntry
        MAX-ACCESS  not-accessible
        STATUS      current
        DESCRIPTION
            "A list of Virtual LAN instances."
		::= { vLanGroup 1 }
    vLanEntry  OBJECT-TYPE
        SYNTAX  VLanEntry
        MAX-ACCESS  not-accessible
        STATUS  current
        DESCRIPTION
            "VLAN entry." 
		INDEX { vLanNumber }
		::= { vLanTable 1 }
	VLanEntry ::= SEQUENCE {
		vLanNumber          INTEGER,
		vLanMembers         OCTET STRING,
		vLanDescription     DisplayString,
		vLanAdminStatus     VlanAdminStatusCode,
		vLanOperStatus      VlanOperStatusCode,
		vLanMode            VlanMode,
        vLanRowStatus		RowStatus
	    }
	vLanNumber  OBJECT-TYPE
	    SYNTAX  INTEGER (1..65535)
	    MAX-ACCESS  not-accessible
	    STATUS  current
	    DESCRIPTION
            "The VLAN number identifying this instance"
	    ::= { vLanEntry 1 }
	vLanMembers  OBJECT-TYPE
        SYNTAX  OCTET STRING (SIZE(32))
        MAX-ACCESS  read-only
        STATUS  current
        DESCRIPTION
            "A bitmap structure presenting the virtual ports assigned to
            this vLan.  Bits are numbered from 1 to 256 starting with the  
            high order bit of the first octet.  Each bit which is set 
            indicates the virtual port number assigned to the this vlan."
        ::= { vLanEntry 2 }
	vLanDescription  OBJECT-TYPE
	    SYNTAX  DisplayString (SIZE (0..31))
	    MAX-ACCESS  read-create
	    STATUS  current
	    DESCRIPTION
		 "Textual description of the VLAN instance."
	    ::= { vLanEntry 5 }
	vLanAdminStatus  OBJECT-TYPE
	    SYNTAX  VlanAdminStatusCode
	    MAX-ACCESS  read-create
	    STATUS  current
	    DESCRIPTION
		"The administrative status which can be set by
		 configuration. 'disable' will disable ALL vPorts
		 that are connected to this VLAN, 'enable' will enable
		 all ports"
	    ::= { vLanEntry 6 }
	vLanOperStatus  OBJECT-TYPE
	    SYNTAX  VlanOperStatusCode
	    MAX-ACCESS  read-only
	    STATUS  current
	    DESCRIPTION
		"Provide operating status of a particular VLAN."
	    ::= { vLanEntry 7 }
	vLanMode  OBJECT-TYPE
	    SYNTAX  VlanMode
	    MAX-ACCESS  read-create
	    STATUS  deprecated
	    DESCRIPTION
		"Provides special operating mode setup and status. Currently
		 this object is used to specify weather the VLAN supports
		 the standard or ATM CIP connections. This is deprecated 
		 because it is not maintained by system software. "
	    ::= { vLanEntry 8 }
	vLanRowStatus  OBJECT-TYPE
	    SYNTAX  RowStatus
	    MAX-ACCESS  read-create
	    STATUS  current
	    DESCRIPTION
		"This attribute may only be set to 'createAndGo' and 'delete'. 
		'notInService' and 'createAndWait' are not supported."
	    ::= { vLanEntry 9 }
	
	
	vRouterTable  OBJECT-TYPE
    	SYNTAX  SEQUENCE OF VRouterEntry
    	MAX-ACCESS  not-accessible
    	STATUS  current
    	DESCRIPTION
        	"A list of Virtual Router instances."
    	::= { vRouterGroup 1 }
	vRouterEntry  OBJECT-TYPE
    	SYNTAX  VRouterEntry
    	MAX-ACCESS  not-accessible
    	STATUS  current
    	DESCRIPTION
        	"A VLAN entry."
    	INDEX { vLanNumber }
    	::= { vRouterTable 1 }
	VRouterEntry ::= SEQUENCE {
    	vRouterProtocol         INTEGER,
    	vRouterIpAddress        IpAddress,
    	vRouterSubNetMask       IpAddress,
    	vRouterBcastAddress     IpAddress,
    	vRouterDescription      DisplayString,
    	vRouterAdminStatus      VlanAdminStatusCode,
    	vRouterOperStatus       VlanOperStatusCode,
    	vRouterRowStatus        RowStatus,
		vRouterIfIndex			InterfaceIndex,
		vRouterRipMode			INTEGER
	}
	vRouterProtocol  OBJECT-TYPE
    	SYNTAX  INTEGER (0..65535)
    	MAX-ACCESS  read-create
    	STATUS  current
    	DESCRIPTION
			"This object is used to enable/disable routing protocols. 
			The value of this object is the logical ORing of each bit
			identifying the routing protocol below, where bit 0 is the
			low order bit, i.e. 2**0.
				ipRip      bit 0
				ipEgp      bit 1
				ipGgp      bit 2
				ipHello    bit 3
				ipIs-is    bit 4
				ipEs-is    bit 5
				ipCiscoIgrp bit 6
				ipBbnSpfIgp bit 7
				ipOspf     bit 8
			Setting the appropriate bit enables the protocol (if
			supported); clearing the bit, disables the protocol."
    	DEFVAL { 0 }
    	::= { vRouterEntry 1 }
	vRouterIpAddress  OBJECT-TYPE
    	SYNTAX  IpAddress
    	MAX-ACCESS  read-create
    	STATUS  current
    	DESCRIPTION
        	 "The IP network address for this virtual bridge
        	  instance for the purpose of allowing access from
        	  the external network management system.
        	  This attribute is required for row creation."
    	::= { vRouterEntry 2 }
	vRouterSubNetMask  OBJECT-TYPE
    	SYNTAX  IpAddress
    	MAX-ACCESS  read-create
    	STATUS  current
    	DESCRIPTION
        	 "The IP network subnet mask for this virtual bridge
        	  instance for the purpose of allowing access from the
        	  external network management system.
        	  This attribute is required for row creation."
    	::= { vRouterEntry 3 }
	vRouterBcastAddress  OBJECT-TYPE
    	SYNTAX  IpAddress
    	MAX-ACCESS  read-create
    	STATUS  current
    	DESCRIPTION
        	 "The IP broadcast address for this virtual bridge
        	  instance for the purpose of allowing access from the
        	  external network management system.
        	  This attribute is required for row creation."
    	::= { vRouterEntry 4 }
	vRouterDescription  OBJECT-TYPE
    	SYNTAX  DisplayString (SIZE (0..31))
    	MAX-ACCESS  read-create
    	STATUS  current
    	DESCRIPTION
        	"Textual description of the router instance."
    	::= { vRouterEntry 5 }
	vRouterAdminStatus  OBJECT-TYPE
    	SYNTAX  VlanAdminStatusCode
    	MAX-ACCESS  read-create
    	STATUS  current
    	DESCRIPTION
			"The particular routing environment can be enable(2) or
			disable(1), its value is determined by the ifAdminStatus of
			the interface associated with this router."
    	::= { vRouterEntry 6 }
	vRouterOperStatus  OBJECT-TYPE
    	SYNTAX  VlanOperStatusCode
    	MAX-ACCESS  read-only
    	STATUS  current
    	DESCRIPTION
			"Provide operating status of a particular router
			environment."
    	::= { vRouterEntry 7 }
	vRouterRowStatus  OBJECT-TYPE
    	SYNTAX  RowStatus
    	MAX-ACCESS  read-create
    	STATUS  current
    	DESCRIPTION
			 "Only supports 'createAndGo' and 'delete' for set
			 operation.    The vLanEntry instance identified by the
			 value of the index   for this attribute must exist before
			 a attempting to create an instance of vRouterRowStatus."
    	::= { vRouterEntry 8 }
	vRouterIfIndex  OBJECT-TYPE
		SYNTAX    InterfaceIndex
		MAX-ACCESS  read-only
		STATUS  current
		DESCRIPTION
			"The value of ifIndex which corresponds to this vRouter
			instance."
		::= { vRouterEntry 9 }
	vRouterRipMode  OBJECT-TYPE
		SYNTAX    INTEGER {
		              silent(1),
		              active(2),
			      deaf(3),
			      inactive(4)
		          }
		MAX-ACCESS  read-create
		STATUS  current
		DESCRIPTION
			"If the value of this object is 'silent', RIP daemon
			processes received routing packets and does NOT send
			routing packets.  If the value of this object is 'active',
			RIP sends and receives routing packets."
		::= { vRouterEntry 10 }
	
	
	
	
	
	
	pPortTable  OBJECT-TYPE
	    SYNTAX  SEQUENCE OF PPortEntry
	    MAX-ACCESS  not-accessible
	    STATUS  current
	    DESCRIPTION
		"A list of Physical Port instances."
	    ::= { physicalPortGroup 1 }
	pPortEntry  OBJECT-TYPE
	    SYNTAX  PPortEntry
	    MAX-ACCESS  not-accessible
	    STATUS  current
	    DESCRIPTION
		"A Physical Port entry."
	    INDEX { pPortNumber }
	    ::= { pPortTable 1 }
	PPortEntry ::= SEQUENCE {
	    pPortNumber         INTEGER,
	    pPortMediaType      PhyPortMediaTypeCode,
	    pPortDescription    DisplayString,
	    pPortIfIndex        InterfaceIndex,
	    pPortDuplexity      INTEGER,
	    pPortAutoNegotiate  INTEGER,
	    pPortAdminStatus    VlanAdminStatusCode,
	    pPortOperStatus     VlanOperStatusCode,
	    pPortSpeed          Integer32,
	    pPortCountersStatus INTEGER
	}
	pPortNumber  OBJECT-TYPE
	    SYNTAX  INTEGER (1..256)
	    MAX-ACCESS  not-accessible
	    STATUS  current
	    DESCRIPTION
		"The phyiscal port number."
	    ::= { pPortEntry 1 }
	pPortMediaType  OBJECT-TYPE
	    SYNTAX  PhyPortMediaTypeCode
	    MAX-ACCESS  read-only
	    STATUS  current
	    DESCRIPTION
		"The physical media type supported by this physical port."
	    ::= { pPortEntry 2 }
	pPortDescription  OBJECT-TYPE
	    SYNTAX  DisplayString (SIZE (0..31))
	    MAX-ACCESS  read-write
	    STATUS  current
	    DESCRIPTION
		"A description of the instance of this physical Port."
	    ::= { pPortEntry 3 }
	pPortIfIndex  OBJECT-TYPE
	    SYNTAX    InterfaceIndex
	    MAX-ACCESS  read-only
	    STATUS  current
	    DESCRIPTION
		"The value of ifIndex which corresponds to this physical port."
	    ::= { pPortEntry 4 }
	pPortDuplexity  OBJECT-TYPE
	    SYNTAX  INTEGER {
                    halfDuplex(1),
                    fullDuplex(2)
                }
	    MAX-ACCESS  read-write
	    STATUS  current
	    DESCRIPTION
		"The duplexity of this pPort."
	    ::= { pPortEntry 5 }
	pPortAutoNegotiate  OBJECT-TYPE
	    SYNTAX  INTEGER {
                    disable(1),
                    enable(2)
                }
	    MAX-ACCESS  read-write
	    STATUS  current
	    DESCRIPTION
		"Only ports whose pPortMediaType is 'eth100' may support
		autonegotiation to determine the portSpeed and pPortDuplexity.
		pPortAutoNegotiate is not writeable for ports whose
		pPortMediaType is not 'eth100'."
	    ::= { pPortEntry 6 }
	pPortAdminStatus  OBJECT-TYPE
	    SYNTAX    VlanAdminStatusCode
	    MAX-ACCESS  read-write
	    STATUS  current
	    DESCRIPTION
		"The administrative status of this pPort. Instances for VRouter and
		 Uplinks (33 and 34) are read-only, the value can be set by ifAdminStatus."
	    ::= { pPortEntry 7 }
	pPortOperStatus  OBJECT-TYPE
	    SYNTAX  VlanOperStatusCode
	    MAX-ACCESS  read-only
	    STATUS  current
	    DESCRIPTION
		"The operational status of this pPort."
	    ::= { pPortEntry 8 }
	pPortSpeed  OBJECT-TYPE
	    SYNTAX  Integer32
	    MAX-ACCESS  read-write
	    STATUS  current
	    DESCRIPTION
		"The speed of the port in bits per second (bps).  For ports
		whose pPortMediaType is 'eth100', and pPortDuplexity has the
		value 'disable' pPortSpeed may be writeable."
	    ::= { pPortEntry 9 }
	pPortCountersStatus  OBJECT-TYPE
	    SYNTAX  INTEGER {
	    			unknown(0),
	    			enable(1),
	    			disable(2)
	    		}
	    MAX-ACCESS  read-write
	    STATUS  current
	    DESCRIPTION
		"An object used to enable or disable counters for physical
		ports whose pPortMediaType is 'eth10', 'eth100', or 'eth100F'.
		In some instances it is not possible to determine the state
		of the counters."
	    ::= { pPortEntry 10 }
	pEtherCountersStatus  OBJECT-TYPE
	    SYNTAX  INTEGER {
	    			enable(1),
	    			disable(2)
	    		}
	    MAX-ACCESS  read-write
	    STATUS  current
	    DESCRIPTION
		"This Object Globally enables or disables the 
		Statistics Collection on the Ethernet Ports. "
	    ::= { physicalPortGroup 2 }
	pStatsPollInterval  OBJECT-TYPE
	    SYNTAX  INTEGER 
	    MAX-ACCESS  read-write
	    STATUS  current
	    DESCRIPTION
		"This Object is the Time interval in seconds between
		Statistics Collection."
	    ::= { physicalPortGroup 3 }
	
    
	
	
	vPortTable  OBJECT-TYPE
	    SYNTAX  SEQUENCE OF VPortEntry
	    MAX-ACCESS  not-accessible
	    STATUS  current
	    DESCRIPTION
		"A list of Virtual Port instances."
	    ::= { virtualPortGroup 1 }
	vPortEntry  OBJECT-TYPE
	    SYNTAX  VPortEntry
	    MAX-ACCESS  not-accessible
	    STATUS  current
	    DESCRIPTION
		"A Virtual Port entry."
	    INDEX { vPortNumber }
	    ::= { vPortTable 1 }
	VPortEntry ::= SEQUENCE {
	    vPortNumber           INTEGER,
        vPortPhyPort          INTEGER,
	    vPortFuncType         PortFuncCode,
	    vPortVlanNumber       INTEGER,
	    vPortDomain           INTEGER,
	    vPortMACaddress       MacAddress,
	    vPortDefaultMacLayer  MACLayerCode,
        vPortBridgeMode       INTEGER,
	    vPortSwitchTimer      INTEGER,
	    vPortDescription      DisplayString,
	    vPortAdminStatus      VlanAdminStatusCode,
	    vPortOperStatus       VlanOperStatusCode,
	    vPortIfIndex          InterfaceIndex
	}
	vPortNumber  OBJECT-TYPE
	    SYNTAX  INTEGER (1..256)
	    MAX-ACCESS  not-accessible
	    STATUS  current
	    DESCRIPTION
	        "A unique number identifies this Virtual Port instance."
	    ::= { vPortEntry 1 }
	vPortPhyPort  OBJECT-TYPE
	    SYNTAX  INTEGER (0..256)
	    MAX-ACCESS  read-only
	    STATUS  current
	    DESCRIPTION
	        "The physical port ID this virtual port is mapped to. If the
	        value is 0, then the virtual port is not associated with a
	        physical port."
	    ::= { vPortEntry 2 }
 
	vPortFuncType  OBJECT-TYPE
	    SYNTAX  PortFuncCode
	    MAX-ACCESS  read-only
	    STATUS  current
	    DESCRIPTION
	        "The function type for this vPort. i.e. router, brige, ATM."
	    ::= { vPortEntry 3 }
 
	vPortVlanNumber  OBJECT-TYPE
	    SYNTAX  INTEGER (1..65535)
	    MAX-ACCESS  read-write
	    STATUS  current
	    DESCRIPTION
	        "The VLAN that this vPort belongs in."
	    ::= { vPortEntry 4 }
	vPortDomain  OBJECT-TYPE
	    SYNTAX  INTEGER (1..65535)
	    MAX-ACCESS  read-only
	    STATUS  current
	    DESCRIPTION
	        "internal ID identifies the VLAN this vport attached to "
	    ::= { vPortEntry 5 }
	vPortMACaddress  OBJECT-TYPE
	    SYNTAX  MacAddress
	    MAX-ACCESS  read-only
	    STATUS  current
	    DESCRIPTION
	        "The MAC address represented by this Virtual Port."
	    ::= { vPortEntry 6 }
	vPortDefaultMacLayer  OBJECT-TYPE
	    SYNTAX  MACLayerCode
	    MAX-ACCESS  read-write
	    STATUS  current
	    DESCRIPTION
	        "The output MAC layer format that this particular vPort
	        supports as a default. The value indicates the format
	        required for output from this vPort."
	    ::= { vPortEntry 7 }
	vPortBridgeMode  OBJECT-TYPE
	    SYNTAX  INTEGER {
	                unknown(1),
	                autoSwitch(2),
	                forceBridge(3),
	                forceSwitch(4)
	            }
	    MAX-ACCESS  read-write
	    STATUS  deprecated
	    DESCRIPTION
		    "A mode of this virtual port for optimization of the bridging
            function.  In 'autoSwitch' the system determines the best mode."
	    ::= { vPortEntry 8 }
    vPortSwitchTimer  OBJECT-TYPE
		SYNTAX  INTEGER (1..65535)
		MAX-ACCESS  read-write
		STATUS  deprecated
		DESCRIPTION
		    "The time out period for a Bridged vPort to convert
		    to a switch optimized mode in seconds if vPortBridgMode
		    is set to autoSwitch(1). Setting it to zero will cause
		    automatic switching between the two modes immediately.
		    The default is 60 seconds."
        ::= { vPortEntry 9 }
	vPortDescription  OBJECT-TYPE
	    SYNTAX  DisplayString (SIZE (0..31))
	    MAX-ACCESS  read-write
	    STATUS  current
	    DESCRIPTION
		    "A string to identify the instance of this virtual port."
	    ::= { vPortEntry 10 }
	vPortAdminStatus  OBJECT-TYPE
	    SYNTAX  VlanAdminStatusCode
	    MAX-ACCESS  read-write
	    STATUS  current
	    DESCRIPTION
		    "The administrative status of this virtual port. Its value is
			determined by the value of ifAdminStatus associated with this
			vPort."
	    ::= { vPortEntry 11 }
	vPortOperStatus  OBJECT-TYPE
	    SYNTAX  VlanOperStatusCode
	    MAX-ACCESS  read-only
	    STATUS  current
	    DESCRIPTION
		    "The operational status of this virtual port. "
	    ::= { vPortEntry 12 }
	vPortIfIndex  OBJECT-TYPE
	    SYNTAX    InterfaceIndex
	    MAX-ACCESS  read-only
	    STATUS  current
	    DESCRIPTION
		"The value of ifIndex which corresponds to this virtual port."
	    ::= { vPortEntry 13 }
	
	
	
	
	
	ipRouteState  OBJECT-TYPE
	    SYNTAX    INTEGER {
			ipForwarding(1),
			ipRouteCacheForward(2)
			}
	    MAX-ACCESS  read-write
	    STATUS  current
	    DESCRIPTION
		"ipRouteState enables or disables RouteCaching"
	    ::= { ipRouteCacheGroup 1 }
	ipRouteCacheTable  OBJECT-TYPE
	    SYNTAX  SEQUENCE OF IpRouteCacheEntry
	    MAX-ACCESS  not-accessible
	    STATUS  current
	    DESCRIPTION
		"A list of IpRouteCache Instances."
	    ::= { ipRouteCacheGroup 2 }
	ipRouteCacheEntry  OBJECT-TYPE
	    SYNTAX  IpRouteCacheEntry
	    MAX-ACCESS  not-accessible
	    STATUS  current
	    DESCRIPTION
		"An IpRouteCache Entry."
	    INDEX { ipRouteCacheIndex }
	    ::= { ipRouteCacheTable 1 }
	IpRouteCacheEntry ::= SEQUENCE {
	    ipRouteCacheIndex           	INTEGER,
            ipRouteCacheDstIpAddress          	IpAddress,
	    ipRouteCacheSrcIpAddress         	IpAddress,
	    ipRouteCacheDstPort       		INTEGER,
	    ipRouteCacheSrcPort           	INTEGER,
	    ipRouteCacheMedia		       	INTEGER,
	    ipRouteCacheVPortNumber  		INTEGER,
            ipRouteCacheVCI       		AtmVci
	}
	ipRouteCacheIndex  OBJECT-TYPE
	    SYNTAX  INTEGER 
	    MAX-ACCESS  read-only
	    STATUS  current
	    DESCRIPTION
	        "The Index of the Route Cache entry." 
	    ::= { ipRouteCacheEntry 1 }
	ipRouteCacheDstIpAddress  OBJECT-TYPE
	    SYNTAX  IpAddress 
	    MAX-ACCESS  read-only
	    STATUS  current
	    DESCRIPTION
	        "The Destination IpAddress  of the Route." 
	    ::= { ipRouteCacheEntry 2 }
	ipRouteCacheSrcIpAddress  OBJECT-TYPE
	    SYNTAX  IpAddress 
	    MAX-ACCESS  read-only
	    STATUS  current
	    DESCRIPTION
	        "The Source IpAddress  of the Route." 
	    ::= { ipRouteCacheEntry 3 }
	ipRouteCacheDstPort  OBJECT-TYPE
	    SYNTAX  INTEGER (1..65535)
	    MAX-ACCESS  read-only
	    STATUS  current
	    DESCRIPTION
	        "The Destination Port of the Route." 
	    ::= { ipRouteCacheEntry 4 }
	ipRouteCacheSrcPort  OBJECT-TYPE
	    SYNTAX  INTEGER (1..65535)
	    MAX-ACCESS  read-only
	    STATUS  current
	    DESCRIPTION
	        "The Source  Port of the Route." 
	    ::= { ipRouteCacheEntry 5 }
	ipRouteCacheMedia  OBJECT-TYPE
	    SYNTAX  INTEGER {
		unknown (1),
		vlan (2),
		cip (3),
		ptop (4),
		csr (5),
		fddi (6),
		atmtrunk (7),
		fdditrunk (8)
		}		
	    MAX-ACCESS  read-only
	    STATUS  current
	    DESCRIPTION
	        "The Physical Media on which the destination can reached from the source."
	    ::= { ipRouteCacheEntry 6 }
	ipRouteCacheVPortNumber  OBJECT-TYPE
	    SYNTAX  INTEGER (1..256)
	    MAX-ACCESS  read-only
	    STATUS  current
	    DESCRIPTION
	        "The Virtual Port using which the Destination can be reached."
	    ::= { ipRouteCacheEntry 7 }
	ipRouteCacheVCI  OBJECT-TYPE
	    SYNTAX  AtmVci 
	    MAX-ACCESS  read-only
	    STATUS  current
	    DESCRIPTION
	        "The VCI on which the destination is reached if the media type is ATM."
	    ::= { ipRouteCacheEntry 8 }
END
