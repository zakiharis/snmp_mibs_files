--
-- she-adsl-mib.mib
-- MIB generated by MG-SOFT Visual MIB Builder Version 6.0  Build 88
-- Tuesday, September 23, 2008 at 16:21:04
--

-- Start of ClearCase branch-information of current release:
-- she-adsl-mib.mib   /main/she_main_grf/26
-- End of ClearCase branch-information.
-- 

	SHE-ADSL-MIB DEFINITIONS ::= BEGIN
 
		IMPORTS
			AdslLineCodingType, AdslPerfTimeElapsed, AdslPerfCurrDayCount, AdslPerfPrevDayCount			
				FROM ADSL-TC-MIB			
			she, DisplayString			
				FROM AN-MIB			
			ifNumber, ifIndex, InterfaceIndex			
				FROM IF-MIB			
			PerfCurrentCount, PerfIntervalCount			
				FROM PerfHist-TC-MIB			
			sheAlarmTimeAndDate, sheAlarmReportingSource, sheAlarmReportingSourceType, sheAlarmSeverity, SheAlarmSevProfileIndex			
				FROM SHE-ALARMING-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			transmission, Integer32, Unsigned32, Gauge32, Counter32, 
			OBJECT-TYPE, MODULE-IDENTITY, NOTIFICATION-TYPE			
				FROM SNMPv2-SMI			
			VariablePointer, TruthValue, TEXTUAL-CONVENTION			
				FROM SNMPv2-TC;
	
	
		sheAdslMib MODULE-IDENTITY 
			LAST-UPDATED "200809231000Z"		-- September 23, 2008 at 10:00 GMT
			ORGANIZATION 
				"Nokia Siemens Networks "
			CONTACT-INFO 
				"Gerd Barchmann
				COO BBA DSLAM RD SDE
				
				gerd.barchmann@nsn.com
				+49 3834 555654"
			DESCRIPTION 
				"The MIB module to describe ADSL product.
				The MIB module that provides objects that are proprietary and extension to ADSL-                                                                         
				LINE-MIB.The MIB includes the following Tables.                
				1.) adslLineTable 
				2.) adslAtucPhysTable  
				3.) adslAturPhysTable
				4.) adslAtucChanTable
				5.) adslAturChanTable
				6.) adslAtucPerfDataTable
				7.) adslAtucIntervalTable
				8.) adslAtucChanPerfDataTable
				9.) adslAturChanPerfDataTable
				10.) adslAtucChanIntervalTable
				11.) adslAturChanIntervalTable
				12.) adslLineConfProfileTable
				13.) adslLineConfExtnProfileTable
				13.) adslLineAlarmConfProfileTable
				14.) adslVccTpTable
				15.) adslRfiMaskTable"
			REVISION "200608231228Z"		-- August 23, 2006 at 12:28 GMT
			DESCRIPTION 
				"Take over by Gerd Barchmann for R2.5.
				Merge on base she MIB version 151."
			REVISION "200609200842Z"		-- September 20, 2006 at 08:42 GMT
			DESCRIPTION 
				"Delete entrys from extnProfileControl-group for elements which could not be modified.
				Same for extnProfileModified-notification.
				Move AdslLineAlarm's to separate group (like in vshe).
				"
			REVISION "200610041111Z"		-- October 04, 2006 at 11:11 GMT
			DESCRIPTION 
				"Add support for dualLatency. Needed changes made for access channeltable's and new parameter in 
				vcctp-table. SHE releases smaller then R2.5 will support old channel tables without channeltype index
				(NO dualLatency support)! SHE release R2.5 and higher support new channel tables with additional 
				channeltype index (dualLatency supported)! 
				Add some removed elements for backward compatibility of the managment system. The NE release up R2.5
				will still NOT support this elements!"
			REVISION "200610170846Z"		-- October 17, 2006 at 08:46 GMT
			DESCRIPTION 
				"New merge with SHE R2.3 MIB-Version 153.
				Expand value list for SheAdslLineConfUpstreamPSDMaskSelectionType."
			REVISION "200611211423Z"		-- November 21, 2006 at 14:23 GMT
			DESCRIPTION 
				"Minor corrections for backward compatibility.
				OID changes for sheAdslAtuc-Notifications (also backward compatibility).
				Modify description for usedDslChannel in VccTp-Table.
				Modify description for linetype configuration."
			REVISION "200612151140Z"		-- December 15, 2006 at 11:40 GMT
			DESCRIPTION 
				"Minor corrections for backward compatibility.
				Correct default value for VccTp-UsedChannel."
			REVISION "200701220821Z"		-- January 22, 2007 at 08:21 GMT
			DESCRIPTION 
				"Merge with SHE R2.3 MIB release 156."
			REVISION "200702061436Z"		-- February 06, 2007 at 14:36 GMT
			DESCRIPTION 
				"Expand range for SheAdslConfMinInpType."
			REVISION "200703281219Z"		-- March 28, 2007 at 12:19 GMT
			DESCRIPTION 
				"New for R2.5.2.
				Add sheAdslLineDpboProfileTable. Assignment via sheAdslLineTable.
				Add separate INP configuration value for US direction to extn. Profile.
				Add sheAdslVccTpPerformanceCounter - Table.
				Add sheAdslVccTpEncapType to sheAdslVccTpTable."
			REVISION "200704160852Z"		-- April 16, 2007 at 08:52 GMT
			DESCRIPTION 
				"Add enum value for support adsl2adsl2PlusOnly standard via sheAdslLineConfExtnProfileStandard value.                  
				Add modified trap for DpboProfile assignment."
			REVISION "200705091118Z"		-- May 09, 2007 at 11:18 GMT
			DESCRIPTION 
				"Correct type for VccTpAlarmSeverityIndex."
			REVISION "200706061028Z"		-- June 06, 2007 at 10:28 GMT
			DESCRIPTION 
				"Correct only descripions regarding feature support in version SHE R2.6."
			REVISION "200706291253Z"		-- June 29, 2007 at 12:53 GMT
			DESCRIPTION 
				"Correct setting for sheAdslLineControlRfiBandMask."
			REVISION "200707121139Z"		-- July 12, 2007 at 11:39 GMT
			DESCRIPTION 
				"sheAdslLineDpboProfileMof not longer supported.
				Correct description for MinINP=0.
				Merge MIB release 160 from SHE R2.3 -> 
				support for SES and UAS ThresholdAlarms.
				Merge MIB release for SHE R2.4 -> 
				sheAdslLineInpValueTruncatedInto2 added into sheAdslConfigurationTraps 
				and add sheAdslAtucPhysCurrentBinStatus."
			REVISION "200708231524Z"		-- August 23, 2007 at 15:24 GMT
			DESCRIPTION 
				"Expand AtucPhys and AturPhys table with BinBitLoading parameters."
			REVISION "200709201241Z"		-- September 20, 2007 at 12:41 GMT
			DESCRIPTION 
				"Modify sheAdslLineInpValueTruncatedInto2 object list (requested by Zhao Ran)."
			REVISION "200711081046Z"		-- November 08, 2007 at 10:46 GMT
			DESCRIPTION 
				"Support additional parameters for DELT status in AtuxPhysTable with SHE R2.4.
				Correct syntax for SheAdslLineConfNtrType.
				Add parameter to AdslLineAlarmConfModifiedTrap."
			REVISION "200802221347Z"		-- February 22, 2008 at 13:47 GMT
			DESCRIPTION 
				"Correct description of minInp value 0 -> null!"
			REVISION "200803191127Z"		-- March 19, 2008 at 11:27 GMT
			DESCRIPTION 
				"Add detailed failure returncode definitions to ReqResult enum. The scheduled support release is not defined yet."
			REVISION "200804211052Z"		-- April 21, 2008 at 10:52 GMT
			DESCRIPTION 
				"Add support for a dynamic use of annex types A/B/I/J by a single adsl line profile.
				Support will start with SHE R2.8. This causes some restrictions to extn. profile parameter
				settings. A new specific profile create command was defined."
			REVISION "200809231618Z"		-- September 23, 2008 at 16:18 GMT
			DESCRIPTION 
				"Add missing value for AdvertisedCapability definition."
			::= { she 6 }

		
	
--
-- Type definitions
--
	
		SheDslSystemType ::= INTEGER
			{
			adsl(1),
			sdsl(2),
			shdsl(3)
			}

		SheDslSystemLineCodingType ::= INTEGER
			{
			other(1),
			dmt(2),
			cap(3),
			qam(4)
			}

		SheDslSystemTxCfgType ::= BITS
			{
			unused(0),
			etsi(1),
			q9921PotsNonOverlapped(2),
			q9921PotsOverlapped(3),
			q9921IsdnNonOverlapped(4),
			q9921IsdnOverlapped(5),
			q9921TcmIsdnNonOverlapped(6),
			q9921TcmIsdnOverlapped(7),
			q9922PotsNonOverlapped(8),
			q9922PotsOverlapped(9),
			q9922TcmIsdnNonOverlapped(10),
			q9922TcmIsdnOverlapped(11),
			q9922TcmIsdnSymmetric(12),
			adslPlusPotsNonOverlapped(13)
			}

--  This type specifies the user commands (control requests)
-- from the TMN-OS or LCT.
		SheAdslControlRequestType ::= INTEGER
			{
			noRequest(1),
			setDslSystemLineTxCfg(101),
			createAdslLineConfProfile(150),
			modifyAdslLineConfProfile(151),
			deleteAdslLineConfProfile(152),
			createAdslLineConfProfileAnnexA(155),
			createAdslLineConfProfileAnnexB(156),
			createAdslLineConfProfileAdsl2PlusAnnexB(157),
			modifyAdslLineConfExtnProfile(161),
			modifyAdslLineEntry(201),
			modifyAdslLineAlarmConfProfileEntry(202),
			modifyAdslLineDeltConfEntry(203),
			forceAdslLinePwrMgmtState(204),
			clearAdslLinePerfCounter(205),
			modifyAdslLineRfiBandMask(206),
			setAdslLineDpboProfileEntry(210),
			createAdslLineAlarmConfProfile(250),
			modifyAdslLineAlarmConfProfile(251),
			deleteAdslLineAlarmConfProfile(252),
			createAdslLineDpboProfile(270),
			modifyAdslLineDpboProfile(271),
			deleteAdslLineDpboProfile(272),
			createAdslVccTp(301),
			deleteAdslVccTp(302),
			modifyAdslVccTp(303),
			modifyAdslVccTpLoopTest(304),
			modifyAdslVccTpEgressShaping(305),
			modifyAdslVccTpIngressPolicing(306),
			modifyAdslVccTpEncap(307),
			modifyAdslVccTpAdminState(315),
			modifyAdslVccTpOrl(316),
			modifyAdslVccTpUsedDslChannel(321),
			deleteAdslVccTpPerformanceCounters(325),
			createAdslRfiBand(351),
			deleteAdslRfiBand(352),
			createAdslLineConfProfileAdsl2AnnexI(400),
			createAdslLineConfProfileAdsl2AnnexJ(401),
			createAdslLineConfProfileAdsl2PlusAnnexI(402),
			createAdslLineConfProfileAdsl2PlusAnnexJ(403),
			createAdslLineConfProfileAdsl2AnnexM(404),
			createAdslLineConfProfileAdsl2PlusAnnexM(405),
			createAdslLineConfProfileAdsl2PlusDynamic(410)
			}

--   This type specifies the result of user commands (control requests)
-- from the TMN-OS or LCT.
		SheAdslControlRequestResultType ::= INTEGER
			{
			noRequest(1),
			comExecStarted(30),
			paramFaulty(31),
			requestBusy(32),
			setDataFailed(34),
			aswTimeout(35),
			commandFailed(36),
			commandSucceeded(37),
			profileNameStringUnknown(2001),
			profileNameToLong(2002),
			profileNameAlreadyExist(2003),
			maxNumberOfProfilesReached(2004),
			profileNotExist(2005),
			profileAssignFailOnActivePort(2006),
			profileTypDefaultCouldNotModified(2010),
			profileCreateFailOnInvalidArguments(2011),
			profileModifyFailOnInvalidArguments(2012),
			profileModifyFailOnInvalidMarginSettings(2013),
			profileModifyFailOnInvalidDataRateSettings(2014),
			profileLineTypModifyFailOnAssignedProfiles(2015),
			internalFailureWriteToDataBase(2020),
			internalFailureReadFromDataBase(2021),
			profileUsedByActivePorts(2022),
			internalFailureDuringIuCommunication(2030),
			portNumberNotExist(2040),
			portNumberHasWrongDSLType(2041),
			profileMinBandwithNotSatisfiedForCAC(2050)
			}

		SheAdslLineConfRateModeType ::= INTEGER
			{
			fixed(1),
			adaptAtStartup(2),
			adaptAtRuntime(3)
			}

		SheAdslLineTrellisModeType ::= INTEGER
			{
			unknown(0),
			trellisOn(1),
			trellisOff(2)
			}

		SheAdslLineConfRsIntCorrectionType ::= INTEGER
			{
			value125us(3),
			value250us(4),
			value500us(5),
			value1ms(6),
			value2ms(7),
			value4ms(8),
			disable(15)
			}

		SheAdslConfLineType ::= INTEGER
			{
			noChannel(1),
			fastOnly(2),
			interleavedOnly(3),
			fastOrInterleaved(4),
			fastAndInterleaved(5)
			}

		SheAdslLineConfExtnProfileRxBinAdjustType ::= INTEGER (0)

		SheAdslLineConfTriggerModeType ::= INTEGER
			{
			disable(0),
			locCrc(1),
			rmtCrc(2),
			snrInc(4),
			snrDec(8)
			}

		SheAdslLineConfExtnProfileAdi2xType ::= INTEGER (1)

--   	
		SheAdslLineConfStandardType ::= INTEGER
			{
			t1413(0),
			gLite(1),
			gDmt(2),
			multiMode(4),
			adsl2(26),
			adsl2Plus(27),
			readsl2(28),
			adsl2Auto(29),
			adsl2PlusAuto(30),
			adsl2adsl2PlusOnly(31)
			}

		SheAdslLineConfInitiateType ::= INTEGER
			{
			waitPn(0),
			ctone(1),
			initiatePn(128)
			}

--   	
		SheAdslLineConfAttenuationType ::= INTEGER
			{
			attenuation0(0),
			attenuation1(1),
			attenuation2(2),
			attenuation3(3),
			attenuation4(4),
			attenuation5(5),
			attenuation6(6),
			attenuation7(7),
			attenuation8(8),
			attenuation9(9),
			attenuation10(10),
			attenuation11(11),
			attenuation12(12),
			attenuation13(13),
			attenuation14(14),
			attenuation15(15),
			attenuation16(16),
			attenuation17(17),
			attenuation18(18),
			attenuation19(19),
			attenuation20(20),
			attenuation21(21),
			attenuation22(22),
			attenuation23(23),
			attenuation24(24),
			attenuation25(25),
			attenuation26(26),
			attenuation27(27),
			attenuation28(28),
			attenuation29(29),
			attenuation30(30),
			attenuation31(31),
			attenuation32(32),
			attenuation33(33),
			attenuation34(34),
			attenuation35(35),
			attenuation36(36),
			attenuation37(37),
			attenuation38(38),
			attenuation39(39),
			attenuation40(40)
			}

--   	
-- 
		SheAdslLineConfGainType ::= INTEGER
			{
			gain0(0),
			gain1(4096),
			gain2(8192),
			gain3(12288),
			gain4(16384),
			gain5(20480),
			gain6(24576),
			gain7(28672),
			auto(65280)
			}

		SheAdslLineConfRsFastOvrhdType ::= INTEGER
			{
			ovrHd50(1),
			ovrHd25(2),
			ovrHd12(3),
			ovrHd6(4),
			ovrHd3(5),
			ovrHd1(7),
			disable(15)
			}

		SheAdslLineConfEnableType ::= INTEGER
			{
			disable(0),
			enable(1)
			}

		SheAdslLineConfExpandedExchangeType ::= INTEGER
			{
			short(0),
			expanded(32768)
			}

		SheAdslLineConfEnableSpecial3Type ::= INTEGER
			{
			enable(0),
			disable(32768)
			}

		SheAdslLineConfEnableSpecial2Type ::= INTEGER
			{
			disable(0),
			enable(32768)
			}

		SheAdslLineConfNtrType ::= INTEGER
			{
			localOcs(0),
			refck8K(1)
			}

		SheAdslLineConfAnnexType ::= INTEGER
			{
			annexA(0),
			annexB(1),
			highSpeed(2),
			annexAdsl2(5),
			annexI(10),
			annexJ(11),
			annexM(12),
			dynamic(50)
			}

		SheAdslLineConfExtnProfileAlctlUsVerType ::= INTEGER (2)

		SheAdslLineConfIntDephtType ::= INTEGER
			{
			value64(0),
			value128(4096),
			value256(8192)
			}

		SheAdslLineConfAdvertisedCapabilitiesType ::= INTEGER
			{
			disable(0),
			annexA(1),
			annexb(2),
			annexI(9),
			annexJ(10),
			annexM(13),
			adslPlus(16),
			adslPlusAnnexA(17)
			}

--   
-- 
		SheAdslLineConfPsdMaskType ::= INTEGER
			{
			adsl(0),
			hsadslM1(3),
			hsadslM2(4),
			adsl2NonOvlpFlat(259),
			adsl2NonOvlpM1(275),
			adsl2NonOvlpM2(291),
			msk2Rf1(32768),
			flatMskRfi(32771),
			cabMsk2Rfi(32772)
			}

		SheAdslLineConfLineDmtConfModeType ::= INTEGER
			{
			ecMode(1),
			fdmMode(2)
			}

		SheAdslLineConfRsMemoryType ::= INTEGER
			{
			present(0),
			notpresent(32768)
			}

		SheAdslConfMinInpType ::= INTEGER
			{
			null(0),
			halfSymbol(50),
			oneSymbol(100),
			twoSymbol(200),
			threeSymbol(203),
			fourSymbol(204),
			fiveSymbol(205),
			sixSymbol(206),
			sevenSymbol(207),
			eigthSymbol(208),
			nineSymbol(209),
			tenSymbol(210),
			elevenSymbol(211),
			twelveSymbol(212),
			thirteenSymbol(213),
			fourteenSymbol(214),
			fifteenSymbol(215),
			sixteenSymbol(216),
			auto(400)
			}

		SheAdslLineConfUpstreamPSDMaskSelectionType ::= INTEGER
			{
			noSelection(0),
			adlu32eu32(1),
			adlu36eu36(2),
			adlu40eu40(3),
			adlu44eu44(4),
			adlu48eu48(5),
			adlu52eu52(6),
			adlu56eu56(7),
			adlu60eu60(8),
			adlu64eu64(9),
			extended(10),
			standard(11),
			jj100(12)
			}

		SheAdslControlPSDMASKdsRequestResultType ::= INTEGER
			{
			noRequest(1),
			commandSucceeded(2),
			psdDataWrongType(30),
			psdDataWrongLength(31),
			missingStartTone(32),
			missingEndTone(33),
			outOfToneRange(34),
			duplicateTone(35),
			oufOfInputPSD(36),
			oufOfPsdLevel(37),
			psdModeNotSupport(38),
			outOfNomPSDRange(39),
			outOfAtpRange(40)
			}

		SheAdslLineActionType ::= INTEGER
			{
			startup(0),
			spectrumReverb(5),
			analogLb(6),
			digitalLb(7),
			atmLb(10),
			spectrumMedley(26),
			spectrumPilot(27),
			spectrumCMtpr(30),
			spectrumRMtpr(32),
			hybridLossTest(33),
			rcvLinearityTest(34),
			rcvFilterTest(35),
			rcvPowerPerBinTest(36),
			idleNoisePerBinTest(37),
			totalIdleNoiseTest(38)
			}

		SheAdslLineClockType ::= INTEGER
			{
			oscillator(0),
			crystal(4)
			}

		SheAdslAtuxCapabilityType ::= BITS
			{
			q9921GspanPlusPotsNonOverlapped(0),
			q9921GspanPlusPotsOverlapped(1),
			q9923Adsl2PotsOverlapped(2),
			q9923Adsl2PotsNonOverlapped(3),
			q9925Adsl2PlusPotsOverlapped(4),
			q9925Adsl2PlusPotsNonOverlapped(5),
			q9923ReAdsl2PotsNonOverlapped(8),
			q9923ReAdsl2PotsOverlapped(9),
			q9925Adsl2PlusIsdnAllDigitalOverlapped(10),
			q9923Adsl2IsdnAllDigitalNonOverlapped(11),
			q9923Adsl2IsdnAllDigitalOverlapped(12),
			adslPlusPotsOverlapped(13),
			q9925Adsl2PlusIsdnNonOverlapped(14),
			q9925Adsl2PlusIsdnOverlapped(15),
			q9923Adsl2IsdnNonOverlapped(16),
			q9923Adsl2IsdnOverlapped(17),
			adslPlusPotsNonOverlapped(18),
			q9921TcmIsdnSymmetric(19),
			q9922TcmIsdnOverlapped(20),
			q9922TcmIsdnNonOverlapped(21),
			q9922PotsOverlapped(22),
			q9922PotsNonOverlapped(23),
			q9921TcmIsdnOverlapped(24),
			q9921TcmIsdnNonOverlapped(25),
			q9921IsdnOverlapped(26),
			q9921IsdnNonOverlapped(27),
			q9921PotsOverlapped(28),
			q9921PotsNonOverlapped(29),
			etsi(30),
			t1413(31),
			q9925Adsl2PlusPotsExtendedUpstreamNonOverlapped(32),
			q9925Adsl2PlusPotsExtendedUpstreamOverlapped(33),
			q9925Adsl2PlusPotsAllDigitalOverlapped(38),
			q9925Adsl2PlusPotsAllDigitalNonOverlapped(39),
			q9925Adsl2PlusIsdnAllDigitalNonOverlapped(51),
			q9923Adsl2PotsAllDigitalNonOverlapped(52),
			q9923Adsl2PotsAllDigitalOverlapped(53),
			q9923Adsl2PotsExtendedUpstreamNonOverlapped(56),
			q9923Adsl2PotsExtendedUpstreamOverlapped(57)
			}

		SheAdslLineCurrentStatusType ::= INTEGER
			{
			noError(1),
			lossOfFraming(2),
			lossOfSignal(4),
			lossOfPower(8),
			lossOfSignalQuality(16),
			lossOfLink(32),
			dataInitFailure(64),
			configInitFailure(128),
			protocolInitFailure(256),
			noPeerAtuPresent(512)
			}

		SheAdslLineOpStateType ::= INTEGER
			{
			idle(0),
			data(1),
			bootUpLoad(8),
			handshake(16),
			training(24),
			framerSync(26),
			fastRetrainInProg(27),
			discovery(46),
			llTest(128),
			dlTest(131),
			txTest(132),
			atmLpTest(133),
			deltTraining(139),
			delt(140)
			}

		SheAdslAtucPhysBertSyncType ::= INTEGER
			{
			bertOutOfSync(0),
			bertInSync(128)
			}

		SheAdslPhysAtucDeltLastTxStateType ::= INTEGER
			{
			dmtatucg9941(0),
			dmtatucquiet1(1),
			dmtatuccomb1(2),
			dmtatucquiet2(3),
			dmtatuccomb2(4),
			dmtatucicomb1(5),
			dmtatuclineprob(6),
			dmtatucquiet3(7),
			dmtatuccomb3(8),
			dmtatucicomb2(9),
			dmtatucmsgfmt(10),
			dmtatucmsgpcb(11),
			dmtatucquiet4(12),
			dmtatucreverb1(13),
			dmtatuctref1(14),
			dmtatucreverb2(15),
			dmtatucect(16),
			dmtatucreverb3(17),
			dmtatuctref2(18),
			dmtatucreverb4(19),
			dmtatucsegue1(20),
			dmtatucmsg1(21),
			dmtatucreverb5(22),
			dmtatucsegue2(23),
			dmtatucmedley(24),
			dmtatucexchmarker(25),
			dmtatucmsg2(26),
			dmtatucreverb6(27),
			dmtatucsegue3(28),
			dmtatucparams(29),
			dmtatucreverb7(30),
			dmtatucsegue4(31),
			dmtatucshowtime(32)
			}

		SheAdslPhysAturDeltLastTxStateType ::= INTEGER
			{
			dmtaturg9941(0),
			dmtaturquiet1(1),
			dmtaturcomb1(2),
			dmtaturquiet2(3),
			dmtaturcomb2(4),
			dmtaturicomb1(5),
			dmtaturlineprob(6),
			dmtaturquiet3(7),
			dmtaturcomb3(8),
			dmtaturicomb2(9),
			dmtaturmsgfmt(10),
			dmtaturmsgpcb(11),
			dmtaturreverb1(12),
			dmtaturquiet4(13),
			dmtaturreverb2(14),
			dmtaturquiet5(15),
			dmtaturreverb3(16),
			dmtaturect(17),
			dmtaturreverb4(18),
			dmtatursegue1(19),
			dmtaturreverb5(20),
			dmtatursegue2(21),
			dmtaturmsg1(22),
			dmtaturmedley(23),
			dmtaturexchmarker(24),
			dmtaturmsg2(25),
			dmtaturreverb6(26),
			dmtatursegue3(27),
			dmtaturparams(28),
			dmtaturreverb7(29),
			dmtatursegue4(30),
			dmtaturshowtime(31)
			}

--   
-- 
		SheAdslAtucPhysParametricTestResultType ::= INTEGER
			{
			ok(0),
			fail(1),
			dspIfFail(2)
			}

		SheAdslLineActStateType ::= INTEGER
			{
			noError(0),
			errPsdMaskds(1),
			errMaxNomPsdds(2),
			errMaxNomAtpds(3),
			errPsdMaskMaxBreakPoints(4),
			errPsdMode(5),
			errResultPsdMask(6),
			errPsdMaskConfig(7),
			warnG997PsdMaskConfig(8),
			warnG997PsdMaskConfigIndexOutOfRange(9),
			warnG997PsdMaskConfigLevelOutOfRange(10),
			warnG997PsdMaskConfigNoVaildBreakPoints(11),
			warnDevPsdMaskMaxBreakPoints(12),
			warnDevPsdMaskOufOfBandBreakPoints(13),
			warnDevPsdInternal(14),
			warnDevPsdMode(15)
			}

		SheAdslLineAtmStatus ::= INTEGER
			{
			noAtmDefect(0),
			noCellDeleniation(1),
			lossOfCellDeleniation(2)
			}

		SheAdslOamLevelType ::= INTEGER
			{
			undefined(0),
			f1(1),
			f2(2),
			f3(3),
			f4(4),
			f5(5)
			}

		SheAdslOamLoopTestType ::= INTEGER
			{
			none(0),
			segment(1),
			endToEnd(2)
			}

		SheAdslVccTpLoopTestResultType ::= INTEGER
			{
			segSuccess(0),
			segFailure(1),
			endToEndSuccess(2),
			endToEndFailure(3),
			aborted(4),
			progress(5),
			notAvailable(65535)
			}

--   
-- 
		SheAdslAtmQosType ::= INTEGER
			{
			unshaped(0),
			shapingCbr(1),
			shapingRtVbr(2),
			shapingNrtVbr(3),
			shapingUbr(4)
			}

		SheAdslLineConfEnableSpecial1Type ::= INTEGER
			{
			enable(1),
			disable(32768)
			}

		SheAdslLineTransAtucCapType ::= BITS
			{
			ansit1413(0),
			etsi(1),
			q9921PotsNonOverlapped(2),
			q9921PotsOverlapped(3),
			q9921IsdnNonOverlapped(4),
			q9921IsdnOverlapped(5),
			q9921TcmIsdnNonOverlapped(6),
			q9921TcmIsdnOverlapped(7),
			q9922PotsNonOverlapped(8),
			q9922PotsOverlapped(9),
			q9922TcmIsdnNonOverlapped(10),
			q9922TcmIsdnOverlapped(11),
			q9922TcmIsdnSymmetric(12),
			adslPlusPotsNonOverlapped(13)
			}

		SheAdslEnableType ::= INTEGER
			{
			enable(1),
			disable(2)
			}

--    L3 mode, no traffic
-- L0 mode, line runs in normal power
-- L2 mode, line runs in reduced power
		SheAdslPwrMgmtPMSFType ::= INTEGER
			{
			pmsfL3ToL0StateForce(0),
			pmsfL0ToL2StateForce(1),
			pmsfL3StateForce(2),
			pmsfL2ToL0StateForce(3)
			}

		SheAdslPwrMgmtStateType ::= INTEGER
			{
			idle(0),
			data(1),
			l2(141)
			}

		SheAdslPwrMgmtModeType ::= INTEGER
			{
			disable(0),
			l2Enabled(1),
			l2andl3Enabled(2)
			}

		SheAdslAtmEncapType ::= INTEGER
			{
			llc(1),
			vcMux(2)
			}

	
--
-- Textual conventions
--
	
		SheAdslLineDeltConfLDSFType ::= TEXTUAL-CONVENTION
			STATUS current
			DESCRIPTION 
				"DELT-related parameter. Not available for ADSL but ADSL2 and ADSL2plus."
			SYNTAX INTEGER
				{
				inhibit(0),
				force(1)
				}

		SheAdslChannelType ::= TEXTUAL-CONVENTION
			STATUS current
			DESCRIPTION 
				"The used adsl bearer channel type."
			SYNTAX INTEGER
				{
				interleaved(1),
				fast(2)
				}

	
--
-- Node definitions
--
	
-- 1.3.6.1.4.1.231.7.1.2.2.1.6.1
		sheAdslMibObjects OBJECT IDENTIFIER ::= { sheAdslMib 1 }

		
--   1.3.6.1.4.1.231.7.1.2.2.1.6.1.1
		sheAdslLineMIB OBJECT IDENTIFIER ::= { sheAdslMibObjects 1 }

		
--   1.3.6.1.4.1.231.7.1.2.2.1.6.1.1.1
-- THIS ELEMENT AND HIS CONTENT WILL NOT LONGER BE SUPPORTED BY NE up R2.5.
		sheDslSystemParamGroup OBJECT IDENTIFIER ::= { sheAdslLineMIB 1 }

		
--   1.3.6.1.4.1.231.7.1.2.2.1.6.1.1.1.1
		sheDslSystemDslType OBJECT-TYPE
			SYNTAX SheDslSystemType
			MAX-ACCESS read-only
			STATUS current
			DESCRIPTION
				"This object identifies the firmware to be downloaded.
				adsl(1),
				sdsl(2),
				shdsl(3)
				"
			::= { sheDslSystemParamGroup 1 }

		
--   1.3.6.1.4.1.231.7.1.2.2.1.6.1.1.1.2
		sheDslSystemLineCodingType OBJECT-TYPE
			SYNTAX SheDslSystemLineCodingType
			MAX-ACCESS read-only
			STATUS current
			DESCRIPTION
				"This object indicates ADSL line code type.
				other(1),
				dmt(2),
				cap(3),
				qam(4)
				"
			::= { sheDslSystemParamGroup 2 }

		
--   1.3.6.1.4.1.231.7.1.2.2.1.6.1.1.1.3
		sheDslSystemLineTxCfg OBJECT-TYPE
			SYNTAX SheDslSystemTxCfgType
			MAX-ACCESS read-only
			STATUS current
			DESCRIPTION
				"This object indicates transmission capabilities with which the DSL system is configured.
				unused(0),
				etsi(1),
				q9921PotsNonOverlapped(2),
				q9921PotsOverlapped(3),
				q9921IsdnNonOverlapped(4),
				q9921IsdnOverlapped(5),
				q9921TcmIsdnNonOverlapped(6),
				q9921TcmIsdnOverlapped(7),
				q9922PotsNonOverlapped(8),
				q9922PotsOverlapped(9),
				q9922TcmIsdnNonOverlapped(10),
				q9922TcmIsdnOverlapped(11),
				q9922TcmIsdnSymmetric(12),
				adslPlusPotsNonOverlapped(13)
				"
			::= { sheDslSystemParamGroup 3 }

		
--   1.3.6.1.4.1.231.7.1.2.2.1.6.1.1.2
-- THIS ELEMENT AND HIS CONTENT WILL NOT LONGER BE SUPPORTED BY NE up R2.5.
		sheDslSystemParamControl OBJECT IDENTIFIER ::= { sheAdslLineMIB 2 }

		
--   1.3.6.1.4.1.231.7.1.2.2.1.6.1.1.2.1
		sheDslSystemParamControlRequest OBJECT-TYPE
			SYNTAX SheAdslControlRequestType
			MAX-ACCESS read-write
			STATUS current
			DESCRIPTION
				"setDslSystemLineTxCfg:
				sheDslSystemParamControlLineTxCfg"
			::= { sheDslSystemParamControl 1 }

		
--   1.3.6.1.4.1.231.7.1.2.2.1.6.1.1.2.2
		sheDslSystemParamControlStatus OBJECT-TYPE
			SYNTAX SheControlStatusType
			MAX-ACCESS read-only
			STATUS current
			DESCRIPTION
				"The status of a user command. 
				"
			::= { sheDslSystemParamControl 2 }

		
--   1.3.6.1.4.1.231.7.1.2.2.1.6.1.1.2.3
		sheDslSystemParamControlTimer OBJECT-TYPE
			SYNTAX Gauge32
			MAX-ACCESS read-only
			STATUS current
			DESCRIPTION
				"The maximum wait time for the manager for a long running user command. 
				"
			::= { sheDslSystemParamControl 3 }

		
--   1.3.6.1.4.1.231.7.1.2.2.1.6.1.1.2.4
		sheDslSystemParamControlReqResult OBJECT-TYPE
			SYNTAX SheAdslControlRequestResultType
			MAX-ACCESS read-only
			STATUS current
			DESCRIPTION
				"The result of the last user command."
			::= { sheDslSystemParamControl 4 }

		
--   1.3.6.1.4.1.231.7.1.2.2.1.6.1.1.2.5
		sheDslSystemParamControlTimeStamp OBJECT-TYPE
			SYNTAX Unsigned32
			UNITS "sec"
			MAX-ACCESS read-only
			STATUS current
			DESCRIPTION
				"The time stamp of the last command (end of command)."
			::= { sheDslSystemParamControl 5 }

		
--   1.3.6.1.4.1.231.7.1.2.2.1.6.1.1.2.6
		sheDslSystemParamControlLineTxCfg OBJECT-TYPE
			SYNTAX SheDslSystemTxCfgType
			MAX-ACCESS read-write
			STATUS current
			DESCRIPTION
				"This object indicates transmission capabilities with which the DSL system is configured."
			::= { sheDslSystemParamControl 6 }

		
--   1.3.6.1.4.1.231.7.1.2.2.1.6.1.1.3
-- THIS ELEMENT AND HIS CONTENT WILL NOT LONGER BE SUPPORTED BY NE up R2.5.
		sheAdslSystemCapabilityGroup OBJECT IDENTIFIER ::= { sheAdslLineMIB 3 }

		
--   1.3.6.1.4.1.231.7.1.2.2.1.6.1.1.3.1
		sheAdslCapabilityLineTxCap OBJECT-TYPE
			SYNTAX SheDslSystemTxCfgType
			MAX-ACCESS read-only
			STATUS current
			DESCRIPTION
				"This bitmap specifies all transmission modes, which the ATU-C is capable of supporting. Right now support for Annex A (q9921PotsNonOverlapped(2) and q9921PotsOverlapped(3)) is present.  This value depends on the DSL PHY firmware present on Columbia MND
				unused(0),
				etsi(1),
				q9921PotsNonOverlapped(2),
				q9921PotsOverlapped(3),
				q9921IsdnNonOverlapped(4),
				q9921IsdnOverlapped(5),
				q9921TcmIsdnNonOverlapped(6),
				q9921TcmIsdnOverlapped(7),
				q9922PotsNonOverlapped(8),
				q9922PotsOverlapped(9),
				q9922TcmIsdnNonOverlapped(10),
				q9922TcmIsdnOverlapped(11),
				q9922TcmIsdnSymmetric(12),
				adslPlusPotsNonOverlapped(13)
				"
			::= { sheAdslSystemCapabilityGroup 1 }

		
--       Profile Group
-- 
-- 1.3.6.1.4.1.231.7.1.2.2.1.6.1.1.4
		sheAdslLineConfProfileTable OBJECT-TYPE
			SYNTAX SEQUENCE OF SheAdslLineConfProfileEntry
			MAX-ACCESS not-accessible
			STATUS current
			DESCRIPTION
				"This table contains information on the ADSL line
				configuration. One entry in this table reflects a
				profile defined by a manager which can be used to
				configure the ADSL line."
			::= { sheAdslLineMIB 4 }

		
--   1.3.6.1.4.1.231.7.1.2.2.1.6.1.1.4.1
		sheAdslLineConfProfileEntry OBJECT-TYPE
			SYNTAX SheAdslLineConfProfileEntry
			MAX-ACCESS not-accessible
			STATUS current
			DESCRIPTION
				"Each entry consists of a list of parameters that
				represents the configuration of an ADSL modem.
				
				`Dynamic' profiles are implemented. A default
				profile will always exist.  This profile's name will
				be set to `DEFVAL' and its parameters will be set
				to vendor specific values, unless otherwise specified
				in this document.
				
				"
			INDEX { sheAdslLineConfProfileIndex }
			::= { sheAdslLineConfProfileTable 1 }

		
		SheAdslLineConfProfileEntry ::=
			SEQUENCE { 
				sheAdslLineConfProfileIndex
					Integer32,
				sheAdslLineConfProfileName
					SnmpAdminString,
				sheAdslLineConfProfileAtucConfRateMode
					SheAdslLineConfRateModeType,
				sheAdslLineConfProfileAtucConfRateChanRatio
					INTEGER,
				sheAdslLineConfProfileAtucConfTargetSnrMgn
					INTEGER,
				sheAdslLineConfProfileAtucConfMaxSnrMgn
					INTEGER,
				sheAdslLineConfProfileAtucConfMinSnrMgn
					INTEGER,
				sheAdslLineConfProfileAtucConfDownshiftSnrMgn
					INTEGER,
				sheAdslLineConfProfileAtucConfUpshiftSnrMgn
					INTEGER,
				sheAdslLineConfProfileAtucConfMinUpshiftTime
					INTEGER,
				sheAdslLineConfProfileAtucConfMinDownshiftTime
					INTEGER,
				sheAdslLineConfProfileAtucChanConfFastMinTxRate
					Unsigned32,
				sheAdslLineConfProfileAtucChanConfInterleaveMinTxRate
					Unsigned32,
				sheAdslLineConfProfileAtucChanConfFastMaxTxRate
					Unsigned32,
				sheAdslLineConfProfileAtucChanConfInterleaveMaxTxRate
					Unsigned32,
				sheAdslLineConfProfileAtucChanConfMaxInterleaveDelay
					INTEGER,
				sheAdslLineConfProfileAturConfRateMode
					SheAdslLineConfRateModeType,
				sheAdslLineConfProfileAturConfRateChanRatio
					INTEGER,
				sheAdslLineConfProfileAturConfTargetSnrMgn
					INTEGER,
				sheAdslLineConfProfileAturConfMaxSnrMgn
					INTEGER,
				sheAdslLineConfProfileAturConfMinSnrMgn
					INTEGER,
				sheAdslLineConfProfileAturConfDownshiftSnrMgn
					INTEGER,
				sheAdslLineConfProfileAturConfUpshiftSnrMgn
					INTEGER,
				sheAdslLineConfProfileAturConfMinUpshiftTime
					INTEGER,
				sheAdslLineConfProfileAturConfMinDownshiftTime
					INTEGER,
				sheAdslLineConfProfileAturChanConfFastMinTxRate
					Unsigned32,
				sheAdslLineConfProfileAturChanConfInterleaveMinTxRate
					Unsigned32,
				sheAdslLineConfProfileAturChanConfFastMaxTxRate
					Unsigned32,
				sheAdslLineConfProfileAturChanConfInterleaveMaxTxRate
					Unsigned32,
				sheAdslLineConfProfileAturChanConfMaxInterleaveDelay
					INTEGER,
				sheAdslLineConfProfileTrellis
					SheAdslLineTrellisModeType,
				sheAdslLineConfProfileAtucConfPwrMgmtL0Time
					INTEGER,
				sheAdslLineConfProfileAtucConfPwrMgmtL2Time
					INTEGER,
				sheAdslLineConfProfileAtucConfPwrMgmtL2ATPR
					INTEGER,
				sheAdslLineConfProfileAtucConfPwrMgmtL2Rate
					INTEGER,
				sheAdslLineConfProfileAtucConfPwrMgmtMode
					SheAdslPwrMgmtModeType
			 }

--   
-- 
-- 1.3.6.1.4.1.231.7.1.2.2.1.6.1.1.4.1.1
		sheAdslLineConfProfileIndex OBJECT-TYPE
			SYNTAX Integer32 (1..300)
			MAX-ACCESS read-only
			STATUS current
			DESCRIPTION
				"The table index."
			::= { sheAdslLineConfProfileEntry 1 }

		
--   1.3.6.1.4.1.231.7.1.2.2.1.6.1.1.4.1.2
		sheAdslLineConfProfileName OBJECT-TYPE
			SYNTAX SnmpAdminString (SIZE (1..32))
			MAX-ACCESS read-only
			STATUS current
			DESCRIPTION
				"This object is used by the line configuration table
				in order to identify a row of this table.
				
				Dynamic profiles are implemented. The profile
				name is user specified.  Also, the system will always
				provide a default profile whose name is `DEFVAL' for Annex A
				and DEFVAL_ISDN fpr Annex B card's (both Adsl2+).
				
				Special characters are not allowed, like:  space : ?
				"
			::= { sheAdslLineConfProfileEntry 2 }

		
--   1.3.6.1.4.1.231.7.1.2.2.1.6.1.1.4.1.3
		sheAdslLineConfProfileAtucConfRateMode OBJECT-TYPE
			SYNTAX SheAdslLineConfRateModeType
			MAX-ACCESS read-only
			STATUS current
			DESCRIPTION
				"Defines what form of transmit rate adaptation is
				configured on this modem.  See ADSL Forum TR-005 [3]
				for more information.
					fixed(1),
					adaptAtStartup(2),
					adaptAtRuntime(3)
				"
			::= { sheAdslLineConfProfileEntry 3 }

		
--   1.3.6.1.4.1.231.7.1.2.2.1.6.1.1.4.1.4
		sheAdslLineConfProfileAtucConfRateChanRatio OBJECT-TYPE
			SYNTAX INTEGER (0..100)
			UNITS "%"
			MAX-ACCESS read-only
			STATUS current
			DESCRIPTION
				"Configured allocation ratio of excess transmit bandwidth between fast and interleaved channels.
				Only applies when two channel mode and rate adaptive DSL are supported.
				A ratio of 20% means, that 20 % of the available data rate (in access of the minimum rate summend over
				all bearer channels) will be assigned to the fast channel and 80% to the interleaved channel.
				
				Only valid if sheAdslLineConfExtnProfileLineType is set to dualLatency mode."
			REFERENCE
				"G997.1 chapter 7.3.2.1.4"
			DEFVAL { 0 }
			::= { sheAdslLineConfProfileEntry 4 }

		
--   1.3.6.1.4.1.231.7.1.2.2.1.6.1.1.4.1.5
		sheAdslLineConfProfileAtucConfTargetSnrMgn OBJECT-TYPE
			SYNTAX INTEGER (0..310)
			UNITS "tenth dB"
			MAX-ACCESS read-only
			STATUS current
			DESCRIPTION
				"Configured Target Signal/Noise Margin.
				This is the Noise Margin the modem must achieve
				with a BER of 10-7 or better to successfully complete
				initialization."
			DEFVAL { 60 }
			::= { sheAdslLineConfProfileEntry 5 }

		
--   1.3.6.1.4.1.231.7.1.2.2.1.6.1.1.4.1.6
		sheAdslLineConfProfileAtucConfMaxSnrMgn OBJECT-TYPE
			SYNTAX INTEGER (0..310)
			UNITS "tenth dB"
			MAX-ACCESS read-only
			STATUS current
			DESCRIPTION
				"Configured Maximum acceptable Signal/Noise Margin.
				If the Noise Margin is above this the modem should
				attempt to reduce its power output to optimize its
				operation."
			DEFVAL { 310 }
			::= { sheAdslLineConfProfileEntry 6 }

		
--   1.3.6.1.4.1.231.7.1.2.2.1.6.1.1.4.1.7
		sheAdslLineConfProfileAtucConfMinSnrMgn OBJECT-TYPE
			SYNTAX INTEGER (0..310)
			UNITS "tenth dB"
			MAX-ACCESS read-only
			STATUS current
			DESCRIPTION
				"Configured Minimum acceptable Signal/Noise Margin.
				If the noise margin falls below this level, the modem
				should attempt to increase its power output.  If that
				is not possible the modem will attempt to
				re-initialize or shut down."
			DEFVAL { 0 }
			::= { sheAdslLineConfProfileEntry 7 }

		
--   1.3.6.1.4.1.231.7.1.2.2.1.6.1.1.4.1.8
		sheAdslLineConfProfileAtucConfDownshiftSnrMgn OBJECT-TYPE
			SYNTAX INTEGER (0..310)
			UNITS "tenth dB"
			MAX-ACCESS read-only
			STATUS current
			DESCRIPTION
				"Configured Signal/Noise Margin for rate downshift.
				If the noise margin falls below this level, the modem
				should attempt to decrease its transmit rate.  In
				the case that adaptAtRuntime mode is not present,
				the value will be 'don't care'."
			DEFVAL { 30 }
			::= { sheAdslLineConfProfileEntry 8 }

		
--   1.3.6.1.4.1.231.7.1.2.2.1.6.1.1.4.1.9
		sheAdslLineConfProfileAtucConfUpshiftSnrMgn OBJECT-TYPE
			SYNTAX INTEGER (0..310)
			UNITS "tenth dB"
			MAX-ACCESS read-only
			STATUS current
			DESCRIPTION
				"Configured Signal/Noise Margin for rate upshift.
				If the noise margin rises above this level, the modem
				should attempt to increase its transmit rate.
				In the case that adaptAtRuntime mode is not present,
				the value will be 'don't care'."
			DEFVAL { 120 }
			::= { sheAdslLineConfProfileEntry 9 }

		
--   1.3.6.1.4.1.231.7.1.2.2.1.6.1.1.4.1.10
		sheAdslLineConfProfileAtucConfMinUpshiftTime OBJECT-TYPE
			SYNTAX INTEGER (0..16383)
			UNITS "seconds"
			MAX-ACCESS read-only
			STATUS current
			DESCRIPTION
				"Minimum time that the current margin is above
				UpshiftSnrMgn before an upshift occurs.
				In the case that adaptAtRuntime mode is not present,
				the value will be 'don't care'."
			::= { sheAdslLineConfProfileEntry 10 }

		
--   1.3.6.1.4.1.231.7.1.2.2.1.6.1.1.4.1.11
		sheAdslLineConfProfileAtucConfMinDownshiftTime OBJECT-TYPE
			SYNTAX INTEGER (0..16383)
			UNITS "seconds"
			MAX-ACCESS read-only
			STATUS current
			DESCRIPTION
				"Minimum time that the current margin is below
				DownshiftSnrMgn before a downshift occurs.
				In the case that adaptAtRuntime mode is not present,
				the value will be 'don't care'."
			::= { sheAdslLineConfProfileEntry 11 }

		
--   1.3.6.1.4.1.231.7.1.2.2.1.6.1.1.4.1.12
		sheAdslLineConfProfileAtucChanConfFastMinTxRate OBJECT-TYPE
			SYNTAX Unsigned32 (32..32736)
			UNITS "kbps"
			MAX-ACCESS read-only
			STATUS current
			DESCRIPTION
				"Configured Minimum Transmit rate for `Fast' channels,
				in kbps.  See adslAtucConfRateChanRatio for information
				regarding RADSL mode and ATUR transmit rate for
				ATUC receive rates.
				Only multiples of 32 will be configured. "
			REFERENCE
				"G997.1 chapter 7.3.2.1.1 / 7.3.2.1.2"
			::= { sheAdslLineConfProfileEntry 12 }

		
--   1.3.6.1.4.1.231.7.1.2.2.1.6.1.1.4.1.13
		sheAdslLineConfProfileAtucChanConfInterleaveMinTxRate OBJECT-TYPE
			SYNTAX Unsigned32 (32..32736)
			UNITS "kbps"
			MAX-ACCESS read-only
			STATUS current
			DESCRIPTION
				"Configured Minimum Transmit rate for `Interleave'
				channels, in kbps.  See adslAtucConfRateChanRatio for
				information regarding RADSL mode and see
				ATUR transmit rate for receive rates.
				Only multiples of 32 will be configured."
			REFERENCE
				"G997.1 chapter 7.3.2.1.1 / 7.3.2.1.2"
			::= { sheAdslLineConfProfileEntry 13 }

		
--   1.3.6.1.4.1.231.7.1.2.2.1.6.1.1.4.1.14
		sheAdslLineConfProfileAtucChanConfFastMaxTxRate OBJECT-TYPE
			SYNTAX Unsigned32 (32..32736)
			UNITS "kbps"
			MAX-ACCESS read-only
			STATUS current
			DESCRIPTION
				"Configured Maximum Transmit rate for `Fast' channels,
				in kbps.  See adslAtucConfRateChanRatio for information
				regarding RADSL mode and see ATUR transmit rate for
				ATUC receive rates.
				Only multiples of 32 will be configured."
			REFERENCE
				"G997.1 chapter 7.3.2.1.3"
			::= { sheAdslLineConfProfileEntry 14 }

		
--   1.3.6.1.4.1.231.7.1.2.2.1.6.1.1.4.1.15
		sheAdslLineConfProfileAtucChanConfInterleaveMaxTxRate OBJECT-TYPE
			SYNTAX Unsigned32 (32..32736)
			UNITS "kbps"
			MAX-ACCESS read-only
			STATUS current
			DESCRIPTION
				"Configured Maximum Transmit rate for `Interleave'
				channels, in kbps.  See adslAtucConfRateChanRatio for
				information regarding RADSL mode and ATUR transmit
				rate for ATUC receive rates.
				Only multiples of 32 will be configured."
			REFERENCE
				"G997.1 chapter 7.3.2.1.3"
			::= { sheAdslLineConfProfileEntry 15 }

		
--   1.3.6.1.4.1.231.7.1.2.2.1.6.1.1.4.1.16
		sheAdslLineConfProfileAtucChanConfMaxInterleaveDelay OBJECT-TYPE
			SYNTAX INTEGER (1..63)
			UNITS "milli-seconds"
			MAX-ACCESS read-only
			STATUS current
			DESCRIPTION
				"Configured maximum Interleave Delay for this channel.
				
				Interleave delay applies only to the interleave channel
				and defines the mapping (relative spacing) between
				subsequent input bytes at the interleaver input and
				their placement in the bit stream at the interleaver
				output.  Larger numbers provide greater separation
				between consecutive input bytes in the output bit
				stream allowing for improved impulse noise immunity
				at the expense of payload latency."
			::= { sheAdslLineConfProfileEntry 16 }

		
--   1.3.6.1.4.1.231.7.1.2.2.1.6.1.1.4.1.17
		sheAdslLineConfProfileAturConfRateMode OBJECT-TYPE
			SYNTAX SheAdslLineConfRateModeType
			MAX-ACCESS read-only
			STATUS current
			DESCRIPTION
				"Defines what form of transmit rate adaptation is
				configured on this modem.  See ADSL Forum TR-005 [3]
				for more information.
					fixed(1),
					adaptAtStartup(2),
					adaptAtRuntime(3)
				"
			::= { sheAdslLineConfProfileEntry 17 }

		
--   1.3.6.1.4.1.231.7.1.2.2.1.6.1.1.4.1.18
		sheAdslLineConfProfileAturConfRateChanRatio OBJECT-TYPE
			SYNTAX INTEGER (0..100)
			UNITS "%"
			MAX-ACCESS read-only
			STATUS current
			DESCRIPTION
				"Configured allocation ratio of excess transmit bandwidth between fast and interleaved channels.
				Only applies when two channel mode and rate adaptive DSL are supported.
				A ratio of 20% means, that 20 % of the available data rate (in access of the minimum rate summend over
				all bearer channels) will be assigned to the fast channel and 80% to the interleaved channel.
				
				Only valid if sheAdslLineConfExtnProfileLineType is set to dualLatency mode."
			DEFVAL { 0 }
			::= { sheAdslLineConfProfileEntry 18 }

		
--   1.3.6.1.4.1.231.7.1.2.2.1.6.1.1.4.1.19
		sheAdslLineConfProfileAturConfTargetSnrMgn OBJECT-TYPE
			SYNTAX INTEGER (0..310)
			UNITS "tenth dB"
			MAX-ACCESS read-only
			STATUS current
			DESCRIPTION
				"Configured Target Signal/Noise Margin.
				This is the Noise Margin the modem must achieve
				with a BER of 10-7 or better to successfully complete
				initialization."
			DEFVAL { 60 }
			::= { sheAdslLineConfProfileEntry 19 }

		
--   1.3.6.1.4.1.231.7.1.2.2.1.6.1.1.4.1.20
		sheAdslLineConfProfileAturConfMaxSnrMgn OBJECT-TYPE
			SYNTAX INTEGER (0..310)
			UNITS "tenth dB"
			MAX-ACCESS read-only
			STATUS current
			DESCRIPTION
				"Configured Maximum acceptable Signal/Noise Margin.
				If the Noise Margin is above this the modem should
				attempt to reduce its power output to optimize its
				operation."
			DEFVAL { 310 }
			::= { sheAdslLineConfProfileEntry 20 }

		
--   1.3.6.1.4.1.231.7.1.2.2.1.6.1.1.4.1.21
		sheAdslLineConfProfileAturConfMinSnrMgn OBJECT-TYPE
			SYNTAX INTEGER (0..310)
			UNITS "tenth dB"
			MAX-ACCESS read-only
			STATUS current
			DESCRIPTION
				"Configured Minimum acceptable Signal/Noise Margin.
				If the noise margin falls below this level, the modem
				should attempt to increase its power output.  If that
				is not possible the modem will attempt to
				re-initialize or shut down."
			DEFVAL { 0 }
			::= { sheAdslLineConfProfileEntry 21 }

		
--   1.3.6.1.4.1.231.7.1.2.2.1.6.1.1.4.1.22
		sheAdslLineConfProfileAturConfDownshiftSnrMgn OBJECT-TYPE
			SYNTAX INTEGER (0..310)
			UNITS "tenth dB"
			MAX-ACCESS read-only
			STATUS current
			DESCRIPTION
				"Configured Signal/Noise Margin for rate downshift.
				If the noise margin falls below this level, the modem
				should attempt to decrease its transmit rate.
				In the case that adaptAtRuntime mode is not present,
				the value will be 'don't care'."
			DEFVAL { 30 }
			::= { sheAdslLineConfProfileEntry 22 }

		
--   1.3.6.1.4.1.231.7.1.2.2.1.6.1.1.4.1.23
		sheAdslLineConfProfileAturConfUpshiftSnrMgn OBJECT-TYPE
			SYNTAX INTEGER (0..310)
			UNITS "tenth dB"
			MAX-ACCESS read-only
			STATUS current
			DESCRIPTION
				"Configured Signal/Noise Margin for rate upshift.
				If the noise margin rises above this level, the modem
				should attempt to increase its transmit rate.
				In the case that adaptAtRuntime mode is not present,
				the value will be 'don't care'."
			DEFVAL { 120 }
			::= { sheAdslLineConfProfileEntry 23 }

		
--   1.3.6.1.4.1.231.7.1.2.2.1.6.1.1.4.1.24
		sheAdslLineConfProfileAturConfMinUpshiftTime OBJECT-TYPE
			SYNTAX INTEGER (0..16383)
			UNITS "seconds"
			MAX-ACCESS read-only
			STATUS current
			DESCRIPTION
				"Minimum time that the current margin is above
				UpshiftSnrMgn before an upshift occurs.
				In the case that adaptAtRuntime mode is not present,
				the value will be 'don't care'."
			::= { sheAdslLineConfProfileEntry 24 }

		
--   1.3.6.1.4.1.231.7.1.2.2.1.6.1.1.4.1.25
		sheAdslLineConfProfileAturConfMinDownshiftTime OBJECT-TYPE
			SYNTAX INTEGER (0..16383)
			UNITS "seconds"
			MAX-ACCESS read-only
			STATUS current
			DESCRIPTION
				"Minimum time that the current margin is below
				DownshiftSnrMgn before a downshift occurs.
				In the case that adaptAtRuntime mode is not present,
				the value will be 'don't care'."
			::= { sheAdslLineConfProfileEntry 25 }

		
--   1.3.6.1.4.1.231.7.1.2.2.1.6.1.1.4.1.26
		sheAdslLineConfProfileAturChanConfFastMinTxRate OBJECT-TYPE
			SYNTAX Unsigned32 (32..3520)
			UNITS "kbps"
			MAX-ACCESS read-only
			STATUS current
			DESCRIPTION
				"Configured Minimum Transmit rate for `Fast' channels,
				in kbps.  See adslAturConfRateChanRatio for information
				regarding RADSL mode and ATUC transmit rate
				for ATUR receive rates.
				Only multiples of 32 will be configured."
			REFERENCE
				"G997.1 chapter 7.3.2.1.1 / 7.3.2.1.2"
			::= { sheAdslLineConfProfileEntry 26 }

		
--   1.3.6.1.4.1.231.7.1.2.2.1.6.1.1.4.1.27
		sheAdslLineConfProfileAturChanConfInterleaveMinTxRate OBJECT-TYPE
			SYNTAX Unsigned32 (32..3520)
			UNITS "kbps"
			MAX-ACCESS read-only
			STATUS current
			DESCRIPTION
				"Configured Minimum Transmit rate for `Interleave'
				channels, in kbps.  See adslAturConfRateChanRatio for
				information regarding RADSL mode and ATUC transmit rate
				for ATUR receive rates.
				Only multiples of 32 will be configured."
			REFERENCE
				"G997.1 chapter 7.3.2.1.1 / 7.3.2.1.2"
			::= { sheAdslLineConfProfileEntry 27 }

		
--   1.3.6.1.4.1.231.7.1.2.2.1.6.1.1.4.1.28
		sheAdslLineConfProfileAturChanConfFastMaxTxRate OBJECT-TYPE
			SYNTAX Unsigned32 (32..3520)
			UNITS "kbps"
			MAX-ACCESS read-only
			STATUS current
			DESCRIPTION
				"Configured Maximum Transmit rate for `Fast' channels,
				in kbps.  See adslAturConfRateChanRatio for information
				regarding RADSL mode and ATUC transmit rate
				for ATUR receive rates.
				Only multiples of 32 will be configured."
			REFERENCE
				"G997.1 chapter 7.3.2.1.3"
			::= { sheAdslLineConfProfileEntry 28 }

		
--   1.3.6.1.4.1.231.7.1.2.2.1.6.1.1.4.1.29
		sheAdslLineConfProfileAturChanConfInterleaveMaxTxRate OBJECT-TYPE
			SYNTAX Unsigned32 (32..3520)
			UNITS "kbps"
			MAX-ACCESS read-only
			STATUS current
			DESCRIPTION
				"Configured Maximum Transmit rate for `Interleave'
				channels, in kbps.  See adslAturConfRateChanRatio for
				information regarding RADSL mode and see
				ATUC transmit rate for ATUR receive rates.
				Only multiples of 32 will be configured."
			REFERENCE
				"G997.1 chapter 7.3.2.1.3"
			::= { sheAdslLineConfProfileEntry 29 }

		
--   1.3.6.1.4.1.231.7.1.2.2.1.6.1.1.4.1.30
		sheAdslLineConfProfileAturChanConfMaxInterleaveDelay OBJECT-TYPE
			SYNTAX INTEGER (1..63)
			UNITS "milli-seconds"
			MAX-ACCESS read-only
			STATUS current
			DESCRIPTION
				"Configured maximum Interleave Delay for this channel.
				
				Interleave delay applies only to the interleave channel
				and defines the mapping (relative spacing) between
				subsequent input bytes at the interleaver input and
				their placement in the bit stream at the interleaver
				output.  Larger numbers provide greater separation
				between consecutive input bytes in the output bit
				stream allowing for improved impulse noise immunity
				at the expense of payload latency."
			::= { sheAdslLineConfProfileEntry 30 }

		
--   1.3.6.1.4.1.231.7.1.2.2.1.6.1.1.4.1.31
		sheAdslLineConfProfileTrellis OBJECT-TYPE
			SYNTAX SheAdslLineTrellisModeType
			MAX-ACCESS read-only
			STATUS current
			DESCRIPTION
				"Indicates if Trelliscoding is enabled or not. If TrellisCoding is used is indicated in sheAdslLineTable and 
				depence also on the Atur-Capabilities.
				The NE will not accept setting trellisOff. It is automatically controlled by firmware and will be switched off if ATU-R 
				will not support this."
			DEFVAL { 1 }
			::= { sheAdslLineConfProfileEntry 31 }

		
		sheAdslLineConfProfileAtucConfPwrMgmtL0Time OBJECT-TYPE
			SYNTAX INTEGER (0..255)
			UNITS "sec"
			MAX-ACCESS read-only
			STATUS current
			DESCRIPTION
				"This parameter represents the minimum time (in seconds)
				between an exit from the L2 state and the next entry into
				the L2 state. It ranges from 0 to 255 seconds.
				
				Only valid for Adsl2 and Adsl2Plus."
			REFERENCE
				"G997.1 chapter 7.3.1.1.5"
			::= { sheAdslLineConfProfileEntry 32 }

		
		sheAdslLineConfProfileAtucConfPwrMgmtL2Time OBJECT-TYPE
			SYNTAX INTEGER (0..255)
			UNITS "sec"
			MAX-ACCESS read-only
			STATUS current
			DESCRIPTION
				"This parameter represents the minimum time (in seconds)
				between an Entry into the L2 state and the first
				Power Trim in the L2 state and between two consecutive
				Power Trims in the L2 State. It ranges from 0 to 255 seconds.
				
				Only valid for Adsl2 and Adsl2Plus."
			REFERENCE
				"G997.1 chapter 7.3.1.1.6"
			::= { sheAdslLineConfProfileEntry 33 }

		
		sheAdslLineConfProfileAtucConfPwrMgmtL2ATPR OBJECT-TYPE
			SYNTAX INTEGER (0..310)
			UNITS "dB/10"
			MAX-ACCESS read-only
			STATUS current
			DESCRIPTION
				"This parameter represents the maximum aggregate transmit
				power reduction (in dB) that can be performed through
				a single Power Trim in the L2 state.
				It ranges from 0 dB/10 to 310 dB/10.
				
				Only valid for Adsl2 and Adsl2Plus."
			REFERENCE
				"G997.1 chapter 7.3.1.1.7"
			::= { sheAdslLineConfProfileEntry 34 }

		
		sheAdslLineConfProfileAtucConfPwrMgmtL2Rate OBJECT-TYPE
			SYNTAX INTEGER (8000..1024000)
			UNITS "bit/s"
			MAX-ACCESS read-only
			STATUS current
			DESCRIPTION
				"This parameter specifies the minimum net data rate during
				the low power state (L2). The data rate is coded in bit/s,
				and can range from 0x1F40 (8000) bps to 0xFA000 (1024000) bps.
				
				Only valid for Adsl2 and Adsl2Plus."
			::= { sheAdslLineConfProfileEntry 35 }

		
		sheAdslLineConfProfileAtucConfPwrMgmtMode OBJECT-TYPE
			SYNTAX SheAdslPwrMgmtModeType
			MAX-ACCESS read-only
			STATUS current
			DESCRIPTION
				"Which ADSL Power Management state is enabled.
				
				Only valid for Adsl2 and Adsl2Plus."
			REFERENCE
				"G997.1 chapter 7.3.1.1.4"
			::= { sheAdslLineConfProfileEntry 36 }

		
--   1.3.6.1.4.1.231.7.1.2.2.1.6.1.1.5
		sheAdslLineConfProfileControl OBJECT IDENTIFIER ::= { sheAdslLineMIB 5 }

		
--   1.3.6.1.4.1.231.7.1.2.2.1.6.1.1.5.1
		sheAdslLineConfProfileControlRequest OBJECT-TYPE
			SYNTAX SheAdslControlRequestType
			MAX-ACCESS read-write
			STATUS current
			DESCRIPTION
				"The different Controltypes for profile creation could be used to select predefined
				values for the supported standard.
				
				createAdslLineConfProfile            (Adsl2PlusAnnexA)
				createAdslLineConfProfileAnnexA
				createAdslLineConfProfileAnnexB
				createAdslLineConfProfileAdsl2PlusAnnexB   
				createAdslLineConfProfileAdsl2AnnexI
				createAdslLineConfProfileAdsl2AnnexJ
				createAdslLineConfProfileAdsl2PlusAnnexI
				createAdslLineConfProfileAdsl2PlusAnnexJ
				createAdslLineConfProfileAdsl2AnnexM
				createAdslLineConfProfileAdsl2PlusAnnexM
				sheAdslLineConfProfileControlName
				...
				
				modifyAdslLineConfProfile
				sheAdslLineConfProfileControlIndex
				sheAdslLineConfProfileControlName
				...
				
				deleteAdslLineConfProfile
				sheAdslLineConfProfileControlIndex
				sheAdslLineConfProfileControlName
				
				New with R2.8:
				createAdslLineConfProfileAdsl2PlusDynamic
				sheAdslLineConfProfileControlName"
			::= { sheAdslLineConfProfileControl 1 }

		
--   1.3.6.1.4.1.231.7.1.2.2.1.6.1.1.5.2
		sheAdslLineConfProfileControlIndex OBJECT-TYPE
			SYNTAX Integer32
			MAX-ACCESS read-write
			STATUS current
			DESCRIPTION
				"Index of the configured table-entry. Needed for modify or delete."
			::= { sheAdslLineConfProfileControl 2 }

		
--   1.3.6.1.4.1.231.7.1.2.2.1.6.1.1.5.3
		sheAdslLineConfProfileControlStatus OBJECT-TYPE
			SYNTAX SheControlStatusType
			MAX-ACCESS read-only
			STATUS current
			DESCRIPTION
				"The status of a user command. 
				"
			::= { sheAdslLineConfProfileControl 3 }

		
--   1.3.6.1.4.1.231.7.1.2.2.1.6.1.1.5.4
		sheAdslLineConfProfileControlTimer OBJECT-TYPE
			SYNTAX Gauge32
			MAX-ACCESS read-only
			STATUS current
			DESCRIPTION
				"The maximum wait time for the manager for a long running user command. 
				"
			::= { sheAdslLineConfProfileControl 4 }

		
--   1.3.6.1.4.1.231.7.1.2.2.1.6.1.1.5.5
		sheAdslLineConfProfileControlReqResult OBJECT-TYPE
			SYNTAX SheAdslControlRequestResultType
			MAX-ACCESS read-only
			STATUS current
			DESCRIPTION
				"The result of the last user command."
			::= { sheAdslLineConfProfileControl 5 }

		
--   1.3.6.1.4.1.231.7.1.2.2.1.6.1.1.5.6
		sheAdslLineConfProfileControlTimeStamp OBJECT-TYPE
			SYNTAX Unsigned32
			UNITS "sec"
			MAX-ACCESS read-only
			STATUS current
			DESCRIPTION
				"The time stamp of the last command (end of command)."
			::= { sheAdslLineConfProfileControl 6 }

		
--   1.3.6.1.4.1.231.7.1.2.2.1.6.1.1.5.7
		sheAdslLineConfProfileControlName OBJECT-TYPE
			SYNTAX SnmpAdminString
			MAX-ACCESS read-write
			STATUS current
			DESCRIPTION
				"Descriptional name."
			::= { sheAdslLineConfProfileControl 7 }

		
--   1.3.6.1.4.1.231.7.1.2.2.1.6.1.1.5.8
		sheAdslLineConfProfileControlAtucConfRateMode OBJECT-TYPE
			SYNTAX SheAdslLineConfRateModeType
			MAX-ACCESS read-write
			STATUS current
			DESCRIPTION
				"Defines what form of transmit rate adaptation is
				configured on this modem.  See ADSL Forum TR-005 [3]
				for more information."
			::= { sheAdslLineConfProfileControl 8 }

		
--   1.3.6.1.4.1.231.7.1.2.2.1.6.1.1.5.9
		sheAdslLineConfProfileControlAtucConfRateChanRatio OBJECT-TYPE
			SYNTAX INTEGER (0..100)
			UNITS "%"
			MAX-ACCESS read-write
			STATUS current
			DESCRIPTION
				"Configured allocation ratio of excess transmit bandwidth between fast and interleaved channels.
				Only applies when two channel mode and rate adaptive DSL are supported.
				A ratio of 20% means, that 20 % of the available data rate (in access of the minimum rate summend over
				all bearer channels) will be assigned to the fast channel and 80% to the interleaved channel.
				
				Only valid if sheAdslLineConfExtnProfileLineType is set to dualLatency mode."
			::= { sheAdslLineConfProfileControl 9 }

		
--    
-- 1.3.6.1.4.1.231.7.1.2.2.1.6.1.1.5.10
		sheAdslLineConfProfileControlAtucConfTargetSnrMgn OBJECT-TYPE
			SYNTAX INTEGER (0..310)
			UNITS "tenth dB"
			MAX-ACCESS read-write
			STATUS current
			DESCRIPTION
				"Configured Target Signal/Noise Margin.
				This is the Noise Margin the modem must achieve
				with a BER of 10-7 or better to successfully complete
				initialization."
			::= { sheAdslLineConfProfileControl 10 }

		
--   1.3.6.1.4.1.231.7.1.2.2.1.6.1.1.5.11
		sheAdslLineConfProfileControlAtucConfMaxSnrMgn OBJECT-TYPE
			SYNTAX INTEGER (0..310)
			UNITS "tenth dB"
			MAX-ACCESS read-write
			STATUS current
			DESCRIPTION
				"Configured Maximum acceptable Signal/Noise Margin.
				If the Noise Margin is above this the modem should
				attempt to reduce its power output to optimize its
				operation."
			::= { sheAdslLineConfProfileControl 11 }

		
--   1.3.6.1.4.1.231.7.1.2.2.1.6.1.1.5.12
		sheAdslLineConfProfileControlAtucConfMinSnrMgn OBJECT-TYPE
			SYNTAX INTEGER (0..310)
			UNITS "tenth dB"
			MAX-ACCESS read-write
			STATUS current
			DESCRIPTION
				"Configured Minimum acceptable Signal/Noise Margin.
				If the noise margin falls below this level, the modem
				should attempt to increase its power output.  If that
				is not possible the modem will attempt to
				re-initialize or shut down."
			::= { sheAdslLineConfProfileControl 12 }

		
--   1.3.6.1.4.1.231.7.1.2.2.1.6.1.1.5.13
		sheAdslLineConfProfileControlAtucConfDownshiftSnrMgn OBJECT-TYPE
			SYNTAX INTEGER (0..310)
			UNITS "tenth dB"
			MAX-ACCESS read-write
			STATUS current
			DESCRIPTION
				"Configured Signal/Noise Margin for rate downshift.
				If the noise margin falls below this level, the modem
				should attempt to decrease its transmit rate.  In
				the case that RADSL mode is not present,
				the value will be `0'."
			::= { sheAdslLineConfProfileControl 13 }

		
--   1.3.6.1.4.1.231.7.1.2.2.1.6.1.1.5.14
		sheAdslLineConfProfileControlAtucConfUpshiftSnrMgn OBJECT-TYPE
			SYNTAX INTEGER (0..310)
			UNITS "tenth dB"
			MAX-ACCESS read-write
			STATUS current
			DESCRIPTION
				"Configured Signal/Noise Margin for rate upshift.
				If the noise margin rises above this level, the modem
				should attempt to increase its transmit rate.    In
				the case that RADSL is not present, the value will
				be `0'."
			::= { sheAdslLineConfProfileControl 14 }

		
--   1.3.6.1.4.1.231.7.1.2.2.1.6.1.1.5.15
		sheAdslLineConfProfileControlAtucConfMinUpshiftTime OBJECT-TYPE
			SYNTAX INTEGER (0..16383)
			UNITS "seconds"
			MAX-ACCESS read-write
			STATUS current
			DESCRIPTION
				"Minimum time that the current margin is above
				UpshiftSnrMgn before an upshift occurs.
				In the case that RADSL is not present, the value will
				be `0'."
			::= { sheAdslLineConfProfileControl 15 }

		
--   1.3.6.1.4.1.231.7.1.2.2.1.6.1.1.5.16
		sheAdslLineConfProfileControlAtucConfMinDownshiftTime OBJECT-TYPE
			SYNTAX INTEGER (0..16383)
			UNITS "seconds"
			MAX-ACCESS read-write
			STATUS current
			DESCRIPTION
				"Minimum time that the current margin is below
				DownshiftSnrMgn before a downshift occurs.
				In the case that RADSL mode is not present,
				the value will be `0'."
			::= { sheAdslLineConfProfileControl 16 }

		
--   1.3.6.1.4.1.231.7.1.2.2.1.6.1.1.5.17
		sheAdslLineConfProfileControlAtucChanConfFastMinTxRate OBJECT-TYPE
			SYNTAX Unsigned32 (0..32736)
			UNITS "kbps"
			MAX-ACCESS read-write
			STATUS current
			DESCRIPTION
				"Configured Minimum Transmit rate for `Fast' channels,
				in kbps.  See adslAtucConfRateChanRatio for information
				regarding RADSL mode and ATUR transmit rate for
				ATUC receive rates.
				Only multiples of 32 will be configured."
			::= { sheAdslLineConfProfileControl 17 }

		
--   1.3.6.1.4.1.231.7.1.2.2.1.6.1.1.5.18
		sheAdslLineConfProfileControlAtucChanConfInterleaveMinTxRate OBJECT-TYPE
			SYNTAX Unsigned32 (0..32736)
			UNITS "kbps"
			MAX-ACCESS read-write
			STATUS current
			DESCRIPTION
				"Configured Minimum Transmit rate for `Interleave'
				channels, in kbps.  See adslAtucConfRateChanRatio for
				information regarding RADSL mode and see
				ATUR transmit rate for receive rates.
				Only multiples of 32 will be configured."
			::= { sheAdslLineConfProfileControl 18 }

		
--   1.3.6.1.4.1.231.7.1.2.2.1.6.1.1.5.19
		sheAdslLineConfProfileControlAtucChanConfFastMaxTxRate OBJECT-TYPE
			SYNTAX Unsigned32 (32..32736)
			UNITS "kbps"
			MAX-ACCESS read-write
			STATUS current
			DESCRIPTION
				"Configured Maximum Transmit rate for `Fast' channels,
				in kbps.  See adslAtucConfRateChanRatio for information
				regarding RADSL mode and see ATUR transmit rate for
				ATUC receive rates.
				Only multiples of 32 will be configured."
			::= { sheAdslLineConfProfileControl 19 }

		
--   1.3.6.1.4.1.231.7.1.2.2.1.6.1.1.5.20
		sheAdslLineConfProfileControlAtucChanConfInterleaveMaxTxRate OBJECT-TYPE
			SYNTAX Unsigned32 (32..32736)
			UNITS "kbps"
			MAX-ACCESS read-write
			STATUS current
			DESCRIPTION
				"Configured Maximum Transmit rate for `Interleave'
				channels, in kbps.  See adslAtucConfRateChanRatio for
				information regarding RADSL mode and ATUR transmit
				rate for ATUC receive rates.
				Only multiples of 32 will be configured."
			::= { sheAdslLineConfProfileControl 20 }

		
--   1.3.6.1.4.1.231.7.1.2.2.1.6.1.1.5.21
		sheAdslLineConfProfileControlAtucChanConfMaxInterleaveDelay OBJECT-TYPE
			SYNTAX INTEGER (0..255)
			UNITS "milli-seconds"
			MAX-ACCESS read-write
			STATUS current
			DESCRIPTION
				"Configured maximum Interleave Delay for this channel.
				
				Interleave delay applies only to the interleave channel
				and defines the mapping (relative spacing) between
				subsequent input bytes at the interleaver input and
				their placement in the bit stream at the interleaver
				output.  Larger numbers provide greater separation
				between consecutive input bytes in the output bit
				stream allowing for improved impulse noise immunity
				at the expense of payload latency."
			::= { sheAdslLineConfProfileControl 21 }

		
--   1.3.6.1.4.1.231.7.1.2.2.1.6.1.1.5.22
		sheAdslLineConfProfileControlAturConfRateMode OBJECT-TYPE
			SYNTAX SheAdslLineConfRateModeType
			MAX-ACCESS read-write
			STATUS current
			DESCRIPTION
				"Defines what form of transmit rate adaptation is
				configured on this modem.  See ADSL Forum TR-005 [3]
				for more information."
			::= { sheAdslLineConfProfileControl 22 }

		
--   1.3.6.1.4.1.231.7.1.2.2.1.6.1.1.5.23
		sheAdslLineConfProfileControlAturConfRateChanRatio OBJECT-TYPE
			SYNTAX INTEGER (0..100)
			UNITS "%"
			MAX-ACCESS read-write
			STATUS current
			DESCRIPTION
				"Configured allocation ratio of excess transmit bandwidth between fast and interleaved channels.
				Only applies when two channel mode and rate adaptive DSL are supported.
				A ratio of 20% means, that 20 % of the available data rate (in access of the minimum rate summend over
				all bearer channels) will be assigned to the fast channel and 80% to the interleaved channel.
				
				Only valid if sheAdslLineConfExtnProfileLineType is set to dualLatency mode."
			::= { sheAdslLineConfProfileControl 23 }

		
--   1.3.6.1.4.1.231.7.1.2.2.1.6.1.1.5.24
		sheAdslLineConfProfileControlAturConfTargetSnrMgn OBJECT-TYPE
			SYNTAX INTEGER (0..310)
			UNITS "tenth dB"
			MAX-ACCESS read-write
			STATUS current
			DESCRIPTION
				"Configured Target Signal/Noise Margin.
				This is the Noise Margin the modem must achieve
				with a BER of 10-7 or better to successfully complete
				initialization."
			::= { sheAdslLineConfProfileControl 24 }

		
--   1.3.6.1.4.1.231.7.1.2.2.1.6.1.1.5.25
		sheAdslLineConfProfileControlAturConfMaxSnrMgn OBJECT-TYPE
			SYNTAX INTEGER (0..310)
			UNITS "tenth dB"
			MAX-ACCESS read-write
			STATUS current
			DESCRIPTION
				"Configured Maximum acceptable Signal/Noise Margin.
				If the Noise Margin is above this the modem should
				attempt to reduce its power output to optimize its
				operation."
			::= { sheAdslLineConfProfileControl 25 }

		
--   1.3.6.1.4.1.231.7.1.2.2.1.6.1.1.5.26
		sheAdslLineConfProfileControlAturConfMinSnrMgn OBJECT-TYPE
			SYNTAX INTEGER (0..310)
			UNITS "tenth dB"
			MAX-ACCESS read-write
			STATUS current
			DESCRIPTION
				"Configured Minimum acceptable Signal/Noise Margin.
				If the noise margin falls below this level, the modem
				should attempt to increase its power output.  If that
				is not possible the modem will attempt to
				re-initialize or shut down."
			::= { sheAdslLineConfProfileControl 26 }

		
--   1.3.6.1.4.1.231.7.1.2.2.1.6.1.1.5.27
		sheAdslLineConfProfileControlAturConfDownshiftSnrMgn OBJECT-TYPE
			SYNTAX INTEGER (0..310)
			UNITS "tenth dB"
			MAX-ACCESS read-write
			STATUS current
			DESCRIPTION
				"Configured Signal/Noise Margin for rate downshift.
				If the noise margin falls below this level, the modem
				should attempt to decrease its transmit rate.
				In the case that RADSL mode is not present,
				the value will be `0'."
			::= { sheAdslLineConfProfileControl 27 }

		
--   1.3.6.1.4.1.231.7.1.2.2.1.6.1.1.5.28
		sheAdslLineConfProfileControlAturConfUpshiftSnrMgn OBJECT-TYPE
			SYNTAX INTEGER (0..310)
			UNITS "tenth dB"
			MAX-ACCESS read-write
			STATUS current
			DESCRIPTION
				"Configured Signal/Noise Margin for rate upshift.
				If the noise margin rises above this level, the modem
				should attempt to increase its transmit rate.
				In the case that RADSL is not present,
				the value will be `0'."
			::= { sheAdslLineConfProfileControl 28 }

		
--   1.3.6.1.4.1.231.7.1.2.2.1.6.1.1.5.29
		sheAdslLineConfProfileControlAturConfMinUpshiftTime OBJECT-TYPE
			SYNTAX INTEGER (0..16383)
			UNITS "seconds"
			MAX-ACCESS read-write
			STATUS current
			DESCRIPTION
				"Minimum time that the current margin is above
				UpshiftSnrMgn before an upshift occurs.
				In the case that RADSL is not present, the value will
				be `0'."
			::= { sheAdslLineConfProfileControl 29 }

		
--   1.3.6.1.4.1.231.7.1.2.2.1.6.1.1.5.30
		sheAdslLineConfProfileControlAturConfMinDownshiftTime OBJECT-TYPE
			SYNTAX INTEGER (0..16383)
			UNITS "seconds"
			MAX-ACCESS read-write
			STATUS current
			DESCRIPTION
				"Minimum time that the current margin is below
				DownshiftSnrMgn before a downshift occurs.
				In the case that RADSL mode is not present,
				the value will be `0'."
			::= { sheAdslLineConfProfileControl 30 }

		
--   1.3.6.1.4.1.231.7.1.2.2.1.6.1.1.5.31
		sheAdslLineConfProfileControlAturChanConfFastMinTxRate OBJECT-TYPE
			SYNTAX Unsigned32 (0..3520)
			UNITS "kbps"
			MAX-ACCESS read-write
			STATUS current
			DESCRIPTION
				"Configured Minimum Transmit rate for `Fast' channels,
				in kbps.  See adslAturConfRateChanRatio for information
				regarding RADSL mode and ATUC transmit rate
				for ATUR receive rates.
				Only multiples of 32 will be configured."
			::= { sheAdslLineConfProfileControl 31 }

		
--   1.3.6.1.4.1.231.7.1.2.2.1.6.1.1.5.32
		sheAdslLineConfProfileControlAturChanConfInterleaveMinTxRate OBJECT-TYPE
			SYNTAX Unsigned32 (0..3520)
			UNITS "kbps"
			MAX-ACCESS read-write
			STATUS current
			DESCRIPTION
				"Configured Minimum Transmit rate for `Interleave'
				channels, in kbps.  See adslAturConfRateChanRatio for
				information regarding RADSL mode and ATUC transmit rate
				for ATUR receive rates.
				Only multiples of 32 will be configured."
			::= { sheAdslLineConfProfileControl 32 }

		
--   1.3.6.1.4.1.231.7.1.2.2.1.6.1.1.5.33
		sheAdslLineConfProfileControlAturChanConfFastMaxTxRate OBJECT-TYPE
			SYNTAX Unsigned32 (32..3520)
			UNITS "kbps"
			MAX-ACCESS read-write
			STATUS current
			DESCRIPTION
				"Configured Maximum Transmit rate for `Fast' channels,
				in kbps.  See adslAturConfRateChanRatio for information
				regarding RADSL mode and ATUC transmit rate
				for ATUR receive rates.
				Only multiples of 32 will be configured."
			::= { sheAdslLineConfProfileControl 33 }

		
--   1.3.6.1.4.1.231.7.1.2.2.1.6.1.1.5.34
		sheAdslLineConfProfileControlAturChanConfInterleaveMaxTxRate OBJECT-TYPE
			SYNTAX Unsigned32 (32..3520)
			UNITS "kbps"
			MAX-ACCESS read-write
			STATUS current
			DESCRIPTION
				"Configured Maximum Transmit rate for `Interleave'
				channels, in kbps.  See adslAturConfRateChanRatio for
				information regarding RADSL mode and see
				ATUC transmit rate for ATUR receive rates.
				Only multiples of 32 will be configured."
			::= { sheAdslLineConfProfileControl 34 }

		
--   1.3.6.1.4.1.231.7.1.2.2.1.6.1.1.5.35
		sheAdslLineConfProfileControlAturChanConfMaxInterleaveDelay OBJECT-TYPE
			SYNTAX INTEGER (0..255)
			UNITS "milli-seconds"
			MAX-ACCESS read-write
			STATUS current
			DESCRIPTION
				"Configured maximum Interleave Delay for this channel.
				
				Interleave delay applies only to the interleave channel
				and defines the mapping (relative spacing) between
				subsequent input bytes at the interleaver input and
				their placement in the bit stream at the interleaver
				output.  Larger numbers provide greater separation
				between consecutive input bytes in the output bit
				stream allowing for improved impulse noise immunity
				at the expense of payload latency."
			::= { sheAdslLineConfProfileControl 35 }

		
--   1.3.6.1.4.1.231.7.1.2.2.1.6.1.1.5.36
		sheAdslLineConfProfileControlTrellis OBJECT-TYPE
			SYNTAX SheAdslLineTrellisModeType
			MAX-ACCESS read-write
			STATUS current
			DESCRIPTION
				"Indicates if Trelliscoding is enabled or not. If TrellisCoding is used is indicated in sheAdslLineTable and 
				depence also on the Atur-Capabilities.
				Do not touch!"
			::= { sheAdslLineConfProfileControl 36 }

		
		sheAdslLineConfProfileControlAtucConfPwrMgmtL0Time OBJECT-TYPE
			SYNTAX INTEGER (0..255)
			UNITS "seconds"
			MAX-ACCESS read-write
			STATUS current
			DESCRIPTION
				"This parameter represents the minimum time (in seconds)
				between an exit from the L2 state and the next entry into
				the L2 state. It ranges from 0 to 255 seconds.
				
				Only valid for Adsl2 and Adsl2Plus."
			::= { sheAdslLineConfProfileControl 37 }

		
		sheAdslLineConfProfileControlAtucConfPwrMgmtL2Time OBJECT-TYPE
			SYNTAX INTEGER (0..255)
			UNITS "seconds"
			MAX-ACCESS read-write
			STATUS current
			DESCRIPTION
				"This parameter represents the minimum time (in seconds)
				between an Entry into the L2 state and the first
				Power Trim in the L2 state and between two consecutive
				Power Trims in the L2 State. It ranges from 0 to 255 seconds.
				
				Only valid for Adsl2 and Adsl2Plus."
			::= { sheAdslLineConfProfileControl 38 }

		
		sheAdslLineConfProfileControlAtucConfPwrMgmtL2ATPR OBJECT-TYPE
			SYNTAX INTEGER (0..310)
			UNITS "dB/10"
			MAX-ACCESS read-write
			STATUS current
			DESCRIPTION
				"This parameter represents the maximum aggregate transmit
				power reduction (in dB) that can be performed through
				a single Power Trim in the L2 state.
				It ranges from 0 dB/10 to 310 dB/10.
				
				Only valid for Adsl2 and Adsl2Plus."
			::= { sheAdslLineConfProfileControl 39 }

		
		sheAdslLineConfProfileControlAtucConfPwrMgmtL2Rate OBJECT-TYPE
			SYNTAX INTEGER (8000..1024000)
			UNITS "bit/s"
			MAX-ACCESS read-write
			STATUS current
			DESCRIPTION
				"This parameter specifies the minimum net data rate during
				the low power state (L2). The data rate is coded in bit/s,
				and can range from 0x1F40 (8000) bps to 0xFA000 (1024000) bps.
				
				Only valid for Adsl2 and Adsl2Plus."
			::= { sheAdslLineConfProfileControl 40 }

		
		sheAdslLineConfProfileControlAtucConfPwrMgmtMode OBJECT-TYPE
			SYNTAX SheAdslPwrMgmtModeType
			MAX-ACCESS read-write
			STATUS current
			DESCRIPTION
				"Which ADSL Power Management state is enabled.
				
				Only valid for Adsl2 and Adsl2Plus."
			::= { sheAdslLineConfProfileControl 41 }

		
--   1.3.6.1.4.1.231.7.1.2.2.1.6.1.1.6
		sheAdslLineConfExtnProfileTable OBJECT-TYPE
			SYNTAX SEQUENCE OF SheAdslLineConfExtnProfileEntry
			MAX-ACCESS not-accessible
			STATUS current
			DESCRIPTION
				"This table contains information on the ADSL line
				configuration. One entry in this table reflects a
				profile defined by a manager which can be used to
				configure the ADSL line."
			::= { sheAdslLineMIB 6 }

		
--   1.3.6.1.4.1.231.7.1.2.2.1.6.1.1.6.1
		sheAdslLineConfExtnProfileEntry OBJECT-TYPE
			SYNTAX SheAdslLineConfExtnProfileEntry
			MAX-ACCESS not-accessible
			STATUS current
			DESCRIPTION
				"Each entry consists of a list of parameters that represents the configuration of an ADSL modem. 
				The index is used from the sheAdslLineConfProfileTable. 
				                            "
			INDEX { sheAdslLineConfProfileIndex }
			::= { sheAdslLineConfExtnProfileTable 1 }

		
		SheAdslLineConfExtnProfileEntry ::=
			SEQUENCE { 
				sheAdslLineConfExtnProfileParametricTestInputFile
					DisplayString,
				sheAdslLineConfExtnProfileRsIntCorrectionUp
					SheAdslLineConfRsIntCorrectionType,
				sheAdslLineConfExtnProfileLineType
					SheAdslConfLineType,
				sheAdslLineConfExtnProfileTxEndBin
					INTEGER,
				sheAdslLineConfExtnProfileTxStartBin
					INTEGER,
				sheAdslLineConfExtnProfileMaxBitsPerBin
					INTEGER,
				sheAdslLineConfExtnProfileRxStartBin
					INTEGER,
				sheAdslLineConfExtnProfileRxEndBin
					INTEGER,
				sheAdslLineConfExtnProfileRxBinAdjust
					SheAdslLineConfExtnProfileRxBinAdjustType,
				sheAdslLineConfExtnProfileTriggerMode
					SheAdslLineConfTriggerModeType,
				sheAdslLineConfExtnProfileAdi2x
					SheAdslLineConfExtnProfileAdi2xType,
				sheAdslLineConfExtnProfileStandard
					SheAdslLineConfStandardType,
				sheAdslLineConfExtnProfileInitiate
					SheAdslLineConfInitiateType,
				sheAdslLineConfExtnProfileTxPowerAttenuation
					SheAdslLineConfAttenuationType,
				sheAdslLineConfExtnProfileCodingGain
					SheAdslLineConfGainType,
				sheAdslLineConfExtnProfileRsFastOvrhdDown
					SheAdslLineConfRsFastOvrhdType,
				sheAdslLineConfExtnProfileIntCorrectionDown
					SheAdslLineConfRsIntCorrectionType,
				sheAdslLineConfExtnProfileRsFastOvrhdUp
					SheAdslLineConfRsFastOvrhdType,
				sheAdslLineConfExtnProfileDrStby
					SheAdslLineConfEnableType,
				sheAdslLineConfExtnProfileExpandedExchange
					SheAdslLineConfExpandedExchangeType,
				sheAdslLineConfExtnProfileEscapeFastRetrainEnable
					SheAdslLineConfEnableType,
				sheAdslLineConfExtnProfileFastRetrainEnable
					SheAdslLineConfEnableSpecial3Type,
				sheAdslLineConfExtnProfileBitSwap
					SheAdslLineConfEnableSpecial2Type,
				sheAdslLineConfExtnProfileNtr
					SheAdslLineConfNtrType,
				sheAdslLineConfExtnProfileAnnexType
					SheAdslLineConfAnnexType,
				sheAdslLineConfExtnProfileAlctlUsVer
					SheAdslLineConfExtnProfileAlctlUsVerType,
				sheAdslLineConfExtnProfileUseCustomBin
					SheAdslLineConfEnableSpecial2Type,
				sheAdslLineConfExtnProfileDnBinUsage
					OCTET STRING,
				sheAdslLineConfExtnProfileMaxDCo
					SheAdslLineConfIntDephtType,
				sheAdslLineConfExtnProfileFullRetrain
					SheAdslLineConfEnableSpecial3Type,
				sheAdslLineConfExtnProfileAdvertisedCapabilities
					SheAdslLineConfAdvertisedCapabilitiesType,
				sheAdslLineConfExtnProfilePsdMaskType
					SheAdslLineConfPsdMaskType,
				sheAdslLineConfExtnProfileLineDmtConfMode
					SheAdslLineConfLineDmtConfModeType,
				sheAdslLineConfExtnProfileEraseProfiles
					SheAdslLineConfEnableSpecial2Type,
				sheAdslLineConfExtnProfileRsMemory
					SheAdslLineConfRsMemoryType,
				sheAdslLineConfExtnProfileParamHybridLossTestStart
					INTEGER,
				sheAdslLineConfExtnProfileParamHybridLossTestEnd
					INTEGER,
				sheAdslLineConfExtnProfileConfMinInp
					SheAdslConfMinInpType,
				sheAdslLineConfExtnProfileRfiBandMask
					OCTET STRING,
				sheAdslLineConfExtnProfileUpstreamPsdMaskSelection
					SheAdslLineConfUpstreamPSDMaskSelectionType,
				sheAdslLineConfExtnProfileMaxNomPsdDs
					INTEGER,
				sheAdslLineConfExtnProfileMaxNomAtpDs
					Gauge32,
				sheAdslLineConfExtnProfilePsdMaskDs
					OCTET STRING,
				sheAdslLineConfExtnProfilePSDMASKdsEnable
					SheAdslLineConfEnableType,
				sheAdslLineConfExtnProfileConfMinInpUs
					SheAdslConfMinInpType
			 }

--   1.3.6.1.4.1.231.7.1.2.2.1.6.1.1.6.1.1
		sheAdslLineConfExtnProfileParametricTestInputFile OBJECT-TYPE
			SYNTAX DisplayString
			MAX-ACCESS read-only
			STATUS current
			DESCRIPTION
				"Indicates Name of the Input file from which to take the Mask Array Size, lower 
				and upper mask Array. Null string means no file is specified.
				Functionality is not supported!"
			::= { sheAdslLineConfExtnProfileEntry 1 }

		
--   1.3.6.1.4.1.231.7.1.2.2.1.6.1.1.6.1.2
		sheAdslLineConfExtnProfileRsIntCorrectionUp OBJECT-TYPE
			SYNTAX SheAdslLineConfRsIntCorrectionType
			MAX-ACCESS read-only
			STATUS current
			DESCRIPTION
				"Sets the correction time for the upstream-interleaved buffer. RS can also be 
				disabled. The Default Value for ADSL+ is 3.
				value125us(3),
				value250us(4),
				value500us(5),
				value1ms(6),
				value2ms(7),
				value4ms(8),
				disable(15)
				"
			::= { sheAdslLineConfExtnProfileEntry 2 }

		
--   1.3.6.1.4.1.231.7.1.2.2.1.6.1.1.6.1.3
		sheAdslLineConfExtnProfileLineType OBJECT-TYPE
			SYNTAX SheAdslConfLineType
			MAX-ACCESS read-only
			STATUS current
			DESCRIPTION
				"This parameter provisions the DSL physical entity at start-up by defining whether
				and how the line will be channelized, i.e. which channel type(s) are supported.
				
				Defined values are:
				
				fastOnly(2)           -- only fast channel exists (singleLatency)
				interleavedOnly(3)    -- only interleaved channel exists (singleLatency, default)
				fastAndInterleaved(5) -- both fast and interleaved channels (dualLatency)
				                         exist
				
				In case of dualLatency (mode 5), the parameter's sheAdslLineConfProfileAtucConfRateChanRatio
				and sheAdslLineConfProfileAturConfRateChanRatio configures the bandwith distribution.
				
				IMPORTANT NOTE:
				The configuration of dualLatency mode is only available for NE releases up R2.5!!
				The modification is only possible for profiles, which are NOT IN USE!"
			DEFVAL { 3 }
			::= { sheAdslLineConfExtnProfileEntry 3 }

		
--   1.3.6.1.4.1.231.7.1.2.2.1.6.1.1.6.1.4
		sheAdslLineConfExtnProfileTxEndBin OBJECT-TYPE
			SYNTAX INTEGER (6..511 | 65535)
			MAX-ACCESS read-only
			STATUS current
			DESCRIPTION
				"Highest bin number allowed for Tx signal. The Range & default for ADSL+ is 
				0x06 - 0x1ff respectively.
				
				NE will not accept any changes and use always default value!
				Ne will select the correct values depending on the configuration of the following values:
				- AnnexType
				- DmtConfMode
				- AdvertisedCapability
				
				New with R2.8:
				If the used annexType was set to 'dynamic', no values of Tx/Rx bins could be set here,
				because this will be done by the IU depending on the used HW and choosen standard.
				The profile configuration will be set to value 65535 (0xffff) which means 'autoSelect'."
			DEFVAL { 511 }
			::= { sheAdslLineConfExtnProfileEntry 4 }

		
--   1.3.6.1.4.1.231.7.1.2.2.1.6.1.1.6.1.5
		sheAdslLineConfExtnProfileTxStartBin OBJECT-TYPE
			SYNTAX INTEGER (6..511 | 65535)
			MAX-ACCESS read-only
			STATUS current
			DESCRIPTION
				"Lowest bin number allowed for Tx signal.The Range for ADSL+ is 0x06 - 0x1ff. 
				The Default for Annex B is 58 respectively. For AnnexA it is 32.
				
				NE will not accept any changes and use always default value!
				Ne will select the correct values depending on the configuration of the following values:
				- AnnexType
				- DmtConfMode
				- AdvertisedCapability
				
				New with R2.8:
				If the used annexType was set to 'dynamic', no values of Tx/Rx bins could be set here,
				because this will be done by the IU depending on the used HW and choosen standard.
				The profile configuration will be set to value 65535 (0xffff) which means 'autoSelect'."
			DEFVAL { 32 }
			::= { sheAdslLineConfExtnProfileEntry 5 }

		
--   1.3.6.1.4.1.231.7.1.2.2.1.6.1.1.6.1.6
		sheAdslLineConfExtnProfileMaxBitsPerBin OBJECT-TYPE
			SYNTAX INTEGER (0..15)
			MAX-ACCESS read-only
			STATUS current
			DESCRIPTION
				"Maximum Rx number of bits per bin.
				
				NE will not accept any changes and use always default value!"
			DEFVAL { 14 }
			::= { sheAdslLineConfExtnProfileEntry 6 }

		
--   1.3.6.1.4.1.231.7.1.2.2.1.6.1.1.6.1.7
		sheAdslLineConfExtnProfileRxStartBin OBJECT-TYPE
			SYNTAX INTEGER (1..57 | 65535)
			MAX-ACCESS read-only
			STATUS current
			DESCRIPTION
				"Lowest bin number allowed for Rx signal. Default value for AnnexA is 6 and 32 for AnnexB.
				
				NE will not accept any changes and use always default value!
				Ne will select the correct values depending on the configuration of the following values:
				- AnnexType
				- DmtConfMode
				- AdvertisedCapability
				
				New with R2.8:
				If the used annexType was set to 'dynamic', no values of Tx/Rx bins could be set here,
				because this will be done by the IU depending on the used HW and choosen standard.
				The profile configuration will be set to value 65535 (0xffff) which means 'autoSelect'."
			DEFVAL { 6 }
			::= { sheAdslLineConfExtnProfileEntry 7 }

		
--   1.3.6.1.4.1.231.7.1.2.2.1.6.1.1.6.1.8
		sheAdslLineConfExtnProfileRxEndBin OBJECT-TYPE
			SYNTAX INTEGER (6..64 | 65535)
			MAX-ACCESS read-only
			STATUS current
			DESCRIPTION
				"Highest bin number allowed for Rx signal. Default Value for AnnexA is 31 and 57 for AnnexB.
				
				NE will not accept any changes and use always default value!
				Ne will select the correct values depending on the configuration of the following values:
				- AnnexType
				- DmtConfMode
				- AdvertisedCapability
				
				New with R2.8:
				If the used annexType was set to 'dynamic', no values of Tx/Rx bins could be set here,
				because this will be done by the IU depending on the used HW and choosen standard.
				The profile configuration will be set to value 65535 (0xffff) which means 'autoSelect'."
			DEFVAL { 31 }
			::= { sheAdslLineConfExtnProfileEntry 8 }

		
--   1.3.6.1.4.1.231.7.1.2.2.1.6.1.1.6.1.9
		sheAdslLineConfExtnProfileRxBinAdjust OBJECT-TYPE
			SYNTAX SheAdslLineConfExtnProfileRxBinAdjustType
			MAX-ACCESS read-only
			STATUS current
			DESCRIPTION
				"Employs Rx Start/End bin settings.
				
				NE will not accept any changes and use always default value!"
			DEFVAL { 0 }
			::= { sheAdslLineConfExtnProfileEntry 9 }

		
--   1.3.6.1.4.1.231.7.1.2.2.1.6.1.1.6.1.10
		sheAdslLineConfExtnProfileTriggerMode OBJECT-TYPE
			SYNTAX SheAdslLineConfTriggerModeType
			MAX-ACCESS read-only
			STATUS current
			DESCRIPTION
				"Indicates the Type of event that triggers fast retrain.
				disable(0),
				locCrc(1),
				rmtCrc(2),
				snrInc(4),
				snrDec(8)
				
				NE will not accept any changes and use always default value!"
			::= { sheAdslLineConfExtnProfileEntry 10 }

		
--   1.3.6.1.4.1.231.7.1.2.2.1.6.1.1.6.1.11
		sheAdslLineConfExtnProfileAdi2x OBJECT-TYPE
			SYNTAX SheAdslLineConfExtnProfileAdi2xType
			MAX-ACCESS read-only
			STATUS current
			DESCRIPTION
				"For non standard compliant ADI CPE.
				
				NE will not accept any changes and use always default value!"
			DEFVAL { 1 }
			::= { sheAdslLineConfExtnProfileEntry 11 }

		
--   1.3.6.1.4.1.231.7.1.2.2.1.6.1.1.6.1.12
		sheAdslLineConfExtnProfileStandard OBJECT-TYPE
			SYNTAX SheAdslLineConfStandardType
			MAX-ACCESS read-only
			STATUS current
			DESCRIPTION
				"Preferred standard compliance. Outcome is dependent upon standard support of the remote unit.GlobespanVirata High Speed ADSL DMT (ADSL+) applications only.
				t1413(0),
				gLite(1),
				gDmt(2),
				multiMode(4),
				adsl2(26),
				adsl2_plus(27),
				readsl2(28),
				adsl2_auto(29),
				adsl2_plus_auto(30),
				adsl2adsl2PlusOnly(31)
				
				New with R2.8:
				If the used annexType was set to 'dynamic', the standardTypes 't1413', 'gLite', 'gDmt'
				and 'readsl2' could NOT be used. 'adsl2_plus_auto' should be the prefered use in that case!"
			::= { sheAdslLineConfExtnProfileEntry 12 }

		
--   1.3.6.1.4.1.231.7.1.2.2.1.6.1.1.6.1.13
		sheAdslLineConfExtnProfileInitiate OBJECT-TYPE
			SYNTAX SheAdslLineConfInitiateType
			MAX-ACCESS read-only
			STATUS current
			DESCRIPTION
				"Specifies which end initiates startup. It is also used to send a C-tone to the remote unit.
				waitPn(0),
				ctone(1),
				initiatePn(128)
				
				NE will not accept any changes and use always default value!
				"
			::= { sheAdslLineConfExtnProfileEntry 13 }

		
--   1.3.6.1.4.1.231.7.1.2.2.1.6.1.1.6.1.14
		sheAdslLineConfExtnProfileTxPowerAttenuation OBJECT-TYPE
			SYNTAX SheAdslLineConfAttenuationType
			UNITS "dB"
			MAX-ACCESS read-only
			STATUS current
			DESCRIPTION
				"Specifies value of Tx power attenuation.
				value0(0)...value21(21)"
			::= { sheAdslLineConfExtnProfileEntry 14 }

		
--   1.3.6.1.4.1.231.7.1.2.2.1.6.1.1.6.1.15
		sheAdslLineConfExtnProfileCodingGain OBJECT-TYPE
			SYNTAX SheAdslLineConfGainType
			UNITS "dB"
			MAX-ACCESS read-only
			STATUS current
			DESCRIPTION
				"Sets the coding gain in dB increments.
				gain0(0),
				gain1(4096),
				gain2(8192),
				gain3(12288),
				gain4(16384),
				gain5(20480),
				gain6(24576),
				gain7(28672),
				auto(65280)
				
				NE will not accept any changes and use always default value!
				"
			::= { sheAdslLineConfExtnProfileEntry 15 }

		
--   1.3.6.1.4.1.231.7.1.2.2.1.6.1.1.6.1.16
		sheAdslLineConfExtnProfileRsFastOvrhdDown OBJECT-TYPE
			SYNTAX SheAdslLineConfRsFastOvrhdType
			MAX-ACCESS read-only
			STATUS current
			DESCRIPTION
				"Sets the percentage overhead for the downstream-fast buffer.
				ovrHd50(1),
				ovrHd25(2),
				ovrHd12(3),
				ovrHd6(4),
				ovrHd3(5),
				ovrHd1(7),
				disable(15)
				
				NE will not accept any changes and use always default value!
				"
			::= { sheAdslLineConfExtnProfileEntry 16 }

		
--   1.3.6.1.4.1.231.7.1.2.2.1.6.1.1.6.1.17
		sheAdslLineConfExtnProfileIntCorrectionDown OBJECT-TYPE
			SYNTAX SheAdslLineConfRsIntCorrectionType
			MAX-ACCESS read-only
			STATUS current
			DESCRIPTION
				"This parameter sets the correction time for the downstream interleaved buffer.
				RS can also be disabled.
				value125us(3),
				value250us(4),
				value500us(5),
				value1ms(6),
				value2ms(7),
				value4ms(8),
				disable(15)
				"
			::= { sheAdslLineConfExtnProfileEntry 17 }

		
--   1.3.6.1.4.1.231.7.1.2.2.1.6.1.1.6.1.18
		sheAdslLineConfExtnProfileRsFastOvrhdUp OBJECT-TYPE
			SYNTAX SheAdslLineConfRsFastOvrhdType
			MAX-ACCESS read-only
			STATUS current
			DESCRIPTION
				"Sets the percentage overhead for the upstream-fast buffer.
				ovrHd50(1),
				ovrHd25(2),
				ovrHd12(3),
				ovrHd6(4),
				ovrHd3(5),
				ovrHd1(7),
				disable(15)
				
				NE will not accept any changes and use always default value!"
			::= { sheAdslLineConfExtnProfileEntry 18 }

		
--   1.3.6.1.4.1.231.7.1.2.2.1.6.1.1.6.1.19
		sheAdslLineConfExtnProfileDrStby OBJECT-TYPE
			SYNTAX SheAdslLineConfEnableType
			MAX-ACCESS read-only
			STATUS current
			DESCRIPTION
				"Provides the ability to disable power to the line driver.
				disable(0),
				enable(1)
				
				NE will not accept any changes and use always default value!
				"
			::= { sheAdslLineConfExtnProfileEntry 19 }

		
--   1.3.6.1.4.1.231.7.1.2.2.1.6.1.1.6.1.20
		sheAdslLineConfExtnProfileExpandedExchange OBJECT-TYPE
			SYNTAX SheAdslLineConfExpandedExchangeType
			MAX-ACCESS read-only
			STATUS current
			DESCRIPTION
				"This object is used to Enable/Disable EES.
				disable(0),
				enable(1)
				
				NE will not accept any changes and use always default value!
				"
			::= { sheAdslLineConfExtnProfileEntry 20 }

		
--   1.3.6.1.4.1.231.7.1.2.2.1.6.1.1.6.1.21
		sheAdslLineConfExtnProfileEscapeFastRetrainEnable OBJECT-TYPE
			SYNTAX SheAdslLineConfEnableType
			MAX-ACCESS read-only
			STATUS current
			DESCRIPTION
				"This object is used to Enable/ Disable escape to the fast retrain capability.
				disable(0),
				enable(1)
				
				NE will not accept any changes and use always default value!
				"
			::= { sheAdslLineConfExtnProfileEntry 21 }

		
--   1.3.6.1.4.1.231.7.1.2.2.1.6.1.1.6.1.22
		sheAdslLineConfExtnProfileFastRetrainEnable OBJECT-TYPE
			SYNTAX SheAdslLineConfEnableSpecial3Type
			MAX-ACCESS read-only
			STATUS current
			DESCRIPTION
				"This object is used to Enable/ Disable the fast retrain capability.
				disable(32768),
				enable(0)
				
				NE will not accept any changes and use always default value!
				"
			::= { sheAdslLineConfExtnProfileEntry 22 }

		
--   1.3.6.1.4.1.231.7.1.2.2.1.6.1.1.6.1.23
		sheAdslLineConfExtnProfileBitSwap OBJECT-TYPE
			SYNTAX SheAdslLineConfEnableSpecial2Type
			MAX-ACCESS read-only
			STATUS current
			DESCRIPTION
				"This object is used to Enable/Disable bit swapping.
				enable(32768),
				disable(0)
				"
			::= { sheAdslLineConfExtnProfileEntry 23 }

		
--   1.3.6.1.4.1.231.7.1.2.2.1.6.1.1.6.1.24
		sheAdslLineConfExtnProfileNtr OBJECT-TYPE
			SYNTAX SheAdslLineConfNtrType
			MAX-ACCESS read-only
			STATUS current
			DESCRIPTION
				"This object is used to Enable/ Disable NTR on a per chip basis."
			::= { sheAdslLineConfExtnProfileEntry 24 }

		
--   1.3.6.1.4.1.231.7.1.2.2.1.6.1.1.6.1.25
		sheAdslLineConfExtnProfileAnnexType OBJECT-TYPE
			SYNTAX SheAdslLineConfAnnexType
			MAX-ACCESS read-only
			STATUS current
			DESCRIPTION
				"This parameter is set as per annex compliance of the code release. GlobespanVirata High Speed ADSL DMT (ADSL+) applications only.
				annexA(0),
				annexB(1),
				highSpeed(2),
				annexAdsl2(5),
				annexI(10),
				annexJ(11),
				annexM(12)
				
				New with R2.8:
				dynamic(50)
				
				If the used annexType was set to 'dynamic', such a profile could be assigned to any type of supported ADSL IU.
				The IU will select the supported annex himself, depending on HW restrictions and
				line parameters. This selection made additional restrictions to the following parameters:
				- tx/rx start and end bin usage
				- profile Standard
				- profile AdvertisedCapabilities
				- profileLineDmtConfMode "
			::= { sheAdslLineConfExtnProfileEntry 25 }

		
--   1.3.6.1.4.1.231.7.1.2.2.1.6.1.1.6.1.26
		sheAdslLineConfExtnProfileAlctlUsVer OBJECT-TYPE
			SYNTAX SheAdslLineConfExtnProfileAlctlUsVerType
			MAX-ACCESS read-only
			STATUS current
			DESCRIPTION
				"This object is used for T1.413 demo purposes only.
				
				NE will not accept any changes and use always default value!"
			DEFVAL { 2 }
			::= { sheAdslLineConfExtnProfileEntry 26 }

		
--   1.3.6.1.4.1.231.7.1.2.2.1.6.1.1.6.1.27
		sheAdslLineConfExtnProfileUseCustomBin OBJECT-TYPE
			SYNTAX SheAdslLineConfEnableSpecial2Type
			MAX-ACCESS read-only
			STATUS current
			DESCRIPTION
				"This object is used to Enable/ Disable user selection of bin-usage defined in 
				sheAdslLineConfExtnProfileDnBinUsage.
				
				disable(0),
				enable(32768)
				"
			DEFVAL { 0 }
			::= { sheAdslLineConfExtnProfileEntry 27 }

		
--   1.3.6.1.4.1.231.7.1.2.2.1.6.1.1.6.1.28
		sheAdslLineConfExtnProfileDnBinUsage OBJECT-TYPE
			SYNTAX OCTET STRING (SIZE (0..64))
			MAX-ACCESS read-only
			STATUS current
			DESCRIPTION
				"The parameter where a 1 in bit position indicates usage of corresponding bin,
				whereas a 0 disables usage of corresponding bin."
			::= { sheAdslLineConfExtnProfileEntry 28 }

		
--   1.3.6.1.4.1.231.7.1.2.2.1.6.1.1.6.1.29
		sheAdslLineConfExtnProfileMaxDCo OBJECT-TYPE
			SYNTAX SheAdslLineConfIntDephtType
			MAX-ACCESS read-only
			STATUS current
			DESCRIPTION
				"This object is used to indicate Maximum interleaving depth supported by the 
				customer's hardware.
				value64(0),
				value128(4096),
				value256(8192)
				"
			::= { sheAdslLineConfExtnProfileEntry 29 }

		
--   1.3.6.1.4.1.231.7.1.2.2.1.6.1.1.6.1.30
		sheAdslLineConfExtnProfileFullRetrain OBJECT-TYPE
			SYNTAX SheAdslLineConfEnableSpecial3Type
			MAX-ACCESS read-only
			STATUS current
			DESCRIPTION
				"This object is used to Indicate enable/disable of auto retrain capability.
				enable(0),
				disable(32768)
				
				NE will not accept any changes and use always default value!
				"
			::= { sheAdslLineConfExtnProfileEntry 30 }

		
--   1.3.6.1.4.1.231.7.1.2.2.1.6.1.1.6.1.31
		sheAdslLineConfExtnProfileAdvertisedCapabilities OBJECT-TYPE
			SYNTAX SheAdslLineConfAdvertisedCapabilitiesType
			MAX-ACCESS read-only
			STATUS current
			DESCRIPTION
				"Controls if the CO will attempt to startup using alternate standards if the CPE 
				does not support ADSL+.
				
				New with R2.8:
				If the used annexType was set to 'dynamic', this parameter should be set to
				'disabled' or 'adslPlus'. All other values will not work with the intended
				set of dynamic annexType selection by IU. "
			::= { sheAdslLineConfExtnProfileEntry 31 }

		
--   1.3.6.1.4.1.231.7.1.2.2.1.6.1.1.6.1.32
		sheAdslLineConfExtnProfilePsdMaskType OBJECT-TYPE
			SYNTAX SheAdslLineConfPsdMaskType
			MAX-ACCESS read-only
			STATUS current
			DESCRIPTION
				"Selects the PSD mask option to be used."
			::= { sheAdslLineConfExtnProfileEntry 32 }

		
--   1.3.6.1.4.1.231.7.1.2.2.1.6.1.1.6.1.33
		sheAdslLineConfExtnProfileLineDmtConfMode OBJECT-TYPE
			SYNTAX SheAdslLineConfLineDmtConfModeType
			MAX-ACCESS read-only
			STATUS current
			DESCRIPTION
				"Selects if there is overlap or no overlap of bins.
				
				Overlapping is only supported by non ISDN profiles and will change the setting for 
				TxStartBin accordingly!!.
				
				New with R2.8:
				If the used annexType was set to 'dynamic', this parameter should be set to
				'fdmMode' only. Other values will not work with the intended set of dynamic
				annexType selection by IU."
			::= { sheAdslLineConfExtnProfileEntry 33 }

		
--   1.3.6.1.4.1.231.7.1.2.2.1.6.1.1.6.1.34
		sheAdslLineConfExtnProfileEraseProfiles OBJECT-TYPE
			SYNTAX SheAdslLineConfEnableSpecial2Type
			MAX-ACCESS read-only
			STATUS current
			DESCRIPTION
				"Enables/Disables the ability to erase all fast retrain profiles at startup.
				disable(0),
				enable(32768)
				"
			::= { sheAdslLineConfExtnProfileEntry 34 }

		
--   1.3.6.1.4.1.231.7.1.2.2.1.6.1.1.6.1.35
		sheAdslLineConfExtnProfileRsMemory OBJECT-TYPE
			SYNTAX SheAdslLineConfRsMemoryType
			MAX-ACCESS read-only
			STATUS current
			DESCRIPTION
				"Indicates whether customer's Hardware should use external RS RAM.
				Could not be configured and depends only on the used card type."
			::= { sheAdslLineConfExtnProfileEntry 35 }

		
--   1.3.6.1.4.1.231.7.1.2.2.1.6.1.1.6.1.36
		sheAdslLineConfExtnProfileParamHybridLossTestStart OBJECT-TYPE
			SYNTAX INTEGER (0..511)
			MAX-ACCESS read-only
			STATUS current
			DESCRIPTION
				"Indicates Start bin for range of bins to be measured."
			DEFVAL { 2 }
			::= { sheAdslLineConfExtnProfileEntry 36 }

		
--   1.3.6.1.4.1.231.7.1.2.2.1.6.1.1.6.1.37
		sheAdslLineConfExtnProfileParamHybridLossTestEnd OBJECT-TYPE
			SYNTAX INTEGER (0..511)
			MAX-ACCESS read-only
			STATUS current
			DESCRIPTION
				"Indicates End bin for range of bins to be measured."
			DEFVAL { 64 }
			::= { sheAdslLineConfExtnProfileEntry 37 }

		
--   1.3.6.1.4.1.231.7.1.2.2.1.6.1.1.6.1.38
		sheAdslLineConfExtnProfileConfMinInp OBJECT-TYPE
			SYNTAX SheAdslConfMinInpType
			MAX-ACCESS read-only
			STATUS current
			DESCRIPTION
				"New ADSL2+ parameter. The user configures the duration of 
				impulse noise the system should withstand.
				
				This parameter configures the value for downstream direction."
			DEFVAL { 400 }
			::= { sheAdslLineConfExtnProfileEntry 38 }

		
--   1.3.6.1.4.1.231.7.1.2.2.1.6.1.1.6.1.39
-- THIS ELEMENT WILL NOT LONGER BE SUPPORTED BY NE up R2.5.
-- Functionality moved to LineTable.
		sheAdslLineConfExtnProfileRfiBandMask OBJECT-TYPE
			SYNTAX OCTET STRING (SIZE (4))
			MAX-ACCESS read-only
			STATUS current
			DESCRIPTION
				"BitMask for sheAdslRfiBandIndex.
				Configured RFI bands are used for this profile."
			::= { sheAdslLineConfExtnProfileEntry 39 }

		
--   1.3.6.1.4.1.231.7.1.2.2.1.6.1.1.6.1.40                     
		sheAdslLineConfExtnProfileUpstreamPsdMaskSelection OBJECT-TYPE
			SYNTAX SheAdslLineConfUpstreamPSDMaskSelectionType
			MAX-ACCESS read-only
			STATUS current
			DESCRIPTION
				"Selects the PSD mask option to be used.
				This parameter is used only for annexes J and M of ITU-T Recs. G.992-3 and G.992.5
				Other profiles will ignore the configured value and use per default the value noSelection(0)."
			REFERENCE
				"G997.1 chapter 7.3.1.2.11"
			::= { sheAdslLineConfExtnProfileEntry 40 }

		
--   1.3.6.1.4.1.231.7.1.2.2.1.6.1.1.6.1.41                     
		sheAdslLineConfExtnProfileMaxNomPsdDs OBJECT-TYPE
			SYNTAX INTEGER (-600..-300)
			UNITS "0.1 dBm/Hz"
			MAX-ACCESS read-only
			STATUS current
			DESCRIPTION
				"The maximum nominal transmit PSD in the downstream direction during 
				initialization and Showtime.  It ranges from -600 to -300 units of 0.1 dBm/Hz.
				(physical values are -60 to -30 dBm/Hz)."
			REFERENCE
				"ITU-T G.997.1, paragraph 7.3.1.2"
			DEFVAL { -400 }
			::= { sheAdslLineConfExtnProfileEntry 41 }

		
--   1.3.6.1.4.1.231.7.1.2.2.1.6.1.1.6.1.42                     
		sheAdslLineConfExtnProfileMaxNomAtpDs OBJECT-TYPE
			SYNTAX Gauge32 (0..255)
			MAX-ACCESS read-only
			STATUS current
			DESCRIPTION
				"The maximum nominal aggregate transmit power in the downstream direction 
				during initialization and Showtime.  It ranges from 0 to 255 units of 0.1 dBm 
				(physical values are 0 to 25.5 dBm)."
			REFERENCE
				"ITU-T G.997.1, paragraph 7.3.1.2"
			DEFVAL { 204 }
			::= { sheAdslLineConfExtnProfileEntry 42 }

		
--   1.3.6.1.4.1.231.7.1.2.2.1.6.1.1.6.1.43                     
		sheAdslLineConfExtnProfilePsdMaskDs OBJECT-TYPE
			SYNTAX OCTET STRING (SIZE (6..96))
			MAX-ACCESS read-only
			STATUS current
			DESCRIPTION
				"The downstream PSD mask applicable at the U-C2 reference point.
				This parameter is used only for G.992.5 and it may impose PSD restrictions
				(breakpoints) in addition to the Limit PSD mask defined in G.992.5.
				This is a string of 32 pairs of values in the following structure:
				Octets 0+1 - Index of 1st sub-carrier used in the context of a first breakpoint.
				Octet 2    - The PSD reduction for the sub-carrier indicated in octets 0 and 1.
				Octets 3-5 - Same, for a 2nd breakpoint.
				Octets 6-8 - Same, for a 3rd breakpoint.
				This architecture continues until octets 94-95, which are associated with a 32nd 
				breakpoint. Each subcarrier index is an unsigned number in the range 1 and NSCds.
				Each PSD reduction value is in the range 0 (0dBm/Hz) to 255 (-127.5dBm/Hz) with steps of 0.5dBm/Hz.
				Valid values are in the range 0 to 190 (0 to -95dBm/Hz). But the range of start-bin and end-bin
				is in range 0 to 195 (0 to -97.5dBm/Hz). 
				Two break points (6 byte) are reserved for start sub-carrier index and end sub-carrier index. 
				So the range of size is 6 up to 96.
				When the number of breakpoints is less than 32, all remaining octets are set to the value 0.  
				Note that the content of this object should be correlated  with the sub-carriers mask and with the RFI setup."
			REFERENCE
				"ITU-T G.997.1, paragraph 7.3.1.2"
			::= { sheAdslLineConfExtnProfileEntry 43 }

		
--  1.3.6.1.4.1.231.7.1.2.2.1.6.1.1.6.1.44
		sheAdslLineConfExtnProfilePSDMASKdsEnable OBJECT-TYPE
			SYNTAX SheAdslLineConfEnableType
			MAX-ACCESS read-only
			STATUS current
			DESCRIPTION
				"User custom PSD mask-related parameter used by the ATU-C to use user custom PSD mask.
				(Not available for ADSL but ADSL2 and ADSL2plus )."
			REFERENCE
				"ITU-T G.997.1, paragraph 7.3.1.2"
			DEFVAL { 0 }
			::= { sheAdslLineConfExtnProfileEntry 44 }

		
--   1.3.6.1.4.1.231.7.1.2.2.1.6.1.1.6.1.38
		sheAdslLineConfExtnProfileConfMinInpUs OBJECT-TYPE
			SYNTAX SheAdslConfMinInpType
			MAX-ACCESS read-only
			STATUS current
			DESCRIPTION
				"New ADSL2+ parameter. The user configures the duration of 
				impulse noise the system should withstand.
				
				This parameter configures the value for upstream direction."
			DEFVAL { 400 }
			::= { sheAdslLineConfExtnProfileEntry 45 }

		
--   1.3.6.1.4.1.231.7.1.2.2.1.6.1.1.7
		sheAdslLineConfExtnProfileControl OBJECT IDENTIFIER ::= { sheAdslLineMIB 7 }

		
--   1.3.6.1.4.1.231.7.1.2.2.1.6.1.1.7.1
		sheAdslLineConfExtnProfileControlRequest OBJECT-TYPE
			SYNTAX SheAdslControlRequestType
			MAX-ACCESS read-write
			STATUS current
			DESCRIPTION
				"modifyAdslLineConfExtnProfile
				sheAdslLineConfExtnProfileControlIndex
				sheAdslLineConfExtnProfileControlName
				...
				
				"
			::= { sheAdslLineConfExtnProfileControl 1 }

		
--   1.3.6.1.4.1.231.7.1.2.2.1.6.1.1.7.2
		sheAdslLineConfExtnProfileControlIndex OBJECT-TYPE
			SYNTAX Integer32
			MAX-ACCESS read-write
			STATUS current
			DESCRIPTION
				"Index of the table entry to be configured. Needed for modify.
				"
			::= { sheAdslLineConfExtnProfileControl 2 }

		
--   1.3.6.1.4.1.231.7.1.2.2.1.6.1.1.7.3
		sheAdslLineConfExtnProfileControlStatus OBJECT-TYPE
			SYNTAX SheControlStatusType
			MAX-ACCESS read-only
			STATUS current
			DESCRIPTION
				"The status of a user command. 
				"
			::= { sheAdslLineConfExtnProfileControl 3 }

		
--   1.3.6.1.4.1.231.7.1.2.2.1.6.1.1.7.4
		sheAdslLineConfExtnProfileControlTimer OBJECT-TYPE
			SYNTAX Gauge32
			MAX-ACCESS read-only
			STATUS current
			DESCRIPTION
				"The maximum wait time for the manager for a long running user command. 
				"
			::= { sheAdslLineConfExtnProfileControl 4 }

		
--   1.3.6.1.4.1.231.7.1.2.2.1.6.1.1.7.5
		sheAdslLineConfExtnProfileControlReqResult OBJECT-TYPE
			SYNTAX SheAdslControlRequestResultType
			MAX-ACCESS read-only
			STATUS current
			DESCRIPTION
				"The result of the last user command."
			::= { sheAdslLineConfExtnProfileControl 5 }

		
--   1.3.6.1.4.1.231.7.1.2.2.1.6.1.1.7.6
		sheAdslLineConfExtnProfileControlTimeStamp OBJECT-TYPE
			SYNTAX Unsigned32
			UNITS "sec"
			MAX-ACCESS read-only
			STATUS current
			DESCRIPTION
				"The time stamp of the last command (end of command)."
			::= { sheAdslLineConfExtnProfileControl 6 }

		
--   1.3.6.1.4.1.231.7.1.2.2.1.6.1.1.7.7
		sheAdslLineConfExtnProfileControlName OBJECT-TYPE
			SYNTAX SnmpAdminString
			MAX-ACCESS read-write
			STATUS current
			DESCRIPTION
				"Descriptional name. The name used during configuration of this profile is equal
				to the name of the sheAdslLineConfProfile with the identical index."
			::= { sheAdslLineConfExtnProfileControl 7 }

		
--   1.3.6.1.4.1.231.7.1.2.2.1.6.1.1.7.8
-- THIS ELEMENT WILL NOT LONGER BE SUPPORTED BY NE up R2.5.
		sheAdslLineConfExtnProfileControlParametricTestInputFile OBJECT-TYPE
			SYNTAX DisplayString
			MAX-ACCESS read-write
			STATUS current
			DESCRIPTION
				"Indicates Name of the Input file from which to take the Mask Array Size, lower and upper mask Array. Null string means no file is specified."
			::= { sheAdslLineConfExtnProfileControl 8 }

		
--   1.3.6.1.4.1.231.7.1.2.2.1.6.1.1.7.9
		sheAdslLineConfExtnProfileControlRsIntCorrectionUp OBJECT-TYPE
			SYNTAX SheAdslLineConfRsIntCorrectionType
			MAX-ACCESS read-write
			STATUS current
			DESCRIPTION
				"Sets the correction time for the upstream-interleaved buffer. RS can also be disabled. The Default Value for ADSL+ is 3."
			::= { sheAdslLineConfExtnProfileControl 9 }

		
--   1.3.6.1.4.1.231.7.1.2.2.1.6.1.1.7.10
		sheAdslLineConfExtnProfileControlLineType OBJECT-TYPE
			SYNTAX SheAdslConfLineType
			MAX-ACCESS read-write
			STATUS current
			DESCRIPTION
				"This parameter provisions the DSL physical entity at start-up by defining whether
				and how the line will be channelized, i.e. which channel type(s) are supported.
				
				Defined values are:
				
				fastOnly(2)           -- only fast channel exists (singleLatency)
				interleavedOnly(3)    -- only interleaved channel exists (singleLatency, default)
				fastAndInterleaved(5) -- both fast and interleaved channels (dualLatency)
				                         exist
				
				In case of dualLatency (mode 5), the parameter's sheAdslLineConfProfileAtucConfRateChanRatio
				and sheAdslLineConfProfileAturConfRateChanRatio configures the bandwith distribution.
				
				IMPORTANT NOTE:
				The configuration of dualLatency mode is only available for NE releases up R2.5!!
				The modification is only possible for profiles, which are NOT IN USE!"
			::= { sheAdslLineConfExtnProfileControl 10 }

		
--   1.3.6.1.4.1.231.7.1.2.2.1.6.1.1.7.11
		sheAdslLineConfExtnProfileControlTxEndBin OBJECT-TYPE
			SYNTAX INTEGER (6..511)
			MAX-ACCESS read-write
			STATUS current
			DESCRIPTION
				"Highest bin number allowed for Tx signal. The Range & default for ADSL+ is 0x06 - 0x1ff respectively.
				
				NE will not accept any changes and use always default value!
				Ne will select the correct values depending on the configuration of the following values:
				- AnnexType
				- DmtConfMode
				- AdvertisedCapability"
			::= { sheAdslLineConfExtnProfileControl 11 }

		
--   1.3.6.1.4.1.231.7.1.2.2.1.6.1.1.7.12
		sheAdslLineConfExtnProfileControlTxStartBin OBJECT-TYPE
			SYNTAX INTEGER (6..511)
			MAX-ACCESS read-write
			STATUS current
			DESCRIPTION
				"Lowest bin number allowed for Tx signal.The Range for ADSL+ is 0x06 - 0x1ff. 
				
				NE will not accept any changes and use always default value!
				Ne will select the correct values depending on the configuration of the following values:
				- AnnexType
				- DmtConfMode
				- AdvertisedCapability"
			::= { sheAdslLineConfExtnProfileControl 12 }

		
--   1.3.6.1.4.1.231.7.1.2.2.1.6.1.1.7.13
-- THIS ELEMENT WILL NOT LONGER BE SUPPORTED BY NE up R2.5.
		sheAdslLineConfExtnProfileControlMaxBitsPerBin OBJECT-TYPE
			SYNTAX INTEGER (0..15)
			MAX-ACCESS read-write
			STATUS current
			DESCRIPTION
				"Maximum Rx number of bits per bin.
				
				NE will not accept any changes and use always default value!"
			::= { sheAdslLineConfExtnProfileControl 13 }

		
--   1.3.6.1.4.1.231.7.1.2.2.1.6.1.1.7.14
		sheAdslLineConfExtnProfileControlRxStartBin OBJECT-TYPE
			SYNTAX INTEGER (1..57)
			MAX-ACCESS read-write
			STATUS current
			DESCRIPTION
				"Lowest bin number allowed for Rx signal. 
				
				
				NE will not accept any changes and use always default value!
				Ne will select the correct values depending on the configuration of the following values:
				- AnnexType
				- DmtConfMode
				- AdvertisedCapability"
			::= { sheAdslLineConfExtnProfileControl 14 }

		
--   1.3.6.1.4.1.231.7.1.2.2.1.6.1.1.7.15
		sheAdslLineConfExtnProfileControlRxEndBin OBJECT-TYPE
			SYNTAX INTEGER (6..64)
			MAX-ACCESS read-write
			STATUS current
			DESCRIPTION
				"Highest bin number allowed for Rx signal. 
				
				NE will not accept any changes and use always default value!
				Ne will select the correct values depending on the configuration of the following values:
				- AnnexType
				- DmtConfMode
				- AdvertisedCapability"
			::= { sheAdslLineConfExtnProfileControl 15 }

		
--   1.3.6.1.4.1.231.7.1.2.2.1.6.1.1.7.16
-- THIS ELEMENT WILL NOT LONGER BE SUPPORTED BY NE up R2.5.
		sheAdslLineConfExtnProfileControlRxBinAdjust OBJECT-TYPE
			SYNTAX SheAdslLineConfExtnProfileRxBinAdjustType
			MAX-ACCESS read-write
			STATUS current
			DESCRIPTION
				"Employs Rx Start/End bin settings.
				
				NE will not accept any changes and use always default value!"
			::= { sheAdslLineConfExtnProfileControl 16 }

		
--   1.3.6.1.4.1.231.7.1.2.2.1.6.1.1.7.17
-- THIS ELEMENT WILL NOT LONGER BE SUPPORTED BY NE up R2.5.
		sheAdslLineConfExtnProfileControlTriggerMode OBJECT-TYPE
			SYNTAX SheAdslLineConfTriggerModeType
			MAX-ACCESS read-write
			STATUS current
			DESCRIPTION
				"Indicates the Type of event that triggers fast retrain.
				
				NE will not accept any changes and use always default value!"
			::= { sheAdslLineConfExtnProfileControl 17 }

		
--   1.3.6.1.4.1.231.7.1.2.2.1.6.1.1.7.18
-- THIS ELEMENT WILL NOT LONGER BE SUPPORTED BY NE up R2.5.
		sheAdslLineConfExtnProfileControlAdi2x OBJECT-TYPE
			SYNTAX SheAdslLineConfExtnProfileAdi2xType
			MAX-ACCESS read-write
			STATUS current
			DESCRIPTION
				"For non standard compliant ADI CPE.
				
				NE will not accept any changes and use always default value!"
			::= { sheAdslLineConfExtnProfileControl 18 }

		
--   1.3.6.1.4.1.231.7.1.2.2.1.6.1.1.7.19
		sheAdslLineConfExtnProfileControlStandard OBJECT-TYPE
			SYNTAX SheAdslLineConfStandardType
			MAX-ACCESS read-write
			STATUS current
			DESCRIPTION
				"Preferred standard compliance. Outcome is dependent upon standard support of the remote unit.GlobespanVirata High Speed ADSL DMT (ADSL+) applications only.
				
				New with R2.8:
				If the used annexType was set to 'dynamic', the standardTypes 't1413', 'gLite', 'gDmt'
				and 'readsl2' could NOT be used. 'adsl2_plus_auto' should be the prefered use in that case!"
			::= { sheAdslLineConfExtnProfileControl 19 }

		
--   1.3.6.1.4.1.231.7.1.2.2.1.6.1.1.7.20
-- THIS ELEMENT WILL NOT LONGER BE SUPPORTED BY NE up R2.5.
		sheAdslLineConfExtnProfileControlInitiate OBJECT-TYPE
			SYNTAX SheAdslLineConfInitiateType
			MAX-ACCESS read-write
			STATUS current
			DESCRIPTION
				"Specifies which end initiates startup. It is also used to send a C-tone to the remote unit.
				
				NE will not accept any changes and use always default value!"
			::= { sheAdslLineConfExtnProfileControl 20 }

		
--   1.3.6.1.4.1.231.7.1.2.2.1.6.1.1.7.21
		sheAdslLineConfExtnProfileControlTxPowerAttenuation OBJECT-TYPE
			SYNTAX SheAdslLineConfAttenuationType
			UNITS "dB"
			MAX-ACCESS read-write
			STATUS current
			DESCRIPTION
				"Specifies value of Tx power attenuation."
			::= { sheAdslLineConfExtnProfileControl 21 }

		
--   1.3.6.1.4.1.231.7.1.2.2.1.6.1.1.7.22
-- THIS ELEMENT WILL NOT LONGER BE SUPPORTED BY NE up R2.5.
		sheAdslLineConfExtnProfileControlCodingGain OBJECT-TYPE
			SYNTAX SheAdslLineConfGainType
			UNITS "dB"
			MAX-ACCESS read-write
			STATUS current
			DESCRIPTION
				"Sets the coding gain in dB increments.
				
				NE will not accept any changes and use always default value!"
			::= { sheAdslLineConfExtnProfileControl 22 }

		
--   1.3.6.1.4.1.231.7.1.2.2.1.6.1.1.7.23
-- THIS ELEMENT WILL NOT LONGER BE SUPPORTED BY NE up R2.5.
		sheAdslLineConfExtnProfileControlRsFastOvrhdDown OBJECT-TYPE
			SYNTAX SheAdslLineConfRsFastOvrhdType
			MAX-ACCESS read-write
			STATUS current
			DESCRIPTION
				"Sets the percentage overhead for the downstream-fast buffer.
				
				NE will not accept any changes and use always default value!"
			::= { sheAdslLineConfExtnProfileControl 23 }

		
--   1.3.6.1.4.1.231.7.1.2.2.1.6.1.1.7.24
		sheAdslLineConfExtnProfileControlIntCorrectionDown OBJECT-TYPE
			SYNTAX SheAdslLineConfRsIntCorrectionType
			MAX-ACCESS read-write
			STATUS current
			DESCRIPTION
				"This parameter sets the correction time for the downstream interleaved buffer.RS can also be disabled."
			::= { sheAdslLineConfExtnProfileControl 24 }

		
--   1.3.6.1.4.1.231.7.1.2.2.1.6.1.1.7.25
-- THIS ELEMENT WILL NOT LONGER BE SUPPORTED BY NE up R2.5.
		sheAdslLineConfExtnProfileControlRsFastOvrhdUp OBJECT-TYPE
			SYNTAX SheAdslLineConfRsFastOvrhdType
			MAX-ACCESS read-write
			STATUS current
			DESCRIPTION
				"Sets the percentage overhead for the upstream-fast buffer.
				
				NE will not accept any changes and use always default value!"
			::= { sheAdslLineConfExtnProfileControl 25 }

		
--   1.3.6.1.4.1.231.7.1.2.2.1.6.1.1.7.26
-- THIS ELEMENT WILL NOT LONGER BE SUPPORTED BY NE up R2.5.
		sheAdslLineConfExtnProfileControlDrStby OBJECT-TYPE
			SYNTAX SheAdslLineConfEnableType
			MAX-ACCESS read-write
			STATUS current
			DESCRIPTION
				"Provides the ability to disable power to the line driver.
				
				NE will not accept any changes and use always default value!"
			::= { sheAdslLineConfExtnProfileControl 26 }

		
--   1.3.6.1.4.1.231.7.1.2.2.1.6.1.1.7.27
-- THIS ELEMENT WILL NOT LONGER BE SUPPORTED BY NE up R2.5.
		sheAdslLineConfExtnProfileControlExpandedExchange OBJECT-TYPE
			SYNTAX SheAdslLineConfExpandedExchangeType
			MAX-ACCESS read-write
			STATUS current
			DESCRIPTION
				"This object is used to Enable/Disable EES.
				
				NE will not accept any changes and use always default value!"
			::= { sheAdslLineConfExtnProfileControl 27 }

		
--   1.3.6.1.4.1.231.7.1.2.2.1.6.1.1.7.28
-- THIS ELEMENT WILL NOT LONGER BE SUPPORTED BY NE up R2.5.
		sheAdslLineConfExtnProfileControlEscapeFastRetrainEnable OBJECT-TYPE
			SYNTAX SheAdslLineConfEnableType
			MAX-ACCESS read-write
			STATUS current
			DESCRIPTION
				"This object is used to Enable/ Disable escape to the fast retrain capability.
				
				
				NE will not accept any changes and use always default value!"
			::= { sheAdslLineConfExtnProfileControl 28 }

		
--   1.3.6.1.4.1.231.7.1.2.2.1.6.1.1.7.29
-- THIS ELEMENT WILL NOT LONGER BE SUPPORTED BY NE up R2.5.
		sheAdslLineConfExtnProfileControlFastRetrainEnable OBJECT-TYPE
			SYNTAX SheAdslLineConfEnableSpecial3Type
			MAX-ACCESS read-write
			STATUS current
			DESCRIPTION
				"This object is used to Enable/ Disable the fast retrain capability.
				
				NE will not accept any changes and use always default value!"
			::= { sheAdslLineConfExtnProfileControl 29 }

		
--   1.3.6.1.4.1.231.7.1.2.2.1.6.1.1.7.30
		sheAdslLineConfExtnProfileControlBitSwap OBJECT-TYPE
			SYNTAX SheAdslLineConfEnableSpecial2Type
			MAX-ACCESS read-write
			STATUS current
			DESCRIPTION
				"This object is used to Enable/Disable bit swapping."
			::= { sheAdslLineConfExtnProfileControl 30 }

		
--   1.3.6.1.4.1.231.7.1.2.2.1.6.1.1.7.31
		sheAdslLineConfExtnProfileControlNtr OBJECT-TYPE
			SYNTAX SheAdslLineConfNtrType
			MAX-ACCESS read-write
			STATUS current
			DESCRIPTION
				"This object is used to Enable/ Disable NTR on a per chip basis."
			::= { sheAdslLineConfExtnProfileControl 31 }

		
--   1.3.6.1.4.1.231.7.1.2.2.1.6.1.1.7.32
		sheAdslLineConfExtnProfileControlAnnexType OBJECT-TYPE
			SYNTAX SheAdslLineConfAnnexType
			MAX-ACCESS read-write
			STATUS current
			DESCRIPTION
				"This parameter is set as per annex compliance of the code release. GlobespanVirata High Speed ADSL DMT (ADSL+) applications only.
				
				New with R2.8:
				dynamic(50)
				
				If the used annexType was set to 'dynamic', such a profile could be assigned to any type of supported ADSL IU.
				The IU will select the supported annex himself, depending on HW restrictions and
				line parameters. This selection made additional restrictions to the following parameters:
				- tx/rx start and end bin usage
				- profile Standard
				- profile AdvertisedCapabilities
				- profileLineDmtConfMode 
				"
			::= { sheAdslLineConfExtnProfileControl 32 }

		
--   1.3.6.1.4.1.231.7.1.2.2.1.6.1.1.7.33
-- THIS ELEMENT WILL NOT LONGER BE SUPPORTED BY NE up R2.5.
		sheAdslLineConfExtnProfileControlAlctlUsVer OBJECT-TYPE
			SYNTAX SheAdslLineConfExtnProfileAlctlUsVerType
			MAX-ACCESS read-write
			STATUS current
			DESCRIPTION
				"This object is used for T1.413 demo purposes only.
				
				NE will not accept any changes and use always default value!"
			::= { sheAdslLineConfExtnProfileControl 33 }

		
--   1.3.6.1.4.1.231.7.1.2.2.1.6.1.1.7.34
		sheAdslLineConfExtnProfileControlUseCustomBin OBJECT-TYPE
			SYNTAX SheAdslLineConfEnableSpecial2Type
			MAX-ACCESS read-write
			STATUS current
			DESCRIPTION
				"This object is used to Enable/ Disable user selection on which of the 256 bins will be enabled for downstream transmission."
			::= { sheAdslLineConfExtnProfileControl 34 }

		
--   1.3.6.1.4.1.231.7.1.2.2.1.6.1.1.7.35
		sheAdslLineConfExtnProfileControlDnBinUsage OBJECT-TYPE
			SYNTAX OCTET STRING (SIZE (0..64))
			MAX-ACCESS read-write
			STATUS current
			DESCRIPTION
				"The parameter where a 1 in bit position indicates usage of corresponding bin,whereas a 0 disables usage of corresponding bin."
			::= { sheAdslLineConfExtnProfileControl 35 }

		
--   1.3.6.1.4.1.231.7.1.2.2.1.6.1.1.7.36
		sheAdslLineConfExtnProfileControlMaxDCo OBJECT-TYPE
			SYNTAX SheAdslLineConfIntDephtType
			MAX-ACCESS read-write
			STATUS current
			DESCRIPTION
				"This object is used to indicate Maximum interleaving depth supported by the customer's hardware."
			::= { sheAdslLineConfExtnProfileControl 36 }

		
--   1.3.6.1.4.1.231.7.1.2.2.1.6.1.1.7.37
-- THIS ELEMENT WILL NOT LONGER BE SUPPORTED BY NE up R2.5.
		sheAdslLineConfExtnProfileControlFullRetrain OBJECT-TYPE
			SYNTAX SheAdslLineConfEnableSpecial3Type
			MAX-ACCESS read-write
			STATUS current
			DESCRIPTION
				"This object is used to Indicate enable/disable of auto retrain capability.
				
				NE will not accept any changes and use always default value!"
			::= { sheAdslLineConfExtnProfileControl 37 }

		
--   1.3.6.1.4.1.231.7.1.2.2.1.6.1.1.7.38
		sheAdslLineConfExtnProfileControlAdvertisedCapabilities OBJECT-TYPE
			SYNTAX SheAdslLineConfAdvertisedCapabilitiesType
			MAX-ACCESS read-write
			STATUS current
			DESCRIPTION
				"Controls if the CO will attempt to startup using alternate standards if the CPE does not support ADSL+. 
				
				New with R2.8:
				If the used annexType was set to 'dynamic', this parameter should be set to
				'disabled' or 'adslPlus'. All other values will not work with the intended
				set of dynamic annexType selection by IU."
			::= { sheAdslLineConfExtnProfileControl 38 }

		
--   1.3.6.1.4.1.231.7.1.2.2.1.6.1.1.7.39
		sheAdslLineConfExtnProfileControlPsdMaskType OBJECT-TYPE
			SYNTAX SheAdslLineConfPsdMaskType
			MAX-ACCESS read-write
			STATUS current
			DESCRIPTION
				"Selects the PSD mask option to be used."
			::= { sheAdslLineConfExtnProfileControl 39 }

		
--   1.3.6.1.4.1.231.7.1.2.2.1.6.1.1.7.40
		sheAdslLineConfExtnProfileControlLineDmtConfMode OBJECT-TYPE
			SYNTAX SheAdslLineConfLineDmtConfModeType
			MAX-ACCESS read-write
			STATUS current
			DESCRIPTION
				"Selects if there is overlap or no overlap of bins.
				
				Overlapping is only supported by non ISDN profiles and will change the setting for 
				TxStartBin accordingly!!.
				
				New with R2.8:
				If the used annexType was set to 'dynamic', this parameter should be set to
				'fdmMode' only. Other values will not work with the intended set of dynamic
				annexType selection by IU."
			::= { sheAdslLineConfExtnProfileControl 40 }

		
--   1.3.6.1.4.1.231.7.1.2.2.1.6.1.1.7.41
		sheAdslLineConfExtnProfileControlEraseProfiles OBJECT-TYPE
			SYNTAX SheAdslLineConfEnableSpecial2Type
			MAX-ACCESS read-write
			STATUS current
			DESCRIPTION
				"Enables/Disables the ability to erase all fast retrain profiles at startup."
			::= { sheAdslLineConfExtnProfileControl 41 }

		
--   1.3.6.1.4.1.231.7.1.2.2.1.6.1.1.7.43
		sheAdslLineConfExtnProfileControlParamHybridLossTestStart OBJECT-TYPE
			SYNTAX INTEGER (0..511)
			MAX-ACCESS read-write
			STATUS current
			DESCRIPTION
				"Indicates Start bin for range of bins to be measured."
			::= { sheAdslLineConfExtnProfileControl 43 }

		
--   1.3.6.1.4.1.231.7.1.2.2.1.6.1.1.7.44
		sheAdslLineConfExtnProfileControlParamHybridLossTestEnd OBJECT-TYPE
			SYNTAX INTEGER (0..511)
			MAX-ACCESS read-write
			STATUS current
			DESCRIPTION
				"Indicates End bin for range of bins to be measured."
			::= { sheAdslLineConfExtnProfileControl 44 }

		
--   1.3.6.1.4.1.231.7.1.2.2.1.6.1.1.7.45
		sheAdslLineConfExtnProfileControlConfMinInp OBJECT-TYPE
			SYNTAX SheAdslConfMinInpType
			MAX-ACCESS read-write
			STATUS current
			DESCRIPTION
				"Look at table."
			::= { sheAdslLineConfExtnProfileControl 45 }

		
--   1.3.6.1.4.1.231.7.1.2.2.1.6.1.1.7.46
-- THIS ELEMENT WILL NOT LONGER BE SUPPORTED BY NE up R2.5.
-- Functionality moved to LineTable.
		sheAdslLineConfExtnProfileControlRfiBandMask OBJECT-TYPE
			SYNTAX OCTET STRING (SIZE (4))
			MAX-ACCESS read-write
			STATUS current
			DESCRIPTION
				"BitMask for sheAdslRfiBandIndex in sheAdslRfiBandTable."
			::= { sheAdslLineConfExtnProfileControl 46 }

		
--   1.3.6.1.4.1.231.7.1.2.2.1.6.1.1.7.47
		sheAdslLineConfExtnProfileControlUpstreamPsdMaskSelection OBJECT-TYPE
			SYNTAX SheAdslLineConfUpstreamPSDMaskSelectionType
			MAX-ACCESS read-write
			STATUS current
			DESCRIPTION
				"This configuration parameter defines which upstream PSD mask is enabled.
				This parameter is used only for annexes J and M of ITU-T Recs. G.992-3 and G.992.5"
			::= { sheAdslLineConfExtnProfileControl 47 }

		
--   1.3.6.1.4.1.231.7.1.2.2.1.6.1.1.7.48
		sheAdslLineConfExtnProfileControlMaxNomPsdDs OBJECT-TYPE
			SYNTAX INTEGER (-600..-300)
			UNITS "0.1 dBm/Hz"
			MAX-ACCESS read-write
			STATUS current
			DESCRIPTION
				"The maximum nominal transmit PSD in the downstream direction during 
				initialization and Showtime.  It ranges from -600 to -300 units of 0.1 dBm/Hz.
				(physical values are -60 to -30 dBm/Hz)."
			REFERENCE
				"ITU-T G.997.1, paragraph 7.3.1.2"
			::= { sheAdslLineConfExtnProfileControl 48 }

		
--   1.3.6.1.4.1.231.7.1.2.2.1.6.1.1.7.49
		sheAdslLineConfExtnProfileControlMaxNomAtpDs OBJECT-TYPE
			SYNTAX Gauge32 (0..255)
			UNITS "0.1 dBm/Hz"
			MAX-ACCESS read-write
			STATUS current
			DESCRIPTION
				"The maximum nominal aggregate transmit power in the downstream direction 
				during initialization and Showtime.  It ranges from 0 to 255 units of 0.1 dBm 
				(physical values are 0 to 25.5 dBm)."
			REFERENCE
				"ITU-T G.997.1, paragraph 7.3.1.2"
			::= { sheAdslLineConfExtnProfileControl 49 }

		
--   1.3.6.1.4.1.231.7.1.2.2.1.6.1.1.7.50
		sheAdslLineConfExtnProfileControlPsdMaskDs OBJECT-TYPE
			SYNTAX OCTET STRING (SIZE (6..96))
			MAX-ACCESS read-write
			STATUS current
			DESCRIPTION
				"The downstream PSD mask applicable at the U-C2 reference point.
				This parameter is used only for G.992.5 and it may impose PSD restrictions
				(breakpoints) in addition to the Limit PSD mask defined in G.992.5.
				This is a string of 32 pairs of values in the following structure:
				Octets 0+1 - Index of 1st sub-carrier used in the context of a first breakpoint.
				Octet 2    - The PSD reduction for the sub-carrier indicated in octets 0 and 1.
				Octets 3-5 - Same, for a 2nd breakpoint.
				Octets 6-8 - Same, for a 3rd breakpoint.
				This architecture continues until octets 94-95, which are associated with a 32nd 
				breakpoint. Each subcarrier index is an unsigned number in the range 1 and NSCds.
				Each PSD reduction value is in the range 0 (0dBm/Hz) to 255 (-127.5dBm/Hz) with steps of 0.5dBm/Hz.
				Valid values are in the range 0 to 190 (0 to -95dBm/Hz). But the range of start-bin and end-bin
				is in range 0 to 195 (0 to -97.5dBm/Hz). 
				Two break points (6 byte) are reserved for start sub-carrier index and end sub-carrier index. 
				So the range of size is 6 up to 96.
				When the number of breakpoints is less than 32, all remaining octets are set to the value 0.  
				Note that the content of this object should be correlated  with the sub-carriers mask and with the RFI setup."
			REFERENCE
				"ITU-T G.997.1, paragraph 7.3.1.2"
			::= { sheAdslLineConfExtnProfileControl 50 }

		
--   1.3.6.1.4.1.231.7.1.2.2.1.6.1.1.7.51
		sheAdslLineConfExtnProfileControlPSDMASKdsEnable OBJECT-TYPE
			SYNTAX SheAdslLineConfEnableType
			MAX-ACCESS read-write
			STATUS current
			DESCRIPTION
				"User custom PSD mask-related parameter used by the ATU-C to use user custom PSD mask.
				(Not available for ADSL but ADSL2 and ADSL2plus )."
			REFERENCE
				"ITU-T G.997.1, paragraph 7.3.1.2"
			::= { sheAdslLineConfExtnProfileControl 51 }

		
--   1.3.6.1.4.1.231.7.1.2.2.1.6.1.1.7.52
		sheAdslLineConfExtnProfileControlPSDMASKdsRequestResult OBJECT-TYPE
			SYNTAX SheAdslControlPSDMASKdsRequestResultType
			MAX-ACCESS read-only
			STATUS current
			DESCRIPTION
				" The result of the last psd commmand"
			::= { sheAdslLineConfExtnProfileControl 52 }

		
--   1.3.6.1.4.1.231.7.1.2.2.1.6.1.1.7.45
		sheAdslLineConfExtnProfileControlConfMinInpUs OBJECT-TYPE
			SYNTAX SheAdslConfMinInpType
			MAX-ACCESS read-write
			STATUS current
			DESCRIPTION
				"Look at table."
			::= { sheAdslLineConfExtnProfileControl 53 }

		
--   1.3.6.1.4.1.231.7.1.2.2.1.6.1.1.8
		sheAdslLineTable OBJECT-TYPE
			SYNTAX SEQUENCE OF SheAdslLineEntry
			MAX-ACCESS not-accessible
			STATUS current
			DESCRIPTION
				"This table includes common attributes describing
				both ends of the line.  It is required for all ADSL
				physical interfaces.  ADSL physical interfaces are
				those ifEntries where ifType is equal to adsl(94)."
			::= { sheAdslLineMIB 8 }

		
--   1.3.6.1.4.1.231.7.1.2.2.1.6.1.1.8.1
		sheAdslLineEntry OBJECT-TYPE
			SYNTAX SheAdslLineEntry
			MAX-ACCESS not-accessible
			STATUS current
			DESCRIPTION
				"An entry in adslLineTable."
			INDEX { ifIndex }
			::= { sheAdslLineTable 1 }

		
		SheAdslLineEntry ::=
			SEQUENCE { 
				sheAdslLineCoding
					AdslLineCodingType,
				sheAdslLineType
					SheAdslConfLineType,
				sheAdslLineSpecific
					VariablePointer,
				sheAdslLineConfProfile
					SnmpAdminString,
				sheAdslLineAlarmConfProfile
					SnmpAdminString,
				sheAdslLineAction
					SheAdslLineActionType,
				sheAdslLineLineDmtTrellis
					SheAdslLineTrellisModeType,
				sheAdslLineUtopiaL2RxAddr
					INTEGER,
				sheAdslLineUtopiaL2TxAddr
					INTEGER,
				sheAdslLineClockType
					SheAdslLineClockType,
				sheAdslLineAtucCapability
					SheAdslAtuxCapabilityType,
				sheAdslLineAturCapability
					SheAdslAtuxCapabilityType,
				sheAdslLineAtuActualCapability
					SheAdslAtuxCapabilityType,
				sheAdslLinePwrMgmtPMSF
					SheAdslPwrMgmtPMSFType,
				sheAdslLineDeltConfLDSF
					SheAdslLineDeltConfLDSFType,
				sheAdslLineRfiBandMask
					OCTET STRING,
				sheAdslLineDpboProfile
					SnmpAdminString
			 }

--   1.3.6.1.4.1.231.7.1.2.2.1.6.1.1.8.1.1
		sheAdslLineCoding OBJECT-TYPE
			SYNTAX AdslLineCodingType
			MAX-ACCESS read-only
			STATUS current
			DESCRIPTION
				"Specifies the ADSL coding type used on this line."
			::= { sheAdslLineEntry 1 }

		
--   1.3.6.1.4.1.231.7.1.2.2.1.6.1.1.8.1.2
		sheAdslLineType OBJECT-TYPE
			SYNTAX SheAdslConfLineType
			MAX-ACCESS read-only
			STATUS current
			DESCRIPTION
				"Shows the type of ADSL physical line entity that exists, by defining
				whether and how the line is channelized. If the line is channelized,
				the value will be other than noChannel(1).
				This object shows which channel type(s) are currently supported.
				
				This values are possible:
				no channels exist (maybe line is not accessible)
				fast channel exists only (singleLatency)
				interleaved channel exists only (singleLatency)
				fast and interleaved channel exist (dualLatency)"
			::= { sheAdslLineEntry 2 }

		
--   1.3.6.1.4.1.231.7.1.2.2.1.6.1.1.8.1.3
		sheAdslLineSpecific OBJECT-TYPE
			SYNTAX VariablePointer
			MAX-ACCESS read-only
			STATUS current
			DESCRIPTION
				"OID instance in vendor-specific MIB. The Instance may
				be used to determine shelf/slot/port of the ATUC
				interface in a DSLAM."
			::= { sheAdslLineEntry 3 }

		
--   1.3.6.1.4.1.231.7.1.2.2.1.6.1.1.8.1.4
		sheAdslLineConfProfile OBJECT-TYPE
			SYNTAX SnmpAdminString (SIZE (1..32))
			MAX-ACCESS read-only
			STATUS current
			DESCRIPTION
				"The value of this object identifies the row in the ADSL Line Configuration Profile Table,
				which applies for this ADSL line, and channels if applicable.
				
				                            A 'DEFVAL' profile will always be exist and set per default.
				"
			::= { sheAdslLineEntry 4 }

		
--   1.3.6.1.4.1.231.7.1.2.2.1.6.1.1.8.1.6
		sheAdslLineAlarmConfProfile OBJECT-TYPE
			SYNTAX SnmpAdminString (SIZE (1..32))
			MAX-ACCESS read-only
			STATUS current
			DESCRIPTION
				"The value of this object identifies the row in the ADSL Line Alarm Configuration Profile Table,
				which applies to this ADSL line, and channels if applicable.
				A 'DEFAULT' profile will always be exist and set.
				"
			::= { sheAdslLineEntry 6 }

		
--   1.3.6.1.4.1.231.7.1.2.2.1.6.1.1.8.1.7
		sheAdslLineAction OBJECT-TYPE
			SYNTAX SheAdslLineActionType
			MAX-ACCESS read-only
			STATUS current
			DESCRIPTION
				"This object indicates parameter that allows actions on a per line basis. 
				These actions include abort, startup, and tests."
			::= { sheAdslLineEntry 7 }

		
--   1.3.6.1.4.1.231.7.1.2.2.1.6.1.1.8.1.8
		sheAdslLineLineDmtTrellis OBJECT-TYPE
			SYNTAX SheAdslLineTrellisModeType
			MAX-ACCESS read-only
			STATUS current
			DESCRIPTION
				"Parameter that indicates whether trellis coding has been enabled or disabled. Trellis coding should always be enabled for its clear performance advantage.
				trellisOn(1),
				trellisOff(2)
				"
			::= { sheAdslLineEntry 8 }

		
--   1.3.6.1.4.1.231.7.1.2.2.1.6.1.1.8.1.9
-- THIS ELEMENT WILL NOT LONGER BE SUPPORTED BY NE up R2.5.
		sheAdslLineUtopiaL2RxAddr OBJECT-TYPE
			SYNTAX INTEGER (1..255)
			MAX-ACCESS read-only
			STATUS current
			DESCRIPTION
				"This object indicates UTOPIA Level 2 Rx address for a line."
			::= { sheAdslLineEntry 9 }

		
--   1.3.6.1.4.1.231.7.1.2.2.1.6.1.1.8.1.10
-- THIS ELEMENT WILL NOT LONGER BE SUPPORTED BY NE up R2.5.
		sheAdslLineUtopiaL2TxAddr OBJECT-TYPE
			SYNTAX INTEGER (1..255)
			MAX-ACCESS read-only
			STATUS current
			DESCRIPTION
				"This object indicates UTOPIA Level 2 Tx address for a line."
			::= { sheAdslLineEntry 10 }

		
--   1.3.6.1.4.1.231.7.1.2.2.1.6.1.1.8.1.12
-- THIS ELEMENT WILL NOT LONGER BE SUPPORTED BY NE up R2.5.
		sheAdslLineClockType OBJECT-TYPE
			SYNTAX SheAdslLineClockType
			MAX-ACCESS read-only
			STATUS current
			DESCRIPTION
				"This object indicates parameter to set use of either crystal or oscillator."
			::= { sheAdslLineEntry 12 }

		
--   1.3.6.1.4.1.231.7.1.2.2.1.6.1.1.8.1.13
		sheAdslLineAtucCapability OBJECT-TYPE
			SYNTAX SheAdslAtuxCapabilityType
			MAX-ACCESS read-only
			STATUS current
			DESCRIPTION
				"The capability of co-side. Be aware that multiple bits could be set! Each bit set to 1 means,
				that the corresponding standart is supported."
			::= { sheAdslLineEntry 13 }

		
--   1.3.6.1.4.1.231.7.1.2.2.1.6.1.1.8.1.14
		sheAdslLineAturCapability OBJECT-TYPE
			SYNTAX SheAdslAtuxCapabilityType
			MAX-ACCESS read-only
			STATUS current
			DESCRIPTION
				"The capability of remote-side. Only available if line has trained - otherwise 0.
				Be aware that multiple bits could be set! Each bit set to 1 means,
				that the corresponding standart is supported."
			::= { sheAdslLineEntry 14 }

		
--   1.3.6.1.4.1.231.7.1.2.2.1.6.1.1.8.1.15
		sheAdslLineAtuActualCapability OBJECT-TYPE
			SYNTAX SheAdslAtuxCapabilityType
			MAX-ACCESS read-only
			STATUS current
			DESCRIPTION
				"The actual used capability of the line. Only available if line has trained - otherwise 0.
				Each bit set to 1 means, that the corresponding standart is supported."
			::= { sheAdslLineEntry 15 }

		
--   1.3.6.1.4.1.231.7.1.2.2.1.6.1.1.8.1.16
		sheAdslLinePwrMgmtPMSF OBJECT-TYPE
			SYNTAX SheAdslPwrMgmtPMSFType
			MAX-ACCESS read-only
			STATUS current
			DESCRIPTION
				"This object indicates the action that forces a change in the line state of
				power management. (Not available for ADSL G992.1)
				Valid values:
				pmsfL0ToL2StateForce(1) -> testmode, set running line to L2 power safe mode
				pmsfL2ToL0StateForce(3) -> switch back line from L2 power safe mode to full power L0 state
				
				The transitions pmsfL3ToL0StateForce (unlock) and pmsfL3StateForce (lock) should always
				be done via ifAdminState setting.
				"
			REFERENCE
				"G997.1 chapter 7.3.1.1.3"
			::= { sheAdslLineEntry 16 }

		
--   1.3.6.1.4.1.231.7.1.2.2.1.6.1.1.8.1.17
		sheAdslLineDeltConfLDSF OBJECT-TYPE
			SYNTAX SheAdslLineDeltConfLDSFType
			MAX-ACCESS read-only
			STATUS current
			DESCRIPTION
				"DELT-related parameter used by the ATU-C to force the line into loop diagnostics mode.
				(Not available for ADSL but ADSL2 and ADSL2plus )."
			DEFVAL { inhibit }
			::= { sheAdslLineEntry 17 }

		
--   1.3.6.1.4.1.231.7.1.2.2.1.6.1.1.8.1.18
		sheAdslLineRfiBandMask OBJECT-TYPE
			SYNTAX OCTET STRING (SIZE (4))
			MAX-ACCESS read-only
			STATUS current
			DESCRIPTION
				"BitMask for used sheAdslRfiBandIndex. A Bit-Position correspond's with an index
				in sheAdslRfiBandTable and mark configured RFI bands they are used for this profile."
			::= { sheAdslLineEntry 18 }

		
--   1.3.6.1.4.1.231.7.1.2.2.1.6.1.1.8.1.19
		sheAdslLineDpboProfile OBJECT-TYPE
			SYNTAX SnmpAdminString (SIZE (0..32))
			MAX-ACCESS read-only
			STATUS current
			DESCRIPTION
				"The value of this object identifies the row in the AdslLineDpboProfile Table,
				which applies for this ADSL line.
				
				No 'DEFVAL' profile will exist. Per default no profile is assigned!"
			DEFVAL { "" }
			::= { sheAdslLineEntry 19 }

		
--   1.3.6.1.4.1.231.7.1.2.2.1.6.1.1.9
		sheAdslLineControl OBJECT IDENTIFIER ::= { sheAdslLineMIB 9 }

		
--   1.3.6.1.4.1.231.7.1.2.2.1.6.1.1.9.1
		sheAdslLineControlRequest OBJECT-TYPE
			SYNTAX SheAdslControlRequestType
			MAX-ACCESS read-write
			STATUS current
			DESCRIPTION
				"modifyAdslLineEntry:
				sheAdslLineControlIndex
				sheAdslLineControlConfProfile
				sheAdslLineControlAction
												
				modifyAdslLineAlarmConfProfileEntry:
				sheAdslLineControlIndex
				sheAdslLineControlAlarmConfProfile
				
				
				forceAdslLinePwrMgmtState:
				vheAdslLineControlIndex
				sheAdslLineControlPwrMgmtPMSF
				modifyAdslLineDeltConfEntry:
				sheAdslLineControlIndex
				sheAdslLineControlDeltConfLDSF
								
				modifyAdslLineRfiBandMask:
				sheAdslLineControlIndex
				sheAdslLineControlRfiBandMask
				
				##New for SHR R2.6
				setAdslLineDpboProfileEntry:
				sheAdslLineControlIndex
				sheAdslLineControlDpboProfile
				"
			::= { sheAdslLineControl 1 }

		
--   1.3.6.1.4.1.231.7.1.2.2.1.6.1.1.9.2
		sheAdslLineControlIndex OBJECT-TYPE
			SYNTAX Integer32
			MAX-ACCESS read-write
			STATUS current
			DESCRIPTION
				"IfIndex of the configured adsl-interface."
			::= { sheAdslLineControl 2 }

		
--   1.3.6.1.4.1.231.7.1.2.2.1.6.1.1.9.3
		sheAdslLineControlStatus OBJECT-TYPE
			SYNTAX SheControlStatusType
			MAX-ACCESS read-only
			STATUS current
			DESCRIPTION
				"The status of a user command. 
				"
			::= { sheAdslLineControl 3 }

		
--   1.3.6.1.4.1.231.7.1.2.2.1.6.1.1.9.4
		sheAdslLineControlTimer OBJECT-TYPE
			SYNTAX Gauge32
			MAX-ACCESS read-only
			STATUS current
			DESCRIPTION
				"The maximum wait time for the manager for a long running user command. 
				"
			::= { sheAdslLineControl 4 }

		
--   1.3.6.1.4.1.231.7.1.2.2.1.6.1.1.9.5
		sheAdslLineControlReqResult OBJECT-TYPE
			SYNTAX SheAdslControlRequestResultType
			MAX-ACCESS read-only
			STATUS current
			DESCRIPTION
				"The result of the last user command."
			::= { sheAdslLineControl 5 }

		
--   1.3.6.1.4.1.231.7.1.2.2.1.6.1.1.9.6
		sheAdslLineControlTimeStamp OBJECT-TYPE
			SYNTAX Unsigned32
			UNITS "sec"
			MAX-ACCESS read-only
			STATUS current
			DESCRIPTION
				"The time stamp of the last command (end of command)."
			::= { sheAdslLineControl 6 }

		
--   1.3.6.1.4.1.231.7.1.2.2.1.6.1.1.9.7
		sheAdslLineControlConfProfile OBJECT-TYPE
			SYNTAX SnmpAdminString (SIZE (1..32))
			MAX-ACCESS read-write
			STATUS current
			DESCRIPTION
				"The value of this object identifies the row
				in the ADSL Line Configuration Profile Table,
				(adslLineConfProfileTable), which applies for this
				ADSL line, and channels if applicable.
				
				For the used `dynamic' mode, in the case which the
				configuration profile has not been set, the
				value will be set to `DEFVAL'.
				
				"
			::= { sheAdslLineControl 7 }

		
--   1.3.6.1.4.1.231.7.1.2.2.1.6.1.1.9.9
		sheAdslLineControlAlarmConfProfile OBJECT-TYPE
			SYNTAX SnmpAdminString (SIZE (1..32))
			MAX-ACCESS read-write
			STATUS current
			DESCRIPTION
				"The value of this object identifies the row
				in the ADSL Line Alarm Configuration Profile Table,
				(adslLineAlarmConfProfileTable), which applies to this
				ADSL line, and channels if applicable.
				
				For the used `dynamic' mode, in the case which the
				alarm profile has not been set, the
				value will be set to `DEFVAL'.
				
				"
			::= { sheAdslLineControl 9 }

		
--   1.3.6.1.4.1.231.7.1.2.2.1.6.1.1.9.10
		sheAdslLineControlAction OBJECT-TYPE
			SYNTAX SheAdslLineActionType
			MAX-ACCESS read-write
			STATUS current
			DESCRIPTION
				"This object indicates parameter that allows actions on a per line basis. These actions include abort, startup, and tests."
			::= { sheAdslLineControl 10 }

		
--   1.3.6.1.4.1.231.7.1.2.2.1.6.1.1.9.11
		sheAdslLineControlPwrMgmtPMSF OBJECT-TYPE
			SYNTAX SheAdslPwrMgmtPMSFType
			MAX-ACCESS read-write
			STATUS current
			DESCRIPTION
				"Force a change in the line state of power management.
				(Not available for ADSL G992.1)
				
				Valid values:
				pmsfL0ToL2StateForce(1) -> testmode, set running line to L2 power safe mode
				pmsfL2ToL0StateForce(3) -> switch back line from L2 power safe mode to full power L0 state
				
				The transitions pmsfL3ToL0StateForce (unlock) and pmsfL3StateForce (lock) should always
				be done via ifAdminState setting."
			::= { sheAdslLineControl 11 }

		
--   1.3.6.1.4.1.231.7.1.2.2.1.6.1.1.9.12
		sheAdslLineControlDeltConfLDSF OBJECT-TYPE
			SYNTAX SheAdslLineDeltConfLDSFType
			MAX-ACCESS read-write
			STATUS current
			DESCRIPTION
				"DELT-related parameter used by the ATU-C to force the line into loop diagnostics mode.
				(Not available for ADSL but ADSL2 and ADSL2plus )."
			::= { sheAdslLineControl 12 }

		
--   1.3.6.1.4.1.231.7.1.2.2.1.6.1.1.9.13			
		sheAdslLineControlRfiBandMask OBJECT-TYPE
			SYNTAX OCTET STRING (SIZE (0..4))
			MAX-ACCESS read-write
			STATUS current
			DESCRIPTION
				"BitMask for sheAdslRfiBandIndex in sheAdslRfiBandTable."
			::= { sheAdslLineControl 13 }

		
--   1.3.6.1.4.1.231.7.1.2.2.1.6.1.1.9.7
		sheAdslLineControlDpboProfile OBJECT-TYPE
			SYNTAX SnmpAdminString (SIZE (0..32))
			MAX-ACCESS read-write
			STATUS current
			DESCRIPTION
				"The value of this object identifies the row in the AdslLineDpboProfile Table,
				which applies for this ADSL line."
			::= { sheAdslLineControl 14 }

		
--   1.3.6.1.4.1.231.7.1.2.2.1.6.1.1.10
		sheAdslAtucPhysTable OBJECT-TYPE
			SYNTAX SEQUENCE OF SheAdslAtucPhysEntry
			MAX-ACCESS not-accessible
			STATUS current
			DESCRIPTION
				"This table provides one row for each ATUC.
				Each row contains the Physical Layer Parameters
				table for that ATUC. ADSL physical interfaces are
				those ifEntries where ifType is equal to adsl(94)."
			::= { sheAdslLineMIB 10 }

		
--   1.3.6.1.4.1.231.7.1.2.2.1.6.1.1.10.1
		sheAdslAtucPhysEntry OBJECT-TYPE
			SYNTAX SheAdslAtucPhysEntry
			MAX-ACCESS not-accessible
			STATUS current
			DESCRIPTION
				"An entry in the adslAtucPhysTable."
			INDEX { ifIndex }
			::= { sheAdslAtucPhysTable 1 }

		
		SheAdslAtucPhysEntry ::=
			SEQUENCE { 
				sheAdslAtucPhysInvSerialNumber
					SnmpAdminString,
				sheAdslAtucPhysInvVendorID
					SnmpAdminString,
				sheAdslAtucPhysInvVersionNumber
					SnmpAdminString,
				sheAdslAtucPhysCurrSnrMgn
					INTEGER,
				sheAdslAtucPhysCurrAtn
					Gauge32,
				sheAdslAtucPhysCurrStatus
					SheAdslLineCurrentStatusType,
				sheAdslAtucPhysCurrOutputPwr
					INTEGER,
				sheAdslAtucPhysCurrAttainableRate
					Gauge32,
				sheAdslAtucPhysOpState
					SheAdslLineOpStateType,
				sheAdslAtucPhysActualStd
					SheAdslLineConfStandardType,
				sheAdslAtucPhysBertError
					Unsigned32,
				sheAdslAtucPhysTxAtmCellCounter
					Counter32,
				sheAdslAtucPhysRxAtmCellCounter
					Unsigned32,
				sheAdslAtucPhysStartProgress
					Unsigned32,
				sheAdslAtucPhysIdleBertError
					Unsigned32,
				sheAdslAtucPhysIdleBertCells
					Unsigned32,
				sheAdslAtucPhysBertSync
					SheAdslAtucPhysBertSyncType,
				sheAdslAtucPhysParametricTestResult
					SheAdslAtucPhysParametricTestResultType,
				sheAdslAtucPwrMgmtState
					SheAdslPwrMgmtStateType,
				sheAdslAtucPhysDeltHLINSCus
					Unsigned32,
				sheAdslAtucPhysDeltHLINpsus
					OCTET STRING,
				sheAdslAtucPhysDeltHLOGMTus
					Unsigned32,
				sheAdslAtucPhysDeltHLOGpsus
					OCTET STRING,
				sheAdslAtucPhysDeltQLNMTus
					Unsigned32,
				sheAdslAtucPhysDeltQLNpsus
					OCTET STRING,
				sheAdslAtucPhysActState
					SheAdslLineActStateType,
				sheAdslAtucPhysCurrentBinStatus
					OCTET STRING,
				sheAdslAtucPhysCurrentBinBitLoading
					OCTET STRING,
				sheAdslAtucPhysDeltSNRMTus
					Unsigned32,
				sheAdslAtucPhysDeltDMTBinSNRus
					OCTET STRING,
				sheAdslAtucPhysDeltLastTxState
					SheAdslPhysAtucDeltLastTxStateType,
				sheAdslAtucPhysDeltSATNus
					Unsigned32
			 }

--   1.3.6.1.4.1.231.7.1.2.2.1.6.1.1.10.1.1
		sheAdslAtucPhysInvSerialNumber OBJECT-TYPE
			SYNTAX SnmpAdminString (SIZE (0..32))
			MAX-ACCESS read-only
			STATUS current
			DESCRIPTION
				"The vendor specific string that identifies the
				vendor equipment."
			::= { sheAdslAtucPhysEntry 1 }

		
--   1.3.6.1.4.1.231.7.1.2.2.1.6.1.1.10.1.2
		sheAdslAtucPhysInvVendorID OBJECT-TYPE
			SYNTAX SnmpAdminString (SIZE (0..16))
			MAX-ACCESS read-only
			STATUS current
			DESCRIPTION
				"The vendor ID code is a copy of the binary
				vendor identification field defined by the
				PHY[10] and expressed as readable characters."
			REFERENCE
				"ANSI T1.413[10]"
			::= { sheAdslAtucPhysEntry 2 }

		
--   1.3.6.1.4.1.231.7.1.2.2.1.6.1.1.10.1.3
		sheAdslAtucPhysInvVersionNumber OBJECT-TYPE
			SYNTAX SnmpAdminString (SIZE (0..16))
			MAX-ACCESS read-only
			STATUS current
			DESCRIPTION
				"The vendor specific version number sent by this ATU
				as part of the initialization messages.  It is a copy
				of the binary version number field defined by the
				PHY[10] and expressed as readable characters."
			REFERENCE
				"ANSI T1.413[10]"
			::= { sheAdslAtucPhysEntry 3 }

		
--   1.3.6.1.4.1.231.7.1.2.2.1.6.1.1.10.1.4
		sheAdslAtucPhysCurrSnrMgn OBJECT-TYPE
			SYNTAX INTEGER (-640..640)
			UNITS "tenth dB"
			MAX-ACCESS read-only
			STATUS current
			DESCRIPTION
				"Noise Margin as seen by this ATU with respect to its
				received signal in tenth dB."
			::= { sheAdslAtucPhysEntry 4 }

		
--   1.3.6.1.4.1.231.7.1.2.2.1.6.1.1.10.1.5
		sheAdslAtucPhysCurrAtn OBJECT-TYPE
			SYNTAX Gauge32 (0..630)
			UNITS "tenth dB"
			MAX-ACCESS read-only
			STATUS current
			DESCRIPTION
				"Measured difference in the total power transmitted by
				the peer ATU and the total power received by this ATU."
			::= { sheAdslAtucPhysEntry 5 }

		
--   1.3.6.1.4.1.231.7.1.2.2.1.6.1.1.10.1.6
		sheAdslAtucPhysCurrStatus OBJECT-TYPE
			SYNTAX SheAdslLineCurrentStatusType
			MAX-ACCESS read-only
			STATUS current
			DESCRIPTION
				"Indicates current state of the ATUC line.  This is a
				bit-map of possible conditions.  The various bit
				positions are:
				
				0      noDefect             There no defects on the line
				
				1      lossOfFraming        ATUC failure due to not
				                     receiving valid frame.
				
				2      lossOfSignal         ATUC failure due to not
				                     receiving signal.
				
				3      lossOfPower          ATUC failure due to loss of
				                     power.
				                     Note: the Agent may still
				                     function.
				
				4      lossOfSignalQuality  Loss of Signal Quality is
				                     declared when the Noise Margin
				                     falls below the Minimum Noise
				                     Margin, or the bit-error-rate
				                     exceeds 10^-7.
				
				5      lossOfLink           ATUC failure due to inability
				                     to link with ATUR.
				
				6      dataInitFailure      ATUC failure during
				                     initialization due to bit
				                     errors corrupting startup
				                     exchange data.
				
				7      configInitFailure    ATUC failure during
				                     initialization due to peer
				                     ATU not able to support
				                     requested configuration
				
				8      protocolInitFailure  ATUC failure during
				                     initialization due to
				                     incompatible protocol used by
				                     the peer ATU.
				
				9      noPeerAtuPresent     ATUC failure during
				                     initialization due to no
				                     activation sequence detected
				                     from peer ATU.
				
				This is intended to supplement ifOperStatus."
			::= { sheAdslAtucPhysEntry 6 }

		
--   1.3.6.1.4.1.231.7.1.2.2.1.6.1.1.10.1.7
		sheAdslAtucPhysCurrOutputPwr OBJECT-TYPE
			SYNTAX INTEGER (-310..310)
			UNITS "tenth dBm"
			MAX-ACCESS read-only
			STATUS current
			DESCRIPTION
				"Measured total output power transmitted by this ATU.
				This is the measurement that was reported during
				the last activation sequence."
			::= { sheAdslAtucPhysEntry 7 }

		
--   1.3.6.1.4.1.231.7.1.2.2.1.6.1.1.10.1.8
		sheAdslAtucPhysCurrAttainableRate OBJECT-TYPE
			SYNTAX Gauge32
			UNITS "kbps"
			MAX-ACCESS read-only
			STATUS current
			DESCRIPTION
				"Indicates the maximum currently attainable data rate
				by the ATU.  This value will be equal or greater than
				the current line rate."
			::= { sheAdslAtucPhysEntry 8 }

		
--   1.3.6.1.4.1.231.7.1.2.2.1.6.1.1.10.1.9
		sheAdslAtucPhysOpState OBJECT-TYPE
			SYNTAX SheAdslLineOpStateType
			MAX-ACCESS read-only
			STATUS current
			DESCRIPTION
				"This object indicates the operational state of the ATU. Values include idle,handshake, training, Delt mode (loop diagnostic mode), etc.
				idle(0),
				data(1),
				bootUpLoad(8),
				handshake(16),
				training(24),
				framerSync(26),
				fastRetrainInProg(27),
				llTest(128),
				dlTest(131),
				txTest(132),
				atmLpTest(133),
				discovery(46),
				deltTraining(139),
				delt(140)
				"
			::= { sheAdslAtucPhysEntry 9 }

		
--   1.3.6.1.4.1.231.7.1.2.2.1.6.1.1.10.1.10
		sheAdslAtucPhysActualStd OBJECT-TYPE
			SYNTAX SheAdslLineConfStandardType
			MAX-ACCESS read-only
			STATUS current
			DESCRIPTION
				"This object provides actual ATU-C configuration based on outcome of negotiation with ATU-R. In this case, the parameter provides actual standard used for the connection."
			::= { sheAdslAtucPhysEntry 10 }

		
--   1.3.6.1.4.1.231.7.1.2.2.1.6.1.1.10.1.11
		sheAdslAtucPhysBertError OBJECT-TYPE
			SYNTAX Unsigned32
			MAX-ACCESS read-only
			STATUS current
			DESCRIPTION
				"This object indicates the No. of bit errors detected during BERT."
			::= { sheAdslAtucPhysEntry 11 }

		
--   1.3.6.1.4.1.231.7.1.2.2.1.6.1.1.10.1.12
		sheAdslAtucPhysTxAtmCellCounter OBJECT-TYPE
			SYNTAX Counter32
			MAX-ACCESS read-only
			STATUS current
			DESCRIPTION
				"This object Provides transmit ATM cell counter."
			::= { sheAdslAtucPhysEntry 12 }

		
--   1.3.6.1.4.1.231.7.1.2.2.1.6.1.1.10.1.13
		sheAdslAtucPhysRxAtmCellCounter OBJECT-TYPE
			SYNTAX Unsigned32
			MAX-ACCESS read-only
			STATUS current
			DESCRIPTION
				"This object Provides receive ATM cell counter."
			::= { sheAdslAtucPhysEntry 13 }

		
--   1.3.6.1.4.1.231.7.1.2.2.1.6.1.1.10.1.14
		sheAdslAtucPhysStartProgress OBJECT-TYPE
			SYNTAX Unsigned32
			MAX-ACCESS read-only
			STATUS current
			DESCRIPTION
				"This object provides current detailed start up information to be used for debugging."
			::= { sheAdslAtucPhysEntry 14 }

		
--   1.3.6.1.4.1.231.7.1.2.2.1.6.1.1.10.1.15
		sheAdslAtucPhysIdleBertError OBJECT-TYPE
			SYNTAX Unsigned32
			MAX-ACCESS read-only
			STATUS current
			DESCRIPTION
				"Number of bit errors."
			::= { sheAdslAtucPhysEntry 15 }

		
--   1.3.6.1.4.1.231.7.1.2.2.1.6.1.1.10.1.16
		sheAdslAtucPhysIdleBertCells OBJECT-TYPE
			SYNTAX Unsigned32
			MAX-ACCESS read-only
			STATUS current
			DESCRIPTION
				"Number of idle cells."
			::= { sheAdslAtucPhysEntry 16 }

		
--   1.3.6.1.4.1.231.7.1.2.2.1.6.1.1.10.1.17
		sheAdslAtucPhysBertSync OBJECT-TYPE
			SYNTAX SheAdslAtucPhysBertSyncType
			MAX-ACCESS read-only
			STATUS current
			DESCRIPTION
				"Indicates if the Signal is in Sync or not."
			::= { sheAdslAtucPhysEntry 17 }

		
--   1.3.6.1.4.1.231.7.1.2.2.1.6.1.1.10.1.18
		sheAdslAtucPhysParametricTestResult OBJECT-TYPE
			SYNTAX SheAdslAtucPhysParametricTestResultType
			MAX-ACCESS read-only
			STATUS current
			DESCRIPTION
				"Indicates the Result of the Parametric Test conducted on the Xcvr."
			::= { sheAdslAtucPhysEntry 18 }

		
--   1.3.6.1.4.1.231.7.1.2.2.1.6.1.1.10.1.19
		sheAdslAtucPwrMgmtState OBJECT-TYPE
			SYNTAX SheAdslPwrMgmtStateType
			MAX-ACCESS read-only
			STATUS current
			DESCRIPTION
				"Line Power Management State. (Not valid for ADSL G992.1)"
			REFERENCE
				"G997.1 chapter 7.5.1.2"
			::= { sheAdslAtucPhysEntry 19 }

		
--   1.3.6.1.4.1.231.7.1.2.2.1.6.1.1.10.1.20
		sheAdslAtucPhysDeltHLINSCus OBJECT-TYPE
			SYNTAX Unsigned32
			MAX-ACCESS read-only
			STATUS current
			DESCRIPTION
				"DELT-related parameter that provides the scale factor to be applied to the 
				upstream Hlin(f) values.
				Only available after a loop diagnostic procedure.
				(Not available for ADSL but ADSL2 & ADSL2plus)."
			REFERENCE
				"G997.1 chapter 7.5.1.18.5"
			::= { sheAdslAtucPhysEntry 20 }

		
--   1.3.6.1.4.1.231.7.1.2.2.1.6.1.1.10.1.21
		sheAdslAtucPhysDeltHLINpsus OBJECT-TYPE
			SYNTAX OCTET STRING (SIZE (0..128))
			MAX-ACCESS read-only
			STATUS current
			DESCRIPTION
				"DELT-related parameter that provides an array of complex upstream Hlin(f) values 
				in linear scale. Every two octects refer to one element in this array of octets.
				(Not available for ADSL but ADSL2 & ADSL2plus).
				
				This parameter is an array of complex upstream Hlin(f) values in linear scale.
				Each array entry represents the Hlin(f = i*HLINGus* delta(f)) value for a 
				particular subcarrier group index i, ranging from 0 to MIN(NSCus - 1,511).
				The Hlin(f) is represented as ((scale/2(exp15))*((a(i) + j*b(i))/2(exp15))), with scale
				being coded as a 16-bit unsigned integer and, a(i) and b(i) coded as 
				16-bit 2s complement signed integers in the (-2(exp15) + 1) to (+2(exp15) - 1) range.
				A special value a(i) = b(i) = -2(exp15) indicates that no measurement could be done
				for this subcarrier group because it is out of the passband or that the 
				attenuation is out of range to be represented. This parameter is only available
				after a loop diagnostic procedure."
			REFERENCE
				"G997.1 chapter 7.5.1.18.6"
			::= { sheAdslAtucPhysEntry 21 }

		
--   1.3.6.1.4.1.231.7.1.2.2.1.6.1.1.10.1.22
		sheAdslAtucPhysDeltHLOGMTus OBJECT-TYPE
			SYNTAX Unsigned32
			MAX-ACCESS read-only
			STATUS current
			DESCRIPTION
				"DELT-related parameter that provides the number of symbols used to measure the 
				upstream Hlog(f). 
				(Not available for ADSL but ADSL2 & ADSL2plus)."
			REFERENCE
				"G997.1 chapter 7.5.1.18.7"
			::= { sheAdslAtucPhysEntry 22 }

		
--   1.3.6.1.4.1.231.7.1.2.2.1.6.1.1.10.1.23
		sheAdslAtucPhysDeltHLOGpsus OBJECT-TYPE
			SYNTAX OCTET STRING (SIZE (0..64))
			MAX-ACCESS read-only
			STATUS current
			DESCRIPTION
				"DELT-related parameter that provides an array of real upstream Hlog(f) values in dB.
				(Not available for ADSL but ADSL2 & ADSL2plus).
				
				This parameter is an array of real upstream Hlog(f) values in dB.
				Each array entry represents the real Hlog(f = i*HLOGGus* delta(f)) value for a
				particular subcarrier group sub-carrier index i, ranging from 0 to MIN(NSCus - 1,511).
				The real Hlog(f) value is represented as (6 - m(i)/10), with m(i) 10-bit
				unsigned integer in the 0 to 1022 range. A special value m = 1023 indicates
				that no measurement could be done for this subcarrier group because it is out
				of the passband or that the attenuation is out of range to be represented."
			REFERENCE
				"G997.1 chapter 7.5.1.18.8"
			::= { sheAdslAtucPhysEntry 23 }

		
--   1.3.6.1.4.1.231.7.1.2.2.1.6.1.1.10.1.24
		sheAdslAtucPhysDeltQLNMTus OBJECT-TYPE
			SYNTAX Unsigned32
			MAX-ACCESS read-only
			STATUS current
			DESCRIPTION
				"DELT-related parameter that provides the number of symbols used to measure the 
				upstream QLN(f) values. 
				(Not available for ADSL but ADSL2 & ADSL2plus)."
			REFERENCE
				"G997.1 chapter 7.5.1.19.3"
			::= { sheAdslAtucPhysEntry 24 }

		
--   1.3.6.1.4.1.231.7.1.2.2.1.6.1.1.10.1.25
		sheAdslAtucPhysDeltQLNpsus OBJECT-TYPE
			SYNTAX OCTET STRING (SIZE (0..32))
			MAX-ACCESS read-only
			STATUS current
			DESCRIPTION
				"DELT-related parameter that provides an array of real upstream QLN(f) values in dBm/Hz. 
				Every two octects refer to one element in this array of octets.
				(Not available for ADSL but ADSL2 & ADSL2plus)
				
				This parameter is an array of real upstream QLN(f) values in dBm/Hz.
				Each array entry represents the QLN(f = i*QLNGus* delta(f)) value for a 
				particular subcarrier group index i, ranging from 0 to MIN(NSCus - 1,511).
				The QLN(f) is represented as (-23 - n(i)/2), with n(i) an 8-bit unsigned integer
				in the 0 to 254 range. A special value n(i) = 255 indicates that no measurement
				could be done for this subcarrier group because it is out of the passband or 
				that the noise PSD is out of range to be represented."
			REFERENCE
				"G997.1 chapter 7.5.1.19.4"
			::= { sheAdslAtucPhysEntry 25 }

		
--   1.3.6.1.4.1.231.7.1.2.2.1.6.1.1.10.1.26
		sheAdslAtucPhysActState OBJECT-TYPE
			SYNTAX SheAdslLineActStateType
			MAX-ACCESS read-only
			STATUS current
			DESCRIPTION
				"This object indicates the result of the ATU's line activation. Values include no error etc."
			::= { sheAdslAtucPhysEntry 26 }

		
--    1.3.6.1.4.1.231.7.1.2.2.1.6.1.1.10.1.27
		sheAdslAtucPhysCurrentBinStatus OBJECT-TYPE
			SYNTAX OCTET STRING (SIZE (0..512))
			MAX-ACCESS read-only
			STATUS current
			DESCRIPTION
				"This parameter represent the current bin status of used subcarriers.
				Each octet map to the corresponding bin."
			::= { sheAdslAtucPhysEntry 27 }

		
--    1.3.6.1.4.1.231.7.1.2.2.1.6.1.1.10.1.28
		sheAdslAtucPhysCurrentBinBitLoading OBJECT-TYPE
			SYNTAX OCTET STRING (SIZE (0..64))
			MAX-ACCESS read-only
			STATUS current
			DESCRIPTION
				"This parameter represent the current used bit loading per bin in upstream direction.
				Each octet map to the corresponding bin."
			::= { sheAdslAtucPhysEntry 28 }

		
--    1.3.6.1.4.1.231.7.1.2.2.1.6.1.1.10.1.29
		sheAdslAtucPhysDeltSNRMTus OBJECT-TYPE
			SYNTAX Unsigned32
			MAX-ACCESS read-only
			STATUS current
			DESCRIPTION
				"DELT-related parameter that provides the number of symbols used to measure 
				the upstream SNR(f) values. (Not available for ADSL and ADSL2plus)
				It is represented as a 16-bit unsigned value.
				After a loop diagnostic procedure, this parameter shall contain the number of symbols 
				used to generate the associate parameter. It should correspond to the value specified 
				in the Recommendation (e.g., the number of symbols in 1 s time interval for G.992.3)."
			::= { sheAdslAtucPhysEntry 29 }

		
--    1.3.6.1.4.1.231.7.1.2.2.1.6.1.1.10.1.30
		sheAdslAtucPhysDeltDMTBinSNRus OBJECT-TYPE
			SYNTAX OCTET STRING (SIZE (0..64))
			MAX-ACCESS read-only
			STATUS current
			DESCRIPTION
				"DELT-related parameter that provides an array of real upstream SNR(f) values 
				in dB (Not available for ADSL and ADSL2plus)
				It is coded in the same way as the related downstream parameter."
			::= { sheAdslAtucPhysEntry 30 }

		
--    1.3.6.1.4.1.231.7.1.2.2.1.6.1.1.10.1.31
		sheAdslAtucPhysDeltLastTxState OBJECT-TYPE
			SYNTAX SheAdslPhysAtucDeltLastTxStateType
			MAX-ACCESS read-only
			STATUS current
			DESCRIPTION
				"DELT-related parameter that provides last successful transmitted initialization 
				state by the ATU-C. (Not available for ADSL and ADSL2plus)
				
				Initialization states are defined in the individual ADSL Recommendations and are 
				counted from 0 (if G.994.1 is used) or 1 (if G.994.1 is not used) up to Showtime. 
				This parameter must be interpreted along with the ADSL Transmission System.
				This parameter is available only when, after a failed full initialization, the line 
				diagnostics procedures are activated on the line. Line diagnostics procedures can be 
				activated by the operator of the system (through the Line State Forced line configuration 
				parameter) or autonomously by the ATU-C or ATU-R."
			::= { sheAdslAtucPhysEntry 31 }

		
--    1.3.6.1.4.1.231.7.1.2.2.1.6.1.1.10.1.32
		sheAdslAtucPhysDeltSATNus OBJECT-TYPE
			SYNTAX Unsigned32 (0..1270)
			UNITS "0.1 dB"
			MAX-ACCESS read-only
			STATUS current
			DESCRIPTION
				"DELT-related parameter that provides the uptream signal attenuation (length = 4 bytes). 
				(Not available for ADSL and ADSL2plus). 				
				This parameter is the measured difference in dB in the total power transmitted by the ATU-R 
				and the total power received by the ATU-C over all subcarriers during showtime. The upstream 
				line attenuation ranges from 0 to +127 dB with 0.1 dB steps. A special value indicates the 
				line attenuation is out of range to be represented.
				NOTE: During showtime, only a subset of the subcarriers may be transmitted by the ATU-R, 
				as compared to diagnostics mode and initialization. Therefore, the upstream Signal attenuation 
				may be significantly lower than the upstream Line attenuation."
			::= { sheAdslAtucPhysEntry 32 }

		
--   1.3.6.1.4.1.231.7.1.2.2.1.6.1.1.11
		sheAdslAtucChanTable OBJECT-TYPE
			SYNTAX SEQUENCE OF SheAdslAtucChanEntry
			MAX-ACCESS not-accessible
			STATUS current
			DESCRIPTION
				"This table provides one row for each ATUC channel."
			::= { sheAdslLineMIB 11 }

		
--   1.3.6.1.4.1.231.7.1.2.2.1.6.1.1.11.1
		sheAdslAtucChanEntry OBJECT-TYPE
			SYNTAX SheAdslAtucChanEntry
			MAX-ACCESS not-accessible
			STATUS current
			DESCRIPTION
				"An entry in the adslAtucChanTable. 
				This table is only supported by NE releases smaller then R2.5 (NO dualLatency support)!!"
			INDEX { ifIndex }
			::= { sheAdslAtucChanTable 1 }

		
		SheAdslAtucChanEntry ::=
			SEQUENCE { 
				sheAdslAtucChanInterleaveDelay
					Gauge32,
				sheAdslAtucChanCurrTxRate
					Gauge32,
				sheAdslAtucChanPrevTxRate
					Gauge32,
				sheAdslAtucChanCrcBlockLength
					Gauge32,
				sheAdslAtucChanCurrAtmStatus
					SheAdslLineAtmStatus,
				sheAdslAtucChanRsSymbols
					Unsigned32,
				sheAdslAtucChanRsDepth
					Unsigned32,
				sheAdslAtucChanRsRedundancy
					Unsigned32
			 }

--   1.3.6.1.4.1.231.7.1.2.2.1.6.1.1.11.1.1
		sheAdslAtucChanInterleaveDelay OBJECT-TYPE
			SYNTAX Gauge32
			UNITS "milli-seconds"
			MAX-ACCESS read-only
			STATUS current
			DESCRIPTION
				"Interleave Delay for this channel.
				
				Interleave delay applies only to the
				interleave channel and defines the mapping
				(relative spacing) between subsequent input
				bytes at the interleaver input and their placement
				in the bit stream at the interleaver output.
				Larger numbers provide greater separation between
				consecutive input bytes in the output bit stream
				allowing for improved impulse noise immunity at
				the expense of payload latency.
				
				In the case where the ifType is Fast(125), use
				noSuchObject."
			::= { sheAdslAtucChanEntry 1 }

		
--   1.3.6.1.4.1.231.7.1.2.2.1.6.1.1.11.1.2
		sheAdslAtucChanCurrTxRate OBJECT-TYPE
			SYNTAX Gauge32 (1..32736)
			UNITS "kbps"
			MAX-ACCESS read-only
			STATUS current
			DESCRIPTION
				"Actual transmit rate on this channel."
			::= { sheAdslAtucChanEntry 2 }

		
--   1.3.6.1.4.1.231.7.1.2.2.1.6.1.1.11.1.3
		sheAdslAtucChanPrevTxRate OBJECT-TYPE
			SYNTAX Gauge32 (1..32736)
			UNITS "kbps"
			MAX-ACCESS read-only
			STATUS current
			DESCRIPTION
				"The rate at the time of the last
				adslAtucRateChangeTrap event. It is also set at
				initialization to prevent a trap being sent.
				
				Rate changes less than adslAtucThresh(*)RateDown
				or less than adslAtucThresh(*)RateUp will not
				cause a trap or cause this object to change.
				(*) == Fast or Interleave.
				See AdslLineAlarmConfProfileEntry."
			::= { sheAdslAtucChanEntry 3 }

		
--   1.3.6.1.4.1.231.7.1.2.2.1.6.1.1.11.1.4
		sheAdslAtucChanCrcBlockLength OBJECT-TYPE
			SYNTAX Gauge32
			UNITS "byte"
			MAX-ACCESS read-only
			STATUS current
			DESCRIPTION
				"Indicates the length of the channel data-block
				on which the CRC operates.  Refer to Line Code
				Specific MIBs, [11] and [12] for more
				information."
			::= { sheAdslAtucChanEntry 4 }

		
--   1.3.6.1.4.1.231.7.1.2.2.1.6.1.1.11.1.5
		sheAdslAtucChanCurrAtmStatus OBJECT-TYPE
			SYNTAX SheAdslLineAtmStatus
			MAX-ACCESS read-only
			STATUS current
			DESCRIPTION
				"indicates an ncd or lcd failure if the counter surpasses 127. If neither ATM counter surpasses 127, the return value will be 'NoAtmDefect'.
				noAtmDefect(0),
				noCellDeleniation(1),
				lossOfCellDeleniation(2)
				"
			::= { sheAdslAtucChanEntry 5 }

		
--   1.3.6.1.4.1.231.7.1.2.2.1.6.1.1.11.1.6
		sheAdslAtucChanRsSymbols OBJECT-TYPE
			SYNTAX Unsigned32
			MAX-ACCESS read-only
			STATUS current
			DESCRIPTION
				"Indicates number of DMT symbols per Reed-Solomon code word (S) in the downstream direction. Note that S is not restricted to interleaved mode only. Even in fast mode, S is a valid constant value and is equal to 1."
			::= { sheAdslAtucChanEntry 6 }

		
--   1.3.6.1.4.1.231.7.1.2.2.1.6.1.1.11.1.7
		sheAdslAtucChanRsDepth OBJECT-TYPE
			SYNTAX Unsigned32
			MAX-ACCESS read-only
			STATUS current
			DESCRIPTION
				"Indicates interleaving depth (D) in the downstream direction. Note that D is not restricted to interleaved mode only. Even in fast mode, D is a valid constant value and is equal to 1."
			::= { sheAdslAtucChanEntry 7 }

		
--   1.3.6.1.4.1.231.7.1.2.2.1.6.1.1.11.1.8
		sheAdslAtucChanRsRedundancy OBJECT-TYPE
			SYNTAX Unsigned32
			MAX-ACCESS read-only
			STATUS current
			DESCRIPTION
				"Indicates number of redundant bytes (R) per Reed-Solomon code in the downstream direction."
			::= { sheAdslAtucChanEntry 8 }

		
--   1.3.6.1.4.1.231.7.1.2.2.1.6.1.1.12
		sheAdslAtucPerfDataTable OBJECT-TYPE
			SYNTAX SEQUENCE OF SheAdslAtucPerfDataEntry
			MAX-ACCESS not-accessible
			STATUS current
			DESCRIPTION
				"This table provides one row for each ATUC.
				ADSL physical interfaces are
				those ifEntries where ifType is equal to adsl(94)."
			::= { sheAdslLineMIB 12 }

		
--   1.3.6.1.4.1.231.7.1.2.2.1.6.1.1.12.1
		sheAdslAtucPerfDataEntry OBJECT-TYPE
			SYNTAX SheAdslAtucPerfDataEntry
			MAX-ACCESS not-accessible
			STATUS current
			DESCRIPTION
				"An entry in adslAtucPerfDataTable."
			INDEX { ifIndex }
			::= { sheAdslAtucPerfDataTable 1 }

		
		SheAdslAtucPerfDataEntry ::=
			SEQUENCE { 
				sheAdslAtucPerfDataLofs
					Counter32,
				sheAdslAtucPerfDataLoss
					Counter32,
				sheAdslAtucPerfDataLols
					Counter32,
				sheAdslAtucPerfDataLprs
					Counter32,
				sheAdslAtucPerfDataESs
					Counter32,
				sheAdslAtucPerfDataInits
					Counter32,
				sheAdslAtucPerfDataStatFastR
					Gauge32,
				sheAdslAtucPerfDataStatFailedFastR
					Gauge32,
				sheAdslAtucPerfDataStatSesL
					Gauge32,
				sheAdslAtucPerfDataStatUasL
					Gauge32,
				sheAdslAtucPerfDataValidIntervals
					INTEGER,
				sheAdslAtucPerfDataInvalidIntervals
					INTEGER,
				sheAdslAtucPerfDataCurr15MinTimeElapsed
					AdslPerfTimeElapsed,
				sheAdslAtucPerfDataCurr15MinLofs
					PerfCurrentCount,
				sheAdslAtucPerfDataCurr15MinLoss
					PerfCurrentCount,
				sheAdslAtucPerfDataCurr15MinLols
					PerfCurrentCount,
				sheAdslAtucPerfDataCurr15MinLprs
					PerfCurrentCount,
				sheAdslAtucPerfDataCurr15MinESs
					PerfCurrentCount,
				sheAdslAtucPerfDataCurr15MinInits
					PerfCurrentCount,
				sheAdslAtucPerfDataCurr15MinFastR
					Gauge32,
				sheAdslAtucPerfDataCurr15MinFailedFastR
					Gauge32,
				sheAdslAtucPerfDataCurr15MinSesL
					Gauge32,
				sheAdslAtucPerfDataCurr15MinUasL
					Gauge32,
				sheAdslAtucPerfDataCurr1DayTimeElapsed
					AdslPerfTimeElapsed,
				sheAdslAtucPerfDataCurr1DayLofs
					AdslPerfCurrDayCount,
				sheAdslAtucPerfDataCurr1DayLoss
					AdslPerfCurrDayCount,
				sheAdslAtucPerfDataCurr1DayLols
					AdslPerfCurrDayCount,
				sheAdslAtucPerfDataCurr1DayLprs
					AdslPerfCurrDayCount,
				sheAdslAtucPerfDataCurr1DayESs
					AdslPerfCurrDayCount,
				sheAdslAtucPerfDataCurr1DayInits
					AdslPerfCurrDayCount,
				sheAdslAtucPerfDataCurr1DayFastR
					Gauge32,
				sheAdslAtucPerfDataCurr1DayFailedFastR
					Gauge32,
				sheAdslAtucPerfDataCurr1DaySesL
					Gauge32,
				sheAdslAtucPerfDataCurr1DayUasL
					Gauge32,
				sheAdslAtucPerfDataPrev1DayTimeElapsed
					Gauge32,
				sheAdslAtucPerfDataPrev1DayMoniSecs
					INTEGER,
				sheAdslAtucPerfDataPrev1DayLofs
					AdslPerfPrevDayCount,
				sheAdslAtucPerfDataPrev1DayLoss
					AdslPerfPrevDayCount,
				sheAdslAtucPerfDataPrev1DayLols
					AdslPerfPrevDayCount,
				sheAdslAtucPerfDataPrev1DayLprs
					AdslPerfPrevDayCount,
				sheAdslAtucPerfDataPrev1DayESs
					AdslPerfPrevDayCount,
				sheAdslAtucPerfDataPrev1DayInits
					AdslPerfPrevDayCount,
				sheAdslAtucPerfDataPrev1DayFastR
					Gauge32,
				sheAdslAtucPerfDataPrev1DayFailedFastR
					Gauge32,
				sheAdslAtucPerfDataPrev1DaySesL
					Gauge32,
				sheAdslAtucPerfDataPrev1DayUasL
					Gauge32
			 }

--       Event Counters
-- 
-- Also see adslAtucIntervalTable for 15 minute interval
-- elapsed counters.
-- 
-- 1.3.6.1.4.1.231.7.1.2.2.1.6.1.1.12.1.1
		sheAdslAtucPerfDataLofs OBJECT-TYPE
			SYNTAX Counter32
			MAX-ACCESS read-only
			STATUS current
			DESCRIPTION
				"Count of the number of Loss of Framing failures since
				agent reset."
			::= { sheAdslAtucPerfDataEntry 1 }

		
--   1.3.6.1.4.1.231.7.1.2.2.1.6.1.1.12.1.2
		sheAdslAtucPerfDataLoss OBJECT-TYPE
			SYNTAX Counter32
			MAX-ACCESS read-only
			STATUS current
			DESCRIPTION
				"Count of the number of Loss of Signal failures since
				agent reset."
			::= { sheAdslAtucPerfDataEntry 2 }

		
--   1.3.6.1.4.1.231.7.1.2.2.1.6.1.1.12.1.3
		sheAdslAtucPerfDataLols OBJECT-TYPE
			SYNTAX Counter32
			MAX-ACCESS read-only
			STATUS current
			DESCRIPTION
				"Count of the number of Loss of Link failures since
				agent reset."
			::= { sheAdslAtucPerfDataEntry 3 }

		
--   1.3.6.1.4.1.231.7.1.2.2.1.6.1.1.12.1.4
		sheAdslAtucPerfDataLprs OBJECT-TYPE
			SYNTAX Counter32
			MAX-ACCESS read-only
			STATUS current
			DESCRIPTION
				"Count of the number of Loss of Power failures since
				agent reset."
			::= { sheAdslAtucPerfDataEntry 4 }

		
--   1.3.6.1.4.1.231.7.1.2.2.1.6.1.1.12.1.5
		sheAdslAtucPerfDataESs OBJECT-TYPE
			SYNTAX Counter32
			MAX-ACCESS read-only
			STATUS current
			DESCRIPTION
				"Count of the number of Errored Seconds since agent
				reset.  The errored second parameter is a count of
				one-second intervals containing one or more crc
				anomalies, or one or more los or sef defects."
			::= { sheAdslAtucPerfDataEntry 5 }

		
--   1.3.6.1.4.1.231.7.1.2.2.1.6.1.1.12.1.6
		sheAdslAtucPerfDataInits OBJECT-TYPE
			SYNTAX Counter32
			MAX-ACCESS read-only
			STATUS current
			DESCRIPTION
				"Count of the line initialization attempts since
				agent reset. Includes both successful and failed
				attempts."
			::= { sheAdslAtucPerfDataEntry 6 }

		
--   1.3.6.1.4.1.231.7.1.2.2.1.6.1.1.12.1.7
		sheAdslAtucPerfDataStatFastR OBJECT-TYPE
			SYNTAX Gauge32
			MAX-ACCESS read-only
			STATUS current
			DESCRIPTION
				"The value of this object indicates the count of fast retrains."
			REFERENCE
				"ITU G.997.1 Section 7.4.15.1"
			::= { sheAdslAtucPerfDataEntry 7 }

		
--   1.3.6.1.4.1.231.7.1.2.2.1.6.1.1.12.1.8
		sheAdslAtucPerfDataStatFailedFastR OBJECT-TYPE
			SYNTAX Gauge32
			MAX-ACCESS read-only
			STATUS current
			DESCRIPTION
				"The value of this object indicates the count of failed fast retrains."
			REFERENCE
				"ITU G.997.1 Section 7.4.15.2"
			::= { sheAdslAtucPerfDataEntry 8 }

		
--   1.3.6.1.4.1.231.7.1.2.2.1.6.1.1.12.1.9
		sheAdslAtucPerfDataStatSesL OBJECT-TYPE
			SYNTAX Gauge32
			MAX-ACCESS read-only
			STATUS current
			DESCRIPTION
				"The value of this object indicates the count of severely errored second line."
			REFERENCE
				" ITU G.997.1 Section 7.2.1.1.7"
			::= { sheAdslAtucPerfDataEntry 9 }

		
--   1.3.6.1.4.1.231.7.1.2.2.1.6.1.1.12.1.10
		sheAdslAtucPerfDataStatUasL OBJECT-TYPE
			SYNTAX Gauge32
			MAX-ACCESS read-only
			STATUS current
			DESCRIPTION
				"The value of this object indicates the count of unavailable errored seconds."
			REFERENCE
				" ITU G.997.1 Section 7.2.1.1.9"
			::= { sheAdslAtucPerfDataEntry 10 }

		
--       general 15 min interval information
-- 
-- 1.3.6.1.4.1.231.7.1.2.2.1.6.1.1.12.1.11
		sheAdslAtucPerfDataValidIntervals OBJECT-TYPE
			SYNTAX INTEGER (0..96)
			MAX-ACCESS read-only
			STATUS current
			DESCRIPTION
				"The number of previous 15-minute intervals in the
				interval table for which data was collected.  Given
				that <n> is the maximum # of intervals supported.
				The value will be <n> unless the measurement was
				(re-)started within the last (<n>*15) minutes, in which
				case the value will be the number of complete 15
				minute intervals for which the agent has at least
				some data. In certain cases (e.g., in the case
				where the agent is a proxy) it is possible that some
				intervals are unavailable.  In this case, this
				interval is the maximum interval number for
				which data is available."
			::= { sheAdslAtucPerfDataEntry 11 }

		
--   1.3.6.1.4.1.231.7.1.2.2.1.6.1.1.12.1.12
		sheAdslAtucPerfDataInvalidIntervals OBJECT-TYPE
			SYNTAX INTEGER (0..96)
			MAX-ACCESS read-only
			STATUS current
			DESCRIPTION
				"The number of intervals in the range from
				0 to the value of adslAtucPerfValidIntervals
				for which no data is available. This object
				will typically be zero except in cases where
				the data for some intervals are not available
				(e.g., in proxy situations)."
			::= { sheAdslAtucPerfDataEntry 12 }

		
--       15 min current performance group
-- 
-- 1.3.6.1.4.1.231.7.1.2.2.1.6.1.1.12.1.13
		sheAdslAtucPerfDataCurr15MinTimeElapsed OBJECT-TYPE
			SYNTAX AdslPerfTimeElapsed (0..899)
			UNITS "seconds"
			MAX-ACCESS read-only
			STATUS current
			DESCRIPTION
				"Total elapsed seconds in this interval."
			::= { sheAdslAtucPerfDataEntry 13 }

		
--   1.3.6.1.4.1.231.7.1.2.2.1.6.1.1.12.1.14
		sheAdslAtucPerfDataCurr15MinLofs OBJECT-TYPE
			SYNTAX PerfCurrentCount
			UNITS "seconds"
			MAX-ACCESS read-only
			STATUS current
			DESCRIPTION
				"Count of seconds in the current 15 minute interval
				when there was Loss of Framing."
			::= { sheAdslAtucPerfDataEntry 14 }

		
--   1.3.6.1.4.1.231.7.1.2.2.1.6.1.1.12.1.15
		sheAdslAtucPerfDataCurr15MinLoss OBJECT-TYPE
			SYNTAX PerfCurrentCount
			UNITS "seconds"
			MAX-ACCESS read-only
			STATUS current
			DESCRIPTION
				"Count of seconds in the current 15 minute interval
				when there was Loss of Signal."
			::= { sheAdslAtucPerfDataEntry 15 }

		
--   1.3.6.1.4.1.231.7.1.2.2.1.6.1.1.12.1.16
		sheAdslAtucPerfDataCurr15MinLols OBJECT-TYPE
			SYNTAX PerfCurrentCount
			UNITS "seconds"
			MAX-ACCESS read-only
			STATUS current
			DESCRIPTION
				"Count of seconds in the current 15 minute interval
				when there was Loss of Link."
			::= { sheAdslAtucPerfDataEntry 16 }

		
--   1.3.6.1.4.1.231.7.1.2.2.1.6.1.1.12.1.17
		sheAdslAtucPerfDataCurr15MinLprs OBJECT-TYPE
			SYNTAX PerfCurrentCount
			UNITS "seconds"
			MAX-ACCESS read-only
			STATUS current
			DESCRIPTION
				"Count of seconds in the current 15 minute interval
				when there was Loss of Power."
			::= { sheAdslAtucPerfDataEntry 17 }

		
--   1.3.6.1.4.1.231.7.1.2.2.1.6.1.1.12.1.18
		sheAdslAtucPerfDataCurr15MinESs OBJECT-TYPE
			SYNTAX PerfCurrentCount
			UNITS "seconds"
			MAX-ACCESS read-only
			STATUS current
			DESCRIPTION
				"Count of Errored Seconds in the current 15 minute
				interval.  The errored second parameter is a count of
				one-second intervals containing one or more crc
				anomalies, or one or more los or sef defects."
			::= { sheAdslAtucPerfDataEntry 18 }

		
--   1.3.6.1.4.1.231.7.1.2.2.1.6.1.1.12.1.19
		sheAdslAtucPerfDataCurr15MinInits OBJECT-TYPE
			SYNTAX PerfCurrentCount
			MAX-ACCESS read-only
			STATUS current
			DESCRIPTION
				"Count of the line initialization attempts in the
				current 15 minute interval. Includes both successful
				and failed attempts."
			::= { sheAdslAtucPerfDataEntry 19 }

		
--   1.3.6.1.4.1.231.7.1.2.2.1.6.1.1.12.1.20
		sheAdslAtucPerfDataCurr15MinFastR OBJECT-TYPE
			SYNTAX Gauge32
			MAX-ACCESS read-only
			STATUS current
			DESCRIPTION
				"Count of seconds in the current 15 minute interval when there was fast retrains. REFERENCE ITU G.997.1 Section 7.4.15.1"
			::= { sheAdslAtucPerfDataEntry 20 }

		
--   1.3.6.1.4.1.231.7.1.2.2.1.6.1.1.12.1.21
		sheAdslAtucPerfDataCurr15MinFailedFastR OBJECT-TYPE
			SYNTAX Gauge32
			MAX-ACCESS read-only
			STATUS current
			DESCRIPTION
				"Count of seconds in the current 15 minute interval when there was failed fast retrains. REFERENCE ITU G.997.1 Section 7.4.15.2"
			::= { sheAdslAtucPerfDataEntry 21 }

		
--   1.3.6.1.4.1.231.7.1.2.2.1.6.1.1.12.1.22
		sheAdslAtucPerfDataCurr15MinSesL OBJECT-TYPE
			SYNTAX Gauge32
			MAX-ACCESS read-only
			STATUS current
			DESCRIPTION
				"Count of seconds in the current 15 minute interval when there was severely errored seconds. REFERENCE ITU G.997.1 Section 7.2.1.1.7"
			::= { sheAdslAtucPerfDataEntry 22 }

		
--   1.3.6.1.4.1.231.7.1.2.2.1.6.1.1.12.1.23
		sheAdslAtucPerfDataCurr15MinUasL OBJECT-TYPE
			SYNTAX Gauge32
			MAX-ACCESS read-only
			STATUS current
			DESCRIPTION
				"Count of seconds in the current 15 minute interval when there was count for unavailable errored seconds. REFERENCE ITU G.997.1 Section 7.2.1.1.9"
			::= { sheAdslAtucPerfDataEntry 23 }

		
--       1-day current and previous performance group
-- 
-- 1.3.6.1.4.1.231.7.1.2.2.1.6.1.1.12.1.24
		sheAdslAtucPerfDataCurr1DayTimeElapsed OBJECT-TYPE
			SYNTAX AdslPerfTimeElapsed (0..86399)
			UNITS "seconds"
			MAX-ACCESS read-only
			STATUS current
			DESCRIPTION
				"Number of seconds that have elapsed since the
				beginning of the current 1-day interval."
			::= { sheAdslAtucPerfDataEntry 24 }

		
--   1.3.6.1.4.1.231.7.1.2.2.1.6.1.1.12.1.25
		sheAdslAtucPerfDataCurr1DayLofs OBJECT-TYPE
			SYNTAX AdslPerfCurrDayCount
			UNITS "seconds"
			MAX-ACCESS read-only
			STATUS current
			DESCRIPTION
				"Count of the number of seconds when there was Loss of
				Framing during the current day as measured by
				adslAtucPerfCurr1DayTimeElapsed."
			::= { sheAdslAtucPerfDataEntry 25 }

		
--   1.3.6.1.4.1.231.7.1.2.2.1.6.1.1.12.1.26
		sheAdslAtucPerfDataCurr1DayLoss OBJECT-TYPE
			SYNTAX AdslPerfCurrDayCount
			UNITS "seconds"
			MAX-ACCESS read-only
			STATUS current
			DESCRIPTION
				"Count of the number of seconds when there was Loss of
				Signal during the current day as measured by
				adslAtucPerfCurr1DayTimeElapsed."
			::= { sheAdslAtucPerfDataEntry 26 }

		
--   1.3.6.1.4.1.231.7.1.2.2.1.6.1.1.12.1.27
		sheAdslAtucPerfDataCurr1DayLols OBJECT-TYPE
			SYNTAX AdslPerfCurrDayCount
			UNITS "seconds"
			MAX-ACCESS read-only
			STATUS current
			DESCRIPTION
				"Count of the number of seconds when there was Loss of
				Link during the current day as measured by
				adslAtucPerfCurr1DayTimeElapsed."
			::= { sheAdslAtucPerfDataEntry 27 }

		
--   1.3.6.1.4.1.231.7.1.2.2.1.6.1.1.12.1.28
		sheAdslAtucPerfDataCurr1DayLprs OBJECT-TYPE
			SYNTAX AdslPerfCurrDayCount
			UNITS "seconds"
			MAX-ACCESS read-only
			STATUS current
			DESCRIPTION
				"Count of the number of seconds when there was Loss of
				Power during the current day as measured by
				adslAtucPerfCurr1DayTimeElapsed."
			::= { sheAdslAtucPerfDataEntry 28 }

		
--   1.3.6.1.4.1.231.7.1.2.2.1.6.1.1.12.1.29
		sheAdslAtucPerfDataCurr1DayESs OBJECT-TYPE
			SYNTAX AdslPerfCurrDayCount
			UNITS "seconds"
			MAX-ACCESS read-only
			STATUS current
			DESCRIPTION
				"Count of Errored Seconds during the current day as
				measured by adslAtucPerfCurr1DayTimeElapsed.
				The errored second parameter is a count of
				one-second intervals containing one or more crc
				anomalies, or one or more los or sef defects."
			::= { sheAdslAtucPerfDataEntry 29 }

		
--   1.3.6.1.4.1.231.7.1.2.2.1.6.1.1.12.1.30
		sheAdslAtucPerfDataCurr1DayInits OBJECT-TYPE
			SYNTAX AdslPerfCurrDayCount
			MAX-ACCESS read-only
			STATUS current
			DESCRIPTION
				"Count of the line initialization attempts in the
				day as measured by adslAtucPerfCurr1DayTimeElapsed.
				Includes both successful and failed attempts."
			::= { sheAdslAtucPerfDataEntry 30 }

		
--   1.3.6.1.4.1.231.7.1.2.2.1.6.1.1.12.1.31
		sheAdslAtucPerfDataCurr1DayFastR OBJECT-TYPE
			SYNTAX Gauge32
			MAX-ACCESS read-only
			STATUS current
			DESCRIPTION
				"Count of the number of seconds when there was fast retrains during the current day as measured by adslAtucPerfCurr1Day TimeElapsed. REFERENCE ITU G.997.1 Section 7.4.15.1"
			::= { sheAdslAtucPerfDataEntry 31 }

		
--   1.3.6.1.4.1.231.7.1.2.2.1.6.1.1.12.1.32
		sheAdslAtucPerfDataCurr1DayFailedFastR OBJECT-TYPE
			SYNTAX Gauge32
			MAX-ACCESS read-only
			STATUS current
			DESCRIPTION
				"Count of the number of seconds when there was failed fast retrains during the current day as measured by adslAtucPerfCurr1Day TimeElapsed.REFERENCE ITU G.997.1 Section 7.4.15.2"
			::= { sheAdslAtucPerfDataEntry 32 }

		
--   1.3.6.1.4.1.231.7.1.2.2.1.6.1.1.12.1.33
		sheAdslAtucPerfDataCurr1DaySesL OBJECT-TYPE
			SYNTAX Gauge32
			MAX-ACCESS read-only
			STATUS current
			DESCRIPTION
				"Count of the number of seconds when there was Severely Errored Seconds during the current day as measured by adslAtucPerfCurr1DayTimeElapsed. REFERENCE ITU G.997.1 Section 7.2.1.1.7"
			::= { sheAdslAtucPerfDataEntry 33 }

		
--   1.3.6.1.4.1.231.7.1.2.2.1.6.1.1.12.1.34
		sheAdslAtucPerfDataCurr1DayUasL OBJECT-TYPE
			SYNTAX Gauge32
			MAX-ACCESS read-only
			STATUS current
			DESCRIPTION
				"Count of the number of seconds when there was Unavailable Errored Seconds during the current day as measured by adslAtucPerfCurr1DayTimeElapsed. REFERENCE ITU G.997.1 Section 7.2.1.1.9"
			::= { sheAdslAtucPerfDataEntry 34 }

		
--   1.3.6.1.4.1.231.7.1.2.2.1.6.1.1.12.1.35
		sheAdslAtucPerfDataPrev1DayTimeElapsed OBJECT-TYPE
			SYNTAX Gauge32
			MAX-ACCESS read-only
			STATUS current
			DESCRIPTION
				"Total elapsed seconds in this interval in seconds."
			::= { sheAdslAtucPerfDataEntry 35 }

		
--   1.3.6.1.4.1.231.7.1.2.2.1.6.1.1.12.1.36
		sheAdslAtucPerfDataPrev1DayMoniSecs OBJECT-TYPE
			SYNTAX INTEGER (0..86400)
			UNITS "seconds"
			MAX-ACCESS read-only
			STATUS current
			DESCRIPTION
				"The amount of time in the previous 1-day interval
				over which the performance monitoring information
				is actually counted. This value will be the same as
				the interval duration except in a situation where
				performance monitoring data could not be collected
				for any reason."
			::= { sheAdslAtucPerfDataEntry 36 }

		
--   1.3.6.1.4.1.231.7.1.2.2.1.6.1.1.12.1.37
		sheAdslAtucPerfDataPrev1DayLofs OBJECT-TYPE
			SYNTAX AdslPerfPrevDayCount
			UNITS "seconds"
			MAX-ACCESS read-only
			STATUS current
			DESCRIPTION
				"Count of seconds in the interval when there was
				Loss of Framing within the most recent previous
				1-day period."
			::= { sheAdslAtucPerfDataEntry 37 }

		
--   1.3.6.1.4.1.231.7.1.2.2.1.6.1.1.12.1.38
		sheAdslAtucPerfDataPrev1DayLoss OBJECT-TYPE
			SYNTAX AdslPerfPrevDayCount
			UNITS "seconds"
			MAX-ACCESS read-only
			STATUS current
			DESCRIPTION
				"Count of seconds in the interval when there was
				Loss of Signal within the most recent previous
				1-day period."
			::= { sheAdslAtucPerfDataEntry 38 }

		
--   1.3.6.1.4.1.231.7.1.2.2.1.6.1.1.12.1.39
		sheAdslAtucPerfDataPrev1DayLols OBJECT-TYPE
			SYNTAX AdslPerfPrevDayCount
			UNITS "seconds"
			MAX-ACCESS read-only
			STATUS current
			DESCRIPTION
				"Count of seconds in the interval when there was
				Loss of Link within the most recent previous
				1-day period."
			::= { sheAdslAtucPerfDataEntry 39 }

		
--   1.3.6.1.4.1.231.7.1.2.2.1.6.1.1.12.1.40
		sheAdslAtucPerfDataPrev1DayLprs OBJECT-TYPE
			SYNTAX AdslPerfPrevDayCount
			UNITS "seconds"
			MAX-ACCESS read-only
			STATUS current
			DESCRIPTION
				"Count of seconds in the interval when there was
				Loss of Power within the most recent previous
				1-day period."
			::= { sheAdslAtucPerfDataEntry 40 }

		
--   1.3.6.1.4.1.231.7.1.2.2.1.6.1.1.12.1.41
		sheAdslAtucPerfDataPrev1DayESs OBJECT-TYPE
			SYNTAX AdslPerfPrevDayCount
			UNITS "seconds"
			MAX-ACCESS read-only
			STATUS current
			DESCRIPTION
				"Count of Errored Seconds within the most recent
				previous 1-day period. The errored second parameter is
				a count of one-second intervals containing one or more
				crc anomalies, or one or more los or sef defects."
			::= { sheAdslAtucPerfDataEntry 41 }

		
--   1.3.6.1.4.1.231.7.1.2.2.1.6.1.1.12.1.42
		sheAdslAtucPerfDataPrev1DayInits OBJECT-TYPE
			SYNTAX AdslPerfPrevDayCount
			MAX-ACCESS read-only
			STATUS current
			DESCRIPTION
				"Count of the line initialization attempts in the most
				recent previous 1-day period. Includes both successful
				and failed attempts."
			::= { sheAdslAtucPerfDataEntry 42 }

		
--   1.3.6.1.4.1.231.7.1.2.2.1.6.1.1.12.1.43
		sheAdslAtucPerfDataPrev1DayFastR OBJECT-TYPE
			SYNTAX Gauge32
			MAX-ACCESS read-only
			STATUS current
			DESCRIPTION
				"Count of seconds in the interval when there was fast retrains within the most recent previous 1 day period. REFERENCE ITU G.997.1 Section 7.4.15.1"
			::= { sheAdslAtucPerfDataEntry 43 }

		
--   1.3.6.1.4.1.231.7.1.2.2.1.6.1.1.12.1.44
		sheAdslAtucPerfDataPrev1DayFailedFastR OBJECT-TYPE
			SYNTAX Gauge32
			MAX-ACCESS read-only
			STATUS current
			DESCRIPTION
				"Count of seconds in the interval when there was failed fast retrains within the most recent previous 1 day period.  REFERENCE ITU G.997.1 Section 7.4.15.2"
			::= { sheAdslAtucPerfDataEntry 44 }

		
--   1.3.6.1.4.1.231.7.1.2.2.1.6.1.1.12.1.45
		sheAdslAtucPerfDataPrev1DaySesL OBJECT-TYPE
			SYNTAX Gauge32
			MAX-ACCESS read-only
			STATUS current
			DESCRIPTION
				"Count of seconds in the interval when there was severely errored seconds within the most recent previous 1 day period. REFERENCE ITU G.997.1 Section 7.2.1.1.7"
			::= { sheAdslAtucPerfDataEntry 45 }

		
--   1.3.6.1.4.1.231.7.1.2.2.1.6.1.1.12.1.46
		sheAdslAtucPerfDataPrev1DayUasL OBJECT-TYPE
			SYNTAX Gauge32
			MAX-ACCESS read-only
			STATUS current
			DESCRIPTION
				"Count of seconds in the interval when there was unavailable errored seconds within the most recent previous 1 day period. REFERENCE ITU G.997.1 Section 7.2.1.1.9"
			::= { sheAdslAtucPerfDataEntry 46 }

		
--   1.3.6.1.4.1.231.7.1.2.2.1.6.1.1.13
		sheAdslAtucIntervalTable OBJECT-TYPE
			SYNTAX SEQUENCE OF SheAdslAtucIntervalEntry
			MAX-ACCESS not-accessible
			STATUS current
			DESCRIPTION
				"This table provides one row for each ATUC
				performance data collection interval.
				ADSL physical interfaces are
				those ifEntries where ifType is equal to adsl(94)."
			::= { sheAdslLineMIB 13 }

		
--   1.3.6.1.4.1.231.7.1.2.2.1.6.1.1.13.1
		sheAdslAtucIntervalEntry OBJECT-TYPE
			SYNTAX SheAdslAtucIntervalEntry
			MAX-ACCESS not-accessible
			STATUS current
			DESCRIPTION
				"An entry in the adslAtucIntervalTable."
			INDEX { ifIndex, sheAdslAtucIntervalNumber }
			::= { sheAdslAtucIntervalTable 1 }

		
		SheAdslAtucIntervalEntry ::=
			SEQUENCE { 
				sheAdslAtucIntervalNumber
					INTEGER,
				sheAdslAtucIntervalValidData
					TruthValue,
				sheAdslAtucIntervalEndTime
					Unsigned32,
				sheAdslAtucIntervalLofs
					PerfIntervalCount,
				sheAdslAtucIntervalLoss
					PerfIntervalCount,
				sheAdslAtucIntervalLols
					PerfIntervalCount,
				sheAdslAtucIntervalLprs
					PerfIntervalCount,
				sheAdslAtucIntervalESs
					PerfIntervalCount,
				sheAdslAtucIntervalInits
					PerfIntervalCount,
				sheAdslAtucIntervalFastR
					Gauge32,
				sheAdslAtucIntervalFailedFastR
					Gauge32,
				sheAdslAtucIntervalSesL
					Gauge32,
				sheAdslAtucIntervalUasL
					Gauge32
			 }

--   1.3.6.1.4.1.231.7.1.2.2.1.6.1.1.13.1.1
		sheAdslAtucIntervalNumber OBJECT-TYPE
			SYNTAX INTEGER (1..96)
			MAX-ACCESS read-only
			STATUS current
			DESCRIPTION
				"Performance Data Interval number 1 is the
				the most recent previous interval; interval
				96 is 24 hours ago.  Intervals 2..96 are
				optional."
			::= { sheAdslAtucIntervalEntry 1 }

		
--   1.3.6.1.4.1.231.7.1.2.2.1.6.1.1.13.1.2
		sheAdslAtucIntervalValidData OBJECT-TYPE
			SYNTAX TruthValue
			MAX-ACCESS read-only
			STATUS current
			DESCRIPTION
				"This variable indicates if the data for this
				interval is valid."
			::= { sheAdslAtucIntervalEntry 2 }

		
--   1.3.6.1.4.1.231.7.1.2.2.1.6.1.1.13.1.3
		sheAdslAtucIntervalEndTime OBJECT-TYPE
			SYNTAX Unsigned32
			MAX-ACCESS read-only
			STATUS current
			DESCRIPTION
				"This variable indicates the time of storing this interval."
			::= { sheAdslAtucIntervalEntry 3 }

		
--   1.3.6.1.4.1.231.7.1.2.2.1.6.1.1.13.1.4
		sheAdslAtucIntervalLofs OBJECT-TYPE
			SYNTAX PerfIntervalCount
			UNITS "seconds"
			MAX-ACCESS read-only
			STATUS current
			DESCRIPTION
				"Count of seconds in the interval when there was Loss
				of Framing."
			::= { sheAdslAtucIntervalEntry 4 }

		
--   1.3.6.1.4.1.231.7.1.2.2.1.6.1.1.13.1.5
		sheAdslAtucIntervalLoss OBJECT-TYPE
			SYNTAX PerfIntervalCount
			UNITS "seconds"
			MAX-ACCESS read-only
			STATUS current
			DESCRIPTION
				"Count of seconds in the interval when there was Loss
				of Signal."
			::= { sheAdslAtucIntervalEntry 5 }

		
--   1.3.6.1.4.1.231.7.1.2.2.1.6.1.1.13.1.6
		sheAdslAtucIntervalLols OBJECT-TYPE
			SYNTAX PerfIntervalCount
			UNITS "seconds"
			MAX-ACCESS read-only
			STATUS current
			DESCRIPTION
				"Count of seconds in the interval when there was Loss
				of Link."
			::= { sheAdslAtucIntervalEntry 6 }

		
--   1.3.6.1.4.1.231.7.1.2.2.1.6.1.1.13.1.7
		sheAdslAtucIntervalLprs OBJECT-TYPE
			SYNTAX PerfIntervalCount
			UNITS "seconds"
			MAX-ACCESS read-only
			STATUS current
			DESCRIPTION
				"Count of seconds in the interval when there was Loss
				of Power."
			::= { sheAdslAtucIntervalEntry 7 }

		
--   1.3.6.1.4.1.231.7.1.2.2.1.6.1.1.13.1.8
		sheAdslAtucIntervalESs OBJECT-TYPE
			SYNTAX PerfIntervalCount
			UNITS "seconds"
			MAX-ACCESS read-only
			STATUS current
			DESCRIPTION
				"Count of Errored Seconds in the interval.
				The errored second parameter is a count of
				one-second intervals containing one or more crc
				anomalies, or one or more los or sef defects."
			::= { sheAdslAtucIntervalEntry 8 }

		
--   1.3.6.1.4.1.231.7.1.2.2.1.6.1.1.13.1.9
		sheAdslAtucIntervalInits OBJECT-TYPE
			SYNTAX PerfIntervalCount
			MAX-ACCESS read-only
			STATUS current
			DESCRIPTION
				"Count of the line initialization attempts
				during the interval. Includes both successful
				and failed attempts."
			::= { sheAdslAtucIntervalEntry 9 }

		
--   1.3.6.1.4.1.231.7.1.2.2.1.6.1.1.13.1.10
		sheAdslAtucIntervalFastR OBJECT-TYPE
			SYNTAX Gauge32
			MAX-ACCESS read-only
			STATUS current
			DESCRIPTION
				"This variable indicates Count of seconds in the interval when there was Fast Retrains."
			::= { sheAdslAtucIntervalEntry 10 }

		
--   1.3.6.1.4.1.231.7.1.2.2.1.6.1.1.13.1.11
		sheAdslAtucIntervalFailedFastR OBJECT-TYPE
			SYNTAX Gauge32
			MAX-ACCESS read-only
			STATUS current
			DESCRIPTION
				"This variable indicates Count of seconds in the interval when there was Failed Fast Retrains."
			::= { sheAdslAtucIntervalEntry 11 }

		
--   1.3.6.1.4.1.231.7.1.2.2.1.6.1.1.13.1.12
		sheAdslAtucIntervalSesL OBJECT-TYPE
			SYNTAX Gauge32
			MAX-ACCESS read-only
			STATUS current
			DESCRIPTION
				"This variable indicates Count of seconds in the interval when there was severely errored seconds."
			::= { sheAdslAtucIntervalEntry 12 }

		
--   1.3.6.1.4.1.231.7.1.2.2.1.6.1.1.13.1.13
		sheAdslAtucIntervalUasL OBJECT-TYPE
			SYNTAX Gauge32
			MAX-ACCESS read-only
			STATUS current
			DESCRIPTION
				"This variable indicates Count of seconds in the interval when there was unavailable errored seconds."
			::= { sheAdslAtucIntervalEntry 13 }

		
--  performance group
-- 
-- Note: block is intended to be the length of the channel
--       data-block on which the CRC operates. See
--       adslAtucChanCrcBlockLength for more information.
--  1.3.6.1.4.1.231.7.1.2.2.1.6.1.1.14
		sheAdslAtucChanPerfDataTable OBJECT-TYPE
			SYNTAX SEQUENCE OF SheAdslAtucChanPerfDataEntry
			MAX-ACCESS not-accessible
			STATUS current
			DESCRIPTION
				"This table provides one row for each ATUC channel."
			::= { sheAdslLineMIB 14 }

		
--   1.3.6.1.4.1.231.7.1.2.2.1.6.1.1.14.1
		sheAdslAtucChanPerfDataEntry OBJECT-TYPE
			SYNTAX SheAdslAtucChanPerfDataEntry
			MAX-ACCESS not-accessible
			STATUS current
			DESCRIPTION
				"An entry in adslAtucChanPerfDataTable.
				This table is only supported by NE releases smaller then R2.5 (NO dualLatency support)!!"
			INDEX { ifIndex }
			::= { sheAdslAtucChanPerfDataTable 1 }

		
		SheAdslAtucChanPerfDataEntry ::=
			SEQUENCE { 
				sheAdslAtucChanPerfDataTimeElapsed
					Gauge32,
				sheAdslAtucChanPerfDataReceivedBlks
					Counter32,
				sheAdslAtucChanPerfDataTransmittedBlks
					Counter32,
				sheAdslAtucChanPerfDataCorrectedBlks
					Counter32,
				sheAdslAtucChanPerfDataUncorrectBlks
					Counter32,
				sheAdslAtucChanPerfDataNcd
					Gauge32,
				sheAdslAtucChanPerfDataOcd
					Gauge32,
				sheAdslAtucChanPerfDataHec
					Gauge32,
				sheAdslAtucChanPerfDataValidIntervals
					INTEGER,
				sheAdslAtucChanPerfDataInvalidIntervals
					INTEGER,
				sheAdslAtucChanPerfDataCurr15MinTimeElapsed
					AdslPerfTimeElapsed,
				sheAdslAtucChanPerfDataCurr15MinReceivedBlks
					PerfCurrentCount,
				sheAdslAtucChanPerfDataCurr15MinTransmittedBlks
					PerfCurrentCount,
				sheAdslAtucChanPerfDataCurr15MinCorrectedBlks
					PerfCurrentCount,
				sheAdslAtucChanPerfDataCurr15MinUncorrectBlks
					PerfCurrentCount,
				sheAdslAtucChanPerfDataCurr15MinNcd
					Gauge32,
				sheAdslAtucChanPerfDataCurr15MinOcd
					Gauge32,
				sheAdslAtucChanPerfDataCurr15MinHec
					Gauge32,
				sheAdslAtucChanPerfDataCurr1DayTimeElapsed
					AdslPerfTimeElapsed,
				sheAdslAtucChanPerfDataCurr1DayReceivedBlks
					AdslPerfCurrDayCount,
				sheAdslAtucChanPerfDataCurr1DayTransmittedBlks
					AdslPerfCurrDayCount,
				sheAdslAtucChanPerfDataCurr1DayCorrectedBlks
					AdslPerfCurrDayCount,
				sheAdslAtucChanPerfDataCurr1DayUncorrectBlks
					AdslPerfCurrDayCount,
				sheAdslAtucChanPerfDataCurr1DayNcd
					Gauge32,
				sheAdslAtucChanPerfDataCurr1DayOcd
					Gauge32,
				sheAdslAtucChanPerfDataCurr1DayHec
					Gauge32,
				sheAdslAtucChanPerfDataPrev1DayMoniSecs
					INTEGER,
				sheAdslAtucChanPerfDataPrev1DayReceivedBlks
					AdslPerfPrevDayCount,
				sheAdslAtucChanPerfDataPrev1DayTransmittedBlks
					AdslPerfPrevDayCount,
				sheAdslAtucChanPerfDataPrev1DayCorrectedBlks
					AdslPerfPrevDayCount,
				sheAdslAtucChanPerfDataPrev1DayUncorrectBlks
					AdslPerfPrevDayCount,
				sheAdslAtucChanPerfDataPrev1DayNcd
					Gauge32,
				sheAdslAtucChanPerfDataPrev1DayOcd
					Gauge32,
				sheAdslAtucChanPerfDataPrev1DayHec
					Gauge32
			 }

--   1.3.6.1.4.1.231.7.1.2.2.1.6.1.1.14.1.1
		sheAdslAtucChanPerfDataTimeElapsed OBJECT-TYPE
			SYNTAX Gauge32
			MAX-ACCESS read-only
			STATUS current
			DESCRIPTION
				" Total elapsed seconds in this interval."
			::= { sheAdslAtucChanPerfDataEntry 1 }

		
--  1.3.6.1.4.1.231.7.1.2.2.1.6.1.1.14.1.2
		sheAdslAtucChanPerfDataReceivedBlks OBJECT-TYPE
			SYNTAX Counter32
			MAX-ACCESS read-only
			STATUS current
			DESCRIPTION
				"Count of all encoded blocks received on this channel
				since agent reset."
			::= { sheAdslAtucChanPerfDataEntry 2 }

		
--   1.3.6.1.4.1.231.7.1.2.2.1.6.1.1.14.1.3
		sheAdslAtucChanPerfDataTransmittedBlks OBJECT-TYPE
			SYNTAX Counter32
			MAX-ACCESS read-only
			STATUS current
			DESCRIPTION
				"Count of all encoded blocks transmitted on this
				channel since agent reset."
			::= { sheAdslAtucChanPerfDataEntry 3 }

		
--   1.3.6.1.4.1.231.7.1.2.2.1.6.1.1.14.1.4
		sheAdslAtucChanPerfDataCorrectedBlks OBJECT-TYPE
			SYNTAX Counter32
			MAX-ACCESS read-only
			STATUS current
			DESCRIPTION
				"Count of all blocks received with errors that were
				corrected since agent reset.  These blocks are passed
				on as good data."
			::= { sheAdslAtucChanPerfDataEntry 4 }

		
--   1.3.6.1.4.1.231.7.1.2.2.1.6.1.1.14.1.5
		sheAdslAtucChanPerfDataUncorrectBlks OBJECT-TYPE
			SYNTAX Counter32
			MAX-ACCESS read-only
			STATUS current
			DESCRIPTION
				"Count of all blocks received with uncorrectable
				errors since agent reset."
			::= { sheAdslAtucChanPerfDataEntry 5 }

		
--   1.3.6.1.4.1.231.7.1.2.2.1.6.1.1.14.1.6
		sheAdslAtucChanPerfDataNcd OBJECT-TYPE
			SYNTAX Gauge32
			MAX-ACCESS read-only
			STATUS current
			DESCRIPTION
				"Count of no cell delineation(ncd) on this channel."
			::= { sheAdslAtucChanPerfDataEntry 6 }

		
--   1.3.6.1.4.1.231.7.1.2.2.1.6.1.1.14.1.7
		sheAdslAtucChanPerfDataOcd OBJECT-TYPE
			SYNTAX Gauge32
			MAX-ACCESS read-only
			STATUS current
			DESCRIPTION
				"Count of out of cell delineation (ocd) on this channel."
			::= { sheAdslAtucChanPerfDataEntry 7 }

		
--   1.3.6.1.4.1.231.7.1.2.2.1.6.1.1.14.1.8
		sheAdslAtucChanPerfDataHec OBJECT-TYPE
			SYNTAX Gauge32
			MAX-ACCESS read-only
			STATUS current
			DESCRIPTION
				"Header error check counter(hec) on this channel."
			::= { sheAdslAtucChanPerfDataEntry 8 }

		
--       general 15 min interval information
-- 
-- 1.3.6.1.4.1.231.7.1.2.2.1.6.1.1.14.1.9
		sheAdslAtucChanPerfDataValidIntervals OBJECT-TYPE
			SYNTAX INTEGER (0..96)
			MAX-ACCESS read-only
			STATUS current
			DESCRIPTION
				"The number of previous 15-minute intervals in the
				interval table for which data was collected.  Given
				that <n> is the maximum # of intervals supported.
				The value will be <n> unless the measurement was
				(re-)started within the last (<n>*15) minutes, in which
				case the value will be the number of complete 15
				minute intervals for which the agent has at least
				some data. In certain cases (e.g., in the case
				where the agent is a proxy) it is possible that some
				intervals are unavailable.  In this case, this
				interval is the maximum interval number for
				which data is available."
			::= { sheAdslAtucChanPerfDataEntry 9 }

		
--   1.3.6.1.4.1.231.7.1.2.2.1.6.1.1.14.1.10
		sheAdslAtucChanPerfDataInvalidIntervals OBJECT-TYPE
			SYNTAX INTEGER (0..96)
			MAX-ACCESS read-only
			STATUS current
			DESCRIPTION
				"The number of intervals in the range from
				0 to the value of adslAtucChanPerfValidIntervals
				for which no data is available. This object
				will typically be zero except in cases where
				the data for some intervals are not available
				(e.g., in proxy situations)."
			::= { sheAdslAtucChanPerfDataEntry 10 }

		
--       15 min current performance group
-- 
-- 
-- 1.3.6.1.4.1.231.7.1.2.2.1.6.1.1.14.1.11
		sheAdslAtucChanPerfDataCurr15MinTimeElapsed OBJECT-TYPE
			SYNTAX AdslPerfTimeElapsed (0..899)
			UNITS "seconds"
			MAX-ACCESS read-only
			STATUS current
			DESCRIPTION
				"Total elapsed seconds in this interval."
			::= { sheAdslAtucChanPerfDataEntry 11 }

		
--   1.3.6.1.4.1.231.7.1.2.2.1.6.1.1.14.1.12
		sheAdslAtucChanPerfDataCurr15MinReceivedBlks OBJECT-TYPE
			SYNTAX PerfCurrentCount
			MAX-ACCESS read-only
			STATUS current
			DESCRIPTION
				"Count of all encoded blocks received on this channel
				within the current 15 minute interval."
			::= { sheAdslAtucChanPerfDataEntry 12 }

		
--   1.3.6.1.4.1.231.7.1.2.2.1.6.1.1.14.1.13
		sheAdslAtucChanPerfDataCurr15MinTransmittedBlks OBJECT-TYPE
			SYNTAX PerfCurrentCount
			MAX-ACCESS read-only
			STATUS current
			DESCRIPTION
				"Count of all encoded blocks transmitted on this
				channel within the current 15 minute interval."
			::= { sheAdslAtucChanPerfDataEntry 13 }

		
--   1.3.6.1.4.1.231.7.1.2.2.1.6.1.1.14.1.14
		sheAdslAtucChanPerfDataCurr15MinCorrectedBlks OBJECT-TYPE
			SYNTAX PerfCurrentCount
			MAX-ACCESS read-only
			STATUS current
			DESCRIPTION
				"Count of all blocks received with errors that were
				corrected on this channel within the current 15 minute
				interval."
			::= { sheAdslAtucChanPerfDataEntry 14 }

		
--   1.3.6.1.4.1.231.7.1.2.2.1.6.1.1.14.1.15
		sheAdslAtucChanPerfDataCurr15MinUncorrectBlks OBJECT-TYPE
			SYNTAX PerfCurrentCount
			MAX-ACCESS read-only
			STATUS current
			DESCRIPTION
				"Count of all blocks received with uncorrectable
				errors on this channel within the current 15 minute
				interval."
			::= { sheAdslAtucChanPerfDataEntry 15 }

		
--   1.3.6.1.4.1.231.7.1.2.2.1.6.1.1.14.1.16
		sheAdslAtucChanPerfDataCurr15MinNcd OBJECT-TYPE
			SYNTAX Gauge32
			MAX-ACCESS read-only
			STATUS current
			DESCRIPTION
				"Count of no cell delineation(ncd) on this channel within the current 15 minute time interval."
			::= { sheAdslAtucChanPerfDataEntry 16 }

		
--   1.3.6.1.4.1.231.7.1.2.2.1.6.1.1.14.1.17
		sheAdslAtucChanPerfDataCurr15MinOcd OBJECT-TYPE
			SYNTAX Gauge32
			MAX-ACCESS read-only
			STATUS current
			DESCRIPTION
				"Count of out of cell delineation (ocd) on this channel within the current 15 minute time interval."
			::= { sheAdslAtucChanPerfDataEntry 17 }

		
--   1.3.6.1.4.1.231.7.1.2.2.1.6.1.1.14.1.18
		sheAdslAtucChanPerfDataCurr15MinHec OBJECT-TYPE
			SYNTAX Gauge32
			MAX-ACCESS read-only
			STATUS current
			DESCRIPTION
				"Header error check counter(hec) on this channel within the current 15 minute time interval."
			::= { sheAdslAtucChanPerfDataEntry 18 }

		
--       1-day current and previous performance group
-- 
-- 1.3.6.1.4.1.231.7.1.2.2.1.6.1.1.14.1.19
		sheAdslAtucChanPerfDataCurr1DayTimeElapsed OBJECT-TYPE
			SYNTAX AdslPerfTimeElapsed (0..86399)
			UNITS "seconds"
			MAX-ACCESS read-only
			STATUS current
			DESCRIPTION
				"Number of seconds that have elapsed since the
				beginning of the current 1-day interval."
			::= { sheAdslAtucChanPerfDataEntry 19 }

		
--   1.3.6.1.4.1.231.7.1.2.2.1.6.1.1.14.1.20
		sheAdslAtucChanPerfDataCurr1DayReceivedBlks OBJECT-TYPE
			SYNTAX AdslPerfCurrDayCount
			MAX-ACCESS read-only
			STATUS current
			DESCRIPTION
				"Count of all encoded blocks received on this
				channel during the current day as measured by
				adslAtucChanPerfCurr1DayTimeElapsed."
			::= { sheAdslAtucChanPerfDataEntry 20 }

		
--   1.3.6.1.4.1.231.7.1.2.2.1.6.1.1.14.1.21
		sheAdslAtucChanPerfDataCurr1DayTransmittedBlks OBJECT-TYPE
			SYNTAX AdslPerfCurrDayCount
			MAX-ACCESS read-only
			STATUS current
			DESCRIPTION
				"Count of all encoded blocks transmitted on this
				channel during the current day as measured by
				adslAtucChanPerfCurr1DayTimeElapsed."
			::= { sheAdslAtucChanPerfDataEntry 21 }

		
--   1.3.6.1.4.1.231.7.1.2.2.1.6.1.1.14.1.22
		sheAdslAtucChanPerfDataCurr1DayCorrectedBlks OBJECT-TYPE
			SYNTAX AdslPerfCurrDayCount
			MAX-ACCESS read-only
			STATUS current
			DESCRIPTION
				"Count of all blocks received with errors that were
				corrected on this channel during the current day as
				measured by adslAtucChanPerfCurr1DayTimeElapsed."
			::= { sheAdslAtucChanPerfDataEntry 22 }

		
--   1.3.6.1.4.1.231.7.1.2.2.1.6.1.1.14.1.23
		sheAdslAtucChanPerfDataCurr1DayUncorrectBlks OBJECT-TYPE
			SYNTAX AdslPerfCurrDayCount
			MAX-ACCESS read-only
			STATUS current
			DESCRIPTION
				"Count of all blocks received with uncorrectable
				errors on this channel during the current day as
				measured by adslAtucChanPerfCurr1DayTimeElapsed."
			::= { sheAdslAtucChanPerfDataEntry 23 }

		
--   1.3.6.1.4.1.231.7.1.2.2.1.6.1.1.14.1.24
		sheAdslAtucChanPerfDataCurr1DayNcd OBJECT-TYPE
			SYNTAX Gauge32
			MAX-ACCESS read-only
			STATUS current
			DESCRIPTION
				"Count of no cell delineation (ncd) on this channel within the current 1 day time interval."
			::= { sheAdslAtucChanPerfDataEntry 24 }

		
--   1.3.6.1.4.1.231.7.1.2.2.1.6.1.1.14.1.25
		sheAdslAtucChanPerfDataCurr1DayOcd OBJECT-TYPE
			SYNTAX Gauge32
			MAX-ACCESS read-only
			STATUS current
			DESCRIPTION
				"Count of out of cell delineation (ocd) on this channel within the current 1 day time interval."
			::= { sheAdslAtucChanPerfDataEntry 25 }

		
--   1.3.6.1.4.1.231.7.1.2.2.1.6.1.1.14.1.26
		sheAdslAtucChanPerfDataCurr1DayHec OBJECT-TYPE
			SYNTAX Gauge32
			MAX-ACCESS read-only
			STATUS current
			DESCRIPTION
				"Header error check counter (hec) on this channel within the current 1 day time interval."
			::= { sheAdslAtucChanPerfDataEntry 26 }

		
--   1.3.6.1.4.1.231.7.1.2.2.1.6.1.1.14.1.27
		sheAdslAtucChanPerfDataPrev1DayMoniSecs OBJECT-TYPE
			SYNTAX INTEGER (0..86400)
			UNITS "seconds"
			MAX-ACCESS read-only
			STATUS current
			DESCRIPTION
				"The amount of time in the previous 1-day interval
				over which the performance monitoring information
				is actually counted. This value will be the same as
				the interval duration except in a situation where
				performance monitoring data could not be collected
				for any reason."
			::= { sheAdslAtucChanPerfDataEntry 27 }

		
--   1.3.6.1.4.1.231.7.1.2.2.1.6.1.1.14.1.28
		sheAdslAtucChanPerfDataPrev1DayReceivedBlks OBJECT-TYPE
			SYNTAX AdslPerfPrevDayCount
			MAX-ACCESS read-only
			STATUS current
			DESCRIPTION
				"Count of all encoded blocks received on this
				channel within the most recent previous 1-day
				period."
			::= { sheAdslAtucChanPerfDataEntry 28 }

		
--   1.3.6.1.4.1.231.7.1.2.2.1.6.1.1.14.1.29
		sheAdslAtucChanPerfDataPrev1DayTransmittedBlks OBJECT-TYPE
			SYNTAX AdslPerfPrevDayCount
			MAX-ACCESS read-only
			STATUS current
			DESCRIPTION
				"Count of all encoded blocks transmitted on this
				channel within the most recent previous 1-day
				period."
			::= { sheAdslAtucChanPerfDataEntry 29 }

		
--   1.3.6.1.4.1.231.7.1.2.2.1.6.1.1.14.1.30
		sheAdslAtucChanPerfDataPrev1DayCorrectedBlks OBJECT-TYPE
			SYNTAX AdslPerfPrevDayCount
			MAX-ACCESS read-only
			STATUS current
			DESCRIPTION
				"Count of all blocks received with errors that were
				corrected on this channel within the most recent
				previous 1-day period."
			::= { sheAdslAtucChanPerfDataEntry 30 }

		
--   1.3.6.1.4.1.231.7.1.2.2.1.6.1.1.14.1.31
		sheAdslAtucChanPerfDataPrev1DayUncorrectBlks OBJECT-TYPE
			SYNTAX AdslPerfPrevDayCount
			MAX-ACCESS read-only
			STATUS current
			DESCRIPTION
				"Count of all blocks received with uncorrectable
				errors on this channel within the most recent previous
				1-day period."
			::= { sheAdslAtucChanPerfDataEntry 31 }

		
--   1.3.6.1.4.1.231.7.1.2.2.1.6.1.1.14.1.32
		sheAdslAtucChanPerfDataPrev1DayNcd OBJECT-TYPE
			SYNTAX Gauge32
			MAX-ACCESS read-only
			STATUS current
			DESCRIPTION
				"Count of no cell delineation (ncd) on this channel within the most recent previous 1-day period."
			::= { sheAdslAtucChanPerfDataEntry 32 }

		
--   1.3.6.1.4.1.231.7.1.2.2.1.6.1.1.14.1.33
		sheAdslAtucChanPerfDataPrev1DayOcd OBJECT-TYPE
			SYNTAX Gauge32
			MAX-ACCESS read-only
			STATUS current
			DESCRIPTION
				"Count of out of cell delineation (ocd) on this channel within the most recent previous 1-day period."
			::= { sheAdslAtucChanPerfDataEntry 33 }

		
--   1.3.6.1.4.1.231.7.1.2.2.1.6.1.1.14.1.34
		sheAdslAtucChanPerfDataPrev1DayHec OBJECT-TYPE
			SYNTAX Gauge32
			MAX-ACCESS read-only
			STATUS current
			DESCRIPTION
				"Header error check counter(hec) on this channel within the most recent previous 1-day period."
			::= { sheAdslAtucChanPerfDataEntry 34 }

		
--   1.3.6.1.4.1.231.7.1.2.2.1.6.1.1.15
		sheAdslAtucChanIntervalTable OBJECT-TYPE
			SYNTAX SEQUENCE OF SheAdslAtucChanIntervalEntry
			MAX-ACCESS not-accessible
			STATUS current
			DESCRIPTION
				"This table provides one row for each ATUC channel's
				performance data collection interval."
			::= { sheAdslLineMIB 15 }

		
--   1.3.6.1.4.1.231.7.1.2.2.1.6.1.1.15.1
		sheAdslAtucChanIntervalEntry OBJECT-TYPE
			SYNTAX SheAdslAtucChanIntervalEntry
			MAX-ACCESS not-accessible
			STATUS current
			DESCRIPTION
				"An entry in the adslAtucIntervalTable.
				This table is only supported by NE releases smaller then R2.5 (NO dualLatency support)!!"
			INDEX { ifIndex, sheAdslAtucChanIntervalNumber }
			::= { sheAdslAtucChanIntervalTable 1 }

		
		SheAdslAtucChanIntervalEntry ::=
			SEQUENCE { 
				sheAdslAtucChanIntervalNumber
					INTEGER,
				sheAdslAtucChanIntervalValidData
					TruthValue,
				sheAdslAtucChanIntervalEndTime
					Unsigned32,
				sheAdslAtucChanIntervalReceivedBlks
					PerfIntervalCount,
				sheAdslAtucChanIntervalTransmittedBlks
					PerfIntervalCount,
				sheAdslAtucChanIntervalCorrectedBlks
					PerfIntervalCount,
				sheAdslAtucChanIntervalUncorrectBlks
					PerfIntervalCount,
				sheAdslAtucChanIntervalNcd
					Counter32,
				sheAdslAtucChanIntervalOcd
					Counter32,
				sheAdslAtucChanIntervalHec
					Counter32
			 }

--   1.3.6.1.4.1.231.7.1.2.2.1.6.1.1.15.1.1
		sheAdslAtucChanIntervalNumber OBJECT-TYPE
			SYNTAX INTEGER (1..96)
			MAX-ACCESS read-only
			STATUS current
			DESCRIPTION
				"Performance Data Interval number 1 is the
				the most recent previous interval; interval
				96 is 24 hours ago.  Intervals 2..96 are
				optional."
			::= { sheAdslAtucChanIntervalEntry 1 }

		
--   1.3.6.1.4.1.231.7.1.2.2.1.6.1.1.15.1.2
		sheAdslAtucChanIntervalValidData OBJECT-TYPE
			SYNTAX TruthValue
			MAX-ACCESS read-only
			STATUS current
			DESCRIPTION
				"This variable indicates if the data for this
				interval is valid."
			::= { sheAdslAtucChanIntervalEntry 2 }

		
--   1.3.6.1.4.1.231.7.1.2.2.1.6.1.1.15.1.3
		sheAdslAtucChanIntervalEndTime OBJECT-TYPE
			SYNTAX Unsigned32
			MAX-ACCESS read-only
			STATUS current
			DESCRIPTION
				"This variable indicates the time of storing this interval."
			::= { sheAdslAtucChanIntervalEntry 3 }

		
--   1.3.6.1.4.1.231.7.1.2.2.1.6.1.1.15.1.4
		sheAdslAtucChanIntervalReceivedBlks OBJECT-TYPE
			SYNTAX PerfIntervalCount
			MAX-ACCESS read-only
			STATUS current
			DESCRIPTION
				"Count of all encoded blocks received on this channel
				during this interval."
			::= { sheAdslAtucChanIntervalEntry 4 }

		
--   1.3.6.1.4.1.231.7.1.2.2.1.6.1.1.15.1.5
		sheAdslAtucChanIntervalTransmittedBlks OBJECT-TYPE
			SYNTAX PerfIntervalCount
			MAX-ACCESS read-only
			STATUS current
			DESCRIPTION
				"Count of all encoded blocks transmitted on this
				channel during this interval."
			::= { sheAdslAtucChanIntervalEntry 5 }

		
--   1.3.6.1.4.1.231.7.1.2.2.1.6.1.1.15.1.6
		sheAdslAtucChanIntervalCorrectedBlks OBJECT-TYPE
			SYNTAX PerfIntervalCount
			MAX-ACCESS read-only
			STATUS current
			DESCRIPTION
				"Count of all blocks received with errors that were
				corrected on this channel during this interval."
			::= { sheAdslAtucChanIntervalEntry 6 }

		
--   1.3.6.1.4.1.231.7.1.2.2.1.6.1.1.15.1.7
		sheAdslAtucChanIntervalUncorrectBlks OBJECT-TYPE
			SYNTAX PerfIntervalCount
			MAX-ACCESS read-only
			STATUS current
			DESCRIPTION
				"Count of all blocks received with uncorrectable
				errors on this channel during this interval."
			::= { sheAdslAtucChanIntervalEntry 7 }

		
--   1.3.6.1.4.1.231.7.1.2.2.1.6.1.1.15.1.8
		sheAdslAtucChanIntervalNcd OBJECT-TYPE
			SYNTAX Counter32
			MAX-ACCESS read-only
			STATUS current
			DESCRIPTION
				"Indicates count of no cell delineation on this channel for this interval."
			::= { sheAdslAtucChanIntervalEntry 8 }

		
--   1.3.6.1.4.1.231.7.1.2.2.1.6.1.1.15.1.9
		sheAdslAtucChanIntervalOcd OBJECT-TYPE
			SYNTAX Counter32
			MAX-ACCESS read-only
			STATUS current
			DESCRIPTION
				"Indicates count of out cell delineation on this channel for this interval."
			::= { sheAdslAtucChanIntervalEntry 9 }

		
--   1.3.6.1.4.1.231.7.1.2.2.1.6.1.1.15.1.10
		sheAdslAtucChanIntervalHec OBJECT-TYPE
			SYNTAX Counter32
			MAX-ACCESS read-only
			STATUS current
			DESCRIPTION
				"Indicates Header error check counter on this channel during this interval."
			::= { sheAdslAtucChanIntervalEntry 10 }

		
--   1.3.6.1.4.1.231.7.1.2.2.1.6.1.1.16
		sheAdslAturPhysTable OBJECT-TYPE
			SYNTAX SEQUENCE OF SheAdslAturPhysEntry
			MAX-ACCESS not-accessible
			STATUS current
			DESCRIPTION
				"This table provides one row for each ATUR
				Each row contains the Physical Layer Parameters
				table for that ATUR. ADSL physical interfaces are
				those ifEntries where ifType is equal to adsl(94)."
			::= { sheAdslLineMIB 16 }

		
--   1.3.6.1.4.1.231.7.1.2.2.1.6.1.1.16.1
		sheAdslAturPhysEntry OBJECT-TYPE
			SYNTAX SheAdslAturPhysEntry
			MAX-ACCESS not-accessible
			STATUS current
			DESCRIPTION
				"An entry in the adslAturPhysTable."
			INDEX { ifIndex }
			::= { sheAdslAturPhysTable 1 }

		
		SheAdslAturPhysEntry ::=
			SEQUENCE { 
				sheAdslAturPhysInvSerialNumber
					SnmpAdminString,
				sheAdslAturPhysInvVendorID
					SnmpAdminString,
				sheAdslAturPhysInvVersionNumber
					SnmpAdminString,
				sheAdslAturPhysCurrSnrMgn
					INTEGER,
				sheAdslAturPhysCurrAtn
					Gauge32,
				sheAdslAturPhysCurrStatus
					SheAdslLineCurrentStatusType,
				sheAdslAturPhysCurrOutputPwr
					INTEGER,
				sheAdslAturPhysCurrAttainableRate
					Gauge32,
				sheAdslAturPhysConfig
					OCTET STRING,
				sheAdslAturPhysDeltHLINSCds
					Unsigned32,
				sheAdslAturPhysDeltHLINpsds
					OCTET STRING,
				sheAdslAturPhysDeltHLOGMTds
					Unsigned32,
				sheAdslAturPhysDeltHLOGpsds
					OCTET STRING,
				sheAdslAturPhysDeltQLNMTds
					Unsigned32,
				sheAdslAturPhysDeltQLNpsds
					OCTET STRING,
				sheAdslAturPhysCurrentBinBitLoading
					OCTET STRING,
				sheAdslAturPhysDeltSNRMTds
					Unsigned32,
				sheAdslAturPhysDeltDMTBinSNRds
					OCTET STRING,
				sheAdslAturPhysDeltLastTxState
					SheAdslPhysAturDeltLastTxStateType,
				sheAdslAturPhysDeltSATNds
					Unsigned32
			 }

--   1.3.6.1.4.1.231.7.1.2.2.1.6.1.1.16.1.1
		sheAdslAturPhysInvSerialNumber OBJECT-TYPE
			SYNTAX SnmpAdminString (SIZE (0..32))
			MAX-ACCESS read-only
			STATUS current
			DESCRIPTION
				"The vendor specific string that identifies the
				vendor equipment."
			::= { sheAdslAturPhysEntry 1 }

		
--   1.3.6.1.4.1.231.7.1.2.2.1.6.1.1.16.1.2
		sheAdslAturPhysInvVendorID OBJECT-TYPE
			SYNTAX SnmpAdminString (SIZE (0..16))
			MAX-ACCESS read-only
			STATUS current
			DESCRIPTION
				"The vendor ID code is a copy of the binary
				vendor identification field defined by the
				PHY[10] and expressed as readable characters."
			REFERENCE
				"ANSI T1.413"
			::= { sheAdslAturPhysEntry 2 }

		
--   1.3.6.1.4.1.231.7.1.2.2.1.6.1.1.16.1.3
		sheAdslAturPhysInvVersionNumber OBJECT-TYPE
			SYNTAX SnmpAdminString (SIZE (0..16))
			MAX-ACCESS read-only
			STATUS current
			DESCRIPTION
				"The vendor specific version number sent by this ATU
				as part of the initialization messages.  It is a copy
				of the binary version number field defined by the
				PHY[10] and expressed as readable characters."
			REFERENCE
				"ANSI T1.413"
			::= { sheAdslAturPhysEntry 3 }

		
--   1.3.6.1.4.1.231.7.1.2.2.1.6.1.1.16.1.4
		sheAdslAturPhysCurrSnrMgn OBJECT-TYPE
			SYNTAX INTEGER (-640..640)
			UNITS "tenth dB"
			MAX-ACCESS read-only
			STATUS current
			DESCRIPTION
				"Noise Margin as seen by this ATU with respect to its
				received signal in tenth dB."
			::= { sheAdslAturPhysEntry 4 }

		
--   1.3.6.1.4.1.231.7.1.2.2.1.6.1.1.16.1.5
		sheAdslAturPhysCurrAtn OBJECT-TYPE
			SYNTAX Gauge32 (0..630)
			UNITS "tenth dB"
			MAX-ACCESS read-only
			STATUS current
			DESCRIPTION
				"Measured difference in the total power transmitted by
				the peer ATU and the total power received by this ATU."
			::= { sheAdslAturPhysEntry 5 }

		
--   1.3.6.1.4.1.231.7.1.2.2.1.6.1.1.16.1.6
		sheAdslAturPhysCurrStatus OBJECT-TYPE
			SYNTAX SheAdslLineCurrentStatusType
			MAX-ACCESS read-only
			STATUS current
			DESCRIPTION
				"Indicates current state of the ATUR line.  This is a
				bit-map of possible conditions.  Due to the isolation
				of the ATUR when line problems occur, many state
				conditions like loss of power, loss of quality signal,
				and initialization errors,  can not be determined.
				While trouble shooting ATUR, also use object,
				adslAtucCurrStatus.  The various bit positions are:
				
				0      noDefect             There no defects on the line
				
				1      lossOfFraming        ATUR failure due to not
				                     receiving valid frame
				
				2      lossOfSignal         ATUR failure due to not
				                     receiving signal
				
				3      lossOfPower          ATUR failure due to loss of
				                     power
				
				4      lossOfSignalQuality  Loss of Signal Quality is
				                     declared when the Noise Margin
				                     falls below the Minimum Noise
				                     Margin, or the
				                     bit-error-rate exceeds 10^-7.
				
				This is intended to supplement ifOperStatus."
			::= { sheAdslAturPhysEntry 6 }

		
--   1.3.6.1.4.1.231.7.1.2.2.1.6.1.1.16.1.7
		sheAdslAturPhysCurrOutputPwr OBJECT-TYPE
			SYNTAX INTEGER (-310..310)
			UNITS "tenth dBm"
			MAX-ACCESS read-only
			STATUS current
			DESCRIPTION
				"Measured total output power transmitted by this ATU.
				This is the measurement that was reported during
				the last activation sequence."
			::= { sheAdslAturPhysEntry 7 }

		
--   1.3.6.1.4.1.231.7.1.2.2.1.6.1.1.16.1.8
		sheAdslAturPhysCurrAttainableRate OBJECT-TYPE
			SYNTAX Gauge32
			UNITS "kbps"
			MAX-ACCESS read-only
			STATUS current
			DESCRIPTION
				"Indicates the maximum currently attainable data rate
				by the ATU.  This value will be equal or greater than
				the current line rate."
			::= { sheAdslAturPhysEntry 8 }

		
--   1.3.6.1.4.1.231.7.1.2.2.1.6.1.1.16.1.9
		sheAdslAturPhysConfig OBJECT-TYPE
			SYNTAX OCTET STRING (SIZE (0..255))
			MAX-ACCESS read-only
			STATUS current
			DESCRIPTION
				"This object provides the upstream and downstream ATU-R configuration data (EOC - read 5 sec after data mode)."
			::= { sheAdslAturPhysEntry 9 }

		
--   1.3.6.1.4.1.231.7.1.2.2.1.6.1.1.16.1.10
		sheAdslAturPhysDeltHLINSCds OBJECT-TYPE
			SYNTAX Unsigned32
			MAX-ACCESS read-only
			STATUS current
			DESCRIPTION
				"DELT-related parameter that provides the scale factor to be applied to the 
				downstream Hlin(f) values.
				(Not available for ADSL but ADSL2 & ADSL2plus)."
			REFERENCE
				"G997.1 chapter 7.5.1.18.1"
			::= { sheAdslAturPhysEntry 10 }

		
--   1.3.6.1.4.1.231.7.1.2.2.1.6.1.1.16.1.11
		sheAdslAturPhysDeltHLINpsds OBJECT-TYPE
			SYNTAX OCTET STRING (SIZE (0..2048))
			MAX-ACCESS read-only
			STATUS current
			DESCRIPTION
				"DELT-related parameter that provides an array of complex downstream Hlin(f) 
				values in linear scale. 
				Every two octects refer to one element in this array of octets.
				(Not available for ADSL but ADSL2 & ADSL2plus).
				
				This parameter is an array of complex downstream Hlin(f) values in linear scale.
				Each array entry represents the Hlin(f = i*HLINGds* delta(f)) value for a 
				particular subcarrier group index i, ranging from 0 to MIN(NSCds - 1,511).
				The Hlin(f) is represented as ((scale/2(exp15))*((a(i) + j*b(i))/2(exp15))), with scale
				being coded as a 16-bit unsigned integer and, a(i) and b(i) coded as 
				16-bit 2s complement signed integers in the (-2(exp15) + 1) to (+2(exp15) - 1) range.
				A special value a(i) = b(i) = -2(exp15) indicates that no measurement could be done
				for this subcarrier group because it is out of the passband or that the 
				attenuation is out of range to be represented. This parameter is only available
				after a loop diagnostic procedure."
			REFERENCE
				"G997.1 chapter 7.5.1.18.2"
			::= { sheAdslAturPhysEntry 11 }

		
--   1.3.6.1.4.1.231.7.1.2.2.1.6.1.1.16.1.12
		sheAdslAturPhysDeltHLOGMTds OBJECT-TYPE
			SYNTAX Unsigned32
			MAX-ACCESS read-only
			STATUS current
			DESCRIPTION
				"DELT-related parameter that provides the number of symbols used to measure the 
				downstream Hlog(f). 
				(Not available for ADSL but ADSL2 & ADSL2plus)."
			REFERENCE
				"G997.1 chapter 7.5.1.18.3"
			::= { sheAdslAturPhysEntry 12 }

		
--   1.3.6.1.4.1.231.7.1.2.2.1.6.1.1.16.1.13
		sheAdslAturPhysDeltHLOGpsds OBJECT-TYPE
			SYNTAX OCTET STRING (SIZE (0..1024))
			MAX-ACCESS read-only
			STATUS current
			DESCRIPTION
				"DELT-related parameter that provides an array of real downstream Hlog(f) values
				in dB. 
				(Not available for ADSL but ADSL2 & ADSL2plus).
				
				This parameter is an array of real downstream Hlog(f) values in dB.
				Each array entry represents the real Hlog(f = i*HLOGGds* delta(f)) value for a
				particular subcarrier group sub-carrier index i, ranging from 0 to MIN(NSCds - 1,511).
				The real Hlog(f) value is represented as (6 - m(i)/10), with m(i) 10-bit
				unsigned integer in the 0 to 1022 range. A special value m = 1023 indicates
				that no measurement could be done for this subcarrier group because it is out
				of the passband or that the attenuation is out of range to be represented."
			REFERENCE
				"G997.1 chapter 7.5.1.18.4"
			::= { sheAdslAturPhysEntry 13 }

		
--   1.3.6.1.4.1.231.7.1.2.2.1.6.1.1.16.1.14
		sheAdslAturPhysDeltQLNMTds OBJECT-TYPE
			SYNTAX Unsigned32
			MAX-ACCESS read-only
			STATUS current
			DESCRIPTION
				"DELT-related parameter that provides the number of symbols used to measure the 
				downstream QLN(f) values. 
				(Not available for ADSL but ADSL2 & ADSL2plus)."
			REFERENCE
				"G997.1 chapter 7.5.1.19.1"
			::= { sheAdslAturPhysEntry 14 }

		
--   1.3.6.1.4.1.231.7.1.2.2.1.6.1.1.16.1.15
		sheAdslAturPhysDeltQLNpsds OBJECT-TYPE
			SYNTAX OCTET STRING (SIZE (0..512))
			MAX-ACCESS read-only
			STATUS current
			DESCRIPTION
				"DELT-related parameter that provides an array of real downstream QLN(f) values 
				in dBm/Hz. 
				Every two octects refer to one element in this array of octets.
				(Not available for ADSL but ADSL2 & ADSL2plus).
				
				This parameter is an array of real downstream QLN(f) values in dBm/Hz.
				Each array entry represents the QLN(f = i*QLNGds* delta(f)) value for a 
				particular subcarrier group index i, ranging from 0 to MIN(NSCds - 1,511).
				The QLN(f) is represented as (-23 - n(i)/2), with n(i) an 8-bit unsigned integer
				in the 0 to 254 range. A special value n(i) = 255 indicates that no measurement
				could be done for this subcarrier group because it is out of the passband or 
				that the noise PSD is out of range to be represented."
			REFERENCE
				"G997.1 chapter 7.5.1.19.2"
			::= { sheAdslAturPhysEntry 15 }

		
--  1.3.6.1.4.1.231.7.1.2.2.1.6.1.1.16.1.16
		sheAdslAturPhysCurrentBinBitLoading OBJECT-TYPE
			SYNTAX OCTET STRING (SIZE (0..512))
			MAX-ACCESS read-only
			STATUS current
			DESCRIPTION
				"This parameter represent the current used bit loading per bin in downstream direction.
				Each octet map to the corresponding bin."
			::= { sheAdslAturPhysEntry 16 }

		
--  1.3.6.1.4.1.231.7.1.2.2.1.6.1.1.16.1.17
		sheAdslAturPhysDeltSNRMTds OBJECT-TYPE
			SYNTAX Unsigned32
			MAX-ACCESS read-only
			STATUS current
			DESCRIPTION
				"DELT-related parameter that provides the number of symbols used to measure 
				the downstream SNR(f) values. (Not available for ADSL and ADSL2plus)
				It is represented as a 16-bit unsigned value.
				After a loop diagnostic procedure, this parameter shall contain the number of symbols 
				used to generate the associate parameter. It should correspond to the value specified 
				in the Recommendation (e.g., the number of symbols in 1 s time interval for G.992.3)."
			::= { sheAdslAturPhysEntry 17 }

		
--  1.3.6.1.4.1.231.7.1.2.2.1.6.1.1.16.1.18
		sheAdslAturPhysDeltDMTBinSNRds OBJECT-TYPE
			SYNTAX OCTET STRING (SIZE (0..512))
			MAX-ACCESS read-only
			STATUS current
			DESCRIPTION
				"DELT-related parameter that provides an array of real downstream SNR(f) values 
				in dB (Not available for ADSL and ADSL2plus)
				Each array entry represents the SNR(f = i*f) value for a particular subcarrier index i, 
				ranging from 0 to NSCds C 1. The SNR(f) is represented as (C32 + snr(i)/2), with snr(i) 
				an 8-bit unsigned integer in the 0 to 254 range. A special value snr(i) = 255 indicates 
				that no measurement could be done for the subcarrier because it is out of the passband or 
				that the noise PSD is out of range to be represented."
			::= { sheAdslAturPhysEntry 18 }

		
--  1.3.6.1.4.1.231.7.1.2.2.1.6.1.1.16.1.19
		sheAdslAturPhysDeltLastTxState OBJECT-TYPE
			SYNTAX SheAdslPhysAturDeltLastTxStateType
			MAX-ACCESS read-only
			STATUS current
			DESCRIPTION
				"DELT-related parameter that provides last successful transmitted initialization 
				state by the ATU-R. (Not available for ADSL and ADSL2plus)
				
				Initialization states are defined in the individual ADSL Recommendations and are 
				counted from 0 (if G.994.1 is used) or 1 (if G.994.1 is not used) up to Showtime. 
				This parameter must be interpreted along with the ADSL Transmission System.
				This parameter is available only when, after a failed full initialization, the line 
				diagnostics procedures are activated on the line. Line diagnostics procedures can be 
				activated by the operator of the system (through the Line State Forced line configuration 
				parameter) or autonomously by the ATU-C or ATU-R."
			::= { sheAdslAturPhysEntry 19 }

		
--  1.3.6.1.4.1.231.7.1.2.2.1.6.1.1.16.1.20
		sheAdslAturPhysDeltSATNds OBJECT-TYPE
			SYNTAX Unsigned32 (0..1270)
			UNITS "0.1 dB"
			MAX-ACCESS read-only
			STATUS current
			DESCRIPTION
				"DELT-related parameter that provides the downtream signal attenuation (length = 4 bytes). 
				(Not available for ADSL and ADSL2plus). 				
				This parameter is the measured difference in the total power transmitted by the ATU-C and 
				the total power received by the ATU-R over all subcarriers during showtime. The downstream 
				line attenuation ranges from 0 to +127 dB with 0.1 dB steps. A special value indicates the 
				line attenuation is out of range to be represented.
				NOTE: During showtime, only a subset of the subcarriers may be transmitted by the ATU-C, 
				as compared to diagnostics mode and initialization. Therefore, the downstream Signal attenuation 
				may be significantly lower than the downstream Line attenuation."
			::= { sheAdslAturPhysEntry 20 }

		
--   1.3.6.1.4.1.231.7.1.2.2.1.6.1.1.17
		sheAdslAturChanTable OBJECT-TYPE
			SYNTAX SEQUENCE OF SheAdslAturChanEntry
			MAX-ACCESS not-accessible
			STATUS current
			DESCRIPTION
				"This table provides one row for each ATUR channel."
			::= { sheAdslLineMIB 17 }

		
--   1.3.6.1.4.1.231.7.1.2.2.1.6.1.1.17.1
		sheAdslAturChanEntry OBJECT-TYPE
			SYNTAX SheAdslAturChanEntry
			MAX-ACCESS not-accessible
			STATUS current
			DESCRIPTION
				"An entry in the adslAturChanTable.
				This table is only supported by NE releases smaller then R2.5 (NO dualLatency support)!!"
			INDEX { ifIndex }
			::= { sheAdslAturChanTable 1 }

		
		SheAdslAturChanEntry ::=
			SEQUENCE { 
				sheAdslAturChanInterleaveDelay
					Gauge32,
				sheAdslAturChanCurrTxRate
					Gauge32,
				sheAdslAturChanPrevTxRate
					Gauge32,
				sheAdslAturChanCrcBlockLength
					Gauge32,
				sheAdslAturChanCurrAtmStatus
					SheAdslLineAtmStatus,
				sheAdslAturChanRsSymbols
					Unsigned32,
				sheAdslAturChanRsDepth
					Unsigned32,
				sheAdslAturChanRsRedundancy
					Unsigned32
			 }

--   1.3.6.1.4.1.231.7.1.2.2.1.6.1.1.17.1.1
		sheAdslAturChanInterleaveDelay OBJECT-TYPE
			SYNTAX Gauge32
			UNITS "milli-seconds"
			MAX-ACCESS read-only
			STATUS current
			DESCRIPTION
				"Interleave Delay for this channel.
				
				Interleave delay applies only to the
				interleave channel and defines the mapping
				(relative spacing) between subsequent input
				bytes at the interleaver input and their placement
				in the bit stream at the interleaver output.
				Larger numbers provide greater separation between
				consecutive input bytes in the output bit stream
				allowing for improved impulse noise immunity at
				the expense of payload latency.
				
				In the case where the ifType is Fast(125), use
				noSuchObject."
			::= { sheAdslAturChanEntry 1 }

		
--   1.3.6.1.4.1.231.7.1.2.2.1.6.1.1.17.1.2
		sheAdslAturChanCurrTxRate OBJECT-TYPE
			SYNTAX Gauge32 (1..32736)
			UNITS "kbps"
			MAX-ACCESS read-only
			STATUS current
			DESCRIPTION
				"Actual transmit rate on this channel."
			::= { sheAdslAturChanEntry 2 }

		
--   1.3.6.1.4.1.231.7.1.2.2.1.6.1.1.17.1.3
		sheAdslAturChanPrevTxRate OBJECT-TYPE
			SYNTAX Gauge32 (1..32736)
			UNITS "kbps"
			MAX-ACCESS read-only
			STATUS current
			DESCRIPTION
				"The rate at the time of the last
				adslAturRateChangeTrap event. It is also set at
				initialization to prevent a trap being sent.
				Rate changes less than adslAturThresh(*)RateDown
				or less than adslAturThresh(*)RateUp will not
				cause a trap or cause this object to change.
				(*) == Fast or Interleave.
				See AdslLineAlarmConfProfileEntry."
			::= { sheAdslAturChanEntry 3 }

		
--   1.3.6.1.4.1.231.7.1.2.2.1.6.1.1.17.1.4
		sheAdslAturChanCrcBlockLength OBJECT-TYPE
			SYNTAX Gauge32
			MAX-ACCESS read-only
			STATUS current
			DESCRIPTION
				"Indicates the length of the channel data-block
				on which the CRC operates.  Refer to Line Code
				Specific MIBs, [11] and [12] for more
				information."
			::= { sheAdslAturChanEntry 4 }

		
--   1.3.6.1.4.1.231.7.1.2.2.1.6.1.1.17.1.5
		sheAdslAturChanCurrAtmStatus OBJECT-TYPE
			SYNTAX SheAdslLineAtmStatus
			MAX-ACCESS read-only
			STATUS current
			DESCRIPTION
				"This object indicates an ncd or lcd failure if the counter surpasses 127. If neither ATM counter surpasses 127, the return value will be NoAtmDefect.
				noAtmDefect(0),
				noCellDeleniation(1),
				lossOfCellDeleniation(2)
				"
			::= { sheAdslAturChanEntry 5 }

		
--   1.3.6.1.4.1.231.7.1.2.2.1.6.1.1.17.1.6
		sheAdslAturChanRsSymbols OBJECT-TYPE
			SYNTAX Unsigned32
			MAX-ACCESS read-only
			STATUS current
			DESCRIPTION
				"This object indicates number of DMT symbols per Reed- Solomon code word (S) in the upstream direction Note that S is not restricted to interleaved mode only. Even in fast mode, S is a valid constant value and is equal to 1."
			::= { sheAdslAturChanEntry 6 }

		
--   1.3.6.1.4.1.231.7.1.2.2.1.6.1.1.17.1.7
		sheAdslAturChanRsDepth OBJECT-TYPE
			SYNTAX Unsigned32
			MAX-ACCESS read-only
			STATUS current
			DESCRIPTION
				"This object indicates interleaving depth (D) in the upstream direction Note that D is not restricted to interleaved mode only. Even in fast mode, D is a valid constant value and is equal to 1."
			::= { sheAdslAturChanEntry 7 }

		
--   1.3.6.1.4.1.231.7.1.2.2.1.6.1.1.17.1.8
		sheAdslAturChanRsRedundancy OBJECT-TYPE
			SYNTAX Unsigned32
			MAX-ACCESS read-only
			STATUS current
			DESCRIPTION
				"This object indicates number of redundant bytes (R) per Reed-Solomon code in the upstream direction."
			::= { sheAdslAturChanEntry 8 }

		
--   1.3.6.1.4.1.231.7.1.2.2.1.6.1.1.18
		sheAdslAturPerfDataTable OBJECT-TYPE
			SYNTAX SEQUENCE OF SheAdslAturPerfDataEntry
			MAX-ACCESS not-accessible
			STATUS current
			DESCRIPTION
				"This table provides one row for each ATUR.
				ADSL physical interfaces are
				those ifEntries where ifType is equal to adsl(94)."
			::= { sheAdslLineMIB 18 }

		
--   1.3.6.1.4.1.231.7.1.2.2.1.6.1.1.18.1
		sheAdslAturPerfDataEntry OBJECT-TYPE
			SYNTAX SheAdslAturPerfDataEntry
			MAX-ACCESS not-accessible
			STATUS current
			DESCRIPTION
				"An entry in adslAturPerfDataTable."
			INDEX { ifIndex }
			::= { sheAdslAturPerfDataTable 1 }

		
		SheAdslAturPerfDataEntry ::=
			SEQUENCE { 
				sheAdslAturPerfDataLofs
					Counter32,
				sheAdslAturPerfDataLoss
					Counter32,
				sheAdslAturPerfDataLprs
					Counter32,
				sheAdslAturPerfDataESs
					Counter32,
				sheAdslAturPerfDataStatSesL
					Counter32,
				sheAdslAturPerfDataStatUasL
					Counter32,
				sheAdslAturPerfDataValidIntervals
					INTEGER,
				sheAdslAturPerfDataInvalidIntervals
					INTEGER,
				sheAdslAturPerfDataCurr15MinTimeElapsed
					AdslPerfTimeElapsed,
				sheAdslAturPerfDataCurr15MinLofs
					PerfCurrentCount,
				sheAdslAturPerfDataCurr15MinLoss
					PerfCurrentCount,
				sheAdslAturPerfDataCurr15MinLprs
					PerfCurrentCount,
				sheAdslAturPerfDataCurr15MinESs
					PerfCurrentCount,
				sheAdslAturPerfDataCurr15MinSesL
					PerfCurrentCount,
				sheAdslAturPerfDataCurr15MinUasL
					PerfCurrentCount,
				sheAdslAturPerfDataCurr1DayTimeElapsed
					AdslPerfTimeElapsed,
				sheAdslAturPerfDataCurr1DayLofs
					AdslPerfCurrDayCount,
				sheAdslAturPerfDataCurr1DayLoss
					AdslPerfCurrDayCount,
				sheAdslAturPerfDataCurr1DayLprs
					AdslPerfCurrDayCount,
				sheAdslAturPerfDataCurr1DayESs
					AdslPerfCurrDayCount,
				sheAdslAturPerfDataCurr1DaySesL
					AdslPerfCurrDayCount,
				sheAdslAturPerfDataCurr1DayUasL
					AdslPerfCurrDayCount,
				sheAdslAturPerfDataPrev1DayMoniSecs
					INTEGER,
				sheAdslAturPerfDataPrev1DayLofs
					AdslPerfPrevDayCount,
				sheAdslAturPerfDataPrev1DayLoss
					AdslPerfPrevDayCount,
				sheAdslAturPerfDataPrev1DayLprs
					AdslPerfPrevDayCount,
				sheAdslAturPerfDataPrev1DayESs
					AdslPerfPrevDayCount,
				sheAdslAturPerfDataPrev1DaySesL
					AdslPerfPrevDayCount,
				sheAdslAturPerfDataPrev1DayUasL
					AdslPerfPrevDayCount
			 }

--   1.3.6.1.4.1.231.7.1.2.2.1.6.1.1.18.1.1
		sheAdslAturPerfDataLofs OBJECT-TYPE
			SYNTAX Counter32
			UNITS "seconds"
			MAX-ACCESS read-only
			STATUS current
			DESCRIPTION
				"Count of the number of Loss of Framing failures since
				agent reset."
			::= { sheAdslAturPerfDataEntry 1 }

		
--   1.3.6.1.4.1.231.7.1.2.2.1.6.1.1.18.1.2
		sheAdslAturPerfDataLoss OBJECT-TYPE
			SYNTAX Counter32
			UNITS "seconds"
			MAX-ACCESS read-only
			STATUS current
			DESCRIPTION
				"Count of the number of Loss of Signal failures since
				agent reset."
			::= { sheAdslAturPerfDataEntry 2 }

		
--   1.3.6.1.4.1.231.7.1.2.2.1.6.1.1.18.1.3
		sheAdslAturPerfDataLprs OBJECT-TYPE
			SYNTAX Counter32
			UNITS "seconds"
			MAX-ACCESS read-only
			STATUS current
			DESCRIPTION
				"Count of the number of Loss of Power failures since
				agent reset."
			::= { sheAdslAturPerfDataEntry 3 }

		
--   1.3.6.1.4.1.231.7.1.2.2.1.6.1.1.18.1.4
		sheAdslAturPerfDataESs OBJECT-TYPE
			SYNTAX Counter32
			UNITS "seconds"
			MAX-ACCESS read-only
			STATUS current
			DESCRIPTION
				"Count of the number of Errored Seconds since agent
				reset.  The errored second parameter is a count of
				one-second intervals containing one or more crc
				anomalies, or one or more los or sef defects."
			::= { sheAdslAturPerfDataEntry 4 }

		
--   1.3.6.1.4.1.231.7.1.2.2.1.6.1.1.18.1.5
		sheAdslAturPerfDataStatSesL OBJECT-TYPE
			SYNTAX Counter32
			UNITS "seconds"
			MAX-ACCESS read-only
			STATUS current
			DESCRIPTION
				"The value of this object reports the count of
				severely errored second-line since the last agent
				reset."
			REFERENCE
				"ITU G.997.1 Section 7.2.1.1.7 "
			::= { sheAdslAturPerfDataEntry 5 }

		
--   1.3.6.1.4.1.231.7.1.2.2.1.6.1.1.18.1.6
		sheAdslAturPerfDataStatUasL OBJECT-TYPE
			SYNTAX Counter32
			UNITS "seconds"
			MAX-ACCESS read-only
			STATUS current
			DESCRIPTION
				"The value of this object reports the count of
				unavailable seconds-line since the last agent
				reset."
			REFERENCE
				"ITU G.997.1 Section 7.2.1.2.9 "
			::= { sheAdslAturPerfDataEntry 6 }

		
--   1.3.6.1.4.1.231.7.1.2.2.1.6.1.1.18.1.7
		sheAdslAturPerfDataValidIntervals OBJECT-TYPE
			SYNTAX INTEGER (0..96)
			MAX-ACCESS read-only
			STATUS current
			DESCRIPTION
				"The number of previous 15-minute intervals in the
				interval table for which data was collected.  Given
				that <n> is the maximum # of intervals supported.
				The value will be <n> unless the measurement was
				(re-)started within the last (<n>*15) minutes, in which
				case the value will be the number of complete 15
				minute intervals for which the agent has at least
				some data. In certain cases (e.g., in the case
				where the agent is a proxy) it is possible that some
				intervals are unavailable.  In this case, this
				interval is the maximum interval number for
				which data is available."
			::= { sheAdslAturPerfDataEntry 7 }

		
--   1.3.6.1.4.1.231.7.1.2.2.1.6.1.1.18.1.8
		sheAdslAturPerfDataInvalidIntervals OBJECT-TYPE
			SYNTAX INTEGER (0..96)
			MAX-ACCESS read-only
			STATUS current
			DESCRIPTION
				"The number of intervals in the range from
				0 to the value of adslAturPerfValidIntervals
				for which no data is available. This object
				will typically be zero except in cases where
				the data for some intervals are not available
				(e.g., in proxy situations)."
			::= { sheAdslAturPerfDataEntry 8 }

		
--   1.3.6.1.4.1.231.7.1.2.2.1.6.1.1.18.1.9
		sheAdslAturPerfDataCurr15MinTimeElapsed OBJECT-TYPE
			SYNTAX AdslPerfTimeElapsed (0..899)
			UNITS "seconds"
			MAX-ACCESS read-only
			STATUS current
			DESCRIPTION
				"Total elapsed seconds in this interval."
			::= { sheAdslAturPerfDataEntry 9 }

		
--   1.3.6.1.4.1.231.7.1.2.2.1.6.1.1.18.1.10
		sheAdslAturPerfDataCurr15MinLofs OBJECT-TYPE
			SYNTAX PerfCurrentCount
			UNITS "seconds"
			MAX-ACCESS read-only
			STATUS current
			DESCRIPTION
				"Count of seconds in the current 15 minute interval
				when there was Loss of Framing."
			::= { sheAdslAturPerfDataEntry 10 }

		
--   1.3.6.1.4.1.231.7.1.2.2.1.6.1.1.18.1.11
		sheAdslAturPerfDataCurr15MinLoss OBJECT-TYPE
			SYNTAX PerfCurrentCount
			UNITS "seconds"
			MAX-ACCESS read-only
			STATUS current
			DESCRIPTION
				"Count of seconds in the current 15 minute interval
				when there was Loss of Signal."
			::= { sheAdslAturPerfDataEntry 11 }

		
--   1.3.6.1.4.1.231.7.1.2.2.1.6.1.1.18.1.12
		sheAdslAturPerfDataCurr15MinLprs OBJECT-TYPE
			SYNTAX PerfCurrentCount
			UNITS "seconds"
			MAX-ACCESS read-only
			STATUS current
			DESCRIPTION
				"Count of seconds in the current 15 minute interval
				when there was Loss of Power."
			::= { sheAdslAturPerfDataEntry 12 }

		
--   1.3.6.1.4.1.231.7.1.2.2.1.6.1.1.18.1.13
		sheAdslAturPerfDataCurr15MinESs OBJECT-TYPE
			SYNTAX PerfCurrentCount
			UNITS "seconds"
			MAX-ACCESS read-only
			STATUS current
			DESCRIPTION
				"Count of Errored Seconds in the current 15 minute
				interval.  The errored second parameter is a count of
				one-second intervals containing one or more crc
				anomalies, or one or more los or sef defects."
			::= { sheAdslAturPerfDataEntry 13 }

		
--   1.3.6.1.4.1.231.7.1.2.2.1.6.1.1.18.1.14
		sheAdslAturPerfDataCurr15MinSesL OBJECT-TYPE
			SYNTAX PerfCurrentCount
			UNITS "seconds"
			MAX-ACCESS read-only
			STATUS current
			DESCRIPTION
				"For the current 15-minute interval,
				adslAturPerfCurr15MinSesL reports the current
				number of seconds during which there have been
				severely errored seconds-line."
			REFERENCE
				"ITU G.997.1 Section 7.2.1.2.7 "
			::= { sheAdslAturPerfDataEntry 14 }

		
--   1.3.6.1.4.1.231.7.1.2.2.1.6.1.1.18.1.15
		sheAdslAturPerfDataCurr15MinUasL OBJECT-TYPE
			SYNTAX PerfCurrentCount
			UNITS "seconds"
			MAX-ACCESS read-only
			STATUS current
			DESCRIPTION
				"For the current 15-minute interval,
				adslAturPerfCurr15MinUasL reports the current
				number of seconds during which there have been
				available seconds-line."
			REFERENCE
				"ITU G.997.1 Section 7.2.1.2.9 "
			::= { sheAdslAturPerfDataEntry 15 }

		
--   1.3.6.1.4.1.231.7.1.2.2.1.6.1.1.18.1.16
		sheAdslAturPerfDataCurr1DayTimeElapsed OBJECT-TYPE
			SYNTAX AdslPerfTimeElapsed (0..86399)
			UNITS "seconds"
			MAX-ACCESS read-only
			STATUS current
			DESCRIPTION
				"Number of seconds that have elapsed since the
				beginning of the current 1-day interval."
			::= { sheAdslAturPerfDataEntry 16 }

		
--   1.3.6.1.4.1.231.7.1.2.2.1.6.1.1.18.1.17
		sheAdslAturPerfDataCurr1DayLofs OBJECT-TYPE
			SYNTAX AdslPerfCurrDayCount
			UNITS "seconds"
			MAX-ACCESS read-only
			STATUS current
			DESCRIPTION
				"Count of the number of seconds when there was Loss
				of Framing during the current day as measured by
				adslAturPerfCurr1DayTimeElapsed."
			::= { sheAdslAturPerfDataEntry 17 }

		
--   1.3.6.1.4.1.231.7.1.2.2.1.6.1.1.18.1.18
		sheAdslAturPerfDataCurr1DayLoss OBJECT-TYPE
			SYNTAX AdslPerfCurrDayCount
			UNITS "seconds"
			MAX-ACCESS read-only
			STATUS current
			DESCRIPTION
				"Count of the number of seconds when there was Loss
				of Signal during the current day as measured by
				adslAturPerfCurr1DayTimeElapsed."
			::= { sheAdslAturPerfDataEntry 18 }

		
--   1.3.6.1.4.1.231.7.1.2.2.1.6.1.1.18.1.19
		sheAdslAturPerfDataCurr1DayLprs OBJECT-TYPE
			SYNTAX AdslPerfCurrDayCount
			UNITS "seconds"
			MAX-ACCESS read-only
			STATUS current
			DESCRIPTION
				"Count of the number of seconds when there was Loss
				of Power during the current day as measured by
				adslAturPerfCurr1DayTimeElapsed."
			::= { sheAdslAturPerfDataEntry 19 }

		
--   1.3.6.1.4.1.231.7.1.2.2.1.6.1.1.18.1.20
		sheAdslAturPerfDataCurr1DayESs OBJECT-TYPE
			SYNTAX AdslPerfCurrDayCount
			UNITS "seconds"
			MAX-ACCESS read-only
			STATUS current
			DESCRIPTION
				"Count of Errored Seconds during the current day as
				measured by adslAturPerfCurr1DayTimeElapsed.
				The errored second parameter is a count of
				one-second intervals containing one or more crc
				anomalies, or one or more los or sef defects."
			::= { sheAdslAturPerfDataEntry 20 }

		
--   1.3.6.1.4.1.231.7.1.2.2.1.6.1.1.18.1.21
		sheAdslAturPerfDataCurr1DaySesL OBJECT-TYPE
			SYNTAX AdslPerfCurrDayCount
			UNITS "seconds"
			MAX-ACCESS read-only
			STATUS current
			DESCRIPTION
				"For the current day as measured by
				adslAturPerfCurr1DayTimeElapsed [RFC2662],
				adslAturPerfCurr1DaySesL reports the
				number of seconds during which there have been
				severely errored seconds-line."
			REFERENCE
				"ITU G.997.1 Section 7.2.1.2.7 "
			::= { sheAdslAturPerfDataEntry 21 }

		
--   1.3.6.1.4.1.231.7.1.2.2.1.6.1.1.18.1.22
		sheAdslAturPerfDataCurr1DayUasL OBJECT-TYPE
			SYNTAX AdslPerfCurrDayCount
			UNITS "seconds"
			MAX-ACCESS read-only
			STATUS current
			DESCRIPTION
				"For the current day as measured by
				adslAturPerfCurr1DayTimeElapsed [RFC2662],
				adslAturPerfCurr1DayUasL reports the
				number of seconds during which there have been
				unavailable seconds-line."
			REFERENCE
				"ITU G.997.1 Section 7.2.1.2.9 "
			::= { sheAdslAturPerfDataEntry 22 }

		
--   1.3.6.1.4.1.231.7.1.2.2.1.6.1.1.18.1.23
		sheAdslAturPerfDataPrev1DayMoniSecs OBJECT-TYPE
			SYNTAX INTEGER (0..86400)
			UNITS "seconds"
			MAX-ACCESS read-only
			STATUS current
			DESCRIPTION
				"The amount of time in the previous 1-day interval
				over which the performance monitoring information
				is actually counted. This value will be the same as
				the interval duration except in a situation where
				performance monitoring data could not be collected
				for any reason."
			::= { sheAdslAturPerfDataEntry 23 }

		
--   1.3.6.1.4.1.231.7.1.2.2.1.6.1.1.18.1.24
		sheAdslAturPerfDataPrev1DayLofs OBJECT-TYPE
			SYNTAX AdslPerfPrevDayCount
			UNITS "seconds"
			MAX-ACCESS read-only
			STATUS current
			DESCRIPTION
				"Count of seconds in the interval when there was
				Loss of Framing within the most recent previous
				1-day period."
			::= { sheAdslAturPerfDataEntry 24 }

		
--   1.3.6.1.4.1.231.7.1.2.2.1.6.1.1.18.1.25
		sheAdslAturPerfDataPrev1DayLoss OBJECT-TYPE
			SYNTAX AdslPerfPrevDayCount
			UNITS "seconds"
			MAX-ACCESS read-only
			STATUS current
			DESCRIPTION
				"Count of seconds in the interval when there was
				Loss of Signal within the most recent previous
				1-day period."
			::= { sheAdslAturPerfDataEntry 25 }

		
--   1.3.6.1.4.1.231.7.1.2.2.1.6.1.1.18.1.26
		sheAdslAturPerfDataPrev1DayLprs OBJECT-TYPE
			SYNTAX AdslPerfPrevDayCount
			UNITS "seconds"
			MAX-ACCESS read-only
			STATUS current
			DESCRIPTION
				"Count of seconds in the interval when there was
				Loss of Power within the most recent previous
				1-day period."
			::= { sheAdslAturPerfDataEntry 26 }

		
--   1.3.6.1.4.1.231.7.1.2.2.1.6.1.1.18.1.27
		sheAdslAturPerfDataPrev1DayESs OBJECT-TYPE
			SYNTAX AdslPerfPrevDayCount
			UNITS "seconds"
			MAX-ACCESS read-only
			STATUS current
			DESCRIPTION
				"Count of Errored Seconds within the most recent
				previous 1-day period. The errored second parameter is
				a count of one-second intervals containing one or more
				crc anomalies, or one or more los or sef defects."
			::= { sheAdslAturPerfDataEntry 27 }

		
--   1.3.6.1.4.1.231.7.1.2.2.1.6.1.1.18.1.28
		sheAdslAturPerfDataPrev1DaySesL OBJECT-TYPE
			SYNTAX AdslPerfPrevDayCount
			UNITS "seconds"
			MAX-ACCESS read-only
			STATUS current
			DESCRIPTION
				"For the previous day, adslAturPerfPrev1DaySesL
				reports the number of seconds during which there
				were severely errored seconds-line."
			REFERENCE
				"ITU G.997.1 Section 7.2.1.2.7 "
			::= { sheAdslAturPerfDataEntry 28 }

		
--   1.3.6.1.4.1.231.7.1.2.2.1.6.1.1.18.1.29
		sheAdslAturPerfDataPrev1DayUasL OBJECT-TYPE
			SYNTAX AdslPerfPrevDayCount
			UNITS "seconds"
			MAX-ACCESS read-only
			STATUS current
			DESCRIPTION
				"For the previous day, adslAturPerfPrev1DayUasL
				reports the number of seconds during which there
				were severely errored seconds-line."
			REFERENCE
				"ITU G.997.1 Section 7.2.1.2.9 "
			::= { sheAdslAturPerfDataEntry 29 }

		
--   1.3.6.1.4.1.231.7.1.2.2.1.6.1.1.19
		sheAdslAturIntervalTable OBJECT-TYPE
			SYNTAX SEQUENCE OF SheAdslAturIntervalEntry
			MAX-ACCESS not-accessible
			STATUS current
			DESCRIPTION
				"This table provides one row for each ATUR
				performance data collection interval.
				ADSL physical interfaces are those
				ifEntries where ifType is equal to adsl(94)."
			::= { sheAdslLineMIB 19 }

		
--   1.3.6.1.4.1.231.7.1.2.2.1.6.1.1.19.1
		sheAdslAturIntervalEntry OBJECT-TYPE
			SYNTAX SheAdslAturIntervalEntry
			MAX-ACCESS not-accessible
			STATUS current
			DESCRIPTION
				"An entry in the adslAturIntervalTable."
			INDEX { ifIndex, sheAdslAturChanIntervalNumber }
			::= { sheAdslAturIntervalTable 1 }

		
		SheAdslAturIntervalEntry ::=
			SEQUENCE { 
				sheAdslAturIntervalNumber
					INTEGER,
				sheAdslAturIntervalValidData
					TruthValue,
				sheAdslAturIntervalEndTime
					Unsigned32,
				sheAdslAturIntervalLofs
					PerfIntervalCount,
				sheAdslAturIntervalLoss
					PerfIntervalCount,
				sheAdslAturIntervalLprs
					PerfIntervalCount,
				sheAdslAturIntervalESs
					PerfIntervalCount,
				sheAdslAturIntervalSesL
					PerfIntervalCount,
				sheAdslAturIntervalUasL
					PerfIntervalCount
			 }

--   1.3.6.1.4.1.231.7.1.2.2.1.6.1.1.19.1.1
		sheAdslAturIntervalNumber OBJECT-TYPE
			SYNTAX INTEGER (1..96)
			MAX-ACCESS read-only
			STATUS current
			DESCRIPTION
				"Performance Data Interval number 1 is the
				the most recent previous interval; interval
				96 is 24 hours ago.  Intervals 2..96 are
				optional."
			::= { sheAdslAturIntervalEntry 1 }

		
--   1.3.6.1.4.1.231.7.1.2.2.1.6.1.1.19.1.2
		sheAdslAturIntervalValidData OBJECT-TYPE
			SYNTAX TruthValue
			MAX-ACCESS read-only
			STATUS current
			DESCRIPTION
				"This variable indicates if the data for this
				interval is valid."
			::= { sheAdslAturIntervalEntry 2 }

		
--   1.3.6.1.4.1.231.7.1.2.2.1.6.1.1.19.1.3
		sheAdslAturIntervalEndTime OBJECT-TYPE
			SYNTAX Unsigned32
			MAX-ACCESS read-only
			STATUS current
			DESCRIPTION
				"This variable indicates the time of storing this interval."
			::= { sheAdslAturIntervalEntry 3 }

		
--   1.3.6.1.4.1.231.7.1.2.2.1.6.1.1.19.1.4
		sheAdslAturIntervalLofs OBJECT-TYPE
			SYNTAX PerfIntervalCount
			UNITS "seconds"
			MAX-ACCESS read-only
			STATUS current
			DESCRIPTION
				"Count of seconds in the interval when there was
				Loss of Framing."
			::= { sheAdslAturIntervalEntry 4 }

		
--   1.3.6.1.4.1.231.7.1.2.2.1.6.1.1.19.1.5
		sheAdslAturIntervalLoss OBJECT-TYPE
			SYNTAX PerfIntervalCount
			UNITS "seconds"
			MAX-ACCESS read-only
			STATUS current
			DESCRIPTION
				"Count of seconds in the interval when there was
				Loss of Signal."
			::= { sheAdslAturIntervalEntry 5 }

		
--   1.3.6.1.4.1.231.7.1.2.2.1.6.1.1.19.1.6
		sheAdslAturIntervalLprs OBJECT-TYPE
			SYNTAX PerfIntervalCount
			UNITS "seconds"
			MAX-ACCESS read-only
			STATUS current
			DESCRIPTION
				"Count of seconds in the interval when there was
				Loss of Power."
			::= { sheAdslAturIntervalEntry 6 }

		
--   1.3.6.1.4.1.231.7.1.2.2.1.6.1.1.19.1.7
		sheAdslAturIntervalESs OBJECT-TYPE
			SYNTAX PerfIntervalCount
			UNITS "seconds"
			MAX-ACCESS read-only
			STATUS current
			DESCRIPTION
				"Count of Errored Seconds in the interval.
				The errored second parameter is a count of
				one-second intervals containing one or more crc
				anomalies, or one or more los or sef defects."
			::= { sheAdslAturIntervalEntry 7 }

		
--   1.3.6.1.4.1.231.7.1.2.2.1.6.1.1.19.1.8
		sheAdslAturIntervalSesL OBJECT-TYPE
			SYNTAX PerfIntervalCount
			UNITS "seconds"
			MAX-ACCESS read-only
			STATUS current
			DESCRIPTION
				"For the each interval, adslAturIntervalSesL
				reports the number of seconds during which
				there have been severely errored seconds-line."
			::= { sheAdslAturIntervalEntry 8 }

		
--   1.3.6.1.4.1.231.7.1.2.2.1.6.1.1.19.1.9
		sheAdslAturIntervalUasL OBJECT-TYPE
			SYNTAX PerfIntervalCount
			UNITS "seconds"
			MAX-ACCESS read-only
			STATUS current
			DESCRIPTION
				"For the each interval, adslAturIntervalUasL
				reports the number of seconds during which
				there have been unavailable seconds-line."
			::= { sheAdslAturIntervalEntry 9 }

		
--   1.3.6.1.4.1.231.7.1.2.2.1.6.1.1.20
		sheAdslAturChanPerfDataTable OBJECT-TYPE
			SYNTAX SEQUENCE OF SheAdslAturChanPerfDataEntry
			MAX-ACCESS not-accessible
			STATUS current
			DESCRIPTION
				"This table provides one row for each ATUR channel."
			::= { sheAdslLineMIB 20 }

		
--   1.3.6.1.4.1.231.7.1.2.2.1.6.1.1.20.1
		sheAdslAturChanPerfDataEntry OBJECT-TYPE
			SYNTAX SheAdslAturChanPerfDataEntry
			MAX-ACCESS not-accessible
			STATUS current
			DESCRIPTION
				"An entry in adslAturChanPerfDataTable.
				This table is only supported by NE releases smaller then R2.5 (NO dualLatency support)!!"
			INDEX { ifIndex }
			::= { sheAdslAturChanPerfDataTable 1 }

		
		SheAdslAturChanPerfDataEntry ::=
			SEQUENCE { 
				sheAdslAturChanPerfDataReceivedBlks
					Counter32,
				sheAdslAturChanPerfDataTransmittedBlks
					Counter32,
				sheAdslAturChanPerfDataCorrectedBlks
					Counter32,
				sheAdslAturChanPerfDataUncorrectBlks
					Counter32,
				sheAdslAturChanPerfDataExtnNcd
					Gauge32,
				sheAdslAturChanPerfDataExtnHec
					Gauge32,
				sheAdslAturChanPerfDataPerfValidIntervals
					INTEGER,
				sheAdslAturChanPerfDataPerfInvalidIntervals
					INTEGER,
				sheAdslAturChanPerfDataCurr15MinTimeElapsed
					AdslPerfTimeElapsed,
				sheAdslAturChanPerfDataCurr15MinReceivedBlks
					PerfCurrentCount,
				sheAdslAturChanPerfDataCurr15MinTransmittedBlks
					PerfCurrentCount,
				sheAdslAturChanPerfDataCurr15MinCorrectedBlks
					PerfCurrentCount,
				sheAdslAturChanPerfDataCurr15MinUncorrectBlks
					PerfCurrentCount,
				sheAdslAturChanPerfDataExtnCurr15MinNcd
					Gauge32,
				sheAdslAturChanPerfDataExtnCurr15MinHec
					Gauge32,
				sheAdslAturChanPerfDataCurr1DayTimeElapsed
					AdslPerfTimeElapsed,
				sheAdslAturChanPerfDataCurr1DayReceivedBlks
					AdslPerfCurrDayCount,
				sheAdslAturChanPerfDataCurr1DayTransmittedBlks
					AdslPerfCurrDayCount,
				sheAdslAturChanPerfDataCurr1DayCorrectedBlks
					AdslPerfCurrDayCount,
				sheAdslAturChanPerfDataCurr1DayUncorrectBlks
					AdslPerfCurrDayCount,
				sheAdslAturChanPerfDataExtnCurr1DayNcd
					Gauge32,
				sheAdslAturChanPerfDataExtnCurr1DayHec
					Gauge32,
				sheAdslAturChanPerfDataPrev1DayMoniSecs
					INTEGER,
				sheAdslAturChanPerfDataPrev1DayReceivedBlks
					AdslPerfPrevDayCount,
				sheAdslAturChanPerfDataPrev1DayTransmittedBlks
					AdslPerfPrevDayCount,
				sheAdslAturChanPerfDataPrev1DayCorrectedBlks
					AdslPerfPrevDayCount,
				sheAdslAturChanPerfDataPrev1DayUncorrectBlks
					AdslPerfPrevDayCount,
				sheAdslAturChanPerfDataExtnPrev1DayNcd
					Gauge32,
				sheAdslAturChanPerfDataExtnPrev1DayHec
					Gauge32
			 }

--   1.3.6.1.4.1.231.7.1.2.2.1.6.1.1.20.1.1
		sheAdslAturChanPerfDataReceivedBlks OBJECT-TYPE
			SYNTAX Counter32
			MAX-ACCESS read-only
			STATUS current
			DESCRIPTION
				"Count of all encoded blocks received on this channel
				since agent reset."
			::= { sheAdslAturChanPerfDataEntry 1 }

		
--   1.3.6.1.4.1.231.7.1.2.2.1.6.1.1.20.1.2
		sheAdslAturChanPerfDataTransmittedBlks OBJECT-TYPE
			SYNTAX Counter32
			MAX-ACCESS read-only
			STATUS current
			DESCRIPTION
				"Count of all encoded blocks transmitted on this
				channel since agent reset."
			::= { sheAdslAturChanPerfDataEntry 2 }

		
--   1.3.6.1.4.1.231.7.1.2.2.1.6.1.1.20.1.3
		sheAdslAturChanPerfDataCorrectedBlks OBJECT-TYPE
			SYNTAX Counter32
			MAX-ACCESS read-only
			STATUS current
			DESCRIPTION
				"Count of all blocks received with errors that were
				corrected since agent reset.  These blocks are passed
				on as good data."
			::= { sheAdslAturChanPerfDataEntry 3 }

		
--   1.3.6.1.4.1.231.7.1.2.2.1.6.1.1.20.1.4
		sheAdslAturChanPerfDataUncorrectBlks OBJECT-TYPE
			SYNTAX Counter32
			MAX-ACCESS read-only
			STATUS current
			DESCRIPTION
				"Count of all blocks received with uncorrectable
				errors since agent reset."
			::= { sheAdslAturChanPerfDataEntry 4 }

		
--   1.3.6.1.4.1.231.7.1.2.2.1.6.1.1.20.1.5
		sheAdslAturChanPerfDataExtnNcd OBJECT-TYPE
			SYNTAX Gauge32
			MAX-ACCESS read-only
			STATUS current
			DESCRIPTION
				"Number of packets with no cell delineation(NCD) error on this channel."
			::= { sheAdslAturChanPerfDataEntry 5 }

		
--   1.3.6.1.4.1.231.7.1.2.2.1.6.1.1.20.1.6
		sheAdslAturChanPerfDataExtnHec OBJECT-TYPE
			SYNTAX Gauge32
			MAX-ACCESS read-only
			STATUS current
			DESCRIPTION
				"Number of packets with Header error check (HEC) error on this channel."
			::= { sheAdslAturChanPerfDataEntry 6 }

		
--   1.3.6.1.4.1.231.7.1.2.2.1.6.1.1.20.1.7
		sheAdslAturChanPerfDataPerfValidIntervals OBJECT-TYPE
			SYNTAX INTEGER (0..96)
			MAX-ACCESS read-only
			STATUS current
			DESCRIPTION
				"The number of previous 15-minute intervals in the
				interval table for which data was collected.  Given
				that <n> is the maximum # of intervals supported.
				The value will be <n> unless the measurement was
				(re-)started within the last (<n>*15) minutes, in which
				case the value will be the number of complete 15
				minute intervals for which the agent has at least
				some data. In certain cases (e.g., in the case
				where the agent is a proxy) it is possible that some
				intervals are unavailable.  In this case, this
				interval is the maximum interval number for
				which data is available."
			::= { sheAdslAturChanPerfDataEntry 7 }

		
--   1.3.6.1.4.1.231.7.1.2.2.1.6.1.1.20.1.8
		sheAdslAturChanPerfDataPerfInvalidIntervals OBJECT-TYPE
			SYNTAX INTEGER (0..96)
			MAX-ACCESS read-only
			STATUS current
			DESCRIPTION
				"The number of intervals in the range from
				0 to the value of adslAturChanPerfValidIntervals
				for which no data is available. This object
				will typically be zero except in cases where
				the data for some intervals are not available
				(e.g., in proxy situations)."
			::= { sheAdslAturChanPerfDataEntry 8 }

		
--   1.3.6.1.4.1.231.7.1.2.2.1.6.1.1.20.1.9
		sheAdslAturChanPerfDataCurr15MinTimeElapsed OBJECT-TYPE
			SYNTAX AdslPerfTimeElapsed (0..899)
			UNITS "seconds"
			MAX-ACCESS read-only
			STATUS current
			DESCRIPTION
				"Total elapsed seconds in this interval.
				A full interval is 900 seconds."
			::= { sheAdslAturChanPerfDataEntry 9 }

		
--   1.3.6.1.4.1.231.7.1.2.2.1.6.1.1.20.1.10
		sheAdslAturChanPerfDataCurr15MinReceivedBlks OBJECT-TYPE
			SYNTAX PerfCurrentCount
			MAX-ACCESS read-only
			STATUS current
			DESCRIPTION
				"Count of all encoded blocks received on this
				channel within the current 15 minute interval."
			::= { sheAdslAturChanPerfDataEntry 10 }

		
--   1.3.6.1.4.1.231.7.1.2.2.1.6.1.1.20.1.11
		sheAdslAturChanPerfDataCurr15MinTransmittedBlks OBJECT-TYPE
			SYNTAX PerfCurrentCount
			MAX-ACCESS read-only
			STATUS current
			DESCRIPTION
				"Count of all encoded blocks transmitted on this
				channel within the current 15 minute interval."
			::= { sheAdslAturChanPerfDataEntry 11 }

		
--   1.3.6.1.4.1.231.7.1.2.2.1.6.1.1.20.1.12
		sheAdslAturChanPerfDataCurr15MinCorrectedBlks OBJECT-TYPE
			SYNTAX PerfCurrentCount
			MAX-ACCESS read-only
			STATUS current
			DESCRIPTION
				"Count of all blocks received with errors that were
				corrected on this channel within the current 15 minute
				interval."
			::= { sheAdslAturChanPerfDataEntry 12 }

		
--   1.3.6.1.4.1.231.7.1.2.2.1.6.1.1.20.1.13
		sheAdslAturChanPerfDataCurr15MinUncorrectBlks OBJECT-TYPE
			SYNTAX PerfCurrentCount
			MAX-ACCESS read-only
			STATUS current
			DESCRIPTION
				"Count of all blocks received with uncorrectable
				errors on this channel within the current 15 minute
				interval."
			::= { sheAdslAturChanPerfDataEntry 13 }

		
--   1.3.6.1.4.1.231.7.1.2.2.1.6.1.1.20.1.14
		sheAdslAturChanPerfDataExtnCurr15MinNcd OBJECT-TYPE
			SYNTAX Gauge32
			MAX-ACCESS read-only
			STATUS current
			DESCRIPTION
				"Number of packets with no cell delineation(NCD) error on this channel within the current 15 minute time interval."
			::= { sheAdslAturChanPerfDataEntry 14 }

		
--   1.3.6.1.4.1.231.7.1.2.2.1.6.1.1.20.1.15
		sheAdslAturChanPerfDataExtnCurr15MinHec OBJECT-TYPE
			SYNTAX Gauge32
			MAX-ACCESS read-only
			STATUS current
			DESCRIPTION
				"Number of packets with Header error check (HEC) error on this channel within the current 15 minute time interval."
			::= { sheAdslAturChanPerfDataEntry 15 }

		
--   1.3.6.1.4.1.231.7.1.2.2.1.6.1.1.20.1.16
		sheAdslAturChanPerfDataCurr1DayTimeElapsed OBJECT-TYPE
			SYNTAX AdslPerfTimeElapsed (0..86399)
			UNITS "seconds"
			MAX-ACCESS read-only
			STATUS current
			DESCRIPTION
				"Number of seconds that have elapsed since the
				beginning of the current 1-day interval."
			::= { sheAdslAturChanPerfDataEntry 16 }

		
--   1.3.6.1.4.1.231.7.1.2.2.1.6.1.1.20.1.17
		sheAdslAturChanPerfDataCurr1DayReceivedBlks OBJECT-TYPE
			SYNTAX AdslPerfCurrDayCount
			MAX-ACCESS read-only
			STATUS current
			DESCRIPTION
				"Count of all encoded blocks received on this
				channel during the current day as measured by
				adslAturChanPerfCurr1DayTimeElapsed."
			::= { sheAdslAturChanPerfDataEntry 17 }

		
--   1.3.6.1.4.1.231.7.1.2.2.1.6.1.1.20.1.18
		sheAdslAturChanPerfDataCurr1DayTransmittedBlks OBJECT-TYPE
			SYNTAX AdslPerfCurrDayCount
			MAX-ACCESS read-only
			STATUS current
			DESCRIPTION
				"Count of all encoded blocks transmitted on this
				channel during the current day as measured by
				adslAturChanPerfCurr1DayTimeElapsed."
			::= { sheAdslAturChanPerfDataEntry 18 }

		
--   1.3.6.1.4.1.231.7.1.2.2.1.6.1.1.20.1.19
		sheAdslAturChanPerfDataCurr1DayCorrectedBlks OBJECT-TYPE
			SYNTAX AdslPerfCurrDayCount
			MAX-ACCESS read-only
			STATUS current
			DESCRIPTION
				"Count of all blocks received with errors that were
				corrected on this channel during the current day as
				measured by adslAturChanPerfCurr1DayTimeElapsed."
			::= { sheAdslAturChanPerfDataEntry 19 }

		
--   1.3.6.1.4.1.231.7.1.2.2.1.6.1.1.20.1.20
		sheAdslAturChanPerfDataCurr1DayUncorrectBlks OBJECT-TYPE
			SYNTAX AdslPerfCurrDayCount
			MAX-ACCESS read-only
			STATUS current
			DESCRIPTION
				"Count of all blocks received with uncorrectable
				errors on this channel during the current day as
				measured by adslAturChanPerfCurr1DayTimeElapsed."
			::= { sheAdslAturChanPerfDataEntry 20 }

		
--   1.3.6.1.4.1.231.7.1.2.2.1.6.1.1.20.1.21
		sheAdslAturChanPerfDataExtnCurr1DayNcd OBJECT-TYPE
			SYNTAX Gauge32
			MAX-ACCESS read-only
			STATUS current
			DESCRIPTION
				"Number of packets with no cell delineation (NCD) error on this channel within the current 1 day time interval."
			::= { sheAdslAturChanPerfDataEntry 21 }

		
--   1.3.6.1.4.1.231.7.1.2.2.1.6.1.1.20.1.22
		sheAdslAturChanPerfDataExtnCurr1DayHec OBJECT-TYPE
			SYNTAX Gauge32
			MAX-ACCESS read-only
			STATUS current
			DESCRIPTION
				"Number of packets with Header error check (HEC) error on this channel within the current 1 day time interval."
			::= { sheAdslAturChanPerfDataEntry 22 }

		
--   1.3.6.1.4.1.231.7.1.2.2.1.6.1.1.20.1.23
		sheAdslAturChanPerfDataPrev1DayMoniSecs OBJECT-TYPE
			SYNTAX INTEGER (0..86400)
			UNITS "seconds"
			MAX-ACCESS read-only
			STATUS current
			DESCRIPTION
				"The amount of time in the previous 1-day interval
				over which the performance monitoring information
				is actually counted. This value will be the same as
				the interval duration except in a situation where
				performance monitoring data could not be collected
				for any reason."
			::= { sheAdslAturChanPerfDataEntry 23 }

		
--   1.3.6.1.4.1.231.7.1.2.2.1.6.1.1.20.1.24
		sheAdslAturChanPerfDataPrev1DayReceivedBlks OBJECT-TYPE
			SYNTAX AdslPerfPrevDayCount
			MAX-ACCESS read-only
			STATUS current
			DESCRIPTION
				"Count of all encoded blocks received on this
				channel within the most recent previous 1-day
				period."
			::= { sheAdslAturChanPerfDataEntry 24 }

		
--   1.3.6.1.4.1.231.7.1.2.2.1.6.1.1.20.1.25
		sheAdslAturChanPerfDataPrev1DayTransmittedBlks OBJECT-TYPE
			SYNTAX AdslPerfPrevDayCount
			MAX-ACCESS read-only
			STATUS current
			DESCRIPTION
				"Count of all encoded blocks transmitted on this
				channel within the most recent previous 1-day
				period."
			::= { sheAdslAturChanPerfDataEntry 25 }

		
--   1.3.6.1.4.1.231.7.1.2.2.1.6.1.1.20.1.26
		sheAdslAturChanPerfDataPrev1DayCorrectedBlks OBJECT-TYPE
			SYNTAX AdslPerfPrevDayCount
			MAX-ACCESS read-only
			STATUS current
			DESCRIPTION
				"Count of all blocks received with errors that were
				corrected on this channel within the most recent
				previous 1-day period."
			::= { sheAdslAturChanPerfDataEntry 26 }

		
--   1.3.6.1.4.1.231.7.1.2.2.1.6.1.1.20.1.27
		sheAdslAturChanPerfDataPrev1DayUncorrectBlks OBJECT-TYPE
			SYNTAX AdslPerfPrevDayCount
			MAX-ACCESS read-only
			STATUS current
			DESCRIPTION
				"Count of all blocks received with uncorrectable
				errors on this channel within the most recent previous
				1-day period."
			::= { sheAdslAturChanPerfDataEntry 27 }

		
--   1.3.6.1.4.1.231.7.1.2.2.1.6.1.1.20.1.28
		sheAdslAturChanPerfDataExtnPrev1DayNcd OBJECT-TYPE
			SYNTAX Gauge32
			MAX-ACCESS read-only
			STATUS current
			DESCRIPTION
				"Number of packets with no cell delineation (NCD) error on this channel within the most recent previous period."
			::= { sheAdslAturChanPerfDataEntry 28 }

		
--   1.3.6.1.4.1.231.7.1.2.2.1.6.1.1.20.1.29
		sheAdslAturChanPerfDataExtnPrev1DayHec OBJECT-TYPE
			SYNTAX Gauge32
			MAX-ACCESS read-only
			STATUS current
			DESCRIPTION
				"Number of packets with Header error check (HEC) error on this channel within the most recent previous period."
			::= { sheAdslAturChanPerfDataEntry 29 }

		
--   1.3.6.1.4.1.231.7.1.2.2.1.6.1.1.21
		sheAdslAturChanIntervalTable OBJECT-TYPE
			SYNTAX SEQUENCE OF SheAdslAturChanIntervalEntry
			MAX-ACCESS not-accessible
			STATUS current
			DESCRIPTION
				"This table provides one row for each ATUR channel's
				performance data collection interval.
				"
			::= { sheAdslLineMIB 21 }

		
--   1.3.6.1.4.1.231.7.1.2.2.1.6.1.1.21.1
		sheAdslAturChanIntervalEntry OBJECT-TYPE
			SYNTAX SheAdslAturChanIntervalEntry
			MAX-ACCESS not-accessible
			STATUS current
			DESCRIPTION
				"An entry in the adslAturIntervalTable.
				This table is only supported by NE releases smaller then R2.5 (NO dualLatency support)!!"
			INDEX { ifIndex, sheAdslAturChanIntervalNumber }
			::= { sheAdslAturChanIntervalTable 1 }

		
		SheAdslAturChanIntervalEntry ::=
			SEQUENCE { 
				sheAdslAturChanIntervalNumber
					INTEGER,
				sheAdslAturChanIntervalValidData
					TruthValue,
				sheAdslAturChanIntervalEndTime
					Unsigned32,
				sheAdslAturChanIntervalReceivedBlks
					PerfIntervalCount,
				sheAdslAturChanIntervalTransmittedBlks
					PerfIntervalCount,
				sheAdslAturChanIntervalCorrectedBlks
					PerfIntervalCount,
				sheAdslAturChanIntervalUncorrectBlks
					PerfIntervalCount,
				sheAdslAturChanIntervalNcd
					Gauge32,
				sheAdslAturChanIntervalHec
					Gauge32
			 }

--   1.3.6.1.4.1.231.7.1.2.2.1.6.1.1.21.1.1
		sheAdslAturChanIntervalNumber OBJECT-TYPE
			SYNTAX INTEGER (1..96)
			MAX-ACCESS read-only
			STATUS current
			DESCRIPTION
				"Performance Data Interval number 1 is the
				the most recent previous interval; interval
				96 is 24 hours ago.  Intervals 2..96 are
				optional."
			::= { sheAdslAturChanIntervalEntry 1 }

		
--   1.3.6.1.4.1.231.7.1.2.2.1.6.1.1.21.1.2
		sheAdslAturChanIntervalValidData OBJECT-TYPE
			SYNTAX TruthValue
			MAX-ACCESS read-only
			STATUS current
			DESCRIPTION
				"This variable indicates if the data for this
				interval is valid."
			::= { sheAdslAturChanIntervalEntry 2 }

		
--   1.3.6.1.4.1.231.7.1.2.2.1.6.1.1.21.1.3
		sheAdslAturChanIntervalEndTime OBJECT-TYPE
			SYNTAX Unsigned32
			MAX-ACCESS read-only
			STATUS current
			DESCRIPTION
				"This variable indicates the time of storing this interval."
			::= { sheAdslAturChanIntervalEntry 3 }

		
--   1.3.6.1.4.1.231.7.1.2.2.1.6.1.1.21.1.4
		sheAdslAturChanIntervalReceivedBlks OBJECT-TYPE
			SYNTAX PerfIntervalCount
			MAX-ACCESS read-only
			STATUS current
			DESCRIPTION
				"Count of all encoded blocks received on this channel
				during this interval."
			::= { sheAdslAturChanIntervalEntry 4 }

		
--   1.3.6.1.4.1.231.7.1.2.2.1.6.1.1.21.1.5
		sheAdslAturChanIntervalTransmittedBlks OBJECT-TYPE
			SYNTAX PerfIntervalCount
			MAX-ACCESS read-only
			STATUS current
			DESCRIPTION
				"Count of all encoded blocks transmitted on this
				channel during this interval."
			::= { sheAdslAturChanIntervalEntry 5 }

		
--   1.3.6.1.4.1.231.7.1.2.2.1.6.1.1.21.1.6
		sheAdslAturChanIntervalCorrectedBlks OBJECT-TYPE
			SYNTAX PerfIntervalCount
			MAX-ACCESS read-only
			STATUS current
			DESCRIPTION
				"Count of all blocks received with errors that were
				corrected on this channel during this interval."
			::= { sheAdslAturChanIntervalEntry 6 }

		
--   1.3.6.1.4.1.231.7.1.2.2.1.6.1.1.21.1.7
		sheAdslAturChanIntervalUncorrectBlks OBJECT-TYPE
			SYNTAX PerfIntervalCount
			MAX-ACCESS read-only
			STATUS current
			DESCRIPTION
				"Count of all blocks received with uncorrectable
				errors on this channel during this interval."
			::= { sheAdslAturChanIntervalEntry 7 }

		
--   1.3.6.1.4.1.231.7.1.2.2.1.6.1.1.21.1.8
		sheAdslAturChanIntervalNcd OBJECT-TYPE
			SYNTAX Gauge32
			MAX-ACCESS read-only
			STATUS current
			DESCRIPTION
				"Indicates count of no cell delineation on this channel for this interval."
			::= { sheAdslAturChanIntervalEntry 8 }

		
--   1.3.6.1.4.1.231.7.1.2.2.1.6.1.1.21.1.9
		sheAdslAturChanIntervalHec OBJECT-TYPE
			SYNTAX Gauge32
			MAX-ACCESS read-only
			STATUS current
			DESCRIPTION
				"Indicates Header error check counter on this channel during this interval."
			::= { sheAdslAturChanIntervalEntry 9 }

		
--   1.3.6.1.4.1.231.7.1.2.2.1.6.1.1.22
		sheAdslLineAlarmConfProfileTable OBJECT-TYPE
			SYNTAX SEQUENCE OF SheAdslLineAlarmConfProfileEntry
			MAX-ACCESS not-accessible
			STATUS current
			DESCRIPTION
				"This table contains information on the ADSL line
				configuration.  One entry in this table reflects a
				profile defined by a manager which can be used to
				configure the modem for a physical line"
			::= { sheAdslLineMIB 22 }

		
--   1.3.6.1.4.1.231.7.1.2.2.1.6.1.1.22.1
		sheAdslLineAlarmConfProfileEntry OBJECT-TYPE
			SYNTAX SheAdslLineAlarmConfProfileEntry
			MAX-ACCESS not-accessible
			STATUS current
			DESCRIPTION
				"Each entry consists of a list of parameters that
				represents the configuration of an ADSL modem.
				
				'Dynamic' profiles are implemented. A default
				profile will always exist.  This profile's name will
				be set to `DEFVAL' and its parameters will be set to
				vendor specific values, unless otherwise specified
				in this document.
				
				"
			INDEX { sheAdslLineAlarmConfProfileIndex }
			::= { sheAdslLineAlarmConfProfileTable 1 }

		
		SheAdslLineAlarmConfProfileEntry ::=
			SEQUENCE { 
				sheAdslLineAlarmConfProfileIndex
					Integer32,
				sheAdslLineAlarmConfProfileName
					SnmpAdminString,
				sheAdslLineAlarmConfProfileOpStateTrapEnable
					TruthValue,
				sheAdslLineAlarmConfProfileAtucThreshFastRateUp
					Unsigned32,
				sheAdslLineAlarmConfProfileAtucThreshInterleaveRateUp
					Unsigned32,
				sheAdslLineAlarmConfProfileAtucThreshFastRateDown
					Unsigned32,
				sheAdslLineAlarmConfProfileAtucThreshInterleaveRateDown
					Unsigned32,
				sheAdslLineAlarmConfProfileAtucInitFailureTrapEnable
					TruthValue,
				sheAdslLineAlarmConfProfileAtucThresh15MinLofs
					INTEGER,
				sheAdslLineAlarmConfProfileAtucThresh15MinLoss
					INTEGER,
				sheAdslLineAlarmConfProfileAtucThresh15MinLols
					INTEGER,
				sheAdslLineAlarmConfProfileAtucThresh15MinLprs
					INTEGER,
				sheAdslLineAlarmConfProfileAtucThresh15MinESs
					INTEGER,
				sheAdslLineAlarmConfProfileAtucThresh15MinSesL
					INTEGER,
				sheAdslLineAlarmConfProfileAtucThresh15MinUasL
					INTEGER,
				sheAdslLineAlarmConfProfileAtucThresh15MinFailFastR
					INTEGER,
				sheAdslLineAlarmConfProfileAturThreshFastRateUp
					Unsigned32,
				sheAdslLineAlarmConfProfileAturThreshInterleaveRateUp
					Unsigned32,
				sheAdslLineAlarmConfProfileAturThreshFastRateDown
					Unsigned32,
				sheAdslLineAlarmConfProfileAturThreshInterleaveRateDown
					Unsigned32,
				sheAdslLineAlarmConfProfileAturThresh15MinLofs
					INTEGER,
				sheAdslLineAlarmConfProfileAturThresh15MinLoss
					INTEGER,
				sheAdslLineAlarmConfProfileAturThresh15MinLprs
					INTEGER,
				sheAdslLineAlarmConfProfileAturThresh15MinESs
					INTEGER,
				sheAdslLineAlarmConfProfileAturThresh15MinSesL
					INTEGER,
				sheAdslLineAlarmConfProfileAturThresh15MinUasL
					INTEGER
			 }

--   1.3.6.1.4.1.231.7.1.2.2.1.6.1.1.22.1.1
		sheAdslLineAlarmConfProfileIndex OBJECT-TYPE
			SYNTAX Integer32 (1..65535)
			MAX-ACCESS read-only
			STATUS current
			DESCRIPTION
				"Tableindex."
			::= { sheAdslLineAlarmConfProfileEntry 1 }

		
--   1.3.6.1.4.1.231.7.1.2.2.1.6.1.1.22.1.2
		sheAdslLineAlarmConfProfileName OBJECT-TYPE
			SYNTAX SnmpAdminString (SIZE (1..32))
			MAX-ACCESS read-only
			STATUS current
			DESCRIPTION
				"This object is used by the line alarm configuration table in order to identify
				a row of this table.
				
				Dynamic profiles are implemented. The profile name is user specified.
				The system will always provide a default profile whose name is `DEFVAL'.
				
				This characters are not allowed:  space : ? leading numbers "
			::= { sheAdslLineAlarmConfProfileEntry 2 }

		
--   1.3.6.1.4.1.231.7.1.2.2.1.6.1.1.22.1.3
		sheAdslLineAlarmConfProfileOpStateTrapEnable OBJECT-TYPE
			SYNTAX TruthValue
			MAX-ACCESS read-only
			STATUS current
			DESCRIPTION
				"Enables and disables the OpStateChangeTrap."
			DEFVAL { false }
			::= { sheAdslLineAlarmConfProfileEntry 3 }

		
--   1.3.6.1.4.1.231.7.1.2.2.1.6.1.1.22.1.4
		sheAdslLineAlarmConfProfileAtucThreshFastRateUp OBJECT-TYPE
			SYNTAX Unsigned32 (0..65535)
			UNITS "bps"
			MAX-ACCESS read-only
			STATUS current
			DESCRIPTION
				"Applies to `Fast' channels only.
				Configured change in rate causing an adslAtucRateChangeTrap.
				A trap is produced when: ChanCurrTxRate >= ChanPrevTxRate plus the value of
				this object. A value of `0' will disable the trap."
			DEFVAL { 0 }
			::= { sheAdslLineAlarmConfProfileEntry 4 }

		
--   1.3.6.1.4.1.231.7.1.2.2.1.6.1.1.22.1.5
		sheAdslLineAlarmConfProfileAtucThreshInterleaveRateUp OBJECT-TYPE
			SYNTAX Unsigned32 (0..65535)
			UNITS "bps"
			MAX-ACCESS read-only
			STATUS current
			DESCRIPTION
				"Applies to `Interleave' channels only.
				Configured change in rate causing an adslAtucRateChangeTrap.  
				A trap is produced when: ChanCurrTxRate >= ChanPrevTxRate plus the value of
				this object. A value of `0' will disable the trap."
			DEFVAL { 0 }
			::= { sheAdslLineAlarmConfProfileEntry 5 }

		
--   1.3.6.1.4.1.231.7.1.2.2.1.6.1.1.22.1.6
		sheAdslLineAlarmConfProfileAtucThreshFastRateDown OBJECT-TYPE
			SYNTAX Unsigned32 (0..65535)
			UNITS "bps"
			MAX-ACCESS read-only
			STATUS current
			DESCRIPTION
				"Applies to `Fast' channels only.
				Configured change in rate causing an adslAtucRateChangeTrap.  
				A trap is produced when: ChanCurrTxRate <= ChanPrevTxRate minus the value of
				this object. A value of `0' will disable the trap."
			DEFVAL { 0 }
			::= { sheAdslLineAlarmConfProfileEntry 6 }

		
--   1.3.6.1.4.1.231.7.1.2.2.1.6.1.1.22.1.7
		sheAdslLineAlarmConfProfileAtucThreshInterleaveRateDown OBJECT-TYPE
			SYNTAX Unsigned32 (0..65535)
			UNITS "bps"
			MAX-ACCESS read-only
			STATUS current
			DESCRIPTION
				"Applies to `Interleave' channels only.
				Configured change in rate causing an adslAtucRateChangeTrap.  
				A trap is produced when:ChanCurrTxRate <= ChanPrevTxRate minus the value of
				this object. A value of `0' will disable the trap."
			DEFVAL { 0 }
			::= { sheAdslLineAlarmConfProfileEntry 7 }

		
--   1.3.6.1.4.1.231.7.1.2.2.1.6.1.1.22.1.8
		sheAdslLineAlarmConfProfileAtucInitFailureTrapEnable OBJECT-TYPE
			SYNTAX TruthValue
			MAX-ACCESS read-only
			STATUS current
			DESCRIPTION
				"Enables and disables the InitFailureTrap. This object is defaulted disable(2)."
			DEFVAL { false }
			::= { sheAdslLineAlarmConfProfileEntry 8 }

		
--   1.3.6.1.4.1.231.7.1.2.2.1.6.1.1.22.1.9
		sheAdslLineAlarmConfProfileAtucThresh15MinLofs OBJECT-TYPE
			SYNTAX INTEGER (0..900)
			UNITS "seconds"
			MAX-ACCESS read-only
			STATUS current
			DESCRIPTION
				"The number of Loss of Frame Seconds encountered by an ADSL interface within
				any given 15 minutes performance data collection period, which causes the SNMP
				agent to send an adslAtucPerfLofsThreshTrap.
				One trap will be sent per interval per interface.
				A value of `0' will disable the trap."
			DEFVAL { 0 }
			::= { sheAdslLineAlarmConfProfileEntry 9 }

		
--   1.3.6.1.4.1.231.7.1.2.2.1.6.1.1.22.1.10
		sheAdslLineAlarmConfProfileAtucThresh15MinLoss OBJECT-TYPE
			SYNTAX INTEGER (0..900)
			UNITS "seconds"
			MAX-ACCESS read-only
			STATUS current
			DESCRIPTION
				"The number of Loss of Signal Seconds encountered by an ADSL interface within 
				any given 15 minutes performance data collection period, which causes the SNMP 
				agent to send an adslAtucPerfLossThreshTrap.
				One trap will be sent per interval per interface.
				A value of `0' will disable the trap."
			DEFVAL { 0 }
			::= { sheAdslLineAlarmConfProfileEntry 10 }

		
--   1.3.6.1.4.1.231.7.1.2.2.1.6.1.1.22.1.11
		sheAdslLineAlarmConfProfileAtucThresh15MinLols OBJECT-TYPE
			SYNTAX INTEGER (0..900)
			UNITS "seconds"
			MAX-ACCESS read-only
			STATUS current
			DESCRIPTION
				"The number of Loss of Link Seconds encountered by an ADSL interface within 
				any given 15 minutes performance data collection period, which causes the SNMP 
				agent to send an adslAtucPerfLolsThreshTrap.
				One trap will be sent per interval per interface.
				A value of `0' will disable the trap."
			DEFVAL { 0 }
			::= { sheAdslLineAlarmConfProfileEntry 11 }

		
--   1.3.6.1.4.1.231.7.1.2.2.1.6.1.1.22.1.12
		sheAdslLineAlarmConfProfileAtucThresh15MinLprs OBJECT-TYPE
			SYNTAX INTEGER (0..900)
			UNITS "seconds"
			MAX-ACCESS read-only
			STATUS current
			DESCRIPTION
				"The number of Loss of Power Seconds encountered by an ADSL interface within 
				any given 15 minutes performance data collection period, which causes the SNMP 
				agent to send an adslAtucPerfLprsThreshTrap.
				One trap will be sent per interval per interface.
				A value of `0' will disable the trap."
			DEFVAL { 0 }
			::= { sheAdslLineAlarmConfProfileEntry 12 }

		
--   1.3.6.1.4.1.231.7.1.2.2.1.6.1.1.22.1.13
		sheAdslLineAlarmConfProfileAtucThresh15MinESs OBJECT-TYPE
			SYNTAX INTEGER (0..900)
			UNITS "seconds"
			MAX-ACCESS read-only
			STATUS current
			DESCRIPTION
				"The number of Errored Seconds encountered by an ADSL interface within any 
				given 15 minutes performance data collection period, which causes the SNMP 
				agent to send an adslAtucPerfESsThreshTrap.
				One trap will be sent per interval per interface.
				A value of `0' will disable the trap."
			DEFVAL { 0 }
			::= { sheAdslLineAlarmConfProfileEntry 13 }

		
--   1.3.6.1.4.1.231.7.1.2.2.1.6.1.1.22.1.14
		sheAdslLineAlarmConfProfileAtucThresh15MinSesL OBJECT-TYPE
			SYNTAX INTEGER (0..900)
			MAX-ACCESS read-only
			STATUS current
			DESCRIPTION
				"The number of Severe errored seconds encountered by an ADSL interface within 
				any giving 15 minutes performance data collection period, which cause the SNMP 
				agend to send an adslAtucPerfSesLTrap.
				One trap will be sent per interval per interface.
				A value of `0' will disable the trap.
				"
			DEFVAL { 0 }
			::= { sheAdslLineAlarmConfProfileEntry 14 }

		
--   1.3.6.1.4.1.231.7.1.2.2.1.6.1.1.22.1.15
		sheAdslLineAlarmConfProfileAtucThresh15MinUasL OBJECT-TYPE
			SYNTAX INTEGER (0..900)
			MAX-ACCESS read-only
			STATUS current
			DESCRIPTION
				"The number of Unavailable seconds encountered by an ADSL interface within 
				any giving 15 minutes performance data collection period, which cause the SNMP 
				agend to send an adslAtucPerfUasLTrap.
				One trap will be sent per interval per interface.
				A value of `0' will disable the trap.
				"
			DEFVAL { 0 }
			::= { sheAdslLineAlarmConfProfileEntry 15 }

		
--   1.3.6.1.4.1.231.7.1.2.2.1.6.1.1.22.1.16
		sheAdslLineAlarmConfProfileAtucThresh15MinFailFastR OBJECT-TYPE
			SYNTAX INTEGER (0..900)
			MAX-ACCESS read-only
			STATUS current
			DESCRIPTION
				"The number of failed retrains encountered by an ADSL interface within any giving 15 minutes performance data collection period, which cause the SNMP agent to send an adslAtucFailedFastRTrap.
				Not supported yet! "
			DEFVAL { 0 }
			::= { sheAdslLineAlarmConfProfileEntry 16 }

		
--   1.3.6.1.4.1.231.7.1.2.2.1.6.1.1.22.1.17
		sheAdslLineAlarmConfProfileAturThreshFastRateUp OBJECT-TYPE
			SYNTAX Unsigned32 (0..65535)
			UNITS "bps"
			MAX-ACCESS read-only
			STATUS current
			DESCRIPTION
				"Applies to `Fast' channels only. 
				Configured change in rate causing an adslAturRateChangeTrap. 
				A trap is produced when: 
				ChanCurrTxRate >= ChanPrevTxRate plus the value of this object. 
				A value of `0' will disable the trap."
			DEFVAL { 0 }
			::= { sheAdslLineAlarmConfProfileEntry 17 }

		
--   1.3.6.1.4.1.231.7.1.2.2.1.6.1.1.22.1.18
		sheAdslLineAlarmConfProfileAturThreshInterleaveRateUp OBJECT-TYPE
			SYNTAX Unsigned32 (0..65535)
			UNITS "bps"
			MAX-ACCESS read-only
			STATUS current
			DESCRIPTION
				"Applies to `Interleave' channels only. 
				Configured change in rate causing an adslAturRateChangeTrap.  
				A trap is produced when:
				ChanCurrTxRate >= ChanPrevTxRate plus the value of this object. 
				A value of `0' will disable the trap."
			DEFVAL { 0 }
			::= { sheAdslLineAlarmConfProfileEntry 18 }

		
--   1.3.6.1.4.1.231.7.1.2.2.1.6.1.1.22.1.19
		sheAdslLineAlarmConfProfileAturThreshFastRateDown OBJECT-TYPE
			SYNTAX Unsigned32 (0..65535)
			UNITS "bps"
			MAX-ACCESS read-only
			STATUS current
			DESCRIPTION
				"Applies to `Fast' channels only. 
				Configured change in rate causing an adslAturRateChangeTrap. 
				A trap is produced when:
				ChanCurrTxRate <= ChanPrevTxRate minus the value of this object. 
				A value of `0' will disable the trap."
			DEFVAL { 0 }
			::= { sheAdslLineAlarmConfProfileEntry 19 }

		
--   1.3.6.1.4.1.231.7.1.2.2.1.6.1.1.22.1.20
		sheAdslLineAlarmConfProfileAturThreshInterleaveRateDown OBJECT-TYPE
			SYNTAX Unsigned32 (0..65535)
			UNITS "bps"
			MAX-ACCESS read-only
			STATUS current
			DESCRIPTION
				"Applies to `Interleave' channels only. 
				Configured change in rate causing an adslAturRateChangeTrap.  
				A trap is produced when:
				ChanCurrTxRate <= ChanPrevTxRate minus the value of this object. 
				A value of `0' will disable the trap."
			DEFVAL { 0 }
			::= { sheAdslLineAlarmConfProfileEntry 20 }

		
--   1.3.6.1.4.1.231.7.1.2.2.1.6.1.1.22.1.21
		sheAdslLineAlarmConfProfileAturThresh15MinLofs OBJECT-TYPE
			SYNTAX INTEGER (0..900)
			UNITS "seconds"
			MAX-ACCESS read-only
			STATUS current
			DESCRIPTION
				"The number of Loss of Frame Seconds encountered by an ADSL interface within 
				any given 15 minutes performance data collection period, which causes the SNMP 
				agent to send an adslAturPerfLofsThreshTrap.
				One trap will be sent per interval per interface.
				A value of `0' will disable the trap."
			DEFVAL { 0 }
			::= { sheAdslLineAlarmConfProfileEntry 21 }

		
--   1.3.6.1.4.1.231.7.1.2.2.1.6.1.1.22.1.22
		sheAdslLineAlarmConfProfileAturThresh15MinLoss OBJECT-TYPE
			SYNTAX INTEGER (0..900)
			UNITS "seconds"
			MAX-ACCESS read-only
			STATUS current
			DESCRIPTION
				"The number of Loss of Signal Seconds encountered by an ADSL interface within 
				any given 15 minutes performance data collection period, which causes the SNMP 
				agent to send an adslAturPerfLossThreshTrap.
				One trap will be sent per interval per interface.
				A value of `0' will disable the trap."
			DEFVAL { 0 }
			::= { sheAdslLineAlarmConfProfileEntry 22 }

		
--   1.3.6.1.4.1.231.7.1.2.2.1.6.1.1.22.1.23
		sheAdslLineAlarmConfProfileAturThresh15MinLprs OBJECT-TYPE
			SYNTAX INTEGER (0..900)
			UNITS "seconds"
			MAX-ACCESS read-only
			STATUS current
			DESCRIPTION
				"The number of Loss of Power Seconds encountered by an ADSL interface within 
				any given 15 minutes performance data collection period, which causes the SNMP 
				agent to send an adslAturPerfLprsThreshTrap.
				One trap will be sent per interval per interface.
				A value of `0' will disable the trap."
			DEFVAL { 0 }
			::= { sheAdslLineAlarmConfProfileEntry 23 }

		
--   1.3.6.1.4.1.231.7.1.2.2.1.6.1.1.22.1.24
		sheAdslLineAlarmConfProfileAturThresh15MinESs OBJECT-TYPE
			SYNTAX INTEGER (0..900)
			UNITS "seconds"
			MAX-ACCESS read-only
			STATUS current
			DESCRIPTION
				"The number of Errored Seconds encountered by an ADSL interface within 
				any given 15 minutes performance data collection period, which causes the SNMP 
				agent to send an 
				adslAturPerfESsThreshTrap.
				One trap will be sent per interval per interface.
				A value of `0' will disable the trap."
			DEFVAL { 0 }
			::= { sheAdslLineAlarmConfProfileEntry 24 }

		
--   1.3.6.1.4.1.231.7.1.2.2.1.6.1.1.22.1.25
		sheAdslLineAlarmConfProfileAturThresh15MinSesL OBJECT-TYPE
			SYNTAX INTEGER (0..900)
			MAX-ACCESS read-only
			STATUS current
			DESCRIPTION
				"The number of Severe errored seconds encountered by an ADSL interface within 
				any given 15 minutes performance data collection period, which causes the SNMP 
				agent to send an adslAturPerfSesLThreshTrap.
				One trap will be sent per interval per interface.
				A value of `0' will disable the trap.
				"
			DEFVAL { 0 }
			::= { sheAdslLineAlarmConfProfileEntry 25 }

		
--   1.3.6.1.4.1.231.7.1.2.2.1.6.1.1.22.1.26
		sheAdslLineAlarmConfProfileAturThresh15MinUasL OBJECT-TYPE
			SYNTAX INTEGER (0..900)
			MAX-ACCESS read-only
			STATUS current
			DESCRIPTION
				"The number of Unavailable seconds encountered by an ADSL interface within 
				any giving 15 minutes performance data collection period, which cause the SNMP 
				agend to send an adslAturPerfUasLTrap.
				One trap will be sent per interval per interface.
				A value of `0' will disable the trap.
				"
			DEFVAL { 0 }
			::= { sheAdslLineAlarmConfProfileEntry 26 }

		
--   1.3.6.1.4.1.231.7.1.2.2.1.6.1.1.23
		sheAdslLineAlarmConfProfileControl OBJECT IDENTIFIER ::= { sheAdslLineMIB 23 }

		
--   1.3.6.1.4.1.231.7.1.2.2.1.6.1.1.23.1
		sheAdslLineAlarmConfProfileControlRequest OBJECT-TYPE
			SYNTAX SheAdslControlRequestType
			MAX-ACCESS read-write
			STATUS current
			DESCRIPTION
				"createAdslLineAlarmConfProfile:
				sheAdslLineAlarmConfProfileControlName
				...
				
				modifyAdslLineAlarmConfProfile:
				sheAdslLineAlarmConfProfileControlIndex
				sheAdslLineAlarmConfProfileControlName
				...
				
				deleteAdslLineAlarmConfProfile:
				sheAdslLineAlarmConfProfileControlIndex
				sheAdslLineAlarmConfProfileControlName
				"
			::= { sheAdslLineAlarmConfProfileControl 1 }

		
--   1.3.6.1.4.1.231.7.1.2.2.1.6.1.1.23.2
		sheAdslLineAlarmConfProfileControlIndex OBJECT-TYPE
			SYNTAX Integer32
			MAX-ACCESS read-write
			STATUS current
			DESCRIPTION
				"Index of the table entry to be configured. Needed for modify or delete."
			::= { sheAdslLineAlarmConfProfileControl 2 }

		
--   1.3.6.1.4.1.231.7.1.2.2.1.6.1.1.23.3
		sheAdslLineAlarmConfProfileControlStatus OBJECT-TYPE
			SYNTAX SheControlStatusType
			MAX-ACCESS read-only
			STATUS current
			DESCRIPTION
				"The status of a user command. 
				"
			::= { sheAdslLineAlarmConfProfileControl 3 }

		
--   1.3.6.1.4.1.231.7.1.2.2.1.6.1.1.23.4
		sheAdslLineAlarmConfProfileControlTimer OBJECT-TYPE
			SYNTAX Gauge32
			MAX-ACCESS read-only
			STATUS current
			DESCRIPTION
				"The maximum wait time for the manager for a long running user command. 
				"
			::= { sheAdslLineAlarmConfProfileControl 4 }

		
--   1.3.6.1.4.1.231.7.1.2.2.1.6.1.1.23.5
		sheAdslLineAlarmConfProfileControlReqResult OBJECT-TYPE
			SYNTAX SheAdslControlRequestResultType
			MAX-ACCESS read-only
			STATUS current
			DESCRIPTION
				"The result of the last user command."
			::= { sheAdslLineAlarmConfProfileControl 5 }

		
--   1.3.6.1.4.1.231.7.1.2.2.1.6.1.1.23.6
		sheAdslLineAlarmConfProfileControlTimeStamp OBJECT-TYPE
			SYNTAX Unsigned32
			UNITS "sec"
			MAX-ACCESS read-only
			STATUS current
			DESCRIPTION
				"The time stamp of the last command (end of command)."
			::= { sheAdslLineAlarmConfProfileControl 6 }

		
--   1.3.6.1.4.1.231.7.1.2.2.1.6.1.1.23.7
		sheAdslLineAlarmConfProfileControlName OBJECT-TYPE
			SYNTAX SnmpAdminString
			MAX-ACCESS read-write
			STATUS current
			DESCRIPTION
				"Descriptional name."
			::= { sheAdslLineAlarmConfProfileControl 7 }

		
--   1.3.6.1.4.1.231.7.1.2.2.1.6.1.1.23.8
		sheAdslLineAlarmConfProfileControlOpStateTrapEnable OBJECT-TYPE
			SYNTAX TruthValue
			MAX-ACCESS read-write
			STATUS current
			DESCRIPTION
				"Enables and disables the LineStateTrap."
			::= { sheAdslLineAlarmConfProfileControl 8 }

		
--   1.3.6.1.4.1.231.7.1.2.2.1.6.1.1.23.9
		sheAdslLineAlarmConfProfileControlAtucThreshFastRateUp OBJECT-TYPE
			SYNTAX Unsigned32 (0..65535)
			UNITS "bps"
			MAX-ACCESS read-write
			STATUS current
			DESCRIPTION
				"Applies to `Fast' channels only.
				Configured change in rate causing an
				adslAtucRateChangeTrap. A trap is produced when:
				ChanCurrTxRate >= ChanPrevTxRate plus the value of
				this object. A value of `0' will disable the trap."
			::= { sheAdslLineAlarmConfProfileControl 9 }

		
--   1.3.6.1.4.1.231.7.1.2.2.1.6.1.1.23.10
		sheAdslLineAlarmConfProfileControlAtucThreshInterleaveRateUp OBJECT-TYPE
			SYNTAX Unsigned32 (0..65535)
			UNITS "bps"
			MAX-ACCESS read-write
			STATUS current
			DESCRIPTION
				"Applies to `Interleave' channels only.
				Configured change in rate causing an
				adslAtucRateChangeTrap.  A trap is produced when:
				ChanCurrTxRate >= ChanPrevTxRate plus the value of
				this object. A value of `0' will disable the trap."
			::= { sheAdslLineAlarmConfProfileControl 10 }

		
--   1.3.6.1.4.1.231.7.1.2.2.1.6.1.1.23.11
		sheAdslLineAlarmConfProfileControlAtucThreshFastRateDown OBJECT-TYPE
			SYNTAX Unsigned32 (0..65535)
			UNITS "bps"
			MAX-ACCESS read-write
			STATUS current
			DESCRIPTION
				"Applies to `Fast' channels only.
				Configured change in rate causing an
				adslAtucRateChangeTrap.  A trap is produced when:
				ChanCurrTxRate <= ChanPrevTxRate minus the value of
				this object. A value of `0' will disable the trap."
			::= { sheAdslLineAlarmConfProfileControl 11 }

		
--   1.3.6.1.4.1.231.7.1.2.2.1.6.1.1.23.12
		sheAdslLineAlarmConfProfileControlAtucThreshInterleaveRateDown OBJECT-TYPE
			SYNTAX Unsigned32 (0..65535)
			UNITS "bps"
			MAX-ACCESS read-write
			STATUS current
			DESCRIPTION
				"Applies to `Interleave' channels only.
				Configured change in rate causing an
				adslAtucRateChangeTrap.  A trap is produced when:
				ChanCurrTxRate <= ChanPrevTxRate minus the value of
				this object. A value of `0' will disable the trap."
			::= { sheAdslLineAlarmConfProfileControl 12 }

		
--   1.3.6.1.4.1.231.7.1.2.2.1.6.1.1.23.13
		sheAdslLineAlarmConfProfileControlAtucInitFailureTrapEnable OBJECT-TYPE
			SYNTAX TruthValue
			MAX-ACCESS read-write
			STATUS current
			DESCRIPTION
				"Enables and disables the InitFailureTrap.  This
				object is defaulted disable(2)."
			::= { sheAdslLineAlarmConfProfileControl 13 }

		
--   1.3.6.1.4.1.231.7.1.2.2.1.6.1.1.23.14
		sheAdslLineAlarmConfProfileControlAtucThresh15MinLofs OBJECT-TYPE
			SYNTAX INTEGER (0..900)
			UNITS "seconds"
			MAX-ACCESS read-write
			STATUS current
			DESCRIPTION
				"The number of Loss of Frame Seconds
				encountered by an ADSL interface within any given 15
				minutes performance data collection period, which
				causes the SNMP agent to send an
				adslAtucPerfLofsThreshTrap.
				One trap will be sent per interval per interface.
				A value of `0' will disable the trap."
			::= { sheAdslLineAlarmConfProfileControl 14 }

		
--   1.3.6.1.4.1.231.7.1.2.2.1.6.1.1.23.15
		sheAdslLineAlarmConfProfileControlAtucThresh15MinLoss OBJECT-TYPE
			SYNTAX INTEGER (0..900)
			UNITS "seconds"
			MAX-ACCESS read-write
			STATUS current
			DESCRIPTION
				"The number of Loss of Signal Seconds
				encountered by an ADSL interface within any given 15
				minutes performance data collection period, which
				causes the SNMP agent to send an
				adslAtucPerfLossThreshTrap.
				One trap will be sent per interval per interface.
				A value of `0' will disable the trap."
			::= { sheAdslLineAlarmConfProfileControl 15 }

		
--   1.3.6.1.4.1.231.7.1.2.2.1.6.1.1.23.16
		sheAdslLineAlarmConfProfileControlAtucThresh15MinLols OBJECT-TYPE
			SYNTAX INTEGER (0..900)
			UNITS "seconds"
			MAX-ACCESS read-write
			STATUS current
			DESCRIPTION
				"The number of Loss of Link Seconds
				encountered by an ADSL interface within any given 15
				minutes performance data collection period, which
				causes the SNMP agent to send an
				adslAtucPerfLolsThreshTrap.
				One trap will be sent per interval per interface.
				A value of `0' will disable the trap."
			::= { sheAdslLineAlarmConfProfileControl 16 }

		
--   1.3.6.1.4.1.231.7.1.2.2.1.6.1.1.23.17
		sheAdslLineAlarmConfProfileControlAtucThresh15MinLprs OBJECT-TYPE
			SYNTAX INTEGER (0..900)
			UNITS "seconds"
			MAX-ACCESS read-write
			STATUS current
			DESCRIPTION
				"The number of Loss of Power Seconds
				encountered by an ADSL interface within any given 15
				minutes performance data collection period, which
				causes the SNMP agent to send an
				adslAtucPerfLprsThreshTrap.
				One trap will be sent per interval per interface.
				A value of `0' will disable the trap."
			::= { sheAdslLineAlarmConfProfileControl 17 }

		
--   1.3.6.1.4.1.231.7.1.2.2.1.6.1.1.23.18
		sheAdslLineAlarmConfProfileControlAtucThresh15MinESs OBJECT-TYPE
			SYNTAX INTEGER (0..900)
			UNITS "seconds"
			MAX-ACCESS read-write
			STATUS current
			DESCRIPTION
				"The number of Errored Seconds
				encountered by an ADSL interface within any given 15
				minutes performance data collection period, which
				causes the SNMP agent to send an
				adslAtucPerfESsThreshTrap.
				One trap will be sent per interval per interface.
				A value of `0' will disable the trap."
			::= { sheAdslLineAlarmConfProfileControl 18 }

		
--   1.3.6.1.4.1.231.7.1.2.2.1.6.1.1.23.19
		sheAdslLineAlarmConfProfileControlAtucThresh15MinSesL OBJECT-TYPE
			SYNTAX INTEGER (0..900)
			UNITS "seconds"
			MAX-ACCESS read-write
			STATUS current
			DESCRIPTION
				"The number of Errored Seconds
				encountered by an ADSL interface within any given 15
				minutes performance data collection period, which
				causes the SNMP agent to send an
				adslAtucPerfSesLThreshTrap.
				One trap will be sent per interval per interface.
				A value of `0' will disable the trap."
			::= { sheAdslLineAlarmConfProfileControl 19 }

		
--   1.3.6.1.4.1.231.7.1.2.2.1.6.1.1.23.20
		sheAdslLineAlarmConfProfileControlAtucThresh15MinUasL OBJECT-TYPE
			SYNTAX INTEGER (0..900)
			UNITS "seconds"
			MAX-ACCESS read-write
			STATUS current
			DESCRIPTION
				"The number of Errored Seconds
				encountered by an ADSL interface within any given 15
				minutes performance data collection period, which
				causes the SNMP agent to send an
				adslAtucPerfUasLThreshTrap.
				One trap will be sent per interval per interface.
				A value of `0' will disable the trap."
			::= { sheAdslLineAlarmConfProfileControl 20 }

		
--   1.3.6.1.4.1.231.7.1.2.2.1.6.1.1.23.21
		sheAdslLineAlarmConfProfileControlAtucThresh15MinFailFastR OBJECT-TYPE
			SYNTAX INTEGER (0..900)
			MAX-ACCESS read-write
			STATUS current
			DESCRIPTION
				"The number of failed retrains encountered by an ADSL interface within any giving 15 minutes performance data collection period, which cause the SNMP agent to send an adslAtucFailedFastRTrap."
			::= { sheAdslLineAlarmConfProfileControl 21 }

		
--   1.3.6.1.4.1.231.7.1.2.2.1.6.1.1.23.22
		sheAdslLineAlarmConfProfileControlAturThreshFastRateUp OBJECT-TYPE
			SYNTAX Unsigned32 (0..65535)
			UNITS "bps"
			MAX-ACCESS read-write
			STATUS current
			DESCRIPTION
				"Applies to `Fast' channels only.
				Configured change in rate causing an
				adslAturRateChangeTrap.  A trap is produced when:
				ChanCurrTxRate >= ChanPrevTxRate plus the value of
				this object. A value of `0' will disable the trap."
			::= { sheAdslLineAlarmConfProfileControl 22 }

		
--   1.3.6.1.4.1.231.7.1.2.2.1.6.1.1.23.23
		sheAdslLineAlarmConfProfileControlAturThreshInterleaveRateUp OBJECT-TYPE
			SYNTAX Unsigned32 (0..65535)
			UNITS "bps"
			MAX-ACCESS read-write
			STATUS current
			DESCRIPTION
				"Applies to `Interleave' channels only.
				configured change in rate causing an
				adslAturRateChangeTrap.  A trap is produced when:
				ChanCurrTxRate >= ChanPrevTxRate plus the value of
				this object. A value of `0' will disable the trap."
			::= { sheAdslLineAlarmConfProfileControl 23 }

		
--   1.3.6.1.4.1.231.7.1.2.2.1.6.1.1.23.24
		sheAdslLineAlarmConfProfileControlAturThreshFastRateDown OBJECT-TYPE
			SYNTAX Unsigned32 (0..65535)
			UNITS "bps"
			MAX-ACCESS read-write
			STATUS current
			DESCRIPTION
				"Applies to `Fast' channels only.
				Configured change in rate causing an
				adslAturRateChangeTrap.  A trap is produced when:
				ChanCurrTxRate <= ChanPrevTxRate minus the value of
				this object. A value of `0' will disable the trap."
			::= { sheAdslLineAlarmConfProfileControl 24 }

		
--   1.3.6.1.4.1.231.7.1.2.2.1.6.1.1.23.25
		sheAdslLineAlarmConfProfileControlAturThreshInterleaveRateDown OBJECT-TYPE
			SYNTAX Unsigned32 (0..65535)
			UNITS "bps"
			MAX-ACCESS read-write
			STATUS current
			DESCRIPTION
				"Applies to `Interleave' channels only.
				Configured change in rate causing an
				adslAturRateChangeTrap.  A trap is produced when:
				ChanCurrTxRate <= ChanPrevTxRate minus the value of
				this object. A value of `0' will disable the trap."
			::= { sheAdslLineAlarmConfProfileControl 25 }

		
--   1.3.6.1.4.1.231.7.1.2.2.1.6.1.1.23.26
		sheAdslLineAlarmConfProfileControlAturThresh15MinLofs OBJECT-TYPE
			SYNTAX INTEGER (0..900)
			UNITS "seconds"
			MAX-ACCESS read-write
			STATUS current
			DESCRIPTION
				"The number of Loss of Frame Seconds
				encountered by an ADSL interface within any given 15
				minutes performance data collection period, which
				causes the SNMP agent to send an
				adslAturPerfLofsThreshTrap.
				One trap will be sent per interval per interface.
				A value of `0' will disable the trap."
			::= { sheAdslLineAlarmConfProfileControl 26 }

		
--   1.3.6.1.4.1.231.7.1.2.2.1.6.1.1.23.27
		sheAdslLineAlarmConfProfileControlAturThresh15MinLoss OBJECT-TYPE
			SYNTAX INTEGER (0..900)
			UNITS "seconds"
			MAX-ACCESS read-write
			STATUS current
			DESCRIPTION
				"The number of Loss of Signal Seconds
				encountered by an ADSL interface within any given 15
				minutes performance data collection period, which
				causes the SNMP agent to send an
				adslAturPerfLossThreshTrap.
				One trap will be sent per interval per interface.
				A value of `0' will disable the trap."
			::= { sheAdslLineAlarmConfProfileControl 27 }

		
--   1.3.6.1.4.1.231.7.1.2.2.1.6.1.1.23.28
		sheAdslLineAlarmConfProfileControlAturThresh15MinLprs OBJECT-TYPE
			SYNTAX INTEGER (0..900)
			UNITS "seconds"
			MAX-ACCESS read-write
			STATUS current
			DESCRIPTION
				"The number of Loss of Power Seconds
				encountered by an ADSL interface within any given 15
				minutes performance data collection period, which
				causes the SNMP agent to send an
				adslAturPerfLprsThreshTrap.
				One trap will be sent per interval per interface.
				A value of `0' will disable the trap."
			::= { sheAdslLineAlarmConfProfileControl 28 }

		
--   1.3.6.1.4.1.231.7.1.2.2.1.6.1.1.23.29
		sheAdslLineAlarmConfProfileControlAturThresh15MinESs OBJECT-TYPE
			SYNTAX INTEGER (0..900)
			UNITS "seconds"
			MAX-ACCESS read-write
			STATUS current
			DESCRIPTION
				"The number of Errored Seconds
				encountered by an ADSL interface within any given 15
				minutes performance data collection period, which
				causes the SNMP agent to send an
				adslAturPerfESsThreshTrap.
				One trap will be sent per interval per interface.
				A value of `0' will disable the trap."
			::= { sheAdslLineAlarmConfProfileControl 29 }

		
--   1.3.6.1.4.1.231.7.1.2.2.1.6.1.1.23.30
		sheAdslLineAlarmConfProfileControlAturThresh15MinSesL OBJECT-TYPE
			SYNTAX INTEGER (0..900)
			UNITS "seconds"
			MAX-ACCESS read-write
			STATUS current
			DESCRIPTION
				"The number of Errored Seconds
				encountered by an ADSL interface within any given 15
				minutes performance data collection period, which
				causes the SNMP agent to send an
				adslAturPerfSesLThreshTrap.
				One trap will be sent per interval per interface.
				A value of `0' will disable the trap."
			::= { sheAdslLineAlarmConfProfileControl 30 }

		
--   1.3.6.1.4.1.231.7.1.2.2.1.6.1.1.23.31
		sheAdslLineAlarmConfProfileControlAturThresh15MinUasL OBJECT-TYPE
			SYNTAX INTEGER (0..900)
			UNITS "seconds"
			MAX-ACCESS read-write
			STATUS current
			DESCRIPTION
				"The number of Errored Seconds
				encountered by an ADSL interface within any given 15
				minutes performance data collection period, which
				causes the SNMP agent to send an
				adslAturPerfUasLThreshTrap.
				One trap will be sent per interval per interface.
				A value of `0' will disable the trap."
			::= { sheAdslLineAlarmConfProfileControl 31 }

		
--       trap definitions
-- 
-- 1.3.6.1.4.1.231.7.1.2.2.1.6.1.1.24
		sheAdslNotifications OBJECT IDENTIFIER ::= { sheAdslLineMIB 24 }

		
--   1.3.6.1.4.1.231.7.1.2.2.1.6.1.1.24.1
		sheAdslAtucTraps OBJECT IDENTIFIER ::= { sheAdslNotifications 1 }

		
--   1.3.6.1.4.1.231.7.1.2.2.1.6.1.1.24.1.1
		sheAdslAtucPerfLofsThreshTrap NOTIFICATION-TYPE
			OBJECTS { sheAdslAtucPerfDataCurr15MinLofs, sheAdslLineAlarmConfProfileAtucThresh15MinLofs }
			STATUS current
			DESCRIPTION 
				"Loss of Framing 15-minute interval threshold reached."
			::= { sheAdslAtucTraps 1 }

		
--   1.3.6.1.4.1.231.7.1.2.2.1.6.1.1.24.1.2
		sheAdslAtucPerfLossThreshTrap NOTIFICATION-TYPE
			OBJECTS { sheAdslAtucPerfDataCurr15MinLoss, sheAdslLineAlarmConfProfileAtucThresh15MinLoss }
			STATUS current
			DESCRIPTION 
				"Loss of Signal 15-minute interval threshold reached."
			::= { sheAdslAtucTraps 2 }

		
--   1.3.6.1.4.1.231.7.1.2.2.1.6.1.1.24.1.3
		sheAdslAtucPerfLolsThreshTrap NOTIFICATION-TYPE
			OBJECTS { sheAdslAtucPerfDataCurr15MinLols, sheAdslLineAlarmConfProfileAtucThresh15MinLols }
			STATUS current
			DESCRIPTION 
				"Loss of Link 15-minute interval threshold reached."
			::= { sheAdslAtucTraps 3 }

		
--   1.3.6.1.4.1.231.7.1.2.2.1.6.1.1.24.1.4
		sheAdslAtucPerfLprsThreshTrap NOTIFICATION-TYPE
			OBJECTS { sheAdslAtucPerfDataCurr15MinLprs, sheAdslLineAlarmConfProfileAtucThresh15MinLprs }
			STATUS current
			DESCRIPTION 
				"Loss of Power 15-minute interval threshold reached."
			::= { sheAdslAtucTraps 4 }

		
--   1.3.6.1.4.1.231.7.1.2.2.1.6.1.1.24.1.5
		sheAdslAtucPerfESsThreshTrap NOTIFICATION-TYPE
			OBJECTS { sheAdslAtucPerfDataCurr15MinESs, sheAdslLineAlarmConfProfileAtucThresh15MinESs }
			STATUS current
			DESCRIPTION 
				"Errored Second 15-minute interval threshold reached."
			::= { sheAdslAtucTraps 5 }

		
--   1.3.6.1.4.1.231.7.1.2.2.1.6.1.1.24.1.6
		sheAdslAtucRateChangeTrap NOTIFICATION-TYPE
			OBJECTS { sheAdslAtucChanCurrTxRate, sheAdslAtucChanPrevTxRate }
			STATUS current
			DESCRIPTION 
				"The ATUCs transmit rate has changed (RADSL mode only)"
			::= { sheAdslAtucTraps 6 }

		
--   1.3.6.1.4.1.231.7.1.2.2.1.6.1.1.24.1.7
		sheAdslAtucStatusTrap NOTIFICATION-TYPE
			OBJECTS { sheAdslAtucPhysCurrStatus, sheAdslAtucChanCurrAtmStatus }
			STATUS current
			DESCRIPTION 
				"ATUC initialization failed. See sheAdslAtucPhysCurrStatus
				for potential reasons."
			::= { sheAdslAtucTraps 7 }

		
--   1.3.6.1.4.1.231.7.1.2.2.1.6.1.1.24.1.8
		sheAdslAtucFailedFastRThreshTrap NOTIFICATION-TYPE
			OBJECTS { sheAdslAtucPerfDataCurr15MinFailedFastR, sheAdslLineAlarmConfProfileAtucThresh15MinFailFastR }
			STATUS current
			DESCRIPTION 
				"Failed Fast Retrains 15-minute threshold reached."
			::= { sheAdslAtucTraps 8 }

		
--   1.3.6.1.4.1.231.7.1.2.2.1.6.1.1.24.1.9
		sheAdslAtucPerfSesLThreshTrap NOTIFICATION-TYPE
			OBJECTS { sheAdslAtucPerfDataCurr15MinSesL, sheAdslLineAlarmConfProfileAtucThresh15MinSesL }
			STATUS current
			DESCRIPTION 
				"Severely errored seconds-line 15-minute threshold
				reached."
			::= { sheAdslAtucTraps 9 }

		
--   1.3.6.1.4.1.231.7.1.2.2.1.6.1.1.24.1.10
		sheAdslAtucPerfUasLThreshTrap NOTIFICATION-TYPE
			OBJECTS { sheAdslAtucPerfDataCurr15MinUasL, sheAdslLineAlarmConfProfileAturThresh15MinUasL }
			STATUS current
			DESCRIPTION 
				"Unavailable seconds-line 15-minute threshold
				reached."
			::= { sheAdslAtucTraps 10 }

		
--   1.3.6.1.4.1.231.7.1.2.2.1.6.1.1.24.1.11
		sheAdslLineStateTrap NOTIFICATION-TYPE
			OBJECTS { sheAdslAtucPhysOpState }
			STATUS current
			DESCRIPTION 
				"The operational line state was changed. This trap will be enabled/disabled over the value of
				sheLineAlarmConfProfileOpStateTrapEnable.
				"
			::= { sheAdslAtucTraps 11 }

		
--   1.3.6.1.4.1.231.7.1.2.2.1.6.1.1.24.1.12
		sheAdslAtucPerfLol NOTIFICATION-TYPE
			OBJECTS { sheAlarmTimeAndDate, sheAlarmReportingSource, sheAlarmReportingSourceType, sheAlarmSeverity }
			STATUS current
			DESCRIPTION 
				"This alarm informs the link between the line card and modem is disconnected for unidentied reason, not dying gasp. "
			::= { sheAdslAtucTraps 12 }

		
--   1.3.6.1.4.1.231.7.1.2.2.1.6.1.1.24.1.13
-- THIS ELEMENT WILL NOT LONGER BE SUPPORTED BY NE up R2.5. 
-- Replaced by sheAdslLineAlarmTraps!
		sheAdslAtucPerfLpr NOTIFICATION-TYPE
			OBJECTS { sheAlarmTimeAndDate, sheAlarmReportingSource, sheAlarmReportingSourceType, sheAlarmSeverity }
			STATUS current
			DESCRIPTION 
				"This alarm informs the link between the line card and modem is disconnected for dying gasp. "
			::= { sheAdslAtucTraps 13 }

		
--   1.3.6.1.4.1.231.7.1.2.2.1.6.1.1.24.1.14
-- THIS ELEMENT WILL NOT LONGER BE SUPPORTED BY NE up R2.5. 
-- Replaced by sheAdslLineAlarmTraps!
		sheAdslAtucPerfLos NOTIFICATION-TYPE
			OBJECTS { sheAlarmTimeAndDate, sheAlarmReportingSource, sheAlarmReportingSourceType, sheAlarmSeverity }
			STATUS current
			DESCRIPTION 
				"An LOS failure is declared after 2.5 +(-) 0.5 s of contiguous LOS defect, 
				or, if LOS defect is present when the criteria for LOF failure declaration have been met (see LOF definition below). 
				A LOS failure is cleared after 10 +(-) 0.5 s of no LOS defect. "
			::= { sheAdslAtucTraps 14 }

		
--   1.3.6.1.4.1.231.7.1.2.2.1.6.1.1.24.1.15
-- THIS ELEMENT WILL NOT LONGER BE SUPPORTED BY NE up R2.5. 
-- Replaced by sheAdslLineAlarmTraps!
		sheAdslAtucPerfLof NOTIFICATION-TYPE
			OBJECTS { sheAlarmTimeAndDate, sheAlarmReportingSource, sheAlarmReportingSourceType, sheAlarmSeverity }
			STATUS current
			DESCRIPTION 
				"An LOF failure is declared after 2.5 +(-) 0.5 s of contiguous SEF defect, except when an LOS defect or failure is present (see LOS definition above). 
				A LOF failure is cleared when LOS failure is declared, or after 10 +(-) 0.5 s of no SEF defect. "
			::= { sheAdslAtucTraps 15 }

		
--   1.3.6.1.4.1.231.7.1.2.2.1.6.1.1.24.1.16
		sheAdslLineActStateTrap NOTIFICATION-TYPE
			OBJECTS { sheAdslAtucPhysActState }
			STATUS current
			DESCRIPTION 
				"The line activation command was sent to Line card system"
			::= { sheAdslAtucTraps 16 }

		
		sheAdslInitFailTrap NOTIFICATION-TYPE
			OBJECTS { sheAdslAtucPhysCurrStatus }
			STATUS current
			DESCRIPTION 
				"The init fail trap, trap will only send if a initialication was detected.
				This trap could be enabled/disabled over the value of
				sheLineAlarmConfProfileInitFailTrapEnable."
			::= { sheAdslAtucTraps 17 }

		
--   1.3.6.1.4.1.231.7.1.2.2.1.6.1.1.24.2
		sheAdslAturTraps OBJECT IDENTIFIER ::= { sheAdslNotifications 2 }

		
--   1.3.6.1.4.1.231.7.1.2.2.1.6.1.1.24.2.1
		sheAdslAturRateChangeTrap NOTIFICATION-TYPE
			OBJECTS { sheAdslAturChanCurrTxRate, sheAdslAturChanPrevTxRate }
			STATUS current
			DESCRIPTION 
				"The ATURs transmit rate has changed (RADSL mode only)"
			::= { sheAdslAturTraps 1 }

		
--   1.3.6.1.4.1.231.7.1.2.2.1.6.1.1.24.2.2
		sheAdslAturPerfLofsThreshTrap NOTIFICATION-TYPE
			OBJECTS { sheAdslAturPerfDataCurr15MinLofs, sheAdslLineAlarmConfProfileAturThresh15MinLofs }
			STATUS current
			DESCRIPTION 
				"Loss of Framing 15-minute interval threshold reached."
			::= { sheAdslAturTraps 2 }

		
--   1.3.6.1.4.1.231.7.1.2.2.1.6.1.1.24.2.3
		sheAdslAturPerfLossThreshTrap NOTIFICATION-TYPE
			OBJECTS { sheAdslAturPerfDataCurr15MinLoss, sheAdslLineAlarmConfProfileAturThresh15MinLoss }
			STATUS current
			DESCRIPTION 
				"Loss of Signal 15-minute interval threshold reached."
			::= { sheAdslAturTraps 3 }

		
--   1.3.6.1.4.1.231.7.1.2.2.1.6.1.1.24.2.4
		sheAdslAturPerfLprsThreshTrap NOTIFICATION-TYPE
			OBJECTS { sheAdslAturPerfDataCurr15MinLprs, sheAdslLineAlarmConfProfileAturThresh15MinLprs }
			STATUS current
			DESCRIPTION 
				"Loss of Power 15-minute interval threshold reached."
			::= { sheAdslAturTraps 4 }

		
--   1.3.6.1.4.1.231.7.1.2.2.1.6.1.1.24.2.5
		sheAdslAturPerfESsThreshTrap NOTIFICATION-TYPE
			OBJECTS { sheAdslAturPerfDataCurr15MinESs, sheAdslLineAlarmConfProfileAturThresh15MinESs }
			STATUS current
			DESCRIPTION 
				"Errored Second 15-minute interval threshold reached."
			::= { sheAdslAturTraps 5 }

		
--   1.3.6.1.4.1.231.7.1.2.2.1.6.1.1.24.2.6
		sheAdslAturPerfSesLThreshTrap NOTIFICATION-TYPE
			OBJECTS { sheAdslAturPerfDataCurr15MinSesL, sheAdslLineAlarmConfProfileAturThresh15MinSesL }
			STATUS current
			DESCRIPTION 
				"Severely errored seconds-line 15-minute threshold
				reached."
			::= { sheAdslAturTraps 6 }

		
--   1.3.6.1.4.1.231.7.1.2.2.1.6.1.1.24.2.7
		sheAdslAturPerfUasLThreshTrap NOTIFICATION-TYPE
			OBJECTS { sheAdslAturPerfDataCurr15MinUasL, sheAdslLineAlarmConfProfileAturThresh15MinUasL }
			STATUS current
			DESCRIPTION 
				"Unavailable seconds-line 15-minute threshold
				reached."
			::= { sheAdslAturTraps 7 }

		
--   1.3.6.1.4.1.231.7.1.2.2.1.6.1.1.24.2.8
		sheAdslAturStatusTrap NOTIFICATION-TYPE
			OBJECTS { sheAdslAturPhysCurrStatus, sheAdslAturChanCurrAtmStatus }
			STATUS current
			DESCRIPTION 
				"ATUC initialization failed. See sheAdslAtucPhysCurrStatus
				for potential reasons."
			::= { sheAdslAturTraps 8 }

		
--   1.3.6.1.4.1.231.7.1.2.2.1.6.1.1.24.2.9
-- THIS ELEMENT WILL NOT LONGER BE SUPPORTED BY NE up R2.5. 
-- Replaced by sheAdslLineAlarmTraps!
		sheAdslAturPerfLos NOTIFICATION-TYPE
			OBJECTS { sheAlarmTimeAndDate, sheAlarmReportingSource, sheAlarmReportingSourceType, sheAlarmSeverity }
			STATUS current
			DESCRIPTION 
				"An LOS failure is declared after 2.5 +(-) 0.5 s of contiguous LOS defect, 
				or, if LOS defect is present when the criteria for LOF failure declaration have been met (see LOF definition below). 
				A LOS failure is cleared after 10 +(-) 0.5 s of no LOS defect.."
			::= { sheAdslAturTraps 9 }

		
--   1.3.6.1.4.1.231.7.1.2.2.1.6.1.1.24.2.10
-- THIS ELEMENT WILL NOT LONGER BE SUPPORTED BY NE up R2.5. 
-- Replaced by sheAdslLineAlarmTraps!
		sheAdslAturPerfLof NOTIFICATION-TYPE
			OBJECTS { sheAlarmTimeAndDate, sheAlarmReportingSource, sheAlarmReportingSourceType, sheAlarmSeverity }
			STATUS current
			DESCRIPTION 
				"An LOF failure is declared after 2.5 +(-) 0.5 s of contiguous SEF defect, except when an LOS defect or failure is present (see LOS definition above). 
				A LOF failure is cleared when LOS failure is declared, or after 10 +(-) 0.5 s of no SEF defect."
			::= { sheAdslAturTraps 10 }

		
--   1.3.6.1.4.1.231.7.1.2.2.1.6.1.1.24.3
		sheAdslConfigurationTraps OBJECT IDENTIFIER ::= { sheAdslNotifications 3 }

		
--   1.3.6.1.4.1.231.7.1.2.2.1.6.1.1.24.3.2
		sheAdslLineConfProfileCreated NOTIFICATION-TYPE
			OBJECTS { sheAdslLineConfProfileControlIndex, sheAdslLineConfProfileControlTimeStamp, sheAdslLineConfProfileControlName, sheAdslLineConfProfileControlAtucConfRateMode, sheAdslLineConfProfileControlAtucConfRateChanRatio, 
				sheAdslLineConfProfileControlAtucConfTargetSnrMgn, sheAdslLineConfProfileControlAtucConfMaxSnrMgn, sheAdslLineConfProfileControlAtucConfMinSnrMgn, sheAdslLineConfProfileControlAtucConfDownshiftSnrMgn, sheAdslLineConfProfileControlAtucConfUpshiftSnrMgn, 
				sheAdslLineConfProfileControlAtucConfMinUpshiftTime, sheAdslLineConfProfileControlAtucConfMinDownshiftTime, sheAdslLineConfProfileControlAtucChanConfFastMinTxRate, sheAdslLineConfProfileControlAtucChanConfInterleaveMinTxRate, sheAdslLineConfProfileControlAtucChanConfFastMaxTxRate, 
				sheAdslLineConfProfileControlAtucChanConfInterleaveMaxTxRate, sheAdslLineConfProfileControlAtucChanConfMaxInterleaveDelay, sheAdslLineConfProfileControlAturConfRateMode, sheAdslLineConfProfileControlAturConfRateChanRatio, sheAdslLineConfProfileControlAturConfTargetSnrMgn, 
				sheAdslLineConfProfileControlAturConfMaxSnrMgn, sheAdslLineConfProfileControlAturConfMinSnrMgn, sheAdslLineConfProfileControlAturConfDownshiftSnrMgn, sheAdslLineConfProfileControlAturConfUpshiftSnrMgn, sheAdslLineConfProfileControlAturConfMinUpshiftTime, 
				sheAdslLineConfProfileControlAturConfMinDownshiftTime, sheAdslLineConfProfileControlAturChanConfFastMinTxRate, sheAdslLineConfProfileControlAturChanConfInterleaveMinTxRate, sheAdslLineConfProfileControlAturChanConfFastMaxTxRate, sheAdslLineConfProfileControlAturChanConfInterleaveMaxTxRate, 
				sheAdslLineConfProfileControlAturChanConfMaxInterleaveDelay, sheAdslLineConfProfileControlTrellis, sheAdslLineConfProfileControlAtucConfPwrMgmtL0Time, sheAdslLineConfProfileControlAtucConfPwrMgmtL2Time, sheAdslLineConfProfileControlAtucConfPwrMgmtL2ATPR, 
				sheAdslLineConfProfileControlAtucConfPwrMgmtL2Rate, sheAdslLineConfProfileControlAtucConfPwrMgmtMode }
			STATUS current
			DESCRIPTION 
				"Configuration notification."
			::= { sheAdslConfigurationTraps 2 }

		
--   1.3.6.1.4.1.231.7.1.2.2.1.6.1.1.24.3.3
		sheAdslLineConfProfileModified NOTIFICATION-TYPE
			OBJECTS { sheAdslLineConfProfileControlIndex, sheAdslLineConfProfileControlTimeStamp, sheAdslLineConfProfileControlName, sheAdslLineConfProfileControlAtucConfRateMode, sheAdslLineConfProfileControlAtucConfRateChanRatio, 
				sheAdslLineConfProfileControlAtucConfTargetSnrMgn, sheAdslLineConfProfileControlAtucConfMaxSnrMgn, sheAdslLineConfProfileControlAtucConfMinSnrMgn, sheAdslLineConfProfileControlAtucConfDownshiftSnrMgn, sheAdslLineConfProfileControlAtucConfUpshiftSnrMgn, 
				sheAdslLineConfProfileControlAtucConfMinUpshiftTime, sheAdslLineConfProfileControlAtucConfMinDownshiftTime, sheAdslLineConfProfileControlAtucChanConfFastMinTxRate, sheAdslLineConfProfileControlAtucChanConfInterleaveMinTxRate, sheAdslLineConfProfileControlAtucChanConfFastMaxTxRate, 
				sheAdslLineConfProfileControlAtucChanConfInterleaveMaxTxRate, sheAdslLineConfProfileControlAtucChanConfMaxInterleaveDelay, sheAdslLineConfProfileControlAturConfRateMode, sheAdslLineConfProfileControlAturConfRateChanRatio, sheAdslLineConfProfileControlAturConfTargetSnrMgn, 
				sheAdslLineConfProfileControlAturConfMaxSnrMgn, sheAdslLineConfProfileControlAturConfMinSnrMgn, sheAdslLineConfProfileControlAturConfDownshiftSnrMgn, sheAdslLineConfProfileControlAturConfUpshiftSnrMgn, sheAdslLineConfProfileControlAturConfMinUpshiftTime, 
				sheAdslLineConfProfileControlAturConfMinDownshiftTime, sheAdslLineConfProfileControlAturChanConfFastMinTxRate, sheAdslLineConfProfileControlAturChanConfInterleaveMinTxRate, sheAdslLineConfProfileControlAturChanConfFastMaxTxRate, sheAdslLineConfProfileControlAturChanConfInterleaveMaxTxRate, 
				sheAdslLineConfProfileControlAturChanConfMaxInterleaveDelay, sheAdslLineConfProfileControlTrellis, sheAdslLineConfProfileControlAtucConfPwrMgmtL0Time, sheAdslLineConfProfileControlAtucConfPwrMgmtL2Time, sheAdslLineConfProfileControlAtucConfPwrMgmtL2ATPR, 
				sheAdslLineConfProfileControlAtucConfPwrMgmtL2Rate, sheAdslLineConfProfileControlAtucConfPwrMgmtMode }
			STATUS current
			DESCRIPTION 
				"Configuration notification."
			::= { sheAdslConfigurationTraps 3 }

		
--   1.3.6.1.4.1.231.7.1.2.2.1.6.1.1.24.3.4
		sheAdslLineConfProfileDeleted NOTIFICATION-TYPE
			OBJECTS { sheAdslLineConfProfileControlIndex, sheAdslLineConfProfileControlTimeStamp, sheAdslLineConfProfileControlName }
			STATUS current
			DESCRIPTION 
				"Configuration notification."
			::= { sheAdslConfigurationTraps 4 }

		
--   1.3.6.1.4.1.231.7.1.2.2.1.6.1.1.24.3.6
		sheAdslLineConfExtnProfileModified NOTIFICATION-TYPE
			OBJECTS { sheAdslLineConfExtnProfileControlIndex, sheAdslLineConfExtnProfileControlTimeStamp, sheAdslLineConfExtnProfileControlName, sheAdslLineConfExtnProfileControlRsIntCorrectionUp, sheAdslLineConfExtnProfileControlLineType, 
				sheAdslLineConfExtnProfileControlTxEndBin, sheAdslLineConfExtnProfileControlTxStartBin, sheAdslLineConfExtnProfileControlRxStartBin, sheAdslLineConfExtnProfileControlRxEndBin, sheAdslLineConfExtnProfileControlStandard, 
				sheAdslLineConfExtnProfileControlTxPowerAttenuation, sheAdslLineConfExtnProfileControlIntCorrectionDown, sheAdslLineConfExtnProfileControlBitSwap, sheAdslLineConfExtnProfileControlNtr, sheAdslLineConfExtnProfileControlAnnexType, 
				sheAdslLineConfExtnProfileControlUseCustomBin, sheAdslLineConfExtnProfileControlDnBinUsage, sheAdslLineConfExtnProfileControlMaxDCo, sheAdslLineConfExtnProfileControlAdvertisedCapabilities, sheAdslLineConfExtnProfileControlPsdMaskType, 
				sheAdslLineConfExtnProfileControlLineDmtConfMode, sheAdslLineConfExtnProfileControlEraseProfiles, sheAdslLineConfExtnProfileControlParamHybridLossTestStart, sheAdslLineConfExtnProfileControlParamHybridLossTestEnd, sheAdslLineConfExtnProfileControlConfMinInp, 
				sheAdslLineConfExtnProfileControlUpstreamPsdMaskSelection, sheAdslLineConfExtnProfileControlMaxNomPsdDs, sheAdslLineConfExtnProfileControlMaxNomAtpDs, sheAdslLineConfExtnProfileControlPsdMaskDs, sheAdslLineConfExtnProfileControlPSDMASKdsEnable, 
				sheAdslLineConfExtnProfileControlConfMinInpUs }
			STATUS current
			DESCRIPTION 
				"Configuration notification."
			::= { sheAdslConfigurationTraps 6 }

		
--   1.3.6.1.4.1.231.7.1.2.2.1.6.1.1.24.3.8
		sheAdslLineAlarmConfProfileCreated NOTIFICATION-TYPE
			OBJECTS { sheAdslLineAlarmConfProfileControlIndex, sheAdslLineAlarmConfProfileControlTimeStamp, sheAdslLineAlarmConfProfileControlName, sheAdslLineAlarmConfProfileControlOpStateTrapEnable, sheAdslLineAlarmConfProfileControlAtucThreshFastRateUp, 
				sheAdslLineAlarmConfProfileControlAtucThreshInterleaveRateUp, sheAdslLineAlarmConfProfileControlAtucThreshFastRateDown, sheAdslLineAlarmConfProfileControlAtucThreshInterleaveRateDown, sheAdslLineAlarmConfProfileControlAtucInitFailureTrapEnable, sheAdslLineAlarmConfProfileControlAtucThresh15MinLofs, 
				sheAdslLineAlarmConfProfileControlAtucThresh15MinLoss, sheAdslLineAlarmConfProfileControlAtucThresh15MinLols, sheAdslLineAlarmConfProfileControlAtucThresh15MinLprs, sheAdslLineAlarmConfProfileControlAtucThresh15MinESs, sheAdslLineAlarmConfProfileControlAtucThresh15MinSesL, 
				sheAdslLineAlarmConfProfileControlAtucThresh15MinUasL, sheAdslLineAlarmConfProfileControlAtucThresh15MinFailFastR, sheAdslLineAlarmConfProfileControlAturThreshFastRateUp, sheAdslLineAlarmConfProfileControlAturThreshInterleaveRateUp, sheAdslLineAlarmConfProfileControlAturThreshFastRateDown, 
				sheAdslLineAlarmConfProfileControlAturThreshInterleaveRateDown, sheAdslLineAlarmConfProfileControlAturThresh15MinLofs, sheAdslLineAlarmConfProfileControlAturThresh15MinLoss, sheAdslLineAlarmConfProfileControlAturThresh15MinLprs, sheAdslLineAlarmConfProfileControlAturThresh15MinESs, 
				sheAdslLineAlarmConfProfileControlAturThresh15MinSesL, sheAdslLineAlarmConfProfileControlAturThresh15MinUasL }
			STATUS current
			DESCRIPTION 
				"Configuration notification."
			::= { sheAdslConfigurationTraps 8 }

		
--   1.3.6.1.4.1.231.7.1.2.2.1.6.1.1.24.3.9
		sheAdslLineAlarmConfProfileModified NOTIFICATION-TYPE
			OBJECTS { sheAdslLineAlarmConfProfileControlIndex, sheAdslLineAlarmConfProfileControlTimeStamp, sheAdslLineAlarmConfProfileControlName, sheAdslLineAlarmConfProfileControlOpStateTrapEnable, sheAdslLineAlarmConfProfileControlAtucThreshFastRateUp, 
				sheAdslLineAlarmConfProfileControlAtucThreshInterleaveRateUp, sheAdslLineAlarmConfProfileControlAtucThreshFastRateDown, sheAdslLineAlarmConfProfileControlAtucThreshInterleaveRateDown, sheAdslLineAlarmConfProfileControlAtucInitFailureTrapEnable, sheAdslLineAlarmConfProfileControlAtucThresh15MinLofs, 
				sheAdslLineAlarmConfProfileControlAtucThresh15MinLoss, sheAdslLineAlarmConfProfileControlAtucThresh15MinLols, sheAdslLineAlarmConfProfileControlAtucThresh15MinLprs, sheAdslLineAlarmConfProfileControlAtucThresh15MinESs, sheAdslLineAlarmConfProfileControlAtucThresh15MinSesL, 
				sheAdslLineAlarmConfProfileControlAtucThresh15MinUasL, sheAdslLineAlarmConfProfileControlAtucThresh15MinFailFastR, sheAdslLineAlarmConfProfileControlAturThreshFastRateUp, sheAdslLineAlarmConfProfileControlAturThreshInterleaveRateUp, sheAdslLineAlarmConfProfileControlAturThreshFastRateDown, 
				sheAdslLineAlarmConfProfileControlAturThreshInterleaveRateDown, sheAdslLineAlarmConfProfileControlAturThresh15MinLofs, sheAdslLineAlarmConfProfileControlAturThresh15MinLoss, sheAdslLineAlarmConfProfileControlAturThresh15MinLprs, sheAdslLineAlarmConfProfileControlAturThresh15MinESs, 
				sheAdslLineAlarmConfProfileControlAturThresh15MinSesL, sheAdslLineAlarmConfProfileControlAturThresh15MinUasL }
			STATUS current
			DESCRIPTION 
				"Configuration notification."
			::= { sheAdslConfigurationTraps 9 }

		
--   1.3.6.1.4.1.231.7.1.2.2.1.6.1.1.24.3.10
		sheAdslLineAlarmConfProfileDeleted NOTIFICATION-TYPE
			OBJECTS { sheAdslLineAlarmConfProfileControlIndex, sheAdslLineAlarmConfProfileControlTimeStamp, sheAdslLineAlarmConfProfileControlName }
			STATUS current
			DESCRIPTION 
				"Configuration notification."
			::= { sheAdslConfigurationTraps 10 }

		
--   1.3.6.1.4.1.231.7.1.2.2.1.6.1.1.24.3.11
		sheAdslLineConfigurationModified NOTIFICATION-TYPE
			OBJECTS { sheAdslLineControlIndex, sheAdslLineControlTimeStamp, sheAdslLineControlConfProfile, sheAdslLineControlAlarmConfProfile, sheAdslLineControlAction, 
				sheAdslLineControlPwrMgmtPMSF, sheAdslLineControlDeltConfLDSF, sheAdslLineControlRfiBandMask }
			STATUS current
			DESCRIPTION 
				"Configuration notification."
			::= { sheAdslConfigurationTraps 11 }

		
		sheAdslLinePerfCounterCleared NOTIFICATION-TYPE
			OBJECTS { sheAdslLineControlIndex, sheAdslLineControlTimeStamp }
			STATUS current
			DESCRIPTION 
				"performance counter cleared"
			::= { sheAdslConfigurationTraps 12 }

		
		sheAdslLineConfProfileReqResult NOTIFICATION-TYPE
			OBJECTS { sheAdslLineConfProfileControlIndex, sheAdslLineConfProfileControlTimeStamp, sheAdslLineConfProfileControlName, sheAdslLineConfProfileControlRequest, sheAdslLineConfProfileControlStatus, 
				sheAdslLineConfProfileControlReqResult }
			STATUS current
			DESCRIPTION 
				"Configuration notification for long running command - Result-Trap."
			::= { sheAdslConfigurationTraps 13 }

		
		sheAdslLineConfExtnProfileReqResult NOTIFICATION-TYPE
			OBJECTS { sheAdslLineConfExtnProfileControlIndex, sheAdslLineConfExtnProfileControlTimeStamp, sheAdslLineConfExtnProfileControlName, sheAdslLineConfExtnProfileControlRequest, sheAdslLineConfExtnProfileControlStatus, 
				sheAdslLineConfExtnProfileControlReqResult }
			STATUS current
			DESCRIPTION 
				"Configuration notification for long running command - Result-Trap."
			::= { sheAdslConfigurationTraps 14 }

		
		sheAdslLineAlarmConfProfileReqResult NOTIFICATION-TYPE
			OBJECTS { sheAdslLineAlarmConfProfileControlIndex, sheAdslLineAlarmConfProfileControlTimeStamp, sheAdslLineAlarmConfProfileControlName, sheAdslLineAlarmConfProfileControlRequest, sheAdslLineAlarmConfProfileControlStatus, 
				sheAdslLineAlarmConfProfileControlReqResult }
			STATUS current
			DESCRIPTION 
				"Configuration notification for long running command - Result-Trap."
			::= { sheAdslConfigurationTraps 15 }

		
--   1.3.6.1.4.1.231.7.1.2.2.1.6.1.1.24.3.2
		sheAdslLineDpboProfileCreated NOTIFICATION-TYPE
			OBJECTS { sheAdslLineDpboProfileControlIndex, sheAdslLineDpboProfileControlTimeStamp, sheAdslLineDpboProfileControlName, sheAdslLineDpboProfileControlEsel, sheAdslLineDpboProfileControlEselMin, 
				sheAdslLineDpboProfileControlMus, sheAdslLineDpboProfileControlMof, sheAdslLineDpboProfileControlFMin, sheAdslLineDpboProfileControlFMax, sheAdslLineDpboProfileControlEpsd, 
				sheAdslLineDpboProfileControlEScmA, sheAdslLineDpboProfileControlEScmB, sheAdslLineDpboProfileControlEScmC }
			STATUS current
			DESCRIPTION 
				"Configuration notification."
			::= { sheAdslConfigurationTraps 16 }

		
--   1.3.6.1.4.1.231.7.1.2.2.1.6.1.1.24.3.2
		sheAdslLineDpboProfileModified NOTIFICATION-TYPE
			OBJECTS { sheAdslLineDpboProfileControlIndex, sheAdslLineDpboProfileControlTimeStamp, sheAdslLineDpboProfileControlName, sheAdslLineDpboProfileControlEsel, sheAdslLineDpboProfileControlEselMin, 
				sheAdslLineDpboProfileControlMus, sheAdslLineDpboProfileControlMof, sheAdslLineDpboProfileControlFMin, sheAdslLineDpboProfileControlFMax, sheAdslLineDpboProfileControlEpsd, 
				sheAdslLineDpboProfileControlEScmA, sheAdslLineDpboProfileControlEScmB, sheAdslLineDpboProfileControlEScmC }
			STATUS current
			DESCRIPTION 
				"Configuration notification."
			::= { sheAdslConfigurationTraps 17 }

		
--   1.3.6.1.4.1.231.7.1.2.2.1.6.1.1.24.3.4
		sheAdslLineDpboProfileDeleted NOTIFICATION-TYPE
			OBJECTS { sheAdslLineDpboProfileControlIndex, sheAdslLineDpboProfileControlTimeStamp, sheAdslLineDpboProfileControlName }
			STATUS current
			DESCRIPTION 
				"Configuration notification."
			::= { sheAdslConfigurationTraps 18 }

		
		sheAdslLineDpboProfileReqResult NOTIFICATION-TYPE
			OBJECTS { sheAdslLineDpboProfileControlIndex, sheAdslLineDpboProfileControlRequest, sheAdslLineDpboProfileControlStatus, sheAdslLineDpboProfileControlTimeStamp, sheAdslLineDpboProfileControlReqResult
				 }
			STATUS current
			DESCRIPTION 
				"Configuration notification for long running command - Result-Trap."
			::= { sheAdslConfigurationTraps 19 }

		
		sheAdslLineDpboProfileSetReqResult NOTIFICATION-TYPE
			OBJECTS { sheAdslLineControlIndex, sheAdslLineControlStatus, sheAdslLineControlReqResult, sheAdslLineControlTimeStamp, sheAdslLineControlDpboProfile
				 }
			STATUS current
			DESCRIPTION 
				"Configuration notification for long running command - Result-Trap."
			::= { sheAdslConfigurationTraps 20 }

		
		sheAdslLineDpboProfileSetModified NOTIFICATION-TYPE
			OBJECTS { sheAdslLineControlIndex, sheAdslLineControlTimeStamp, sheAdslLineControlDpboProfile }
			STATUS current
			DESCRIPTION 
				"Configuration notification."
			::= { sheAdslConfigurationTraps 21 }

		
		sheAdslLineInpValueTruncatedInto2 NOTIFICATION-TYPE
			OBJECTS { sheAdslLineConfProfileControlIndex, sheAdslLineControlIndex, sheAdslLineControlTimeStamp }
			STATUS current
			DESCRIPTION 
				"INP value was truncated into 2 because of the limitation of Conexant."
			::= { sheAdslConfigurationTraps 22 }

		
		sheAdslLineAlarmTraps OBJECT IDENTIFIER ::= { sheAdslNotifications 4 }

		
		sheAdslLineAlarmLOS NOTIFICATION-TYPE
			OBJECTS { sheAlarmTimeAndDate, sheAlarmReportingSource, sheAlarmReportingSourceType, sheAlarmSeverity }
			STATUS current
			DESCRIPTION 
				"ATUC failure due to not receiving signal"
			::= { sheAdslLineAlarmTraps 1 }

		
		sheAdslLineAlarmLOF NOTIFICATION-TYPE
			OBJECTS { sheAlarmTimeAndDate, sheAlarmReportingSource, sheAlarmReportingSourceType, sheAlarmSeverity }
			STATUS current
			DESCRIPTION 
				"ATUC failure due to not receiving valid frame."
			::= { sheAdslLineAlarmTraps 2 }

		
		sheAdslLineAlarmLOL NOTIFICATION-TYPE
			OBJECTS { sheAlarmTimeAndDate, sheAlarmReportingSource, sheAlarmReportingSourceType, sheAlarmSeverity }
			STATUS current
			DESCRIPTION 
				"ATUC failure due to inability to link with xTUR"
			::= { sheAdslLineAlarmTraps 3 }

		
		sheAdslLineAlarmLPR NOTIFICATION-TYPE
			OBJECTS { sheAlarmTimeAndDate, sheAlarmReportingSource, sheAlarmReportingSourceType, sheAlarmSeverity }
			STATUS current
			DESCRIPTION 
				"ATUR failure due to loss of power"
			::= { sheAdslLineAlarmTraps 4 }

		
		sheAdslLineAlarmIMNR NOTIFICATION-TYPE
			OBJECTS { sheAlarmTimeAndDate, sheAlarmReportingSource, sheAlarmReportingSourceType, sheAlarmSeverity }
			STATUS current
			DESCRIPTION 
				"Loss of Signal Quality is declared when the Noise Margin falls below the Minimum Noise Margin, or the bit-error-rate exceeds 10^-7.
				Detected by Atuc-side."
			::= { sheAdslLineAlarmTraps 5 }

		
--   1.3.6.1.4.1.231.7.1.2.2.1.6.1.1.25
		sheAdslVccTpTable OBJECT-TYPE
			SYNTAX SEQUENCE OF SheAdslVccTpEntry
			MAX-ACCESS not-accessible
			STATUS current
			DESCRIPTION
				"The VccTp-Table."
			::= { sheAdslLineMIB 25 }

		
--   1.3.6.1.4.1.231.7.1.2.2.1.6.1.1.25.1
		sheAdslVccTpEntry OBJECT-TYPE
			SYNTAX SheAdslVccTpEntry
			MAX-ACCESS not-accessible
			STATUS current
			DESCRIPTION
				"This table contains the VccTp-Configurations. There will be one
				entry for every adsl-interface available per default. This default
				entry should never be deleted."
			INDEX { sheAdslVccTpIndex }
			::= { sheAdslVccTpTable 1 }

		
		SheAdslVccTpEntry ::=
			SEQUENCE { 
				sheAdslVccTpIndex
					Integer32,
				sheAdslVccTpSubLayerIndex
					InterfaceIndex,
				sheAdslVccTpNumber
					Integer32,
				sheAdslVccTpVpi
					Integer32,
				sheAdslVccTpVci
					Integer32,
				sheAdslVccTpOamLevel
					SheAdslOamLevelType,
				sheAdslVccTpLoopTest
					SheAdslOamLoopTestType,
				sheAdslVccTpLoopTestResult
					SheAdslVccTpLoopTestResultType,
				sheAdslVccTpLoopLocId
					OCTET STRING,
				sheAdslVccTpAlarmSeverityIndex
					SheAlarmSevProfileIndex,
				sheAdslVccTpEgressQosClass
					SheAdslAtmQosType,
				sheAdslVccTpEgressPeakCellRate
					Unsigned32,
				sheAdslVccTpEgressSustainedCellRate
					Unsigned32,
				sheAdslVccTpEgressMaxBurstSize
					Unsigned32,
				sheAdslVccTpEgressWeight
					Integer32,
				sheAdslVccTpIngressSustainedCellRate
					Unsigned32,
				sheAdslVccTpIngressMaxBurstSize
					Unsigned32,
				sheAdslVccTpAdminState
					SheAdslEnableType,
				sheAdslVccTpOrl
					Unsigned32,
				sheAdslVccTpUsedDslChannel
					SheAdslConfLineType,
				sheAdslVccTpEncapsulation
					SheAdslAtmEncapType
			 }

--   1.3.6.1.4.1.231.7.1.2.2.1.6.1.1.25.1.1
		sheAdslVccTpIndex OBJECT-TYPE
			SYNTAX Integer32 (1..65565)
			MAX-ACCESS read-only
			STATUS current
			DESCRIPTION
				"Index for that table. The index will follow this rule:
				VccTpIndex = (VccTpSubLayerIndex << 4) + VccTpNumber"
			::= { sheAdslVccTpEntry 1 }

		
--   1.3.6.1.4.1.231.7.1.2.2.1.6.1.1.25.1.2
		sheAdslVccTpSubLayerIndex OBJECT-TYPE
			SYNTAX InterfaceIndex
			MAX-ACCESS read-only
			STATUS current
			DESCRIPTION
				"ifIndex of the underlaying adsl-interface."
			::= { sheAdslVccTpEntry 2 }

		
--   1.3.6.1.4.1.231.7.1.2.2.1.6.1.1.25.1.3
		sheAdslVccTpNumber OBJECT-TYPE
			SYNTAX Integer32 (1..8)
			MAX-ACCESS read-only
			STATUS current
			DESCRIPTION
				"This is the logical number of VccTP on the corresponding interface. Maximum value is 8."
			::= { sheAdslVccTpEntry 3 }

		
--   1.3.6.1.4.1.231.7.1.2.2.1.6.1.1.25.1.4
		sheAdslVccTpVpi OBJECT-TYPE
			SYNTAX Integer32 (0..255)
			MAX-ACCESS read-only
			STATUS current
			DESCRIPTION
				"The VPI - Value."
			DEFVAL { 0 }
			::= { sheAdslVccTpEntry 4 }

		
--   1.3.6.1.4.1.231.7.1.2.2.1.6.1.1.25.1.5
		sheAdslVccTpVci OBJECT-TYPE
			SYNTAX Integer32 (32..65535)
			MAX-ACCESS read-only
			STATUS current
			DESCRIPTION
				"The Vci - Value."
			DEFVAL { 32 }
			::= { sheAdslVccTpEntry 5 }

		
--   1.3.6.1.4.1.231.7.1.2.2.1.6.1.1.25.1.6
		sheAdslVccTpOamLevel OBJECT-TYPE
			SYNTAX SheAdslOamLevelType (4..5)
			MAX-ACCESS read-only
			STATUS current
			DESCRIPTION
				"The OAM level for loop test on VP/VC level.
				Valid:    f5 (for VC). "
			DEFVAL { 5 }
			::= { sheAdslVccTpEntry 6 }

		
--   1.3.6.1.4.1.231.7.1.2.2.1.6.1.1.25.1.7
		sheAdslVccTpLoopTest OBJECT-TYPE
			SYNTAX SheAdslOamLoopTestType
			MAX-ACCESS read-only
			STATUS current
			DESCRIPTION
				"The type of loop test .
				For EndToEnd loop test loop location ID is FF..FF."
			DEFVAL { 0 }
			::= { sheAdslVccTpEntry 7 }

		
--   1.3.6.1.4.1.231.7.1.2.2.1.6.1.1.25.1.8
		sheAdslVccTpLoopTestResult OBJECT-TYPE
			SYNTAX SheAdslVccTpLoopTestResultType
			MAX-ACCESS read-only
			STATUS current
			DESCRIPTION
				"Possible values:
				segSuccess(0),
				segFailure(1),
				endToEndSuccess(2),
				endToEndFailure(3),
				aborted(4),
				progress(5),
				notAvailable(65535)
				"
			::= { sheAdslVccTpEntry 8 }

		
--   1.3.6.1.4.1.231.7.1.2.2.1.6.1.1.25.1.9
		sheAdslVccTpLoopLocId OBJECT-TYPE
			SYNTAX OCTET STRING (SIZE (0..16))
			MAX-ACCESS read-only
			STATUS current
			DESCRIPTION
				"Test cell loopback location. It is an identifier known
				by the crafts person identifying a ATM node in the ATM
				network.  For EndToEnd loop test the default value is valid. "
			DEFVAL { 'FFFFFFFFFFFFFFFFFFFFFFFFFFFFFFFF'h }
			::= { sheAdslVccTpEntry 9 }

		
--   1.3.6.1.4.1.231.7.1.2.2.1.6.1.1.25.1.10
		sheAdslVccTpAlarmSeverityIndex OBJECT-TYPE
			SYNTAX SheAlarmSevProfileIndex
			MAX-ACCESS read-only
			STATUS current
			DESCRIPTION
				"Index to the AlarmSeverityProfileTable. Defines the actual 
				AlarmSeverities for all alarms per VccTp."
			::= { sheAdslVccTpEntry 10 }

		
--   1.3.6.1.4.1.231.7.1.2.2.1.6.1.1.25.1.11
		sheAdslVccTpEgressQosClass OBJECT-TYPE
			SYNTAX SheAdslAtmQosType
			MAX-ACCESS read-only
			STATUS current
			DESCRIPTION
				"Egress Qos Type"
			DEFVAL { 1 }
			::= { sheAdslVccTpEntry 11 }

		
--   1.3.6.1.4.1.231.7.1.2.2.1.6.1.1.25.1.12
		sheAdslVccTpEgressPeakCellRate OBJECT-TYPE
			SYNTAX Unsigned32 (0..365000)
			UNITS "cell/second"
			MAX-ACCESS read-only
			STATUS current
			DESCRIPTION
				"Valid when sheAdslVccTpEgressQosClass is not unshaped"
			::= { sheAdslVccTpEntry 12 }

		
--   1.3.6.1.4.1.231.7.1.2.2.1.6.1.1.25.1.13
		sheAdslVccTpEgressSustainedCellRate OBJECT-TYPE
			SYNTAX Unsigned32 (0..365000)
			UNITS "cell/second"
			MAX-ACCESS read-only
			STATUS current
			DESCRIPTION
				"Valid when sheAdslVccTpEgressQosClass is shapingRtVbr or shapingNrtVbr"
			::= { sheAdslVccTpEntry 13 }

		
--   1.3.6.1.4.1.231.7.1.2.2.1.6.1.1.25.1.14
		sheAdslVccTpEgressMaxBurstSize OBJECT-TYPE
			SYNTAX Unsigned32 (0..1073741824)
			UNITS "cell"
			MAX-ACCESS read-only
			STATUS current
			DESCRIPTION
				"Valid when sheAdslVccTpEgressQosClass is shapingRtVbr or shapingNrtVbr"
			::= { sheAdslVccTpEntry 14 }

		
--   1.3.6.1.4.1.231.7.1.2.2.1.6.1.1.25.1.15
		sheAdslVccTpEgressWeight OBJECT-TYPE
			SYNTAX Integer32 (1..8)
			MAX-ACCESS read-only
			STATUS current
			DESCRIPTION
				"Valid only when sheAdslVccTpEgressQosClass is unshaped."
			::= { sheAdslVccTpEntry 15 }

		
--   1.3.6.1.4.1.231.7.1.2.2.1.6.1.1.25.1.16
		sheAdslVccTpIngressSustainedCellRate OBJECT-TYPE
			SYNTAX Unsigned32 (0..365000)
			UNITS "cell/second"
			MAX-ACCESS read-only
			STATUS current
			DESCRIPTION
				"GFR scr for ingress policing"
			::= { sheAdslVccTpEntry 16 }

		
--   1.3.6.1.4.1.231.7.1.2.2.1.6.1.1.25.1.17
		sheAdslVccTpIngressMaxBurstSize OBJECT-TYPE
			SYNTAX Unsigned32 (0..1073741824)
			UNITS "cell"
			MAX-ACCESS read-only
			STATUS current
			DESCRIPTION
				"GFR mbs for ingress policing"
			::= { sheAdslVccTpEntry 17 }

		
--   1.3.6.1.4.1.231.7.1.2.2.1.6.1.1.25.1.18
		sheAdslVccTpAdminState OBJECT-TYPE
			SYNTAX SheAdslEnableType
			MAX-ACCESS read-only
			STATUS current
			DESCRIPTION
				"Enable/disable single VccTp. Default value is enabled."
			DEFVAL { 1 }
			::= { sheAdslVccTpEntry 18 }

		
--   1.3.6.1.4.1.231.7.1.2.2.1.6.1.1.25.1.19		
		sheAdslVccTpOrl OBJECT-TYPE
			SYNTAX Unsigned32 (0 | 64..29952)
			UNITS "kbps"
			MAX-ACCESS read-only
			STATUS current
			DESCRIPTION
				"The output rate limiting value. This value is only valid for the default VccTp-entry's 
				with VccTp-Number 1. All other will show a 0 and could not be modified."
			DEFVAL { 24000 }
			::= { sheAdslVccTpEntry 19 }

		
		sheAdslVccTpUsedDslChannel OBJECT-TYPE
			SYNTAX SheAdslConfLineType
			MAX-ACCESS read-only
			STATUS current
			DESCRIPTION
				"This attribute defines the usage of a dsl bearer channel by this VccTp.
				The availability of dsl channels depends on the configuration of the underlaying 
				adsl line (VccTpSublayerIndex points to this line).
				
				Valid values for configuration:
				fastOnly(2)          - only in dualLatency mode available          
				interleavedOnly(3)   - only in dualLatency mode available          
				
				If singleLatency mode is used on the underlaying dslInterface, the port will select
				the available channel for all existing VccTP's automaticaly.
				
				Note:
				Depending on the used AdslLineProfile configuration, the following scenarios are possible:
				1. default state:
				->line uses interleaved channel only
				->VccTp's uses always the available channel.
				->A modification of sheAdslVccTpUsedDslChannel will be rejected!
				2. modify line profile
				->line uses fast channel only
				->VccTp's uses always the available channel.
				->CXU send notifications. 
				->A modification of sheAdslVccTpUsedDslChannel will be rejected!
				3. modify line profile
				->line uses dualLatency
				->VccTp's uses the same channel as before. 
				4. modify VccTp entry
				->line uses dualLatency
				->the slected VccTp uses fast or interleaved channel only according to the configuration.
				->A setting of value fastOrInterleaved(4) will be rejected.
				5. modify line profile
				->line goes back to use interleaved channel only
				->VccTp's uses the interleaved channel ->notification will be send if a change is needed.
				"
			::= { sheAdslVccTpEntry 20 }

		
		sheAdslVccTpEncapsulation OBJECT-TYPE
			SYNTAX SheAdslAtmEncapType
			MAX-ACCESS read-only
			STATUS current
			DESCRIPTION
				"Used encapsulation type over AAL5 for this VccTp."
			DEFVAL { llc }
			::= { sheAdslVccTpEntry 21 }

		
--   1.3.6.1.4.1.231.7.1.2.2.1.6.1.1.26
		sheAdslVccTpControl OBJECT IDENTIFIER ::= { sheAdslLineMIB 26 }

		
--   1.3.6.1.4.1.231.7.1.2.2.1.6.1.1.26.1
		sheAdslVccTpControlRequest OBJECT-TYPE
			SYNTAX SheAdslControlRequestType
			MAX-ACCESS read-write
			STATUS current
			DESCRIPTION
				"createAdslVccTp:
				sheAdslVccTpControlSubLayerIndex
				sheAdslVccTpControlVpi
				sheAdslVccTpControlVci
				
				deleteAdslVccTp:
				sheAdslVccTpControlIndex
				
				modifyAdslVccTp:
				sheAdslVccTpControlIndex
				sheAdslVccTpControlVpi
				sheAdslVccTpControlVci
				sheAdslVccTpControlAlarmSeverityIndex
				
				modifyAdslVccTpLoopTest:
				sheAdslVccTpControlIndex
				sheAdslVccTpControlLoopTest
				
				modifyAdslVccTpEgressShaping:
				sheAdslVccTpControlIndex
				sheAdslVccTpControlEgressQosClass
				sheAdslVccTpControlEgressPeakCellRate
				sheAdslVccTpControlEgressSustainedCellRate
				sheAdslVccTpControlEgressMaxBurstSize
				sheAdslVccTpControlEgressWeight
				
				modifyAdslVccTpIngressPolicing:
				sheAdslVccTpControlIndex
				sheAdslVccTpControlIngressSustainedCellRate
				sheAdslVccTpControlIngressMaxBurstSize
				
				modifyAdslVccTpAdminState:
				sheAdslVccTpControlIndex
				sheAdslVccTpControlAdminState
				
				modifyAdslVccTpOrl:
				sheAdslVccTpControlIndex
				sheAdslVccTpControlOrl
				
				Only in dualLatency mode possible!!
				modifyAdslVccTpUsedDslChannel:
				sheAdslVccTpControlIndex
				sheAdslVccTpControlUsedDslChannel
				
				##
				New for R2.6
				deleteAdslVccTpPerformanceCounters:
				sheAdslVccTpControlIndex
				
				modifyAdslVccTpEncap:
				sheAdslVccTpControlIndex
				sheAdslVccTpControlEncapsulation"
			::= { sheAdslVccTpControl 1 }

		
--   1.3.6.1.4.1.231.7.1.2.2.1.6.1.1.26.2
		sheAdslVccTpControlIndex OBJECT-TYPE
			SYNTAX Integer32
			MAX-ACCESS read-write
			STATUS current
			DESCRIPTION
				"Index of the Table-entry to be configured."
			::= { sheAdslVccTpControl 2 }

		
--   1.3.6.1.4.1.231.7.1.2.2.1.6.1.1.26.3
		sheAdslVccTpControlStatus OBJECT-TYPE
			SYNTAX SheControlStatusType
			MAX-ACCESS read-only
			STATUS current
			DESCRIPTION
				"The status of a user command. 
				"
			::= { sheAdslVccTpControl 3 }

		
--   1.3.6.1.4.1.231.7.1.2.2.1.6.1.1.26.4
		sheAdslVccTpControlTimer OBJECT-TYPE
			SYNTAX Gauge32
			MAX-ACCESS read-only
			STATUS current
			DESCRIPTION
				"The maximum wait time for the manager for a long running user command. 
				"
			::= { sheAdslVccTpControl 4 }

		
--   1.3.6.1.4.1.231.7.1.2.2.1.6.1.1.26.5
		sheAdslVccTpControlReqResult OBJECT-TYPE
			SYNTAX SheAdslControlRequestResultType
			MAX-ACCESS read-only
			STATUS current
			DESCRIPTION
				"The result of the last user command."
			::= { sheAdslVccTpControl 5 }

		
--   1.3.6.1.4.1.231.7.1.2.2.1.6.1.1.26.6
		sheAdslVccTpControlTimeStamp OBJECT-TYPE
			SYNTAX Unsigned32
			UNITS "sec"
			MAX-ACCESS read-only
			STATUS current
			DESCRIPTION
				"The time stamp of the last command (end of command)."
			::= { sheAdslVccTpControl 6 }

		
--   1.3.6.1.4.1.231.7.1.2.2.1.6.1.1.26.7
		sheAdslVccTpControlSubLayerIndex OBJECT-TYPE
			SYNTAX InterfaceIndex
			MAX-ACCESS read-write
			STATUS current
			DESCRIPTION
				"Description."
			::= { sheAdslVccTpControl 7 }

		
--   1.3.6.1.4.1.231.7.1.2.2.1.6.1.1.26.9
		sheAdslVccTpControlVpi OBJECT-TYPE
			SYNTAX Integer32 (0..255)
			MAX-ACCESS read-write
			STATUS current
			DESCRIPTION
				"Vpi"
			::= { sheAdslVccTpControl 9 }

		
--   1.3.6.1.4.1.231.7.1.2.2.1.6.1.1.26.10
		sheAdslVccTpControlVci OBJECT-TYPE
			SYNTAX Integer32 (32..65535)
			MAX-ACCESS read-write
			STATUS current
			DESCRIPTION
				"Vci"
			::= { sheAdslVccTpControl 10 }

		
--   1.3.6.1.4.1.231.7.1.2.2.1.6.1.1.26.11
		sheAdslVccTpControlLoopTest OBJECT-TYPE
			SYNTAX SheAdslOamLoopTestType
			MAX-ACCESS read-write
			STATUS current
			DESCRIPTION
				"Actual LoopTest-Value. Only None or endToEnd will be accepted."
			::= { sheAdslVccTpControl 11 }

		
--   1.3.6.1.4.1.231.7.1.2.2.1.6.1.1.26.12
		sheAdslVccTpControlAlarmSeverityIndex OBJECT-TYPE
			SYNTAX SheAlarmSevProfileIndex
			MAX-ACCESS read-write
			STATUS current
			DESCRIPTION
				"Index of the used AlarmSeverityProfile."
			::= { sheAdslVccTpControl 12 }

		
--   1.3.6.1.4.1.231.7.1.2.2.1.6.1.1.26.13
		sheAdslVccTpControlEgressQosClass OBJECT-TYPE
			SYNTAX SheAdslAtmQosType
			MAX-ACCESS read-write
			STATUS current
			DESCRIPTION
				"Egress QoS Type."
			::= { sheAdslVccTpControl 13 }

		
--   1.3.6.1.4.1.231.7.1.2.2.1.6.1.1.26.14
		sheAdslVccTpControlEgressPeakCellRate OBJECT-TYPE
			SYNTAX Unsigned32 (0..365000)
			UNITS "cell/second"
			MAX-ACCESS read-write
			STATUS current
			DESCRIPTION
				"Valid when sheAdslVccTpEgressQosClass is not unshaped"
			::= { sheAdslVccTpControl 14 }

		
--   1.3.6.1.4.1.231.7.1.2.2.1.6.1.1.26.15
		sheAdslVccTpControlEgressSustainedCellRate OBJECT-TYPE
			SYNTAX Unsigned32 (0..365000)
			UNITS "cell/second"
			MAX-ACCESS read-write
			STATUS current
			DESCRIPTION
				"Valid when sheAdslVccTpEgressQosClass is shapingRtVbr or shapingNrtVbr"
			::= { sheAdslVccTpControl 15 }

		
--   1.3.6.1.4.1.231.7.1.2.2.1.6.1.1.26.16
		sheAdslVccTpControlEgressMaxBurstSize OBJECT-TYPE
			SYNTAX Unsigned32 (0..1073741824)
			UNITS "cell"
			MAX-ACCESS read-write
			STATUS current
			DESCRIPTION
				"Valid when sheAdslVccTpEgressQosClass is shapingRtVbr or shapingNrtVbr"
			::= { sheAdslVccTpControl 16 }

		
--   1.3.6.1.4.1.231.7.1.2.2.1.6.1.1.26.17
		sheAdslVccTpControlEgressWeight OBJECT-TYPE
			SYNTAX Integer32 (1..8)
			MAX-ACCESS read-write
			STATUS current
			DESCRIPTION
				"Valid only when sheAdslVccTpEgressQosClass is unshaped."
			::= { sheAdslVccTpControl 17 }

		
--   1.3.6.1.4.1.231.7.1.2.2.1.6.1.1.26.18
		sheAdslVccTpControlIngressSustainedCellRate OBJECT-TYPE
			SYNTAX Unsigned32 (0..365000)
			UNITS "cell/second"
			MAX-ACCESS read-write
			STATUS current
			DESCRIPTION
				"GFR scr for ingress policing"
			::= { sheAdslVccTpControl 18 }

		
--   1.3.6.1.4.1.231.7.1.2.2.1.6.1.1.26.19
		sheAdslVccTpControlIngressMaxBurstSize OBJECT-TYPE
			SYNTAX Unsigned32 (0..1073741824)
			UNITS "cell"
			MAX-ACCESS read-write
			STATUS current
			DESCRIPTION
				"GFR mbs for ingress policing"
			::= { sheAdslVccTpControl 19 }

		
--   1.3.6.1.4.1.231.7.1.2.2.1.6.1.1.26.20       	
		sheAdslVccTpControlAdminState OBJECT-TYPE
			SYNTAX SheAdslEnableType
			MAX-ACCESS read-write
			STATUS current
			DESCRIPTION
				"look at table"
			::= { sheAdslVccTpControl 20 }

		
--   1.3.6.1.4.1.231.7.1.2.2.1.6.1.1.26.21		
		sheAdslVccTpControlOrl OBJECT-TYPE
			SYNTAX Unsigned32 (64..29952)
			UNITS "kbps"
			MAX-ACCESS read-write
			STATUS current
			DESCRIPTION
				"look at table"
			::= { sheAdslVccTpControl 21 }

		
		sheAdslVccTpControlUsedDslChannel OBJECT-TYPE
			SYNTAX SheAdslConfLineType
			MAX-ACCESS read-write
			STATUS current
			DESCRIPTION
				"This attribute defines the usage of a dsl bearer channel by this VccTp.
				The availability of dsl channels depends on the configuration of the underlaying 
				adsl line (VccTpSublayerIndex points to this line).
				
				Valid values for configuration:
				fastOnly(2)          - only in dualLatency mode available          
				interleavedOnly(3)   - only in dualLatency mode available  
				
				In singleLatency mode , no configuration is possible.        
				
				"
			::= { sheAdslVccTpControl 22 }

		
		sheAdslVccTpControlEncapsulation OBJECT-TYPE
			SYNTAX SheAdslAtmEncapType
			MAX-ACCESS read-write
			STATUS current
			DESCRIPTION
				"Encapsulation type over AAL5."
			::= { sheAdslVccTpControl 23 }

		
--   1.3.6.1.4.1.231.7.1.2.2.1.6.1.1.27
		sheAdslVccTpNotifications OBJECT IDENTIFIER ::= { sheAdslLineMIB 27 }

		
--   1.3.6.1.4.1.231.7.1.2.2.1.6.1.1.27.1
		sheAdslVccTpCreated NOTIFICATION-TYPE
			OBJECTS { sheAdslVccTpControlIndex, sheAdslVccTpNumber, sheAdslVccTpControlTimeStamp, sheAdslVccTpControlVpi, sheAdslVccTpControlVci, 
				sheAdslVccTpControlAlarmSeverityIndex, sheAdslVccTpControlSubLayerIndex, sheAdslVccTpControlLoopTest, sheAdslVccTpControlOrl, sheAdslVccTpControlAdminState
				 }
			STATUS current
			DESCRIPTION 
				"Configuration notification."
			::= { sheAdslVccTpNotifications 1 }

		
--   1.3.6.1.4.1.231.7.1.2.2.1.6.1.1.27.2
		sheAdslVccTpModified NOTIFICATION-TYPE
			OBJECTS { sheAdslVccTpControlIndex, sheAdslVccTpControlTimeStamp, sheAdslVccTpControlVpi, sheAdslVccTpControlVci, sheAdslVccTpControlLoopTest, 
				sheAdslVccTpControlAlarmSeverityIndex }
			STATUS current
			DESCRIPTION 
				"Configuration notification."
			::= { sheAdslVccTpNotifications 2 }

		
--   1.3.6.1.4.1.231.7.1.2.2.1.6.1.1.27.3
		sheAdslVccTpDeleted NOTIFICATION-TYPE
			OBJECTS { sheAdslVccTpControlIndex, sheAdslVccTpControlTimeStamp }
			STATUS current
			DESCRIPTION 
				"Configuration notification."
			::= { sheAdslVccTpNotifications 3 }

		
--   1.3.6.1.4.1.231.7.1.2.2.1.6.1.1.27.4
		sheAdslVccRDIAlarm NOTIFICATION-TYPE
			OBJECTS { sheAlarmTimeAndDate, sheAlarmReportingSource, sheAlarmReportingSourceType, sheAlarmSeverity }
			STATUS current
			DESCRIPTION 
				"RDI detected."
			::= { sheAdslVccTpNotifications 4 }

		
--   1.3.6.1.4.1.231.7.1.2.2.1.6.1.1.27.5
		sheAdslVccAISAlarm NOTIFICATION-TYPE
			OBJECTS { sheAlarmTimeAndDate, sheAlarmReportingSource, sheAlarmReportingSourceType, sheAlarmSeverity }
			STATUS current
			DESCRIPTION 
				"AIS detected. "
			::= { sheAdslVccTpNotifications 5 }

		
--   1.3.6.1.4.1.231.7.1.2.2.1.6.1.1.27.6
		sheAdslVccTpConfigurationFailed NOTIFICATION-TYPE
			OBJECTS { sheAdslVccTpControlRequest, sheAdslVccTpControlIndex, sheAdslVccTpControlTimeStamp, sheAdslVccTpControlStatus, sheAdslVccTpControlReqResult, 
				sheAdslVccTpControlSubLayerIndex }
			STATUS current
			DESCRIPTION 
				"Notification in case of failed VccTp-Configuration."
			::= { sheAdslVccTpNotifications 6 }

		
--   1.3.6.1.4.1.231.7.1.2.2.1.6.1.1.27.7
		sheAdslVccTpChangedEgressShaping NOTIFICATION-TYPE
			OBJECTS { sheAdslVccTpControlIndex, sheAdslVccTpControlEgressQosClass, sheAdslVccTpControlEgressPeakCellRate, sheAdslVccTpControlEgressSustainedCellRate, sheAdslVccTpControlEgressMaxBurstSize, 
				sheAdslVccTpControlEgressWeight }
			STATUS current
			DESCRIPTION 
				"ATM egress shaping paramters were changed."
			::= { sheAdslVccTpNotifications 7 }

		
--   1.3.6.1.4.1.231.7.1.2.2.1.6.1.1.27.8
		sheAdslVccTpChangedIngressPolicing NOTIFICATION-TYPE
			OBJECTS { sheAdslVccTpControlIndex, sheAdslVccTpControlIngressSustainedCellRate, sheAdslVccTpControlIngressMaxBurstSize }
			STATUS current
			DESCRIPTION 
				"ATM ingress policing paramters were changed."
			::= { sheAdslVccTpNotifications 8 }

		
--   1.3.6.1.4.1.231.7.1.2.2.1.6.1.1.27.9			
		sheAdslVccTpAdminStateChanged NOTIFICATION-TYPE
			OBJECTS { sheAdslVccTpControlIndex, sheAdslVccTpControlTimeStamp, sheAdslVccTpControlAdminState }
			STATUS current
			DESCRIPTION 
				"Configuration notification."
			::= { sheAdslVccTpNotifications 9 }

		
--   1.3.6.1.4.1.231.7.1.2.2.1.6.1.1.27.10		
		sheAdslVccTpOrlChanged NOTIFICATION-TYPE
			OBJECTS { sheAdslVccTpControlIndex, sheAdslVccTpControlTimeStamp, sheAdslVccTpControlOrl }
			STATUS current
			DESCRIPTION 
				"Configuration trap."
			::= { sheAdslVccTpNotifications 10 }

		
--   1.3.6.1.4.1.231.7.1.2.2.1.6.1.1.27.10		
		sheAdslVccTpUsedDslChannelChanged NOTIFICATION-TYPE
			OBJECTS { sheAdslVccTpControlIndex, sheAdslVccTpControlTimeStamp, sheAdslVccTpControlUsedDslChannel }
			STATUS current
			DESCRIPTION 
				"Modification trap."
			::= { sheAdslVccTpNotifications 11 }

		
--   1.3.6.1.4.1.231.7.1.2.2.1.6.1.1.27.3
		sheAdslVccTpPerformanceCountersCleared NOTIFICATION-TYPE
			OBJECTS { sheAdslVccTpControlIndex, sheAdslVccTpControlTimeStamp }
			STATUS current
			DESCRIPTION 
				"Configuration notification."
			::= { sheAdslVccTpNotifications 12 }

		
--   1.3.6.1.4.1.231.7.1.2.2.1.6.1.1.27.3
		sheAdslVccTpEncapsulationChanged NOTIFICATION-TYPE
			OBJECTS { sheAdslVccTpControlIndex, sheAdslVccTpControlTimeStamp, sheAdslVccTpControlEncapsulation }
			STATUS current
			DESCRIPTION 
				"Configuration notification."
			::= { sheAdslVccTpNotifications 13 }

		
--  RFI BAND
-- 1.3.6.1.4.1.231.7.1.2.2.1.6.1.1.29
		sheAdslRfiBandTable OBJECT-TYPE
			SYNTAX SEQUENCE OF SheAdslRfiBandEntry
			MAX-ACCESS not-accessible
			STATUS current
			DESCRIPTION
				"The RFI Band Table."
			::= { sheAdslLineMIB 29 }

		
--   1.3.6.1.4.1.231.7.1.2.2.1.6.1.1.29.1
		sheAdslRfiBandEntry OBJECT-TYPE
			SYNTAX SheAdslRfiBandEntry
			MAX-ACCESS not-accessible
			STATUS current
			DESCRIPTION
				"This table contains RFI band configuration.
				For more details, refer ITU-T G.992.5 and ITU-T G.997.1."
			INDEX { sheAdslRfiBandIndex }
			::= { sheAdslRfiBandTable 1 }

		
		SheAdslRfiBandEntry ::=
			SEQUENCE { 
				sheAdslRfiBandIndex
					Integer32,
				sheAdslRfiBandName
					OCTET STRING,
				sheAdslRfiBandStartTone
					Integer32,
				sheAdslRfiBandStopTone
					Integer32
			 }

--   1.3.6.1.4.1.231.7.1.2.2.1.6.1.1.29.1.1
		sheAdslRfiBandIndex OBJECT-TYPE
			SYNTAX Integer32 (1..32)
			MAX-ACCESS read-only
			STATUS current
			DESCRIPTION
				"Table Index, automatically generated when the table is created.
				This is used as Bit mask index of sheAdslLineConfExtnProfileRfiBandMask"
			::= { sheAdslRfiBandEntry 1 }

		
--   1.3.6.1.4.1.231.7.1.2.2.1.6.1.1.29.1.2
		sheAdslRfiBandName OBJECT-TYPE
			SYNTAX OCTET STRING (SIZE (1..32))
			MAX-ACCESS read-only
			STATUS current
			DESCRIPTION
				"A descriptional name for the RFI band.
				
				Special characters are not allowed, like:  space : ?"
			::= { sheAdslRfiBandEntry 2 }

		
--   1.3.6.1.4.1.231.7.1.2.2.1.6.1.1.29.1.3
		sheAdslRfiBandStartTone OBJECT-TYPE
			SYNTAX Integer32 (1..512)
			MAX-ACCESS read-only
			STATUS current
			DESCRIPTION
				"The start subcarrier index belonging to breakpoint:[ti;ti+1],
				corresponding to the low level of notch."
			::= { sheAdslRfiBandEntry 3 }

		
--   1.3.6.1.4.1.231.7.1.2.2.1.6.1.1.29.1.4
		sheAdslRfiBandStopTone OBJECT-TYPE
			SYNTAX Integer32 (1..512)
			MAX-ACCESS read-only
			STATUS current
			DESCRIPTION
				"The stop subcarrier index belonging to breakpoint:[ti;ti+1],
				corresponding to the low level of notch."
			::= { sheAdslRfiBandEntry 4 }

		
--   1.3.6.1.4.1.231.7.1.2.2.1.6.1.1.30
		sheAdslRfiBandControl OBJECT IDENTIFIER ::= { sheAdslLineMIB 30 }

		
--   1.3.6.1.4.1.231.7.1.2.2.1.6.1.1.30.1
		sheAdslRfiBandControlRequest OBJECT-TYPE
			SYNTAX SheAdslControlRequestType
			MAX-ACCESS read-write
			STATUS current
			DESCRIPTION
				"createAdslRfiBand:
				sheAdslRfiBandControlName
				sheAdslRfiBandControlStartTone
				sheAdslRfiBandControlStopTone
				
				deleteAdslRfiBand:
				sheAdslRfiBandControlIndex"
			::= { sheAdslRfiBandControl 1 }

		
--   1.3.6.1.4.1.231.7.1.2.2.1.6.1.1.30.2
		sheAdslRfiBandControlIndex OBJECT-TYPE
			SYNTAX Integer32
			MAX-ACCESS read-write
			STATUS current
			DESCRIPTION
				"Index of the Table-entry to be configured."
			::= { sheAdslRfiBandControl 2 }

		
--   1.3.6.1.4.1.231.7.1.2.2.1.6.1.1.30.3
		sheAdslRfiBandControlStatus OBJECT-TYPE
			SYNTAX SheControlStatusType
			MAX-ACCESS read-only
			STATUS current
			DESCRIPTION
				"The status of a user command. 
				"
			::= { sheAdslRfiBandControl 3 }

		
--   1.3.6.1.4.1.231.7.1.2.2.1.6.1.1.30.4
		sheAdslRfiBandControlTimer OBJECT-TYPE
			SYNTAX Gauge32
			MAX-ACCESS read-only
			STATUS current
			DESCRIPTION
				"The maximum wait time for the manager for a long running user command. 
				"
			::= { sheAdslRfiBandControl 4 }

		
--   1.3.6.1.4.1.231.7.1.2.2.1.6.1.1.30.5
		sheAdslRfiBandControlReqResult OBJECT-TYPE
			SYNTAX SheAdslControlRequestResultType
			MAX-ACCESS read-only
			STATUS current
			DESCRIPTION
				"The result of the last user command."
			::= { sheAdslRfiBandControl 5 }

		
--   1.3.6.1.4.1.231.7.1.2.2.1.6.1.1.30.6
		sheAdslRfiBandControlTimeStamp OBJECT-TYPE
			SYNTAX Unsigned32
			UNITS "sec"
			MAX-ACCESS read-only
			STATUS current
			DESCRIPTION
				"The time stamp of the last command (end of command)."
			::= { sheAdslRfiBandControl 6 }

		
--   1.3.6.1.4.1.231.7.1.2.2.1.6.1.1.30.7
		sheAdslRfiBandControlName OBJECT-TYPE
			SYNTAX OCTET STRING (SIZE (1..32))
			MAX-ACCESS read-write
			STATUS current
			DESCRIPTION
				"A descriptional name for the RFI band."
			::= { sheAdslRfiBandControl 7 }

		
--   1.3.6.1.4.1.231.7.1.2.2.1.6.1.1.30.8
		sheAdslRfiBandControlStartTone OBJECT-TYPE
			SYNTAX Integer32 (1..512)
			MAX-ACCESS read-write
			STATUS current
			DESCRIPTION
				"The start subcarrier index belonging to breakpoint:[ti;ti+1],
				corresponding to the low level of notch."
			::= { sheAdslRfiBandControl 8 }

		
--   1.3.6.1.4.1.231.7.1.2.2.1.6.1.1.30.9
		sheAdslRfiBandControlStopTone OBJECT-TYPE
			SYNTAX Integer32 (1..512)
			MAX-ACCESS read-write
			STATUS current
			DESCRIPTION
				"The stop subcarrier index belonging to breakpoint:[ti;ti+1],
				corresponding to the low level of notch."
			::= { sheAdslRfiBandControl 9 }

		
--   1.3.6.1.4.1.231.7.1.2.2.1.6.1.1.31
		sheAdslRfiBandNotifications OBJECT IDENTIFIER ::= { sheAdslLineMIB 31 }

		
--   1.3.6.1.4.1.231.7.1.2.2.1.6.1.1.31.1
		sheAdslRfiBandCreated NOTIFICATION-TYPE
			OBJECTS { sheAdslRfiBandControlIndex, sheAdslRfiBandControlName, sheAdslRfiBandControlStartTone, sheAdslRfiBandControlStopTone }
			STATUS current
			DESCRIPTION 
				"When an ADSL RFI Band is created, it occurs."
			::= { sheAdslRfiBandNotifications 1 }

		
--   1.3.6.1.4.1.231.7.1.2.2.1.6.1.1.31.2
		sheAdslRfiBandDeleted NOTIFICATION-TYPE
			OBJECTS { sheAdslRfiBandControlIndex }
			STATUS current
			DESCRIPTION 
				"When an ADSL RFI Band is removed, it occurs."
			::= { sheAdslRfiBandNotifications 2 }

		
--   1.3.6.1.4.1.231.7.1.2.2.1.6.1.1.32
		sheAdslAtucPsdRefMasks OBJECT IDENTIFIER ::= { sheAdslLineMIB 32 }

		
--   1.3.6.1.4.1.231.7.1.2.2.1.6.1.1.32.1
		sheAdslAtucPsdRefMaskAdsl2AnnexA OBJECT-TYPE
			SYNTAX OCTET STRING (SIZE (6..96))
			MAX-ACCESS read-only
			STATUS current
			DESCRIPTION
				"
				< PSD reference mask data format description >
				PSD mask can be described with a set of breakpoints. Breakpoint is a pair of tone index and PSD level. 
				Number of maximum breakpoint is 32. All variable in this format is network byte order (big endian).
				
				< Data field of PSD reference mask >
				Breakpoint# tone index : tone index for breakpoint. Valid range is 1~255 for sheAdslAtucPsdRefMaskAdsl2AnnexA, sheAdslAtucPsdRefMaskAdsl2AnnexB and sheAdslAtucPsdRefMaskAnnexL, 
				1-511 for sheAdslAtucPsdRefMaskAdsl2plusAnnexA and sheAdslAtucPsdRefMaskAdsl2plusAnnexB. 
				Breakpoint# PSD level : According to ITU-T G.997.1, the PSD maks level shall be coded as an unsigned integer represening PSD levels 0dBm/Hz (coded as 0) to -127.5 dBm/Hz (coded as 255), 
				in the steps of 0.5dBm/Hz, with valid range 0 to -95dBm/Hz. So Valid value range is 0~190. 
				Tone index of first breakpoint should be 1. Tone index of last valid breakpoint should be 255 in case of Adsl2AnnexA, Adsl2AnnexB, AnnexL. 
				And should be 511 for Adsl2plusAnnexA, Adsl2plusAnnexB case Breakpoint should be alligned with increasing tone order.
				
				< PSD Reference mask data format (Maximum 128 bytes) >
				Breakpoint1 tone index (2bytes)	Breakpoint1 PSD level (1bytes)
				Breakpoint2 tone index (2bytes)	Breakpoint2 PSD level (1bytes)
				Breakpoint3 tone index (2bytes)	Breakpoint3 PSD level (1bytes)
				Breakpoint32 tone index (2bytes)	Breakpoint32 PSD level (1bytes)
				"
			::= { sheAdslAtucPsdRefMasks 1 }

		
--   1.3.6.1.4.1.231.7.1.2.2.1.6.1.1.32.2
		sheAdslAtucPsdRefMaskAdsl2AnnexB OBJECT-TYPE
			SYNTAX OCTET STRING (SIZE (6..96))
			MAX-ACCESS read-only
			STATUS current
			DESCRIPTION
				"Refer to the sheAdslAtucPsdRefMaskAdsl2AnnexA description."
			::= { sheAdslAtucPsdRefMasks 2 }

		
--   1.3.6.1.4.1.231.7.1.2.2.1.6.1.1.32.3
		sheAdslAtucPsdRefMaskAdsl2plusAnnexA OBJECT-TYPE
			SYNTAX OCTET STRING (SIZE (6..96))
			MAX-ACCESS read-only
			STATUS current
			DESCRIPTION
				"Refer to the sheAdslAtucPsdRefMaskAdsl2AnnexA description."
			::= { sheAdslAtucPsdRefMasks 3 }

		
--   1.3.6.1.4.1.231.7.1.2.2.1.6.1.1.32.4
		sheAdslAtucPsdRefMaskAdsl2plusAnnexB OBJECT-TYPE
			SYNTAX OCTET STRING (SIZE (6..96))
			MAX-ACCESS read-only
			STATUS current
			DESCRIPTION
				"Refer to the sheAdslAtucPsdRefMaskAdsl2AnnexA description."
			::= { sheAdslAtucPsdRefMasks 4 }

		
--   1.3.6.1.4.1.231.7.1.2.2.1.6.1.1.32.5
		sheAdslAtucPsdRefMaskAnnexL OBJECT-TYPE
			SYNTAX OCTET STRING (SIZE (6..96))
			MAX-ACCESS read-only
			STATUS current
			DESCRIPTION
				"Refer to the sheAdslAtucPsdRefMaskAdsl2AnnexA description"
			::= { sheAdslAtucPsdRefMasks 5 }

		
--   1.3.6.1.4.1.231.7.1.2.2.1.6.1.1.33
		sheAdslAtucDualChanTable OBJECT-TYPE
			SYNTAX SEQUENCE OF SheAdslAtucDualChanEntry
			MAX-ACCESS not-accessible
			STATUS current
			DESCRIPTION
				"This table provides one row for each ATUC channel. Only supported by NE R2.5 and higher."
			::= { sheAdslLineMIB 33 }

		
--   1.3.6.1.4.1.231.7.1.2.2.1.6.1.1.33.1
		sheAdslAtucDualChanEntry OBJECT-TYPE
			SYNTAX SheAdslAtucDualChanEntry
			MAX-ACCESS not-accessible
			STATUS current
			DESCRIPTION
				"An entry in the adslAtucChanTable. New table only supported by NE releases up R2.5.
				Indexed by ifIndex - ChanType."
			INDEX { ifIndex, sheAdslAtucDualChanType }
			::= { sheAdslAtucDualChanTable 1 }

		
		SheAdslAtucDualChanEntry ::=
			SEQUENCE { 
				sheAdslAtucDualChanInterleaveDelay
					Gauge32,
				sheAdslAtucDualChanCurrTxRate
					Gauge32,
				sheAdslAtucDualChanPrevTxRate
					Gauge32,
				sheAdslAtucDualChanCrcBlockLength
					Gauge32,
				sheAdslAtucDualChanCurrAtmStatus
					SheAdslLineAtmStatus,
				sheAdslAtucDualChanRsSymbols
					Unsigned32,
				sheAdslAtucDualChanRsDepth
					Unsigned32,
				sheAdslAtucDualChanRsRedundancy
					Unsigned32,
				sheAdslAtucDualChanType
					SheAdslChannelType
			 }

--   1.3.6.1.4.1.231.7.1.2.2.1.6.1.1.33.1.1
		sheAdslAtucDualChanInterleaveDelay OBJECT-TYPE
			SYNTAX Gauge32
			UNITS "milli-seconds"
			MAX-ACCESS read-only
			STATUS current
			DESCRIPTION
				"Interleave Delay for this channel.
				
				Interleave delay applies only to the
				interleave channel and defines the mapping
				(relative spacing) between subsequent input
				bytes at the interleaver input and their placement
				in the bit stream at the interleaver output.
				Larger numbers provide greater separation between
				consecutive input bytes in the output bit stream
				allowing for improved impulse noise immunity at
				the expense of payload latency.
				
				In the case where the ifType is Fast(125), use
				noSuchObject."
			::= { sheAdslAtucDualChanEntry 1 }

		
--   1.3.6.1.4.1.231.7.1.2.2.1.6.1.1.33.1.2
		sheAdslAtucDualChanCurrTxRate OBJECT-TYPE
			SYNTAX Gauge32 (1..32736)
			UNITS "kbps"
			MAX-ACCESS read-only
			STATUS current
			DESCRIPTION
				"Actual transmit rate on this channel."
			::= { sheAdslAtucDualChanEntry 2 }

		
--   1.3.6.1.4.1.231.7.1.2.2.1.6.1.1.33.1.3
		sheAdslAtucDualChanPrevTxRate OBJECT-TYPE
			SYNTAX Gauge32 (1..32736)
			UNITS "kbps"
			MAX-ACCESS read-only
			STATUS current
			DESCRIPTION
				"The rate at the time of the last
				adslAtucRateChangeTrap event. It is also set at
				initialization to prevent a trap being sent.
				
				Rate changes less than adslAtucThresh(*)RateDown
				or less than adslAtucThresh(*)RateUp will not
				cause a trap or cause this object to change.
				(*) == Fast or Interleave.
				See AdslLineAlarmConfProfileEntry."
			::= { sheAdslAtucDualChanEntry 3 }

		
--   1.3.6.1.4.1.231.7.1.2.2.1.6.1.1.33.1.4
		sheAdslAtucDualChanCrcBlockLength OBJECT-TYPE
			SYNTAX Gauge32
			UNITS "byte"
			MAX-ACCESS read-only
			STATUS current
			DESCRIPTION
				"Indicates the length of the channel data-block
				on which the CRC operates.  Refer to Line Code
				Specific MIBs, [11] and [12] for more
				information."
			::= { sheAdslAtucDualChanEntry 4 }

		
--   1.3.6.1.4.1.231.7.1.2.2.1.6.1.1.33.1.5
		sheAdslAtucDualChanCurrAtmStatus OBJECT-TYPE
			SYNTAX SheAdslLineAtmStatus
			MAX-ACCESS read-only
			STATUS current
			DESCRIPTION
				"indicates an ncd or lcd failure if the counter surpasses 127. If neither ATM counter surpasses 127, the return value will be 'NoAtmDefect'.
				noAtmDefect(0),
				noCellDeleniation(1),
				lossOfCellDeleniation(2)
				"
			::= { sheAdslAtucDualChanEntry 5 }

		
--   1.3.6.1.4.1.231.7.1.2.2.1.6.1.1.33.1.6
		sheAdslAtucDualChanRsSymbols OBJECT-TYPE
			SYNTAX Unsigned32
			MAX-ACCESS read-only
			STATUS current
			DESCRIPTION
				"Indicates number of DMT symbols per Reed-Solomon code word (S) in the downstream direction. Note that S is not restricted to interleaved mode only. Even in fast mode, S is a valid constant value and is equal to 1."
			::= { sheAdslAtucDualChanEntry 6 }

		
--   1.3.6.1.4.1.231.7.1.2.2.1.6.1.1.33.1.7
		sheAdslAtucDualChanRsDepth OBJECT-TYPE
			SYNTAX Unsigned32
			MAX-ACCESS read-only
			STATUS current
			DESCRIPTION
				"Indicates interleaving depth (D) in the downstream direction. Note that D is not restricted to interleaved mode only. Even in fast mode, D is a valid constant value and is equal to 1."
			::= { sheAdslAtucDualChanEntry 7 }

		
--   1.3.6.1.4.1.231.7.1.2.2.1.6.1.1.33.1.8
		sheAdslAtucDualChanRsRedundancy OBJECT-TYPE
			SYNTAX Unsigned32
			MAX-ACCESS read-only
			STATUS current
			DESCRIPTION
				"Indicates number of redundant bytes (R) per Reed-Solomon code in the downstream direction."
			::= { sheAdslAtucDualChanEntry 8 }

		
--   1.3.6.1.4.1.231.7.1.2.2.1.6.1.1.33.1.9
		sheAdslAtucDualChanType OBJECT-TYPE
			SYNTAX SheAdslChannelType
			MAX-ACCESS read-only
			STATUS current
			DESCRIPTION
				"Explains the type of channel entry interleaved or fast!
				
				(1) interleaved channel
				(2) fast channel"
			::= { sheAdslAtucDualChanEntry 9 }

		
--   1.3.6.1.4.1.231.7.1.2.2.1.6.1.1.34
		sheAdslAturDualChanTable OBJECT-TYPE
			SYNTAX SEQUENCE OF SheAdslAturDualChanEntry
			MAX-ACCESS not-accessible
			STATUS current
			DESCRIPTION
				"This table provides one row for each ATUR channel. Only supported by NE R2.5 and higher."
			::= { sheAdslLineMIB 34 }

		
--   1.3.6.1.4.1.231.7.1.2.2.1.6.1.1.34.1
		sheAdslAturDualChanEntry OBJECT-TYPE
			SYNTAX SheAdslAturDualChanEntry
			MAX-ACCESS not-accessible
			STATUS current
			DESCRIPTION
				"An entry in the adslAturChanTable. New table only supported by NE releases up R2.5.
				Indexed by ifIndex - ChanType."
			INDEX { ifIndex, sheAdslAturDualChanType }
			::= { sheAdslAturDualChanTable 1 }

		
		SheAdslAturDualChanEntry ::=
			SEQUENCE { 
				sheAdslAturDualChanInterleaveDelay
					Gauge32,
				sheAdslAturDualChanCurrTxRate
					Gauge32,
				sheAdslAturDualChanPrevTxRate
					Gauge32,
				sheAdslAturDualChanCrcBlockLength
					Gauge32,
				sheAdslAturDualChanCurrAtmStatus
					SheAdslLineAtmStatus,
				sheAdslAturDualChanRsSymbols
					Unsigned32,
				sheAdslAturDualChanRsDepth
					Unsigned32,
				sheAdslAturDualChanRsRedundancy
					Unsigned32,
				sheAdslAturDualChanType
					SheAdslChannelType
			 }

--   1.3.6.1.4.1.231.7.1.2.2.1.6.1.1.34.1.1
		sheAdslAturDualChanInterleaveDelay OBJECT-TYPE
			SYNTAX Gauge32
			UNITS "milli-seconds"
			MAX-ACCESS read-only
			STATUS current
			DESCRIPTION
				"Interleave Delay for this channel.
				
				Interleave delay applies only to the
				interleave channel and defines the mapping
				(relative spacing) between subsequent input
				bytes at the interleaver input and their placement
				in the bit stream at the interleaver output.
				Larger numbers provide greater separation between
				consecutive input bytes in the output bit stream
				allowing for improved impulse noise immunity at
				the expense of payload latency.
				
				In the case where the ifType is Fast(125), use
				noSuchObject."
			::= { sheAdslAturDualChanEntry 1 }

		
--   1.3.6.1.4.1.231.7.1.2.2.1.6.1.1.34.1.2
		sheAdslAturDualChanCurrTxRate OBJECT-TYPE
			SYNTAX Gauge32 (1..32736)
			UNITS "kbps"
			MAX-ACCESS read-only
			STATUS current
			DESCRIPTION
				"Actual transmit rate on this channel."
			::= { sheAdslAturDualChanEntry 2 }

		
--   1.3.6.1.4.1.231.7.1.2.2.1.6.1.1.34.1.3
		sheAdslAturDualChanPrevTxRate OBJECT-TYPE
			SYNTAX Gauge32 (1..32736)
			UNITS "kbps"
			MAX-ACCESS read-only
			STATUS current
			DESCRIPTION
				"The rate at the time of the last
				adslAturRateChangeTrap event. It is also set at
				initialization to prevent a trap being sent.
				Rate changes less than adslAturThresh(*)RateDown
				or less than adslAturThresh(*)RateUp will not
				cause a trap or cause this object to change.
				(*) == Fast or Interleave.
				See AdslLineAlarmConfProfileEntry."
			::= { sheAdslAturDualChanEntry 3 }

		
--   1.3.6.1.4.1.231.7.1.2.2.1.6.1.1.34.1.4
		sheAdslAturDualChanCrcBlockLength OBJECT-TYPE
			SYNTAX Gauge32
			MAX-ACCESS read-only
			STATUS current
			DESCRIPTION
				"Indicates the length of the channel data-block
				on which the CRC operates.  Refer to Line Code
				Specific MIBs, [11] and [12] for more
				information."
			::= { sheAdslAturDualChanEntry 4 }

		
--   1.3.6.1.4.1.231.7.1.2.2.1.6.1.1.34.1.5
		sheAdslAturDualChanCurrAtmStatus OBJECT-TYPE
			SYNTAX SheAdslLineAtmStatus
			MAX-ACCESS read-only
			STATUS current
			DESCRIPTION
				"This object indicates an ncd or lcd failure if the counter surpasses 127. If neither ATM counter surpasses 127, the return value will be NoAtmDefect.
				noAtmDefect(0),
				noCellDeleniation(1),
				lossOfCellDeleniation(2)
				"
			::= { sheAdslAturDualChanEntry 5 }

		
--   1.3.6.1.4.1.231.7.1.2.2.1.6.1.1.34.1.6
		sheAdslAturDualChanRsSymbols OBJECT-TYPE
			SYNTAX Unsigned32
			MAX-ACCESS read-only
			STATUS current
			DESCRIPTION
				"This object indicates number of DMT symbols per Reed- Solomon code word (S) in the upstream direction Note that S is not restricted to interleaved mode only. Even in fast mode, S is a valid constant value and is equal to 1."
			::= { sheAdslAturDualChanEntry 6 }

		
--   1.3.6.1.4.1.231.7.1.2.2.1.6.1.1.34.1.7
		sheAdslAturDualChanRsDepth OBJECT-TYPE
			SYNTAX Unsigned32
			MAX-ACCESS read-only
			STATUS current
			DESCRIPTION
				"This object indicates interleaving depth (D) in the upstream direction Note that D is not restricted to interleaved mode only. Even in fast mode, D is a valid constant value and is equal to 1."
			::= { sheAdslAturDualChanEntry 7 }

		
--   1.3.6.1.4.1.231.7.1.2.2.1.6.1.1.34.1.8
		sheAdslAturDualChanRsRedundancy OBJECT-TYPE
			SYNTAX Unsigned32
			MAX-ACCESS read-only
			STATUS current
			DESCRIPTION
				"This object indicates number of redundant bytes (R) per Reed-Solomon code in the upstream direction."
			::= { sheAdslAturDualChanEntry 8 }

		
--   1.3.6.1.4.1.231.7.1.2.2.1.6.1.1.34.1.9
		sheAdslAturDualChanType OBJECT-TYPE
			SYNTAX SheAdslChannelType
			MAX-ACCESS read-only
			STATUS current
			DESCRIPTION
				"Explains the type of channel entry interleaved or fast!
				
				(1) interleaved channel
				(2) fast channel"
			::= { sheAdslAturDualChanEntry 9 }

		
--   1.3.6.1.4.1.231.7.1.2.2.1.6.1.1.35
-- performance group
-- 
-- Note: block is intended to be the length of the channel
--       data-block on which the CRC operates. See
--       adslAtucDualChanCrcBlockLength for more information.
		sheAdslAtucDualChanPerfDataTable OBJECT-TYPE
			SYNTAX SEQUENCE OF SheAdslAtucDualChanPerfDataEntry
			MAX-ACCESS not-accessible
			STATUS current
			DESCRIPTION
				"This table provides one row for each ATUC channel. Only supported by NE R2.5 and higher."
			::= { sheAdslLineMIB 35 }

		
--   1.3.6.1.4.1.231.7.1.2.2.1.6.1.1.35.1
		sheAdslAtucDualChanPerfDataEntry OBJECT-TYPE
			SYNTAX SheAdslAtucDualChanPerfDataEntry
			MAX-ACCESS not-accessible
			STATUS current
			DESCRIPTION
				"An entry in adslAtucChanPerfDataTable. New table only supported by NE releases up R2.5.
				Indexed by ifIndex - ChanType."
			INDEX { ifIndex, sheAdslAtucDualChanType }
			::= { sheAdslAtucDualChanPerfDataTable 1 }

		
		SheAdslAtucDualChanPerfDataEntry ::=
			SEQUENCE { 
				sheAdslAtucDualChanPerfDataTimeElapsed
					Gauge32,
				sheAdslAtucDualChanPerfDataReceivedBlks
					Counter32,
				sheAdslAtucDualChanPerfDataTransmittedBlks
					Counter32,
				sheAdslAtucDualChanPerfDataCorrectedBlks
					Counter32,
				sheAdslAtucDualChanPerfDataUncorrectBlks
					Counter32,
				sheAdslAtucDualChanPerfDataNcd
					Gauge32,
				sheAdslAtucDualChanPerfDataOcd
					Gauge32,
				sheAdslAtucDualChanPerfDataHec
					Gauge32,
				sheAdslAtucDualChanPerfDataValidIntervals
					INTEGER,
				sheAdslAtucDualChanPerfDataInvalidIntervals
					INTEGER,
				sheAdslAtucDualChanPerfDataCurr15MinTimeElapsed
					AdslPerfTimeElapsed,
				sheAdslAtucDualChanPerfDataCurr15MinReceivedBlks
					PerfCurrentCount,
				sheAdslAtucDualChanPerfDataCurr15MinTransmittedBlks
					PerfCurrentCount,
				sheAdslAtucDualChanPerfDataCurr15MinCorrectedBlks
					PerfCurrentCount,
				sheAdslAtucDualChanPerfDataCurr15MinUncorrectBlks
					PerfCurrentCount,
				sheAdslAtucDualChanPerfDataCurr15MinNcd
					Gauge32,
				sheAdslAtucDualChanPerfDataCurr15MinOcd
					Gauge32,
				sheAdslAtucDualChanPerfDataCurr15MinHec
					Gauge32,
				sheAdslAtucDualChanPerfDataCurr1DayTimeElapsed
					AdslPerfTimeElapsed,
				sheAdslAtucDualChanPerfDataCurr1DayReceivedBlks
					AdslPerfCurrDayCount,
				sheAdslAtucDualChanPerfDataCurr1DayTransmittedBlks
					AdslPerfCurrDayCount,
				sheAdslAtucDualChanPerfDataCurr1DayCorrectedBlks
					AdslPerfCurrDayCount,
				sheAdslAtucDualChanPerfDataCurr1DayUncorrectBlks
					AdslPerfCurrDayCount,
				sheAdslAtucDualChanPerfDataCurr1DayNcd
					Gauge32,
				sheAdslAtucDualChanPerfDataCurr1DayOcd
					Gauge32,
				sheAdslAtucDualChanPerfDataCurr1DayHec
					Gauge32,
				sheAdslAtucDualChanPerfDataPrev1DayMoniSecs
					INTEGER,
				sheAdslAtucDualChanPerfDataPrev1DayReceivedBlks
					AdslPerfPrevDayCount,
				sheAdslAtucDualChanPerfDataPrev1DayTransmittedBlks
					AdslPerfPrevDayCount,
				sheAdslAtucDualChanPerfDataPrev1DayCorrectedBlks
					AdslPerfPrevDayCount,
				sheAdslAtucDualChanPerfDataPrev1DayUncorrectBlks
					AdslPerfPrevDayCount,
				sheAdslAtucDualChanPerfDataPrev1DayNcd
					Gauge32,
				sheAdslAtucDualChanPerfDataPrev1DayOcd
					Gauge32,
				sheAdslAtucDualChanPerfDataPrev1DayHec
					Gauge32
			 }

--   1.3.6.1.4.1.231.7.1.2.2.1.6.1.1.35.1.1
		sheAdslAtucDualChanPerfDataTimeElapsed OBJECT-TYPE
			SYNTAX Gauge32
			MAX-ACCESS read-only
			STATUS current
			DESCRIPTION
				" Total elapsed seconds in this interval."
			::= { sheAdslAtucDualChanPerfDataEntry 1 }

		
--  1.3.6.1.4.1.231.7.1.2.2.1.6.1.1.35.1.2
		sheAdslAtucDualChanPerfDataReceivedBlks OBJECT-TYPE
			SYNTAX Counter32
			MAX-ACCESS read-only
			STATUS current
			DESCRIPTION
				"Count of all encoded blocks received on this channel
				since agent reset."
			::= { sheAdslAtucDualChanPerfDataEntry 2 }

		
--   1.3.6.1.4.1.231.7.1.2.2.1.6.1.1.35.1.3
		sheAdslAtucDualChanPerfDataTransmittedBlks OBJECT-TYPE
			SYNTAX Counter32
			MAX-ACCESS read-only
			STATUS current
			DESCRIPTION
				"Count of all encoded blocks transmitted on this
				channel since agent reset."
			::= { sheAdslAtucDualChanPerfDataEntry 3 }

		
--   1.3.6.1.4.1.231.7.1.2.2.1.6.1.1.35.1.4
		sheAdslAtucDualChanPerfDataCorrectedBlks OBJECT-TYPE
			SYNTAX Counter32
			MAX-ACCESS read-only
			STATUS current
			DESCRIPTION
				"Count of all blocks received with errors that were
				corrected since agent reset.  These blocks are passed
				on as good data."
			::= { sheAdslAtucDualChanPerfDataEntry 4 }

		
--   1.3.6.1.4.1.231.7.1.2.2.1.6.1.1.35.1.5
		sheAdslAtucDualChanPerfDataUncorrectBlks OBJECT-TYPE
			SYNTAX Counter32
			MAX-ACCESS read-only
			STATUS current
			DESCRIPTION
				"Count of all blocks received with uncorrectable
				errors since agent reset."
			::= { sheAdslAtucDualChanPerfDataEntry 5 }

		
--   1.3.6.1.4.1.231.7.1.2.2.1.6.1.1.35.1.6
		sheAdslAtucDualChanPerfDataNcd OBJECT-TYPE
			SYNTAX Gauge32
			MAX-ACCESS read-only
			STATUS current
			DESCRIPTION
				"Count of no cell delineation(ncd) on this channel."
			::= { sheAdslAtucDualChanPerfDataEntry 6 }

		
--   1.3.6.1.4.1.231.7.1.2.2.1.6.1.1.35.1.7
		sheAdslAtucDualChanPerfDataOcd OBJECT-TYPE
			SYNTAX Gauge32
			MAX-ACCESS read-only
			STATUS current
			DESCRIPTION
				"Count of out of cell delineation (ocd) on this channel."
			::= { sheAdslAtucDualChanPerfDataEntry 7 }

		
--   1.3.6.1.4.1.231.7.1.2.2.1.6.1.1.35.1.8
		sheAdslAtucDualChanPerfDataHec OBJECT-TYPE
			SYNTAX Gauge32
			MAX-ACCESS read-only
			STATUS current
			DESCRIPTION
				"Header error check counter(hec) on this channel."
			::= { sheAdslAtucDualChanPerfDataEntry 8 }

		
--  general 15 min interval information
-- 
-- 1.3.6.1.4.1.231.7.1.2.2.1.6.1.1.35.1.9
		sheAdslAtucDualChanPerfDataValidIntervals OBJECT-TYPE
			SYNTAX INTEGER (0..96)
			MAX-ACCESS read-only
			STATUS current
			DESCRIPTION
				"The number of previous 15-minute intervals in the
				interval table for which data was collected.  Given
				that <n> is the maximum # of intervals supported.
				The value will be <n> unless the measurement was
				(re-)started within the last (<n>*15) minutes, in which
				case the value will be the number of complete 15
				minute intervals for which the agent has at least
				some data. In certain cases (e.g., in the case
				where the agent is a proxy) it is possible that some
				intervals are unavailable.  In this case, this
				interval is the maximum interval number for
				which data is available."
			::= { sheAdslAtucDualChanPerfDataEntry 9 }

		
--   1.3.6.1.4.1.231.7.1.2.2.1.6.1.1.35.1.10
		sheAdslAtucDualChanPerfDataInvalidIntervals OBJECT-TYPE
			SYNTAX INTEGER (0..96)
			MAX-ACCESS read-only
			STATUS current
			DESCRIPTION
				"The number of intervals in the range from
				0 to the value of adslAtucChanPerfValidIntervals
				for which no data is available. This object
				will typically be zero except in cases where
				the data for some intervals are not available
				(e.g., in proxy situations)."
			::= { sheAdslAtucDualChanPerfDataEntry 10 }

		
--  15 min current performance group
-- 
-- 
-- 1.3.6.1.4.1.231.7.1.2.2.1.6.1.1.35.1.11
		sheAdslAtucDualChanPerfDataCurr15MinTimeElapsed OBJECT-TYPE
			SYNTAX AdslPerfTimeElapsed (0..899)
			UNITS "seconds"
			MAX-ACCESS read-only
			STATUS current
			DESCRIPTION
				"Total elapsed seconds in this interval."
			::= { sheAdslAtucDualChanPerfDataEntry 11 }

		
--   1.3.6.1.4.1.231.7.1.2.2.1.6.1.1.35.1.12
		sheAdslAtucDualChanPerfDataCurr15MinReceivedBlks OBJECT-TYPE
			SYNTAX PerfCurrentCount
			MAX-ACCESS read-only
			STATUS current
			DESCRIPTION
				"Count of all encoded blocks received on this channel
				within the current 15 minute interval."
			::= { sheAdslAtucDualChanPerfDataEntry 12 }

		
--   1.3.6.1.4.1.231.7.1.2.2.1.6.1.1.35.1.13
		sheAdslAtucDualChanPerfDataCurr15MinTransmittedBlks OBJECT-TYPE
			SYNTAX PerfCurrentCount
			MAX-ACCESS read-only
			STATUS current
			DESCRIPTION
				"Count of all encoded blocks transmitted on this
				channel within the current 15 minute interval."
			::= { sheAdslAtucDualChanPerfDataEntry 13 }

		
--   1.3.6.1.4.1.231.7.1.2.2.1.6.1.1.35.1.14
		sheAdslAtucDualChanPerfDataCurr15MinCorrectedBlks OBJECT-TYPE
			SYNTAX PerfCurrentCount
			MAX-ACCESS read-only
			STATUS current
			DESCRIPTION
				"Count of all blocks received with errors that were
				corrected on this channel within the current 15 minute
				interval."
			::= { sheAdslAtucDualChanPerfDataEntry 14 }

		
--   1.3.6.1.4.1.231.7.1.2.2.1.6.1.1.35.1.15
		sheAdslAtucDualChanPerfDataCurr15MinUncorrectBlks OBJECT-TYPE
			SYNTAX PerfCurrentCount
			MAX-ACCESS read-only
			STATUS current
			DESCRIPTION
				"Count of all blocks received with uncorrectable
				errors on this channel within the current 15 minute
				interval."
			::= { sheAdslAtucDualChanPerfDataEntry 15 }

		
--   1.3.6.1.4.1.231.7.1.2.2.1.6.1.1.35.1.16
		sheAdslAtucDualChanPerfDataCurr15MinNcd OBJECT-TYPE
			SYNTAX Gauge32
			MAX-ACCESS read-only
			STATUS current
			DESCRIPTION
				"Count of no cell delineation(ncd) on this channel within the current 15 minute time interval."
			::= { sheAdslAtucDualChanPerfDataEntry 16 }

		
--   1.3.6.1.4.1.231.7.1.2.2.1.6.1.1.35.1.17
		sheAdslAtucDualChanPerfDataCurr15MinOcd OBJECT-TYPE
			SYNTAX Gauge32
			MAX-ACCESS read-only
			STATUS current
			DESCRIPTION
				"Count of out of cell delineation (ocd) on this channel within the current 15 minute time interval."
			::= { sheAdslAtucDualChanPerfDataEntry 17 }

		
--   1.3.6.1.4.1.231.7.1.2.2.1.6.1.1.35.1.18
		sheAdslAtucDualChanPerfDataCurr15MinHec OBJECT-TYPE
			SYNTAX Gauge32
			MAX-ACCESS read-only
			STATUS current
			DESCRIPTION
				"Header error check counter(hec) on this channel within the current 15 minute time interval."
			::= { sheAdslAtucDualChanPerfDataEntry 18 }

		
--  1-day current and previous performance group
-- 
-- 1.3.6.1.4.1.231.7.1.2.2.1.6.1.1.35.1.19
		sheAdslAtucDualChanPerfDataCurr1DayTimeElapsed OBJECT-TYPE
			SYNTAX AdslPerfTimeElapsed (0..86399)
			UNITS "seconds"
			MAX-ACCESS read-only
			STATUS current
			DESCRIPTION
				"Number of seconds that have elapsed since the
				beginning of the current 1-day interval."
			::= { sheAdslAtucDualChanPerfDataEntry 19 }

		
--   1.3.6.1.4.1.231.7.1.2.2.1.6.1.1.35.1.20
		sheAdslAtucDualChanPerfDataCurr1DayReceivedBlks OBJECT-TYPE
			SYNTAX AdslPerfCurrDayCount
			MAX-ACCESS read-only
			STATUS current
			DESCRIPTION
				"Count of all encoded blocks received on this
				channel during the current day as measured by
				adslAtucChanPerfCurr1DayTimeElapsed."
			::= { sheAdslAtucDualChanPerfDataEntry 20 }

		
--   1.3.6.1.4.1.231.7.1.2.2.1.6.1.1.35.1.21
		sheAdslAtucDualChanPerfDataCurr1DayTransmittedBlks OBJECT-TYPE
			SYNTAX AdslPerfCurrDayCount
			MAX-ACCESS read-only
			STATUS current
			DESCRIPTION
				"Count of all encoded blocks transmitted on this
				channel during the current day as measured by
				adslAtucChanPerfCurr1DayTimeElapsed."
			::= { sheAdslAtucDualChanPerfDataEntry 21 }

		
--   1.3.6.1.4.1.231.7.1.2.2.1.6.1.1.35.1.22
		sheAdslAtucDualChanPerfDataCurr1DayCorrectedBlks OBJECT-TYPE
			SYNTAX AdslPerfCurrDayCount
			MAX-ACCESS read-only
			STATUS current
			DESCRIPTION
				"Count of all blocks received with errors that were
				corrected on this channel during the current day as
				measured by adslAtucChanPerfCurr1DayTimeElapsed."
			::= { sheAdslAtucDualChanPerfDataEntry 22 }

		
--   1.3.6.1.4.1.231.7.1.2.2.1.6.1.1.35.1.23
		sheAdslAtucDualChanPerfDataCurr1DayUncorrectBlks OBJECT-TYPE
			SYNTAX AdslPerfCurrDayCount
			MAX-ACCESS read-only
			STATUS current
			DESCRIPTION
				"Count of all blocks received with uncorrectable
				errors on this channel during the current day as
				measured by adslAtucChanPerfCurr1DayTimeElapsed."
			::= { sheAdslAtucDualChanPerfDataEntry 23 }

		
--   1.3.6.1.4.1.231.7.1.2.2.1.6.1.1.35.1.24
		sheAdslAtucDualChanPerfDataCurr1DayNcd OBJECT-TYPE
			SYNTAX Gauge32
			MAX-ACCESS read-only
			STATUS current
			DESCRIPTION
				"Count of no cell delineation (ncd) on this channel within the current 1 day time interval."
			::= { sheAdslAtucDualChanPerfDataEntry 24 }

		
--   1.3.6.1.4.1.231.7.1.2.2.1.6.1.1.35.1.25
		sheAdslAtucDualChanPerfDataCurr1DayOcd OBJECT-TYPE
			SYNTAX Gauge32
			MAX-ACCESS read-only
			STATUS current
			DESCRIPTION
				"Count of out of cell delineation (ocd) on this channel within the current 1 day time interval."
			::= { sheAdslAtucDualChanPerfDataEntry 25 }

		
--   1.3.6.1.4.1.231.7.1.2.2.1.6.1.1.35.1.26
		sheAdslAtucDualChanPerfDataCurr1DayHec OBJECT-TYPE
			SYNTAX Gauge32
			MAX-ACCESS read-only
			STATUS current
			DESCRIPTION
				"Header error check counter (hec) on this channel within the current 1 day time interval."
			::= { sheAdslAtucDualChanPerfDataEntry 26 }

		
--   1.3.6.1.4.1.231.7.1.2.2.1.6.1.1.35.1.27
		sheAdslAtucDualChanPerfDataPrev1DayMoniSecs OBJECT-TYPE
			SYNTAX INTEGER (0..86400)
			UNITS "seconds"
			MAX-ACCESS read-only
			STATUS current
			DESCRIPTION
				"The amount of time in the previous 1-day interval
				over which the performance monitoring information
				is actually counted. This value will be the same as
				the interval duration except in a situation where
				performance monitoring data could not be collected
				for any reason."
			::= { sheAdslAtucDualChanPerfDataEntry 27 }

		
--   1.3.6.1.4.1.231.7.1.2.2.1.6.1.1.35.1.28
		sheAdslAtucDualChanPerfDataPrev1DayReceivedBlks OBJECT-TYPE
			SYNTAX AdslPerfPrevDayCount
			MAX-ACCESS read-only
			STATUS current
			DESCRIPTION
				"Count of all encoded blocks received on this
				channel within the most recent previous 1-day
				period."
			::= { sheAdslAtucDualChanPerfDataEntry 28 }

		
--   1.3.6.1.4.1.231.7.1.2.2.1.6.1.1.35.1.29
		sheAdslAtucDualChanPerfDataPrev1DayTransmittedBlks OBJECT-TYPE
			SYNTAX AdslPerfPrevDayCount
			MAX-ACCESS read-only
			STATUS current
			DESCRIPTION
				"Count of all encoded blocks transmitted on this
				channel within the most recent previous 1-day
				period."
			::= { sheAdslAtucDualChanPerfDataEntry 29 }

		
--   1.3.6.1.4.1.231.7.1.2.2.1.6.1.1.35.1.30
		sheAdslAtucDualChanPerfDataPrev1DayCorrectedBlks OBJECT-TYPE
			SYNTAX AdslPerfPrevDayCount
			MAX-ACCESS read-only
			STATUS current
			DESCRIPTION
				"Count of all blocks received with errors that were
				corrected on this channel within the most recent
				previous 1-day period."
			::= { sheAdslAtucDualChanPerfDataEntry 30 }

		
--   1.3.6.1.4.1.231.7.1.2.2.1.6.1.1.35.1.31
		sheAdslAtucDualChanPerfDataPrev1DayUncorrectBlks OBJECT-TYPE
			SYNTAX AdslPerfPrevDayCount
			MAX-ACCESS read-only
			STATUS current
			DESCRIPTION
				"Count of all blocks received with uncorrectable
				errors on this channel within the most recent previous
				1-day period."
			::= { sheAdslAtucDualChanPerfDataEntry 31 }

		
--   1.3.6.1.4.1.231.7.1.2.2.1.6.1.1.35.1.32
		sheAdslAtucDualChanPerfDataPrev1DayNcd OBJECT-TYPE
			SYNTAX Gauge32
			MAX-ACCESS read-only
			STATUS current
			DESCRIPTION
				"Count of no cell delineation (ncd) on this channel within the most recent previous 1-day period."
			::= { sheAdslAtucDualChanPerfDataEntry 32 }

		
--   1.3.6.1.4.1.231.7.1.2.2.1.6.1.1.35.1.33
		sheAdslAtucDualChanPerfDataPrev1DayOcd OBJECT-TYPE
			SYNTAX Gauge32
			MAX-ACCESS read-only
			STATUS current
			DESCRIPTION
				"Count of out of cell delineation (ocd) on this channel within the most recent previous 1-day period."
			::= { sheAdslAtucDualChanPerfDataEntry 33 }

		
--   1.3.6.1.4.1.231.7.1.2.2.1.6.1.1.35.1.34
		sheAdslAtucDualChanPerfDataPrev1DayHec OBJECT-TYPE
			SYNTAX Gauge32
			MAX-ACCESS read-only
			STATUS current
			DESCRIPTION
				"Header error check counter(hec) on this channel within the most recent previous 1-day period."
			::= { sheAdslAtucDualChanPerfDataEntry 34 }

		
--   1.3.6.1.4.1.231.7.1.2.2.1.6.1.1.36
		sheAdslAturDualChanPerfDataTable OBJECT-TYPE
			SYNTAX SEQUENCE OF SheAdslAturDualChanPerfDataEntry
			MAX-ACCESS not-accessible
			STATUS current
			DESCRIPTION
				"This table provides one row for each ATUR channel. Only supported by NE R2.5 and higher."
			::= { sheAdslLineMIB 36 }

		
--   1.3.6.1.4.1.231.7.1.2.2.1.6.1.1.36.1
		sheAdslAturDualChanPerfDataEntry OBJECT-TYPE
			SYNTAX SheAdslAturDualChanPerfDataEntry
			MAX-ACCESS not-accessible
			STATUS current
			DESCRIPTION
				"An entry in adslAturChanPerfDataTable. New table only supported by NE releases up R2.5.
				Indexed by ifIndex - ChanType."
			INDEX { ifIndex, sheAdslAturDualChanType }
			::= { sheAdslAturDualChanPerfDataTable 1 }

		
		SheAdslAturDualChanPerfDataEntry ::=
			SEQUENCE { 
				sheAdslAturDualChanPerfDataReceivedBlks
					Counter32,
				sheAdslAturDualChanPerfDataTransmittedBlks
					Counter32,
				sheAdslAturDualChanPerfDataCorrectedBlks
					Counter32,
				sheAdslAturDualChanPerfDataUncorrectBlks
					Counter32,
				sheAdslAturDualChanPerfDataExtnNcd
					Gauge32,
				sheAdslAturDualChanPerfDataExtnHec
					Gauge32,
				sheAdslAturDualChanPerfDataPerfValidIntervals
					INTEGER,
				sheAdslAturDualChanPerfDataPerfInvalidIntervals
					INTEGER,
				sheAdslAturDualChanPerfDataCurr15MinTimeElapsed
					AdslPerfTimeElapsed,
				sheAdslAturDualChanPerfDataCurr15MinReceivedBlks
					PerfCurrentCount,
				sheAdslAturDualChanPerfDataCurr15MinTransmittedBlks
					PerfCurrentCount,
				sheAdslAturDualChanPerfDataCurr15MinCorrectedBlks
					PerfCurrentCount,
				sheAdslAturDualChanPerfDataCurr15MinUncorrectBlks
					PerfCurrentCount,
				sheAdslAturDualChanPerfDataExtnCurr15MinNcd
					Gauge32,
				sheAdslAturDualChanPerfDataExtnCurr15MinHec
					Gauge32,
				sheAdslAturDualChanPerfDataCurr1DayTimeElapsed
					AdslPerfTimeElapsed,
				sheAdslAturDualChanPerfDataCurr1DayReceivedBlks
					AdslPerfCurrDayCount,
				sheAdslAturDualChanPerfDataCurr1DayTransmittedBlks
					AdslPerfCurrDayCount,
				sheAdslAturDualChanPerfDataCurr1DayCorrectedBlks
					AdslPerfCurrDayCount,
				sheAdslAturDualChanPerfDataCurr1DayUncorrectBlks
					AdslPerfCurrDayCount,
				sheAdslAturDualChanPerfDataExtnCurr1DayNcd
					Gauge32,
				sheAdslAturDualChanPerfDataExtnCurr1DayHec
					Gauge32,
				sheAdslAturDualChanPerfDataPrev1DayMoniSecs
					INTEGER,
				sheAdslAturDualChanPerfDataPrev1DayReceivedBlks
					AdslPerfPrevDayCount,
				sheAdslAturDualChanPerfDataPrev1DayTransmittedBlks
					AdslPerfPrevDayCount,
				sheAdslAturDualChanPerfDataPrev1DayCorrectedBlks
					AdslPerfPrevDayCount,
				sheAdslAturDualChanPerfDataPrev1DayUncorrectBlks
					AdslPerfPrevDayCount,
				sheAdslAturDualChanPerfDataExtnPrev1DayNcd
					Gauge32,
				sheAdslAturDualChanPerfDataExtnPrev1DayHec
					Gauge32
			 }

--   1.3.6.1.4.1.231.7.1.2.2.1.6.1.1.36.1.1
		sheAdslAturDualChanPerfDataReceivedBlks OBJECT-TYPE
			SYNTAX Counter32
			MAX-ACCESS read-only
			STATUS current
			DESCRIPTION
				"Count of all encoded blocks received on this channel
				since agent reset."
			::= { sheAdslAturDualChanPerfDataEntry 1 }

		
--   1.3.6.1.4.1.231.7.1.2.2.1.6.1.1.36.1.2
		sheAdslAturDualChanPerfDataTransmittedBlks OBJECT-TYPE
			SYNTAX Counter32
			MAX-ACCESS read-only
			STATUS current
			DESCRIPTION
				"Count of all encoded blocks transmitted on this
				channel since agent reset."
			::= { sheAdslAturDualChanPerfDataEntry 2 }

		
--   1.3.6.1.4.1.231.7.1.2.2.1.6.1.1.36.1.3
		sheAdslAturDualChanPerfDataCorrectedBlks OBJECT-TYPE
			SYNTAX Counter32
			MAX-ACCESS read-only
			STATUS current
			DESCRIPTION
				"Count of all blocks received with errors that were
				corrected since agent reset.  These blocks are passed
				on as good data."
			::= { sheAdslAturDualChanPerfDataEntry 3 }

		
--   1.3.6.1.4.1.231.7.1.2.2.1.6.1.1.36.1.4
		sheAdslAturDualChanPerfDataUncorrectBlks OBJECT-TYPE
			SYNTAX Counter32
			MAX-ACCESS read-only
			STATUS current
			DESCRIPTION
				"Count of all blocks received with uncorrectable
				errors since agent reset."
			::= { sheAdslAturDualChanPerfDataEntry 4 }

		
--   1.3.6.1.4.1.231.7.1.2.2.1.6.1.1.36.1.5
		sheAdslAturDualChanPerfDataExtnNcd OBJECT-TYPE
			SYNTAX Gauge32
			MAX-ACCESS read-only
			STATUS current
			DESCRIPTION
				"Number of packets with no cell delineation(NCD) error on this channel."
			::= { sheAdslAturDualChanPerfDataEntry 5 }

		
--   1.3.6.1.4.1.231.7.1.2.2.1.6.1.1.36.1.6
		sheAdslAturDualChanPerfDataExtnHec OBJECT-TYPE
			SYNTAX Gauge32
			MAX-ACCESS read-only
			STATUS current
			DESCRIPTION
				"Number of packets with Header error check (HEC) error on this channel."
			::= { sheAdslAturDualChanPerfDataEntry 6 }

		
--   1.3.6.1.4.1.231.7.1.2.2.1.6.1.1.36.1.7
		sheAdslAturDualChanPerfDataPerfValidIntervals OBJECT-TYPE
			SYNTAX INTEGER (0..96)
			MAX-ACCESS read-only
			STATUS current
			DESCRIPTION
				"The number of previous 15-minute intervals in the
				interval table for which data was collected.  Given
				that <n> is the maximum # of intervals supported.
				The value will be <n> unless the measurement was
				(re-)started within the last (<n>*15) minutes, in which
				case the value will be the number of complete 15
				minute intervals for which the agent has at least
				some data. In certain cases (e.g., in the case
				where the agent is a proxy) it is possible that some
				intervals are unavailable.  In this case, this
				interval is the maximum interval number for
				which data is available."
			::= { sheAdslAturDualChanPerfDataEntry 7 }

		
--   1.3.6.1.4.1.231.7.1.2.2.1.6.1.1.36.1.8
		sheAdslAturDualChanPerfDataPerfInvalidIntervals OBJECT-TYPE
			SYNTAX INTEGER (0..96)
			MAX-ACCESS read-only
			STATUS current
			DESCRIPTION
				"The number of intervals in the range from
				0 to the value of adslAturChanPerfValidIntervals
				for which no data is available. This object
				will typically be zero except in cases where
				the data for some intervals are not available
				(e.g., in proxy situations)."
			::= { sheAdslAturDualChanPerfDataEntry 8 }

		
--   1.3.6.1.4.1.231.7.1.2.2.1.6.1.1.36.1.9
		sheAdslAturDualChanPerfDataCurr15MinTimeElapsed OBJECT-TYPE
			SYNTAX AdslPerfTimeElapsed (0..899)
			UNITS "seconds"
			MAX-ACCESS read-only
			STATUS current
			DESCRIPTION
				"Total elapsed seconds in this interval.
				A full interval is 900 seconds."
			::= { sheAdslAturDualChanPerfDataEntry 9 }

		
--   1.3.6.1.4.1.231.7.1.2.2.1.6.1.1.36.1.10
		sheAdslAturDualChanPerfDataCurr15MinReceivedBlks OBJECT-TYPE
			SYNTAX PerfCurrentCount
			MAX-ACCESS read-only
			STATUS current
			DESCRIPTION
				"Count of all encoded blocks received on this
				channel within the current 15 minute interval."
			::= { sheAdslAturDualChanPerfDataEntry 10 }

		
--   1.3.6.1.4.1.231.7.1.2.2.1.6.1.1.36.1.11
		sheAdslAturDualChanPerfDataCurr15MinTransmittedBlks OBJECT-TYPE
			SYNTAX PerfCurrentCount
			MAX-ACCESS read-only
			STATUS current
			DESCRIPTION
				"Count of all encoded blocks transmitted on this
				channel within the current 15 minute interval."
			::= { sheAdslAturDualChanPerfDataEntry 11 }

		
--   1.3.6.1.4.1.231.7.1.2.2.1.6.1.1.36.1.12
		sheAdslAturDualChanPerfDataCurr15MinCorrectedBlks OBJECT-TYPE
			SYNTAX PerfCurrentCount
			MAX-ACCESS read-only
			STATUS current
			DESCRIPTION
				"Count of all blocks received with errors that were
				corrected on this channel within the current 15 minute
				interval."
			::= { sheAdslAturDualChanPerfDataEntry 12 }

		
--   1.3.6.1.4.1.231.7.1.2.2.1.6.1.1.36.1.13
		sheAdslAturDualChanPerfDataCurr15MinUncorrectBlks OBJECT-TYPE
			SYNTAX PerfCurrentCount
			MAX-ACCESS read-only
			STATUS current
			DESCRIPTION
				"Count of all blocks received with uncorrectable
				errors on this channel within the current 15 minute
				interval."
			::= { sheAdslAturDualChanPerfDataEntry 13 }

		
--   1.3.6.1.4.1.231.7.1.2.2.1.6.1.1.36.1.14
		sheAdslAturDualChanPerfDataExtnCurr15MinNcd OBJECT-TYPE
			SYNTAX Gauge32
			MAX-ACCESS read-only
			STATUS current
			DESCRIPTION
				"Number of packets with no cell delineation(NCD) error on this channel within the current 15 minute time interval."
			::= { sheAdslAturDualChanPerfDataEntry 14 }

		
--   1.3.6.1.4.1.231.7.1.2.2.1.6.1.1.36.1.15
		sheAdslAturDualChanPerfDataExtnCurr15MinHec OBJECT-TYPE
			SYNTAX Gauge32
			MAX-ACCESS read-only
			STATUS current
			DESCRIPTION
				"Number of packets with Header error check (HEC) error on this channel within the current 15 minute time interval."
			::= { sheAdslAturDualChanPerfDataEntry 15 }

		
--   1.3.6.1.4.1.231.7.1.2.2.1.6.1.1.36.1.16
		sheAdslAturDualChanPerfDataCurr1DayTimeElapsed OBJECT-TYPE
			SYNTAX AdslPerfTimeElapsed (0..86399)
			UNITS "seconds"
			MAX-ACCESS read-only
			STATUS current
			DESCRIPTION
				"Number of seconds that have elapsed since the
				beginning of the current 1-day interval."
			::= { sheAdslAturDualChanPerfDataEntry 16 }

		
--   1.3.6.1.4.1.231.7.1.2.2.1.6.1.1.36.1.17
		sheAdslAturDualChanPerfDataCurr1DayReceivedBlks OBJECT-TYPE
			SYNTAX AdslPerfCurrDayCount
			MAX-ACCESS read-only
			STATUS current
			DESCRIPTION
				"Count of all encoded blocks received on this
				channel during the current day as measured by
				adslAturChanPerfCurr1DayTimeElapsed."
			::= { sheAdslAturDualChanPerfDataEntry 17 }

		
--   1.3.6.1.4.1.231.7.1.2.2.1.6.1.1.36.1.18
		sheAdslAturDualChanPerfDataCurr1DayTransmittedBlks OBJECT-TYPE
			SYNTAX AdslPerfCurrDayCount
			MAX-ACCESS read-only
			STATUS current
			DESCRIPTION
				"Count of all encoded blocks transmitted on this
				channel during the current day as measured by
				adslAturChanPerfCurr1DayTimeElapsed."
			::= { sheAdslAturDualChanPerfDataEntry 18 }

		
--   1.3.6.1.4.1.231.7.1.2.2.1.6.1.1.36.1.19
		sheAdslAturDualChanPerfDataCurr1DayCorrectedBlks OBJECT-TYPE
			SYNTAX AdslPerfCurrDayCount
			MAX-ACCESS read-only
			STATUS current
			DESCRIPTION
				"Count of all blocks received with errors that were
				corrected on this channel during the current day as
				measured by adslAturChanPerfCurr1DayTimeElapsed."
			::= { sheAdslAturDualChanPerfDataEntry 19 }

		
--   1.3.6.1.4.1.231.7.1.2.2.1.6.1.1.36.1.20
		sheAdslAturDualChanPerfDataCurr1DayUncorrectBlks OBJECT-TYPE
			SYNTAX AdslPerfCurrDayCount
			MAX-ACCESS read-only
			STATUS current
			DESCRIPTION
				"Count of all blocks received with uncorrectable
				errors on this channel during the current day as
				measured by adslAturChanPerfCurr1DayTimeElapsed."
			::= { sheAdslAturDualChanPerfDataEntry 20 }

		
--   1.3.6.1.4.1.231.7.1.2.2.1.6.1.1.36.1.21
		sheAdslAturDualChanPerfDataExtnCurr1DayNcd OBJECT-TYPE
			SYNTAX Gauge32
			MAX-ACCESS read-only
			STATUS current
			DESCRIPTION
				"Number of packets with no cell delineation (NCD) error on this channel within the current 1 day time interval."
			::= { sheAdslAturDualChanPerfDataEntry 21 }

		
--   1.3.6.1.4.1.231.7.1.2.2.1.6.1.1.36.1.22
		sheAdslAturDualChanPerfDataExtnCurr1DayHec OBJECT-TYPE
			SYNTAX Gauge32
			MAX-ACCESS read-only
			STATUS current
			DESCRIPTION
				"Number of packets with Header error check (HEC) error on this channel within the current 1 day time interval."
			::= { sheAdslAturDualChanPerfDataEntry 22 }

		
--   1.3.6.1.4.1.231.7.1.2.2.1.6.1.1.36.1.23
		sheAdslAturDualChanPerfDataPrev1DayMoniSecs OBJECT-TYPE
			SYNTAX INTEGER (0..86400)
			UNITS "seconds"
			MAX-ACCESS read-only
			STATUS current
			DESCRIPTION
				"The amount of time in the previous 1-day interval
				over which the performance monitoring information
				is actually counted. This value will be the same as
				the interval duration except in a situation where
				performance monitoring data could not be collected
				for any reason."
			::= { sheAdslAturDualChanPerfDataEntry 23 }

		
--   1.3.6.1.4.1.231.7.1.2.2.1.6.1.1.36.1.24
		sheAdslAturDualChanPerfDataPrev1DayReceivedBlks OBJECT-TYPE
			SYNTAX AdslPerfPrevDayCount
			MAX-ACCESS read-only
			STATUS current
			DESCRIPTION
				"Count of all encoded blocks received on this
				channel within the most recent previous 1-day
				period."
			::= { sheAdslAturDualChanPerfDataEntry 24 }

		
--   1.3.6.1.4.1.231.7.1.2.2.1.6.1.1.36.1.25
		sheAdslAturDualChanPerfDataPrev1DayTransmittedBlks OBJECT-TYPE
			SYNTAX AdslPerfPrevDayCount
			MAX-ACCESS read-only
			STATUS current
			DESCRIPTION
				"Count of all encoded blocks transmitted on this
				channel within the most recent previous 1-day
				period."
			::= { sheAdslAturDualChanPerfDataEntry 25 }

		
--   1.3.6.1.4.1.231.7.1.2.2.1.6.1.1.36.1.26
		sheAdslAturDualChanPerfDataPrev1DayCorrectedBlks OBJECT-TYPE
			SYNTAX AdslPerfPrevDayCount
			MAX-ACCESS read-only
			STATUS current
			DESCRIPTION
				"Count of all blocks received with errors that were
				corrected on this channel within the most recent
				previous 1-day period."
			::= { sheAdslAturDualChanPerfDataEntry 26 }

		
--   1.3.6.1.4.1.231.7.1.2.2.1.6.1.1.36.1.27
		sheAdslAturDualChanPerfDataPrev1DayUncorrectBlks OBJECT-TYPE
			SYNTAX AdslPerfPrevDayCount
			MAX-ACCESS read-only
			STATUS current
			DESCRIPTION
				"Count of all blocks received with uncorrectable
				errors on this channel within the most recent previous
				1-day period."
			::= { sheAdslAturDualChanPerfDataEntry 27 }

		
--   1.3.6.1.4.1.231.7.1.2.2.1.6.1.1.36.1.28
		sheAdslAturDualChanPerfDataExtnPrev1DayNcd OBJECT-TYPE
			SYNTAX Gauge32
			MAX-ACCESS read-only
			STATUS current
			DESCRIPTION
				"Number of packets with no cell delineation (NCD) error on this channel within the most recent previous period."
			::= { sheAdslAturDualChanPerfDataEntry 28 }

		
--   1.3.6.1.4.1.231.7.1.2.2.1.6.1.1.36.1.29
		sheAdslAturDualChanPerfDataExtnPrev1DayHec OBJECT-TYPE
			SYNTAX Gauge32
			MAX-ACCESS read-only
			STATUS current
			DESCRIPTION
				"Number of packets with Header error check (HEC) error on this channel within the most recent previous period."
			::= { sheAdslAturDualChanPerfDataEntry 29 }

		
--   1.3.6.1.4.1.231.7.1.2.2.1.6.1.1.37
		sheAdslAtucDualChanIntervalTable OBJECT-TYPE
			SYNTAX SEQUENCE OF SheAdslAtucDualChanIntervalEntry
			MAX-ACCESS not-accessible
			STATUS current
			DESCRIPTION
				"This table provides one row for each ATUC channel's performance data collection interval.
				Only supported by NE R2.5 and higher."
			::= { sheAdslLineMIB 37 }

		
--   1.3.6.1.4.1.231.7.1.2.2.1.6.1.1.37.1
		sheAdslAtucDualChanIntervalEntry OBJECT-TYPE
			SYNTAX SheAdslAtucDualChanIntervalEntry
			MAX-ACCESS not-accessible
			STATUS current
			DESCRIPTION
				"An entry in the adslAtucIntervalTable. New table only supported by NE releases up R2.5.
				Indexed by ifIndex - ChanType - IntervalNumber."
			INDEX { ifIndex, sheAdslAtucDualChanType, sheAdslAtucChanIntervalNumber }
			::= { sheAdslAtucDualChanIntervalTable 1 }

		
		SheAdslAtucDualChanIntervalEntry ::=
			SEQUENCE { 
				sheAdslAtucDualChanIntervalNumber
					INTEGER,
				sheAdslAtucDualChanIntervalValidData
					TruthValue,
				sheAdslAtucDualChanIntervalEndTime
					Unsigned32,
				sheAdslAtucDualChanIntervalReceivedBlks
					PerfIntervalCount,
				sheAdslAtucDualChanIntervalTransmittedBlks
					PerfIntervalCount,
				sheAdslAtucDualChanIntervalCorrectedBlks
					PerfIntervalCount,
				sheAdslAtucDualChanIntervalUncorrectBlks
					PerfIntervalCount,
				sheAdslAtucDualChanIntervalNcd
					Counter32,
				sheAdslAtucDualChanIntervalOcd
					Counter32,
				sheAdslAtucDualChanIntervalHec
					Counter32
			 }

--   1.3.6.1.4.1.231.7.1.2.2.1.6.1.1.37.1.1
		sheAdslAtucDualChanIntervalNumber OBJECT-TYPE
			SYNTAX INTEGER (1..96)
			MAX-ACCESS read-only
			STATUS current
			DESCRIPTION
				"Performance Data Interval number 1 is the
				the most recent previous interval; interval
				96 is 24 hours ago.  Intervals 2..96 are
				optional."
			::= { sheAdslAtucDualChanIntervalEntry 1 }

		
--   1.3.6.1.4.1.231.7.1.2.2.1.6.1.1.37.1.2
		sheAdslAtucDualChanIntervalValidData OBJECT-TYPE
			SYNTAX TruthValue
			MAX-ACCESS read-only
			STATUS current
			DESCRIPTION
				"This variable indicates if the data for this
				interval is valid."
			::= { sheAdslAtucDualChanIntervalEntry 2 }

		
--   1.3.6.1.4.1.231.7.1.2.2.1.6.1.1.37.1.3
		sheAdslAtucDualChanIntervalEndTime OBJECT-TYPE
			SYNTAX Unsigned32
			MAX-ACCESS read-only
			STATUS current
			DESCRIPTION
				"This variable indicates the time of storing this interval."
			::= { sheAdslAtucDualChanIntervalEntry 3 }

		
--   1.3.6.1.4.1.231.7.1.2.2.1.6.1.1.37.1.4
		sheAdslAtucDualChanIntervalReceivedBlks OBJECT-TYPE
			SYNTAX PerfIntervalCount
			MAX-ACCESS read-only
			STATUS current
			DESCRIPTION
				"Count of all encoded blocks received on this channel
				during this interval."
			::= { sheAdslAtucDualChanIntervalEntry 4 }

		
--   1.3.6.1.4.1.231.7.1.2.2.1.6.1.1.37.1.5
		sheAdslAtucDualChanIntervalTransmittedBlks OBJECT-TYPE
			SYNTAX PerfIntervalCount
			MAX-ACCESS read-only
			STATUS current
			DESCRIPTION
				"Count of all encoded blocks transmitted on this
				channel during this interval."
			::= { sheAdslAtucDualChanIntervalEntry 5 }

		
--   1.3.6.1.4.1.231.7.1.2.2.1.6.1.1.37.1.6
		sheAdslAtucDualChanIntervalCorrectedBlks OBJECT-TYPE
			SYNTAX PerfIntervalCount
			MAX-ACCESS read-only
			STATUS current
			DESCRIPTION
				"Count of all blocks received with errors that were
				corrected on this channel during this interval."
			::= { sheAdslAtucDualChanIntervalEntry 6 }

		
--   1.3.6.1.4.1.231.7.1.2.2.1.6.1.1.37.1.7
		sheAdslAtucDualChanIntervalUncorrectBlks OBJECT-TYPE
			SYNTAX PerfIntervalCount
			MAX-ACCESS read-only
			STATUS current
			DESCRIPTION
				"Count of all blocks received with uncorrectable
				errors on this channel during this interval."
			::= { sheAdslAtucDualChanIntervalEntry 7 }

		
--   1.3.6.1.4.1.231.7.1.2.2.1.6.1.1.37.1.8
		sheAdslAtucDualChanIntervalNcd OBJECT-TYPE
			SYNTAX Counter32
			MAX-ACCESS read-only
			STATUS current
			DESCRIPTION
				"Indicates count of no cell delineation on this channel for this interval."
			::= { sheAdslAtucDualChanIntervalEntry 8 }

		
--   1.3.6.1.4.1.231.7.1.2.2.1.6.1.1.37.1.9
		sheAdslAtucDualChanIntervalOcd OBJECT-TYPE
			SYNTAX Counter32
			MAX-ACCESS read-only
			STATUS current
			DESCRIPTION
				"Indicates count of out cell delineation on this channel for this interval."
			::= { sheAdslAtucDualChanIntervalEntry 9 }

		
--   1.3.6.1.4.1.231.7.1.2.2.1.6.1.1.37.1.10
		sheAdslAtucDualChanIntervalHec OBJECT-TYPE
			SYNTAX Counter32
			MAX-ACCESS read-only
			STATUS current
			DESCRIPTION
				"Indicates Header error check counter on this channel during this interval."
			::= { sheAdslAtucDualChanIntervalEntry 10 }

		
--   1.3.6.1.4.1.231.7.1.2.2.1.6.1.1.38
		sheAdslAturDualChanIntervalTable OBJECT-TYPE
			SYNTAX SEQUENCE OF SheAdslAturDualChanIntervalEntry
			MAX-ACCESS not-accessible
			STATUS current
			DESCRIPTION
				"This table provides one row for each ATUR channel's performance data collection interval.
				Only supported by NE R2.5 and higher.
				"
			::= { sheAdslLineMIB 38 }

		
--   1.3.6.1.4.1.231.7.1.2.2.1.6.1.1.38.1
		sheAdslAturDualChanIntervalEntry OBJECT-TYPE
			SYNTAX SheAdslAturDualChanIntervalEntry
			MAX-ACCESS not-accessible
			STATUS current
			DESCRIPTION
				"An entry in the adslAturIntervalTable. New table only supported by NE releases up R2.5.
				Indexed by ifIndex - ChanType - IntervalNumber."
			INDEX { ifIndex, sheAdslAturDualChanType, sheAdslAturChanIntervalNumber }
			::= { sheAdslAturDualChanIntervalTable 1 }

		
		SheAdslAturDualChanIntervalEntry ::=
			SEQUENCE { 
				sheAdslAturDualChanIntervalNumber
					INTEGER,
				sheAdslAturDualChanIntervalValidData
					TruthValue,
				sheAdslAturDualChanIntervalEndTime
					Unsigned32,
				sheAdslAturDualChanIntervalReceivedBlks
					PerfIntervalCount,
				sheAdslAturDualChanIntervalTransmittedBlks
					PerfIntervalCount,
				sheAdslAturDualChanIntervalCorrectedBlks
					PerfIntervalCount,
				sheAdslAturDualChanIntervalUncorrectBlks
					PerfIntervalCount,
				sheAdslAturDualChanIntervalNcd
					Gauge32,
				sheAdslAturDualChanIntervalHec
					Gauge32
			 }

--   1.3.6.1.4.1.231.7.1.2.2.1.6.1.1.38.1.1
		sheAdslAturDualChanIntervalNumber OBJECT-TYPE
			SYNTAX INTEGER (1..96)
			MAX-ACCESS read-only
			STATUS current
			DESCRIPTION
				"Performance Data Interval number 1 is the
				the most recent previous interval; interval
				96 is 24 hours ago.  Intervals 2..96 are
				optional."
			::= { sheAdslAturDualChanIntervalEntry 1 }

		
--   1.3.6.1.4.1.231.7.1.2.2.1.6.1.1.38.1.2
		sheAdslAturDualChanIntervalValidData OBJECT-TYPE
			SYNTAX TruthValue
			MAX-ACCESS read-only
			STATUS current
			DESCRIPTION
				"This variable indicates if the data for this
				interval is valid."
			::= { sheAdslAturDualChanIntervalEntry 2 }

		
--   1.3.6.1.4.1.231.7.1.2.2.1.6.1.1.38.1.3
		sheAdslAturDualChanIntervalEndTime OBJECT-TYPE
			SYNTAX Unsigned32
			MAX-ACCESS read-only
			STATUS current
			DESCRIPTION
				"This variable indicates the time of storing this interval."
			::= { sheAdslAturDualChanIntervalEntry 3 }

		
--   1.3.6.1.4.1.231.7.1.2.2.1.6.1.1.38.1.4
		sheAdslAturDualChanIntervalReceivedBlks OBJECT-TYPE
			SYNTAX PerfIntervalCount
			MAX-ACCESS read-only
			STATUS current
			DESCRIPTION
				"Count of all encoded blocks received on this channel
				during this interval."
			::= { sheAdslAturDualChanIntervalEntry 4 }

		
--   1.3.6.1.4.1.231.7.1.2.2.1.6.1.1.38.1.5
		sheAdslAturDualChanIntervalTransmittedBlks OBJECT-TYPE
			SYNTAX PerfIntervalCount
			MAX-ACCESS read-only
			STATUS current
			DESCRIPTION
				"Count of all encoded blocks transmitted on this
				channel during this interval."
			::= { sheAdslAturDualChanIntervalEntry 5 }

		
--   1.3.6.1.4.1.231.7.1.2.2.1.6.1.1.38.1.6
		sheAdslAturDualChanIntervalCorrectedBlks OBJECT-TYPE
			SYNTAX PerfIntervalCount
			MAX-ACCESS read-only
			STATUS current
			DESCRIPTION
				"Count of all blocks received with errors that were
				corrected on this channel during this interval."
			::= { sheAdslAturDualChanIntervalEntry 6 }

		
--   1.3.6.1.4.1.231.7.1.2.2.1.6.1.1.38.1.7
		sheAdslAturDualChanIntervalUncorrectBlks OBJECT-TYPE
			SYNTAX PerfIntervalCount
			MAX-ACCESS read-only
			STATUS current
			DESCRIPTION
				"Count of all blocks received with uncorrectable
				errors on this channel during this interval."
			::= { sheAdslAturDualChanIntervalEntry 7 }

		
--   1.3.6.1.4.1.231.7.1.2.2.1.6.1.1.38.1.8
		sheAdslAturDualChanIntervalNcd OBJECT-TYPE
			SYNTAX Gauge32
			MAX-ACCESS read-only
			STATUS current
			DESCRIPTION
				"Indicates count of no cell delineation on this channel for this interval."
			::= { sheAdslAturDualChanIntervalEntry 8 }

		
--   1.3.6.1.4.1.231.7.1.2.2.1.6.1.1.38.1.9
		sheAdslAturDualChanIntervalHec OBJECT-TYPE
			SYNTAX Gauge32
			MAX-ACCESS read-only
			STATUS current
			DESCRIPTION
				"Indicates Header error check counter on this channel during this interval."
			::= { sheAdslAturDualChanIntervalEntry 9 }

		
--  DPBO Profile configuration according g997.1 chapter 7.3.1.2.13
-- 1.3.6.1.4.1.231.7.1.2.2.1.6.1.1.39
		sheAdslLineDpboProfileTable OBJECT-TYPE
			SYNTAX SEQUENCE OF SheAdslLineDpboProfileEntry
			MAX-ACCESS not-accessible
			STATUS current
			DESCRIPTION
				"The Dpbo Profile Table. Support with SHE R2.6 RP2."
			::= { sheAdslLineMIB 39 }

		
--   1.3.6.1.4.1.231.7.1.2.2.1.6.1.1.39.1
		sheAdslLineDpboProfileEntry OBJECT-TYPE
			SYNTAX SheAdslLineDpboProfileEntry
			MAX-ACCESS not-accessible
			STATUS current
			DESCRIPTION
				"This table contains DPBO profile configuration.
				For more details, refer ITU-T G.997.1 chapter 7.3.1.2.13."
			INDEX { sheAdslLineDpboProfileIndex }
			::= { sheAdslLineDpboProfileTable 1 }

		
		SheAdslLineDpboProfileEntry ::=
			SEQUENCE { 
				sheAdslLineDpboProfileIndex
					Integer32,
				sheAdslLineDpboProfileName
					OCTET STRING,
				sheAdslLineDpboProfileEsel
					Unsigned32,
				sheAdslLineDpboProfileEselMin
					Unsigned32,
				sheAdslLineDpboProfileMus
					Unsigned32,
				sheAdslLineDpboProfileMof
					Unsigned32,
				sheAdslLineDpboProfileFMin
					Unsigned32,
				sheAdslLineDpboProfileFMax
					Unsigned32,
				sheAdslLineDpboProfileEpsd
					OCTET STRING,
				sheAdslLineDpboProfileEScmA
					Unsigned32,
				sheAdslLineDpboProfileEScmB
					Unsigned32,
				sheAdslLineDpboProfileEScmC
					Unsigned32
			 }

--   1.3.6.1.4.1.231.7.1.2.2.1.6.1.1.39.1.1
		sheAdslLineDpboProfileIndex OBJECT-TYPE
			SYNTAX Integer32 (1..100)
			MAX-ACCESS read-only
			STATUS current
			DESCRIPTION
				"Table Index, automatically generated when the table entry is created."
			::= { sheAdslLineDpboProfileEntry 1 }

		
--   1.3.6.1.4.1.231.7.1.2.2.1.6.1.1.39.1.2
		sheAdslLineDpboProfileName OBJECT-TYPE
			SYNTAX OCTET STRING (SIZE (1..32))
			MAX-ACCESS read-only
			STATUS current
			DESCRIPTION
				"This object is used by the line configuration table in order to identify a row
				of this table for Dpbo profile assign.
				
				Special characters are not allowed, like:  space : ?"
			::= { sheAdslLineDpboProfileEntry 2 }

		
--   1.3.6.1.4.1.231.7.1.2.2.1.6.1.1.39.1.3
		sheAdslLineDpboProfileEsel OBJECT-TYPE
			SYNTAX Unsigned32 (0..511)
			UNITS "0.5dB"
			MAX-ACCESS read-only
			STATUS current
			DESCRIPTION
				"This configuration parameter defines the assumed electrical length of cables
				(E-side cables) connecting exchange based DSL services to a remote flexibility
				point (cabinet), that may also host remotely located DSL that is subject
				to spectrally shaped downstream power backoff depending on this length.
				For this parameter the electrical length is defined as the loss (in dB)
				of an equivalent length of hypothetical cable at a reference frequency
				defined by the network operator or in spectrum management regulations.
				All values which can be represented by the format are valid values.
				
				If this value is zero, the DPBO in this section shall be disabled.
				If this value is not zero and sheAdslLineDpboProfileEselMin is not
				512 (disabled EselMin), sheAdslLineDpboProfileEsel >= sheAdslLineDpboProfileEselMin
				is required!
				"
			REFERENCE
				"g.997 chapter 7.3.1.2.13"
			DEFVAL { 0 }
			::= { sheAdslLineDpboProfileEntry 3 }

		
--   1.3.6.1.4.1.231.7.1.2.2.1.6.1.1.39.1.4
		sheAdslLineDpboProfileEselMin OBJECT-TYPE
			SYNTAX Unsigned32 (0..512)
			UNITS "0.5dB"
			MAX-ACCESS read-only
			STATUS current
			DESCRIPTION
				"This configuration parameter defines the minimum assumed electrical length 
				of cables (E-side cables) connecting exchange based DSL services to a 
				remote flexibility point (cabinet), that may also host remotely located DSL
				that is subject to spectrally shaped downstream power backoff depending on this
				length. For this parameter the electrical length is defined as the loss (in dB)
				of an equivalent length of hypothetical cable at a reference frequency
				defined by the network operator or in spectrum management regulations.
				All values which can be represented by the format are valid values.
				
				Default: sheAdslLineDpboProfileEselMin = 512
				
				If this value is not 512 (disabled) and sheAdslLineDpboProfileEsel is not
				zero (DPBO disabled), sheAdslLineDpboProfileEsel >= sheAdslLineDpboProfileEselMin
				is required!
				
				"
			REFERENCE
				"g.997 chapter 7.3.1.2.13"
			DEFVAL { 512 }
			::= { sheAdslLineDpboProfileEntry 4 }

		
--   1.3.6.1.4.1.231.7.1.2.2.1.6.1.1.39.1.5
		sheAdslLineDpboProfileMus OBJECT-TYPE
			SYNTAX Unsigned32 (0..255)
			UNITS "0.5 dBm/Hz"
			MAX-ACCESS read-only
			STATUS current
			DESCRIPTION
				"DPBOMUS defines the assumed Minimum Usable receive Signal PSD (in dBm/Hz) for
				exchange based services, used to modify parameter DPBOFMAX defined below. 
				All values which can be represented by the format are valid values:
				0 = 0 dBm/Hz .. -127.5 dBm/Hz (coded as 255)."
			REFERENCE
				"g.997 chapter 7.3.1.2.13"
			DEFVAL { 216 }
			::= { sheAdslLineDpboProfileEntry 5 }

		
--   1.3.6.1.4.1.231.7.1.2.2.1.6.1.1.39.1.6
		sheAdslLineDpboProfileMof OBJECT-TYPE
			SYNTAX Unsigned32 (0..255)
			UNITS "0.5 dBm/Hz"
			MAX-ACCESS read-only
			STATUS current
			DESCRIPTION
				"DPBOMOF (mask overall floor) defines the absolut minimum of the used PSD mask
				(in dBm/Hz) for exchange based services.
				All values which can be represented by the format are valid values:
				0 = 0 dBm/Hz .. -127.5 dBm/Hz (coded as 255).
				
				Note:
				Not longer supported!"
			REFERENCE
				"g.997 chapter 7.3.1.2.13"
			DEFVAL { 190 }
			::= { sheAdslLineDpboProfileEntry 6 }

		
--   1.3.6.1.4.1.231.7.1.2.2.1.6.1.1.39.1.7
		sheAdslLineDpboProfileFMin OBJECT-TYPE
			SYNTAX Unsigned32 (1..512)
			MAX-ACCESS read-only
			STATUS current
			DESCRIPTION
				"DPBO shall be applied in the range starting at DPBOFMIN and should
				be configured as an subcarrier index. 
				The range of valid values is from 1 to 512."
			REFERENCE
				"g.997 chapter 7.3.1.2.13"
			DEFVAL { 64 }
			::= { sheAdslLineDpboProfileEntry 7 }

		
--   1.3.6.1.4.1.231.7.1.2.2.1.6.1.1.39.1.8
		sheAdslLineDpboProfileFMax OBJECT-TYPE
			SYNTAX Unsigned32 (1..512)
			MAX-ACCESS read-only
			STATUS current
			DESCRIPTION
				"The maximum subcarrier at which DPBO may be applied is DPBOFMAX. 
				The range of valid values is from 1 to 512."
			REFERENCE
				"g.997 chapter 7.3.1.2.13"
			DEFVAL { 512 }
			::= { sheAdslLineDpboProfileEntry 8 }

		
--   1.3.6.1.4.1.231.7.1.2.2.1.6.1.1.39.1.9
		sheAdslLineDpboProfileEpsd OBJECT-TYPE
			SYNTAX OCTET STRING (SIZE (64))
			MAX-ACCESS read-only
			STATUS current
			DESCRIPTION
				"Used PSD mask that is assumed to be permitted at the exchange.
				The set of breakpoints can be represented as [(t1, PSD1),(t2, PSD2),
				.. , (tN, PSDN)]. The subcarrier index (tN) shall be coded as an unsigned
				integer (16 bit, range 1..512). The MIB PSD mask level (PSDN) shall be
				coded as an unsigned integer (16 bit) representing the MIB PSD mask levels
				0 dBm/Hz (coded as 0) to -127.5 dBm/Hz (coded as 255), in steps of 0.5 dBm/Hz.
				
				The maximum number of breakpoints for DPBOEPSD is 16. If less then maximum
				breakpoints will be defined, all used breakpoints should be configured in a
				consecutive way without spaces (t1 - t2 - t3.. and not t1 - t5 - t7..). The
				default value should be set according PSD settings for ADSL2+.
				
				Subcarrier     PSD
				59             -36.5 
				256            -36.5
				314            -42
				376            -46.5
				499            -47.5
				"
			REFERENCE
				"g.997 chapter 7.3.1.2.13"
			DEFVAL { '003B004901000049013A00540178005D01F3005F'h }
			::= { sheAdslLineDpboProfileEntry 9 }

		
--   1.3.6.1.4.1.231.7.1.2.2.1.6.1.1.39.1.10
		sheAdslLineDpboProfileEScmA OBJECT-TYPE
			SYNTAX Unsigned32 (0..640)
			UNITS "2^-8"
			MAX-ACCESS read-only
			STATUS current
			DESCRIPTION
				"This configuration parameter defines a cable model in terms of three
				scalars DPBOESCMA, DPBOESCMB and DPBOESCMC that are used to estimate
				the frequency dependent loss of E-side cables calculated from the
				
				DPBOESEL parameter using the formula:
				  ESCM(f) = (DPBOESCMA + DPBOESCMB*sqrt(f) + DPBOESCMC*f )*DPBOESCL
				
				Where ESCM is expressed in dB and f is expressed in MHz.
				DPBOESCMA, DPBOESCMB, DPBOESCMC shall be coded as unsigned integers
				representing a scalar value from -1 (coded as 0) to 1.5 (coded as 640)
				in step of 2^-8. All values are valid."
			REFERENCE
				"g.997 chapter 7.3.1.2.13"
			DEFVAL { 270 }
			::= { sheAdslLineDpboProfileEntry 10 }

		
--   1.3.6.1.4.1.231.7.1.2.2.1.6.1.1.39.1.11
		sheAdslLineDpboProfileEScmB OBJECT-TYPE
			SYNTAX Unsigned32 (0..640)
			UNITS "2^-8"
			MAX-ACCESS read-only
			STATUS current
			DESCRIPTION
				"This configuration parameter defines a cable model in terms of three
				scalars DPBOESCMA, DPBOESCMB and DPBOESCMC that are used to estimate
				the frequency dependent loss of E-side cables calculated from the
				
				DPBOESEL parameter using the formula:
				  ESCM(f) = (DPBOESCMA + DPBOESCMB*sqrt(f) + DPBOESCMC*f )*DPBOESCL
				
				Where ESCM is expressed in dB and f is expressed in MHz.
				DPBOESCMA, DPBOESCMB, DPBOESCMC shall be coded as unsigned integers
				representing a scalar value from -1 (coded as 0) to 1.5 (coded as 640)
				in step of 2^-8. All values are valid."
			REFERENCE
				"g.997 chapter 7.3.1.2.13"
			DEFVAL { 490 }
			::= { sheAdslLineDpboProfileEntry 11 }

		
--   1.3.6.1.4.1.231.7.1.2.2.1.6.1.1.39.1.12
		sheAdslLineDpboProfileEScmC OBJECT-TYPE
			SYNTAX Unsigned32 (0..640)
			UNITS "2^-8"
			MAX-ACCESS read-only
			STATUS current
			DESCRIPTION
				"This configuration parameter defines a cable model in terms of three
				scalars DPBOESCMA, DPBOESCMB and DPBOESCMC that are used to estimate
				the frequency dependent loss of E-side cables calculated from the
				
				DPBOESEL parameter using the formula:
				  ESCM(f) = (DPBOESCMA + DPBOESCMB*sqrt(f) + DPBOESCMC*f )*DPBOESCL
				
				Where ESCM is expressed in dB and f is expressed in MHz.
				DPBOESCMA, DPBOESCMB, DPBOESCMC shall be coded as unsigned integers
				representing a scalar value from -1 (coded as 0) to 1.5 (coded as 640)
				in step of 2^-8. All values are valid."
			REFERENCE
				"g.997 chapter 7.3.1.2.13"
			DEFVAL { 264 }
			::= { sheAdslLineDpboProfileEntry 12 }

		
--   1.3.6.1.4.1.231.7.1.2.2.1.6.1.1.30
-- Support with SHE R2.6 RP2.
		sheAdslLineDpboProfileControl OBJECT IDENTIFIER ::= { sheAdslLineMIB 40 }

		
--   1.3.6.1.4.1.231.7.1.2.2.1.6.1.1.40.1
		sheAdslLineDpboProfileControlRequest OBJECT-TYPE
			SYNTAX SheAdslControlRequestType
			MAX-ACCESS read-write
			STATUS current
			DESCRIPTION
				"createAdslLineDpboProfile:
				sheAdslLineDpboProfileControlName
				sheAdslLineDpboProfileControlEsel
				sheAdslLineDpboProfileControlEselMin
				sheAdslLineDpboProfileControlMus
				sheAdslLineDpboProfileControlMof
				sheAdslLineDpboProfileControlFMin
				sheAdslLineDpboProfileControlFMax
				sheAdslLineDpboProfileControlEpsd
				sheAdslLineDpboProfileControlEScmA
				sheAdslLineDpboProfileControlEScmB
				sheAdslLineDpboProfileControlEScmC
				
				modifyAdslLineDpboProfile:
				sheAdslLineDpboProfileControlIndex
				sheAdslLineDpboProfileControlEsel
				sheAdslLineDpboProfileControlEselMin
				sheAdslLineDpboProfileControlMus
				sheAdslLineDpboProfileControlMof
				sheAdslLineDpboProfileControlFMin
				sheAdslLineDpboProfileControlFMax
				sheAdslLineDpboProfileControlEpsd
				sheAdslLineDpboProfileControlEScmA
				sheAdslLineDpboProfileControlEScmB
				sheAdslLineDpboProfileControlEScmC
				
				deleteAdslLineDpboProfile
				sheAdslLineDpboProfileControlIndex"
			::= { sheAdslLineDpboProfileControl 1 }

		
--   1.3.6.1.4.1.231.7.1.2.2.1.6.1.1.40.2
		sheAdslLineDpboProfileControlIndex OBJECT-TYPE
			SYNTAX Integer32 (1..100)
			MAX-ACCESS read-write
			STATUS current
			DESCRIPTION
				"Index of the Table-entry to be configured."
			::= { sheAdslLineDpboProfileControl 2 }

		
--   1.3.6.1.4.1.231.7.1.2.2.1.6.1.1.40.3
		sheAdslLineDpboProfileControlStatus OBJECT-TYPE
			SYNTAX SheControlStatusType
			MAX-ACCESS read-only
			STATUS current
			DESCRIPTION
				"The status of a user command. 
				"
			::= { sheAdslLineDpboProfileControl 3 }

		
--   1.3.6.1.4.1.231.7.1.2.2.1.6.1.1.40.4
		sheAdslLineDpboProfileControlTimer OBJECT-TYPE
			SYNTAX Gauge32
			MAX-ACCESS read-only
			STATUS current
			DESCRIPTION
				"The maximum wait time for the manager for a long running user command. 
				"
			::= { sheAdslLineDpboProfileControl 4 }

		
--   1.3.6.1.4.1.231.7.1.2.2.1.6.1.1.40.5
		sheAdslLineDpboProfileControlReqResult OBJECT-TYPE
			SYNTAX SheAdslControlRequestResultType
			MAX-ACCESS read-only
			STATUS current
			DESCRIPTION
				"The result of the last user command."
			::= { sheAdslLineDpboProfileControl 5 }

		
--   1.3.6.1.4.1.231.7.1.2.2.1.6.1.1.40.6
		sheAdslLineDpboProfileControlTimeStamp OBJECT-TYPE
			SYNTAX Unsigned32
			UNITS "sec"
			MAX-ACCESS read-only
			STATUS current
			DESCRIPTION
				"The time stamp of the last command (end of command)."
			::= { sheAdslLineDpboProfileControl 6 }

		
--   1.3.6.1.4.1.231.7.1.2.2.1.6.1.1.40.7
		sheAdslLineDpboProfileControlName OBJECT-TYPE
			SYNTAX OCTET STRING (SIZE (1..32))
			MAX-ACCESS read-write
			STATUS current
			DESCRIPTION
				"A descriptional name for the Dpbo profile."
			::= { sheAdslLineDpboProfileControl 7 }

		
--   1.3.6.1.4.1.231.7.1.2.2.1.6.1.1.40.8
		sheAdslLineDpboProfileControlEsel OBJECT-TYPE
			SYNTAX Unsigned32 (0..511)
			UNITS "0.5dB"
			MAX-ACCESS read-write
			STATUS current
			DESCRIPTION
				"look at table"
			::= { sheAdslLineDpboProfileControl 8 }

		
--   1.3.6.1.4.1.231.7.1.2.2.1.6.1.1.40.9
		sheAdslLineDpboProfileControlEselMin OBJECT-TYPE
			SYNTAX Unsigned32 (0..512)
			UNITS "0.5dB"
			MAX-ACCESS read-write
			STATUS current
			DESCRIPTION
				"look at table"
			::= { sheAdslLineDpboProfileControl 9 }

		
--   1.3.6.1.4.1.231.7.1.2.2.1.6.1.1.40.10
		sheAdslLineDpboProfileControlMus OBJECT-TYPE
			SYNTAX Unsigned32 (0..255)
			UNITS "0.5 dBm/Hz"
			MAX-ACCESS read-write
			STATUS current
			DESCRIPTION
				"look at table"
			::= { sheAdslLineDpboProfileControl 10 }

		
--   1.3.6.1.4.1.231.7.1.2.2.1.6.1.1.40.11
		sheAdslLineDpboProfileControlMof OBJECT-TYPE
			SYNTAX Unsigned32 (0..255)
			UNITS "0.5 dBm/Hz"
			MAX-ACCESS read-write
			STATUS current
			DESCRIPTION
				"look at table
				
				Note:
				Not longer supported!"
			::= { sheAdslLineDpboProfileControl 11 }

		
--   1.3.6.1.4.1.231.7.1.2.2.1.6.1.1.40.12
		sheAdslLineDpboProfileControlFMin OBJECT-TYPE
			SYNTAX Unsigned32 (1..512)
			MAX-ACCESS read-write
			STATUS current
			DESCRIPTION
				"look at table"
			::= { sheAdslLineDpboProfileControl 12 }

		
--   1.3.6.1.4.1.231.7.1.2.2.1.6.1.1.40.13
		sheAdslLineDpboProfileControlFMax OBJECT-TYPE
			SYNTAX Unsigned32 (1..512)
			MAX-ACCESS read-write
			STATUS current
			DESCRIPTION
				"look at table"
			::= { sheAdslLineDpboProfileControl 13 }

		
--   1.3.6.1.4.1.231.7.1.2.2.1.6.1.1.40.14
		sheAdslLineDpboProfileControlEpsd OBJECT-TYPE
			SYNTAX OCTET STRING (SIZE (64))
			MAX-ACCESS read-write
			STATUS current
			DESCRIPTION
				"look at table."
			::= { sheAdslLineDpboProfileControl 14 }

		
--   1.3.6.1.4.1.231.7.1.2.2.1.6.1.1.40.15
		sheAdslLineDpboProfileControlEScmA OBJECT-TYPE
			SYNTAX Unsigned32 (0..640)
			UNITS "2^-8"
			MAX-ACCESS read-write
			STATUS current
			DESCRIPTION
				"look at table."
			::= { sheAdslLineDpboProfileControl 15 }

		
--   1.3.6.1.4.1.231.7.1.2.2.1.6.1.1.40.16
		sheAdslLineDpboProfileControlEScmB OBJECT-TYPE
			SYNTAX Unsigned32 (0..640)
			UNITS "2^-8"
			MAX-ACCESS read-write
			STATUS current
			DESCRIPTION
				"look at table."
			::= { sheAdslLineDpboProfileControl 16 }

		
--   1.3.6.1.4.1.231.7.1.2.2.1.6.1.1.40.17
		sheAdslLineDpboProfileControlEScmC OBJECT-TYPE
			SYNTAX Unsigned32 (0..640)
			UNITS "2^-8"
			MAX-ACCESS read-write
			STATUS current
			DESCRIPTION
				"look at table."
			::= { sheAdslLineDpboProfileControl 17 }

		
--   1.3.6.1.4.1.231.7.1.2.2.1.6.1.1.39
		sheAdslVccTpPerformanceTable OBJECT-TYPE
			SYNTAX SEQUENCE OF SheAdslVccTpPerformanceEntry
			MAX-ACCESS not-accessible
			STATUS current
			DESCRIPTION
				"The VccTpPerformance-Table."
			::= { sheAdslLineMIB 41 }

		
--   1.3.6.1.4.1.231.7.1.2.2.1.6.1.1.25.1
		sheAdslVccTpPerformanceEntry OBJECT-TYPE
			SYNTAX SheAdslVccTpPerformanceEntry
			MAX-ACCESS not-accessible
			STATUS current
			DESCRIPTION
				"This table contains the VccTpPerformance-Counters.
				These are free running counters. The counters could be deleted with command 
				deleteAdslVccTpPerformanceCounters via sheAdslVccTpControl-Group.
				"
			INDEX { sheAdslVccTpIndex }
			::= { sheAdslVccTpPerformanceTable 1 }

		
		SheAdslVccTpPerformanceEntry ::=
			SEQUENCE { 
				sheAdslVccTpIngressUnicastPackets
					Counter32,
				sheAdslVccTpIngressMulticastPackets
					Counter32,
				sheAdslVccTpIngressBroadcastPackets
					Counter32,
				sheAdslVccTpIngressDiscardPackets
					Counter32,
				sheAdslVccTpEgressUnicastPackets
					Counter32,
				sheAdslVccTpEgressMulticastPackets
					Counter32,
				sheAdslVccTpEgressBroadcastPackets
					Counter32,
				sheAdslVccTpEgressDiscardPackets
					Counter32
			 }

--   1.3.6.1.4.1.231.7.1.2.2.1.6.1.1.39.1.1
		sheAdslVccTpIngressUnicastPackets OBJECT-TYPE
			SYNTAX Counter32
			MAX-ACCESS read-only
			STATUS current
			DESCRIPTION
				"Ingress Unicast Packet Counter for this VccTp."
			::= { sheAdslVccTpPerformanceEntry 1 }

		
--   1.3.6.1.4.1.231.7.1.2.2.1.6.1.1.39.1.1
		sheAdslVccTpIngressMulticastPackets OBJECT-TYPE
			SYNTAX Counter32
			MAX-ACCESS read-only
			STATUS current
			DESCRIPTION
				"Ingress Multicast Packet Counter for this VccTp."
			::= { sheAdslVccTpPerformanceEntry 2 }

		
--   1.3.6.1.4.1.231.7.1.2.2.1.6.1.1.39.1.1
		sheAdslVccTpIngressBroadcastPackets OBJECT-TYPE
			SYNTAX Counter32
			MAX-ACCESS read-only
			STATUS current
			DESCRIPTION
				"Ingress Broadcast Packet Counter for this VccTp."
			::= { sheAdslVccTpPerformanceEntry 3 }

		
--   1.3.6.1.4.1.231.7.1.2.2.1.6.1.1.39.1.1
		sheAdslVccTpIngressDiscardPackets OBJECT-TYPE
			SYNTAX Counter32
			MAX-ACCESS read-only
			STATUS current
			DESCRIPTION
				"Ingress Discard Packet Counter for this VccTp."
			::= { sheAdslVccTpPerformanceEntry 4 }

		
--   1.3.6.1.4.1.231.7.1.2.2.1.6.1.1.39.1.1
		sheAdslVccTpEgressUnicastPackets OBJECT-TYPE
			SYNTAX Counter32
			MAX-ACCESS read-only
			STATUS current
			DESCRIPTION
				"Egress Unicast Packet Counter for this VccTp."
			::= { sheAdslVccTpPerformanceEntry 5 }

		
--   1.3.6.1.4.1.231.7.1.2.2.1.6.1.1.39.1.1
		sheAdslVccTpEgressMulticastPackets OBJECT-TYPE
			SYNTAX Counter32
			MAX-ACCESS read-only
			STATUS current
			DESCRIPTION
				"Egress Multicast Packet Counter for this VccTp."
			::= { sheAdslVccTpPerformanceEntry 6 }

		
--   1.3.6.1.4.1.231.7.1.2.2.1.6.1.1.39.1.1
		sheAdslVccTpEgressBroadcastPackets OBJECT-TYPE
			SYNTAX Counter32
			MAX-ACCESS read-only
			STATUS current
			DESCRIPTION
				"Egress Broadcast Packet Counter for this VccTp."
			::= { sheAdslVccTpPerformanceEntry 7 }

		
--   1.3.6.1.4.1.231.7.1.2.2.1.6.1.1.39.1.1
		sheAdslVccTpEgressDiscardPackets OBJECT-TYPE
			SYNTAX Counter32
			MAX-ACCESS read-only
			STATUS current
			DESCRIPTION
				"Egress Discard Packet Counter for this VccTp."
			::= { sheAdslVccTpPerformanceEntry 8 }

		
--   1.3.6.1.4.1.231.7.1.2.2.1.6.1.1.100
		sheAdslConformance OBJECT IDENTIFIER ::= { sheAdslLineMIB 100 }

		
--   1.3.6.1.4.1.231.7.1.2.2.1.6.1.1.100.1
		sheAdslCompliances OBJECT IDENTIFIER ::= { sheAdslConformance 1 }

		
-- 1.3.6.1.4.1.231.7.1.2.2.1.6.1.1.100.1.1
-- 
		sheAdslCompliance MODULE-COMPLIANCE
			STATUS current
			DESCRIPTION 
				"Description."
			MODULE -- this module
				MANDATORY-GROUPS { sheAdslVccTpGroup, sheAdslVccTpControlGroup, sheAdslVccTpNotificationGroup, sheAdslGroup, sheAdslControlGroup, 
					sheAdslNotificationGroup }
				GROUP sheAdslDualChanGroup
					DESCRIPTION 
						"Only supported by NE releases up R2.5."
				GROUP sheAdslObsoleteGroup
					DESCRIPTION 
						"THIS ELEMENTS WILL NOT LONGER BE SUPPORTED BY NE up R2.5."
				GROUP sheAdslObsoleteNotificationGroup
					DESCRIPTION 
						"THIS ELEMENTS WILL NOT LONGER BE SUPPORTED BY NE up R2.5."
			::= { sheAdslCompliances 1 }

		
--   1.3.6.1.4.1.231.7.1.2.2.1.6.1.1.100.2
		sheAdslGroups OBJECT IDENTIFIER ::= { sheAdslConformance 2 }

		
--   1.3.6.1.4.1.231.7.1.2.2.1.6.1.1.100.2.1
		sheAdslVccTpGroup OBJECT-GROUP
			OBJECTS { sheAdslVccTpVpi, sheAdslVccTpVci, sheAdslVccTpOamLevel, sheAdslVccTpAlarmSeverityIndex, sheAdslVccTpLoopTestResult, 
				sheAdslVccTpNumber, sheAdslVccTpSubLayerIndex, sheAdslVccTpIndex, sheAdslVccTpEgressQosClass, sheAdslVccTpEgressPeakCellRate, 
				sheAdslVccTpEgressSustainedCellRate, sheAdslVccTpEgressMaxBurstSize, sheAdslVccTpEgressWeight, sheAdslVccTpIngressSustainedCellRate, sheAdslVccTpIngressMaxBurstSize, 
				sheAdslVccTpUsedDslChannel, sheAdslVccTpIngressUnicastPackets, sheAdslVccTpIngressMulticastPackets, sheAdslVccTpIngressBroadcastPackets, sheAdslVccTpIngressDiscardPackets, 
				sheAdslVccTpEgressUnicastPackets, sheAdslVccTpEgressMulticastPackets, sheAdslVccTpEgressBroadcastPackets, sheAdslVccTpEgressDiscardPackets, sheAdslVccTpEncapsulation, 
				sheAdslVccTpLoopLocId, sheAdslVccTpLoopTest, sheAdslVccTpAdminState, sheAdslVccTpOrl }
			STATUS current
			DESCRIPTION 
				"Description."
			::= { sheAdslGroups 1 }

		
--   1.3.6.1.4.1.231.7.1.2.2.1.6.1.1.100.2.2
		sheAdslVccTpControlGroup OBJECT-GROUP
			OBJECTS { sheAdslVccTpControlRequest, sheAdslVccTpControlIndex, sheAdslVccTpControlStatus, sheAdslVccTpControlTimer, sheAdslVccTpControlReqResult, 
				sheAdslVccTpControlTimeStamp, sheAdslVccTpControlVpi, sheAdslVccTpControlVci, sheAdslVccTpControlEgressQosClass, sheAdslVccTpControlEgressPeakCellRate, 
				sheAdslVccTpControlEgressSustainedCellRate, sheAdslVccTpControlEgressMaxBurstSize, sheAdslVccTpControlEgressWeight, sheAdslVccTpControlIngressSustainedCellRate, sheAdslVccTpControlIngressMaxBurstSize, 
				sheAdslVccTpControlUsedDslChannel, sheAdslVccTpControlEncapsulation, sheAdslVccTpControlLoopTest, sheAdslVccTpControlSubLayerIndex, sheAdslVccTpControlAlarmSeverityIndex, 
				sheAdslVccTpControlAdminState, sheAdslVccTpControlOrl }
			STATUS current
			DESCRIPTION 
				"Description."
			::= { sheAdslGroups 2 }

		
--   1.3.6.1.4.1.231.7.1.2.2.1.6.1.1.100.2.3
		sheAdslVccTpNotificationGroup NOTIFICATION-GROUP
			NOTIFICATIONS { sheAdslVccTpCreated, sheAdslVccRDIAlarm, sheAdslVccAISAlarm, sheAdslVccTpConfigurationFailed, sheAdslVccTpAdminStateChanged, 
				sheAdslVccTpOrlChanged, sheAdslVccTpChangedEgressShaping, sheAdslVccTpChangedIngressPolicing, sheAdslVccTpUsedDslChannelChanged, sheAdslVccTpPerformanceCountersCleared, 
				sheAdslVccTpDeleted, sheAdslVccTpModified, sheAdslVccTpEncapsulationChanged }
			STATUS current
			DESCRIPTION 
				"Description."
			::= { sheAdslGroups 3 }

		
--   1.3.6.1.4.1.231.7.1.2.2.1.6.1.1.100.2.4
		sheAdslGroup OBJECT-GROUP
			OBJECTS { sheAdslLineConfProfileIndex, sheAdslLineConfProfileName, sheAdslLineConfProfileAtucConfRateMode, sheAdslLineConfProfileAtucConfRateChanRatio, sheAdslLineConfProfileAtucConfTargetSnrMgn, 
				sheAdslLineConfProfileAtucConfMaxSnrMgn, sheAdslLineConfProfileAtucConfMinSnrMgn, sheAdslLineConfProfileAtucConfDownshiftSnrMgn, sheAdslLineConfProfileAtucConfUpshiftSnrMgn, sheAdslLineConfProfileAtucConfMinUpshiftTime, 
				sheAdslLineConfProfileAtucConfMinDownshiftTime, sheAdslLineConfProfileAtucChanConfFastMinTxRate, sheAdslLineConfProfileAtucChanConfInterleaveMinTxRate, sheAdslLineConfProfileAtucChanConfFastMaxTxRate, sheAdslLineConfProfileAtucChanConfInterleaveMaxTxRate, 
				sheAdslLineConfProfileAtucChanConfMaxInterleaveDelay, sheAdslLineConfProfileAturConfRateMode, sheAdslLineConfProfileAturConfRateChanRatio, sheAdslLineConfProfileAturConfTargetSnrMgn, sheAdslLineConfProfileAturConfMaxSnrMgn, 
				sheAdslLineConfProfileAturConfMinSnrMgn, sheAdslLineConfProfileAturConfDownshiftSnrMgn, sheAdslLineConfProfileAturConfUpshiftSnrMgn, sheAdslLineConfProfileAturConfMinUpshiftTime, sheAdslLineConfProfileAturConfMinDownshiftTime, 
				sheAdslLineConfProfileAturChanConfFastMinTxRate, sheAdslLineConfProfileAturChanConfInterleaveMinTxRate, sheAdslLineConfProfileAturChanConfFastMaxTxRate, sheAdslLineConfProfileAturChanConfInterleaveMaxTxRate, sheAdslLineConfProfileAturChanConfMaxInterleaveDelay, 
				sheAdslLineConfProfileTrellis, sheAdslLineConfProfileAtucConfPwrMgmtL0Time, sheAdslLineConfProfileAtucConfPwrMgmtL2Time, sheAdslLineConfProfileAtucConfPwrMgmtL2ATPR, sheAdslLineConfProfileAtucConfPwrMgmtL2Rate, 
				sheAdslLineConfProfileAtucConfPwrMgmtMode, sheAdslLineConfExtnProfileParametricTestInputFile, sheAdslLineConfExtnProfileRsIntCorrectionUp, sheAdslLineConfExtnProfileLineType, sheAdslLineConfExtnProfileTxEndBin, 
				sheAdslLineConfExtnProfileTxStartBin, sheAdslLineConfExtnProfileMaxBitsPerBin, sheAdslLineConfExtnProfileRxStartBin, sheAdslLineConfExtnProfileRxEndBin, sheAdslLineConfExtnProfileRxBinAdjust, 
				sheAdslLineConfExtnProfileTriggerMode, sheAdslLineConfExtnProfileAdi2x, sheAdslLineConfExtnProfileStandard, sheAdslLineConfExtnProfileInitiate, sheAdslLineConfExtnProfileTxPowerAttenuation, 
				sheAdslLineConfExtnProfileCodingGain, sheAdslLineConfExtnProfileRsFastOvrhdDown, sheAdslLineConfExtnProfileIntCorrectionDown, sheAdslLineConfExtnProfileRsFastOvrhdUp, sheAdslLineConfExtnProfileDrStby, 
				sheAdslLineConfExtnProfileExpandedExchange, sheAdslLineConfExtnProfileEscapeFastRetrainEnable, sheAdslLineConfExtnProfileFastRetrainEnable, sheAdslLineConfExtnProfileBitSwap, sheAdslLineConfExtnProfileNtr, 
				sheAdslLineConfExtnProfileAnnexType, sheAdslLineConfExtnProfileAlctlUsVer, sheAdslLineConfExtnProfileUseCustomBin, sheAdslLineConfExtnProfileDnBinUsage, sheAdslLineConfExtnProfileMaxDCo, 
				sheAdslLineConfExtnProfileFullRetrain, sheAdslLineConfExtnProfileAdvertisedCapabilities, sheAdslLineConfExtnProfilePsdMaskType, sheAdslLineConfExtnProfileLineDmtConfMode, sheAdslLineConfExtnProfileEraseProfiles, 
				sheAdslLineConfExtnProfileRsMemory, sheAdslLineConfExtnProfileParamHybridLossTestStart, sheAdslLineConfExtnProfileParamHybridLossTestEnd, sheAdslLineConfExtnProfileConfMinInp, sheAdslLineConfExtnProfileUpstreamPsdMaskSelection, 
				sheAdslLineConfExtnProfileMaxNomPsdDs, sheAdslLineConfExtnProfileMaxNomAtpDs, sheAdslLineConfExtnProfilePsdMaskDs, sheAdslLineCoding, sheAdslLineType, 
				sheAdslLineSpecific, sheAdslLineConfProfile, sheAdslLineAlarmConfProfile, sheAdslLineAction, sheAdslLineLineDmtTrellis, 
				sheAdslLineAtucCapability, sheAdslLineAturCapability, sheAdslLineAtuActualCapability, sheAdslLinePwrMgmtPMSF, sheAdslLineDeltConfLDSF, 
				sheAdslLineRfiBandMask, sheAdslAtucPhysInvSerialNumber, sheAdslAtucPhysInvVendorID, sheAdslAtucPhysInvVersionNumber, sheAdslAtucPhysCurrSnrMgn, 
				sheAdslAtucPhysCurrAtn, sheAdslAtucPhysCurrStatus, sheAdslAtucPhysCurrOutputPwr, sheAdslAtucPhysCurrAttainableRate, sheAdslAtucPhysOpState, 
				sheAdslAtucPhysActualStd, sheAdslAtucPhysBertError, sheAdslAtucPhysTxAtmCellCounter, sheAdslAtucPhysRxAtmCellCounter, sheAdslAtucPhysStartProgress, 
				sheAdslAtucPhysIdleBertError, sheAdslAtucPhysIdleBertCells, sheAdslAtucPhysBertSync, sheAdslAtucPhysParametricTestResult, sheAdslAtucPwrMgmtState, 
				sheAdslAtucPhysDeltHLINSCus, sheAdslAtucPhysDeltHLINpsus, sheAdslAtucPhysDeltHLOGMTus, sheAdslAtucPhysDeltHLOGpsus, sheAdslAtucPhysDeltQLNMTus, 
				sheAdslAtucPhysDeltQLNpsus, sheAdslAtucChanInterleaveDelay, sheAdslAtucChanCurrTxRate, sheAdslAtucChanPrevTxRate, sheAdslAtucChanCrcBlockLength, 
				sheAdslAtucChanCurrAtmStatus, sheAdslAtucChanRsSymbols, sheAdslAtucChanRsDepth, sheAdslAtucChanRsRedundancy, sheAdslAtucPerfDataLofs, 
				sheAdslAtucPerfDataLoss, sheAdslAtucPerfDataLols, sheAdslAtucPerfDataLprs, sheAdslAtucPerfDataESs, sheAdslAtucPerfDataInits, 
				sheAdslAtucPerfDataStatFastR, sheAdslAtucPerfDataStatFailedFastR, sheAdslAtucPerfDataStatSesL, sheAdslAtucPerfDataStatUasL, sheAdslAtucPerfDataValidIntervals, 
				sheAdslAtucPerfDataInvalidIntervals, sheAdslAtucPerfDataCurr15MinTimeElapsed, sheAdslAtucPerfDataCurr15MinLofs, sheAdslAtucPerfDataCurr15MinLoss, sheAdslAtucPerfDataCurr15MinLols, 
				sheAdslAtucPerfDataCurr15MinLprs, sheAdslAtucPerfDataCurr15MinESs, sheAdslAtucPerfDataCurr15MinInits, sheAdslAtucPerfDataCurr15MinFastR, sheAdslAtucPerfDataCurr15MinFailedFastR, 
				sheAdslAtucPerfDataCurr15MinSesL, sheAdslAtucPerfDataCurr15MinUasL, sheAdslAtucPerfDataCurr1DayTimeElapsed, sheAdslAtucPerfDataCurr1DayLofs, sheAdslAtucPerfDataCurr1DayLoss, 
				sheAdslAtucPerfDataCurr1DayLols, sheAdslAtucPerfDataCurr1DayLprs, sheAdslAtucPerfDataCurr1DayESs, sheAdslAtucPerfDataCurr1DayInits, sheAdslAtucPerfDataCurr1DayFastR, 
				sheAdslAtucPerfDataCurr1DayFailedFastR, sheAdslAtucPerfDataCurr1DaySesL, sheAdslAtucPerfDataCurr1DayUasL, sheAdslAtucPerfDataPrev1DayTimeElapsed, sheAdslAtucPerfDataPrev1DayMoniSecs, 
				sheAdslAtucPerfDataPrev1DayLofs, sheAdslAtucPerfDataPrev1DayLoss, sheAdslAtucPerfDataPrev1DayLols, sheAdslAtucPerfDataPrev1DayLprs, sheAdslAtucPerfDataPrev1DayESs, 
				sheAdslAtucPerfDataPrev1DayInits, sheAdslAtucPerfDataPrev1DayFastR, sheAdslAtucPerfDataPrev1DayFailedFastR, sheAdslAtucPerfDataPrev1DaySesL, sheAdslAtucPerfDataPrev1DayUasL, 
				sheAdslAtucIntervalNumber, sheAdslAtucIntervalValidData, sheAdslAtucIntervalEndTime, sheAdslAtucIntervalLofs, sheAdslAtucIntervalLoss, 
				sheAdslAtucIntervalLols, sheAdslAtucIntervalLprs, sheAdslAtucIntervalESs, sheAdslAtucIntervalInits, sheAdslAtucIntervalFastR, 
				sheAdslAtucIntervalFailedFastR, sheAdslAtucIntervalSesL, sheAdslAtucIntervalUasL, sheAdslAtucChanPerfDataTimeElapsed, sheAdslAtucChanPerfDataReceivedBlks, 
				sheAdslAtucChanPerfDataTransmittedBlks, sheAdslAtucChanPerfDataCorrectedBlks, sheAdslAtucChanPerfDataUncorrectBlks, sheAdslAtucChanPerfDataNcd, sheAdslAtucChanPerfDataOcd, 
				sheAdslAtucChanPerfDataHec, sheAdslAtucChanPerfDataValidIntervals, sheAdslAtucChanPerfDataInvalidIntervals, sheAdslAtucChanPerfDataCurr15MinTimeElapsed, sheAdslAtucChanPerfDataCurr15MinReceivedBlks, 
				sheAdslAtucChanPerfDataCurr15MinTransmittedBlks, sheAdslAtucChanPerfDataCurr15MinCorrectedBlks, sheAdslAtucChanPerfDataCurr15MinUncorrectBlks, sheAdslAtucChanPerfDataCurr15MinNcd, sheAdslAtucChanPerfDataCurr15MinOcd, 
				sheAdslAtucChanPerfDataCurr15MinHec, sheAdslAtucChanPerfDataCurr1DayTimeElapsed, sheAdslAtucChanPerfDataCurr1DayReceivedBlks, sheAdslAtucChanPerfDataCurr1DayTransmittedBlks, sheAdslAtucChanPerfDataCurr1DayCorrectedBlks, 
				sheAdslAtucChanPerfDataCurr1DayUncorrectBlks, sheAdslAtucChanPerfDataCurr1DayNcd, sheAdslAtucChanPerfDataCurr1DayOcd, sheAdslAtucChanPerfDataCurr1DayHec, sheAdslAtucChanPerfDataPrev1DayMoniSecs, 
				sheAdslAtucChanPerfDataPrev1DayReceivedBlks, sheAdslAtucChanPerfDataPrev1DayTransmittedBlks, sheAdslAtucChanPerfDataPrev1DayCorrectedBlks, sheAdslAtucChanPerfDataPrev1DayUncorrectBlks, sheAdslAtucChanPerfDataPrev1DayNcd, 
				sheAdslAtucChanPerfDataPrev1DayOcd, sheAdslAtucChanPerfDataPrev1DayHec, sheAdslAtucChanIntervalNumber, sheAdslAtucChanIntervalValidData, sheAdslAtucChanIntervalEndTime, 
				sheAdslAtucChanIntervalReceivedBlks, sheAdslAtucChanIntervalTransmittedBlks, sheAdslAtucChanIntervalCorrectedBlks, sheAdslAtucChanIntervalUncorrectBlks, sheAdslAtucChanIntervalNcd, 
				sheAdslAtucChanIntervalOcd, sheAdslAtucChanIntervalHec, sheAdslAturPhysInvSerialNumber, sheAdslAturPhysInvVendorID, sheAdslAturPhysInvVersionNumber, 
				sheAdslAturPhysCurrSnrMgn, sheAdslAturPhysCurrAtn, sheAdslAturPhysCurrStatus, sheAdslAturPhysCurrOutputPwr, sheAdslAturPhysCurrAttainableRate, 
				sheAdslAturPhysConfig, sheAdslAturPhysDeltHLINSCds, sheAdslAturPhysDeltHLINpsds, sheAdslAturPhysDeltHLOGMTds, sheAdslAturPhysDeltHLOGpsds, 
				sheAdslAturPhysDeltQLNMTds, sheAdslAturPhysDeltQLNpsds, sheAdslAturChanInterleaveDelay, sheAdslAturChanCurrTxRate, sheAdslAturChanPrevTxRate, 
				sheAdslAturChanCrcBlockLength, sheAdslAturChanCurrAtmStatus, sheAdslAturChanRsSymbols, sheAdslAturChanRsDepth, sheAdslAturChanRsRedundancy, 
				sheAdslAturPerfDataLofs, sheAdslAturPerfDataLoss, sheAdslAturPerfDataLprs, sheAdslAturPerfDataESs, sheAdslAturPerfDataStatSesL, 
				sheAdslAturPerfDataStatUasL, sheAdslAturPerfDataValidIntervals, sheAdslAturPerfDataInvalidIntervals, sheAdslAturPerfDataCurr15MinTimeElapsed, sheAdslAturPerfDataCurr15MinLofs, 
				sheAdslAturPerfDataCurr15MinLoss, sheAdslAturPerfDataCurr15MinLprs, sheAdslAturPerfDataCurr15MinESs, sheAdslAturPerfDataCurr15MinSesL, sheAdslAturPerfDataCurr15MinUasL, 
				sheAdslAturPerfDataCurr1DayTimeElapsed, sheAdslAturPerfDataCurr1DayLofs, sheAdslAturPerfDataCurr1DayLoss, sheAdslAturPerfDataCurr1DayLprs, sheAdslAturPerfDataCurr1DayESs, 
				sheAdslAturPerfDataCurr1DaySesL, sheAdslAturPerfDataCurr1DayUasL, sheAdslAturPerfDataPrev1DayMoniSecs, sheAdslAturPerfDataPrev1DayLofs, sheAdslAturPerfDataPrev1DayLoss, 
				sheAdslAturPerfDataPrev1DayLprs, sheAdslAturPerfDataPrev1DayESs, sheAdslAturPerfDataPrev1DaySesL, sheAdslAturPerfDataPrev1DayUasL, sheAdslAturIntervalNumber, 
				sheAdslAturIntervalValidData, sheAdslAturIntervalEndTime, sheAdslAturIntervalLofs, sheAdslAturIntervalLoss, sheAdslAturIntervalLprs, 
				sheAdslAturIntervalESs, sheAdslAturIntervalSesL, sheAdslAturIntervalUasL, sheAdslAturChanPerfDataReceivedBlks, sheAdslAturChanPerfDataTransmittedBlks, 
				sheAdslAturChanPerfDataCorrectedBlks, sheAdslAturChanPerfDataUncorrectBlks, sheAdslAturChanPerfDataExtnNcd, sheAdslAturChanPerfDataExtnHec, sheAdslAturChanPerfDataPerfValidIntervals, 
				sheAdslAturChanPerfDataPerfInvalidIntervals, sheAdslAturChanPerfDataCurr15MinTimeElapsed, sheAdslAturChanPerfDataCurr15MinReceivedBlks, sheAdslAturChanPerfDataCurr15MinTransmittedBlks, sheAdslAturChanPerfDataCurr15MinCorrectedBlks, 
				sheAdslAturChanPerfDataCurr15MinUncorrectBlks, sheAdslAturChanPerfDataExtnCurr15MinNcd, sheAdslAturChanPerfDataExtnCurr15MinHec, sheAdslAturChanPerfDataCurr1DayTimeElapsed, sheAdslAturChanPerfDataCurr1DayReceivedBlks, 
				sheAdslAturChanPerfDataCurr1DayTransmittedBlks, sheAdslAturChanPerfDataCurr1DayCorrectedBlks, sheAdslAturChanPerfDataCurr1DayUncorrectBlks, sheAdslAturChanPerfDataExtnCurr1DayNcd, sheAdslAturChanPerfDataExtnCurr1DayHec, 
				sheAdslAturChanPerfDataPrev1DayMoniSecs, sheAdslAturChanPerfDataPrev1DayReceivedBlks, sheAdslAturChanPerfDataPrev1DayTransmittedBlks, sheAdslAturChanPerfDataPrev1DayCorrectedBlks, sheAdslAturChanPerfDataPrev1DayUncorrectBlks, 
				sheAdslAturChanPerfDataExtnPrev1DayNcd, sheAdslAturChanPerfDataExtnPrev1DayHec, sheAdslAturChanIntervalNumber, sheAdslAturChanIntervalValidData, sheAdslAturChanIntervalEndTime, 
				sheAdslAturChanIntervalReceivedBlks, sheAdslAturChanIntervalTransmittedBlks, sheAdslAturChanIntervalCorrectedBlks, sheAdslAturChanIntervalUncorrectBlks, sheAdslAturChanIntervalNcd, 
				sheAdslAturChanIntervalHec, sheAdslLineAlarmConfProfileIndex, sheAdslLineAlarmConfProfileName, sheAdslLineAlarmConfProfileOpStateTrapEnable, sheAdslLineAlarmConfProfileAtucThreshFastRateUp, 
				sheAdslLineAlarmConfProfileAtucThreshInterleaveRateUp, sheAdslLineAlarmConfProfileAtucThreshFastRateDown, sheAdslLineAlarmConfProfileAtucThreshInterleaveRateDown, sheAdslLineAlarmConfProfileAtucInitFailureTrapEnable, sheAdslLineAlarmConfProfileAtucThresh15MinLofs, 
				sheAdslLineAlarmConfProfileAtucThresh15MinLoss, sheAdslLineAlarmConfProfileAtucThresh15MinLols, sheAdslLineAlarmConfProfileAtucThresh15MinLprs, sheAdslLineAlarmConfProfileAtucThresh15MinESs, sheAdslLineAlarmConfProfileAtucThresh15MinSesL, 
				sheAdslLineAlarmConfProfileAtucThresh15MinUasL, sheAdslLineAlarmConfProfileAtucThresh15MinFailFastR, sheAdslLineAlarmConfProfileAturThreshFastRateUp, sheAdslLineAlarmConfProfileAturThreshInterleaveRateUp, sheAdslLineAlarmConfProfileAturThreshFastRateDown, 
				sheAdslLineAlarmConfProfileAturThreshInterleaveRateDown, sheAdslLineAlarmConfProfileAturThresh15MinLofs, sheAdslLineAlarmConfProfileAturThresh15MinLoss, sheAdslLineAlarmConfProfileAturThresh15MinLprs, sheAdslLineAlarmConfProfileAturThresh15MinESs, 
				sheAdslLineAlarmConfProfileAturThresh15MinSesL, sheAdslLineAlarmConfProfileAturThresh15MinUasL, sheAdslRfiBandIndex, sheAdslRfiBandName, sheAdslRfiBandStartTone, 
				sheAdslLineConfExtnProfilePSDMASKdsEnable, sheAdslLineDpboProfileIndex, sheAdslLineDpboProfileName, sheAdslLineDpboProfileEsel, sheAdslLineDpboProfileEselMin, 
				sheAdslLineDpboProfileMus, sheAdslLineDpboProfileMof, sheAdslLineDpboProfileFMin, sheAdslLineDpboProfileFMax, sheAdslLineDpboProfileEpsd, 
				sheAdslLineDpboProfileEScmA, sheAdslLineDpboProfileEScmB, sheAdslLineDpboProfileEScmC, sheAdslLineDpboProfile, sheAdslLineConfExtnProfileConfMinInpUs, 
				sheAdslAtucPhysCurrentBinStatus, sheAdslRfiBandStopTone, sheAdslAtucPhysActState, sheAdslLineConfExtnProfileRfiBandMask, sheAdslLineConfExtnProfileControlRequest, 
				sheAdslLineConfExtnProfileControlIndex, sheAdslLineConfExtnProfileControlStatus, sheAdslLineConfExtnProfileControlTimer, sheAdslLineConfExtnProfileControlReqResult, sheAdslLineConfExtnProfileControlTimeStamp, 
				sheAdslLineConfExtnProfileControlName, sheAdslLineConfExtnProfileControlParametricTestInputFile, sheAdslLineConfExtnProfileControlRsIntCorrectionUp, sheAdslLineConfExtnProfileControlLineType, sheAdslLineConfExtnProfileControlTxEndBin, 
				sheAdslLineConfExtnProfileControlTxStartBin, sheAdslLineConfExtnProfileControlMaxBitsPerBin, sheAdslLineConfExtnProfileControlRxStartBin, sheAdslLineConfExtnProfileControlRxEndBin, sheAdslLineConfExtnProfileControlRxBinAdjust, 
				sheAdslLineConfExtnProfileControlTriggerMode, sheAdslLineConfExtnProfileControlAdi2x, sheAdslLineConfExtnProfileControlStandard, sheAdslLineConfExtnProfileControlInitiate, sheAdslLineConfExtnProfileControlTxPowerAttenuation, 
				sheAdslLineConfExtnProfileControlCodingGain, sheAdslLineConfExtnProfileControlRsFastOvrhdDown, sheAdslLineConfExtnProfileControlIntCorrectionDown, sheAdslLineConfExtnProfileControlRsFastOvrhdUp, sheAdslLineConfExtnProfileControlDrStby, 
				sheAdslLineConfExtnProfileControlExpandedExchange, sheAdslLineConfExtnProfileControlEscapeFastRetrainEnable, sheAdslLineConfExtnProfileControlFastRetrainEnable, sheAdslLineConfExtnProfileControlBitSwap, sheAdslLineConfExtnProfileControlNtr, 
				sheAdslLineConfExtnProfileControlAnnexType, sheAdslLineConfExtnProfileControlAlctlUsVer, sheAdslLineConfExtnProfileControlUseCustomBin, sheAdslLineConfExtnProfileControlDnBinUsage, sheAdslLineConfExtnProfileControlMaxDCo, 
				sheAdslLineConfExtnProfileControlFullRetrain, sheAdslLineConfExtnProfileControlAdvertisedCapabilities, sheAdslLineConfExtnProfileControlPsdMaskType, sheAdslLineConfExtnProfileControlLineDmtConfMode, sheAdslLineConfExtnProfileControlEraseProfiles, 
				sheAdslLineConfExtnProfileControlParamHybridLossTestStart, sheAdslLineConfExtnProfileControlParamHybridLossTestEnd, sheAdslLineConfExtnProfileControlConfMinInp, sheAdslLineConfExtnProfileControlRfiBandMask, sheAdslLineConfExtnProfileControlUpstreamPsdMaskSelection, 
				sheAdslLineConfExtnProfileControlMaxNomPsdDs, sheAdslLineConfExtnProfileControlMaxNomAtpDs, sheAdslLineConfExtnProfileControlPsdMaskDs, sheAdslLineConfExtnProfileControlPSDMASKdsEnable, sheAdslLineConfExtnProfileControlPSDMASKdsRequestResult, 
				sheAdslLineConfExtnProfileControlConfMinInpUs, sheAdslLineUtopiaL2RxAddr, sheAdslLineUtopiaL2TxAddr, sheAdslLineClockType, sheAdslLineControlRequest, 
				sheAdslLineControlIndex, sheAdslLineControlStatus, sheAdslLineControlTimer, sheAdslLineControlReqResult, sheAdslLineControlTimeStamp, 
				sheAdslLineControlConfProfile, sheAdslLineControlAlarmConfProfile, sheAdslLineControlAction, sheAdslLineControlPwrMgmtPMSF, sheAdslLineControlDeltConfLDSF, 
				sheAdslLineControlRfiBandMask, sheAdslLineControlDpboProfile, sheAdslAtucPhysCurrentBinBitLoading, sheAdslAturPhysCurrentBinBitLoading, sheAdslAturPhysDeltSNRMTds, 
				sheAdslAtucPhysDeltSNRMTus, sheAdslAturPhysDeltDMTBinSNRds, sheAdslAtucPhysDeltDMTBinSNRus, sheAdslAtucPhysDeltSATNus, sheAdslAturPhysDeltSATNds, 
				sheAdslAturPhysDeltLastTxState, sheAdslAtucPhysDeltLastTxState }
			STATUS current
			DESCRIPTION 
				"Description."
			::= { sheAdslGroups 4 }

		
--   1.3.6.1.4.1.231.7.1.2.2.1.6.1.1.100.2.5
		sheAdslControlGroup OBJECT-GROUP
			OBJECTS { sheAdslLineConfProfileControlRequest, sheAdslLineConfProfileControlIndex, sheAdslLineConfProfileControlStatus, sheAdslLineConfProfileControlTimer, sheAdslLineConfProfileControlReqResult, 
				sheAdslLineConfProfileControlTimeStamp, sheAdslLineConfProfileControlName, sheAdslLineConfProfileControlAtucConfRateMode, sheAdslLineConfProfileControlAtucConfRateChanRatio, sheAdslLineConfProfileControlAtucConfTargetSnrMgn, 
				sheAdslLineConfProfileControlAtucConfMaxSnrMgn, sheAdslLineConfProfileControlAtucConfMinSnrMgn, sheAdslLineConfProfileControlAtucConfDownshiftSnrMgn, sheAdslLineConfProfileControlAtucConfUpshiftSnrMgn, sheAdslLineConfProfileControlAtucConfMinUpshiftTime, 
				sheAdslLineConfProfileControlAtucConfMinDownshiftTime, sheAdslLineConfProfileControlAtucChanConfFastMinTxRate, sheAdslLineConfProfileControlAtucChanConfInterleaveMinTxRate, sheAdslLineConfProfileControlAtucChanConfFastMaxTxRate, sheAdslLineConfProfileControlAtucChanConfInterleaveMaxTxRate, 
				sheAdslLineConfProfileControlAtucChanConfMaxInterleaveDelay, sheAdslLineConfProfileControlAturConfRateMode, sheAdslLineConfProfileControlAturConfRateChanRatio, sheAdslLineConfProfileControlAturConfTargetSnrMgn, sheAdslLineConfProfileControlAturConfMaxSnrMgn, 
				sheAdslLineConfProfileControlAturConfMinSnrMgn, sheAdslLineConfProfileControlAturConfDownshiftSnrMgn, sheAdslLineConfProfileControlAturConfUpshiftSnrMgn, sheAdslLineConfProfileControlAturConfMinUpshiftTime, sheAdslLineConfProfileControlAturConfMinDownshiftTime, 
				sheAdslLineConfProfileControlAturChanConfFastMinTxRate, sheAdslLineConfProfileControlAturChanConfInterleaveMinTxRate, sheAdslLineConfProfileControlAturChanConfFastMaxTxRate, sheAdslLineConfProfileControlAturChanConfInterleaveMaxTxRate, sheAdslLineConfProfileControlAturChanConfMaxInterleaveDelay, 
				sheAdslLineConfProfileControlTrellis, sheAdslLineConfProfileControlAtucConfPwrMgmtL0Time, sheAdslLineConfProfileControlAtucConfPwrMgmtL2Time, sheAdslLineConfProfileControlAtucConfPwrMgmtL2ATPR, sheAdslLineConfProfileControlAtucConfPwrMgmtL2Rate, 
				sheAdslLineConfProfileControlAtucConfPwrMgmtMode, sheAdslLineConfExtnProfileControlRequest, sheAdslLineConfExtnProfileControlIndex, sheAdslLineConfExtnProfileControlStatus, sheAdslLineConfExtnProfileControlTimer, 
				sheAdslLineConfExtnProfileControlReqResult, sheAdslLineConfExtnProfileControlTimeStamp, sheAdslLineConfExtnProfileControlName, sheAdslLineConfExtnProfileControlRsIntCorrectionUp, sheAdslLineConfExtnProfileControlLineType, 
				sheAdslLineConfExtnProfileControlTxEndBin, sheAdslLineConfExtnProfileControlTxStartBin, sheAdslLineConfExtnProfileControlRxStartBin, sheAdslLineConfExtnProfileControlRxEndBin, sheAdslLineConfExtnProfileControlStandard, 
				sheAdslLineConfExtnProfileControlTxPowerAttenuation, sheAdslLineConfExtnProfileControlIntCorrectionDown, sheAdslLineConfExtnProfileControlBitSwap, sheAdslLineConfExtnProfileControlNtr, sheAdslLineConfExtnProfileControlAnnexType, 
				sheAdslLineConfExtnProfileControlUseCustomBin, sheAdslLineConfExtnProfileControlDnBinUsage, sheAdslLineConfExtnProfileControlMaxDCo, sheAdslLineConfExtnProfileControlAdvertisedCapabilities, sheAdslLineConfExtnProfileControlPsdMaskType, 
				sheAdslLineConfExtnProfileControlLineDmtConfMode, sheAdslLineConfExtnProfileControlEraseProfiles, sheAdslLineConfExtnProfileControlParamHybridLossTestStart, sheAdslLineConfExtnProfileControlParamHybridLossTestEnd, sheAdslLineConfExtnProfileControlConfMinInp, 
				sheAdslLineConfExtnProfileControlUpstreamPsdMaskSelection, sheAdslLineConfExtnProfileControlMaxNomPsdDs, sheAdslLineConfExtnProfileControlMaxNomAtpDs, sheAdslLineConfExtnProfileControlPsdMaskDs, sheAdslLineControlRequest, 
				sheAdslLineControlIndex, sheAdslLineControlStatus, sheAdslLineControlTimer, sheAdslLineControlReqResult, sheAdslLineControlTimeStamp, 
				sheAdslLineControlConfProfile, sheAdslLineControlAlarmConfProfile, sheAdslLineControlAction, sheAdslLineControlPwrMgmtPMSF, sheAdslLineControlDeltConfLDSF, 
				sheAdslLineControlRfiBandMask, sheAdslLineAlarmConfProfileControlRequest, sheAdslLineAlarmConfProfileControlIndex, sheAdslLineAlarmConfProfileControlStatus, sheAdslLineAlarmConfProfileControlTimer, 
				sheAdslLineAlarmConfProfileControlReqResult, sheAdslLineAlarmConfProfileControlTimeStamp, sheAdslLineAlarmConfProfileControlName, sheAdslLineAlarmConfProfileControlOpStateTrapEnable, sheAdslLineAlarmConfProfileControlAtucThreshFastRateUp, 
				sheAdslLineAlarmConfProfileControlAtucThreshInterleaveRateUp, sheAdslLineAlarmConfProfileControlAtucThreshFastRateDown, sheAdslLineAlarmConfProfileControlAtucThreshInterleaveRateDown, sheAdslLineAlarmConfProfileControlAtucInitFailureTrapEnable, sheAdslLineAlarmConfProfileControlAtucThresh15MinLofs, 
				sheAdslLineAlarmConfProfileControlAtucThresh15MinLoss, sheAdslLineAlarmConfProfileControlAtucThresh15MinLols, sheAdslLineAlarmConfProfileControlAtucThresh15MinLprs, sheAdslLineAlarmConfProfileControlAtucThresh15MinESs, sheAdslLineAlarmConfProfileControlAtucThresh15MinFailFastR, 
				sheAdslLineAlarmConfProfileControlAturThreshFastRateUp, sheAdslLineAlarmConfProfileControlAturThreshInterleaveRateUp, sheAdslLineAlarmConfProfileControlAturThreshFastRateDown, sheAdslLineAlarmConfProfileControlAturThreshInterleaveRateDown, sheAdslLineAlarmConfProfileControlAturThresh15MinLofs, 
				sheAdslLineAlarmConfProfileControlAturThresh15MinLoss, sheAdslLineAlarmConfProfileControlAturThresh15MinLprs, sheAdslLineAlarmConfProfileControlAturThresh15MinESs, sheAdslRfiBandControlRequest, sheAdslRfiBandControlIndex, 
				sheAdslRfiBandControlStatus, sheAdslRfiBandControlTimer, sheAdslRfiBandControlReqResult, sheAdslRfiBandControlTimeStamp, sheAdslRfiBandControlName, 
				sheAdslRfiBandControlStartTone, sheAdslRfiBandControlStopTone, sheAdslAtucPsdRefMaskAdsl2AnnexA, sheAdslAtucPsdRefMaskAdsl2AnnexB, sheAdslAtucPsdRefMaskAdsl2plusAnnexA, 
				sheAdslAtucPsdRefMaskAdsl2plusAnnexB, sheAdslAtucPsdRefMaskAnnexL, sheAdslLineControlDpboProfile, sheAdslLineDpboProfileControlRequest, sheAdslLineDpboProfileControlIndex, 
				sheAdslLineDpboProfileControlStatus, sheAdslLineDpboProfileControlTimer, sheAdslLineDpboProfileControlReqResult, sheAdslLineDpboProfileControlTimeStamp, sheAdslLineDpboProfileControlName, 
				sheAdslLineDpboProfileControlEsel, sheAdslLineDpboProfileControlEselMin, sheAdslLineDpboProfileControlMus, sheAdslLineDpboProfileControlMof, sheAdslLineDpboProfileControlFMin, 
				sheAdslLineDpboProfileControlFMax, sheAdslLineDpboProfileControlEpsd, sheAdslLineDpboProfileControlEScmA, sheAdslLineDpboProfileControlEScmB, sheAdslLineDpboProfileControlEScmC, 
				sheAdslLineConfExtnProfileControlConfMinInpUs, sheAdslLineAlarmConfProfileControlAtucThresh15MinSesL, sheAdslLineAlarmConfProfileControlAtucThresh15MinUasL, sheAdslLineAlarmConfProfileControlAturThresh15MinSesL, sheAdslLineAlarmConfProfileControlAturThresh15MinUasL, 
				sheAdslLineConfExtnProfileControlPSDMASKdsRequestResult, sheAdslLineConfExtnProfileControlPSDMASKdsEnable }
			STATUS current
			DESCRIPTION 
				"Description."
			::= { sheAdslGroups 5 }

		
--   1.3.6.1.4.1.231.7.1.2.2.1.6.1.1.100.2.6
		sheAdslNotificationGroup NOTIFICATION-GROUP
			NOTIFICATIONS { sheAdslAtucPerfLofsThreshTrap, sheAdslAtucPerfLossThreshTrap, sheAdslAtucPerfLolsThreshTrap, sheAdslAtucPerfLprsThreshTrap, sheAdslAtucPerfESsThreshTrap, 
				sheAdslAtucRateChangeTrap, sheAdslAtucStatusTrap, sheAdslAtucFailedFastRThreshTrap, sheAdslLineStateTrap, sheAdslInitFailTrap, 
				sheAdslAturRateChangeTrap, sheAdslAturPerfLofsThreshTrap, sheAdslAturPerfLossThreshTrap, sheAdslAturPerfLprsThreshTrap, sheAdslAturPerfESsThreshTrap, 
				sheAdslAturStatusTrap, sheAdslLineConfProfileCreated, sheAdslLineConfProfileModified, sheAdslLineConfProfileDeleted, sheAdslLineConfExtnProfileModified, 
				sheAdslLineAlarmConfProfileCreated, sheAdslLineAlarmConfProfileModified, sheAdslLineAlarmConfProfileDeleted, sheAdslLineConfigurationModified, sheAdslLinePerfCounterCleared, 
				sheAdslLineConfProfileReqResult, sheAdslLineConfExtnProfileReqResult, sheAdslLineAlarmConfProfileReqResult, sheAdslLineAlarmLOS, sheAdslLineAlarmLOF, 
				sheAdslLineAlarmLOL, sheAdslLineAlarmLPR, sheAdslLineAlarmIMNR, sheAdslRfiBandCreated, sheAdslLineDpboProfileCreated, 
				sheAdslLineDpboProfileModified, sheAdslLineDpboProfileDeleted, sheAdslLineDpboProfileReqResult, sheAdslLineDpboProfileSetReqResult, sheAdslLineDpboProfileSetModified, 
				sheAdslRfiBandDeleted, sheAdslLineInpValueTruncatedInto2, sheAdslLineActStateTrap, sheAdslAtucPerfSesLThreshTrap, sheAdslAtucPerfUasLThreshTrap, 
				sheAdslAturPerfSesLThreshTrap, sheAdslAturPerfUasLThreshTrap }
			STATUS current
			DESCRIPTION 
				"Description."
			::= { sheAdslGroups 6 }

		
--   1.3.6.1.4.1.231.7.1.2.2.1.6.1.1.100.2.7
		sheAdslDualChanGroup OBJECT-GROUP
			OBJECTS { sheAdslAtucDualChanInterleaveDelay, sheAdslAtucDualChanCurrTxRate, sheAdslAtucDualChanPrevTxRate, sheAdslAtucDualChanCrcBlockLength, sheAdslAtucDualChanCurrAtmStatus, 
				sheAdslAtucDualChanRsSymbols, sheAdslAtucDualChanRsDepth, sheAdslAtucDualChanRsRedundancy, sheAdslAtucDualChanType, sheAdslAturDualChanInterleaveDelay, 
				sheAdslAturDualChanCurrTxRate, sheAdslAturDualChanPrevTxRate, sheAdslAturDualChanCrcBlockLength, sheAdslAturDualChanCurrAtmStatus, sheAdslAturDualChanRsSymbols, 
				sheAdslAturDualChanRsDepth, sheAdslAturDualChanRsRedundancy, sheAdslAturDualChanType, sheAdslAtucDualChanPerfDataTimeElapsed, sheAdslAtucDualChanPerfDataReceivedBlks, 
				sheAdslAtucDualChanPerfDataTransmittedBlks, sheAdslAtucDualChanPerfDataCorrectedBlks, sheAdslAtucDualChanPerfDataUncorrectBlks, sheAdslAtucDualChanPerfDataNcd, sheAdslAtucDualChanPerfDataOcd, 
				sheAdslAtucDualChanPerfDataHec, sheAdslAtucDualChanPerfDataValidIntervals, sheAdslAtucDualChanPerfDataInvalidIntervals, sheAdslAtucDualChanPerfDataCurr15MinTimeElapsed, sheAdslAtucDualChanPerfDataCurr15MinReceivedBlks, 
				sheAdslAtucDualChanPerfDataCurr15MinTransmittedBlks, sheAdslAtucDualChanPerfDataCurr15MinCorrectedBlks, sheAdslAtucDualChanPerfDataCurr15MinUncorrectBlks, sheAdslAtucDualChanPerfDataCurr15MinNcd, sheAdslAtucDualChanPerfDataCurr15MinOcd, 
				sheAdslAtucDualChanPerfDataCurr15MinHec, sheAdslAtucDualChanPerfDataCurr1DayTimeElapsed, sheAdslAtucDualChanPerfDataCurr1DayReceivedBlks, sheAdslAtucDualChanPerfDataCurr1DayTransmittedBlks, sheAdslAtucDualChanPerfDataCurr1DayCorrectedBlks, 
				sheAdslAtucDualChanPerfDataCurr1DayUncorrectBlks, sheAdslAtucDualChanPerfDataCurr1DayNcd, sheAdslAtucDualChanPerfDataCurr1DayOcd, sheAdslAtucDualChanPerfDataCurr1DayHec, sheAdslAtucDualChanPerfDataPrev1DayMoniSecs, 
				sheAdslAtucDualChanPerfDataPrev1DayReceivedBlks, sheAdslAtucDualChanPerfDataPrev1DayTransmittedBlks, sheAdslAtucDualChanPerfDataPrev1DayCorrectedBlks, sheAdslAtucDualChanPerfDataPrev1DayUncorrectBlks, sheAdslAtucDualChanPerfDataPrev1DayNcd, 
				sheAdslAtucDualChanPerfDataPrev1DayOcd, sheAdslAtucDualChanPerfDataPrev1DayHec, sheAdslAturDualChanPerfDataReceivedBlks, sheAdslAturDualChanPerfDataTransmittedBlks, sheAdslAturDualChanPerfDataCorrectedBlks, 
				sheAdslAturDualChanPerfDataUncorrectBlks, sheAdslAturDualChanPerfDataExtnNcd, sheAdslAturDualChanPerfDataExtnHec, sheAdslAturDualChanPerfDataPerfValidIntervals, sheAdslAturDualChanPerfDataPerfInvalidIntervals, 
				sheAdslAturDualChanPerfDataCurr15MinTimeElapsed, sheAdslAturDualChanPerfDataCurr15MinReceivedBlks, sheAdslAturDualChanPerfDataCurr15MinTransmittedBlks, sheAdslAturDualChanPerfDataCurr15MinCorrectedBlks, sheAdslAturDualChanPerfDataCurr15MinUncorrectBlks, 
				sheAdslAturDualChanPerfDataExtnCurr15MinNcd, sheAdslAturDualChanPerfDataExtnCurr15MinHec, sheAdslAturDualChanPerfDataCurr1DayTimeElapsed, sheAdslAturDualChanPerfDataCurr1DayReceivedBlks, sheAdslAturDualChanPerfDataCurr1DayTransmittedBlks, 
				sheAdslAturDualChanPerfDataCurr1DayCorrectedBlks, sheAdslAturDualChanPerfDataCurr1DayUncorrectBlks, sheAdslAturDualChanPerfDataExtnCurr1DayNcd, sheAdslAturDualChanPerfDataExtnCurr1DayHec, sheAdslAturDualChanPerfDataPrev1DayMoniSecs, 
				sheAdslAturDualChanPerfDataPrev1DayReceivedBlks, sheAdslAturDualChanPerfDataPrev1DayTransmittedBlks, sheAdslAturDualChanPerfDataPrev1DayCorrectedBlks, sheAdslAturDualChanPerfDataPrev1DayUncorrectBlks, sheAdslAturDualChanPerfDataExtnPrev1DayNcd, 
				sheAdslAturDualChanPerfDataExtnPrev1DayHec, sheAdslAtucDualChanIntervalNumber, sheAdslAtucDualChanIntervalValidData, sheAdslAtucDualChanIntervalEndTime, sheAdslAtucDualChanIntervalReceivedBlks, 
				sheAdslAtucDualChanIntervalTransmittedBlks, sheAdslAtucDualChanIntervalCorrectedBlks, sheAdslAtucDualChanIntervalUncorrectBlks, sheAdslAtucDualChanIntervalNcd, sheAdslAtucDualChanIntervalOcd, 
				sheAdslAtucDualChanIntervalHec, sheAdslAturDualChanIntervalNumber, sheAdslAturDualChanIntervalValidData, sheAdslAturDualChanIntervalEndTime, sheAdslAturDualChanIntervalReceivedBlks, 
				sheAdslAturDualChanIntervalTransmittedBlks, sheAdslAturDualChanIntervalCorrectedBlks, sheAdslAturDualChanIntervalUncorrectBlks, sheAdslAturDualChanIntervalNcd, sheAdslAturDualChanIntervalHec
				 }
			STATUS current
			DESCRIPTION 
				"Description."
			::= { sheAdslGroups 7 }

		
		sheAdslObsoleteGroup OBJECT-GROUP
			OBJECTS { sheDslSystemLineTxCfg, sheDslSystemLineCodingType, sheDslSystemDslType, sheDslSystemParamControlRequest, sheDslSystemParamControlStatus, 
				sheDslSystemParamControlTimer, sheDslSystemParamControlReqResult, sheDslSystemParamControlTimeStamp, sheDslSystemParamControlLineTxCfg, sheAdslCapabilityLineTxCap, 
				sheAdslLineConfExtnProfileControlParametricTestInputFile, sheAdslLineConfExtnProfileControlMaxBitsPerBin, sheAdslLineConfExtnProfileControlTriggerMode, sheAdslLineConfExtnProfileControlAdi2x, sheAdslLineConfExtnProfileControlCodingGain, 
				sheAdslLineConfExtnProfileControlDrStby, sheAdslLineConfExtnProfileControlEscapeFastRetrainEnable, sheAdslLineConfExtnProfileControlFastRetrainEnable, sheAdslLineConfExtnProfileControlAlctlUsVer, sheAdslLineConfExtnProfileControlFullRetrain, 
				sheAdslLineConfExtnProfileControlRfiBandMask, sheAdslLineUtopiaL2RxAddr, sheAdslLineUtopiaL2TxAddr, sheAdslLineConfExtnProfileControlRxBinAdjust, sheAdslLineConfExtnProfileRfiBandMask, 
				sheAdslLineClockType, sheAdslLineConfExtnProfileControlInitiate, sheAdslLineConfExtnProfileControlRsFastOvrhdDown, sheAdslLineConfExtnProfileControlRsFastOvrhdUp, sheAdslLineConfExtnProfileControlExpandedExchange
				 }
			STATUS current
			DESCRIPTION 
				"Description."
			::= { sheAdslGroups 9 }

		
--   1.3.6.1.4.1.231.7.1.2.2.1.6.1.1.100.2.6
		sheAdslObsoleteNotificationGroup NOTIFICATION-GROUP
			NOTIFICATIONS { sheAdslAtucPerfLpr, sheAdslAtucPerfLos, sheAdslAtucPerfLof, sheAdslAturPerfLos, sheAdslAturPerfLof, 
				sheAdslAtucPerfLol }
			STATUS current
			DESCRIPTION 
				"Description."
			::= { sheAdslGroups 10 }

		
	
	END

--
-- she-adsl-mib.mib
--
