--
-- SYMBOL-WS5000-MIB.mib
-- MIB generated by MG-SOFT Visual MIB Builder Version 5.0  Build 250
-- Friday, May 05, 2006 at 16:59:08
--

-- ***********************************************
-- ***
-- *** update this version tag on every edit !!!
-- ***
-- ***********************************************
-- 
-- MIB-file-version: v24b08
-- 

	SYMBOL-WS5000-MIB DEFINITIONS ::= BEGIN
 
		IMPORTS
			DisplayString			
				FROM RFC1213-MIB			
			OBJECT-GROUP, MODULE-COMPLIANCE, NOTIFICATION-GROUP			
				FROM SNMPv2-CONF			
			enterprises, TimeTicks, IpAddress, Integer32, Unsigned32, 
			Gauge32, Counter32, Counter64, OBJECT-TYPE, 
			MODULE-IDENTITY, OBJECT-IDENTITY, NOTIFICATION-TYPE			
				FROM SNMPv2-SMI			
			TEXTUAL-CONVENTION			
				FROM SNMPv2-TC;
	
	
		-- 1.3.6.1.4.1.388.6.6.1000.1
		ccModuleId MODULE-IDENTITY 
			LAST-UPDATED "200405031524Z"		-- May 03, 2004 at 15:24 GMT
			ORGANIZATION 
				"Organization."
			CONTACT-INFO 
				"Contact-info."
			DESCRIPTION 
				"Description."
			::= { ccV1dot2dot5Groups 1 }

		
	
--
-- Type definitions
--
	
		DoActionNow ::= INTEGER
			{
			doActionRightNow(1),
			idleState(2)
			}
-- This datatype always means that the MIB variable is
-- a TruthValue that when written to 'doActionRightNow', 
-- causes the described action to take place, (much like 
-- a button pressed in a UI).
-- 
-- Such a value does NOT remain in state 'doActionRightNow'
-- while the operation is in-process, but instead when read 
-- always returns 'idleState'.
-- 
		MultiPointer63 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63)
			}

-- In order to make the switch's implementation of some
-- dynamic tables simpler, tables using this datatype
-- use an abbreviated form of RowStatus.
-- 
-- Only CreateAndGo and Destroy states are supported.
-- 
-- On row creation, a single SET-PDU must contain all
-- the required values, including this value set to
-- createAndGo.  (This greatly simplifies row validation
-- for the switch).
-- 
-- Setting this value to Destroy causes the corresponding
-- row to be deleted.
-- 
		AbbrevRowStatus ::= INTEGER
			{
			createAndGo(4),
			destroy(6)
			}

		PartsPer10k ::= Unsigned32 (0..10000)
-- This datatype is used for all percentage values that have
-- interesting tenths and hundreths, (such as 1.37%).  SNMP
-- cannot report decimals, only whole numbers.  Values of 
-- this datatype are expressed not as parts-per-100, (percent),
-- but as parts-per-10000.
-- 
-- Said another way, values of this type are percent 
-- multiplied by 100.
-- 
-- For example, 1.37% would be reported as 137.
-- 
-- Values of this type are passwords.  They can be written,
-- but when read, they return a 0-length string.
-- 
-- Values of this type are passwords.  They can be written,
-- but when read, they return a 0-length string.
-- 
		Password ::= OCTET STRING

-- Values of this type are keys, expressed in hexadecimal as
-- a sequence of characters '0'..'9' plus 'A'..'F'.
-- 
-- Unless otherwise noted, the default value for variables of
-- this type is all-0s.
-- 
-- Values of this type are passwords.  They can be written,
-- but when read, they return a 0-length string.
-- 
		HexPassword ::= OCTET STRING

		RadioType ::= INTEGER
			{
			radio802dot11A(1),
			radio802dot11B(2),
			radio802dot11G(3),
			radio802dot11FH(4)
			}
-- In order to make the switch's implementation of 
-- numerous tables simpler, tables using this datatype
-- have a fixed number of entries with fixed indices.
-- In such tables, no entries may be added or deleted, 
-- but the pre-existing rows can be enabled or disabled 
-- using the value declared with this datatype.
-- 
-- In order to make the switch's implementation of 
-- numerous tables simpler, tables using this datatype
-- have a fixed number of entries with fixed indices.
-- In such tables, no entries may be added or deleted, 
-- but the pre-existing rows can be enabled or disabled 
-- using the value declared with this datatype.
-- 
		StaticRowEnable ::= INTEGER
			{
			enable(1),
			disable(2)
			}

		MultiPointer255 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63),
			referToEntry064(64),
			referToEntry065(65),
			referToEntry066(66),
			referToEntry067(67),
			referToEntry068(68),
			referToEntry069(69),
			referToEntry070(70),
			referToEntry071(71),
			referToEntry072(72),
			referToEntry073(73),
			referToEntry074(74),
			referToEntry075(75),
			referToEntry076(76),
			referToEntry077(77),
			referToEntry078(78),
			referToEntry079(79),
			referToEntry080(80),
			referToEntry081(81),
			referToEntry082(82),
			referToEntry083(83),
			referToEntry084(84),
			referToEntry085(85),
			referToEntry086(86),
			referToEntry087(87),
			referToEntry088(88),
			referToEntry089(89),
			referToEntry090(90),
			referToEntry091(91),
			referToEntry092(92),
			referToEntry093(93),
			referToEntry094(94),
			referToEntry095(95),
			referToEntry096(96),
			referToEntry097(97),
			referToEntry098(98),
			referToEntry099(99),
			referToEntry100(100),
			referToEntry101(101),
			referToEntry102(102),
			referToEntry103(103),
			referToEntry104(104),
			referToEntry105(105),
			referToEntry106(106),
			referToEntry107(107),
			referToEntry108(108),
			referToEntry109(109),
			referToEntry110(110),
			referToEntry111(111),
			referToEntry112(112),
			referToEntry113(113),
			referToEntry114(114),
			referToEntry115(115),
			referToEntry116(116),
			referToEntry117(117),
			referToEntry118(118),
			referToEntry119(119),
			referToEntry120(120),
			referToEntry121(121),
			referToEntry122(122),
			referToEntry123(123),
			referToEntry124(124),
			referToEntry125(125),
			referToEntry126(126),
			referToEntry127(127),
			referToEntry128(128),
			referToEntry129(129),
			referToEntry130(130),
			referToEntry131(131),
			referToEntry132(132),
			referToEntry133(133),
			referToEntry134(134),
			referToEntry135(135),
			referToEntry136(136),
			referToEntry137(137),
			referToEntry138(138),
			referToEntry139(139),
			referToEntry140(140),
			referToEntry141(141),
			referToEntry142(142),
			referToEntry143(143),
			referToEntry144(144),
			referToEntry145(145),
			referToEntry146(146),
			referToEntry147(147),
			referToEntry148(148),
			referToEntry149(149),
			referToEntry150(150),
			referToEntry151(151),
			referToEntry152(152),
			referToEntry153(153),
			referToEntry154(154),
			referToEntry155(155),
			referToEntry156(156),
			referToEntry157(157),
			referToEntry158(158),
			referToEntry159(159),
			referToEntry160(160),
			referToEntry161(161),
			referToEntry162(162),
			referToEntry163(163),
			referToEntry164(164),
			referToEntry165(165),
			referToEntry166(166),
			referToEntry167(167),
			referToEntry168(168),
			referToEntry169(169),
			referToEntry170(170),
			referToEntry171(171),
			referToEntry172(172),
			referToEntry173(173),
			referToEntry174(174),
			referToEntry175(175),
			referToEntry176(176),
			referToEntry177(177),
			referToEntry178(178),
			referToEntry179(179),
			referToEntry180(180),
			referToEntry181(181),
			referToEntry182(182),
			referToEntry183(183),
			referToEntry184(184),
			referToEntry185(185),
			referToEntry186(186),
			referToEntry187(187),
			referToEntry188(188),
			referToEntry189(189),
			referToEntry190(190),
			referToEntry191(191),
			referToEntry192(192),
			referToEntry193(193),
			referToEntry194(194),
			referToEntry195(195),
			referToEntry196(196),
			referToEntry197(197),
			referToEntry198(198),
			referToEntry199(199),
			referToEntry200(200),
			referToEntry201(201),
			referToEntry202(202),
			referToEntry203(203),
			referToEntry204(204),
			referToEntry205(205),
			referToEntry206(206),
			referToEntry207(207),
			referToEntry208(208),
			referToEntry209(209),
			referToEntry210(210),
			referToEntry211(211),
			referToEntry212(212),
			referToEntry213(213),
			referToEntry214(214),
			referToEntry215(215),
			referToEntry216(216),
			referToEntry217(217),
			referToEntry218(218),
			referToEntry219(219),
			referToEntry220(220),
			referToEntry221(221),
			referToEntry222(222),
			referToEntry223(223),
			referToEntry224(224),
			referToEntry225(225),
			referToEntry226(226),
			referToEntry227(227),
			referToEntry228(228),
			referToEntry229(229),
			referToEntry230(230),
			referToEntry231(231),
			referToEntry232(232),
			referToEntry233(233),
			referToEntry234(234),
			referToEntry235(235),
			referToEntry236(236),
			referToEntry237(237),
			referToEntry238(238),
			referToEntry239(239),
			referToEntry240(240),
			referToEntry241(241),
			referToEntry242(242),
			referToEntry243(243),
			referToEntry244(244),
			referToEntry245(245),
			referToEntry246(246),
			referToEntry247(247),
			referToEntry248(248),
			referToEntry249(249),
			referToEntry250(250),
			referToEntry251(251),
			referToEntry252(252),
			referToEntry253(253),
			referToEntry254(254),
			referToEntry255(255)
			}

		SinglePointer ::= INTEGER (0..255)

		TransmitRate ::= BITS
			{
			null(0),
			rate1Mb(1),
			rate2Mb(2),
			rate5pt5Mb(3),
			rate6Mb(4),
			rate9Mb(5),
			rate11Mb(6),
			rate12Mb(7),
			rate18Mb(8),
			rate22Mb(9),
			rate24Mb(10),
			rate36Mb(11),
			rate48Mb(12),
			rate54Mb(13)
			}

		DoActionShowProgress ::= INTEGER
			{
			doActionRightNow(1),
			idleState(2)
			}
-- This datatype always means that the MIB variable is
-- a simple ENUM that when written to 'doActionRightNow', 
-- causes the described action to take place, (much like 
-- a button pressed in a UI).
-- 
-- Such a value DOES remain in state 'doActionRightNow'
-- while the operation is in-process;  when the operation is
-- completed, it will then return the value 'idleState'.
-- 
		ScaleBy100 ::= Unsigned32

	
--
-- Textual conventions
--
	
		SnmpOpers ::= TEXTUAL-CONVENTION
			STATUS current
			DESCRIPTION 
				"		
				softkill(0),
				hardkill(1),
				restart(2),
				updatecfg(3)
				"
			SYNTAX INTEGER
				{
				softkill(0),
				hardkill(1),
				restart(2),
				updatecfg(3)
				}

		TruthValue ::= TEXTUAL-CONVENTION
			STATUS current
			DESCRIPTION 
				"Represents a boolean value."
			SYNTAX INTEGER
				{
				true(1),
				false(2)
				}

		FHAlgorithm ::= TEXTUAL-CONVENTION
			STATUS current
			DESCRIPTION 
				"IEEE(0),
				Hop Delta(1)"
			SYNTAX INTEGER
				{
				ieee(0),
				hopdelta(1)
				}

		SnmpAdminString ::= TEXTUAL-CONVENTION
			DISPLAY-HINT 
				"255a"
			STATUS current
			DESCRIPTION 
				"An octet string containing administrative
				information, preferably in human-readable form.
				
				To facilitate internationalization, this
				information is represented using the ISO/IEC
				IS 10646-1 character set, encoded as an octet
				string using the UTF-8 transformation format
				described in [RFC2279].
				
				Since additional code points are added by
				amendments to the 10646 standard from time
				to time, implementations must be prepared to
				encounter any code point from 0x00000000 to
				0x7fffffff.  Byte sequences that do not
				correspond to the valid UTF-8 encoding of a
				code point or are outside this range are
				prohibited.
				
				The use of control codes should be avoided.
				
				When it is necessary to represent a newline,
				the control code sequence CR LF should be used.
				
				The use of leading or trailing white space should
				be avoided.
				
				For code points not directly supported by user
				interface hardware or software, an alternative
				means of entry and display, such as hexadecimal,
				may be provided.
				
				For information encoded in 7-bit US-ASCII,
				the UTF-8 encoding is identical to the
				US-ASCII encoding.
				
				UTF-8 may require multiple bytes to represent a
				single character / code point; thus the length
				of this object in octets may be different from
				the number of characters encoded.  Similarly,
				size constraints refer to the number of encoded
				octets, not the number of characters represented
				by an encoding.
				
				Note that when this TC is used for an object that
				is used or envisioned to be used as an index, then
				a SIZE restriction MUST be specified so that the
				number of sub-identifiers for any object instance
				does not exceed the limit of 128, as defined by
				[RFC1905].
				
				Note that the size of an SnmpAdminString object is
				measured in octets, not characters.
				      "
			SYNTAX OCTET STRING (SIZE (0..255))

		APOnlineStatus ::= TEXTUAL-CONVENTION
			STATUS current
			DESCRIPTION 
				"		
				unavailable(0),
				active(1),
				inactive(2),
				alert(3),
				reset(4)
				"
			SYNTAX INTEGER
				{
				unavailable(0),
				active(1),
				inactive(2),
				alert(3),
				reset(4)
				}

		EncrType ::= TEXTUAL-CONVENTION
			STATUS current
			DESCRIPTION 
				"The list of availabe encryption types which could be 
				used for BroadCast/MultiCast/Unicast."
			SYNTAX INTEGER
				{
				unknown(0),
				open(1),
				wep40(2),
				wep104(4),
				keyguard(8),
				tkip(16),
				aesCcmp(32)
				}
-- Mower: to eliminate a compiler warning, rename 'aes-ccmp'
-- to 'aesCcmp'.
		MCValueOffset ::= TEXTUAL-CONVENTION
			STATUS current
			DESCRIPTION 
				"
				srcMacAddr(0),
				desMacAddr(1),
				etherType(2),
				vlanID(3),
				userPriority(4),
				protocol(5),
				tos(6),
				srcIPAddr(7),
				desIPAddr(8),
				srcPort(9),
				desPort(10),
				multicastMask(11)
				"
			SYNTAX INTEGER
				{
				srcMacAddr(0),
				desMacAddr(1),
				etherType(2),
				vlanID(3),
				userPriority(4),
				protocol(5),
				tos(6),
				srcIPAddr(7),
				desIPAddr(8),
				srcPort(9),
				desPort(10),
				multicastMask(11)
				}
-- Mower: to eliminate a compiler warning, rename 'no-offset'
-- to 'noOffset'.
		HsbState ::= TEXTUAL-CONVENTION
			STATUS current
			DESCRIPTION 
				"Represents a Standby State."
			SYNTAX INTEGER
				{
				startup(1),
				findStandby(2),
				waitingForConnectivity(3),
				connected(4),
				halted(5),
				monitoring(6),
				actingAsPrimary(7),
				tryingtoReconnect(8),
				reconnected(9),
				autoreverting(10)
				}

		MUDeviceType ::= TEXTUAL-CONVENTION
			STATUS current
			DESCRIPTION 
				"Indicates the device type of the Mobile Unit."
			SYNTAX INTEGER
				{
				data(0),
				voice(1),
				wirelessAP(2)
				}

		APStatus ::= TEXTUAL-CONVENTION
			STATUS current
			DESCRIPTION 
				"Indicates the association status of the AccessPort."
			SYNTAX INTEGER
				{
				away(0),
				associated(1)
				}

		MUSecurityStatus ::= TEXTUAL-CONVENTION
			STATUS current
			DESCRIPTION 
				"The security status for this MU."
			SYNTAX INTEGER
				{
				noEncryption(0),
				wepPerMUKey(1),
				wepSharedKey(2),
				tkipPerMUKey(3),
				tkipSharedKey(4)
				}

		CurrentRate ::= TEXTUAL-CONVENTION
			STATUS current
			DESCRIPTION 
				"Indicates the current communication rate on the MU."
			SYNTAX INTEGER
				{
				rt1Mbps(0),
				rt2Mbps(1),
				rt55Mbps(2),
				rt11Mbps(3)
				}

		SupportedRates ::= TEXTUAL-CONVENTION
			STATUS current
			DESCRIPTION 
				"Indicates the current supported rates."
			SYNTAX INTEGER
				{
				none(0),
				rt1Mbps(1),
				rt2Mbps(2),
				rt1and2Mbps(3),
				rt55Mbps(4),
				rt1and55Mbps(5),
				rt2and55Mbps(6),
				rt1and2and55Mbps(7),
				rt11Mbps(8),
				rt1and11Mbps(9),
				rt2and11Mbps(10),
				rt1and2and11Mbps(11),
				rt55and11Mbps(12),
				rt1and55and11Mbps(13),
				rt2and55and11Mbps(14),
				rt1and2and55and11Mbps(15)
				}
-- Mower: to eliminate a compiler warning, change '-' to 'and'
-- in each of the following:
--   rt1-2Mbps
--   rt1-55Mbps
--   rt2-55Mbps
--   rt1-2-55Mbps
--   rt1-11Mbps
--   rt2-11Mbps
--   rt1-2-11Mbps
--   rt55-11Mbps
--   rt1-55-11Mbps
--   rt2-55-11Mbps
--   rt1-2-55-11Mbps
-- 
-- (Also, this should have been a BITS definition).
		PSPowerMode ::= TEXTUAL-CONVENTION
			STATUS current
			DESCRIPTION 
				"Indicates the current power mode setting on this MU."
			SYNTAX INTEGER
				{
				cam(0),
				psp(1)
				}

		AuthState ::= TEXTUAL-CONVENTION
			STATUS current
			DESCRIPTION 
				"Used to inform whether the MU is authenticated or not."
			SYNTAX INTEGER
				{
				notauthenticated(0),
				authenticated(1)
				}

		AuthMethod ::= TEXTUAL-CONVENTION
			STATUS current
			DESCRIPTION 
				"The authentication method being used by the MU."
			SYNTAX INTEGER
				{
				unknown(0),
				open(1),
				preshared(2),
				eap8021x(4),
				kerberos(8)
				}

		StorageType ::= TEXTUAL-CONVENTION
			STATUS current
			DESCRIPTION 
				"Describes the memory realization of a conceptual row.  A
				row which is volatile(2) is lost upon reboot.  A row which
				is either nonVolatile(3), permanent(4) or readOnly(5), is
				backed up by stable storage.  A row which is permanent(4)
				can be changed but not deleted.  A row which is readOnly(5)
				cannot be changed nor deleted.
				
				If the value of an object with this syntax is either
				permanent(4) or readOnly(5), it cannot be modified.
				Conversely, if the value is either other(1), volatile(2) or
				nonVolatile(3), it cannot be modified to be permanent(4) or
				readOnly(5).
				
				Every usage of this textual convention is required to
				specify the columnar objects which a permanent(4) row must
				at a minimum allow to be writable."
			SYNTAX INTEGER
				{
				other(1),
				volatile(2),
				nonVolatile(3),
				permanent(4),
				readOnly(5)
				}

		RowStatus ::= TEXTUAL-CONVENTION
			STATUS current
			DESCRIPTION 
				"The RowStatus textual convention is used to manage the
				creation and deletion of conceptual rows, and is used as the
				value of the SYNTAX clause for the status column of a
				conceptual row (as described in Section 7.7.1 of [2].)
				
				The status column has six defined values:
				
				     - `active', which indicates that the conceptual row is
				     available for use by the managed device;
				
				     - `notInService', which indicates that the conceptual
				     row exists in the agent, but is unavailable for use by
				     the managed device (see NOTE below);
				
				     - `notReady', which indicates that the conceptual row
				     exists in the agent, but is missing information
				     necessary in order to be available for use by the
				     managed device;
				
				     - `createAndGo', which is supplied by a management
				     station wishing to create a new instance of a
				     conceptual row and to have its status automatically set
				     to active, making it available for use by the managed
				     device;
				
				     - `createAndWait', which is supplied by a management
				     station wishing to create a new instance of a
				     conceptual row (but not make it available for use by
				     the managed device); and,
				
				     - `destroy', which is supplied by a management station
				     wishing to delete all of the instances associated with
				     an existing conceptual row.
				
				Whereas five of the six values (all except `notReady') may
				be specified in a management protocol set operation, only
				three values will be returned in response to a management
				protocol retrieval operation:  `notReady', `notInService' or
				`active'.  That is, when queried, an existing conceptual row
				has only three states:  it is either available for use by
				the managed device (the status column has value `active');
				it is not available for use by the managed device, though
				the agent has sufficient information to make it so (the
				status column has value `notInService'); or, it is not
				available for use by the managed device, and an attempt to
				make it so would fail because the agent has insufficient
				information (the state column has value `notReady').
				
				                         NOTE WELL
				
				     This textual convention may be used for a MIB table,
				     irrespective of whether the values of that table's
				     conceptual rows are able to be modified while it is
				     active, or whether its conceptual rows must be taken
				     out of service in order to be modified.  That is, it is
				     the responsibility of the DESCRIPTION clause of the
				     status column to specify whether the status column must
				     not be `active' in order for the value of some other
				     column of the same conceptual row to be modified.  If
				     such a specification is made, affected columns may be
				     changed by an SNMP set PDU if the RowStatus would not
				     be equal to `active' either immediately before or after
				     processing the PDU.  In other words, if the PDU also
				     contained a varbind that would change the RowStatus
				     value, the column in question may be changed if the
				     RowStatus was not equal to `active' as the PDU was
				     received, or if the varbind sets the status to a value
				     other than 'active'.
				
				
				Also note that whenever any elements of a row exist, the
				RowStatus column must also exist.
				
				To summarize the effect of having a conceptual row with a
				status column having a SYNTAX clause value of RowStatus,
				consider the following state diagram:
				
				
				                                           STATE
				                +--------------+-----------+-------------+-------------
				                |      A       |     B     |      C      |      D
				                |              |status col.|status column|
				                |status column |    is     |      is     |status column
				      ACTION    |does not exist|  notReady | notInService|  is active
				  --------------+--------------+-----------+-------------+-------------
				  set status    |noError    ->D|inconsist- |inconsistent-|inconsistent-
				  column to     |       or     |   entValue|        Value|        Value
				  createAndGo   |inconsistent- |           |             |
				                |         Value|           |             |
				  --------------+--------------+-----------+-------------+-------------
				  set status    |noError  see 1|inconsist- |inconsistent-|inconsistent-
				  column to     |       or     |   entValue|        Value|        Value
				  createAndWait |wrongValue    |           |             |
				  --------------+--------------+-----------+-------------+-------------
				  set status    |inconsistent- |inconsist- |noError      |noError
				  column to     |         Value|   entValue|             |
				  active        |              |           |             |
				                |              |     or    |             |
				                |              |           |             |
				                |              |see 2   ->D|          ->D|          ->D
				  --------------+--------------+-----------+-------------+-------------
				  set status    |inconsistent- |inconsist- |noError      |noError   ->C
				  column to     |         Value|   entValue|             |
				  notInService  |              |           |             |
				                |              |     or    |             |      or
				                |              |           |             |
				                |              |see 3   ->C|          ->C|wrongValue
				  --------------+--------------+-----------+-------------+-------------
				  set status    |noError       |noError    |noError      |noError
				  column to     |              |           |             |
				  destroy       |           ->A|        ->A|          ->A|          ->A
				  --------------+--------------+-----------+-------------+-------------
				  set any other |see 4         |noError    |noError      |see 5
				  column to some|              |           |             |
				  value         |              |      see 1|          ->C|          ->D
				  --------------+--------------+-----------+-------------+-------------
				  
				(1) goto B or C, depending on information available to the
				agent.
				
				(2) if other variable bindings included in the same PDU,
				provide values for all columns which are missing but
				required, then return noError and goto D.
				
				(3) if other variable bindings included in the same PDU,
				provide values for all columns which are missing but
				required, then return noError and goto C.
				
				(4) at the discretion of the agent, the return value may be
				either:
				
				     inconsistentName:  because the agent does not choose to
				     create such an instance when the corresponding
				     RowStatus instance does not exist, or
				
				     inconsistentValue:  if the supplied value is
				     inconsistent with the state of some other MIB object's
				     value, or
				
				     noError: because the agent chooses to create the
				     instance.
				
				If noError is returned, then the instance of the status
				column must also be created, and the new state is B or C,
				depending on the information available to the agent.  If
				inconsistentName or inconsistentValue is returned, the row
				remains in state A.
				
				(5) depending on the MIB definition for the column/table,
				either noError or inconsistentValue may be returned.
				
				NOTE: Other processing of the set request may result in a
				response other than noError being returned, e.g.,
				wrongValue, noCreation, etc.
				
				
				                  Conceptual Row Creation
				
				There are four potential interactions when creating a
				conceptual row:  selecting an instance-identifier which is
				not in use; creating the conceptual row; initializing any
				objects for which the agent does not supply a default; and,
				making the conceptual row available for use by the managed
				device.
				
				Interaction 1: Selecting an Instance-Identifier
				
				The algorithm used to select an instance-identifier varies
				for each conceptual row.  In some cases, the instance-
				identifier is semantically significant, e.g., the
				destination address of a route, and a management station
				selects the instance-identifier according to the semantics.
				
				In other cases, the instance-identifier is used solely to
				distinguish conceptual rows, and a management station
				without specific knowledge of the conceptual row might
				examine the instances present in order to determine an
				unused instance-identifier.  (This approach may be used, but
				it is often highly sub-optimal; however, it is also a
				questionable practice for a naive management station to
				attempt conceptual row creation.)
				
				Alternately, the MIB module which defines the conceptual row
				might provide one or more objects which provide assistance
				in determining an unused instance-identifier.  For example,
				if the conceptual row is indexed by an integer-value, then
				an object having an integer-valued SYNTAX clause might be
				defined for such a purpose, allowing a management station to
				issue a management protocol retrieval operation.  In order
				to avoid unnecessary collisions between competing management
				stations, `adjacent' retrievals of this object should be
				different.
				
				Finally, the management station could select a pseudo-random
				number to use as the index.  In the event that this index
				was already in use and an inconsistentValue was returned in
				response to the management protocol set operation, the
				management station should simply select a new pseudo-random
				number and retry the operation.
				
				A MIB designer should choose between the two latter
				algorithms based on the size of the table (and therefore the
				efficiency of each algorithm).  For tables in which a large
				number of entries are expected, it is recommended that a MIB
				object be defined that returns an acceptable index for
				creation.  For tables with small numbers of entries, it is
				recommended that the latter pseudo-random index mechanism be
				used.
				
				
				Interaction 2: Creating the Conceptual Row
				
				Once an unused instance-identifier has been selected, the
				management station determines if it wishes to create and
				activate the conceptual row in one transaction or in a
				negotiated set of interactions.
				
				Interaction 2a: Creating and Activating the Conceptual Row
				
				The management station must first determine the column
				requirements, i.e., it must determine those columns for
				which it must or must not provide values.  Depending on the
				complexity of the table and the management station's
				knowledge of the agent's capabilities, this determination
				can be made locally by the management station.  Alternately,
				the management station issues a management protocol get
				operation to examine all columns in the conceptual row that
				it wishes to create.  In response, for each column, there
				are three possible outcomes:
				
				     - a value is returned, indicating that some other
				     management station has already created this conceptual
				     row.  We return to interaction 1.
				
				     - the exception `noSuchInstance' is returned,
				     indicating that the agent implements the object-type
				     associated with this column, and that this column in at
				     least one conceptual row would be accessible in the MIB
				     view used by the retrieval were it to exist. For those
				     columns to which the agent provides read-create access,
				     the `noSuchInstance' exception tells the management
				     station that it should supply a value for this column
				     when the conceptual row is to be created.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				Once the column requirements have been determined, a
				management protocol set operation is accordingly issued.
				This operation also sets the new instance of the status
				column to `createAndGo'.
				
				When the agent processes the set operation, it verifies that
				it has sufficient information to make the conceptual row
				available for use by the managed device.  The information
				available to the agent is provided by two sources:  the
				management protocol set operation which creates the
				conceptual row, and, implementation-specific defaults
				supplied by the agent (note that an agent must provide
				implementation-specific defaults for at least those objects
				which it implements as read-only).  If there is sufficient
				information available, then the conceptual row is created, a
				`noError' response is returned, the status column is set to
				`active', and no further interactions are necessary (i.e.,
				interactions 3 and 4 are skipped).  If there is insufficient
				information, then the conceptual row is not created, and the
				set operation fails with an error of `inconsistentValue'.
				On this error, the management station can issue a management
				protocol retrieval operation to determine if this was
				because it failed to specify a value for a required column,
				or, because the selected instance of the status column
				already existed.  In the latter case, we return to
				interaction 1.  In the former case, the management station
				can re-issue the set operation with the additional
				information, or begin interaction 2 again using
				`createAndWait' in order to negotiate creation of the
				conceptual row.
				
				                         NOTE WELL
				
				     Regardless of the method used to determine the column
				     requirements, it is possible that the management
				     station might deem a column necessary when, in fact,
				     the agent will not allow that particular columnar
				     instance to be created or written.  In this case, the
				     management protocol set operation will fail with an
				     error such as `noCreation' or `notWritable'.  In this
				     case, the management station decides whether it needs
				     to be able to set a value for that particular columnar
				     instance.  If not, the management station re-issues the
				     management protocol set operation, but without setting
				     a value for that particular columnar instance;
				     otherwise, the management station aborts the row
				     creation algorithm.
				
				Interaction 2b: Negotiating the Creation of the Conceptual
				Row
				
				The management station issues a management protocol set
				operation which sets the desired instance of the status
				column to `createAndWait'.  If the agent is unwilling to
				process a request of this sort, the set operation fails with
				an error of `wrongValue'.  (As a consequence, such an agent
				must be prepared to accept a single management protocol set
				operation, i.e., interaction 2a above, containing all of the
				columns indicated by its column requirements.)  Otherwise,
				the conceptual row is created, a `noError' response is
				returned, and the status column is immediately set to either
				`notInService' or `notReady', depending on whether it has
				sufficient information to make the conceptual row available
				for use by the managed device.  If there is sufficient
				information available, then the status column is set to
				`notInService'; otherwise, if there is insufficient
				information, then the status column is set to `notReady'.
				Regardless, we proceed to interaction 3.
				
				Interaction 3: Initializing non-defaulted Objects
				
				The management station must now determine the column
				requirements.  It issues a management protocol get operation
				to examine all columns in the created conceptual row.  In
				the response, for each column, there are three possible
				outcomes:
				
				     - a value is returned, indicating that the agent
				     implements the object-type associated with this column
				     and had sufficient information to provide a value.  For
				     those columns to which the agent provides read-create
				     access (and for which the agent allows their values to
				     be changed after their creation), a value return tells
				     the management station that it may issue additional
				     management protocol set operations, if it desires, in
				     order to change the value associated with this column.
				
				     - the exception `noSuchInstance' is returned,
				     indicating that the agent implements the object-type
				     associated with this column, and that this column in at
				     least one conceptual row would be accessible in the MIB
				     view used by the retrieval were it to exist. However,
				     the agent does not have sufficient information to
				     provide a value, and until a value is provided, the
				     conceptual row may not be made available for use by the
				     managed device.  For those columns to which the agent
				     provides read-create access, the `noSuchInstance'
				     exception tells the management station that it must
				     issue additional management protocol set operations, in
				     order to provide a value associated with this column.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				If the value associated with the status column is
				`notReady', then the management station must first deal with
				all `noSuchInstance' columns, if any.  Having done so, the
				value of the status column becomes `notInService', and we
				proceed to interaction 4.
				
				Interaction 4: Making the Conceptual Row Available
				
				Once the management station is satisfied with the values
				associated with the columns of the conceptual row, it issues
				a management protocol set operation to set the status column
				to `active'.  If the agent has sufficient information to
				make the conceptual row available for use by the managed
				device, the management protocol set operation succeeds (a
				`noError' response is returned).  Otherwise, the management
				protocol set operation fails with an error of
				`inconsistentValue'.
				
				
				                         NOTE WELL
				
				     A conceptual row having a status column with value
				     `notInService' or `notReady' is unavailable to the
				     managed device.  As such, it is possible for the
				     managed device to create its own instances during the
				     time between the management protocol set operation
				     which sets the status column to `createAndWait' and the
				     management protocol set operation which sets the status
				     column to `active'.  In this case, when the management
				     protocol set operation is issued to set the status
				     column to `active', the values held in the agent
				     supersede those used by the managed device.
				
				If the management station is prevented from setting the
				status column to `active' (e.g., due to management station
				or network failure) the conceptual row will be left in the
				`notInService' or `notReady' state, consuming resources
				indefinitely.  The agent must detect conceptual rows that
				have been in either state for an abnormally long period of
				time and remove them.  It is the responsibility of the
				DESCRIPTION clause of the status column to indicate what an
				abnormally long period of time would be.  This period of
				time should be long enough to allow for human response time
				(including `think time') between the creation of the
				conceptual row and the setting of the status to `active'.
				In the absense of such information in the DESCRIPTION
				clause, it is suggested that this period be approximately 5
				minutes in length.  This removal action applies not only to
				newly-created rows, but also to previously active rows which
				are set to, and left in, the notInService state for a
				prolonged period exceeding that which is considered normal
				for such a conceptual row.
				
				
				                 Conceptual Row Suspension
				
				When a conceptual row is `active', the management station
				may issue a management protocol set operation which sets the
				instance of the status column to `notInService'.  If the
				agent is unwilling to do so, the set operation fails with an
				error of `wrongValue'.  Otherwise, the conceptual row is
				taken out of service, and a `noError' response is returned.
				It is the responsibility of the DESCRIPTION clause of the
				status column to indicate under what circumstances the
				status column should be taken out of service (e.g., in order
				for the value of some other column of the same conceptual
				row to be modified).
				
				
				                  Conceptual Row Deletion
				
				For deletion of conceptual rows, a management protocol set
				operation is issued which sets the instance of the status
				column to `destroy'.  This request may be made regardless of
				the current value of the status column (e.g., it is possible
				to delete conceptual rows which are either `notReady',
				`notInService' or `active'.)  If the operation succeeds,
				then all instances associated with the conceptual row are
				immediately removed."
			SYNTAX INTEGER
				{
				active(1),
				notInService(2),
				notReady(3),
				createAndGo(4),
				createAndWait(5),
				destroy(6)
				}

		TargetOptions ::= TEXTUAL-CONVENTION
			STATUS current
			DESCRIPTION 
				"		
				com2sec(0),
				trap2sink(1),
				trapsink(2),
				com2secAndtrap2sink(3),
				all(4)
				"
			SYNTAX INTEGER (0..4)

	
--
-- Node definitions
--
	
		-- 1.3.6.1.4.1.388
		symbol OBJECT IDENTIFIER ::= { enterprises 388 }

		
		-- 1.3.6.1.4.1.388.6
		symbolCC OBJECT IDENTIFIER ::= { symbol 6 }

		
		-- 1.3.6.1.4.1.388.6.0
		ws5000 OBJECT-IDENTITY
			STATUS current
			DESCRIPTION 
				"sysOID value for Wireless Switch 5000;  (not the
				family of 5000s, but the actual older 5000 hardware
				with 128Mb DRAM, 128Mb DOM, 100Mb Ethernet ports).
				
				This sysOID value is also reported for Mantis
				devices."
			::= { symbolCC 0 }
-- Mower: added this with v1.3.  This OID was the value that
-- had been used for WS5000 since the start of the project,
-- but it had never been defined in the MIB.
		
		-- 1.3.6.1.4.1.388.6.0.1
		ws5100 OBJECT-IDENTITY
			STATUS current
			DESCRIPTION 
				"sysOID value for Wireless Switch 5100;  (the new
				hardware first shipping around 7/2004, first supported
				via software v1.3;  upgraded to 256Mb DRAM, 256Mb DOM,
				1000Mb Ethernet ports)."
			::= { ws5000 1 }
-- Mower: added this with v1.3.  This OID is new as of 1.3,
-- for the new 5100 hardware.  It's location as a child of
-- 'ws5000' is awkward, but that seems the most logical place
-- to locate it.
		
		-- 1.3.6.1.4.1.388.6.1
		symbolCCSystem OBJECT IDENTIFIER ::= { symbolCC 1 }

		
		-- 1.3.6.1.4.1.388.6.1.1
		ccSysCfg OBJECT IDENTIFIER ::= { symbolCCSystem 1 }

		
		-- 1.3.6.1.4.1.388.6.1.1.1
		ccModuleName OBJECT-TYPE
			SYNTAX DisplayString (SIZE (1..50))
			MAX-ACCESS read-write
			STATUS current
			DESCRIPTION
				"The name of the Wireless Switch.
				Changing the switch name will require the KDC configuration 
				to be recreated if it is currently configured.
				       Note that the following characters cannot be part of the name string - 
				        . , ' , \ , &, # and double quotes "
			::= { ccSysCfg 1 }

		
		-- 1.3.6.1.4.1.388.6.1.1.2
		ccModuleDesc OBJECT-TYPE
			SYNTAX DisplayString (SIZE (0..255))
			MAX-ACCESS read-write
			STATUS current
			DESCRIPTION
				"A description of the Wireless Switch module.
				
				Ex. <Butterfly@Symbol Technologies>"
			::= { ccSysCfg 2 }

		
		-- 1.3.6.1.4.1.388.6.1.1.3
		ccManufacture OBJECT-TYPE
			SYNTAX DisplayString (SIZE (0..255))
			MAX-ACCESS read-only
			STATUS current
			DESCRIPTION
				"The manufacturer of the Wireless Switch."
			::= { ccSysCfg 3 }

		
		-- 1.3.6.1.4.1.388.6.1.1.4
		ccCopyright OBJECT-TYPE
			SYNTAX DisplayString (SIZE (0..255))
			MAX-ACCESS read-only
			STATUS current
			DESCRIPTION
				"The Copyright information about the Wireless Switch."
			::= { ccSysCfg 4 }

		
		-- 1.3.6.1.4.1.388.6.1.1.5
		ccModuleVer OBJECT-TYPE
			SYNTAX DisplayString (SIZE (0..32))
			MAX-ACCESS read-only
			STATUS current
			DESCRIPTION
				"The software version for this model."
			::= { ccSysCfg 5 }

		
		-- 1.3.6.1.4.1.388.6.1.1.6
		ccMaxNumAP OBJECT-TYPE
			SYNTAX INTEGER (0..300)
			MAX-ACCESS read-only
			STATUS current
			DESCRIPTION
				"The maximum number of Access Ports supported by the Wireless Switch."
			::= { ccSysCfg 6 }

		
		-- 1.3.6.1.4.1.388.6.1.1.7
		ccMaxNumMu OBJECT-TYPE
			SYNTAX INTEGER (0..1000)
			MAX-ACCESS read-only
			STATUS current
			DESCRIPTION
				"The maxium number of Mobile Unit supported by the Wireless Switch."
			::= { ccSysCfg 7 }

		
		-- 1.3.6.1.4.1.388.6.1.1.8
		ccActivePolicy OBJECT-TYPE
			SYNTAX DisplayString (SIZE (0..32))
			MAX-ACCESS read-write
			STATUS current
			DESCRIPTION
				"The current Wireless Switch policy for this model."
			::= { ccSysCfg 8 }

		
		-- 1.3.6.1.4.1.388.6.1.1.9
		ccTaf OBJECT-TYPE
			SYNTAX DisplayString (SIZE (0..128))
			MAX-ACCESS read-write
			STATUS current
			DESCRIPTION
				"The object is for running TAF executable.
				Ex. 
				1. 'addgw $1 $2'
				addgw: Add a new gateway into the system routing table.
					$1: new gateway IP
				                $2: IP family
				
					More usage: <addgw/remgw/printgw> <gateway> <ip family>
				
				2. '<telneton/telnetoff / ftpon/ftpoff / sslon/ssloff / 				snmpon/snmpoff'
				
				Turn on/off TELNET, FTP, SSL and SNMP.
				
				3. '<adddns/remdns/printdns> <DNS ip address>'
				
				4. 'state <filename>'
				
				Note:To add gateway to the local network give the value
				of <ip family> as <0.0.0.0>. To add gateway to local
				network first disable dhcp on both NIC."
			::= { ccSysCfg 9 }

		
		-- 1.3.6.1.4.1.388.6.1.1.10
		ccSnmpOpers OBJECT-TYPE
			SYNTAX SnmpOpers
			MAX-ACCESS read-write
			STATUS current
			DESCRIPTION
				"This object should be one of the following value:
				
				0 - Soft Kill		== Save the current changes in the agent and terminate the agent.
				1 - Hard Kill      == Just terminate the agent without any saving.
				2 - Restart Snmpd  == Restart the agent with hardly killing the old one.
				3 - Update Config  == Update the configuration files for the Agent.
				"
			::= { ccSysCfg 10 }

		
		-- 1.3.6.1.4.1.388.6.1.1.11
		ccUptime OBJECT-TYPE
			SYNTAX DisplayString (SIZE (1..20))
			MAX-ACCESS read-only
			STATUS current
			DESCRIPTION
				"The time since when the Wireless Switch has been up."
			::= { ccSysCfg 11 }

		
		-- 1.3.6.1.4.1.388.6.1.1.12
		ccFTP OBJECT-TYPE
			SYNTAX TruthValue
			MAX-ACCESS read-only
			STATUS current
			DESCRIPTION
				"The status of FTP in the Wireless Switch.
				True implies that FTP is on."
			::= { ccSysCfg 12 }

		
		-- 1.3.6.1.4.1.388.6.1.1.13
		ccTelnet OBJECT-TYPE
			SYNTAX TruthValue
			MAX-ACCESS read-only
			STATUS current
			DESCRIPTION
				"The status of Telnet in the Wireless Switch.
				True implies that Telnet is on."
			::= { ccSysCfg 13 }

		
		-- 1.3.6.1.4.1.388.6.1.1.14
		ccWeb OBJECT-TYPE
			SYNTAX DisplayString (SIZE (4..10))
			MAX-ACCESS read-only
			STATUS current
			DESCRIPTION
				"Returns 'http' or 'https' depending on 
				whether SSL is being used by the web server or not."
			::= { ccSysCfg 14 }

		
		-- 1.3.6.1.4.1.388.6.1.1.15
		ccSNMPFlag OBJECT-TYPE
			SYNTAX TruthValue
			MAX-ACCESS read-write
			STATUS current
			DESCRIPTION
				"A 'true' as input forces the Wireless Switch to re-read the SNMP Trap configuration.
				'false' is not an acceptable input.
				This object is SET-only."
			::= { ccSysCfg 15 }

		
		-- 1.3.6.1.4.1.388.6.1.1.16
		ccTime OBJECT-TYPE
			SYNTAX DisplayString (SIZE (21..30))
			MAX-ACCESS read-write
			STATUS current
			DESCRIPTION
				"Set CC time and timezone. Here's the format:
				'yyyy/mm/dd hh:mm:dd timezone daylight',
				where, yyyy = 4 digit of year
				mm = 2 digit of month [1-12]
				dd = 2 digit of date [1-31]		 
				hh = 2 digit of hour [0-23]
				mm = 2 digit of minute [0-59]
				ss = 2 digit of second [0-59].
				daylight saving settings=  
						   0 -> Disabled
				                       1 -> USA
				                       2 -> Australia
				                       3 -> Eastern Europe
				                       4 -> Central Europe
				                       5 -> Western Europe 
				
				timezone = Valid range is -12:00 to +13:00 [+/-](HH:MM)
				GMT offset, DST style and cities are defined below : 
				
				(GMT offset)(daylight saving) (zones)
				(GMT -12:00)	0		Eniwetok, Kwajalein
				(GMT -11:00)	0		Midway Island, Samoa
				(GMT -10:00)	0		Hawaii
				(GMT -09:00)	0,1		Alaska
				(GMT -08:00)	0,1		Pacific Time (US & Canada); Tijuana
				(GMT -07:00)	0,1		Arizona, Mountain Time (US & Canada)
				(GMT -06:00)	0,1		Central America, Central Time (US & Canada), Mexico City, Saskatchewan
				(GMT -05:00)	0,1		Bogota, Lima, Quito, Eastern Time (US & Canada), Indiana (East)
				(GMT -04:00)	0,1		Atlantic Time (Canada), Caracas, La Paz, Santiago
				(GMT -03:30)	0,1		Newfoundland
				(GMT -03:00)	0,3,4,5	Brasilia, Buenos Aires, Georgetown, Greenland
				(GMT -02:00)	0,4		Mid-Atlantic
				(GMT -01:00)	0,3,4,5	Azores, Cape Verde Is
				(GMT  00:00)	0,3,4,5	Casablanca, Monrovia, Greenwich Mean Time : Dublin, Edinburgh, Lisbon, London
				(GMT +01:00)	0,3,4,5	Amsterdam, Berlin, Bern, Rome, Stockholm, Vienna, Belgrade, Bratislava, Budapest, Ljubljana, Prague, Brussels, Copenhagen, Madrid, Paris, Sarajevo, Skopje, Sofija, Vilnius, Warsaw, Zagreb, West Central Africa
				(GMT +02:00)	0,3,4,5	Athens, Istanbul, Minsk, Bucharest, Cairo, Harare, Pretoria, Helsinki, Riga, Tallinn, Jerusalem
				(GMT +03:00)	0,4,5	Baghdad, Kuwait, Riyadh, Moscow, St. Petersburg, Volgograd, Nairobi
				(GMT +03:30)	0		Tehran
				(GMT +04:00)	0,3,4,5	Abu Dhabi, Muscat, Baku, Tbilisi, Yerevan
				(GMT +04:30)	0		Kabul
				(GMT +05:00)	0,5		Ekaterinburg, Islamabad, Karachi, Tashkent
				(GMT +05:30)	0		Calcutta, Chennai, Mumbai, New Delhi
				(GMT +05:45)	0		Kathmandu
				(GMT +06:00)	0,4,5	Almaty, Novosibirsk, Astana, Dhaka, Sri Jayawardenepura
				(GMT +06:30)	0		Rangoon
				(GMT +07:00)	0,4,5	Bangkok, Hanoi, Jakarta, Krasnoyarsk
				(GMT +08:00)	0,2,5	Beijing, Chongqing, Hong Kong, Urumqi, Irkutsk, Ulaan Bataar, Kuala Lumpur, Singapore, Perth, Taipei
				(GMT +09:00)	0,5		Osaka, Sapporo, Tokyo, Seoul, Yakutsk
				(GMT +09:30)	0,2		Adelaide, Darwin
				(GMT +10:00)	0,2,5	Brisbane, Canberra, Melbourne, Sydney, Guam, Port Moresby, Hobart, Vladivostok
				(GMT +11:00)	0,4		Magadan, Solomon Is., New Caledonia
				(GMT +12:00)	0,2		Auckland, Wellington, Fiji, Kamchatka, Marshall Is.
				(GMT +13:00)	0		Nuku'alofa"
			::= { ccSysCfg 16 }

		
		-- 1.3.6.1.4.1.388.6.1.1.17
		ccSNMPKdc OBJECT-TYPE
			SYNTAX TruthValue
			MAX-ACCESS read-write
			STATUS current
			DESCRIPTION
				"Regardless of the input value, always to disable Snmp KDC feature.
				After disabling the KDC feature, there is no data returned from the
				OID tree <ccOnBoardKerberos>.
				The agent will return an error message:
					No value(s) returned for query.
				"
			::= { ccSysCfg 17 }

		
		-- 1.3.6.1.4.1.388.6.1.1.18
		ccCliKdc OBJECT-TYPE
			SYNTAX TruthValue
			MAX-ACCESS read-write
			STATUS current
			DESCRIPTION
				"Regardless of the input value, always to disable CLI Kdc feature.
				"
			::= { ccSysCfg 18 }

		
		-- 1.3.6.1.4.1.388.6.1.1.19
		ccPolicyAddObj OBJECT-TYPE
			SYNTAX DisplayString (SIZE (1..50))
			MAX-ACCESS read-write
			STATUS current
			DESCRIPTION
				"Add one Wireless Switch Policy for this Wireless Switch object. The maximum number of 
				characters allowed is 50, and the following characters cannot be part of the input 
				string - ',.,\,&, # and double quotes."
			::= { ccSysCfg 19 }

		
		-- 1.3.6.1.4.1.388.6.1.1.20
		ccPolicyRemObj OBJECT-TYPE
			SYNTAX DisplayString (SIZE (1..50))
			MAX-ACCESS read-write
			STATUS current
			DESCRIPTION
				"Remove one Wireless Switch Policy for this Wireless Switch object.
				The maximum number of characters allowed is 50, and the following 
				characters cannot be part of the input string - ',.,\,&, # and double quotes.
				Note: You can only remove an UNACTIVE switch policy.
				      Trying to remove a ACTIVE Switch Policy will get an eror like:
					  SNMP Commit fail.
				"
			::= { ccSysCfg 20 }

		
		-- 1.3.6.1.4.1.388.6.1.1.23
		ccLicenseCount OBJECT-TYPE
			SYNTAX Integer32
			MAX-ACCESS read-only
			STATUS current
			DESCRIPTION
				"The number of licenses issued to the WS-5000 Wireless Switch. (the number of AP that 
				the switch can adopt at the current state)
				
				Note: The number of AP that the system can adopt depends on the state of the 
				Switch.
				 
				When it is a StandBy and disabled, it will return 0. If it is StandBy and enabled, 
				it will either return 0 (if not connected to a Primary), or the number of AP of its Primary.
				
				"
			::= { ccSysCfg 23 }

		
		-- 1.3.6.1.4.1.388.6.1.1.24
		ccEmergencyPolicy OBJECT-TYPE
			SYNTAX DisplayString (SIZE (0..200))
			MAX-ACCESS read-write
			STATUS current
			DESCRIPTION
				"The policy which will become the emergency active policy for the switch. 
				In order to undefine an emergency policy, leave the input blank while SETting this variable."
			::= { ccSysCfg 24 }

		
		-- 1.3.6.1.4.1.388.6.1.1.25
		ccEmergencyMode OBJECT-TYPE
			SYNTAX TruthValue
			MAX-ACCESS read-write
			STATUS current
			DESCRIPTION
				" 'true' activates the emergency mode. Which means that the switch
				will immediately start working under the emergency policy if 'true' is sent.
				'false' will deactivate the emergency mode."
			::= { ccSysCfg 25 }

		
		-- 1.3.6.1.4.1.388.6.1.1.26
		ccRunACS OBJECT-TYPE
			SYNTAX TruthValue
			MAX-ACCESS read-write
			STATUS current
			DESCRIPTION
				"Setting it to 'true' will run Automatic Channel Selection.
				'false' is not an acceptable input. 
				This object is SET-only."
			::= { ccSysCfg 26 }

		
		-- 1.3.6.1.4.1.388.6.1.1.27
		ccEnableSNMPTrap OBJECT-TYPE
			SYNTAX TruthValue
			MAX-ACCESS read-write
			STATUS current
			DESCRIPTION
				" Enable/Disable the trap functionality in the switch.
				'true' enables it, 'false' disables it"
			::= { ccSysCfg 27 }

		
		-- 1.3.6.1.4.1.388.6.1.1.28
		ccEnableWVPNSupport OBJECT-TYPE
			SYNTAX OCTET STRING
			MAX-ACCESS read-write
			STATUS current
			DESCRIPTION
				"Enable(1)/Disable(2) WVPN Support.
				 This will reboot the switch and subsequent
				 reboots will have WVPN enabled at startup.
				 Enable(1)/Disable(2) WVPN Support.
				  syntax <1>  
				         or
				         <1> , <license file name>
				         or
				         <2>
				 Note: If no license file name is given then it takes up 
				       the default file name <license.lk>.
				       In case of failure error code returned is:
				 Error: 99.
				       While enabling vpnsupport the system does not 
				       have a minimum 256MB Ram, need minimum 256MB ram
				       to enable vpn support.
				 Error: 98
				       While enabling vpnsupport the given License file 
				       is invalid use the system interface mac address to 
				       get the correct serial number and Obtain a license for 
				       that serial number.              
				 Error: 97
				       When user tries to disable vpnsuport and 
				       dhcp server is enabled.
								
				 
				"
			::= { ccSysCfg 28 }

		
		-- 1.3.6.1.4.1.388.6.1.1.29
		ccEnableRap OBJECT-TYPE
			SYNTAX TruthValue
			MAX-ACCESS read-write
			STATUS current
			DESCRIPTION
				"Enable the Rogue AP feature on the switch. 
				To begin RogueAP detection, ccDetectorAP has to be
				enabled for an active AP."
			::= { ccSysCfg 29 }

		
		-- 1.3.6.1.4.1.388.6.1.1.30
		ccAPTxPPS OBJECT-TYPE
			SYNTAX INTEGER (0..100000)
			MAX-ACCESS read-only
			STATUS current
			DESCRIPTION
				"Display packets transmitted per sec by all APs adapted to WS.
				"
			::= { ccSysCfg 30 }

		
		-- 1.3.6.1.4.1.388.6.1.1.31
		ccAPRxPPS OBJECT-TYPE
			SYNTAX INTEGER (0..100000)
			MAX-ACCESS read-only
			STATUS current
			DESCRIPTION
				"Display packets received per sec by all APs adopted
				 to WS"
			::= { ccSysCfg 31 }

		
		-- 1.3.6.1.4.1.388.6.1.1.32
		ccAvgTxRetry OBJECT-TYPE
			SYNTAX INTEGER (0..100000)
			MAX-ACCESS read-only
			STATUS current
			DESCRIPTION
				"Display transmit retry packets by all AP's adopted to WS"
			::= { ccSysCfg 32 }

		
		-- 1.3.6.1.4.1.388.6.1.1.33
		ccAvgRSSI OBJECT-TYPE
			SYNTAX INTEGER (0..100000)
			MAX-ACCESS read-only
			STATUS current
			DESCRIPTION
				"Display avg Receive Signal Strength Indicator(RSSI) 
				for the WS. "
			::= { ccSysCfg 33 }

		
		-- 1.3.6.1.4.1.388.6.1.1.34
		ccAvgSNR OBJECT-TYPE
			SYNTAX INTEGER (0..100000)
			MAX-ACCESS read-only
			STATUS current
			DESCRIPTION
				"Display average Signal to Noise Ratio (SNR) for WS. "
			::= { ccSysCfg 34 }

		
		-- 1.3.6.1.4.1.388.6.1.1.49
		ccConfigChangeLast OBJECT-TYPE
			SYNTAX DisplayString
			MAX-ACCESS read-only
			STATUS current
			DESCRIPTION
				"Description.
				 Last Configuration Changed."
			::= { ccSysCfg 49 }

		
		-- 1.3.6.1.4.1.388.6.1.1.60
		ccNTP OBJECT IDENTIFIER ::= { ccSysCfg 60 }

		
		-- 1.3.6.1.4.1.388.6.1.1.60.1
		ccNtpPrefTimeServer OBJECT-TYPE
			SYNTAX IpAddress
			MAX-ACCESS read-write
			STATUS current
			DESCRIPTION
				"The IP Address for the preferred time server."
			::= { ccNTP 1 }

		
		-- 1.3.6.1.4.1.388.6.1.1.60.2
		ccNtpFirstAltTimeServer OBJECT-TYPE
			SYNTAX IpAddress
			MAX-ACCESS read-write
			STATUS current
			DESCRIPTION
				"The IP Address for the first alternative time server.
				Note: 
				  If the other two Time Servers (prefer time server
				and the second time server) are invalid time
				server IP Addresses, this one should be a 
				valid time server IP address."
			::= { ccNTP 2 }

		
		-- 1.3.6.1.4.1.388.6.1.1.60.3
		ccNtpSecondAltTimeServer OBJECT-TYPE
			SYNTAX IpAddress
			MAX-ACCESS read-write
			STATUS current
			DESCRIPTION
				"The IP Address for the second alternative time server.
				Note: 
				  If the other two Time Servers (prefer time server
				and the first time server) are invalid time
				server IP Addresses, this one should be a valid time 
				server IP address."
			::= { ccNTP 3 }

		
		-- 1.3.6.1.4.1.388.6.1.1.60.4
		ccNtpGroupSetTimeServer OBJECT-TYPE
			SYNTAX DisplayString
			MAX-ACCESS read-write
			STATUS current
			DESCRIPTION
				"Instead of setting each object one by one, this entry can
				be used to set all the time servers at the same time. 
				Input string format:
					<timesrv_1,timesrv_2,timesrv3>
				Ex. 
					timesrv_1: 156.234.82.99
					timesrv_2: 144.22.121.1
					timesrv_3: 221.32.11.33
				So, input string becomes <156.234.82.99,144.22.121.1,221.32.11.33>
				Note:
				    Out of the three IP Addresses, at least one of them must be 
				    a valid NTP server IP address. Otherwise, this SET doesn't work.
					
					Since this operation takes longer time than others, so
					please check the TIMEOUT setting in the manager program and make sure 
					that the value should be at least 5 minutes."
			::= { ccNTP 4 }

		
		-- 1.3.6.1.4.1.388.6.1.1.60.5
		ccNtpDelAll OBJECT-TYPE
			SYNTAX TruthValue
			MAX-ACCESS read-write
			STATUS current
			DESCRIPTION
				"Delete all NTP servers."
			::= { ccNTP 5 }

		
--  1.3.6.1.4.1.388.6.1.2
		-- 1.3.6.1.4.1.388.6.1.2
		ccPolicyTable OBJECT-TYPE
			SYNTAX SEQUENCE OF CcPolicyEntry
			MAX-ACCESS not-accessible
			STATUS current
			DESCRIPTION
				"Wireless Switch  Policy Table."
			::= { symbolCCSystem 2 }

		
--  1.3.6.1.4.1.388.6.1.2.1
		-- 1.3.6.1.4.1.388.6.1.2.1
		ccPolicyEntry OBJECT-TYPE
			SYNTAX CcPolicyEntry
			MAX-ACCESS not-accessible
			STATUS current
			DESCRIPTION
				"The entries of information about the Wireless Switch Policies."
			INDEX { ccPolicyIndex }
			::= { ccPolicyTable 1 }

		
		CcPolicyEntry ::=
			SEQUENCE { 
				ccPolicyIndex
					INTEGER,
				ccPolicyName
					DisplayString,
				ccPolicyDesc
					DisplayString,
				ccPolicyCountry
					DisplayString,
				ccPolicyDefAdoptAPPolicy
					DisplayString,
				ccPolicyAPPolicyCount
					INTEGER,
				ccPolicyAPNameOfPolicy
					DisplayString,
				ccPolicyAddAPPolicy
					DisplayString,
				ccPolicyRmvAPPolicy
					DisplayString,
				ccPolicyExcludeInfo
					DisplayString,
				ccPolicyExcludeEdit
					DisplayString,
				ccPolicyExcludeRmv
					DisplayString,
				ccPolicyIncludeInfo
					DisplayString,
				ccPolicyIncludeEdit
					DisplayString,
				ccPolicyIncludeRmv
					DisplayString,
				ccPolicyEtherPolicy
					DisplayString,
				ccPolicyTrap
					TruthValue,
				ccPolicyDefChannel
					INTEGER,
				ccPolicyDefPower
					INTEGER,
				ccPolicyChannel11a
					DisplayString,
				ccPolicyPower11a
					DisplayString,
				ccPolicyChannel11b
					DisplayString,
				ccPolicyPower11b
					DisplayString,
				ccPolicyDSCoExistence
					TruthValue,
				ccPolicyDefAdoptAPPolicy11a
					DisplayString,
				ccPolicyDefAdoptAPPolicy11b
					DisplayString,
				ccPolicyDefAdoptAPPolicyFH
					DisplayString,
				ccPolicyDefAdoptAPPolicy11g
					DisplayString,
				ccPolicyChannel11g
					DisplayString,
				ccPolicyPower11g
					DisplayString
			 }

--  1.3.6.1.4.1.388.6.1.2.1.1
		-- 1.3.6.1.4.1.388.6.1.2.1.1
		ccPolicyIndex OBJECT-TYPE
			SYNTAX INTEGER (1..100)
			MAX-ACCESS not-accessible
			STATUS current
			DESCRIPTION
				"The index of the policy."
			::= { ccPolicyEntry 1 }

		
--  Mower: changed range from 0.. to 1..
-- 1.3.6.1.4.1.388.6.1.2.1.2
		-- 1.3.6.1.4.1.388.6.1.2.1.2
		ccPolicyName OBJECT-TYPE
			SYNTAX DisplayString (SIZE (1..50))
			MAX-ACCESS read-write
			STATUS current
			DESCRIPTION
				"The name of the policy. The Maximum length of the Policy Name 
				can be 50 characters, Note that the following characters cannot be part 
				of Policy Name field, double quotes,',.,\,& and #."
			::= { ccPolicyEntry 2 }

		
--  1.3.6.1.4.1.388.6.1.2.1.3
		-- 1.3.6.1.4.1.388.6.1.2.1.3
		ccPolicyDesc OBJECT-TYPE
			SYNTAX DisplayString (SIZE (0..128))
			MAX-ACCESS read-write
			STATUS current
			DESCRIPTION
				"The description of the policy. The Maximum length of the description 
				can be 128 characters, please note that the following characters cannot 
				be part of description double quotes,' and #."
			::= { ccPolicyEntry 3 }

		
--  1.3.6.1.4.1.388.6.1.2.1.4
		-- 1.3.6.1.4.1.388.6.1.2.1.4
		ccPolicyCountry OBJECT-TYPE
			SYNTAX DisplayString (SIZE (0..2))
			MAX-ACCESS read-write
			STATUS current
			DESCRIPTION
				"The Country Code chosed by this policy."
			::= { ccPolicyEntry 4 }

		
--  (In 1.2.5, changed from 1..20 to 1..2).
-- 1.3.6.1.4.1.388.6.1.2.1.5
		-- 1.3.6.1.4.1.388.6.1.2.1.5
		ccPolicyDefAdoptAPPolicy OBJECT-TYPE
			SYNTAX DisplayString (SIZE (1..32))
			MAX-ACCESS read-write
			STATUS deprecated
			DESCRIPTION
				"The default AP policy for any adopted Access Port."
			::= { ccPolicyEntry 5 }

		
--  1.3.6.1.4.1.388.6.1.2.1.6
		-- 1.3.6.1.4.1.388.6.1.2.1.6
		ccPolicyAPPolicyCount OBJECT-TYPE
			SYNTAX INTEGER (0..100)
			MAX-ACCESS read-only
			STATUS current
			DESCRIPTION
				"The number of Access Port policies used by the Wireless Switch policy."
			::= { ccPolicyEntry 6 }

		
--  Mower: renamed from ccAPPolicyCount to eliminate the only 
-- inconsistant name in this table.
-- 1.3.6.1.4.1.388.6.1.2.1.7
		-- 1.3.6.1.4.1.388.6.1.2.1.7
		ccPolicyAPNameOfPolicy OBJECT-TYPE
			SYNTAX DisplayString (SIZE (1..32))
			MAX-ACCESS read-only
			STATUS current
			DESCRIPTION
				"A list of AP policies applied for this ccPolicy."
			::= { ccPolicyEntry 7 }

		
--  Mower: renamed from ccAPPolicyName to solve a 
-- name-collision in this new [merged/single] MIB.
-- 1.3.6.1.4.1.388.6.1.2.1.8
		-- 1.3.6.1.4.1.388.6.1.2.1.8
		ccPolicyAddAPPolicy OBJECT-TYPE
			SYNTAX DisplayString (SIZE (1..50))
			MAX-ACCESS read-write
			STATUS current
			DESCRIPTION
				"Add an AP policy to the Wireless Switch Policy. The maximum number of 
				characters allowed is 50, and the following characters cannot be
				part of the input string - ',.,\,&, # and double quotes.
				This OID is write-only."
			::= { ccPolicyEntry 8 }

		
--  1.3.6.1.4.1.388.6.1.2.1.9
		-- 1.3.6.1.4.1.388.6.1.2.1.9
		ccPolicyRmvAPPolicy OBJECT-TYPE
			SYNTAX DisplayString (SIZE (1..50))
			MAX-ACCESS read-write
			STATUS current
			DESCRIPTION
				"Remove an AP policy from the Wireless Switch Policy. The maximum number of 
				characters allowed is 50, and the following characters cannot be
				part of the input string - ',.,\,&, # and double quotes.
				This OID is write-only."
			::= { ccPolicyEntry 9 }

		
--  1.3.6.1.4.1.388.6.1.2.1.10
		-- 1.3.6.1.4.1.388.6.1.2.1.10
		ccPolicyExcludeInfo OBJECT-TYPE
			SYNTAX DisplayString (SIZE (0..512))
			MAX-ACCESS read-write
			STATUS current
			DESCRIPTION
				"Add new entries to be excluded from adoption by the WS5000 Wireless Switch, 
				and view the current exclusion list.
				This table includs MAC-Start and MAC-End address,and the radio type.
				The returned string has the format:
				<Start Mac - End Mac,RadioType>
				And the input string has to be in the same format.
				If there is no End-Mac(i.e. only one MAC address 
				needs to be excluded), just specify the Start Mac,
				so that	the format looks like:
				<Start Mac,RadioType>.
				RadioType should be one of 'A', 'B', 'G' or 'FH'.
				The maximum number of total entries in the list cannot 
				be greater than 200."
			::= { ccPolicyEntry 10 }

		
--  1.3.6.1.4.1.388.6.1.2.1.11
		-- 1.3.6.1.4.1.388.6.1.2.1.11
		ccPolicyExcludeEdit OBJECT-TYPE
			SYNTAX DisplayString (SIZE (0..512))
			MAX-ACCESS read-write
			STATUS current
			DESCRIPTION
				" Edit the existing Exclude Table.
				Note: the input string format must be in the following format:
				1. <OldMacStartAddr,OldRadioType,NewMacStartAddr,NewRadioType>
				2. <OldMacStartAddr,OldRadioType,NewMacStartAddr-NewMacEndAddr,NewRadioType>.
				RadioType should be one of 'A', 'B', 'G' or 'FH'.
				The maximum number of total entries in the list cannot 
				be greater than 200.
				This OID is write-only."
			::= { ccPolicyEntry 11 }

		
--  1.3.6.1.4.1.388.6.1.2.1.12
		-- 1.3.6.1.4.1.388.6.1.2.1.12
		ccPolicyExcludeRmv OBJECT-TYPE
			SYNTAX DisplayString (SIZE (0..512))
			MAX-ACCESS read-write
			STATUS current
			DESCRIPTION
				" Remove an existing entry from the Exclude Table in the Adoption List.
				Note: the input string must be in the format:
				<Start-MAC, RadioType>,
				              where Start-MAC is the
				starting MAC address of a particular entry.
				RadioType should be one of 'A', 'B', 'G' or 'FH'.
				This OID is write-only."
			::= { ccPolicyEntry 12 }

		
--  1.3.6.1.4.1.388.6.1.2.1.13
		-- 1.3.6.1.4.1.388.6.1.2.1.13
		ccPolicyIncludeInfo OBJECT-TYPE
			SYNTAX DisplayString (SIZE (0..512))
			MAX-ACCESS read-write
			STATUS current
			DESCRIPTION
				"Add new entries to be included for adoption by the WS5000 Wireless Switch.
				This table includes MAC-Start and MAC-End address,the radio type, and the APPolicy
				with which the radio will be adopted, upon inclusion.
				The returned string has the format:
				<Start Mac - End Mac,RadioType,APPolicy>
				And the input string has to be in the same format.
				If there is no End-Mac(i.e. only one MAC address 
				needs to be included), just specify the start MAC:
				<Start Mac,RadioType,APPolicy>.
				RadioType should be one of 'A', 'B', 'G' or 'FH'.
				The maximum number of total entries in the list cannot 
				be greater than 200."
			::= { ccPolicyEntry 13 }

		
--  1.3.6.1.4.1.388.6.1.2.1.14
		-- 1.3.6.1.4.1.388.6.1.2.1.14
		ccPolicyIncludeEdit OBJECT-TYPE
			SYNTAX DisplayString (SIZE (0..225))
			MAX-ACCESS read-write
			STATUS current
			DESCRIPTION
				"Edit an existing entry in the Include list for adoption.
				The entered string should have either of the following format:
				1. <OldMacStartAddr,OldRadioType,NewMacStartAddr,NewRadioType,NewAPPolicyName>
				2. <OldMacStartAddr,OldRadioType,NewMacStartAddr-NewMacEndAddr,NewRadioType,NewAPPolicyName>
				RadioType should be one of 'A', 'B', 'G' or 'FH'.
				The maximum number of total entries in the list cannot 
				be greater than 200.
				This OID is write-only."
			::= { ccPolicyEntry 14 }

		
--  1.3.6.1.4.1.388.6.1.2.1.15
		-- 1.3.6.1.4.1.388.6.1.2.1.15
		ccPolicyIncludeRmv OBJECT-TYPE
			SYNTAX DisplayString (SIZE (0..80))
			MAX-ACCESS read-write
			STATUS current
			DESCRIPTION
				" Remove an existing entry from the Include Table in the Adoption List.
				Note: the input string must be in the format:
				<Start MAC, RadioType>, 
				              where Start-MAC is the
				starting MAC address of a particular entry.
				RadioType should be one of 'A', 'B', 'G' or 'FH'.
				This OID is write-only."
			::= { ccPolicyEntry 15 }

		
--  1.3.6.1.4.1.388.6.1.2.1.16
		-- 1.3.6.1.4.1.388.6.1.2.1.16
		ccPolicyEtherPolicy OBJECT-TYPE
			SYNTAX DisplayString (SIZE (1..32))
			MAX-ACCESS read-write
			STATUS current
			DESCRIPTION
				"The current active Ethernet policy for the Ethernet Port."
			::= { ccPolicyEntry 16 }

		
--  1.3.6.1.4.1.388.6.1.2.1.17
		-- 1.3.6.1.4.1.388.6.1.2.1.17
		ccPolicyTrap OBJECT-TYPE
			SYNTAX TruthValue
			MAX-ACCESS read-write
			STATUS current
			DESCRIPTION
				"The true(1) indicates: send a SNMP trap when deny an AP adoption.
				
				The false(2) indicates: not send a SNMP trap when deny an AP adoption"
			::= { ccPolicyEntry 17 }

		
--  1.3.6.1.4.1.388.6.1.2.1.18
		-- 1.3.6.1.4.1.388.6.1.2.1.18
		ccPolicyDefChannel OBJECT-TYPE
			SYNTAX INTEGER (1..14)
			MAX-ACCESS read-write
			STATUS deprecated
			DESCRIPTION
				"The default Channel to be used."
			::= { ccPolicyEntry 18 }

		
--  1.3.6.1.4.1.388.6.1.2.1.19
		-- 1.3.6.1.4.1.388.6.1.2.1.19
		ccPolicyDefPower OBJECT-TYPE
			SYNTAX INTEGER (1..100)
			MAX-ACCESS read-write
			STATUS deprecated
			DESCRIPTION
				"The default power to be used (in mW).
				Valid values are :1,5,10,15,100."
			::= { ccPolicyEntry 19 }

		
--  1.3.6.1.4.1.388.6.1.2.1.20
		-- 1.3.6.1.4.1.388.6.1.2.1.20
		ccPolicyChannel11a OBJECT-TYPE
			SYNTAX DisplayString (SIZE (1..200))
			MAX-ACCESS read-write
			STATUS current
			DESCRIPTION
				"The Channel to be used for 11a radios.
				Valid values for this channel are:
				36, 40, 44, 48, 52, 56, 60, 64, 149, 153, 157, 161
				You can also input 'auto-always' for allowing the switch to choose
				channels automatically. 'auto-once' can be input if 
				you want the switch to choose a channel automatically, only once.
				Enter 'random' to select a random channel."
			::= { ccPolicyEntry 20 }

		
--  1.3.6.1.4.1.388.6.1.2.1.21
		-- 1.3.6.1.4.1.388.6.1.2.1.21
		ccPolicyPower11a OBJECT-TYPE
			SYNTAX DisplayString (SIZE (1..20))
			MAX-ACCESS read-write
			STATUS current
			DESCRIPTION
				"The power to be used (in dbM).
				Valid values are :4-20"
			::= { ccPolicyEntry 21 }

		
--  1.3.6.1.4.1.388.6.1.2.1.22
		-- 1.3.6.1.4.1.388.6.1.2.1.22
		ccPolicyChannel11b OBJECT-TYPE
			SYNTAX DisplayString (SIZE (1..200))
			MAX-ACCESS read-write
			STATUS current
			DESCRIPTION
				"The Channel to be used for 11b radios.
				Valid values range from 1,2,3... through 14.
				You can also input 'auto-always' for allowing the switch to choose
				channels automatically. 'auto-once' can be input if 
				you want the switch to choose a channel automatically, only once.
				Enter 'random' to select a random channel."
			::= { ccPolicyEntry 22 }

		
--  1.3.6.1.4.1.388.6.1.2.1.23
		-- 1.3.6.1.4.1.388.6.1.2.1.23
		ccPolicyPower11b OBJECT-TYPE
			SYNTAX DisplayString (SIZE (1..20))
			MAX-ACCESS read-write
			STATUS current
			DESCRIPTION
				"The power to be used (in dBm).
				Valid values are :4-20"
			::= { ccPolicyEntry 23 }

		
--  1.3.6.1.4.1.388.6.1.2.1.24
		-- 1.3.6.1.4.1.388.6.1.2.1.24
		ccPolicyDSCoExistence OBJECT-TYPE
			SYNTAX TruthValue
			MAX-ACCESS read-write
			STATUS current
			DESCRIPTION
				"Enable(true)/disable(false) FH and DS coexistence. 
				Set for country code US,Israel,Mexico,Sri Lanka,Japan returns an error and Get returns -1."
			::= { ccPolicyEntry 24 }

		
--  1.3.6.1.4.1.388.6.1.2.1.25
		-- 1.3.6.1.4.1.388.6.1.2.1.25
		ccPolicyDefAdoptAPPolicy11a OBJECT-TYPE
			SYNTAX DisplayString (SIZE (0..200))
			MAX-ACCESS read-write
			STATUS current
			DESCRIPTION
				"The default AP policy to be used for adopted 11a radios.
				To clear the existing policy, leave the input blank."
			::= { ccPolicyEntry 25 }

		
--  1.3.6.1.4.1.388.6.1.2.1.26
		-- 1.3.6.1.4.1.388.6.1.2.1.26
		ccPolicyDefAdoptAPPolicy11b OBJECT-TYPE
			SYNTAX DisplayString (SIZE (0..200))
			MAX-ACCESS read-write
			STATUS current
			DESCRIPTION
				"The default AP policy to be used for adopted 11b radios.
				To clear the existing policy, leave the input blank."
			::= { ccPolicyEntry 26 }

		
--  1.3.6.1.4.1.388.6.1.2.1.27
		-- 1.3.6.1.4.1.388.6.1.2.1.27
		ccPolicyDefAdoptAPPolicyFH OBJECT-TYPE
			SYNTAX DisplayString (SIZE (0..200))
			MAX-ACCESS read-write
			STATUS current
			DESCRIPTION
				"The default AP policy to be used for adopted FH radios.
				To clear the existing policy, leave the input blank."
			::= { ccPolicyEntry 27 }

		
--  1.3.6.1.4.1.388.6.1.2.1.28 
		-- 1.3.6.1.4.1.388.6.1.2.1.28
		ccPolicyDefAdoptAPPolicy11g OBJECT-TYPE
			SYNTAX DisplayString (SIZE (0..200))
			MAX-ACCESS read-write
			STATUS current
			DESCRIPTION
				"The default AP policy to be used for adopted 11g radios.
				To clear the existing policy, leave the input blank."
			::= { ccPolicyEntry 28 }

		
		-- 1.3.6.1.4.1.388.6.1.2.1.29
		ccPolicyChannel11g OBJECT-TYPE
			SYNTAX DisplayString (SIZE (1..200))
			MAX-ACCESS read-write
			STATUS current
			DESCRIPTION
				"The default Channel to be used for 11g radios. Valid values are 1 to 14.  
				You can also input 'auto-always' for allowing the switch to choose channels automatically. 
				'auto-once' can be input if you want the switch to choose a channel automatically, 
				only once. Enter 'random' to select a random channel."
			::= { ccPolicyEntry 29 }

		
		-- 1.3.6.1.4.1.388.6.1.2.1.30
		ccPolicyPower11g OBJECT-TYPE
			SYNTAX DisplayString (SIZE (1..20))
			MAX-ACCESS read-write
			STATUS current
			DESCRIPTION
				"The power to be used (in dBm).
				Valid values are :4-20"
			::= { ccPolicyEntry 30 }

		
--  1.3.6.1.4.1.388.6.1.3
		-- 1.3.6.1.4.1.388.6.1.3
		ccCountryInfoTable OBJECT-TYPE
			SYNTAX SEQUENCE OF CcCountryInfoEntry
			MAX-ACCESS not-accessible
			STATUS current
			DESCRIPTION
				"Country Information Table."
			::= { symbolCCSystem 3 }

		
--  1.3.6.1.4.1.388.6.1.3.1
		-- 1.3.6.1.4.1.388.6.1.3.1
		ccCountryInfoEntry OBJECT-TYPE
			SYNTAX CcCountryInfoEntry
			MAX-ACCESS not-accessible
			STATUS current
			DESCRIPTION
				"An entry in this table indicates one country information."
			INDEX { ccCCIndex }
			::= { ccCountryInfoTable 1 }

		
		CcCountryInfoEntry ::=
			SEQUENCE { 
				ccCCIndex
					INTEGER,
				ccCCode
					DisplayString,
				ccFullName
					DisplayString,
				cc11aChannels
					DisplayString,
				cc11bChannels
					DisplayString,
				ccFHTableNum
					INTEGER,
				ccFHChannels
					DisplayString,
				ccFHAlgorithm
					FHAlgorithm,
				ccFHContiguous
					INTEGER,
				ccFHHopSequence
					DisplayString,
				cc11gChannels
					DisplayString
			 }

--  1.3.6.1.4.1.388.6.1.3.1.1
		-- 1.3.6.1.4.1.388.6.1.3.1.1
		ccCCIndex OBJECT-TYPE
			SYNTAX INTEGER (1..100)
			MAX-ACCESS read-only
			STATUS current
			DESCRIPTION
				"Index of the table."
			::= { ccCountryInfoEntry 1 }

		
--  Mower: changed range from 0.. to 1..
-- 1.3.6.1.4.1.388.6.1.3.1.2
		-- 1.3.6.1.4.1.388.6.1.3.1.2
		ccCCode OBJECT-TYPE
			SYNTAX DisplayString (SIZE (0..20))
			MAX-ACCESS read-only
			STATUS current
			DESCRIPTION
				"The Country Code for this country"
			::= { ccCountryInfoEntry 2 }

		
--  1.3.6.1.4.1.388.6.1.3.1.3
		-- 1.3.6.1.4.1.388.6.1.3.1.3
		ccFullName OBJECT-TYPE
			SYNTAX DisplayString (SIZE (0..32))
			MAX-ACCESS read-only
			STATUS current
			DESCRIPTION
				"The name of this country."
			::= { ccCountryInfoEntry 3 }

		
--  1.3.6.1.4.1.388.6.1.3.1.6
		-- 1.3.6.1.4.1.388.6.1.3.1.6
		cc11aChannels OBJECT-TYPE
			SYNTAX DisplayString (SIZE (0..1000))
			MAX-ACCESS read-only
			STATUS current
			DESCRIPTION
				"The list of 11a channels applicable to this country."
			::= { ccCountryInfoEntry 6 }

		
--  1.3.6.1.4.1.388.6.1.3.1.7
		-- 1.3.6.1.4.1.388.6.1.3.1.7
		cc11bChannels OBJECT-TYPE
			SYNTAX DisplayString (SIZE (0..1000))
			MAX-ACCESS read-only
			STATUS current
			DESCRIPTION
				"The list of 11b channels applicable to this country."
			::= { ccCountryInfoEntry 7 }

		
--  1.3.6.1.4.1.388.6.1.3.1.8
		-- 1.3.6.1.4.1.388.6.1.3.1.8
		ccFHTableNum OBJECT-TYPE
			SYNTAX INTEGER (0..20)
			MAX-ACCESS read-only
			STATUS current
			DESCRIPTION
				"The hop sequence table number"
			::= { ccCountryInfoEntry 8 }

		
--  1.3.6.1.4.1.388.6.1.3.1.9
		-- 1.3.6.1.4.1.388.6.1.3.1.9
		ccFHChannels OBJECT-TYPE
			SYNTAX DisplayString (SIZE (0..100))
			MAX-ACCESS read-only
			STATUS current
			DESCRIPTION
				"List of all FH Channels"
			::= { ccCountryInfoEntry 9 }

		
--  1.3.6.1.4.1.388.6.1.3.1.10
		-- 1.3.6.1.4.1.388.6.1.3.1.10
		ccFHAlgorithm OBJECT-TYPE
			SYNTAX FHAlgorithm
			MAX-ACCESS read-only
			STATUS current
			DESCRIPTION
				"The algorithm used for frequency hopping."
			::= { ccCountryInfoEntry 10 }

		
--  1.3.6.1.4.1.388.6.1.3.1.11
		-- 1.3.6.1.4.1.388.6.1.3.1.11
		ccFHContiguous OBJECT-TYPE
			SYNTAX INTEGER (0..100)
			MAX-ACCESS read-only
			STATUS current
			DESCRIPTION
				"Number of total contiguous channels"
			::= { ccCountryInfoEntry 11 }

		
--  1.3.6.1.4.1.388.6.1.3.1.12
		-- 1.3.6.1.4.1.388.6.1.3.1.12
		ccFHHopSequence OBJECT-TYPE
			SYNTAX DisplayString (SIZE (0..1000))
			MAX-ACCESS read-only
			STATUS current
			DESCRIPTION
				"The Hop Sequence used in the frequency hopping algorithm"
			::= { ccCountryInfoEntry 12 }

		
		-- 1.3.6.1.4.1.388.6.1.3.1.13
		cc11gChannels OBJECT-TYPE
			SYNTAX DisplayString (SIZE (0..1000))
			MAX-ACCESS read-only
			STATUS current
			DESCRIPTION
				"The list of 11g channels applicable to this country."
			::= { ccCountryInfoEntry 13 }

		
--  1.3.6.1.4.1.388.6.1.4
		-- 1.3.6.1.4.1.388.6.1.4
		ccOnBoardKerberos OBJECT IDENTIFIER ::= { symbolCCSystem 4 }

		
--  1.3.6.1.4.1.388.6.1.4.3
		-- 1.3.6.1.4.1.388.6.1.4.3
		kerbCfgKDC OBJECT IDENTIFIER ::= { ccOnBoardKerberos 3 }

		
--  1.3.6.1.4.1.388.6.1.4.3.1
		-- 1.3.6.1.4.1.388.6.1.4.3.1
		kdcType OBJECT-TYPE
			SYNTAX DisplayString (SIZE (1..6))
			MAX-ACCESS read-only
			STATUS current
			DESCRIPTION
				"Represent the current KDC type MASTER/SLAVE.
				return string format: <master> or <slave> or <neither>
				Note:
				 	<neither> means that no KDC server has been configured yet,
					and you need to configurate one.
				"
			::= { kerbCfgKDC 1 }

		
--  1.3.6.1.4.1.388.6.1.4.3.7
		-- 1.3.6.1.4.1.388.6.1.4.3.7
		masterHost OBJECT-TYPE
			SYNTAX DisplayString (SIZE (0..32))
			MAX-ACCESS read-only
			STATUS current
			DESCRIPTION
				"The host name of a remote master KDC used by the on-board Slave-KDC.
				This object is valid when the onboard KDC is configured is Slave."
			::= { kerbCfgKDC 7 }

		
--  1.3.6.1.4.1.388.6.1.4.3.8
		-- 1.3.6.1.4.1.388.6.1.4.3.8
		masterIPAddress OBJECT-TYPE
			SYNTAX IpAddress
			MAX-ACCESS read-only
			STATUS current
			DESCRIPTION
				"The IP address of a remote master KDC used by the on-board Slave-KDC.
				only valid for creating a Slave-KDC."
			::= { kerbCfgKDC 8 }

		
--  1.3.6.1.4.1.388.6.1.4.3.9
		-- 1.3.6.1.4.1.388.6.1.4.3.9
		createMsKdc OBJECT-TYPE
			SYNTAX DisplayString (SIZE (1..120))
			MAX-ACCESS read-write
			STATUS current
			DESCRIPTION
				"Configure an on-board Master KDC.
				Input string format: 
						<realm,interface>
				Input string length limits:
						realm:		32 bytes
						interface   integer
				The following characters are not allowed for realm:
				` @ # $ & ( ) = | \ ; double-quote ' < > / sp
				
				and	interface  should be 1 or 2.    
				Note:
				If the on-board KDC is already configured as master or slave
				then reconfiguring is not possible till the earlier configuration
				is deleted.
				"
			::= { kerbCfgKDC 9 }

		
--  1.3.6.1.4.1.388.6.1.4.3.10
		-- 1.3.6.1.4.1.388.6.1.4.3.10
		delMsKdc OBJECT-TYPE
			SYNTAX TruthValue
			MAX-ACCESS read-write
			STATUS current
			DESCRIPTION
				"True will delete the Master KDC and false is an invalid input."
			::= { kerbCfgKDC 10 }

		
--  1.3.6.1.4.1.388.6.1.4.3.11
		-- 1.3.6.1.4.1.388.6.1.4.3.11
		createSlvKdc OBJECT-TYPE
			SYNTAX DisplayString (SIZE (0..150))
			MAX-ACCESS read-write
			STATUS current
			DESCRIPTION
				"Configure an on-board Slave KDC.
				Input string format: 
						<realm,master_hostname,master_ip,interface>
				Input string length limits:
						realm:		32 characters
						hostname:	50 characters
				For realm, the following characters are not allowed:
						 ` @ # $ & ( ) = | \ ; double-quote ' < > / sp
				 And for hostname, only the following characters are allowed:
				 0123456789ABCDEFGHIJKLMNOPQRSTUVWXYZabcdefghijklmnopqrstuvwxyz_- 
				 Also, '_' and '-' cannot be the first or last character of the hostname.
				interface could be 1 or 2 (etherport no.)
				Note:
				    If the on-board KDC is already configured as master or slave
				    then reconfiguring is not possible till the earlier configuration
				    is deleted."
			::= { kerbCfgKDC 11 }

		
--  1.3.6.1.4.1.388.6.1.4.3.12
		-- 1.3.6.1.4.1.388.6.1.4.3.12
		delSlvKdc OBJECT-TYPE
			SYNTAX TruthValue
			MAX-ACCESS read-write
			STATUS current
			DESCRIPTION
				"True will delete the Slave KDC and false is an invalid input."
			::= { kerbCfgKDC 12 }

		
--  1.3.6.1.4.1.388.6.1.4.3.13
		-- 1.3.6.1.4.1.388.6.1.4.3.13
		kdcRealm OBJECT-TYPE
			SYNTAX DisplayString (SIZE (0..32))
			MAX-ACCESS read-only
			STATUS current
			DESCRIPTION
				"The REALM of the on-board KDC. The Maximum length of the KDC Realm 
				can be 32 characters. Note that the following characters cannot be part 
				of KDC Realm field - `@#$&()|\\;'<>/ = and double quotes."
			::= { kerbCfgKDC 13 }

		
--  1.3.6.1.4.1.388.6.1.4.3.14
		-- 1.3.6.1.4.1.388.6.1.4.3.14
		interfaceNumber OBJECT-TYPE
			SYNTAX DisplayString
			MAX-ACCESS read-only
			STATUS current
			DESCRIPTION
				"The Interface this KDC is to be configured on.
				Valid Interface values 'ethernet1' & 'ethernet2'."
			::= { kerbCfgKDC 14 }

		
		-- 1.3.6.1.4.1.388.6.1.4.3.15
		addkdcMu OBJECT-TYPE
			SYNTAX DisplayString
			MAX-ACCESS read-write
			STATUS current
			DESCRIPTION
				"Add a KDC user.
				This is Write-only.
				 syntax <kdcUsername,password,ticket_life>
				"
			::= { kerbCfgKDC 15 }

		
		-- 1.3.6.1.4.1.388.6.1.4.3.16
		remkdcMu OBJECT-TYPE
			SYNTAX DisplayString
			MAX-ACCESS read-write
			STATUS current
			DESCRIPTION
				"Remove a KDC user
				This is Write-only."
			::= { kerbCfgKDC 16 }

		
--  (In v1.2.5 MIB file, changed from INTEGER to DisplayString;
-- implementation was always as a DisplayString).
-- 1.3.6.1.4.1.388.6.1.4.4
		-- 1.3.6.1.4.1.388.6.1.4.4
		kerbCfgSlave OBJECT IDENTIFIER ::= { ccOnBoardKerberos 4 }

		
--  1.3.6.1.4.1.388.6.1.4.4.1
		-- 1.3.6.1.4.1.388.6.1.4.4.1
		addSlave OBJECT-TYPE
			SYNTAX DisplayString (SIZE (0..80))
			MAX-ACCESS read-write
			STATUS current
			DESCRIPTION
				"Add one slave kdc into the on-board Master KDC.
				Input string format:
				  <hostname,domain,ip>
				For hostname, only the following characters are allowed:
				0123456789ABCDEFGHIJKLMNOPQRSTUVWXYZabcdefghijklmnopqrstuvwxyz_-
				Also, '_' and '-' cannot be the first or last character of the hostname.
				
				For domain, only the following characters are allowed:  
				0123456789ABCDEFGHIJKLMNOPQRSTUVWXYZabcdefghijklmnopqrstuvwxyz._-
				Also, '_' , '-' and '.' cannot be the first or last character of the domain name.                         
				"
			::= { kerbCfgSlave 1 }

		
--  1.3.6.1.4.1.388.6.1.4.4.2
		-- 1.3.6.1.4.1.388.6.1.4.4.2
		delSlave OBJECT-TYPE
			SYNTAX DisplayString (SIZE (0..80))
			MAX-ACCESS read-write
			STATUS current
			DESCRIPTION
				"Delete one slave kdc from the on-board Master KDC.
				Input string format:
				  <hostname,domain,ip>  
				 For hostname, only the following characters are allowed:
				0123456789ABCDEFGHIJKLMNOPQRSTUVWXYZabcdefghijklmnopqrstuvwxyz_-
				Also, '_' and '-' cannot be the first or last character of the hostname.
				
				For domain, only the following characters are allowed:  
				0123456789ABCDEFGHIJKLMNOPQRSTUVWXYZabcdefghijklmnopqrstuvwxyz._-
				Also, '_' , '-' and '.' cannot be the first or last character of the domain name. 
				"
			::= { kerbCfgSlave 2 }

		
--  1.3.6.1.4.1.388.6.1.4.4.3
		-- 1.3.6.1.4.1.388.6.1.4.4.3
		slaveCount OBJECT-TYPE
			SYNTAX Integer32
			MAX-ACCESS read-only
			STATUS current
			DESCRIPTION
				"The index of the KDC-Slave for this on-board Kerberos."
			::= { kerbCfgSlave 3 }

		
--  1.3.6.1.4.1.388.6.1.4.4.4
		-- 1.3.6.1.4.1.388.6.1.4.4.4
		slaveTable OBJECT-TYPE
			SYNTAX SEQUENCE OF SlaveEntry
			MAX-ACCESS not-accessible
			STATUS current
			DESCRIPTION
				"A table of remote Slave-KDC information.
				Then we assume that the current on-board KDC is a master KDC."
			::= { kerbCfgSlave 4 }

		
--  1.3.6.1.4.1.388.6.1.4.4.4.1
		-- 1.3.6.1.4.1.388.6.1.4.4.4.1
		slaveEntry OBJECT-TYPE
			SYNTAX SlaveEntry
			MAX-ACCESS not-accessible
			STATUS current
			DESCRIPTION
				"The entries of information about the remote Slave-KDC."
			INDEX { slaveIndex }
			::= { slaveTable 1 }

		
		SlaveEntry ::=
			SEQUENCE { 
				hostName
					DisplayString,
				realM
					DisplayString,
				ipAddress
					IpAddress,
				domainName
					DisplayString,
				slaveIndex
					INTEGER
			 }

--  1.3.6.1.4.1.388.6.1.4.4.4.1.1
		-- 1.3.6.1.4.1.388.6.1.4.4.4.1.1
		hostName OBJECT-TYPE
			SYNTAX DisplayString (SIZE (1..50))
			MAX-ACCESS read-only
			STATUS current
			DESCRIPTION
				"The host name of a remote slave KDC. The Maximum length of the KDC Host Name 
				can be 50 characters. 
				For hostname, only the following characters are allowed:
				0123456789ABCDEFGHIJKLMNOPQRSTUVWXYZabcdefghijklmnopqrstuvwxyz_-
				Also, '_' and '-' cannot be the first or last character of the hostname.
				"
			::= { slaveEntry 1 }

		
--  1.3.6.1.4.1.388.6.1.4.4.4.1.2
		-- 1.3.6.1.4.1.388.6.1.4.4.4.1.2
		realM OBJECT-TYPE
			SYNTAX DisplayString (SIZE (1..32))
			MAX-ACCESS read-only
			STATUS current
			DESCRIPTION
				"The realm for the remote Slave-KDC. The Maximum length of the KDC Realm 
				can be 32 characters. Note that the following characters cannot be part 
				of KDC Realm field - `@#$&()|\\;'<>/ = and double quotes."
			::= { slaveEntry 2 }

		
--  1.3.6.1.4.1.388.6.1.4.4.4.1.3
		-- 1.3.6.1.4.1.388.6.1.4.4.4.1.3
		ipAddress OBJECT-TYPE
			SYNTAX IpAddress
			MAX-ACCESS read-only
			STATUS current
			DESCRIPTION
				"The IP address of the remote Slave-KDC."
			::= { slaveEntry 3 }

		
--  1.3.6.1.4.1.388.6.1.4.4.4.1.4
		-- 1.3.6.1.4.1.388.6.1.4.4.4.1.4
		domainName OBJECT-TYPE
			SYNTAX DisplayString (SIZE (0..50))
			MAX-ACCESS read-only
			STATUS current
			DESCRIPTION
				"The domain name of a remote slave KDC. 
				For domain, only the following characters are allowed:  
				0123456789ABCDEFGHIJKLMNOPQRSTUVWXYZabcdefghijklmnopqrstuvwxyz._-
				Also, '_' , '-' and '.' cannot be the first or last character of the domain name
				"
			::= { slaveEntry 4 }

		
--  1.3.6.1.4.1.388.6.1.4.4.4.1.5
		-- 1.3.6.1.4.1.388.6.1.4.4.4.1.5
		slaveIndex OBJECT-TYPE
			SYNTAX INTEGER (1..100)
			MAX-ACCESS not-accessible
			STATUS current
			DESCRIPTION
				"The index of the SlaveTable"
			::= { slaveEntry 5 }

		
--  1.3.6.1.4.1.388.6.1.4.4.5
		-- 1.3.6.1.4.1.388.6.1.4.4.5
		syncDB OBJECT-TYPE
			SYNTAX DisplayString (SIZE (0..80))
			MAX-ACCESS read-write
			STATUS current
			DESCRIPTION
				"Synchronize the slave KDC database.
				Input string format:
				  <hostname,domain,ip>
				 For hostname, only the following characters are allowed:
				0123456789ABCDEFGHIJKLMNOPQRSTUVWXYZabcdefghijklmnopqrstuvwxyz_-
				Also, '_' and '-' cannot be the first or last character of the hostname.
					
				For domain, only the following characters are allowed:  
				0123456789ABCDEFGHIJKLMNOPQRSTUVWXYZabcdefghijklmnopqrstuvwxyz._-
				Also, '_' , '-' and '.' cannot be the first or last character of the domain name 
				"
			::= { kerbCfgSlave 5 }

		
--  1.3.6.1.4.1.388.6.1.4.5
		-- 1.3.6.1.4.1.388.6.1.4.5
		kerbCfgNTP OBJECT IDENTIFIER ::= { ccOnBoardKerberos 5 }

		
--  1.3.6.1.4.1.388.6.1.4.5.1
		-- 1.3.6.1.4.1.388.6.1.4.5.1
		prefTimeServer OBJECT-TYPE
			SYNTAX IpAddress
			MAX-ACCESS read-write
			STATUS current
			DESCRIPTION
				"The IP address for the preferred time server."
			::= { kerbCfgNTP 1 }

		
--  1.3.6.1.4.1.388.6.1.4.5.2
		-- 1.3.6.1.4.1.388.6.1.4.5.2
		firstAltTimeServer OBJECT-TYPE
			SYNTAX IpAddress
			MAX-ACCESS read-write
			STATUS current
			DESCRIPTION
				"The IP address for the first alternative time server.
				Note:
					If other two Time Server (prefer time server and the second time
					server ) are invalid time server ip address, this one should be a 
					valid time server ip address.
				
				"
			::= { kerbCfgNTP 2 }

		
--  1.3.6.1.4.1.388.6.1.4.5.3
		-- 1.3.6.1.4.1.388.6.1.4.5.3
		secondAltTimeServer OBJECT-TYPE
			SYNTAX IpAddress
			MAX-ACCESS read-write
			STATUS current
			DESCRIPTION
				"The IP address for the second alternative time server.
				Note:
					If other two Time Server (prefer time server and the first time
					server ) are invalid time server ip address, this one should be a 
					valid time server ip address.
				"
			::= { kerbCfgNTP 3 }

		
--  1.3.6.1.4.1.388.6.1.4.5.4
		-- 1.3.6.1.4.1.388.6.1.4.5.4
		groupSetTimeServer OBJECT-TYPE
			SYNTAX DisplayString (SIZE (0..60))
			MAX-ACCESS read-write
			STATUS current
			DESCRIPTION
				"Instead of setting each object one by one, this entry can
				be used to set all the time servers at the same time. 
				Input string format:
					<timesrv_1,timesrv_2,timesrv3>
				Ex. 
					timesrv_1: 156.234.82.99
					timesrv_2: 144.22.121.1
					timesrv_3: 221.32.11.33
				So, input string becomes <156.234.82.99,144.22.121.1,221.32.11.33>
				Note:
				    Out of the three IP Addresses, at least one of them must be 
				    a valid NTP server IP address. Otherwise, this SET doesn't work.
					
					Since this operation takes longer time than others, so
					please check the TIMEOUT setting in the manager program and make sure 
					that the value should be at least 5 minutes."
			::= { kerbCfgNTP 4 }

		
--  1.3.6.1.4.1.388.6.1.4.5.5
		-- 1.3.6.1.4.1.388.6.1.4.5.5
		delAll OBJECT-TYPE
			SYNTAX TruthValue
			MAX-ACCESS read-write
			STATUS current
			DESCRIPTION
				"Delete all of NTP servers."
			::= { kerbCfgNTP 5 }

		
--  1.3.6.1.4.1.388.6.1.4.5.6
		-- 1.3.6.1.4.1.388.6.1.4.5.6
		delTimeServer OBJECT-TYPE
			SYNTAX DisplayString (SIZE (1..32))
			MAX-ACCESS read-write
			STATUS deprecated
			DESCRIPTION
				"Delete a Time Server.Enter either '1' or '2' or '3',
				to delete the preferred, first alternative server, 
				and second alternative server respectively"
			::= { kerbCfgNTP 6 }

		
--  (depricated as of 1.2.5)
-- 1.3.6.1.4.1.388.6.1.4.6
		-- 1.3.6.1.4.1.388.6.1.4.6
		kerbKDCUsers OBJECT IDENTIFIER ::= { ccOnBoardKerberos 6 }

		
--  1.3.6.1.4.1.388.6.1.4.6.1
		-- 1.3.6.1.4.1.388.6.1.4.6.1
		kdcUserTable OBJECT-TYPE
			SYNTAX SEQUENCE OF KdcUserEntry
			MAX-ACCESS not-accessible
			STATUS current
			DESCRIPTION
				" "
			::= { kerbKDCUsers 1 }

		
--  1.3.6.1.4.1.388.6.1.4.6.1.1
		-- 1.3.6.1.4.1.388.6.1.4.6.1.1
		kdcUserEntry OBJECT-TYPE
			SYNTAX KdcUserEntry
			MAX-ACCESS not-accessible
			STATUS current
			DESCRIPTION
				"The Users(MU's) in the KDC with ticketlife."
			INDEX { kdcUserIndex }
			::= { kdcUserTable 1 }

		
		KdcUserEntry ::=
			SEQUENCE { 
				kdcUserIndex
					INTEGER,
				kdcUserName
					DisplayString,
				kdcUserTlife
					Integer32
			 }

--  1.3.6.1.4.1.388.6.1.4.6.1.1.1
		-- 1.3.6.1.4.1.388.6.1.4.6.1.1.1
		kdcUserIndex OBJECT-TYPE
			SYNTAX INTEGER (1..4096)
			MAX-ACCESS not-accessible
			STATUS current
			DESCRIPTION
				"The Index of the kdcUserEntry table."
			::= { kdcUserEntry 1 }

		
--  1.3.6.1.4.1.388.6.1.4.6.1.1.2
		-- 1.3.6.1.4.1.388.6.1.4.6.1.1.2
		kdcUserName OBJECT-TYPE
			SYNTAX DisplayString (SIZE (1..20))
			MAX-ACCESS read-only
			STATUS current
			DESCRIPTION
				"The list of Users(MU's) registered in the KDC. The Maximum length of the User Name 
				can be 20 characters. Note that the following characters cannot be part 
				of User Name field - ',@,#,$,&,\,<, ,> and double quotes. and double quotes."
			::= { kdcUserEntry 2 }

		
--  1.3.6.1.4.1.388.6.1.4.6.1.1.3
		-- 1.3.6.1.4.1.388.6.1.4.6.1.1.3
		kdcUserTlife OBJECT-TYPE
			SYNTAX Integer32
			MAX-ACCESS read-write
			STATUS current
			DESCRIPTION
				"A Kerberos Ticket life time for this user.
				The range would be in (1 - 600)."
			::= { kdcUserEntry 3 }

		
--  1.3.6.1.4.1.388.6.1.4.6.2
		-- 1.3.6.1.4.1.388.6.1.4.6.2
		kdcWLANTable OBJECT-TYPE
			SYNTAX SEQUENCE OF KdcWLANEntry
			MAX-ACCESS not-accessible
			STATUS current
			DESCRIPTION
				" "
			::= { kerbKDCUsers 2 }

		
--  1.3.6.1.4.1.388.6.1.4.6.2.1
		-- 1.3.6.1.4.1.388.6.1.4.6.2.1
		kdcWLANEntry OBJECT-TYPE
			SYNTAX KdcWLANEntry
			MAX-ACCESS not-accessible
			STATUS current
			DESCRIPTION
				"The list of WLAN's registered in the KDC."
			INDEX { kdcWLANIndex }
			::= { kdcWLANTable 1 }

		
		KdcWLANEntry ::=
			SEQUENCE { 
				kdcWLANIndex
					INTEGER,
				kdcWLANName
					DisplayString,
				kdcWLANTlife
					Integer32
			 }

--  1.3.6.1.4.1.388.6.1.4.6.2.1.1
		-- 1.3.6.1.4.1.388.6.1.4.6.2.1.1
		kdcWLANIndex OBJECT-TYPE
			SYNTAX INTEGER (1..200)
			MAX-ACCESS not-accessible
			STATUS current
			DESCRIPTION
				"The index of the WLANs for this on-board Kerberos."
			::= { kdcWLANEntry 1 }

		
--  1.3.6.1.4.1.388.6.1.4.6.2.1.2
		-- 1.3.6.1.4.1.388.6.1.4.6.2.1.2
		kdcWLANName OBJECT-TYPE
			SYNTAX DisplayString (SIZE (1..50))
			MAX-ACCESS read-only
			STATUS current
			DESCRIPTION
				"The name of a WLAN's which has a registered account in the On-Board KDC."
			::= { kdcWLANEntry 2 }

		
--  1.3.6.1.4.1.388.6.1.4.6.2.1.3
		-- 1.3.6.1.4.1.388.6.1.4.6.2.1.3
		kdcWLANTlife OBJECT-TYPE
			SYNTAX Integer32
			MAX-ACCESS read-write
			STATUS current
			DESCRIPTION
				"A Kerberos Ticket life time for this WLAN.
				The range would be in (0 - 600)."
			::= { kdcWLANEntry 3 }

		
--  10th Nov 2003
-- 10th Nov, 2003
-- 1st Sep 2003
		-- 1.3.6.1.4.1.388.6.1.5
		radiusAuthentication OBJECT IDENTIFIER ::= { symbolCCSystem 5 }

		
		-- 1.3.6.1.4.1.388.6.1.5.2
		radiusAuthClientMIB OBJECT IDENTIFIER ::= { radiusAuthentication 2 }
-- Mower: changed this from a MODULE-IDENTITY to just a
-- simple non-leaf OID, since the new [merged/single] MIB can
-- only have one MODULE-IDENTITY, and that single 
-- MODULE-IDENTITY will be in the 'newInV1dot3' group, not
-- here.
		
		-- 1.3.6.1.4.1.388.6.1.5.2.1
		radiusAuthClientMIBObjects OBJECT IDENTIFIER ::= { radiusAuthClientMIB 1 }

		
		-- 1.3.6.1.4.1.388.6.1.5.2.1.1
		radiusAuthClient OBJECT IDENTIFIER ::= { radiusAuthClientMIBObjects 1 }

		
		-- 1.3.6.1.4.1.388.6.1.5.2.1.1.1
		radiusAuthClientInvalidServerAddresses OBJECT-TYPE
			SYNTAX Counter32
			MAX-ACCESS read-only
			STATUS current
			DESCRIPTION
				"The number of RADIUS Access-Response packets
				received from unknown addresses"
			::= { radiusAuthClient 1 }

		
		-- 1.3.6.1.4.1.388.6.1.5.2.1.1.3
		radiusAuthServerTable OBJECT-TYPE
			SYNTAX SEQUENCE OF RadiusAuthServerEntry
			MAX-ACCESS not-accessible
			STATUS current
			DESCRIPTION
				"The (conceptual) table listing the RADIUS authentication
				servers with which the client shares a secret."
			::= { radiusAuthClient 3 }

		
		-- 1.3.6.1.4.1.388.6.1.5.2.1.1.3.1
		radiusAuthServerEntry OBJECT-TYPE
			SYNTAX RadiusAuthServerEntry
			MAX-ACCESS not-accessible
			STATUS current
			DESCRIPTION
				"An entry (conceptual row) representing a RADIUS
				authentication server with which the client shares
				a secret."
			INDEX { radiusAuthServerIndex }
			::= { radiusAuthServerTable 1 }
-- For Request/Response statistics...
-- 
-- TotalIncomingPackets = Accepts + Rejects + Challenges + UnknownTypes
-- 
-- TotalIncomingPackets - MalformedResponses - BadAuthenticators -
-- UnknownTypes - PacketsDropped = Successfully received
-- 
-- AccessRequests + PendingRequests + ClientTimeouts =
-- Successfully Received
		
		RadiusAuthServerEntry ::=
			SEQUENCE { 
				radiusAuthServerIndex
					Integer32,
				radiusAuthServerAddress
					DisplayString,
				radiusAuthClientServerPortNumber
					Integer32,
				radiusAuthClientRoundTripTime
					TimeTicks,
				radiusAuthClientAccessRequests
					Counter32,
				radiusAuthClientAccessRetransmissions
					INTEGER,
				radiusAuthClientAccessAccepts
					Counter32,
				radiusAuthClientAccessRejects
					Counter32,
				radiusAuthClientAccessChallenges
					Counter32,
				radiusAuthClientMalformedAccessResponses
					Counter32,
				radiusAuthClientBadAuthenticators
					Counter32,
				radiusAuthClientPendingRequests
					Gauge32,
				radiusAuthClientTimeouts
					INTEGER,
				radiusAuthClientUnknownTypes
					Counter32,
				radiusAuthClientPacketsDropped
					Counter32,
				radiusAuthClientIdentifier
					SnmpAdminString
			 }

		-- 1.3.6.1.4.1.388.6.1.5.2.1.1.3.1.1
		radiusAuthServerIndex OBJECT-TYPE
			SYNTAX Integer32 (1..2147483647)
			MAX-ACCESS not-accessible
			STATUS current
			DESCRIPTION
				"A number uniquely identifying each RADIUS
				Authentication server with which this client
				communicates. Note that Index 1 denotes the Primary
				RADIUS server, while 2 denotes the secondary RADIUS server."
			::= { radiusAuthServerEntry 1 }

		
		-- 1.3.6.1.4.1.388.6.1.5.2.1.1.3.1.2
		radiusAuthServerAddress OBJECT-TYPE
			SYNTAX DisplayString
			MAX-ACCESS read-write
			STATUS current
			DESCRIPTION
				"The IP address or the name of the RADIUS authentication 
				server referred to in this table entry.The syntax for
				the input is :<host_name/IP>,<RADIUS Secret>.
				"
			::= { radiusAuthServerEntry 2 }

		
		-- 1.3.6.1.4.1.388.6.1.5.2.1.1.3.1.3
		radiusAuthClientServerPortNumber OBJECT-TYPE
			SYNTAX Integer32 (1..65535)
			MAX-ACCESS read-write
			STATUS current
			DESCRIPTION
				"The UDP port the client is using to send requests to
				this server."
			::= { radiusAuthServerEntry 3 }

		
		-- 1.3.6.1.4.1.388.6.1.5.2.1.1.3.1.4
		radiusAuthClientRoundTripTime OBJECT-TYPE
			SYNTAX TimeTicks
			MAX-ACCESS read-only
			STATUS current
			DESCRIPTION
				"The time interval (in hundredths of a second) between
				the most recent Access-Reply/Access-Challenge and the
				Access-Request that matched it from this RADIUS
				authentication server."
			::= { radiusAuthServerEntry 4 }

		
		-- 1.3.6.1.4.1.388.6.1.5.2.1.1.3.1.5
		radiusAuthClientAccessRequests OBJECT-TYPE
			SYNTAX Counter32
			MAX-ACCESS read-only
			STATUS current
			DESCRIPTION
				"The number of RADIUS Access-Request packets sent
				to this server. This does not include retransmissions."
			::= { radiusAuthServerEntry 5 }

		
		-- 1.3.6.1.4.1.388.6.1.5.2.1.1.3.1.6
		radiusAuthClientAccessRetransmissions OBJECT-TYPE
			SYNTAX INTEGER (1..10)
			MAX-ACCESS read-write
			STATUS current
			DESCRIPTION
				"The number of RADIUS Access-Request packets
				retransmitted to this RADIUS authentication server."
			::= { radiusAuthServerEntry 6 }

		
		-- 1.3.6.1.4.1.388.6.1.5.2.1.1.3.1.7
		radiusAuthClientAccessAccepts OBJECT-TYPE
			SYNTAX Counter32
			MAX-ACCESS read-only
			STATUS current
			DESCRIPTION
				"The number of RADIUS Access-Accept packets
				(valid or invalid) received from this server."
			::= { radiusAuthServerEntry 7 }

		
		-- 1.3.6.1.4.1.388.6.1.5.2.1.1.3.1.8
		radiusAuthClientAccessRejects OBJECT-TYPE
			SYNTAX Counter32
			MAX-ACCESS read-only
			STATUS current
			DESCRIPTION
				"The number of RADIUS Access-Reject packets
				(valid or invalid) received from this server."
			::= { radiusAuthServerEntry 8 }

		
		-- 1.3.6.1.4.1.388.6.1.5.2.1.1.3.1.9
		radiusAuthClientAccessChallenges OBJECT-TYPE
			SYNTAX Counter32
			MAX-ACCESS read-only
			STATUS current
			DESCRIPTION
				"The number of RADIUS Access-Challenge packets
				(valid or invalid) received from this server."
			::= { radiusAuthServerEntry 9 }

		
-- "Access-Response" includes an Access-Accept, Access-Challenge
-- or Access-Reject.
		-- 1.3.6.1.4.1.388.6.1.5.2.1.1.3.1.10
		radiusAuthClientMalformedAccessResponses OBJECT-TYPE
			SYNTAX Counter32
			MAX-ACCESS read-only
			STATUS current
			DESCRIPTION
				"The number of malformed RADIUS Access-Response
				packets received from this server.
				Malformed packets include packets with
				an invalid length. Bad authenticators or
				Signature attributes or unknown types are not
				included as malformed access responses."
			::= { radiusAuthServerEntry 10 }

		
		-- 1.3.6.1.4.1.388.6.1.5.2.1.1.3.1.11
		radiusAuthClientBadAuthenticators OBJECT-TYPE
			SYNTAX Counter32
			MAX-ACCESS read-only
			STATUS current
			DESCRIPTION
				"The number of RADIUS Access-Response packets
				containing invalid authenticators or Signature
				attributes received from this server."
			::= { radiusAuthServerEntry 11 }

		
		-- 1.3.6.1.4.1.388.6.1.5.2.1.1.3.1.12
		radiusAuthClientPendingRequests OBJECT-TYPE
			SYNTAX Gauge32
			MAX-ACCESS read-only
			STATUS current
			DESCRIPTION
				"The number of RADIUS Access-Request packets
				destined for this server that have not yet timed out
				or received a response. This variable is incremented
				when an Access-Request is sent and decremented due to
				receipt of an Acess-Accept, Access-Reject or
				Access-Challenge, a timeout or retransmission."
			::= { radiusAuthServerEntry 12 }

		
		-- 1.3.6.1.4.1.388.6.1.5.2.1.1.3.1.13
		radiusAuthClientTimeouts OBJECT-TYPE
			SYNTAX INTEGER (5..20)
			MAX-ACCESS read-write
			STATUS current
			DESCRIPTION
				"The number of authentication timeouts to this server.
				After a timeout the client may retry to the same
				server, send to a different server, or
				give up. A retry to the same server is counted as a
				retransmit as well as a timeout. A send to a different
				server is counted as a Request as well as a timeout."
			::= { radiusAuthServerEntry 13 }

		
		-- 1.3.6.1.4.1.388.6.1.5.2.1.1.3.1.14
		radiusAuthClientUnknownTypes OBJECT-TYPE
			SYNTAX Counter32
			MAX-ACCESS read-only
			STATUS current
			DESCRIPTION
				"The number of RADIUS packets of unknown type which
				were received from this server on the authentication port."
			::= { radiusAuthServerEntry 14 }

		
		-- 1.3.6.1.4.1.388.6.1.5.2.1.1.3.1.15
		radiusAuthClientPacketsDropped OBJECT-TYPE
			SYNTAX Counter32
			MAX-ACCESS read-only
			STATUS current
			DESCRIPTION
				"The number of RADIUS packets of which were
				received from this server on the authentication port
				and dropped for some other reason."
			::= { radiusAuthServerEntry 15 }

		
		-- 1.3.6.1.4.1.388.6.1.5.2.1.1.3.1.16
		radiusAuthClientIdentifier OBJECT-TYPE
			SYNTAX SnmpAdminString
			MAX-ACCESS read-only
			STATUS current
			DESCRIPTION
				"The NAS identifier of the RADIUS authentication client."
			::= { radiusAuthServerEntry 16 }

		
		-- 1.3.6.1.4.1.388.6.1.5.2.2
		radiusAuthClientMIBConformance OBJECT IDENTIFIER ::= { radiusAuthClientMIB 2 }

		
		-- 1.3.6.1.4.1.388.6.1.5.2.2.1
		radiusAuthClientMIBCompliances OBJECT IDENTIFIER ::= { radiusAuthClientMIBConformance 1 }

		
--  this module
		-- 1.3.6.1.4.1.388.6.1.5.2.2.1.1
		radiusAuthClientMIBCompliance MODULE-COMPLIANCE
			STATUS current
			DESCRIPTION 
				"The compliance statement for authentication clients
				implementing the RADIUS Authentication Client MIB."
			MODULE SYMBOL-CC-WS5000-MIB
				MANDATORY-GROUPS { radiusAuthClientMIBGroup }
			::= { radiusAuthClientMIBCompliances 1 }

		
		-- 1.3.6.1.4.1.388.6.1.5.2.2.2
		radiusAuthClientMIBGroups OBJECT IDENTIFIER ::= { radiusAuthClientMIBConformance 2 }

		
		-- 1.3.6.1.4.1.388.6.1.5.2.2.2.1
		radiusAuthClientMIBGroup OBJECT-GROUP
			OBJECTS { radiusAuthClientInvalidServerAddresses, radiusAuthServerAddress, radiusAuthClientServerPortNumber, radiusAuthClientRoundTripTime, radiusAuthClientAccessRequests, 
				radiusAuthClientAccessRetransmissions, radiusAuthClientAccessAccepts, radiusAuthClientAccessRejects, radiusAuthClientAccessChallenges, radiusAuthClientMalformedAccessResponses, 
				radiusAuthClientBadAuthenticators, radiusAuthClientPendingRequests, radiusAuthClientTimeouts, radiusAuthClientUnknownTypes, radiusAuthClientPacketsDropped, 
				radiusAuthClientIdentifier }
			STATUS current
			DESCRIPTION 
				"The basic collection of objects providing management of
				RADIUS Authentication Clients."
			::= { radiusAuthClientMIBGroups 1 }

		
		-- 1.3.6.1.4.1.388.6.1.6
		ccEventsObjects OBJECT IDENTIFIER ::= { symbolCCSystem 6 }

		
		-- 1.3.6.1.4.1.388.6.1.6.1
		ccEventsAllLocalLog OBJECT-TYPE
			SYNTAX TruthValue
			MAX-ACCESS read-write
			STATUS current
			DESCRIPTION
				"Enable/Disable local logging for all Events.
				This variable is SET-only."
			::= { ccEventsObjects 1 }

		
		-- 1.3.6.1.4.1.388.6.1.6.2
		ccEventsAllSNMPTrap OBJECT-TYPE
			SYNTAX TruthValue
			MAX-ACCESS read-write
			STATUS current
			DESCRIPTION
				"Enable/Disable SNMP Trap for all Events.
				This variable is SET-only."
			::= { ccEventsObjects 2 }

		
		-- 1.3.6.1.4.1.388.6.1.6.3
		ccEventsAllSyslog OBJECT-TYPE
			SYNTAX DisplayString (SIZE (3..10))
			MAX-ACCESS read-write
			STATUS current
			DESCRIPTION
				"Enable/Disable Syslog for all Events. In order
				to SET the Syslog level for all Events to a particular severity level,
				enter the severity level as the input. The accepted severity levels are:
				   'emerg' for emergency level,
				'alert' for alert level,
				'crit' for critical level,
				'err' for error level,
				'warning' for warning level,
				'notice' for notice level,
				'info' for info level,
				'debug' for debug level
				In order to disable Syslogging for all Events, 
				enter 'disable' as the input (without the single quotes).
				This variable is SET-only."
			::= { ccEventsObjects 3 }

		
		-- 1.3.6.1.4.1.388.6.1.6.4
		ccEventsAllDefault OBJECT-TYPE
			SYNTAX TruthValue
			MAX-ACCESS read-write
			STATUS current
			DESCRIPTION
				"Set all Events to their default state. Only 'true' 
				is a valid input.
				This variable is SET-only."
			::= { ccEventsObjects 4 }

		
		-- 1.3.6.1.4.1.388.6.1.6.5
		ccEventTable OBJECT-TYPE
			SYNTAX SEQUENCE OF CcEventEntry
			MAX-ACCESS not-accessible
			STATUS current
			DESCRIPTION
				"A list of Syslog predefined events"
			::= { ccEventsObjects 5 }

		
		-- 1.3.6.1.4.1.388.6.1.6.5.1
		ccEventEntry OBJECT-TYPE
			SYNTAX CcEventEntry
			MAX-ACCESS not-accessible
			STATUS current
			DESCRIPTION
				"An entry in the Events Table"
			INDEX { ccEventIndex }
			::= { ccEventTable 1 }

		
		CcEventEntry ::=
			SEQUENCE { 
				ccEventIndex
					INTEGER,
				ccEventDescr
					DisplayString,
				ccEventDefault
					TruthValue,
				ccEventSyslog
					DisplayString,
				ccEventSNMPTrap
					TruthValue,
				ccEventLocalLog
					TruthValue
			 }

		-- 1.3.6.1.4.1.388.6.1.6.5.1.1
		ccEventIndex OBJECT-TYPE
			SYNTAX INTEGER (1..100)
			MAX-ACCESS not-accessible
			STATUS current
			DESCRIPTION
				"Index of an specific event."
			::= { ccEventEntry 1 }

		
		-- 1.3.6.1.4.1.388.6.1.6.5.1.2
		ccEventDescr OBJECT-TYPE
			SYNTAX DisplayString (SIZE (1..200))
			MAX-ACCESS read-only
			STATUS current
			DESCRIPTION
				"Description of an specific event."
			::= { ccEventEntry 2 }

		
		-- 1.3.6.1.4.1.388.6.1.6.5.1.3
		ccEventDefault OBJECT-TYPE
			SYNTAX TruthValue
			MAX-ACCESS read-write
			STATUS current
			DESCRIPTION
				"Set the event to its default state. Only 'true' 
				is an acceptable value.
				This variable is SET-only."
			::= { ccEventEntry 3 }

		
		-- 1.3.6.1.4.1.388.6.1.6.5.1.4
		ccEventSyslog OBJECT-TYPE
			SYNTAX DisplayString (SIZE (1..20))
			MAX-ACCESS read-write
			STATUS current
			DESCRIPTION
				"Enable/Disable Syslog for this Event. In order
				to SET the Syslog level for this Event to a particular severity level,
				enter the severity level as the input. The accepted severity levels are:
				   'emerg' for emergency level,
				'alert' for alert level,
				'crit' for critical level,
				'err' for error level,
				'warning' for warning level,
				'notice' for notice level,
				'info' for info level,
				'debug' for debug level
				In order to disable Syslogging for this Event, 
				enter 'disable' as the input (without the single quotes) "
			::= { ccEventEntry 4 }

		
		-- 1.3.6.1.4.1.388.6.1.6.5.1.5
		ccEventSNMPTrap OBJECT-TYPE
			SYNTAX TruthValue
			MAX-ACCESS read-write
			STATUS current
			DESCRIPTION
				"Current SNMP-Trap's status of an specific event.
				Setting it to 'true' activates the SNMP trap for this particular Event,
				while 'false' deactivates it"
			::= { ccEventEntry 5 }

		
		-- 1.3.6.1.4.1.388.6.1.6.5.1.6
		ccEventLocalLog OBJECT-TYPE
			SYNTAX TruthValue
			MAX-ACCESS read-write
			STATUS current
			DESCRIPTION
				"Activate/Deactivate local logging.
				'true' activates local logging.
				'false' deactivates local logging for this particular Event."
			::= { ccEventEntry 6 }

		
		-- 1.3.6.1.4.1.388.6.1.6.6
		ccSyslogObjects OBJECT IDENTIFIER ::= { ccEventsObjects 6 }

		
		-- 1.3.6.1.4.1.388.6.1.6.6.1
		ccSysLogStatus OBJECT-TYPE
			SYNTAX TruthValue
			MAX-ACCESS read-write
			STATUS current
			DESCRIPTION
				"To retrieve and set the current syslog settings 
				within CC.  Acceptable values are: True(1), False(2)"
			::= { ccSyslogObjects 1 }

		
		-- 1.3.6.1.4.1.388.6.1.6.6.2
		ccSyslogHosts OBJECT IDENTIFIER ::= { ccSyslogObjects 2 }

		
		-- 1.3.6.1.4.1.388.6.1.6.6.2.1
		ccSyslogAddHost OBJECT-TYPE
			SYNTAX DisplayString (SIZE (1..200))
			MAX-ACCESS read-write
			STATUS current
			DESCRIPTION
				"Add a new Syslog collector host.
				You also need to provide the IP address of the host,
				so the input format is :
				<hostname,IP Address>
				Only the following characters can be part of the hostname:
				0123456789ABCDEFGHIJKLMNOPQRSTUVWXYZabcdefghijklmnopqrstuvwxyz_-
				Also, '_' and '-' cannot be the first or the last character of the hostname."
			::= { ccSyslogHosts 1 }

		
		-- 1.3.6.1.4.1.388.6.1.6.6.2.2
		ccSyslogRemHost OBJECT-TYPE
			SYNTAX DisplayString (SIZE (1..50))
			MAX-ACCESS read-write
			STATUS current
			DESCRIPTION
				"Remove an existing Syslog collector host."
			::= { ccSyslogHosts 2 }

		
		-- 1.3.6.1.4.1.388.6.1.6.6.2.3
		ccSyslogHostsTable OBJECT-TYPE
			SYNTAX SEQUENCE OF CcSyslogHostsEntry
			MAX-ACCESS not-accessible
			STATUS current
			DESCRIPTION
				"A list of Syslog Hosts"
			::= { ccSyslogHosts 3 }

		
		-- 1.3.6.1.4.1.388.6.1.6.6.2.3.1
		ccSyslogHostsEntry OBJECT-TYPE
			SYNTAX CcSyslogHostsEntry
			MAX-ACCESS not-accessible
			STATUS current
			DESCRIPTION
				"An entry in Syslog Hosts table"
			INDEX { ccSyslogHostIndex }
			::= { ccSyslogHostsTable 1 }

		
		CcSyslogHostsEntry ::=
			SEQUENCE { 
				ccSyslogHostIndex
					INTEGER,
				ccSyslogHostName
					DisplayString,
				ccSyslogHostIPAddr
					IpAddress,
				ccSyslogHostDomain
					DisplayString,
				ccSyslogHostSetSeverity
					DisplayString,
				ccSyslogHostSeverityList
					DisplayString
			 }

		-- 1.3.6.1.4.1.388.6.1.6.6.2.3.1.1
		ccSyslogHostIndex OBJECT-TYPE
			SYNTAX INTEGER (1..100)
			MAX-ACCESS not-accessible
			STATUS current
			DESCRIPTION
				"Index of specific Syslog Host."
			::= { ccSyslogHostsEntry 1 }

		
		-- 1.3.6.1.4.1.388.6.1.6.6.2.3.1.2
		ccSyslogHostName OBJECT-TYPE
			SYNTAX DisplayString (SIZE (1..200))
			MAX-ACCESS read-only
			STATUS current
			DESCRIPTION
				"DNS name of specific Syslog Host."
			::= { ccSyslogHostsEntry 2 }

		
		-- 1.3.6.1.4.1.388.6.1.6.6.2.3.1.3
		ccSyslogHostIPAddr OBJECT-TYPE
			SYNTAX IpAddress
			MAX-ACCESS read-write
			STATUS current
			DESCRIPTION
				"IP address of the Syslog Host"
			::= { ccSyslogHostsEntry 3 }

		
		-- 1.3.6.1.4.1.388.6.1.6.6.2.3.1.4
		ccSyslogHostDomain OBJECT-TYPE
			SYNTAX DisplayString (SIZE (1..200))
			MAX-ACCESS read-write
			STATUS current
			DESCRIPTION
				"Domain Name of the Syslog Host.
				Note that only the following characters are allowed in the domain name:
				0123456789ABCDEFGHIJKLMNOPQRSTUVWXYZabcdefghijklmnopqrstuvwxyz._-
				Also, '_' , '-' and '.' cannot be the first or last character of the domain name.
				
				If no Domain Name has been specified,
				then 'NA' is returned by the wireless switch."
			::= { ccSyslogHostsEntry 4 }

		
		-- 1.3.6.1.4.1.388.6.1.6.6.2.3.1.5
		ccSyslogHostSetSeverity OBJECT-TYPE
			SYNTAX DisplayString (SIZE (1..200))
			MAX-ACCESS read-write
			STATUS current
			DESCRIPTION
				"Set the severity level for which
				this particular host will receive syslog messages.
				The input format is:
				<SeverityLevel/'all','on'/'off'>
				where SeverityLevel can be one of the following strings: 
					'emerg' for emergency level,
					'alert' for alert level,
					'crit' for critical level,
					'err' for error level,
					'warning' for warning level,
					'notice' for notice level,
					'info' for info level,
					'debug' for debug level.
				'all' as SeverityLevel configures the collector to
				receive syslog messages for all severity levels.	  
				'on' is used to activate the host for receiving syslog messages.
				'off' causes the host to stop receiving syslog messages for that particular severity level.
				This variable is SET-only."
			::= { ccSyslogHostsEntry 5 }

		
		-- 1.3.6.1.4.1.388.6.1.6.6.2.3.1.6
		ccSyslogHostSeverityList OBJECT-TYPE
			SYNTAX DisplayString (SIZE (1..200))
			MAX-ACCESS read-only
			STATUS current
			DESCRIPTION
				" The list of all severity levels whose messages this host is configured to receive."
			::= { ccSyslogHostsEntry 6 }

		
		-- 1.3.6.1.4.1.388.6.1.7
		ccSystemHosts OBJECT IDENTIFIER ::= { symbolCCSystem 7 }

		
		-- 1.3.6.1.4.1.388.6.1.7.1
		ccSystemAddHost OBJECT-TYPE
			SYNTAX DisplayString (SIZE (1..200))
			MAX-ACCESS read-write
			STATUS current
			DESCRIPTION
				"Add a new System Host.
				You also need to provide the IP address of the host,
				so the input format is :
				<hostname,IP Address>
				              Only the following characters can be part of the hostname:
				0123456789ABCDEFGHIJKLMNOPQRSTUVWXYZabcdefghijklmnopqrstuvwxyz_-
				Also, '_' and '-' cannot be the first or the last character of the hostname."
			::= { ccSystemHosts 1 }

		
		-- 1.3.6.1.4.1.388.6.1.7.2
		ccSystemRemHost OBJECT-TYPE
			SYNTAX DisplayString (SIZE (1..200))
			MAX-ACCESS read-write
			STATUS current
			DESCRIPTION
				"Remove an existing System Host."
			::= { ccSystemHosts 2 }

		
		-- 1.3.6.1.4.1.388.6.1.7.3
		ccSystemHostsTable OBJECT-TYPE
			SYNTAX SEQUENCE OF CcSystemHostsEntry
			MAX-ACCESS not-accessible
			STATUS current
			DESCRIPTION
				"A list of Syslog Hosts"
			::= { ccSystemHosts 3 }

		
		-- 1.3.6.1.4.1.388.6.1.7.3.1
		ccSystemHostsEntry OBJECT-TYPE
			SYNTAX CcSystemHostsEntry
			MAX-ACCESS not-accessible
			STATUS current
			DESCRIPTION
				"An entry in Syslog Hosts table"
			INDEX { ccSystemHostIndex }
			::= { ccSystemHostsTable 1 }

		
		CcSystemHostsEntry ::=
			SEQUENCE { 
				ccSystemHostIndex
					INTEGER,
				ccSystemHostName
					DisplayString,
				ccSystemHostIPAddr
					IpAddress,
				ccSystemHostDomain
					DisplayString
			 }

		-- 1.3.6.1.4.1.388.6.1.7.3.1.1
		ccSystemHostIndex OBJECT-TYPE
			SYNTAX INTEGER (1..100)
			MAX-ACCESS not-accessible
			STATUS current
			DESCRIPTION
				"Index of specific System Host."
			::= { ccSystemHostsEntry 1 }

		
		-- 1.3.6.1.4.1.388.6.1.7.3.1.2
		ccSystemHostName OBJECT-TYPE
			SYNTAX DisplayString (SIZE (1..200))
			MAX-ACCESS read-only
			STATUS current
			DESCRIPTION
				"DNS name of specific System Host."
			::= { ccSystemHostsEntry 2 }

		
		-- 1.3.6.1.4.1.388.6.1.7.3.1.3
		ccSystemHostIPAddr OBJECT-TYPE
			SYNTAX IpAddress
			MAX-ACCESS read-write
			STATUS current
			DESCRIPTION
				"IP address of the System Host"
			::= { ccSystemHostsEntry 3 }

		
		-- 1.3.6.1.4.1.388.6.1.7.3.1.4
		ccSystemHostDomain OBJECT-TYPE
			SYNTAX DisplayString (SIZE (1..200))
			MAX-ACCESS read-write
			STATUS current
			DESCRIPTION
				"Domain Name of the System Host.
				Note that only the following characters are allowed in the domain name:
				0123456789ABCDEFGHIJKLMNOPQRSTUVWXYZabcdefghijklmnopqrstuvwxyz._-
				Also, '_' , '-' and '.' cannot be the first or last character of the domain name.
				
				If no Domain Name has been specified,
				then 'NA' is returned by the wireless switch."
			::= { ccSystemHostsEntry 4 }

		
		-- 1.3.6.1.4.1.388.6.1.8
		ccPolicyRCObjects OBJECT IDENTIFIER ::= { symbolCCSystem 8 }

		
		-- 1.3.6.1.4.1.388.6.1.8.1
		ccPolicyRCAddRemTable OBJECT-TYPE
			SYNTAX SEQUENCE OF CcPolicyRCAddRemEntry
			MAX-ACCESS not-accessible
			STATUS current
			DESCRIPTION
				"A list of objects used to add/remove items from
				the Restricted channels list"
			::= { ccPolicyRCObjects 1 }

		
		-- 1.3.6.1.4.1.388.6.1.8.1.1
		ccPolicyRCAddRemEntry OBJECT-TYPE
			SYNTAX CcPolicyRCAddRemEntry
			MAX-ACCESS not-accessible
			STATUS current
			DESCRIPTION
				"An entry in the table of RC Add Remove objects.
				The two indices are ccPolicyIndex and ccPolicyRadioType.
				ccPolicyIndex is taken from the ccPolicyTable, and specifies which 
				CCPolicy's Restricted Channel table is being accessed.
				ccPolicyRadioType is used to specify the type of the radio (A or B)
				to which the Restricted Channel table belongs"
			INDEX { ccPolicyIndex, ccPolicyRadioType }
			::= { ccPolicyRCAddRemTable 1 }

		
		CcPolicyRCAddRemEntry ::=
			SEQUENCE { 
				ccPolicyRadioType
					INTEGER,
				ccPolicyRCAdd
					DisplayString,
				ccPolicyRCRem
					DisplayString
			 }

		-- 1.3.6.1.4.1.388.6.1.8.1.1.1
		ccPolicyRadioType OBJECT-TYPE
			SYNTAX INTEGER (1..10)
			MAX-ACCESS not-accessible
			STATUS current
			DESCRIPTION
				"ccPolicyRadioType is used as one of the indicies
				to specify the type of the radio (A or B)
				   to which the Restricted Channel table belongs.
				   A value of 1 for this index denotes an 11a radio and 
				   2 denotes an 11b radio."
			::= { ccPolicyRCAddRemEntry 1 }

		
		-- 1.3.6.1.4.1.388.6.1.8.1.1.2
		ccPolicyRCAdd OBJECT-TYPE
			SYNTAX DisplayString (SIZE (1..44))
			MAX-ACCESS read-write
			STATUS current
			DESCRIPTION
				"Add an entry into the RC Table for this CCPolicy and radiotype.
				If you want to specify a reason for declaring a particular channel as a
				restricted channel, you can enter the data in this format:
				<Channel number, reason>. The 'reason' is optional (i.e. you can enter only the channel number)
				but the channel reason/description if entered, should not be more than 40 characters."
			::= { ccPolicyRCAddRemEntry 2 }

		
		-- 1.3.6.1.4.1.388.6.1.8.1.1.3
		ccPolicyRCRem OBJECT-TYPE
			SYNTAX DisplayString (SIZE (1..300))
			MAX-ACCESS read-write
			STATUS current
			DESCRIPTION
				"Remove an entry from the RC Table for this CCPolicy and radiotype.
				You just need to specify the channel number which you want to be removed
				from the table."
			::= { ccPolicyRCAddRemEntry 3 }

		
		-- 1.3.6.1.4.1.388.6.1.8.2
		ccPolicyRCTable OBJECT-TYPE
			SYNTAX SEQUENCE OF CcPolicyRCEntry
			MAX-ACCESS not-accessible
			STATUS current
			DESCRIPTION
				"A list of restricted channels and their descriptions.
				(Per CCPolicy, per RadioType)"
			::= { ccPolicyRCObjects 2 }

		
		-- 1.3.6.1.4.1.388.6.1.8.2.1
		ccPolicyRCEntry OBJECT-TYPE
			SYNTAX CcPolicyRCEntry
			MAX-ACCESS not-accessible
			STATUS current
			DESCRIPTION
				"An entry in the Restricted Channels table.
				The three indices are ccPolicyIndex,ccPolicyRadioType, and ccPolicyRcIndex.
				ccPolicyIndex is taken from the ccPolicyTable, and specifies which 
				CCPolicy's Restricted Channel table is being accessed.
				ccPolicyRadioType is used to specify the type of the radio (A or B)
				to which the Restricted Channel table belongs (index is 1 for 11a,
				and 2 for 11b).
				ccPolicyRcIndex specifies one particular listing in the Restricted Channels Table"
			INDEX { ccPolicyIndex, ccPolicyRadioType, ccPolicyRcIndex }
			::= { ccPolicyRCTable 1 }

		
		CcPolicyRCEntry ::=
			SEQUENCE { 
				ccPolicyRcIndex
					INTEGER,
				ccPolicyRCChannelDescr
					DisplayString
			 }

		-- 1.3.6.1.4.1.388.6.1.8.2.1.1
		ccPolicyRcIndex OBJECT-TYPE
			SYNTAX INTEGER (1..300)
			MAX-ACCESS not-accessible
			STATUS current
			DESCRIPTION
				"The index of the restricted channel"
			::= { ccPolicyRCEntry 1 }

		
		-- 1.3.6.1.4.1.388.6.1.8.2.1.2
		ccPolicyRCChannelDescr OBJECT-TYPE
			SYNTAX DisplayString (SIZE (1..44))
			MAX-ACCESS read-only
			STATUS current
			DESCRIPTION
				"The channel number and description,at this particular index
				in the Restricted channel table. The returned string is in the format
				<channel,description>. Note that if no description has been entered for 
				that particular channel, you will receive the reply as <channel,>, i.e. nothing
				in the description field"
			::= { ccPolicyRCEntry 2 }

		
		-- 1.3.6.1.4.1.388.6.1.9
		ccPolicyObject OBJECT IDENTIFIER ::= { symbolCCSystem 9 }

		
		-- 1.3.6.1.4.1.388.6.1.9.2
		ccPolicyAPPolicyTable OBJECT-TYPE
			SYNTAX SEQUENCE OF CcPolicyAPPolicyEntry
			MAX-ACCESS not-accessible
			STATUS current
			DESCRIPTION
				"Table of APPolicies per Wireless Switch Policy"
			::= { ccPolicyObject 2 }

		
		-- 1.3.6.1.4.1.388.6.1.9.2.1
		ccPolicyAPPolicyEntry OBJECT-TYPE
			SYNTAX CcPolicyAPPolicyEntry
			MAX-ACCESS not-accessible
			STATUS current
			DESCRIPTION
				"The entries of APPolicies per Wireless Switch Policy."
			INDEX { ccPolicyIndex, ccPolicyAPPolicyIndex }
			::= { ccPolicyAPPolicyTable 1 }

		
		CcPolicyAPPolicyEntry ::=
			SEQUENCE { 
				ccPolicyAPPolicyIndex
					INTEGER,
				ccPolicyAPPolicyName
					DisplayString
			 }

		-- 1.3.6.1.4.1.388.6.1.9.2.1.1
		ccPolicyAPPolicyIndex OBJECT-TYPE
			SYNTAX INTEGER (1..100)
			MAX-ACCESS not-accessible
			STATUS current
			DESCRIPTION
				"The index of the AP policy."
			::= { ccPolicyAPPolicyEntry 1 }
-- Mower: changed range from 0.. to 1..
		
		-- 1.3.6.1.4.1.388.6.1.9.2.1.2
		ccPolicyAPPolicyName OBJECT-TYPE
			SYNTAX DisplayString (SIZE (1..50))
			MAX-ACCESS read-only
			STATUS current
			DESCRIPTION
				"A list of AP policies applied for this Switch Policy."
			::= { ccPolicyAPPolicyEntry 2 }

		
--  1.3.6.1.4.1.388.6.2
		-- 1.3.6.1.4.1.388.6.2
		symbolCCInterfaces OBJECT IDENTIFIER ::= { symbolCC 2 }

		
--  1.3.6.1.4.1.388.6.2.1
		-- 1.3.6.1.4.1.388.6.2.1
		ccAPPolicyAddObj OBJECT-TYPE
			SYNTAX DisplayString (SIZE (1..50))
			MAX-ACCESS read-write
			STATUS current
			DESCRIPTION
				"Add one AP Policy object into the AP Policy table. The Maximum length of the AP Policy 
				Name can be 50 characters, Note that the following characters cannot be part 
				of Policy Name field, double quotes,',.,\,& and #."
			::= { symbolCCInterfaces 1 }

		
--  1.3.6.1.4.1.388.6.2.2
		-- 1.3.6.1.4.1.388.6.2.2
		ccAPPolicyRemObj OBJECT-TYPE
			SYNTAX DisplayString (SIZE (1..50))
			MAX-ACCESS read-write
			STATUS current
			DESCRIPTION
				"Remove one AP Policy object from the AP Policy table."
			::= { symbolCCInterfaces 2 }

		
--  1.3.6.1.4.1.388.6.2.3
		-- 1.3.6.1.4.1.388.6.2.3
		ccEPPAddObj OBJECT-TYPE
			SYNTAX DisplayString (SIZE (1..50))
			MAX-ACCESS read-write
			STATUS current
			DESCRIPTION
				"Add one Ethernet policy object into the EPP table. The Maximum length of the Ethernet Policy
				Name can be 50 characters,Note that the following characters cannot be part of 
				Ethernet Policy Name field, double quotes,',.,\,& and #."
			::= { symbolCCInterfaces 3 }

		
--  1.3.6.1.4.1.388.6.2.4
		-- 1.3.6.1.4.1.388.6.2.4
		ccEPPRemObj OBJECT-TYPE
			SYNTAX DisplayString (SIZE (1..50))
			MAX-ACCESS read-write
			STATUS current
			DESCRIPTION
				"Remove one Ethernet policy object from the EPP table. The Maximum length of the Ethernet Policy
				Name can be 50 characters,Note that the following characters cannot be part of 
				Ethernet Policy Name field, double quotes,',.,\,& and #."
			::= { symbolCCInterfaces 4 }

		
--  1.3.6.1.4.1.388.6.2.5
		-- 1.3.6.1.4.1.388.6.2.5
		ccAccessPortAddObj OBJECT-TYPE
			SYNTAX DisplayString (SIZE (1..255))
			MAX-ACCESS read-write
			STATUS current
			DESCRIPTION
				"Add an access port. The input string should have the following syntax:
				
				<dev_mac,dev_type,radio1_name,radio1_mac,radio2_name,radio2_mac>.
				dev_mac is the mac address of the Access Port's NIC. 
				dev_type must be one of 'ap300''ap200','ap100', 'ap3020' 'ap4131' or 'ap4121'. 
								
				For 'ap200' and ap300, radio1 will be considered to be of type 802.11a, and at least
				one such radio definitely needs to be specified. 
							
				For 'ap100' 'ap4131' or 'ap4121', only provide the radio1_name value, since there can 
				be only one radio on a 'ap100' 'ap4131' or 'ap4121' accessport, and that one radio
				definitely has the same MAC address as the device, and also, that one radio 
				is always an 802.11b radio. 
					
				Similarly, for a device of type 'ap3020', provide only radio1_name, since the
				FH radio will have the same MAC as that of the device.
								
				Note: The following characters cannot be part of radio1_name and radio2_name Name 
				field - ',.,,&, # and double quotes, 
				and the maximum characters allowed for each of these names are 50.
				
				few synatx examples are given below:- 
				To add AP100 :<dev_mac>,ap100,<radio_name>,<radio_mac>
				Note:radio_mac is optional for Ap100 
							
				To add AP3020-3021: <dev_mac>,ap3020,<radio_name>,<radio_mac>
				Note:radio mac is optioanl for AP3020
							
				To add AP300: <dev_mac>,ap300,<g_radio_name>,<g_mac>,<a_radio>,<a_mac>
				Note:One can add only 'g' radio also.
							
				To add AP200: <dev_mac>,ap200,<a_radio_name>,<a_mac>,<b_radio>,<b_mac>
				Note:One can add only 'a' radio also 
								
				To add AP4121:<dev_mac>,ap4121,<radio_name>,<radio_mac>
				Note:radio mac is optional for ap4121
								
				To add AP4131:<dev_mac>,ap4132,<radio_name>,<radio_mac>
				Note:radio mac is optional for ap4131
				 
				
				"
			::= { symbolCCInterfaces 5 }

		
--  1.3.6.1.4.1.388.6.2.6
		-- 1.3.6.1.4.1.388.6.2.6
		ccAccessPortRemObj OBJECT-TYPE
			SYNTAX DisplayString (SIZE (1..50))
			MAX-ACCESS read-write
			STATUS current
			DESCRIPTION
				"Remove an AccessPort
				 syntax :<port name> 
				
				 When a ap200/ap300 Access port is removed both the radio
				 macs are removed."
			::= { symbolCCInterfaces 6 }

		
		-- 1.3.6.1.4.1.388.6.2.7
		ccFWLanAddObj OBJECT-TYPE
			SYNTAX DisplayString (SIZE (1..50))
			MAX-ACCESS read-write
			STATUS current
			DESCRIPTION
				"Add a LAN to the system."
			::= { symbolCCInterfaces 7 }

		
-- 
-- 
		-- 1.3.6.1.4.1.388.6.2.8
		ccFWLanRemObj OBJECT-TYPE
			SYNTAX DisplayString (SIZE (1..50))
			MAX-ACCESS read-write
			STATUS current
			DESCRIPTION
				"Remove the LAN from the system."
			::= { symbolCCInterfaces 8 }

		
--  1.3.6.1.4.1.388.6.2.10
		-- 1.3.6.1.4.1.388.6.2.10
		ccAPTable OBJECT-TYPE
			SYNTAX SEQUENCE OF CcAPEntry
			MAX-ACCESS not-accessible
			STATUS current
			DESCRIPTION
				"The Table of AccessPorts."
			::= { symbolCCInterfaces 10 }

		
--  1.3.6.1.4.1.388.6.2.10.1
		-- 1.3.6.1.4.1.388.6.2.10.1
		ccAPEntry OBJECT-TYPE
			SYNTAX CcAPEntry
			MAX-ACCESS not-accessible
			STATUS current
			DESCRIPTION
				"An AccessPort Configuration entry."
			INDEX { ccRadioIndex }
			::= { ccAPTable 1 }

		
		CcAPEntry ::=
			SEQUENCE { 
				ccRadioIndex
					INTEGER,
				ccRadioName
					DisplayString,
				ccRadioDesc
					DisplayString,
				ccRadioOnlineStatus
					APOnlineStatus,
				ccRadioMAC
					DisplayString,
				ccDeviceMAC
					DisplayString,
				ccDeviceLocation
					DisplayString,
				ccRadioType
					DisplayString,
				ccRadioChannel
					DisplayString,
				ccRadioPower
					DisplayString,
				ccRadioPolicy
					DisplayString,
				ccDeviceNic
					INTEGER,
				ccDeviceType
					DisplayString,
				ccRadioCCAmode
					INTEGER,
				ccRadioCCAthresh
					INTEGER,
				ccRadioDiversity
					INTEGER,
				ccDeviceVlanid
					INTEGER,
				ccDeviceVlanTagsSeen
					DisplayString,
				ccRadioUptime
					DisplayString,
				ccRadioTxpps
					INTEGER,
				ccRadioMUs
					INTEGER,
				ccRadioGatherStatistics
					TruthValue,
				ccRadioReset
					TruthValue,
				ccDeviceClearSeenVlanTags
					TruthValue,
				ccDeviceReset
					TruthValue,
				ccRadioAuto
					TruthValue,
				ccRadioMUPower
					DisplayString,
				ccRadioProtection
					DisplayString,
				ccRadioShortSlot
					DisplayString,
				ccRadioAntenna
					DisplayString,
				ccRadioCurrentChannel
					DisplayString,
				ccRadioAllChannels
					DisplayString,
				ccRadioPowerdBm
					DisplayString,
				ccRadioCurrentPower
					DisplayString,
				ccRadioAllPower
					DisplayString,
				ccRadioMUPowerdBm
					DisplayString,
				ccRadioAntCorrection
					INTEGER,
				ccRadioIndoor
					DisplayString,
				ccRadioDFS
					DisplayString,
				ccRadioTPC
					DisplayString,
				ccRadioRadarChannels
					DisplayString,
				ccDetectorAp
					TruthValue,
				ccRadioMaxMUs
					INTEGER,
				ccSimulateRadar
					DoActionNow,
				ccRadioUser802x
					OCTET STRING
			 }

--  1.3.6.1.4.1.388.6.2.10.1.28
		-- 1.3.6.1.4.1.388.6.2.10.1.28
		ccRadioIndex OBJECT-TYPE
			SYNTAX INTEGER (1..300)
			MAX-ACCESS not-accessible
			STATUS current
			DESCRIPTION
				"The Index for the Access port."
			::= { ccAPEntry 28 }

		
--  Mower: changed range from 0.. to 1..
-- 1.3.6.1.4.1.388.6.2.10.1.29
		-- 1.3.6.1.4.1.388.6.2.10.1.29
		ccRadioName OBJECT-TYPE
			SYNTAX DisplayString (SIZE (1..50))
			MAX-ACCESS read-write
			STATUS current
			DESCRIPTION
				"The Name of the Access port. The Maximum length of the Radio Name 
				can be 50 characters. Note that the following characters cannot be part 
				of Radio Name field - ',.,\,&, # and double quotes"
			::= { ccAPEntry 29 }

		
--  1.3.6.1.4.1.388.6.2.10.1.30
		-- 1.3.6.1.4.1.388.6.2.10.1.30
		ccRadioDesc OBJECT-TYPE
			SYNTAX DisplayString (SIZE (0..128))
			MAX-ACCESS read-write
			STATUS current
			DESCRIPTION
				"The description of the Access port. The Maximum length of the description 
				can be 128 characters. Note that the following characters cannot be part 
				of description - ',# and double quotes."
			::= { ccAPEntry 30 }

		
--  1.3.6.1.4.1.388.6.2.10.1.31
		-- 1.3.6.1.4.1.388.6.2.10.1.31
		ccRadioOnlineStatus OBJECT-TYPE
			SYNTAX APOnlineStatus
			MAX-ACCESS read-only
			STATUS current
			DESCRIPTION
				"Online status for this Access port.
				0(zero) means 'unavailable' or non-existent.
				1 means 'active',, i.e. functional 
				2 means 'inactive',existent but not functional.
				3 means 'alert' indicating that some errors have occured with
				   this accessport. For example, a time-out or a reset."
			::= { ccAPEntry 31 }

		
--  1.3.6.1.4.1.388.6.2.10.1.32
		-- 1.3.6.1.4.1.388.6.2.10.1.32
		ccRadioMAC OBJECT-TYPE
			SYNTAX DisplayString
			MAX-ACCESS read-only
			STATUS current
			DESCRIPTION
				"The MAC address of this radio."
			::= { ccAPEntry 32 }

		
--  1.3.6.1.4.1.388.6.2.10.1.33
		-- 1.3.6.1.4.1.388.6.2.10.1.33
		ccDeviceMAC OBJECT-TYPE
			SYNTAX DisplayString
			MAX-ACCESS read-only
			STATUS current
			DESCRIPTION
				"The MAC address of the device to which this radio belongs."
			::= { ccAPEntry 33 }

		
--  1.3.6.1.4.1.388.6.2.10.1.34
		-- 1.3.6.1.4.1.388.6.2.10.1.34
		ccDeviceLocation OBJECT-TYPE
			SYNTAX DisplayString (SIZE (0..50))
			MAX-ACCESS read-write
			STATUS current
			DESCRIPTION
				"The location of this device."
			::= { ccAPEntry 34 }

		
--  1.3.6.1.4.1.388.6.2.10.1.35
		-- 1.3.6.1.4.1.388.6.2.10.1.35
		ccRadioType OBJECT-TYPE
			SYNTAX DisplayString (SIZE (1..32))
			MAX-ACCESS read-only
			STATUS current
			DESCRIPTION
				"The type of this radio. 'A' or 'B' denote 802.11a and 802.11b respectively.
				'FH' denotes an FH radio."
			::= { ccAPEntry 35 }

		
--  1.3.6.1.4.1.388.6.2.10.1.36
		-- 1.3.6.1.4.1.388.6.2.10.1.36
		ccRadioChannel OBJECT-TYPE
			SYNTAX DisplayString (SIZE (1..200))
			MAX-ACCESS read-write
			STATUS current
			DESCRIPTION
				"The channel on which this radio is operating. 
				Valid values for 11a are:34,36,38,40...64.
				Valid values for 11b are:1,2,3,...14.
				Also, 'auto-once' is a valid channel if you want switch to choose
				channel automaticlly. 'auto-always' and 'random' are also valid channels.
				Note that this property is not applicable to FH radios. 
				So a GET returns the appropriate message, and a SET fails."
			::= { ccAPEntry 36 }

		
--  1.3.6.1.4.1.388.6.2.10.1.37
		-- 1.3.6.1.4.1.388.6.2.10.1.37
		ccRadioPower OBJECT-TYPE
			SYNTAX DisplayString (SIZE (1..20))
			MAX-ACCESS read-only
			STATUS deprecated
			DESCRIPTION
				"The power on which this radio is operating.
				Valid values for both 11a and 11b are :1,5,15,30,Full."
			::= { ccAPEntry 37 }

		
--  1.3.6.1.4.1.388.6.2.10.1.38
		-- 1.3.6.1.4.1.388.6.2.10.1.38
		ccRadioPolicy OBJECT-TYPE
			SYNTAX DisplayString (SIZE (0..50))
			MAX-ACCESS read-write
			STATUS current
			DESCRIPTION
				"The policy governing this radio.
				To clear the existing policy, leave the input blank."
			::= { ccAPEntry 38 }

		
--  1.3.6.1.4.1.388.6.2.10.1.39
		-- 1.3.6.1.4.1.388.6.2.10.1.39
		ccDeviceNic OBJECT-TYPE
			SYNTAX INTEGER (1..20)
			MAX-ACCESS read-only
			STATUS current
			DESCRIPTION
				"The NIC number on which this device is connected to the WS5000 wireless Switch.
				Valid Values are 1 or 2"
			::= { ccAPEntry 39 }

		
--  1.3.6.1.4.1.388.6.2.10.1.40
		-- 1.3.6.1.4.1.388.6.2.10.1.40
		ccDeviceType OBJECT-TYPE
			SYNTAX DisplayString (SIZE (1..32))
			MAX-ACCESS read-only
			STATUS current
			DESCRIPTION
				"The type of the device. Expect either of 'AP200','AP100','AP300','AP4121','AP3020/3021' as the value."
			::= { ccAPEntry 40 }

		
--  1.3.6.1.4.1.388.6.2.10.1.41
		-- 1.3.6.1.4.1.388.6.2.10.1.41
		ccRadioCCAmode OBJECT-TYPE
			SYNTAX INTEGER (0..3)
			MAX-ACCESS read-write
			STATUS current
			DESCRIPTION
				"The CCA Mode for the Access port."
			::= { ccAPEntry 41 }

		
--  1.3.6.1.4.1.388.6.2.10.1.42
		-- 1.3.6.1.4.1.388.6.2.10.1.42
		ccRadioCCAthresh OBJECT-TYPE
			SYNTAX INTEGER (0..31)
			MAX-ACCESS read-write
			STATUS current
			DESCRIPTION
				"The CCA threshold for the Access port."
			::= { ccAPEntry 42 }

		
--  1.3.6.1.4.1.388.6.2.10.1.43
		-- 1.3.6.1.4.1.388.6.2.10.1.43
		ccRadioDiversity OBJECT-TYPE
			SYNTAX INTEGER (0..10)
			MAX-ACCESS read-write
			STATUS current
			DESCRIPTION
				"The antenna setting for the Access Port. 
				Valid values are 0,1 and 2. 0 indicates Full, 1 indicates primary,
				and 2 indicates secondary."
			::= { ccAPEntry 43 }

		
--  1.3.6.1.4.1.388.6.2.10.1.44
		-- 1.3.6.1.4.1.388.6.2.10.1.44
		ccDeviceVlanid OBJECT-TYPE
			SYNTAX INTEGER (1..4095)
			MAX-ACCESS read-only
			STATUS current
			DESCRIPTION
				"The VLAN id for the Access port.
				"
			::= { ccAPEntry 44 }

		
--  1.3.6.1.4.1.388.6.2.10.1.45
		-- 1.3.6.1.4.1.388.6.2.10.1.45
		ccDeviceVlanTagsSeen OBJECT-TYPE
			SYNTAX DisplayString (SIZE (1..100))
			MAX-ACCESS read-only
			STATUS current
			DESCRIPTION
				"The Vlan Tags seen by this device."
			::= { ccAPEntry 45 }

		
--  1.3.6.1.4.1.388.6.2.10.1.46
		-- 1.3.6.1.4.1.388.6.2.10.1.46
		ccRadioUptime OBJECT-TYPE
			SYNTAX DisplayString (SIZE (1..32))
			MAX-ACCESS read-only
			STATUS current
			DESCRIPTION
				"The time for which this radio has been up."
			::= { ccAPEntry 46 }

		
--  1.3.6.1.4.1.388.6.2.10.1.47
		-- 1.3.6.1.4.1.388.6.2.10.1.47
		ccRadioTxpps OBJECT-TYPE
			SYNTAX INTEGER (1..100000)
			MAX-ACCESS read-only
			STATUS current
			DESCRIPTION
				"The number of packets transmitted per second between AP and MU."
			::= { ccAPEntry 47 }

		
--  1.3.6.1.4.1.388.6.2.10.1.48
		-- 1.3.6.1.4.1.388.6.2.10.1.48
		ccRadioMUs OBJECT-TYPE
			SYNTAX INTEGER (0..200)
			MAX-ACCESS read-only
			STATUS current
			DESCRIPTION
				"The number of MUs associated with this radio."
			::= { ccAPEntry 48 }

		
--  1.3.6.1.4.1.388.6.2.10.1.49
		-- 1.3.6.1.4.1.388.6.2.10.1.49
		ccRadioGatherStatistics OBJECT-TYPE
			SYNTAX TruthValue
			MAX-ACCESS read-write
			STATUS current
			DESCRIPTION
				"true(1)/false(2) to turn on/off the functionality of gathering AP
				statistic data."
			::= { ccAPEntry 49 }

		
--  1.3.6.1.4.1.388.6.2.10.1.50
		-- 1.3.6.1.4.1.388.6.2.10.1.50
		ccRadioReset OBJECT-TYPE
			SYNTAX TruthValue
			MAX-ACCESS read-write
			STATUS current
			DESCRIPTION
				"A 'true' as input will reset the Radio. 
				'false' is not an acceptable input. 
				Note that a Reset message can be sent out only if
				the radio is in 'active' state.
				This object is SET-only."
			::= { ccAPEntry 50 }

		
--  1.3.6.1.4.1.388.6.2.10.1.51
		-- 1.3.6.1.4.1.388.6.2.10.1.51
		ccDeviceClearSeenVlanTags OBJECT-TYPE
			SYNTAX TruthValue
			MAX-ACCESS read-write
			STATUS deprecated
			DESCRIPTION
				"true(1) will clear the seen Vlans"
			::= { ccAPEntry 51 }

		
--  1.3.6.1.4.1.388.6.2.10.1.52
		-- 1.3.6.1.4.1.388.6.2.10.1.52
		ccDeviceReset OBJECT-TYPE
			SYNTAX TruthValue
			MAX-ACCESS read-write
			STATUS current
			DESCRIPTION
				"A 'true' as input will reset the Device. 
				'false' is not an acceptable input.
				This object is SET-only."
			::= { ccAPEntry 52 }

		
--  1.3.6.1.4.1.388.6.2.10.1.53
		-- 1.3.6.1.4.1.388.6.2.10.1.53
		ccRadioAuto OBJECT-TYPE
			SYNTAX TruthValue
			MAX-ACCESS read-only
			STATUS deprecated
			DESCRIPTION
				"'true' enables ACS-on-adoption for this
				particular radio.'false' disables it."
			::= { ccAPEntry 53 }

		
--  1.3.6.1.4.1.388.6.2.10.1.54
		-- 1.3.6.1.4.1.388.6.2.10.1.54
		ccRadioMUPower OBJECT-TYPE
			SYNTAX DisplayString (SIZE (1..8))
			MAX-ACCESS read-only
			STATUS deprecated
			DESCRIPTION
				"The power value to be put in the beacon of this radio.
				Valid values are : 1,5,15,30,Full,default.
				Note that 'default' as input causes the beacon to have the 
				same power level as this radio."
			::= { ccAPEntry 54 }

		
		-- 1.3.6.1.4.1.388.6.2.10.1.55
		ccRadioProtection OBJECT-TYPE
			SYNTAX DisplayString (SIZE (1..5))
			MAX-ACCESS read-only
			STATUS current
			DESCRIPTION
				"Defines whether 'Protection' is On or Off."
			::= { ccAPEntry 55 }

		
		-- 1.3.6.1.4.1.388.6.2.10.1.56
		ccRadioShortSlot OBJECT-TYPE
			SYNTAX DisplayString (SIZE (1..5))
			MAX-ACCESS read-only
			STATUS current
			DESCRIPTION
				"Defines whether Short Slot is On or Off."
			::= { ccAPEntry 56 }

		
		-- 1.3.6.1.4.1.388.6.2.10.1.57
		ccRadioAntenna OBJECT-TYPE
			SYNTAX DisplayString (SIZE (1..10))
			MAX-ACCESS read-only
			STATUS current
			DESCRIPTION
				"Defines whether antenna type is internal, external or unknown."
			::= { ccAPEntry 57 }

		
		-- 1.3.6.1.4.1.388.6.2.10.1.58
		ccRadioCurrentChannel OBJECT-TYPE
			SYNTAX DisplayString (SIZE (1..200))
			MAX-ACCESS read-only
			STATUS current
			DESCRIPTION
				"Current channel."
			::= { ccAPEntry 58 }

		
		-- 1.3.6.1.4.1.388.6.2.10.1.59
		ccRadioAllChannels OBJECT-TYPE
			SYNTAX DisplayString (SIZE (1..200))
			MAX-ACCESS read-only
			STATUS current
			DESCRIPTION
				"A comma seperated list of all channels valid for this radio."
			::= { ccAPEntry 59 }

		
		-- 1.3.6.1.4.1.388.6.2.10.1.60
		ccRadioPowerdBm OBJECT-TYPE
			SYNTAX DisplayString (SIZE (1..20))
			MAX-ACCESS read-write
			STATUS current
			DESCRIPTION
				"The power on which the radio is configured to operate in dBm.
				Valid range depends on the country and radio configuration.
				It is as defined in the 'ccRadioAllPower' object."
			::= { ccAPEntry 60 }

		
		-- 1.3.6.1.4.1.388.6.2.10.1.61
		ccRadioCurrentPower OBJECT-TYPE
			SYNTAX DisplayString (SIZE (1..20))
			MAX-ACCESS read-only
			STATUS current
			DESCRIPTION
				"The power on which the radio is currently operating in dBm."
			::= { ccAPEntry 61 }

		
		-- 1.3.6.1.4.1.388.6.2.10.1.62
		ccRadioAllPower OBJECT-TYPE
			SYNTAX DisplayString (SIZE (1..20))
			MAX-ACCESS read-only
			STATUS current
			DESCRIPTION
				"The valid power range for the radio in the format 'min_power-max_power'."
			::= { ccAPEntry 62 }

		
		-- 1.3.6.1.4.1.388.6.2.10.1.63
		ccRadioMUPowerdBm OBJECT-TYPE
			SYNTAX DisplayString (SIZE (1..32))
			MAX-ACCESS read-write
			STATUS current
			DESCRIPTION
				"Power level adjustment for MU. The valid range is -20 to 20 dB."
			::= { ccAPEntry 63 }

		
		-- 1.3.6.1.4.1.388.6.2.10.1.64
		ccRadioAntCorrection OBJECT-TYPE
			SYNTAX INTEGER (0..1)
			MAX-ACCESS read-write
			STATUS current
			DESCRIPTION
				"Antenna correction factor. The valid range is -20 to 20dBi.
				Note:This OID is supported only for AP300 device 
				     with external antenna "
			::= { ccAPEntry 64 }

		
		-- 1.3.6.1.4.1.388.6.2.10.1.65
		ccRadioIndoor OBJECT-TYPE
			SYNTAX DisplayString (SIZE (1..20))
			MAX-ACCESS read-write
			STATUS current
			DESCRIPTION
				"Radio location indoor or outdoor. Valid values are 'in' or 'out'.
				Note:This OID is supported only for AP300 device 
				with external antenna "
			::= { ccAPEntry 65 }

		
		-- 1.3.6.1.4.1.388.6.2.10.1.66
		ccRadioDFS OBJECT-TYPE
			SYNTAX DisplayString (SIZE (1..32))
			MAX-ACCESS read-only
			STATUS current
			DESCRIPTION
				"DFS status. Valid values are:off,on,active,channel scan.
				Supported only for 11a radio."
			::= { ccAPEntry 66 }

		
		-- 1.3.6.1.4.1.388.6.2.10.1.67
		ccRadioTPC OBJECT-TYPE
			SYNTAX DisplayString (SIZE (1..32))
			MAX-ACCESS read-only
			STATUS current
			DESCRIPTION
				"TPC status. Valid values are: off,on.
				Supported only for 11a radio."
			::= { ccAPEntry 67 }

		
		-- 1.3.6.1.4.1.388.6.2.10.1.68
		ccRadioRadarChannels OBJECT-TYPE
			SYNTAX DisplayString (SIZE (1..200))
			MAX-ACCESS read-only
			STATUS current
			DESCRIPTION
				"A comma seperated list of all channels with timestamps where radar was detected."
			::= { ccAPEntry 68 }

		
		-- 1.3.6.1.4.1.388.6.2.10.1.69
		ccDetectorAp OBJECT-TYPE
			SYNTAX TruthValue
			MAX-ACCESS read-write
			STATUS current
			DESCRIPTION
				"If this is enabled, the switch uses this AP to 
				detect Rogue APs."
			::= { ccAPEntry 69 }

		
		-- 1.3.6.1.4.1.388.6.2.10.1.70
		ccRadioMaxMUs OBJECT-TYPE
			SYNTAX INTEGER (1..256)
			MAX-ACCESS read-write
			STATUS current
			DESCRIPTION
				"The number of maximum MUs for the Access port"
			::= { ccAPEntry 70 }

		
		-- 1.3.6.1.4.1.388.6.2.10.1.71
		ccSimulateRadar OBJECT-TYPE
			SYNTAX DoActionNow
			MAX-ACCESS read-write
			STATUS current
			DESCRIPTION
				"True(1) value will set simulateradar. 
				Setting it true sets the Dwell time value.
								
				Note: A get over it always return idealState(2) and
				      this OID is supported only for AP300 device type
				      A set operation over other device type's will
				      return Not writeable
				"
			::= { ccAPEntry 71 }

		
		-- 1.3.6.1.4.1.388.6.2.10.1.72
		ccRadioUser802x OBJECT-TYPE
			SYNTAX OCTET STRING
			MAX-ACCESS read-write
			STATUS current
			DESCRIPTION
				"Set the 802.1x user name and password
					Syntax: <user name>,<password>
								
				Note: This OID is supported only for AP300 device type
				      The maximum length of user and password is 32 each.
				 
				"
			::= { ccAPEntry 72 }

		
--  1.3.6.1.4.1.388.6.2.11
		-- 1.3.6.1.4.1.388.6.2.11
		ccAPPolicyTable OBJECT-TYPE
			SYNTAX SEQUENCE OF CcAPPolicyEntry
			MAX-ACCESS not-accessible
			STATUS current
			DESCRIPTION
				"APPolicy Table."
			::= { symbolCCInterfaces 11 }

		
--  1.3.6.1.4.1.388.6.2.11.1
		-- 1.3.6.1.4.1.388.6.2.11.1
		ccAPPolicyEntry OBJECT-TYPE
			SYNTAX CcAPPolicyEntry
			MAX-ACCESS not-accessible
			STATUS current
			DESCRIPTION
				"An entry in this table indicates the interface policy information."
			INDEX { ccAPPolicyIndex }
			::= { ccAPPolicyTable 1 }

		
		CcAPPolicyEntry ::=
			SEQUENCE { 
				ccAPPolicyIndex
					INTEGER,
				ccAPPolicyName
					DisplayString,
				ccAPPolicyDesc
					DisplayString,
				ccAPPolicyPreAmble
					DisplayString,
				ccAPPolicyBeaconInterval
					INTEGER,
				ccAPPolicyRTSThreshold
					INTEGER,
				ccAPPolicyDTIM
					INTEGER,
				ccAPPolicyBasicRates11a
					DisplayString,
				ccAPPolicySupportedRates11a
					DisplayString,
				ccAPPolicyBasicRates11b
					DisplayString,
				ccAPPolicySupportedRates11b
					DisplayString,
				ccAPPolicyBasicRatesFH
					DisplayString,
				ccAPPolicySupportedRatesFH
					DisplayString,
				ccAPPolicyBasicRates11g
					DisplayString,
				ccAPPolicySupportedRates11g
					DisplayString,
				ccAPPolicyNonSpectrumMgmt
					DisplayString,
				ccAPPolicyAddAllWlan
					DisplayString,
				ccAPPolicyRemAllWlan
					DisplayString,
				ccAPPolicyWMEEnable
					DisplayString,
				ccAPPolicyWMEProfile
					DisplayString,
				ccAPPolicyDTIM2
					INTEGER,
				ccAPPolicyDTIM3
					INTEGER,
				ccAPPolicyDTIM4
					INTEGER
			 }

--  1.3.6.1.4.1.388.6.2.11.1.1
		-- 1.3.6.1.4.1.388.6.2.11.1.1
		ccAPPolicyIndex OBJECT-TYPE
			SYNTAX INTEGER (1..100)
			MAX-ACCESS not-accessible
			STATUS current
			DESCRIPTION
				"The index of the AP policy."
			::= { ccAPPolicyEntry 1 }

		
--  Mower: changed range from 0.. to 1..
-- 1.3.6.1.4.1.388.6.2.11.1.2
		-- 1.3.6.1.4.1.388.6.2.11.1.2
		ccAPPolicyName OBJECT-TYPE
			SYNTAX DisplayString
			MAX-ACCESS read-write
			STATUS current
			DESCRIPTION
				"The name of the policy. The Maximum length of the Policy Name 
				can be 50 characters, Note that the following characters cannot be part 
				of Policy Name field, double quotes,',.,\,& and #."
			::= { ccAPPolicyEntry 2 }

		
--  1.3.6.1.4.1.388.6.2.11.1.3
		-- 1.3.6.1.4.1.388.6.2.11.1.3
		ccAPPolicyDesc OBJECT-TYPE
			SYNTAX DisplayString (SIZE (0..128))
			MAX-ACCESS read-write
			STATUS current
			DESCRIPTION
				"The description of the AP policy. The Maximum length of the description 
				can be 128 characters. Note that the following characters cannot be part 
				of description double quotes,' and #"
			::= { ccAPPolicyEntry 3 }

		
--  1.3.6.1.4.1.388.6.2.11.1.10
		-- 1.3.6.1.4.1.388.6.2.11.1.10
		ccAPPolicyPreAmble OBJECT-TYPE
			SYNTAX DisplayString (SIZE (4..5))
			MAX-ACCESS read-write
			STATUS current
			DESCRIPTION
				"Long/Short preamble feature for the WLANs in this APPolicy."
			::= { ccAPPolicyEntry 10 }

		
--  1.3.6.1.4.1.388.6.2.11.1.11
		-- 1.3.6.1.4.1.388.6.2.11.1.11
		ccAPPolicyBeaconInterval OBJECT-TYPE
			SYNTAX INTEGER (20..1000)
			MAX-ACCESS read-write
			STATUS current
			DESCRIPTION
				"The interval at which beacons are transmitted.
				Valid values are between 20 to 1000"
			::= { ccAPPolicyEntry 11 }

		
--  1.3.6.1.4.1.388.6.2.11.1.12
		-- 1.3.6.1.4.1.388.6.2.11.1.12
		ccAPPolicyRTSThreshold OBJECT-TYPE
			SYNTAX INTEGER (0..2347)
			MAX-ACCESS read-write
			STATUS current
			DESCRIPTION
				"The RTS (Request To Send) threshold for this WLAN.
				This threshold means that any unicast data or management frames 
				larger than this setting must be transmitted using the RTS/CTS 
				(Clear to Send) handshake exchange. By default, the value is 2347,
				which has the effect of deactivating RTS/CTS clearing before
				transmission. Setting the object to 0 activates the RTS/CTS 
				handshake before every transmission. 
				The valid values are from 0 to 2437."
			::= { ccAPPolicyEntry 12 }

		
--  1.3.6.1.4.1.388.6.2.11.1.13
		-- 1.3.6.1.4.1.388.6.2.11.1.13
		ccAPPolicyDTIM OBJECT-TYPE
			SYNTAX INTEGER (0..20)
			MAX-ACCESS read-write
			STATUS current
			DESCRIPTION
				"This setting, always a multiple of the beacon period, determines 
				how often the beacon contains a delivery traffic indication message(DTIM). 
				The DTIM tells power-save client devices that a packet is waiting 
				for them.
				Valid values are from 1 to 20, both inclusive.
				"
			::= { ccAPPolicyEntry 13 }

		
--  1.3.6.1.4.1.388.6.2.11.1.14
		-- 1.3.6.1.4.1.388.6.2.11.1.14
		ccAPPolicyBasicRates11a OBJECT-TYPE
			SYNTAX DisplayString (SIZE (1..32))
			MAX-ACCESS read-write
			STATUS current
			DESCRIPTION
				"The Basic Rate set for 11a radios which shall be governed by this policy.
				Valid values could be any combination of 6,9,12,18,24,36,48,54."
			::= { ccAPPolicyEntry 14 }

		
--  1.3.6.1.4.1.388.6.2.11.1.15
		-- 1.3.6.1.4.1.388.6.2.11.1.15
		ccAPPolicySupportedRates11a OBJECT-TYPE
			SYNTAX DisplayString (SIZE (1..32))
			MAX-ACCESS read-write
			STATUS current
			DESCRIPTION
				"The Supported Rate set for 11a radios which shall be governed by this policy.
				Valid values could be any combination of 6,9,12,18,24,36,48,54"
			::= { ccAPPolicyEntry 15 }

		
--  1.3.6.1.4.1.388.6.2.11.1.16
		-- 1.3.6.1.4.1.388.6.2.11.1.16
		ccAPPolicyBasicRates11b OBJECT-TYPE
			SYNTAX DisplayString (SIZE (1..32))
			MAX-ACCESS read-write
			STATUS current
			DESCRIPTION
				"The Basic Rate set for 11b radios which shall be governed by this policy.
				Valid values are any combination of 1,2,5.5,11"
			::= { ccAPPolicyEntry 16 }

		
--  1.3.6.1.4.1.388.6.2.11.1.17
		-- 1.3.6.1.4.1.388.6.2.11.1.17
		ccAPPolicySupportedRates11b OBJECT-TYPE
			SYNTAX DisplayString (SIZE (1..32))
			MAX-ACCESS read-write
			STATUS current
			DESCRIPTION
				"The Supported Rate set for 11b radios which shall be governed by this policy.
				Valid values are any combination of 1,2,5.5,11"
			::= { ccAPPolicyEntry 17 }

		
--  1.3.6.1.4.1.388.6.2.11.1.18
		-- 1.3.6.1.4.1.388.6.2.11.1.18
		ccAPPolicyBasicRatesFH OBJECT-TYPE
			SYNTAX DisplayString (SIZE (1..32))
			MAX-ACCESS read-write
			STATUS current
			DESCRIPTION
				"The Basic Rate set for FH radios which shall be governed by this policy.
				Valid values are any combination of 1 and 2"
			::= { ccAPPolicyEntry 18 }

		
--  1.3.6.1.4.1.388.6.2.11.1.19
		-- 1.3.6.1.4.1.388.6.2.11.1.19
		ccAPPolicySupportedRatesFH OBJECT-TYPE
			SYNTAX DisplayString (SIZE (1..32))
			MAX-ACCESS read-write
			STATUS current
			DESCRIPTION
				"The Supported Rate set for FH radios which shall be governed by this policy.
				Valid values are any combination of 1 and 2, or blank"
			::= { ccAPPolicyEntry 19 }

		
		-- 1.3.6.1.4.1.388.6.2.11.1.20
		ccAPPolicyBasicRates11g OBJECT-TYPE
			SYNTAX DisplayString (SIZE (1..32))
			MAX-ACCESS read-write
			STATUS current
			DESCRIPTION
				"The Basic Rate set for 11g radios that shall be governed by this policy. 
				Valid values could be any combination of 1,2,5.5,11,6, 9,12,18,24,36,48,54."
			::= { ccAPPolicyEntry 20 }

		
		-- 1.3.6.1.4.1.388.6.2.11.1.21
		ccAPPolicySupportedRates11g OBJECT-TYPE
			SYNTAX DisplayString (SIZE (1..32))
			MAX-ACCESS read-write
			STATUS current
			DESCRIPTION
				"The Supported Rate set for 11g radios that shall be governed by this policy. 
				Valid values could be any combination of 1,2,5.5,11,6, 9,12,18,24,36,48,54 or blank."
			::= { ccAPPolicyEntry 21 }

		
		-- 1.3.6.1.4.1.388.6.2.11.1.22
		ccAPPolicyNonSpectrumMgmt OBJECT-TYPE
			SYNTAX DisplayString (SIZE (1..32))
			MAX-ACCESS read-write
			STATUS current
			DESCRIPTION
				"Allow non DFC/TPC MU to associate when spectrum management 
				is required. Valid values:true,false."
			::= { ccAPPolicyEntry 22 }

		
		-- 1.3.6.1.4.1.388.6.2.11.1.23
		ccAPPolicyAddAllWlan OBJECT-TYPE
			SYNTAX DisplayString (SIZE (1..50))
			MAX-ACCESS read-write
			STATUS current
			DESCRIPTION
				"Add a WLAN to a Access Port Policy, WLAN added should be a valid WLAN and should
				not have already been added to this policy. Upto 16 WLANs can be added to a AP Policy.
				A get on this object returns nothing. The WLAN added will be added to all the mappings.
				Use ccAPPolicyAddRemWLAN table for select/unselect a WLAN for mapping, and ccAPPolicyWLANTable
				for bandwith, bss etc."
			::= { ccAPPolicyEntry 23 }

		
		-- 1.3.6.1.4.1.388.6.2.11.1.24
		ccAPPolicyRemAllWlan OBJECT-TYPE
			SYNTAX DisplayString (SIZE (1..50))
			MAX-ACCESS read-write
			STATUS current
			DESCRIPTION
				"Removes a WLAN from a Access Port Policy. The WLAN to be removed should have already
				been added to this policy. Thw WLAN will be removed from all the mappings and the 
				corresponding primary settings will be reset."
			::= { ccAPPolicyEntry 24 }

		
		-- 1.3.6.1.4.1.388.6.2.11.1.25
		ccAPPolicyWMEEnable OBJECT-TYPE
			SYNTAX DisplayString
			MAX-ACCESS read-write
			STATUS current
			DESCRIPTION
				"Description.
				 Enable/Disable of WME for APPolicy"
			::= { ccAPPolicyEntry 25 }

		
		-- 1.3.6.1.4.1.388.6.2.11.1.26
		ccAPPolicyWMEProfile OBJECT-TYPE
			SYNTAX DisplayString
			MAX-ACCESS read-write
			STATUS current
			DESCRIPTION
				"Description.
				WME Profile of APpolicy."
			::= { ccAPPolicyEntry 26 }

		
		-- 1.3.6.1.4.1.388.6.2.11.1.27
		ccAPPolicyDTIM2 OBJECT-TYPE
			SYNTAX INTEGER (1..20)
			MAX-ACCESS read-write
			STATUS current
			DESCRIPTION
				"Description."
			::= { ccAPPolicyEntry 27 }

		
		-- 1.3.6.1.4.1.388.6.2.11.1.28
		ccAPPolicyDTIM3 OBJECT-TYPE
			SYNTAX INTEGER (1..20)
			MAX-ACCESS read-write
			STATUS current
			DESCRIPTION
				"Description."
			::= { ccAPPolicyEntry 28 }

		
		-- 1.3.6.1.4.1.388.6.2.11.1.29
		ccAPPolicyDTIM4 OBJECT-TYPE
			SYNTAX INTEGER (1..20)
			MAX-ACCESS read-write
			STATUS current
			DESCRIPTION
				"Description."
			::= { ccAPPolicyEntry 29 }

		
--  1.3.6.1.4.1.388.6.2.12
		-- 1.3.6.1.4.1.388.6.2.12
		ccEPTable OBJECT-TYPE
			SYNTAX SEQUENCE OF CcEPEntry
			MAX-ACCESS not-accessible
			STATUS current
			DESCRIPTION
				"EtherPorts entries."
			::= { symbolCCInterfaces 12 }

		
--  1.3.6.1.4.1.388.6.2.12.1
		-- 1.3.6.1.4.1.388.6.2.12.1
		ccEPEntry OBJECT-TYPE
			SYNTAX CcEPEntry
			MAX-ACCESS not-accessible
			STATUS current
			DESCRIPTION
				"An ethernet port configuration entry."
			INDEX { ccEPIndex }
			::= { ccEPTable 1 }

		
		CcEPEntry ::=
			SEQUENCE { 
				ccEPIndex
					INTEGER,
				ccEPNic
					INTEGER,
				ccEPName
					DisplayString,
				ccEPDesc
					DisplayString,
				ccEPMacAddr
					DisplayString,
				ccEPEnable
					DisplayString,
				ccEPSpeed
					INTEGER,
				ccEPEnableDHCP
					TruthValue,
				ccEPIPAddr
					IpAddress,
				ccEPNetMask
					IpAddress,
				ccEPDnsCount
					INTEGER,
				ccEPDnsList
					DisplayString,
				ccEPPrimaryVid
					INTEGER,
				ccEPOnline
					TruthValue,
				ccEPDisplayName
					DisplayString,
				ccEPUptime
					DisplayString,
				ccEPTx
					Counter32,
				ccEPRx
					Counter32,
				ccEPDomain
					DisplayString,
				ccEPGateway
					IpAddress,
				ccEPCFGMode
					DisplayString,
				ccEPDuplex
					DisplayString,
				ccEPMode
					DisplayString,
				ccEPDhcpPriVlan
					TruthValue,
				ccEPDDNSStatus
					TruthValue,
				ccEPDDNSttl
					Integer32,
				ccEPDDNSUpdateAll
					DisplayString,
				ccEPDDNSMUserStatus
					TruthValue,
				ccEPDDNSDomainName
					DisplayString
			 }

--  1.3.6.1.4.1.388.6.2.12.1.1
		-- 1.3.6.1.4.1.388.6.2.12.1.1
		ccEPIndex OBJECT-TYPE
			SYNTAX INTEGER (1..100)
			MAX-ACCESS read-only
			STATUS current
			DESCRIPTION
				"The Index for the Ethernet port."
			::= { ccEPEntry 1 }

		
--  Mower: changed range from 0.. to 1..
-- 1.3.6.1.4.1.388.6.2.12.1.2
		-- 1.3.6.1.4.1.388.6.2.12.1.2
		ccEPNic OBJECT-TYPE
			SYNTAX INTEGER (0..10)
			MAX-ACCESS read-only
			STATUS current
			DESCRIPTION
				"This number indicates an index of NIC cards in the system."
			::= { ccEPEntry 2 }

		
--  1.3.6.1.4.1.388.6.2.12.1.3
		-- 1.3.6.1.4.1.388.6.2.12.1.3
		ccEPName OBJECT-TYPE
			SYNTAX DisplayString (SIZE (1..50))
			MAX-ACCESS read-only
			STATUS current
			DESCRIPTION
				"The Name of this ethernet port."
			::= { ccEPEntry 3 }

		
--  1.3.6.1.4.1.388.6.2.12.1.4
		-- 1.3.6.1.4.1.388.6.2.12.1.4
		ccEPDesc OBJECT-TYPE
			SYNTAX DisplayString (SIZE (0..128))
			MAX-ACCESS read-write
			STATUS current
			DESCRIPTION
				"The detailed description for the ethernet port. The Maximum length of the 
				description can be 128 characters. Note that the following characters cannot be part 
				 of description - ',# and double quotes."
			::= { ccEPEntry 4 }

		
--  1.3.6.1.4.1.388.6.2.12.1.5
		-- 1.3.6.1.4.1.388.6.2.12.1.5
		ccEPMacAddr OBJECT-TYPE
			SYNTAX DisplayString
			MAX-ACCESS read-only
			STATUS current
			DESCRIPTION
				"The Mac address for the Ethernet port."
			::= { ccEPEntry 5 }

		
--  1.3.6.1.4.1.388.6.2.12.1.6
		-- 1.3.6.1.4.1.388.6.2.12.1.6
		ccEPEnable OBJECT-TYPE
			SYNTAX DisplayString
			MAX-ACCESS read-write
			STATUS current
			DESCRIPTION
				"Enable/Disable the ethernet port to be a 802.1q Trunk port.
				 Syntax:For enabling  <1,PrimaryVLanId>
				        For disabling <0>."
			::= { ccEPEntry 6 }

		
--  1.3.6.1.4.1.388.6.2.12.1.7
		-- 1.3.6.1.4.1.388.6.2.12.1.7
		ccEPSpeed OBJECT-TYPE
			SYNTAX INTEGER (0..100)
			MAX-ACCESS read-only
			STATUS deprecated
			DESCRIPTION
				"The speed of the ethernet port, such as 10 means the 10 Mps or 100 means 100 Mps."
			::= { ccEPEntry 7 }

		
--  1.3.6.1.4.1.388.6.2.12.1.8
		-- 1.3.6.1.4.1.388.6.2.12.1.8
		ccEPEnableDHCP OBJECT-TYPE
			SYNTAX TruthValue
			MAX-ACCESS read-write
			STATUS current
			DESCRIPTION
				"Enable/Disable DHCP server for this Ethernet port."
			::= { ccEPEntry 8 }

		
--  1.3.6.1.4.1.388.6.2.12.1.9
		-- 1.3.6.1.4.1.388.6.2.12.1.9
		ccEPIPAddr OBJECT-TYPE
			SYNTAX IpAddress
			MAX-ACCESS read-write
			STATUS current
			DESCRIPTION
				"The IP address of Ethernet port."
			::= { ccEPEntry 9 }

		
--  1.3.6.1.4.1.388.6.2.12.1.10
		-- 1.3.6.1.4.1.388.6.2.12.1.10
		ccEPNetMask OBJECT-TYPE
			SYNTAX IpAddress
			MAX-ACCESS read-write
			STATUS current
			DESCRIPTION
				"The netmask address for the Ethernet port."
			::= { ccEPEntry 10 }

		
--  1.3.6.1.4.1.388.6.2.12.1.13
		-- 1.3.6.1.4.1.388.6.2.12.1.13
		ccEPDnsCount OBJECT-TYPE
			SYNTAX INTEGER (0..999)
			MAX-ACCESS read-only
			STATUS current
			DESCRIPTION
				"The number of DNS used by the ethernet port."
			::= { ccEPEntry 13 }

		
--  1.3.6.1.4.1.388.6.2.12.1.14
		-- 1.3.6.1.4.1.388.6.2.12.1.14
		ccEPDnsList OBJECT-TYPE
			SYNTAX DisplayString (SIZE (0..1042))
			MAX-ACCESS read-only
			STATUS current
			DESCRIPTION
				"A list of DNS address for Ethernet port."
			::= { ccEPEntry 14 }

		
--  1.3.6.1.4.1.388.6.2.12.1.15
		-- 1.3.6.1.4.1.388.6.2.12.1.15
		ccEPPrimaryVid OBJECT-TYPE
			SYNTAX INTEGER (1..4095)
			MAX-ACCESS read-write
			STATUS current
			DESCRIPTION
				"Primary VLANId for this etherport.
				Note: 
				               0 or 4096 means non-trunked(no VLAN)"
			::= { ccEPEntry 15 }

		
--  1.3.6.1.4.1.388.6.2.12.1.16
		-- 1.3.6.1.4.1.388.6.2.12.1.16
		ccEPOnline OBJECT-TYPE
			SYNTAX TruthValue
			MAX-ACCESS read-only
			STATUS current
			DESCRIPTION
				"false(2) means the online status of the ethernet port is NOT Active.
				true(1) means the ethernet port is Active."
			::= { ccEPEntry 16 }

		
--  1.3.6.1.4.1.388.6.2.12.1.17
		-- 1.3.6.1.4.1.388.6.2.12.1.17
		ccEPDisplayName OBJECT-TYPE
			SYNTAX DisplayString (SIZE (1..100))
			MAX-ACCESS read-only
			STATUS current
			DESCRIPTION
				"The user-friendly name of the Ethernet Port."
			::= { ccEPEntry 17 }

		
--  1.3.6.1.4.1.388.6.2.12.1.18
		-- 1.3.6.1.4.1.388.6.2.12.1.18
		ccEPUptime OBJECT-TYPE
			SYNTAX DisplayString (SIZE (1..100))
			MAX-ACCESS read-only
			STATUS current
			DESCRIPTION
				"The time elapsed since the EtherPort has been up."
			::= { ccEPEntry 18 }

		
--  1.3.6.1.4.1.388.6.2.12.1.19
		-- 1.3.6.1.4.1.388.6.2.12.1.19
		ccEPTx OBJECT-TYPE
			SYNTAX Counter32
			MAX-ACCESS read-only
			STATUS current
			DESCRIPTION
				"The number of output packets transmitted."
			::= { ccEPEntry 19 }

		
--  1.3.6.1.4.1.388.6.2.12.1.20
		-- 1.3.6.1.4.1.388.6.2.12.1.20
		ccEPRx OBJECT-TYPE
			SYNTAX Counter32
			MAX-ACCESS read-only
			STATUS current
			DESCRIPTION
				"The number of input packets received."
			::= { ccEPEntry 20 }

		
--  1.3.6.1.4.1.388.6.2.12.1.21
		-- 1.3.6.1.4.1.388.6.2.12.1.21
		ccEPDomain OBJECT-TYPE
			SYNTAX DisplayString (SIZE (1..50))
			MAX-ACCESS read-write
			STATUS current
			DESCRIPTION
				"The domain name on this Ethernet Port.
				Note that only the following characters are allowed in the domain name:
				0123456789ABCDEFGHIJKLMNOPQRSTUVWXYZabcdefghijklmnopqrstuvwxyz._-
				Also, '_' , '-' and '.' cannot be the first or last character of the domain name.
				
				Note that changing the domain name will require the KDC configuration to be recreated 
				if it is currently configured."
			::= { ccEPEntry 21 }

		
--  1.3.6.1.4.1.388.6.2.12.1.22
		-- 1.3.6.1.4.1.388.6.2.12.1.22
		ccEPGateway OBJECT-TYPE
			SYNTAX IpAddress
			MAX-ACCESS read-only
			STATUS current
			DESCRIPTION
				"The gateway address being used by the Ethernet port.
				Note:To add a gateway use ccTaf OID."
			::= { ccEPEntry 22 }

		
--  1.3.6.1.4.1.388.6.2.12.1.23
		-- 1.3.6.1.4.1.388.6.2.12.1.23
		ccEPCFGMode OBJECT-TYPE
			SYNTAX DisplayString (SIZE (4..10))
			MAX-ACCESS read-write
			STATUS current
			DESCRIPTION
				"The configured mode of this Etherport.
				Valid inputs are : '10_half','10_full','100_half',
				'100_full','auto'."
			::= { ccEPEntry 23 }

		
--  1.3.6.1.4.1.388.6.2.12.1.24
		-- 1.3.6.1.4.1.388.6.2.12.1.24
		ccEPDuplex OBJECT-TYPE
			SYNTAX DisplayString (SIZE (4..5))
			MAX-ACCESS read-only
			STATUS current
			DESCRIPTION
				"Negotiated mode - duplex"
			::= { ccEPEntry 24 }

		
--  1.3.6.1.4.1.388.6.2.12.1.25
		-- 1.3.6.1.4.1.388.6.2.12.1.25
		ccEPMode OBJECT-TYPE
			SYNTAX DisplayString (SIZE (4..5))
			MAX-ACCESS read-only
			STATUS current
			DESCRIPTION
				"Negotiated mode - speed"
			::= { ccEPEntry 25 }

		
		-- 1.3.6.1.4.1.388.6.2.12.1.26
		ccEPDhcpPriVlan OBJECT-TYPE
			SYNTAX TruthValue
			MAX-ACCESS read-write
			STATUS current
			DESCRIPTION
				"Description."
			::= { ccEPEntry 26 }

		
		-- 1.3.6.1.4.1.388.6.2.12.1.27
		ccEPDDNSStatus OBJECT-TYPE
			SYNTAX TruthValue
			MAX-ACCESS read-write
			STATUS current
			DESCRIPTION
				"Enable (1) / Disable (2) DDNS updates by DHCP Server"
			::= { ccEPEntry 27 }

		
		-- 1.3.6.1.4.1.388.6.2.12.1.28
		ccEPDDNSttl OBJECT-TYPE
			SYNTAX Integer32
			MAX-ACCESS read-write
			STATUS current
			DESCRIPTION
				"TTL for DDNS"
			::= { ccEPEntry 28 }

		
		-- 1.3.6.1.4.1.388.6.2.12.1.29
		ccEPDDNSUpdateAll OBJECT-TYPE
			SYNTAX DisplayString
			MAX-ACCESS read-write
			STATUS current
			DESCRIPTION
				"Update all DDNS entries"
			::= { ccEPEntry 29 }

		
		-- 1.3.6.1.4.1.388.6.2.12.1.30
		ccEPDDNSMUserStatus OBJECT-TYPE
			SYNTAX TruthValue
			MAX-ACCESS read-write
			STATUS current
			DESCRIPTION
				"Enable (1) / Disable (2) RFC 3004 Multiple User Class"
			::= { ccEPEntry 30 }

		
		-- 1.3.6.1.4.1.388.6.2.12.1.31
		ccEPDDNSDomainName OBJECT-TYPE
			SYNTAX DisplayString
			MAX-ACCESS read-write
			STATUS current
			DESCRIPTION
				"the domain to be updated by DDNS"
			::= { ccEPEntry 31 }

		
--  1.3.6.1.4.1.388.6.2.13
		-- 1.3.6.1.4.1.388.6.2.13
		ccEPPTable OBJECT-TYPE
			SYNTAX SEQUENCE OF CcEPPEntry
			MAX-ACCESS not-accessible
			STATUS current
			DESCRIPTION
				"A list of Ethernet port policy entries."
			::= { symbolCCInterfaces 13 }

		
--  1.3.6.1.4.1.388.6.2.13.1
		-- 1.3.6.1.4.1.388.6.2.13.1
		ccEPPEntry OBJECT-TYPE
			SYNTAX CcEPPEntry
			MAX-ACCESS not-accessible
			STATUS current
			DESCRIPTION
				"An Ethernet port policy entry."
			INDEX { ccEPPIndex }
			::= { ccEPPTable 1 }

		
		CcEPPEntry ::=
			SEQUENCE { 
				ccEPPIndex
					INTEGER,
				ccEPPName
					DisplayString,
				ccEPPAlias
					DisplayString,
				ccEPPDesc
					DisplayString,
				ccEPPRonnic
					INTEGER,
				ccEPPVlanCount
					INTEGER,
				ccEPPVlanList
					DisplayString,
				ccEPPCreateNewVlan
					DisplayString,
				ccEPPRemVlan
					DisplayString,
				ccEPPDropVlan
					TruthValue
			 }

--  1.3.6.1.4.1.388.6.2.13.1.1
		-- 1.3.6.1.4.1.388.6.2.13.1.1
		ccEPPIndex OBJECT-TYPE
			SYNTAX INTEGER (1..200)
			MAX-ACCESS read-only
			STATUS current
			DESCRIPTION
				"The Index for the Ethernet policy."
			::= { ccEPPEntry 1 }

		
--  Mower: changed range from 0.. to 1..
-- 1.3.6.1.4.1.388.6.2.13.1.2
		-- 1.3.6.1.4.1.388.6.2.13.1.2
		ccEPPName OBJECT-TYPE
			SYNTAX DisplayString (SIZE (1..50))
			MAX-ACCESS read-only
			STATUS current
			DESCRIPTION
				"Ethernet policy name for one record."
			::= { ccEPPEntry 2 }

		
--  1.3.6.1.4.1.388.6.2.13.1.3
		-- 1.3.6.1.4.1.388.6.2.13.1.3
		ccEPPAlias OBJECT-TYPE
			SYNTAX DisplayString (SIZE (1..50))
			MAX-ACCESS read-write
			STATUS current
			DESCRIPTION
				"The Alias for this EtherPort Policy. The Maximum length of the EP Policy Name 
				can be 50 characters. Note that the following characters cannot be part 
				of EP Policy Name field - ',.,\,&, # and double quotes."
			::= { ccEPPEntry 3 }

		
--  1.3.6.1.4.1.388.6.2.13.1.4
		-- 1.3.6.1.4.1.388.6.2.13.1.4
		ccEPPDesc OBJECT-TYPE
			SYNTAX DisplayString (SIZE (0..128))
			MAX-ACCESS read-write
			STATUS current
			DESCRIPTION
				"A description about this ethernet policy. The Maximum length of the description 
				can be 128 characters. Note that the following characters cannot be part 
				of description ',# and double quotes."
			::= { ccEPPEntry 4 }

		
--  1.3.6.1.4.1.388.6.2.13.1.5
		-- 1.3.6.1.4.1.388.6.2.13.1.5
		ccEPPRonnic OBJECT-TYPE
			SYNTAX INTEGER (0..200)
			MAX-ACCESS read-write
			STATUS current
			DESCRIPTION
				"This object indicates a NIC port number through which
				the WS-5000 Wireless Switch will talk to the rest of network. That means,
				in case of NO VLAN, every incoming packet will go out at this 
				NIC port number."
			::= { ccEPPEntry 5 }

		
--  1.3.6.1.4.1.388.6.2.13.1.6
		-- 1.3.6.1.4.1.388.6.2.13.1.6
		ccEPPVlanCount OBJECT-TYPE
			SYNTAX INTEGER (0..500)
			MAX-ACCESS read-only
			STATUS current
			DESCRIPTION
				"The number of VLANs attached to the Ethernet policy."
			::= { ccEPPEntry 6 }

		
--  1.3.6.1.4.1.388.6.2.13.1.7
		-- 1.3.6.1.4.1.388.6.2.13.1.7
		ccEPPVlanList OBJECT-TYPE
			SYNTAX DisplayString (SIZE (0..100))
			MAX-ACCESS read-only
			STATUS current
			DESCRIPTION
				"Show a list of VLAN objects attatched to this ethernet policy.
				 Display Format
				 LAN1,LAN2,VLAN:Interface number"
			::= { ccEPPEntry 7 }

		
--  1.3.6.1.4.1.388.6.2.13.1.8
		-- 1.3.6.1.4.1.388.6.2.13.1.8
		ccEPPCreateNewVlan OBJECT-TYPE
			SYNTAX DisplayString (SIZE (1..32))
			MAX-ACCESS read-write
			STATUS current
			DESCRIPTION
				"Create a new VLAN in this EtherPort Policy.
				The input has to be of the format: <VlanID,NicNumber>,
				where VlanID can be any integer from 1 through 4095,
				and NicNumber is the etherport on which this VLAN is set.
				The NicNumber can be either '1','2', or 'all'.
				1 as the NicNumber stands for Ethernet1,
				2 as the NicNumber stands for Ethernet2,
				and 'all' stands for both.
				Note that if the etherport on which this VLAN is to be set,
				is a non-trunked port, then the VLAN creation will fail.
				To trunk an etherport, SET the Primary VlanId of that 
				etherport to any integer from 1 through 4095."
			::= { ccEPPEntry 8 }

		
--  1.3.6.1.4.1.388.6.2.13.1.9
		-- 1.3.6.1.4.1.388.6.2.13.1.9
		ccEPPRemVlan OBJECT-TYPE
			SYNTAX DisplayString (SIZE (1..32))
			MAX-ACCESS read-write
			STATUS current
			DESCRIPTION
				"Remove one VLAN from this Etherport policy.
				Only the Vlan Id needs to be input for removal"
			::= { ccEPPEntry 9 }

		
--  1.3.6.1.4.1.388.6.2.13.1.10
		-- 1.3.6.1.4.1.388.6.2.13.1.10
		ccEPPDropVlan OBJECT-TYPE
			SYNTAX TruthValue
			MAX-ACCESS read-write
			STATUS current
			DESCRIPTION
				"Drop all the VLANs for this Etherpolicy. A 'true' does the job"
			::= { ccEPPEntry 10 }

		
--  1.3.6.1.4.1.388.6.2.14
		-- 1.3.6.1.4.1.388.6.2.14
		ccdot11FHPhyTable OBJECT-TYPE
			SYNTAX SEQUENCE OF Ccdot11FHPhyEntry
			MAX-ACCESS not-accessible
			STATUS current
			DESCRIPTION
				"The table for FH specific configuration parameters"
			::= { symbolCCInterfaces 14 }

		
--  1.3.6.1.4.1.388.6.2.14.1
		-- 1.3.6.1.4.1.388.6.2.14.1
		ccdot11FHPhyEntry OBJECT-TYPE
			SYNTAX Ccdot11FHPhyEntry
			MAX-ACCESS not-accessible
			STATUS current
			DESCRIPTION
				"An entry in the FH Phy Table."
			INDEX { ccdot11FHIndex }
			::= { ccdot11FHPhyTable 1 }

		
		Ccdot11FHPhyEntry ::=
			SEQUENCE { 
				ccdot11FHIndex
					Integer32,
				ccdot11FHHopTime
					Integer32,
				ccdot11FHCurrentChannelNumber
					Integer32,
				ccdot11FHMaxDwellTime
					Integer32,
				ccdot11FHCurrentDwellTime
					Integer32,
				ccdot11FHCurrentSet
					Integer32,
				ccdot11FHCurrentPattern
					Integer32,
				ccdot11FHCurrentIndex
					Integer32
			 }

--  1.3.6.1.4.1.388.6.2.14.1.1
		-- 1.3.6.1.4.1.388.6.2.14.1.1
		ccdot11FHIndex OBJECT-TYPE
			SYNTAX Integer32 (1..2147483647)
			MAX-ACCESS not-accessible
			STATUS current
			DESCRIPTION
				"The index of this FH radio."
			::= { ccdot11FHPhyEntry 1 }

		
--  ??Mower: added a range 1..2**31 to eliminate an error,
-- but what range is correct?
-- 1.3.6.1.4.1.388.6.2.14.1.2
		-- 1.3.6.1.4.1.388.6.2.14.1.2
		ccdot11FHHopTime OBJECT-TYPE
			SYNTAX Integer32
			MAX-ACCESS read-only
			STATUS current
			DESCRIPTION
				"The time in microseconds for the PMD to change from channel 2 
				to channel 80."
			::= { ccdot11FHPhyEntry 2 }

		
--  1.3.6.1.4.1.388.6.2.14.1.3
		-- 1.3.6.1.4.1.388.6.2.14.1.3
		ccdot11FHCurrentChannelNumber OBJECT-TYPE
			SYNTAX Integer32
			MAX-ACCESS read-only
			STATUS current
			DESCRIPTION
				"The current channel number of the frequency output by the RF synthesizer."
			::= { ccdot11FHPhyEntry 3 }

		
--  1.3.6.1.4.1.388.6.2.14.1.4
		-- 1.3.6.1.4.1.388.6.2.14.1.4
		ccdot11FHMaxDwellTime OBJECT-TYPE
			SYNTAX Integer32
			MAX-ACCESS read-only
			STATUS current
			DESCRIPTION
				"The maximum time in TU that the transmitter is permitted to operate on a single channel."
			::= { ccdot11FHPhyEntry 4 }

		
--  1.3.6.1.4.1.388.6.2.14.1.5
		-- 1.3.6.1.4.1.388.6.2.14.1.5
		ccdot11FHCurrentDwellTime OBJECT-TYPE
			SYNTAX Integer32
			MAX-ACCESS read-write
			STATUS current
			DESCRIPTION
				"The current time in TU that the transmitter shall operate on a single channel, as set by the MAC.
				The valid range is from 25 to 1000 milliseconds (both inclusive). A value of 65535 returned by the
				switch indicates that there is no value set for this variable. "
			::= { ccdot11FHPhyEntry 5 }

		
--  1.3.6.1.4.1.388.6.2.14.1.6
		-- 1.3.6.1.4.1.388.6.2.14.1.6
		ccdot11FHCurrentSet OBJECT-TYPE
			SYNTAX Integer32
			MAX-ACCESS read-write
			STATUS current
			DESCRIPTION
				"The current set of patterns the PHY LME is using to determine the hopping sequence.
				A value of 255 returned by the
				switch indicates that there is no value set for this variable."
			::= { ccdot11FHPhyEntry 6 }

		
--  1.3.6.1.4.1.388.6.2.14.1.7
		-- 1.3.6.1.4.1.388.6.2.14.1.7
		ccdot11FHCurrentPattern OBJECT-TYPE
			SYNTAX Integer32
			MAX-ACCESS read-write
			STATUS current
			DESCRIPTION
				"The current pattern the PHY LME is using to determine the hop sequence.
				A value of 255 returned by the
				switch indicates that there is no value set for this variable."
			::= { ccdot11FHPhyEntry 7 }

		
--  1.3.6.1.4.1.388.6.2.14.1.8
		-- 1.3.6.1.4.1.388.6.2.14.1.8
		ccdot11FHCurrentIndex OBJECT-TYPE
			SYNTAX Integer32
			MAX-ACCESS read-only
			STATUS current
			DESCRIPTION
				"The current index value the PHY LME is using the determine the CurrentChannelNumber."
			::= { ccdot11FHPhyEntry 8 }

		
--  1.3.6.1.4.1.388.6.2.16
		-- 1.3.6.1.4.1.388.6.2.16
		ccAPPolicyObjects OBJECT IDENTIFIER ::= { symbolCCInterfaces 16 }

		
--  1.3.6.1.4.1.388.6.2.16.2
		-- 1.3.6.1.4.1.388.6.2.16.2
		ccAPPolicyAddRemWLANTable OBJECT-TYPE
			SYNTAX SEQUENCE OF CcAPPolicyAddRemWLANEntry
			MAX-ACCESS not-accessible
			STATUS current
			DESCRIPTION
				"A table for adding and removing WLANs"
			::= { ccAPPolicyObjects 2 }

		
--  1.3.6.1.4.1.388.6.2.16.2.1
		-- 1.3.6.1.4.1.388.6.2.16.2.1
		ccAPPolicyAddRemWLANEntry OBJECT-TYPE
			SYNTAX CcAPPolicyAddRemWLANEntry
			MAX-ACCESS not-accessible
			STATUS current
			DESCRIPTION
				"A table for adding and removing WLANs. Select/Unselect and WLAN for a mapping. The second index is the mapping. 
				1 as its value indicates addition/removal of a WLAN to/from an AP100 (4BSS-4ESS mapping). 
				2 as its value indicates addition/removal of a WLAN to/from an FH radio (1BSS-1ESS mapping).
				3 as its value indicates addition/removal of a WLAN from an AP200-11a radio (1BSS-16ESS mapping).
				4 as its value indicates addition/removal of a WLAN from an AP200-11b radio, AP300, AP4121 (4BSS-16ESS mapping).		
								
				"
			INDEX { ccAPPolicyIndex, ccAPPolicyDeviceType }
			::= { ccAPPolicyAddRemWLANTable 1 }

		
		CcAPPolicyAddRemWLANEntry ::=
			SEQUENCE { 
				ccAPPolicyDeviceType
					INTEGER,
				ccAPPolicyAddWLAN
					DisplayString,
				ccAPPolicyRemWLAN
					DisplayString,
				ccAPPolicySelectWLAN
					DisplayString,
				ccAPPolicyUnselectWLAN
					DisplayString
			 }

--  1.3.6.1.4.1.388.6.2.16.2.1.1
		-- 1.3.6.1.4.1.388.6.2.16.2.1.1
		ccAPPolicyDeviceType OBJECT-TYPE
			SYNTAX INTEGER (1..20)
			MAX-ACCESS not-accessible
			STATUS current
			DESCRIPTION
				"The type of mapping to/from which WLANs will be selected/unselected."
			::= { ccAPPolicyAddRemWLANEntry 1 }

		
--  1.3.6.1.4.1.388.6.2.16.2.1.2
		-- 1.3.6.1.4.1.388.6.2.16.2.1.2
		ccAPPolicyAddWLAN OBJECT-TYPE
			SYNTAX DisplayString (SIZE (1..100))
			MAX-ACCESS read-only
			STATUS deprecated
			DESCRIPTION
				"Add a WLAN to this particular APPolicy and device.
				The format for entering the input is
				 <existing Wlan,bandwidth>, where the sum of all bandwidth for 
				 this AP policy and Device Type should be less than or equal to 100%.
				 Also, the bandwidth for any WLAN cannot be less than 5%.
				 Note:
				 1. Default AP Policy cannot be edited.
				          2. Always set Bandwidth as 100% if you are adding WLAN to an FH port.
				                 Setting the bandwidth to less than 100% for FH results in an error.
				                 This also means that at any given instant, no more than one WLANs
				                 can be added to an FH Port."
			::= { ccAPPolicyAddRemWLANEntry 2 }

		
--  1.3.6.1.4.1.388.6.2.16.2.1.3
		-- 1.3.6.1.4.1.388.6.2.16.2.1.3
		ccAPPolicyRemWLAN OBJECT-TYPE
			SYNTAX DisplayString (SIZE (1..100))
			MAX-ACCESS read-only
			STATUS deprecated
			DESCRIPTION
				" Remove a WLAN from this particular APPolicy and device.
				Note:Default AP Policy cannot be edited"
			::= { ccAPPolicyAddRemWLANEntry 3 }

		
		-- 1.3.6.1.4.1.388.6.2.16.2.1.4
		ccAPPolicySelectWLAN OBJECT-TYPE
			SYNTAX DisplayString (SIZE (1..100))
			MAX-ACCESS read-write
			STATUS current
			DESCRIPTION
				"Select a WLAN for this mapping. The WLAN should already be added 
				          to this Access Port Policy for mapping.
								
				       (4BSS-4ESS) :Four WLANs can be selected, if full unselect a existing 
						    WLAN before selecting a different one.
				       (1BSS-1ESS) :One WLAN can be selected for this mapping, if already 
					            selected unselect a existing WLAN before selecting a 
						    different one.
				       (1BSS-16ESS):Only one WLAN can be made primary so selected WLAN is 
					            set as primary.
				       (4BSS-16ESS):One can Select upto maximum of four WLAN as primary.
				"
			::= { ccAPPolicyAddRemWLANEntry 4 }

		
		-- 1.3.6.1.4.1.388.6.2.16.2.1.5
		ccAPPolicyUnselectWLAN OBJECT-TYPE
			SYNTAX DisplayString (SIZE (1..100))
			MAX-ACCESS read-write
			STATUS current
			DESCRIPTION
				"UnSelect a WLAN for this mapping. The WLAN should already have been selected for this mapping.
				WLAN can be unselected for (4BSS-4ESS) and (1BSS-1ESS) mapping only."
			::= { ccAPPolicyAddRemWLANEntry 5 }

		
--  1.3.6.1.4.1.388.6.2.16.3
		-- 1.3.6.1.4.1.388.6.2.16.3
		ccAPPolicyWLANTable OBJECT-TYPE
			SYNTAX SEQUENCE OF CcAPPolicyWLANEntry
			MAX-ACCESS not-accessible
			STATUS current
			DESCRIPTION
				"A table for setting attributes of a wlan for a particular mapping for a Access Port Policy."
			::= { ccAPPolicyObjects 3 }

		
--  1.3.6.1.4.1.388.6.2.16.3.1
		-- 1.3.6.1.4.1.388.6.2.16.3.1
		ccAPPolicyWLANEntry OBJECT-TYPE
			SYNTAX CcAPPolicyWLANEntry
			MAX-ACCESS not-accessible
			STATUS current
			DESCRIPTION
				"This table allows Get/Set attributes of a WLAN for a mapping for a particular AP policy.
				First index is a AP Policy, Second index is the Mapping
				1 indicates mapping to/from an AP100 (4BSS-4ESS mapping). 
				2 indicates mapping of a WLAN to/from an FH radio (1BSS-1ESS mapping).
				3 indicates mapping of a WLAN from an AP200-11a radio (1BSS-16ESS mapping).
				4 indicates mapping of a WLAN from an AP200-11b radio, AP300, AP4121 (4BSS-16ESS mapping).
				
				Third index is the WLAN."
			INDEX { ccAPPolicyIndex, ccAPPolicyDeviceType, ccAPPolicyWLANIndex }
			::= { ccAPPolicyWLANTable 1 }

		
		CcAPPolicyWLANEntry ::=
			SEQUENCE { 
				ccAPPolicyWLANIndex
					INTEGER,
				ccAPPolicyWLAN
					DisplayString,
				ccAPPolicyWLANBW
					DisplayString,
				ccAPPolicyWLANNP
					DisplayString,
				ccAPPolicyWLANBSS
					DisplayString
			 }

--  1.3.6.1.4.1.388.6.2.16.3.1.1
		-- 1.3.6.1.4.1.388.6.2.16.3.1.1
		ccAPPolicyWLANIndex OBJECT-TYPE
			SYNTAX INTEGER (1..200)
			MAX-ACCESS not-accessible
			STATUS current
			DESCRIPTION
				"The index of this particular WLAN."
			::= { ccAPPolicyWLANEntry 1 }

		
--  1.3.6.1.4.1.388.6.2.16.3.1.2
		-- 1.3.6.1.4.1.388.6.2.16.3.1.2
		ccAPPolicyWLAN OBJECT-TYPE
			SYNTAX DisplayString (SIZE (1..100))
			MAX-ACCESS read-only
			STATUS current
			DESCRIPTION
				"Name of this particular WLAN which belongs to this APPolicy and this 
				devicetype."
			::= { ccAPPolicyWLANEntry 2 }

		
--  1.3.6.1.4.1.388.6.2.16.3.1.3
		-- 1.3.6.1.4.1.388.6.2.16.3.1.3
		ccAPPolicyWLANBW OBJECT-TYPE
			SYNTAX DisplayString (SIZE (1..32))
			MAX-ACCESS read-write
			STATUS current
			DESCRIPTION
				"The bandwidth allocated to this particular WLAN, which belongs to this 
				APPolicy and this devicetype. Bandwidth of an FH port is 100% by default,
				and any attempt to set the bandwidth of an FH port results in an error."
			::= { ccAPPolicyWLANEntry 3 }

		
--  1.3.6.1.4.1.388.6.2.16.3.1.4
		-- 1.3.6.1.4.1.388.6.2.16.3.1.4
		ccAPPolicyWLANNP OBJECT-TYPE
			SYNTAX DisplayString (SIZE (0..200))
			MAX-ACCESS read-write
			STATUS current
			DESCRIPTION
				"The Network Policy which belongs to this particular WLAN, which belongs 
				to this APPolicy. WLAN must already be configured for this AP Policy to 
				set the Network Policy. SETting of Network Policy takes effect across all the devices,
				and not for a particular device. As an example, if you SET
				the Network Policy of a WLAN for the devicetype AP200, the policy will be applied to 
				all the devices of that WLAN. Note that the GET continues to be per device.
				In order to remove the Network Policy, just leave the field blank
				while SETting (send an empty string)"
			::= { ccAPPolicyWLANEntry 4 }

		
--  1.3.6.1.4.1.388.6.2.16.3.1.5
		-- 1.3.6.1.4.1.388.6.2.16.3.1.5
		ccAPPolicyWLANBSS OBJECT-TYPE
			SYNTAX DisplayString (SIZE (1..200))
			MAX-ACCESS read-write
			STATUS current
			DESCRIPTION
				"The BSS of this particular WLAN, which belongs to this APPolicy and this 
				devicetype. BSS ID for AP 100, FHSS, AP200a is set to 1 by default and 
				cannot be modifed. 
				BSS ID of AP200b can be set from 1 through 4."
			::= { ccAPPolicyWLANEntry 5 }

		
--  1.3.6.1.4.1.388.6.2.16.4
		-- 1.3.6.1.4.1.388.6.2.16.4
		ccAPPolicyBSSTable OBJECT-TYPE
			SYNTAX SEQUENCE OF CcAPPolicyBSSEntry
			MAX-ACCESS not-accessible
			STATUS current
			DESCRIPTION
				"A table to GET/SET the primary wlan property of a particular bss and device type"
			::= { ccAPPolicyObjects 4 }

		
--  1.3.6.1.4.1.388.6.2.16.4.1
		-- 1.3.6.1.4.1.388.6.2.16.4.1
		ccAPPolicyBSSEntry OBJECT-TYPE
			SYNTAX CcAPPolicyBSSEntry
			MAX-ACCESS not-accessible
			STATUS current
			DESCRIPTION
				"This table will GET/SET the primary wlan property 'per APPolicy, per devicetype,per BSS.
				ccAPPolicyIndex and ccDeviceType are defined earlier. ccAPPolicyBSS is the current BSS whose 
				primary WLAN is being GET/SET.
				1 indicates mapping to/from an AP100 (4BSS-4ESS mapping). 
				2 indicates mapping of a WLAN to/from an FH radio (1BSS-1ESS mapping).
				3 indicates mapping of a WLAN from an AP200-11a radio (1BSS-16ESS mapping).
				4 indicates mapping of a WLAN from an AP200-11b radio, AP300, AP4121 (4BSS-16ESS mapping).
				"
			INDEX { ccAPPolicyIndex, ccAPPolicyDeviceType, ccAPPolicyBSS }
			::= { ccAPPolicyBSSTable 1 }

		
		CcAPPolicyBSSEntry ::=
			SEQUENCE { 
				ccAPPolicyBSS
					DisplayString,
				ccAPPolicyPrimaryWLAN
					DisplayString
			 }

--  1.3.6.1.4.1.388.6.2.16.4.1.1
		-- 1.3.6.1.4.1.388.6.2.16.4.1.1
		ccAPPolicyBSS OBJECT-TYPE
			SYNTAX DisplayString (SIZE (1..10))
			MAX-ACCESS not-accessible
			STATUS current
			DESCRIPTION
				"The BSS for which the primary wlan property needs to be get/set"
			::= { ccAPPolicyBSSEntry 1 }

		
--  Mower: changed range 1..100 to 1..10.  It's actually an
-- integer, (expressed as a DisplayString), 1..4.
-- 
-- 1.3.6.1.4.1.388.6.2.16.4.1.2
		-- 1.3.6.1.4.1.388.6.2.16.4.1.2
		ccAPPolicyPrimaryWLAN OBJECT-TYPE
			SYNTAX DisplayString (SIZE (1..100))
			MAX-ACCESS read-write
			STATUS current
			DESCRIPTION
				"The primary wlan property  for this particular APPolicy, per 
				device type and per BSS, the WLAN marked as primary should already
				be added as a wlan into this policy.
				Primary WLAN cannot be set for any device except for (1BSS-16ESS) and (4BSS-16ESS) mappings.
				"
			::= { ccAPPolicyBSSEntry 2 }

		
		-- 1.3.6.1.4.1.388.6.2.17
		ccFWLANTable OBJECT-TYPE
			SYNTAX SEQUENCE OF CcFWLANEntry
			MAX-ACCESS not-accessible
			STATUS current
			DESCRIPTION
				"A list of LAN descriptors.
				
				Note:This Feature is VPN dependent feature hence
				if vpnsupport is not enabled then the walk over
				this table will not return anything and the set
				operation over any OID under this table will return 
				an error message- No creation.
								
				"
			::= { symbolCCInterfaces 17 }

		
		-- 1.3.6.1.4.1.388.6.2.17.1
		ccFWLANEntry OBJECT-TYPE
			SYNTAX CcFWLANEntry
			MAX-ACCESS not-accessible
			STATUS current
			DESCRIPTION
				"A LAN descriptor."
			INDEX { ccEPPIndex }
			::= { ccFWLANTable 1 }

		
		CcFWLANEntry ::=
			SEQUENCE { 
				ccLANIndex
					INTEGER,
				ccLANName
					OCTET STRING,
				ccLANDesc
					OCTET STRING,
				ccLANNATCount
					INTEGER,
				ccLANAddNAT
					OCTET STRING,
				ccLANRemNAT
					OCTET STRING,
				ccLANEp
					INTEGER,
				ccLANNp
					OCTET STRING,
				ccLANPfAllow
					DisplayString,
				ccLANPfDeny
					DisplayString
			 }

		-- 1.3.6.1.4.1.388.6.2.17.1.1
		ccLANIndex OBJECT-TYPE
			SYNTAX INTEGER (0..200)
			MAX-ACCESS read-only
			STATUS current
			DESCRIPTION
				"The Index for the LAN descriptor.
				"
			::= { ccFWLANEntry 1 }

		
		-- 1.3.6.1.4.1.388.6.2.17.1.2
		ccLANName OBJECT-TYPE
			SYNTAX OCTET STRING (SIZE (1..32))
			MAX-ACCESS read-only
			STATUS current
			DESCRIPTION
				"LAN name."
			::= { ccFWLANEntry 2 }

		
		-- 1.3.6.1.4.1.388.6.2.17.1.3
		ccLANDesc OBJECT-TYPE
			SYNTAX OCTET STRING (SIZE (0..32))
			MAX-ACCESS read-write
			STATUS current
			DESCRIPTION
				"LAN description."
			::= { ccFWLANEntry 3 }

		
		-- 1.3.6.1.4.1.388.6.2.17.1.4
		ccLANNATCount OBJECT-TYPE
			SYNTAX INTEGER (0..200)
			MAX-ACCESS read-only
			STATUS current
			DESCRIPTION
				"The number of NAT entries attached to a LAN.
				"
			::= { ccFWLANEntry 4 }

		
		-- 1.3.6.1.4.1.388.6.2.17.1.5
		ccLANAddNAT OBJECT-TYPE
			SYNTAX OCTET STRING (SIZE (1..32))
			MAX-ACCESS read-write
			STATUS current
			DESCRIPTION
				"Create a new NAT entry for this LAN.
				Syntax: <RemoteRealIP,LocalNatIP>
				           OR
				        <RemoteRealIP,LocalNatIP,NumberOfEntries>
				
				The agent will execute the appropriate code depending on 
				the number of input parameters.
				
				Valid input values for 'NumberOfEntries' are 0 to 250.
				The maximum number of NAT mappings allowed are 250.
				
				        Possible reasons for Commit Fail:-
								
					1.If number of entries are not in the range 0-250.
					2.If number of NAT mappings are greater than 250.
					3 If the NAT mappings are duplicate.
					
					Note:It takes approximately 10 secs to complete the set operation
					     for 250 entries."
			::= { ccFWLANEntry 5 }

		
		-- 1.3.6.1.4.1.388.6.2.17.1.6
		ccLANRemNAT OBJECT-TYPE
			SYNTAX OCTET STRING (SIZE (1..32))
			MAX-ACCESS read-write
			STATUS current
			DESCRIPTION
				"Remove one NAT entry from this LAN.
				
				Syntax: <RemoteRealIP,LocalNatIP>
				           OR
				        <RemoteRealIP,LocalNatIP,NumberOfEntries>
				
				The agent will execute the appropriate code depending on 
				the number of input parameters."
			::= { ccFWLANEntry 6 }

		
		-- 1.3.6.1.4.1.388.6.2.17.1.7
		ccLANEp OBJECT-TYPE
			SYNTAX INTEGER (0..3)
			MAX-ACCESS read-write
			STATUS current
			DESCRIPTION
				"LAN Ethernet Port.  Enter an ethernet port number. 	
				Valid port numbers are 1 and 2 (for the two
				physical ethernet ports) as well as 3 (for
				a virtual VPN port connection).
				0 as a port number removes Ethernet Port."
			::= { ccFWLANEntry 7 }

		
		-- 1.3.6.1.4.1.388.6.2.17.1.8
		ccLANNp OBJECT-TYPE
			SYNTAX OCTET STRING (SIZE (0..32))
			MAX-ACCESS read-write
			STATUS current
			DESCRIPTION
				"Network policy associated with this LAN.  Enter
				either the name of an existing network policy,
				or enter 'remove' to set the current value to
				blank.
				"
			::= { ccFWLANEntry 8 }

		
		-- 1.3.6.1.4.1.388.6.2.17.1.9
		ccLANPfAllow OBJECT-TYPE
			SYNTAX DisplayString (SIZE (1..32))
			MAX-ACCESS read-write
			STATUS current
			DESCRIPTION
				"Port Filter for this LAN. Valid input values are 
				https ,http ,ftp and telnet .The input values are case sensitive.
				Only one value can be set at a time."
			::= { ccFWLANEntry 9 }

		
		-- 1.3.6.1.4.1.388.6.2.17.1.10
		ccLANPfDeny OBJECT-TYPE
			SYNTAX DisplayString
			MAX-ACCESS read-write
			STATUS current
			DESCRIPTION
				"Port Filter for this LAN. 
				Valid input values are https ,http ,ftp and telnet and web. Only one value
				can be given at a time.
				"
			::= { ccFWLANEntry 10 }

		
		-- 1.3.6.1.4.1.388.6.2.18
		ccFWLANNATTable OBJECT-TYPE
			SYNTAX SEQUENCE OF CcFWLANNATEntry
			MAX-ACCESS not-accessible
			STATUS current
			DESCRIPTION
				"A list of LAN NAT Entries.  This is a
				 	dual-index table, NAT entries for all
				 	LANs are displayed.  A single entry of
				 	0.0.0.0 for a LAN means that LAN has
				 	no NAT entries.
				
				 Note:This Feature is VPN dependent feature hence
				      if vpnsupport is not enabled then the walk over
				      this table will not return anything and the set
				      operation over any OID under this table will return 
				      an error message- No creation.
								
				"
			::= { symbolCCInterfaces 18 }

		
		-- 1.3.6.1.4.1.388.6.2.18.1
		ccFWLANNATEntry OBJECT-TYPE
			SYNTAX CcFWLANNATEntry
			MAX-ACCESS not-accessible
			STATUS current
			DESCRIPTION
				"A LAN descriptor.
				"
			INDEX { ccEPPIndex, ccLANNATIndex }
			::= { ccFWLANNATTable 1 }

		
		CcFWLANNATEntry ::=
			SEQUENCE { 
				ccLANNATIndex
					OCTET STRING,
				ccLANNATRemoteRealIP
					IpAddress,
				ccLANNATLocalNatIP
					IpAddress
			 }

		-- 1.3.6.1.4.1.388.6.2.18.1.1
		ccLANNATIndex OBJECT-TYPE
			SYNTAX OCTET STRING (SIZE (1..32))
			MAX-ACCESS read-only
			STATUS current
			DESCRIPTION
				"The Index for the NAT entry.
				"
			::= { ccFWLANNATEntry 1 }

		
		-- 1.3.6.1.4.1.388.6.2.18.1.2
		ccLANNATRemoteRealIP OBJECT-TYPE
			SYNTAX IpAddress
			MAX-ACCESS read-only
			STATUS current
			DESCRIPTION
				"The Remote Real IP address in a NAT translation.
				"
			::= { ccFWLANNATEntry 2 }

		
		-- 1.3.6.1.4.1.388.6.2.18.1.3
		ccLANNATLocalNatIP OBJECT-TYPE
			SYNTAX IpAddress
			MAX-ACCESS read-only
			STATUS current
			DESCRIPTION
				"The Local NAT IP address in a NAT translation.
				"
			::= { ccFWLANNATEntry 3 }

		
		-- 1.3.6.1.4.1.388.6.2.19
		ccRouteTable OBJECT-TYPE
			SYNTAX SEQUENCE OF CcRouteEntry
			MAX-ACCESS not-accessible
			STATUS current
			DESCRIPTION
				"Display current network routing table.
				"
			::= { symbolCCInterfaces 19 }

		
		-- 1.3.6.1.4.1.388.6.2.19.1
		ccRouteEntry OBJECT-TYPE
			SYNTAX CcRouteEntry
			MAX-ACCESS not-accessible
			STATUS current
			DESCRIPTION
				"A Route entry.
				"
			INDEX { ccRouteIndex }
			::= { ccRouteTable 1 }

		
		CcRouteEntry ::=
			SEQUENCE { 
				ccRouteIndex
					INTEGER,
				ccRouteDest
					OCTET STRING,
				ccRouteGateway
					OCTET STRING,
				ccRouteFlags
					OCTET STRING,
				ccRouteRefs
					INTEGER,
				ccRouteUse
					INTEGER,
				ccRouteInterface
					OCTET STRING,
				ccRouteGenMask
					OCTET STRING
			 }

		-- 1.3.6.1.4.1.388.6.2.19.1.1
		ccRouteIndex OBJECT-TYPE
			SYNTAX INTEGER (1..100)
			MAX-ACCESS read-only
			STATUS current
			DESCRIPTION
				"The Index for the Route entry.
				"
			::= { ccRouteEntry 1 }

		
		-- 1.3.6.1.4.1.388.6.2.19.1.2
		ccRouteDest OBJECT-TYPE
			SYNTAX OCTET STRING (SIZE (1..32))
			MAX-ACCESS read-only
			STATUS current
			DESCRIPTION
				"The Destination for the Route entry.
				"
			::= { ccRouteEntry 2 }

		
		-- 1.3.6.1.4.1.388.6.2.19.1.3
		ccRouteGateway OBJECT-TYPE
			SYNTAX OCTET STRING (SIZE (1..32))
			MAX-ACCESS read-only
			STATUS current
			DESCRIPTION
				"The Gateway for the Route entry.
				"
			::= { ccRouteEntry 3 }

		
		-- 1.3.6.1.4.1.388.6.2.19.1.4
		ccRouteFlags OBJECT-TYPE
			SYNTAX OCTET STRING (SIZE (1..10))
			MAX-ACCESS read-only
			STATUS current
			DESCRIPTION
				"The Flags for the Route entry.
				 	
				 	These are standard 'netstat' flags,
				 	including (but not limited to):
				 	
				 	C - Generate new routes on use
				 	G - Destination requires forwarding by intermediary
				 	H - Host entry (net otherwise)
				 	L - Valid protocol to link address translation
				 	R - Host or net unreachable
				 	U - Route usable
				"
			::= { ccRouteEntry 4 }

		
		-- 1.3.6.1.4.1.388.6.2.19.1.5
		ccRouteRefs OBJECT-TYPE
			SYNTAX INTEGER (1..100)
			MAX-ACCESS read-only
			STATUS current
			DESCRIPTION
				"The number of references to the Route entry.
				"
			::= { ccRouteEntry 5 }

		
		-- 1.3.6.1.4.1.388.6.2.19.1.6
		ccRouteUse OBJECT-TYPE
			SYNTAX INTEGER (1..100)
			MAX-ACCESS read-only
			STATUS current
			DESCRIPTION
				"The Use count for the Route entry.
				"
			::= { ccRouteEntry 6 }

		
		-- 1.3.6.1.4.1.388.6.2.19.1.7
		ccRouteInterface OBJECT-TYPE
			SYNTAX OCTET STRING (SIZE (1..32))
			MAX-ACCESS read-only
			STATUS current
			DESCRIPTION
				"The Interface for the Route entry.
				"
			::= { ccRouteEntry 7 }

		
		-- 1.3.6.1.4.1.388.6.2.19.1.8
		ccRouteGenMask OBJECT-TYPE
			SYNTAX OCTET STRING
			MAX-ACCESS read-only
			STATUS current
			DESCRIPTION
				"The netmask for the Route entry
				"
			::= { ccRouteEntry 8 }

		
		-- 1.3.6.1.4.1.388.6.2.20
		ccRouteAddObj OBJECT-TYPE
			SYNTAX OCTET STRING (SIZE (1..200))
			MAX-ACCESS read-write
			STATUS current
			DESCRIPTION
				"Add route to the network routing table.
				
				 Syntax:host <host addr> <gateway>
					             or
					net <network addr> <gateway> netmask <netmask>		
				 
				"
			::= { symbolCCInterfaces 20 }

		
		-- 1.3.6.1.4.1.388.6.2.21
		ccRouteRemObj OBJECT-TYPE
			SYNTAX OCTET STRING (SIZE (1..200))
			MAX-ACCESS read-write
			STATUS current
			DESCRIPTION
				"Remove route from the network routing table.
				 Syntax:host <host addr> <gateway>
				               or
				 net <network addr> <gateway> netmask <netmask>
								
				 
				
				"
			::= { symbolCCInterfaces 21 }

		
		-- 1.3.6.1.4.1.388.6.2.22
		ccRouteFlush OBJECT-TYPE
			SYNTAX DoActionNow
			MAX-ACCESS read-write
			STATUS current
			DESCRIPTION
				"Remove all routes from the network routing table.
				when set to True
				
				"
			::= { symbolCCInterfaces 22 }

		
		-- 1.3.6.1.4.1.388.6.2.23
		ccDhcpSrvNIC1 OBJECT IDENTIFIER ::= { symbolCCInterfaces 23 }

		
		-- 1.3.6.1.4.1.388.6.2.23.1
		ccDhcp1Srv OBJECT-TYPE
			SYNTAX INTEGER (0..1)
			MAX-ACCESS read-write
			STATUS current
			DESCRIPTION
				"Enable(1)/Disable(2) DHCP Server on Ethernet 1.
				 Note:DHCP Server can be enabled only on single 
				 interface at a time
				
				
				Note:This Feature is VPN dependent feature hence
				if vpnsupport is not enabled then the walk over
				ccDhcpSrvNIC1 will not return anything and the set
				operation over any OID under this table will return 
				an error message- No creation.
				"
			::= { ccDhcpSrvNIC1 1 }

		
		-- 1.3.6.1.4.1.388.6.2.23.2
		ccDhcp1Subnet OBJECT-TYPE
			SYNTAX IpAddress
			MAX-ACCESS read-only
			STATUS current
			DESCRIPTION
				"The subnet on Ethernet port 1 that the 
				 	DHCP Server serves IP address for.
				"
			::= { ccDhcpSrvNIC1 2 }

		
		-- 1.3.6.1.4.1.388.6.2.23.3
		ccDhcp1Netmask OBJECT-TYPE
			SYNTAX IpAddress
			MAX-ACCESS read-only
			STATUS current
			DESCRIPTION
				"The netmask address for the Ethernet port 1
				 	that the DHCP Server serves IP addresses for."
			::= { ccDhcpSrvNIC1 3 }

		
		-- 1.3.6.1.4.1.388.6.2.23.4
		ccDhcp1BcastIP OBJECT-TYPE
			SYNTAX IpAddress
			MAX-ACCESS read-only
			STATUS current
			DESCRIPTION
				"The broadcast IP address for the subnet the
				 	DHCP Server serves on Ethernet Port 1.
				"
			::= { ccDhcpSrvNIC1 4 }

		
		-- 1.3.6.1.4.1.388.6.2.23.5
		ccDhcp1RouterIP OBJECT-TYPE
			SYNTAX IpAddress
			MAX-ACCESS read-write
			STATUS current
			DESCRIPTION
				"The default Router/Gateway IP address for the subnet 
				the DHCP Server serves on Ethernet Port 1. To remove
				the router option set SNMP Set Value to 0.0.0.0 .
				
				"
			::= { ccDhcpSrvNIC1 5 }

		
		-- 1.3.6.1.4.1.388.6.2.23.6
		ccDhcp1PriDNSIP OBJECT-TYPE
			SYNTAX IpAddress
			MAX-ACCESS read-write
			STATUS current
			DESCRIPTION
				"The Primary DNS IP address for the subnet
				the DHCP Server serves on Ethernet Port 1. To
				remove domain-name-servers option, set SNMP Set
				Value to 0.0.0.0 ."
			::= { ccDhcpSrvNIC1 6 }

		
		-- 1.3.6.1.4.1.388.6.2.23.7
		ccDhcp1SecDNSIP OBJECT-TYPE
			SYNTAX IpAddress
			MAX-ACCESS read-write
			STATUS current
			DESCRIPTION
				"The Secondary DNS IP address for the subnet
				the DHCP Server serves on Ethernet Port 1. To
				remove Secondary DNS IP, set SNMP Set Value to
				0.0.0.0 ."
			::= { ccDhcpSrvNIC1 7 }

		
		-- 1.3.6.1.4.1.388.6.2.23.8
		ccDhcp1DomainName OBJECT-TYPE
			SYNTAX OCTET STRING (SIZE (1..100))
			MAX-ACCESS read-write
			STATUS current
			DESCRIPTION
				"The Domain Name for the subnet the DHCP Server
				 	serves on Ethernet Port 1. To remove domain-name
				 	option, set SNMP Set Value to 0.
				"
			::= { ccDhcpSrvNIC1 8 }

		
		-- 1.3.6.1.4.1.388.6.2.23.9
		ccDhcp1DefLease OBJECT-TYPE
			SYNTAX Integer32 (0..31536000)
			UNITS "seconds"
			MAX-ACCESS read-write
			STATUS current
			DESCRIPTION
				"The Default lease time of the IP address for 
				the subnet the DHCP Server serves on
				Ethernet Port 1. To set to default-lease-time option,
				set SNMP Set Value to 0 it automatically sets it to
				21600(default value)."
			::= { ccDhcpSrvNIC1 9 }

		
		-- 1.3.6.1.4.1.388.6.2.23.10
		ccDhcp1MaxLease OBJECT-TYPE
			SYNTAX Integer32 (0..31536000)
			UNITS "seconds"
			MAX-ACCESS read-write
			STATUS current
			DESCRIPTION
				"The Maximum lease time of the IP address for 
				the subnet the DHCP Server serves on 
				Ethernet Port 1. To set to default max-lease-time option,
				set SNMP Set Value to 0 it automatically sets it to
				21600(default value)."
			::= { ccDhcpSrvNIC1 10 }

		
		-- 1.3.6.1.4.1.388.6.2.23.11
		ccDhcp1IPRangeTable OBJECT-TYPE
			SYNTAX SEQUENCE OF CcDhcp1IPRangeEntry
			MAX-ACCESS not-accessible
			STATUS current
			DESCRIPTION
				"A table of DHCP IP Ranges for Ethernet 1.
				"
			::= { ccDhcpSrvNIC1 11 }

		
		-- 1.3.6.1.4.1.388.6.2.23.11.1
		ccDhcp1IPRangeEntry OBJECT-TYPE
			SYNTAX CcDhcp1IPRangeEntry
			MAX-ACCESS not-accessible
			STATUS current
			DESCRIPTION
				"A DHCP IP Range entry.
				"
			INDEX { ccDhcp1RangeIndex }
			::= { ccDhcp1IPRangeTable 1 }

		
		CcDhcp1IPRangeEntry ::=
			SEQUENCE { 
				ccDhcp1RangeIndex
					INTEGER,
				ccDhcp1RangeStartIP
					OCTET STRING,
				ccDhcp1RangeEndIP
					OCTET STRING
			 }

		-- 1.3.6.1.4.1.388.6.2.23.11.1.1
		ccDhcp1RangeIndex OBJECT-TYPE
			SYNTAX INTEGER (1..100)
			MAX-ACCESS read-only
			STATUS current
			DESCRIPTION
				"An integer index for ccDhcp1IPRangeTable.
				"
			::= { ccDhcp1IPRangeEntry 1 }

		
		-- 1.3.6.1.4.1.388.6.2.23.11.1.2
		ccDhcp1RangeStartIP OBJECT-TYPE
			SYNTAX OCTET STRING (SIZE (1..32))
			MAX-ACCESS read-only
			STATUS current
			DESCRIPTION
				"The DHCP IP Range Start IP Address.
				"
			::= { ccDhcp1IPRangeEntry 2 }

		
		-- 1.3.6.1.4.1.388.6.2.23.11.1.3
		ccDhcp1RangeEndIP OBJECT-TYPE
			SYNTAX OCTET STRING (SIZE (1..32))
			MAX-ACCESS read-only
			STATUS current
			DESCRIPTION
				"The DHCP IP Range End IP Address.
				"
			::= { ccDhcp1IPRangeEntry 3 }

		
		-- 1.3.6.1.4.1.388.6.2.23.12
		ccDhcp1AddIPRangeObj OBJECT-TYPE
			SYNTAX OCTET STRING (SIZE (1..255))
			MAX-ACCESS read-write
			STATUS current
			DESCRIPTION
				"Add a DHCP dynamically assignable IP address range.
				 	This is a write-only object. Data input syntax:
				 	start_ip[, end_ip].
				"
			::= { ccDhcpSrvNIC1 12 }

		
		-- 1.3.6.1.4.1.388.6.2.23.13
		ccDhcp1RemIPRangeObj OBJECT-TYPE
			SYNTAX OCTET STRING (SIZE (1..255))
			MAX-ACCESS read-write
			STATUS current
			DESCRIPTION
				"Remove a dynamically assignable DHCP IP address range.
				This is a write-only object. Data input syntax:
				start_ip[, end_ip].
				"
			::= { ccDhcpSrvNIC1 13 }

		
		-- 1.3.6.1.4.1.388.6.2.23.14
		ccDhcp1StaticIPTable OBJECT-TYPE
			SYNTAX SEQUENCE OF CcDhcp1StaticIPEntry
			MAX-ACCESS not-accessible
			STATUS current
			DESCRIPTION
				"A table of DHCP Static Entries for Ethernet 1.
				"
			::= { ccDhcpSrvNIC1 14 }

		
		-- 1.3.6.1.4.1.388.6.2.23.14.1
		ccDhcp1StaticIPEntry OBJECT-TYPE
			SYNTAX CcDhcp1StaticIPEntry
			MAX-ACCESS not-accessible
			STATUS current
			DESCRIPTION
				"A DHCP Static IP entry.
				"
			INDEX { ccDhcp1StaticIPIndex }
			::= { ccDhcp1StaticIPTable 1 }

		
		CcDhcp1StaticIPEntry ::=
			SEQUENCE { 
				ccDhcp1StaticIPIndex
					INTEGER,
				ccDhcp1StaticIP
					OCTET STRING,
				ccDhcp1StaticMac
					OCTET STRING,
				ccDhcp1StaticHost
					OCTET STRING
			 }

		-- 1.3.6.1.4.1.388.6.2.23.14.1.1
		ccDhcp1StaticIPIndex OBJECT-TYPE
			SYNTAX INTEGER (1..100)
			MAX-ACCESS read-only
			STATUS current
			DESCRIPTION
				"An integer index for ccDhcp2StaticIPTable.
				"
			::= { ccDhcp1StaticIPEntry 1 }

		
		-- 1.3.6.1.4.1.388.6.2.23.14.1.2
		ccDhcp1StaticIP OBJECT-TYPE
			SYNTAX OCTET STRING (SIZE (1..32))
			MAX-ACCESS read-only
			STATUS current
			DESCRIPTION
				"The DHCP Static Entry IP Address.
				"
			::= { ccDhcp1StaticIPEntry 2 }

		
		-- 1.3.6.1.4.1.388.6.2.23.14.1.3
		ccDhcp1StaticMac OBJECT-TYPE
			SYNTAX OCTET STRING (SIZE (1..32))
			MAX-ACCESS read-only
			STATUS current
			DESCRIPTION
				"The DHCP Static Entry MAC Address.
				"
			::= { ccDhcp1StaticIPEntry 3 }

		
		-- 1.3.6.1.4.1.388.6.2.23.14.1.4
		ccDhcp1StaticHost OBJECT-TYPE
			SYNTAX OCTET STRING (SIZE (1..32))
			MAX-ACCESS read-only
			STATUS current
			DESCRIPTION
				"The DHCP Static Entry host name.
				"
			::= { ccDhcp1StaticIPEntry 4 }

		
		-- 1.3.6.1.4.1.388.6.2.23.15
		ccDhcp1AddStaticIPObj OBJECT-TYPE
			SYNTAX OCTET STRING (SIZE (1..255))
			MAX-ACCESS read-write
			STATUS current
			DESCRIPTION
				"Add a DHCP statically assigned IP address.	
				This is a write-only object. Data input syntax:
				ip_address, mac_address, host_name.
				"
			::= { ccDhcpSrvNIC1 15 }

		
		-- 1.3.6.1.4.1.388.6.2.23.16
		ccDhcp1RemStaticIPObj OBJECT-TYPE
			SYNTAX OCTET STRING (SIZE (1..255))
			MAX-ACCESS read-write
			STATUS current
			DESCRIPTION
				"Remove a DHCP statically assigned IP address.
				This is a write-only object. Data input syntax:
				ip_address.
				"
			::= { ccDhcpSrvNIC1 16 }

		
		-- 1.3.6.1.4.1.388.6.2.23.17
		ccDhcp1OptionTable OBJECT-TYPE
			SYNTAX SEQUENCE OF CcDhcp1OptionEntry
			MAX-ACCESS not-accessible
			STATUS current
			DESCRIPTION
				"A table of DHCP Options for Ethernet 1.
				"
			::= { ccDhcpSrvNIC1 17 }

		
		-- 1.3.6.1.4.1.388.6.2.23.17.1
		ccDhcp1OptionEntry OBJECT-TYPE
			SYNTAX CcDhcp1OptionEntry
			MAX-ACCESS not-accessible
			STATUS current
			DESCRIPTION
				"A DHCP Option entry.
				"
			INDEX { ccDhcp1OptionIndex }
			::= { ccDhcp1OptionTable 1 }

		
		CcDhcp1OptionEntry ::=
			SEQUENCE { 
				ccDhcp1OptionIndex
					INTEGER,
				ccDhcp1OptionName
					OCTET STRING,
				ccDhcp1OptionCode
					OCTET STRING,
				ccDhcp1OptionType
					OCTET STRING,
				ccDhcp1OptionValue
					OCTET STRING
			 }

		-- 1.3.6.1.4.1.388.6.2.23.17.1.1
		ccDhcp1OptionIndex OBJECT-TYPE
			SYNTAX INTEGER (1..100)
			MAX-ACCESS read-only
			STATUS current
			DESCRIPTION
				"An integer index for ccDhcp1OptionTable.
				"
			::= { ccDhcp1OptionEntry 1 }

		
		-- 1.3.6.1.4.1.388.6.2.23.17.1.2
		ccDhcp1OptionName OBJECT-TYPE
			SYNTAX OCTET STRING (SIZE (1..32))
			MAX-ACCESS read-only
			STATUS current
			DESCRIPTION
				"The DHCP Option name.
				"
			::= { ccDhcp1OptionEntry 2 }

		
		-- 1.3.6.1.4.1.388.6.2.23.17.1.3
		ccDhcp1OptionCode OBJECT-TYPE
			SYNTAX OCTET STRING (SIZE (1..32))
			MAX-ACCESS read-only
			STATUS current
			DESCRIPTION
				"The DHCP Option Code.
				"
			::= { ccDhcp1OptionEntry 3 }

		
		-- 1.3.6.1.4.1.388.6.2.23.17.1.4
		ccDhcp1OptionType OBJECT-TYPE
			SYNTAX OCTET STRING (SIZE (1..32))
			MAX-ACCESS read-only
			STATUS current
			DESCRIPTION
				"The DHCP Option type.
				"
			::= { ccDhcp1OptionEntry 4 }

		
		-- 1.3.6.1.4.1.388.6.2.23.17.1.5
		ccDhcp1OptionValue OBJECT-TYPE
			SYNTAX OCTET STRING (SIZE (1..32))
			MAX-ACCESS read-only
			STATUS current
			DESCRIPTION
				"The DHCP option value.
				"
			::= { ccDhcp1OptionEntry 5 }

		
		-- 1.3.6.1.4.1.388.6.2.23.18
		ccDhcp1AddOptionObj OBJECT-TYPE
			SYNTAX OCTET STRING (SIZE (1..255))
			MAX-ACCESS read-write
			STATUS current
			DESCRIPTION
				"Add a DHCP option. This is a write-only object. 
				Data input syntax:
				option_name, option_code, value_type, value
				value_type = ip-address | text
				"
			::= { ccDhcpSrvNIC1 18 }

		
		-- 1.3.6.1.4.1.388.6.2.23.19
		ccDhcp1RemOptionObj OBJECT-TYPE
			SYNTAX OCTET STRING (SIZE (1..255))
			MAX-ACCESS read-write
			STATUS current
			DESCRIPTION
				"Remove a DHCP option.
				This is a write-only object. Data input syntax:
				option_name.
				"
			::= { ccDhcpSrvNIC1 19 }

		
		-- 1.3.6.1.4.1.388.6.2.23.20
		ccDhcp1LeasesTable OBJECT-TYPE
			SYNTAX SEQUENCE OF CcDhcp1LeasesEntry
			MAX-ACCESS not-accessible
			STATUS current
			DESCRIPTION
				"A table of DHCP Leases for Ethernet 1.
				"
			::= { ccDhcpSrvNIC1 20 }

		
		-- 1.3.6.1.4.1.388.6.2.23.20.1
		ccDhcp1LeasesEntry OBJECT-TYPE
			SYNTAX CcDhcp1LeasesEntry
			MAX-ACCESS not-accessible
			STATUS current
			DESCRIPTION
				"A DHCP lease entry.
				"
			INDEX { ccDhcp1LeaseIndex }
			::= { ccDhcp1LeasesTable 1 }

		
		CcDhcp1LeasesEntry ::=
			SEQUENCE { 
				ccDhcp1LeaseIndex
					INTEGER,
				ccDhcp1LeaseIP
					OCTET STRING,
				ccDhcp1LeaseMac
					OCTET STRING,
				ccDhcp1LeaseStartTime
					OCTET STRING,
				ccDhcp1LeaseEndTime
					OCTET STRING
			 }

		-- 1.3.6.1.4.1.388.6.2.23.20.1.1
		ccDhcp1LeaseIndex OBJECT-TYPE
			SYNTAX INTEGER (1..100)
			MAX-ACCESS read-only
			STATUS current
			DESCRIPTION
				"An integer index for ccDhcpLeaseTable1.
				"
			::= { ccDhcp1LeasesEntry 1 }

		
		-- 1.3.6.1.4.1.388.6.2.23.20.1.2
		ccDhcp1LeaseIP OBJECT-TYPE
			SYNTAX OCTET STRING (SIZE (1..32))
			MAX-ACCESS read-only
			STATUS current
			DESCRIPTION
				"The DHCP lease IP address assigned to MU.
				"
			::= { ccDhcp1LeasesEntry 2 }

		
		-- 1.3.6.1.4.1.388.6.2.23.20.1.3
		ccDhcp1LeaseMac OBJECT-TYPE
			SYNTAX OCTET STRING (SIZE (1..32))
			MAX-ACCESS read-only
			STATUS current
			DESCRIPTION
				"The DHCP lease MAC address for MU.
				"
			::= { ccDhcp1LeasesEntry 3 }

		
		-- 1.3.6.1.4.1.388.6.2.23.20.1.4
		ccDhcp1LeaseStartTime OBJECT-TYPE
			SYNTAX OCTET STRING (SIZE (1..32))
			MAX-ACCESS read-only
			STATUS current
			DESCRIPTION
				"The DHCP lease start time.
				"
			::= { ccDhcp1LeasesEntry 4 }

		
		-- 1.3.6.1.4.1.388.6.2.23.20.1.5
		ccDhcp1LeaseEndTime OBJECT-TYPE
			SYNTAX OCTET STRING (SIZE (1..32))
			MAX-ACCESS read-only
			STATUS current
			DESCRIPTION
				"The DHCP lease expiration time.
				"
			::= { ccDhcp1LeasesEntry 5 }

		
		-- 1.3.6.1.4.1.388.6.2.23.21
		ccDhcp1RemLeaseObj OBJECT-TYPE
			SYNTAX OCTET STRING (SIZE (1..255))
			MAX-ACCESS read-write
			STATUS current
			DESCRIPTION
				"Remove a DHCP lease.
				This is a write-only object. Data input syntax:
				ip_address.
				"
			::= { ccDhcpSrvNIC1 21 }

		
		-- 1.3.6.1.4.1.388.6.2.23.22
		ccDhcp1RemStaticHost OBJECT-TYPE
			SYNTAX DisplayString
			MAX-ACCESS read-write
			STATUS current
			DESCRIPTION
				"Remove a DHCP statically assigned Host name.
				Data input syntax: Host name. 
				A get operation on ccDhcp1RemStaticHost displays
				all the available StaticHost's.
				"
			::= { ccDhcpSrvNIC1 22 }

		
		-- 1.3.6.1.4.1.388.6.2.24
		ccDhcpSrvNIC2 OBJECT IDENTIFIER ::= { symbolCCInterfaces 24 }

		
		-- 1.3.6.1.4.1.388.6.2.24.1
		ccDhcp2Srv OBJECT-TYPE
			SYNTAX INTEGER (0..1)
			MAX-ACCESS read-write
			STATUS current
			DESCRIPTION
				"Enable(1)/Disable(2) DHCP Server on Ethernet 2.
				 Note:DHCP Server can be enabled only on single 
				 interface at a time.
				
				Note:This Feature is VPN dependent feature hence
				if vpnsupport is not enabled then the walk over
				ccDhcpSrvNIC2 will not return anything and the set
				operation over any OID under this table will return 
				an error message- No creation.
				
								
				"
			::= { ccDhcpSrvNIC2 1 }

		
		-- 1.3.6.1.4.1.388.6.2.24.2
		ccDhcp2Subnet OBJECT-TYPE
			SYNTAX IpAddress
			MAX-ACCESS read-only
			STATUS current
			DESCRIPTION
				"The subnet on Ethernet port 2 that the 
				DHCP Server serves IP address for.
				"
			::= { ccDhcpSrvNIC2 2 }

		
		-- 1.3.6.1.4.1.388.6.2.24.3
		ccDhcp2Netmask OBJECT-TYPE
			SYNTAX IpAddress
			MAX-ACCESS read-only
			STATUS current
			DESCRIPTION
				"The netmask address for the Ethernet port 2
				that the DHCP Server serves IP addresses for.
				"
			::= { ccDhcpSrvNIC2 3 }

		
		-- 1.3.6.1.4.1.388.6.2.24.4
		ccDhcp2BcastIP OBJECT-TYPE
			SYNTAX IpAddress
			MAX-ACCESS read-only
			STATUS current
			DESCRIPTION
				"The broadcast IP address for the subnet the
				 	DHCP Server serves on Ethernet Port 2.
				"
			::= { ccDhcpSrvNIC2 4 }

		
		-- 1.3.6.1.4.1.388.6.2.24.5
		ccDhcp2RouterIP OBJECT-TYPE
			SYNTAX IpAddress
			MAX-ACCESS read-write
			STATUS current
			DESCRIPTION
				"The default Router/Gateway IP address for the subnet 
				the DHCP Server serves on Ethernet Port 2. To remove
				the router option set SNMP Set Value to 0.0.0.0 ."
			::= { ccDhcpSrvNIC2 5 }

		
		-- 1.3.6.1.4.1.388.6.2.24.6
		ccDhcp2PriDNSIP OBJECT-TYPE
			SYNTAX IpAddress
			MAX-ACCESS read-write
			STATUS current
			DESCRIPTION
				"The Primary DNS IP address for the subnet
				the DHCP Server serves on Ethernet Port 2. To
				remove domain-name-servers option, set SNMP Set
				Value to 0.0.0.0 ."
			::= { ccDhcpSrvNIC2 6 }

		
		-- 1.3.6.1.4.1.388.6.2.24.7
		ccDhcp2SecDNSIP OBJECT-TYPE
			SYNTAX IpAddress
			MAX-ACCESS read-write
			STATUS current
			DESCRIPTION
				"The Secondary DNS IP address for the subnet
				the DHCP Server serves on Ethernet Port 2. To
				remove Secondary DNS IP, set SNMP Set Value 
				to 0.0.0.0 ."
			::= { ccDhcpSrvNIC2 7 }

		
		-- 1.3.6.1.4.1.388.6.2.24.8
		ccDhcp2DomainName OBJECT-TYPE
			SYNTAX OCTET STRING (SIZE (1..100))
			MAX-ACCESS read-write
			STATUS current
			DESCRIPTION
				"The Domain Name for the subnet the DHCP Server
				 	serves on Ethernet Port 2. To remove domain-name
				 	option, set SNMP Set Value to 0.
				"
			::= { ccDhcpSrvNIC2 8 }

		
		-- 1.3.6.1.4.1.388.6.2.24.9
		ccDhcp2DefLease OBJECT-TYPE
			SYNTAX Integer32 (0..31536000)
			UNITS "seconds"
			MAX-ACCESS read-write
			STATUS current
			DESCRIPTION
				"The Default lease time of the IP address for 
				the subnet the DHCP Server serves on
				Ethernet Port 2. To set to default-lease-time option,
				set SNMP Set Value to 0 it automatically sets it to
				21600(default value)."
			::= { ccDhcpSrvNIC2 9 }

		
		-- 1.3.6.1.4.1.388.6.2.24.10
		ccDhcp2MaxLease OBJECT-TYPE
			SYNTAX Integer32 (0..31536000)
			UNITS "seconds"
			MAX-ACCESS read-write
			STATUS current
			DESCRIPTION
				"The Maximum lease time of the IP address for 
				the subnet the DHCP Server serves on 
				Ethernet Port 2. To set to max-lease-time option,
				set SNMP Set Value to 0 it automatically sets it to
				21600(default value).
				
				"
			::= { ccDhcpSrvNIC2 10 }

		
		-- 1.3.6.1.4.1.388.6.2.24.11
		ccDhcp2IPRangeTable OBJECT-TYPE
			SYNTAX SEQUENCE OF CcDhcp2IPRangeEntry
			MAX-ACCESS not-accessible
			STATUS current
			DESCRIPTION
				"A table of DHCP IP Ranges for Ethernet 2.
				"
			::= { ccDhcpSrvNIC2 11 }

		
		-- 1.3.6.1.4.1.388.6.2.24.11.1
		ccDhcp2IPRangeEntry OBJECT-TYPE
			SYNTAX CcDhcp2IPRangeEntry
			MAX-ACCESS not-accessible
			STATUS current
			DESCRIPTION
				"A DHCP IP Range entry.
				"
			INDEX { ccDhcp2RangeIndex }
			::= { ccDhcp2IPRangeTable 1 }

		
		CcDhcp2IPRangeEntry ::=
			SEQUENCE { 
				ccDhcp2RangeIndex
					INTEGER,
				ccDhcp2RangeStartIP
					OCTET STRING,
				ccDhcp2RangeEndIP
					OCTET STRING
			 }

		-- 1.3.6.1.4.1.388.6.2.24.11.1.1
		ccDhcp2RangeIndex OBJECT-TYPE
			SYNTAX INTEGER (1..100)
			MAX-ACCESS read-only
			STATUS current
			DESCRIPTION
				"An integer index for ccDhcp1IPRangeTable.
				"
			::= { ccDhcp2IPRangeEntry 1 }

		
		-- 1.3.6.1.4.1.388.6.2.24.11.1.2
		ccDhcp2RangeStartIP OBJECT-TYPE
			SYNTAX OCTET STRING (SIZE (1..32))
			MAX-ACCESS read-only
			STATUS current
			DESCRIPTION
				"The DHCP IP Range Start IP Address.
				"
			::= { ccDhcp2IPRangeEntry 2 }

		
		-- 1.3.6.1.4.1.388.6.2.24.11.1.3
		ccDhcp2RangeEndIP OBJECT-TYPE
			SYNTAX OCTET STRING (SIZE (1..32))
			MAX-ACCESS read-only
			STATUS current
			DESCRIPTION
				"The DHCP IP Range End IP Address.
				"
			::= { ccDhcp2IPRangeEntry 3 }

		
		-- 1.3.6.1.4.1.388.6.2.24.12
		ccDhcp2AddIPRangeObj OBJECT-TYPE
			SYNTAX OCTET STRING (SIZE (1..255))
			MAX-ACCESS read-write
			STATUS current
			DESCRIPTION
				"Add a DHCP dynamically assignable IP address range.
				 	This is a write-only object. Data input syntax:
				 	start_ip[, end_ip].
				"
			::= { ccDhcpSrvNIC2 12 }

		
		-- 1.3.6.1.4.1.388.6.2.24.13
		ccDhcp2RemIPRangeObj OBJECT-TYPE
			SYNTAX OCTET STRING (SIZE (1..255))
			MAX-ACCESS read-write
			STATUS current
			DESCRIPTION
				"Remove a dynamically assignable DHCP IP address range.
				 	This is a write-only object. Data input syntax:
				 	start_ip[, end_ip].
				"
			::= { ccDhcpSrvNIC2 13 }

		
		-- 1.3.6.1.4.1.388.6.2.24.14
		ccDhcp2StaticIPTable OBJECT-TYPE
			SYNTAX SEQUENCE OF CcDhcp2StaticIPEntry
			MAX-ACCESS not-accessible
			STATUS current
			DESCRIPTION
				"A table of DHCP Static Entries for Ethernet 2.
				"
			::= { ccDhcpSrvNIC2 14 }

		
		-- 1.3.6.1.4.1.388.6.2.24.14.1
		ccDhcp2StaticIPEntry OBJECT-TYPE
			SYNTAX CcDhcp2StaticIPEntry
			MAX-ACCESS not-accessible
			STATUS current
			DESCRIPTION
				"A DHCP Static IP entry."
			INDEX { ccDhcp2StaticIPIndex }
			::= { ccDhcp2StaticIPTable 1 }

		
		CcDhcp2StaticIPEntry ::=
			SEQUENCE { 
				ccDhcp2StaticIPIndex
					INTEGER,
				ccDhcp2StaticIP
					OCTET STRING,
				ccDhcp2StaticMac
					OCTET STRING,
				ccDhcp2StaticHost
					OCTET STRING
			 }

		-- 1.3.6.1.4.1.388.6.2.24.14.1.1
		ccDhcp2StaticIPIndex OBJECT-TYPE
			SYNTAX INTEGER (1..100)
			MAX-ACCESS read-only
			STATUS current
			DESCRIPTION
				"An integer index for ccDhcp2StaticIPTable.
				"
			::= { ccDhcp2StaticIPEntry 1 }

		
		-- 1.3.6.1.4.1.388.6.2.24.14.1.2
		ccDhcp2StaticIP OBJECT-TYPE
			SYNTAX OCTET STRING (SIZE (1..32))
			MAX-ACCESS read-write
			STATUS current
			DESCRIPTION
				"The DHCP Static Entry IP Address.
				"
			::= { ccDhcp2StaticIPEntry 2 }

		
		-- 1.3.6.1.4.1.388.6.2.24.14.1.3
		ccDhcp2StaticMac OBJECT-TYPE
			SYNTAX OCTET STRING (SIZE (1..32))
			MAX-ACCESS read-only
			STATUS current
			DESCRIPTION
				"The DHCP Static Entry MAC Address.
				"
			::= { ccDhcp2StaticIPEntry 3 }

		
		-- 1.3.6.1.4.1.388.6.2.24.14.1.4
		ccDhcp2StaticHost OBJECT-TYPE
			SYNTAX OCTET STRING (SIZE (1..32))
			MAX-ACCESS read-only
			STATUS current
			DESCRIPTION
				"The DHCP Static Entry host name.
				"
			::= { ccDhcp2StaticIPEntry 4 }

		
		-- 1.3.6.1.4.1.388.6.2.24.15
		ccDhcp2AddStaticIPObj OBJECT-TYPE
			SYNTAX OCTET STRING (SIZE (1..255))
			MAX-ACCESS read-write
			STATUS current
			DESCRIPTION
				"Add a DHCP statically assigned IP address.	
				 	This is a write-only object. Data input syntax:
				 	ip_address, mac_address, host_name.
				"
			::= { ccDhcpSrvNIC2 15 }

		
		-- 1.3.6.1.4.1.388.6.2.24.16
		ccDhcp2RemStaticIPObj OBJECT-TYPE
			SYNTAX OCTET STRING (SIZE (1..255))
			MAX-ACCESS read-write
			STATUS current
			DESCRIPTION
				"Remove a DHCP statically assigned IP address.
				 	This is a write-only object. Data input syntax:
				 	ip_address.
				"
			::= { ccDhcpSrvNIC2 16 }

		
		-- 1.3.6.1.4.1.388.6.2.24.17
		ccDhcp2OptionTable OBJECT-TYPE
			SYNTAX SEQUENCE OF CcDhcp2OptionEntry
			MAX-ACCESS not-accessible
			STATUS current
			DESCRIPTION
				"A table of DHCP Options for Ethernet 2.
				"
			::= { ccDhcpSrvNIC2 17 }

		
		-- 1.3.6.1.4.1.388.6.2.24.17.1
		ccDhcp2OptionEntry OBJECT-TYPE
			SYNTAX CcDhcp2OptionEntry
			MAX-ACCESS not-accessible
			STATUS current
			DESCRIPTION
				"A DHCP Option entry.
				"
			INDEX { ccDhcp2OptionIndex }
			::= { ccDhcp2OptionTable 1 }

		
		CcDhcp2OptionEntry ::=
			SEQUENCE { 
				ccDhcp2OptionIndex
					INTEGER,
				ccDhcp2OptionName
					OCTET STRING,
				ccDhcp2OptionCode
					OCTET STRING,
				ccDhcp2OptionType
					OCTET STRING,
				ccDhcp2OptionValue
					OCTET STRING
			 }

		-- 1.3.6.1.4.1.388.6.2.24.17.1.1
		ccDhcp2OptionIndex OBJECT-TYPE
			SYNTAX INTEGER (1..100)
			MAX-ACCESS read-only
			STATUS current
			DESCRIPTION
				"An integer index for ccDhcp2OptionTable.
				"
			::= { ccDhcp2OptionEntry 1 }

		
		-- 1.3.6.1.4.1.388.6.2.24.17.1.2
		ccDhcp2OptionName OBJECT-TYPE
			SYNTAX OCTET STRING (SIZE (1..32))
			MAX-ACCESS read-only
			STATUS current
			DESCRIPTION
				"The DHCP Option name.
				"
			::= { ccDhcp2OptionEntry 2 }

		
		-- 1.3.6.1.4.1.388.6.2.24.17.1.3
		ccDhcp2OptionCode OBJECT-TYPE
			SYNTAX OCTET STRING (SIZE (1..32))
			MAX-ACCESS read-write
			STATUS current
			DESCRIPTION
				"The DHCP Option Code.
				"
			::= { ccDhcp2OptionEntry 3 }

		
		-- 1.3.6.1.4.1.388.6.2.24.17.1.4
		ccDhcp2OptionType OBJECT-TYPE
			SYNTAX OCTET STRING (SIZE (1..32))
			MAX-ACCESS read-only
			STATUS current
			DESCRIPTION
				"The DHCP Option type.
				"
			::= { ccDhcp2OptionEntry 4 }

		
		-- 1.3.6.1.4.1.388.6.2.24.17.1.5
		ccDhcp2OptionValue OBJECT-TYPE
			SYNTAX OCTET STRING (SIZE (1..32))
			MAX-ACCESS read-only
			STATUS current
			DESCRIPTION
				"The DHCP option value.
				"
			::= { ccDhcp2OptionEntry 5 }

		
		-- 1.3.6.1.4.1.388.6.2.24.18
		ccDhcp2AddOptionObj OBJECT-TYPE
			SYNTAX OCTET STRING (SIZE (1..255))
			MAX-ACCESS read-write
			STATUS current
			DESCRIPTION
				"Add a DHCP option. This is a write-only object. 
				 	Data input syntax:
				 	option_name, option_code, value_type, value
				 	value_type = ip-address | text
				"
			::= { ccDhcpSrvNIC2 18 }

		
		-- 1.3.6.1.4.1.388.6.2.24.19
		ccDhcp2RemOptionObj OBJECT-TYPE
			SYNTAX OCTET STRING (SIZE (1..255))
			MAX-ACCESS read-write
			STATUS current
			DESCRIPTION
				"Remove a DHCP option.
				 	This is a write-only object. Data input syntax:
				 	option_name.
				"
			::= { ccDhcpSrvNIC2 19 }

		
		-- 1.3.6.1.4.1.388.6.2.24.20
		ccDhcp2LeasesTable OBJECT-TYPE
			SYNTAX SEQUENCE OF CcDhcp2LeasesEntry
			MAX-ACCESS not-accessible
			STATUS current
			DESCRIPTION
				"A table of DHCP Leases for Ethernet 2.
				"
			::= { ccDhcpSrvNIC2 20 }

		
		-- 1.3.6.1.4.1.388.6.2.24.20.1
		ccDhcp2LeasesEntry OBJECT-TYPE
			SYNTAX CcDhcp2LeasesEntry
			MAX-ACCESS not-accessible
			STATUS current
			DESCRIPTION
				"A DHCP lease entry.
				"
			INDEX { ccDhcp1LeaseIndex }
			::= { ccDhcp2LeasesTable 1 }

		
		CcDhcp2LeasesEntry ::=
			SEQUENCE { 
				ccDhcp2LeaseIndex
					INTEGER,
				ccDhcp2LeaseIP
					OCTET STRING,
				ccDhcp2LeaseMac
					OCTET STRING,
				ccDhcp2LeaseStartTime
					OCTET STRING,
				ccDhcp2LeaseEndTime
					OCTET STRING
			 }

		-- 1.3.6.1.4.1.388.6.2.24.20.1.1
		ccDhcp2LeaseIndex OBJECT-TYPE
			SYNTAX INTEGER (1..100)
			MAX-ACCESS read-write
			STATUS current
			DESCRIPTION
				"An integer index for ccDhcp2LeaseTable.
				"
			::= { ccDhcp2LeasesEntry 1 }

		
		-- 1.3.6.1.4.1.388.6.2.24.20.1.2
		ccDhcp2LeaseIP OBJECT-TYPE
			SYNTAX OCTET STRING (SIZE (1..32))
			MAX-ACCESS read-only
			STATUS current
			DESCRIPTION
				"The DHCP lease IP address assigned to MU.
				"
			::= { ccDhcp2LeasesEntry 2 }

		
		-- 1.3.6.1.4.1.388.6.2.24.20.1.3
		ccDhcp2LeaseMac OBJECT-TYPE
			SYNTAX OCTET STRING (SIZE (1..32))
			MAX-ACCESS read-only
			STATUS current
			DESCRIPTION
				"The DHCP lease MAC address for MU.
				"
			::= { ccDhcp2LeasesEntry 3 }

		
		-- 1.3.6.1.4.1.388.6.2.24.20.1.4
		ccDhcp2LeaseStartTime OBJECT-TYPE
			SYNTAX OCTET STRING (SIZE (1..32))
			MAX-ACCESS read-only
			STATUS current
			DESCRIPTION
				"The DHCP lease start time.
				"
			::= { ccDhcp2LeasesEntry 4 }

		
		-- 1.3.6.1.4.1.388.6.2.24.20.1.5
		ccDhcp2LeaseEndTime OBJECT-TYPE
			SYNTAX OCTET STRING (SIZE (1..32))
			MAX-ACCESS read-write
			STATUS current
			DESCRIPTION
				"The DHCP lease expiration time.
				"
			::= { ccDhcp2LeasesEntry 5 }

		
		-- 1.3.6.1.4.1.388.6.2.24.21
		ccDhcp2RemLeaseObj OBJECT-TYPE
			SYNTAX OCTET STRING (SIZE (1..255))
			MAX-ACCESS read-write
			STATUS current
			DESCRIPTION
				"Remove a DHCP lease.
				This is a write-only object. Data input syntax:
				ip_address.
				"
			::= { ccDhcpSrvNIC2 21 }

		
		-- 1.3.6.1.4.1.388.6.2.24.22
		ccDhcp2RemStaticHost OBJECT-TYPE
			SYNTAX DisplayString
			MAX-ACCESS read-write
			STATUS current
			DESCRIPTION
				"Remove a DHCP statically assigned Host name.
				Data input syntax: Host name. 
				A get operation on ccDhcp2RemStaticHost displays
				all the available StaticHost's"
			::= { ccDhcpSrvNIC2 22 }

		
		-- 1.3.6.1.4.1.388.6.3
		symbolCCMgmt OBJECT IDENTIFIER ::= { symbolCC 3 }

		
		-- 1.3.6.1.4.1.388.6.3.1
		ccWLANAddObj OBJECT-TYPE
			SYNTAX DisplayString (SIZE (1..50))
			MAX-ACCESS read-write
			STATUS current
			DESCRIPTION
				"Add one WLAN Object into the WLAN Table. The Maximum length of the WLAN 
				Name can be 50 characters, Note that the following characters cannot be part 
				of WLAN Name field, double quotes,',.,\,& and #."
			::= { symbolCCMgmt 1 }

		
		-- 1.3.6.1.4.1.388.6.3.2
		ccWLANRemObj OBJECT-TYPE
			SYNTAX DisplayString (SIZE (1..50))
			MAX-ACCESS read-write
			STATUS current
			DESCRIPTION
				"Remove one WLAN Object from the WLAN Table.The maximum number of 
				characters allowed is 50, and the following characters cannot be
				part of the input string - ',.,\,&, # and double quotes."
			::= { symbolCCMgmt 2 }

		
		-- 1.3.6.1.4.1.388.6.3.3
		ccUserAddObj OBJECT-TYPE
			SYNTAX DisplayString (SIZE (1..32))
			MAX-ACCESS read-write
			STATUS current
			DESCRIPTION
				"Add a user to the User Table. The Maximum length of the User name 
				can be 20 characters. Note that the following characters cannot be part 
				of User Name field - ',&,#,\,space, and double quotes."
			::= { symbolCCMgmt 3 }

		
		-- 1.3.6.1.4.1.388.6.3.4
		ccUserRemObj OBJECT-TYPE
			SYNTAX DisplayString (SIZE (1..32))
			MAX-ACCESS read-write
			STATUS current
			DESCRIPTION
				"Remove a user from the User Table."
			::= { symbolCCMgmt 4 }

		
		-- 1.3.6.1.4.1.388.6.3.5
		ccGraphAddObj OBJECT-TYPE
			SYNTAX DisplayString (SIZE (1..32))
			MAX-ACCESS read-write
			STATUS current
			DESCRIPTION
				"Add a Graph object to the Graph table."
			::= { symbolCCMgmt 5 }

		
		-- 1.3.6.1.4.1.388.6.3.6
		ccGraphRemObj OBJECT-TYPE
			SYNTAX DisplayString (SIZE (1..32))
			MAX-ACCESS read-write
			STATUS current
			DESCRIPTION
				"Remove a Graph object from the Graph table."
			::= { symbolCCMgmt 6 }

		
		-- 1.3.6.1.4.1.388.6.3.11
		ccSecAddObj OBJECT-TYPE
			SYNTAX DisplayString (SIZE (1..32))
			MAX-ACCESS read-write
			STATUS current
			DESCRIPTION
				"Add a security object into the table."
			::= { symbolCCMgmt 11 }

		
		-- 1.3.6.1.4.1.388.6.3.12
		ccSecRemObj OBJECT-TYPE
			SYNTAX DisplayString (SIZE (1..32))
			MAX-ACCESS read-write
			STATUS current
			DESCRIPTION
				"Remove a security object from the table."
			::= { symbolCCMgmt 12 }

		
		-- 1.3.6.1.4.1.388.6.3.13
		ccACLAddObj OBJECT-TYPE
			SYNTAX DisplayString (SIZE (1..32))
			MAX-ACCESS read-write
			STATUS current
			DESCRIPTION
				"Add an ACL object into the table."
			::= { symbolCCMgmt 13 }

		
		-- 1.3.6.1.4.1.388.6.3.14
		ccACLRemObj OBJECT-TYPE
			SYNTAX DisplayString (SIZE (1..32))
			MAX-ACCESS read-write
			STATUS current
			DESCRIPTION
				"Remove an ACL object from the table."
			::= { symbolCCMgmt 14 }

		
		-- 1.3.6.1.4.1.388.6.3.21
		ccUserTable OBJECT-TYPE
			SYNTAX SEQUENCE OF CcUserEntry
			MAX-ACCESS not-accessible
			STATUS current
			DESCRIPTION
				"User information table entries. "
			::= { symbolCCMgmt 21 }

		
		-- 1.3.6.1.4.1.388.6.3.21.1
		ccUserEntry OBJECT-TYPE
			SYNTAX CcUserEntry
			MAX-ACCESS not-accessible
			STATUS current
			DESCRIPTION
				"User Information entries."
			INDEX { ccUserIndex }
			::= { ccUserTable 1 }

		
		CcUserEntry ::=
			SEQUENCE { 
				ccUserID
					DisplayString,
				ccUserFullName
					DisplayString,
				ccUserPwd
					DisplayString,
				ccUserAdminRight
					TruthValue,
				ccUserProfileMgmtRight
					TruthValue,
				ccUserSysAdminRight
					TruthValue,
				ccUserSNMPAdminRight
					TruthValue,
				ccUserSecurityAdminRight
					TruthValue,
				ccUserIndex
					INTEGER
			 }

		-- 1.3.6.1.4.1.388.6.3.21.1.1
		ccUserID OBJECT-TYPE
			SYNTAX DisplayString (SIZE (1..32))
			MAX-ACCESS read-only
			STATUS current
			DESCRIPTION
				"The user name. Cannot
				change the user id, but can achieve the same
				goal through removing and recreating a new
				user with a different name."
			::= { ccUserEntry 1 }

		
		-- 1.3.6.1.4.1.388.6.3.21.1.2
		ccUserFullName OBJECT-TYPE
			SYNTAX DisplayString (SIZE (1..20))
			MAX-ACCESS read-write
			STATUS current
			DESCRIPTION
				"The full name of the user. The Maximum length of the User name 
				can be 20 characters. Note that the following characters cannot be part 
				of User Name field - ',&,#,space and double quotes."
			::= { ccUserEntry 2 }

		
		-- 1.3.6.1.4.1.388.6.3.21.1.3
		ccUserPwd OBJECT-TYPE
			SYNTAX DisplayString (SIZE (6..20))
			MAX-ACCESS read-write
			STATUS current
			DESCRIPTION
				"The user login password to access Wireless Switch services. 
				The Maximum length of the Password is 20 characters. 
				Note that the following characters cannot be part of the password field - ',&,#,\,space and double quotes."
			::= { ccUserEntry 3 }

		
		-- 1.3.6.1.4.1.388.6.3.21.1.4
		ccUserAdminRight OBJECT-TYPE
			SYNTAX TruthValue
			MAX-ACCESS read-write
			STATUS deprecated
			DESCRIPTION
				"Setting this object to the value <true(1)> gives the user admin 
				rights, <false(2)> takes away the admin rights from the user."
			DEFVAL { true }
			::= { ccUserEntry 4 }

		
		-- 1.3.6.1.4.1.388.6.3.21.1.5
		ccUserProfileMgmtRight OBJECT-TYPE
			SYNTAX TruthValue
			MAX-ACCESS read-write
			STATUS current
			DESCRIPTION
				"Setting this object to the value <true(1)> gives the user 
				Profile Management rights, 
				<false(2)> takes away the Profile Management rights from the user."
			DEFVAL { true }
			::= { ccUserEntry 5 }

		
		-- 1.3.6.1.4.1.388.6.3.21.1.6
		ccUserSysAdminRight OBJECT-TYPE
			SYNTAX TruthValue
			MAX-ACCESS read-write
			STATUS current
			DESCRIPTION
				"Setting this object to the value <true(1)> gives the user Sys-Admin 
				rights, <false(2)> takes away the Sys-Admin rights from the user."
			DEFVAL { false }
			::= { ccUserEntry 6 }

		
		-- 1.3.6.1.4.1.388.6.3.21.1.7
		ccUserSNMPAdminRight OBJECT-TYPE
			SYNTAX TruthValue
			MAX-ACCESS read-write
			STATUS current
			DESCRIPTION
				"Setting this object to the value <true(1)> gives the user SNMP-
				Admin rights, <false(2)> takes away the SNMP-Admin rights from the 
				user."
			DEFVAL { true }
			::= { ccUserEntry 7 }

		
		-- 1.3.6.1.4.1.388.6.3.21.1.8
		ccUserSecurityAdminRight OBJECT-TYPE
			SYNTAX TruthValue
			MAX-ACCESS read-write
			STATUS current
			DESCRIPTION
				"Setting this object to the value <true(1)> gives the user Security-
				Admin rights, <false(2)> takes away the Security-Admin rights from 
				the user."
			DEFVAL { true }
			::= { ccUserEntry 8 }

		
		-- 1.3.6.1.4.1.388.6.3.21.1.10
		ccUserIndex OBJECT-TYPE
			SYNTAX INTEGER (1..200)
			MAX-ACCESS not-accessible
			STATUS current
			DESCRIPTION
				"The index of the user table."
			::= { ccUserEntry 10 }

		
		-- 1.3.6.1.4.1.388.6.3.22
		ccWLANTable OBJECT-TYPE
			SYNTAX SEQUENCE OF CcWLANEntry
			MAX-ACCESS not-accessible
			STATUS current
			DESCRIPTION
				"A list of WLAN Object entries."
			::= { symbolCCMgmt 22 }

		
		-- 1.3.6.1.4.1.388.6.3.22.1
		ccWLANEntry OBJECT-TYPE
			SYNTAX CcWLANEntry
			MAX-ACCESS not-accessible
			STATUS current
			DESCRIPTION
				"A WLAN Object entry."
			INDEX { ccWLANIndex }
			::= { ccWLANTable 1 }

		
		CcWLANEntry ::=
			SEQUENCE { 
				ccWLANIndex
					INTEGER,
				ccWLANName
					DisplayString,
				ccESSID
					DisplayString,
				ccSecurity
					DisplayString,
				ccACLEnabled
					TruthValue,
				ccMaxMus
					INTEGER,
				ccKerberosAuthName
					DisplayString,
				ccKerberosAuthPass
					DisplayString,
				ccWLANACL
					DisplayString,
				ccWLANIsAuthenticated
					TruthValue,
				ccWLANMUTraffic
					INTEGER,
				ccWLANSecuredBeacon
					TruthValue,
				ccWLANCurrentMU
					INTEGER,
				ccWLANNetMask
					IpAddress,
				ccWLANDefaultRoute
					IpAddress,
				ccWLANBCMC11A
					EncrType,
				ccWLANBCMC11B
					EncrType,
				ccWLANBCMCFH
					EncrType,
				ccBroadcastEss
					TruthValue,
				ccWLANDesc
					DisplayString,
				ccWlanWMEEnable
					DisplayString,
				ccWlanWMEProfile
					DisplayString
			 }

		-- 1.3.6.1.4.1.388.6.3.22.1.1
		ccWLANIndex OBJECT-TYPE
			SYNTAX INTEGER (1..100)
			MAX-ACCESS read-only
			STATUS current
			DESCRIPTION
				"The index for this WLAN object. "
			::= { ccWLANEntry 1 }
-- Mower: changed range from 0.. to 1..
		
		-- 1.3.6.1.4.1.388.6.3.22.1.2
		ccWLANName OBJECT-TYPE
			SYNTAX DisplayString (SIZE (1..50))
			MAX-ACCESS read-write
			STATUS current
			DESCRIPTION
				"The WLAN object name. The Maximum length of the WLAN Name can be 50 
				characters. Note that the following characters cannot be part of WLAN 
				Name field - ',.,\,&,# and double quotes."
			::= { ccWLANEntry 2 }

		
		-- 1.3.6.1.4.1.388.6.3.22.1.3
		ccESSID OBJECT-TYPE
			SYNTAX DisplayString (SIZE (1..32))
			MAX-ACCESS read-write
			STATUS current
			DESCRIPTION
				"The ESSID for the interface."
			::= { ccWLANEntry 3 }

		
		-- 1.3.6.1.4.1.388.6.3.22.1.4
		ccSecurity OBJECT-TYPE
			SYNTAX DisplayString (SIZE (1..50))
			MAX-ACCESS read-write
			STATUS current
			DESCRIPTION
				"A security Policy to be used by this WLAN.
				If your Network Manager/MIB Browser displays
				an error message, it is likely that the security policy 
				being added is invalid. To find out what the problem could be
				with this particular security policy, query the OID 'ccSecCheckValidity' 
				under ccSecurityTable, and make appropriate changes."
			::= { ccWLANEntry 4 }

		
		-- 1.3.6.1.4.1.388.6.3.22.1.5
		ccACLEnabled OBJECT-TYPE
			SYNTAX TruthValue
			MAX-ACCESS read-write
			STATUS current
			DESCRIPTION
				"Enable or Disable ACL feature."
			::= { ccWLANEntry 5 }

		
		-- 1.3.6.1.4.1.388.6.3.22.1.14
		ccMaxMus OBJECT-TYPE
			SYNTAX INTEGER (1..4096)
			MAX-ACCESS read-write
			STATUS current
			DESCRIPTION
				"The maximum number of MUs supported by this WLAN."
			::= { ccWLANEntry 14 }

		
		-- 1.3.6.1.4.1.388.6.3.22.1.15
		ccKerberosAuthName OBJECT-TYPE
			SYNTAX DisplayString (SIZE (1..32))
			MAX-ACCESS read-write
			STATUS current
			DESCRIPTION
				"The name used for authenticating to a Kerberos Server."
			::= { ccWLANEntry 15 }
-- Kerberos auth name is same as ESSID of a WLAN so it cannot be changed.
		
		-- 1.3.6.1.4.1.388.6.3.22.1.16
		ccKerberosAuthPass OBJECT-TYPE
			SYNTAX DisplayString (SIZE (6..32))
			MAX-ACCESS read-write
			STATUS current
			DESCRIPTION
				"The password for authenticating to a Kerberos Server. The
				minimum length of a password to 6 characters."
			::= { ccWLANEntry 16 }

		
		-- 1.3.6.1.4.1.388.6.3.22.1.17
		ccWLANACL OBJECT-TYPE
			SYNTAX DisplayString (SIZE (1..32))
			MAX-ACCESS read-write
			STATUS current
			DESCRIPTION
				" The ACL used by this WLAN.
				For removing the ACL from this WLAN,
				just input an empty string."
			::= { ccWLANEntry 17 }

		
		-- 1.3.6.1.4.1.388.6.3.22.1.18
		ccWLANIsAuthenticated OBJECT-TYPE
			SYNTAX TruthValue
			MAX-ACCESS read-only
			STATUS current
			DESCRIPTION
				"Tells whether the WLAN is authenticated 
				or not."
			::= { ccWLANEntry 18 }

		
		-- 1.3.6.1.4.1.388.6.3.22.1.19
		ccWLANMUTraffic OBJECT-TYPE
			SYNTAX INTEGER (0..2)
			MAX-ACCESS read-write
			STATUS current
			DESCRIPTION
				"Changes the results of an MU to MU commmunication.
				0 indicates that MU to MU traffic is allowed,
				1 indicates that it is not allowed
				and 2 indicates that all MU to MU traffic is dropped."
			::= { ccWLANEntry 19 }

		
		-- 1.3.6.1.4.1.388.6.3.22.1.20
		ccWLANSecuredBeacon OBJECT-TYPE
			SYNTAX TruthValue
			MAX-ACCESS read-write
			STATUS current
			DESCRIPTION
				"'true' indicates that beacons need to be secured,
				while 'false' allows them to be unsecured."
			::= { ccWLANEntry 20 }

		
		-- 1.3.6.1.4.1.388.6.3.22.1.21
		ccWLANCurrentMU OBJECT-TYPE
			SYNTAX INTEGER (1..4096)
			MAX-ACCESS read-only
			STATUS current
			DESCRIPTION
				"The current number of MUs on this WLAN"
			::= { ccWLANEntry 21 }

		
		-- 1.3.6.1.4.1.388.6.3.22.1.22
		ccWLANNetMask OBJECT-TYPE
			SYNTAX IpAddress
			MAX-ACCESS read-write
			STATUS current
			DESCRIPTION
				"The Network Mask for the subnet."
			::= { ccWLANEntry 22 }

		
		-- 1.3.6.1.4.1.388.6.3.22.1.23
		ccWLANDefaultRoute OBJECT-TYPE
			SYNTAX IpAddress
			MAX-ACCESS read-write
			STATUS current
			DESCRIPTION
				"The IP Address of the default route."
			::= { ccWLANEntry 23 }

		
		-- 1.3.6.1.4.1.388.6.3.22.1.24
		ccWLANBCMC11A OBJECT-TYPE
			SYNTAX EncrType
			MAX-ACCESS read-only
			STATUS current
			DESCRIPTION
				"WLAN broadcast/multicast encryption type on 802.11a radios."
			::= { ccWLANEntry 24 }

		
		-- 1.3.6.1.4.1.388.6.3.22.1.25
		ccWLANBCMC11B OBJECT-TYPE
			SYNTAX EncrType
			MAX-ACCESS read-only
			STATUS current
			DESCRIPTION
				"WLAN broadcast/multicast encryption type on 802.11b radios."
			::= { ccWLANEntry 25 }

		
		-- 1.3.6.1.4.1.388.6.3.22.1.26
		ccWLANBCMCFH OBJECT-TYPE
			SYNTAX EncrType
			MAX-ACCESS read-only
			STATUS current
			DESCRIPTION
				"WLAN broadcast/multicast encryption type on FH radios."
			::= { ccWLANEntry 26 }

		
		-- 1.3.6.1.4.1.388.6.3.22.1.27
		ccBroadcastEss OBJECT-TYPE
			SYNTAX TruthValue
			MAX-ACCESS read-write
			STATUS current
			DESCRIPTION
				"Enable (true)/Disable (false) Broadcast ESS feature for the WLAN.
				Broadcast ESS feature implies that a probe request containing a zero length 
				SSID will be allowed to associate to the particular SSID that is
				designated as the broadcast ESS."
			::= { ccWLANEntry 27 }

		
		-- 1.3.6.1.4.1.388.6.3.22.1.28
		ccWLANDesc OBJECT-TYPE
			SYNTAX DisplayString (SIZE (0..128))
			MAX-ACCESS read-write
			STATUS current
			DESCRIPTION
				"The description of the WLAN. The Maximum length of the description 
				can be 128 characters. Note that the following characters cannot be
				part of description - ',# and double quotes."
			::= { ccWLANEntry 28 }

		
		-- 1.3.6.1.4.1.388.6.3.22.1.29
		ccWlanWMEEnable OBJECT-TYPE
			SYNTAX DisplayString
			MAX-ACCESS read-write
			STATUS current
			DESCRIPTION
				"Description.
				 Enable/Disable of WME for WLAN."
			::= { ccWLANEntry 29 }

		
		-- 1.3.6.1.4.1.388.6.3.22.1.30
		ccWlanWMEProfile OBJECT-TYPE
			SYNTAX DisplayString
			MAX-ACCESS read-write
			STATUS current
			DESCRIPTION
				"Description.
				WME Profile for WLan"
			::= { ccWLANEntry 30 }

		
		-- 1.3.6.1.4.1.388.6.3.23
		ccKnownCCTable OBJECT-TYPE
			SYNTAX SEQUENCE OF CcKnownCCEntry
			MAX-ACCESS not-accessible
			STATUS current
			DESCRIPTION
				"A table of Known Wireless Switch entries"
			::= { symbolCCMgmt 23 }

		
		-- 1.3.6.1.4.1.388.6.3.23.1
		ccKnownCCEntry OBJECT-TYPE
			SYNTAX CcKnownCCEntry
			MAX-ACCESS not-accessible
			STATUS current
			DESCRIPTION
				"The entries of information about the known Wireless Switch."
			INDEX { ccKnownCCIndex }
			::= { ccKnownCCTable 1 }

		
		CcKnownCCEntry ::=
			SEQUENCE { 
				ccKnownCCIndex
					INTEGER,
				ccKnownCCName
					DisplayString,
				ccKnownCCMac
					DisplayString
			 }

		-- 1.3.6.1.4.1.388.6.3.23.1.1
		ccKnownCCIndex OBJECT-TYPE
			SYNTAX INTEGER (1..16)
			MAX-ACCESS read-only
			STATUS current
			DESCRIPTION
				"An index of the table."
			::= { ccKnownCCEntry 1 }

		
		-- 1.3.6.1.4.1.388.6.3.23.1.2
		ccKnownCCName OBJECT-TYPE
			SYNTAX DisplayString (SIZE (1..32))
			MAX-ACCESS read-only
			STATUS current
			DESCRIPTION
				"A known Wireless Switch name."
			::= { ccKnownCCEntry 2 }
-- KnownCC is not implemented in the CC.
		
		-- 1.3.6.1.4.1.388.6.3.23.1.3
		ccKnownCCMac OBJECT-TYPE
			SYNTAX DisplayString (SIZE (1..17))
			MAX-ACCESS read-only
			STATUS current
			DESCRIPTION
				"A known Wireless Switch mac address."
			::= { ccKnownCCEntry 3 }

		
		-- 1.3.6.1.4.1.388.6.3.24
		ccKnownAPTable OBJECT-TYPE
			SYNTAX SEQUENCE OF CcKnownAPEntry
			MAX-ACCESS not-accessible
			STATUS current
			DESCRIPTION
				"A table of Known Access-Point entries. "
			::= { symbolCCMgmt 24 }

		
		-- 1.3.6.1.4.1.388.6.3.24.1
		ccKnownAPEntry OBJECT-TYPE
			SYNTAX CcKnownAPEntry
			MAX-ACCESS not-accessible
			STATUS current
			DESCRIPTION
				"Entries of information about Known APs."
			INDEX { ccKnownAPIndex }
			::= { ccKnownAPTable 1 }

		
		CcKnownAPEntry ::=
			SEQUENCE { 
				ccKnownAPIndex
					INTEGER,
				ccKnownAPMac
					DisplayString,
				ccKnownAPVer
					INTEGER,
				ccKnownAPIP
					IpAddress,
				ccKnownAPPriority
					INTEGER,
				ccKnownAPMus
					INTEGER,
				ccKnownAPType
					INTEGER,
				ccKnownAPAPVer
					INTEGER,
				ccKnownAPEssid
					DisplayString
			 }

		-- 1.3.6.1.4.1.388.6.3.24.1.1
		ccKnownAPIndex OBJECT-TYPE
			SYNTAX INTEGER (1..20000)
			MAX-ACCESS read-only
			STATUS current
			DESCRIPTION
				"A index of the table."
			::= { ccKnownAPEntry 1 }

		
		-- 1.3.6.1.4.1.388.6.3.24.1.2
		ccKnownAPMac OBJECT-TYPE
			SYNTAX DisplayString (SIZE (1..17))
			MAX-ACCESS read-only
			STATUS current
			DESCRIPTION
				"A known AP mac address."
			::= { ccKnownAPEntry 2 }

		
		-- 1.3.6.1.4.1.388.6.3.24.1.3
		ccKnownAPVer OBJECT-TYPE
			SYNTAX INTEGER (1..100)
			MAX-ACCESS read-only
			STATUS current
			DESCRIPTION
				"A known AP version."
			::= { ccKnownAPEntry 3 }

		
		-- 1.3.6.1.4.1.388.6.3.24.1.4
		ccKnownAPIP OBJECT-TYPE
			SYNTAX IpAddress
			MAX-ACCESS read-only
			STATUS current
			DESCRIPTION
				"A known AP IP address."
			::= { ccKnownAPEntry 4 }

		
		-- 1.3.6.1.4.1.388.6.3.24.1.5
		ccKnownAPPriority OBJECT-TYPE
			SYNTAX INTEGER (1..20)
			MAX-ACCESS read-only
			STATUS current
			DESCRIPTION
				"Priority for the known AP."
			::= { ccKnownAPEntry 5 }

		
		-- 1.3.6.1.4.1.388.6.3.24.1.6
		ccKnownAPMus OBJECT-TYPE
			SYNTAX INTEGER (1..1000)
			MAX-ACCESS read-only
			STATUS current
			DESCRIPTION
				"The number of MUs associated with the known AP."
			::= { ccKnownAPEntry 6 }

		
		-- 1.3.6.1.4.1.388.6.3.24.1.7
		ccKnownAPType OBJECT-TYPE
			SYNTAX INTEGER (1..10)
			MAX-ACCESS read-only
			STATUS current
			DESCRIPTION
				"The known AP type ."
			::= { ccKnownAPEntry 7 }

		
		-- 1.3.6.1.4.1.388.6.3.24.1.8
		ccKnownAPAPVer OBJECT-TYPE
			SYNTAX INTEGER (1..10)
			MAX-ACCESS read-only
			STATUS current
			DESCRIPTION
				"The known AP version."
			::= { ccKnownAPEntry 8 }

		
		-- 1.3.6.1.4.1.388.6.3.24.1.9
		ccKnownAPEssid OBJECT-TYPE
			SYNTAX DisplayString (SIZE (1..32))
			MAX-ACCESS read-only
			STATUS current
			DESCRIPTION
				"A known AP ESSID."
			::= { ccKnownAPEntry 9 }

		
		-- 1.3.6.1.4.1.388.6.3.25
		ccGraphTable OBJECT-TYPE
			SYNTAX SEQUENCE OF CcGraphEntry
			MAX-ACCESS not-accessible
			STATUS current
			DESCRIPTION
				"A list of Graph entries."
			::= { symbolCCMgmt 25 }

		
		-- 1.3.6.1.4.1.388.6.3.25.1
		ccGraphEntry OBJECT-TYPE
			SYNTAX CcGraphEntry
			MAX-ACCESS not-accessible
			STATUS current
			DESCRIPTION
				"Graph Object entries."
			INDEX { ccGraphIndex }
			::= { ccGraphTable 1 }

		
		CcGraphEntry ::=
			SEQUENCE { 
				ccGraphIndex
					INTEGER,
				ccGraphName
					DisplayString,
				ccGraphWlanId
					DisplayString
			 }

		-- 1.3.6.1.4.1.388.6.3.25.1.1
		ccGraphIndex OBJECT-TYPE
			SYNTAX INTEGER (1..200)
			MAX-ACCESS read-only
			STATUS current
			DESCRIPTION
				"The index of the graph."
			::= { ccGraphEntry 1 }

		
		-- 1.3.6.1.4.1.388.6.3.25.1.2
		ccGraphName OBJECT-TYPE
			SYNTAX DisplayString (SIZE (1..32))
			MAX-ACCESS read-write
			STATUS current
			DESCRIPTION
				"The name of the graph."
			::= { ccGraphEntry 2 }

		
		-- 1.3.6.1.4.1.388.6.3.25.1.7
		ccGraphWlanId OBJECT-TYPE
			SYNTAX DisplayString (SIZE (1..255))
			MAX-ACCESS read-write
			STATUS current
			DESCRIPTION
				"A WLAN ID attached to this Graph."
			::= { ccGraphEntry 7 }

		
		-- 1.3.6.1.4.1.388.6.3.26
		ccVLANTable OBJECT-TYPE
			SYNTAX SEQUENCE OF CcVLANEntry
			MAX-ACCESS not-accessible
			STATUS current
			DESCRIPTION
				"A list of VLAN Object entries."
			::= { symbolCCMgmt 26 }

		
		-- 1.3.6.1.4.1.388.6.3.26.1
		ccVLANEntry OBJECT-TYPE
			SYNTAX CcVLANEntry
			MAX-ACCESS not-accessible
			STATUS current
			DESCRIPTION
				"A VLAN Object entry."
			INDEX { ccVLANIndex }
			::= { ccVLANTable 1 }

		
		CcVLANEntry ::=
			SEQUENCE { 
				ccVLANIndex
					INTEGER,
				ccVLANName
					DisplayString,
				ccVLANDesc
					DisplayString,
				ccVLANVid
					INTEGER,
				ccVLANPriority
					INTEGER,
				ccVLANPorts
					INTEGER,
				ccVLANEtherPolicy
					DisplayString,
				ccVLANWlan
					INTEGER,
				ccVLANWlanList
					DisplayString,
				ccVLANAddWlan
					DisplayString,
				ccVLANRemWlan
					DisplayString
			 }

		-- 1.3.6.1.4.1.388.6.3.26.1.1
		ccVLANIndex OBJECT-TYPE
			SYNTAX INTEGER (1..100)
			MAX-ACCESS read-only
			STATUS current
			DESCRIPTION
				"The index for this VLAN object. "
			::= { ccVLANEntry 1 }
-- Mower: changed range from 0.. to 1..
		
		-- 1.3.6.1.4.1.388.6.3.26.1.2
		ccVLANName OBJECT-TYPE
			SYNTAX DisplayString (SIZE (1..32))
			MAX-ACCESS read-only
			STATUS current
			DESCRIPTION
				"The Name of the VLAN."
			::= { ccVLANEntry 2 }
-- This VLAN name has to be removed from the EthernetPolicy Object
-- To be implemented after the CLI is implemented [MS]
		
		-- 1.3.6.1.4.1.388.6.3.26.1.3
		ccVLANDesc OBJECT-TYPE
			SYNTAX DisplayString (SIZE (0..128))
			MAX-ACCESS read-write
			STATUS current
			DESCRIPTION
				"A description of the VLAN. The Maximum length of the description 
				can be 128 characters. Note that the following characters cannot be part 
				of description ',# and double quotes."
			::= { ccVLANEntry 3 }

		
		-- 1.3.6.1.4.1.388.6.3.26.1.4
		ccVLANVid OBJECT-TYPE
			SYNTAX INTEGER (0..10000)
			MAX-ACCESS read-only
			STATUS current
			DESCRIPTION
				"An id for this VLAN."
			::= { ccVLANEntry 4 }

		
--  1.3.6.1.4.1.388.6.3.26.1.5
		-- 1.3.6.1.4.1.388.6.3.26.1.5
		ccVLANPriority OBJECT-TYPE
			SYNTAX INTEGER (0..7)
			MAX-ACCESS read-write
			STATUS current
			DESCRIPTION
				"The priority for this VLAN.
				The valid values for priority for VLAN is
				between 0-7."
			::= { ccVLANEntry 5 }

		
--  1.3.6.1.4.1.388.6.3.26.1.6
		-- 1.3.6.1.4.1.388.6.3.26.1.6
		ccVLANPorts OBJECT-TYPE
			SYNTAX INTEGER (0..2)
			MAX-ACCESS read-write
			STATUS current
			DESCRIPTION
				"The ports for this VLAN. 1 means etherport1, 2 means etherport2 and 0 means both etherports."
			::= { ccVLANEntry 6 }

		
		-- 1.3.6.1.4.1.388.6.3.26.1.7
		ccVLANEtherPolicy OBJECT-TYPE
			SYNTAX DisplayString (SIZE (1..200))
			MAX-ACCESS read-only
			STATUS current
			DESCRIPTION
				" The parent etherpolicy of this VLAN."
			::= { ccVLANEntry 7 }

		
		-- 1.3.6.1.4.1.388.6.3.26.1.8
		ccVLANWlan OBJECT-TYPE
			SYNTAX INTEGER (0..100)
			MAX-ACCESS read-only
			STATUS current
			DESCRIPTION
				"The number of WLANs attached to this VLAN object. "
			::= { ccVLANEntry 8 }

		
		-- 1.3.6.1.4.1.388.6.3.26.1.9
		ccVLANWlanList OBJECT-TYPE
			SYNTAX DisplayString (SIZE (1..200))
			MAX-ACCESS read-only
			STATUS current
			DESCRIPTION
				"A list of WLANs attatched to this VLAN."
			::= { ccVLANEntry 9 }

		
		-- 1.3.6.1.4.1.388.6.3.26.1.10
		ccVLANAddWlan OBJECT-TYPE
			SYNTAX DisplayString (SIZE (1..32))
			MAX-ACCESS read-write
			STATUS current
			DESCRIPTION
				"Add a WLAN object into this VLAN."
			::= { ccVLANEntry 10 }

		
		-- 1.3.6.1.4.1.388.6.3.26.1.11
		ccVLANRemWlan OBJECT-TYPE
			SYNTAX DisplayString (SIZE (1..32))
			MAX-ACCESS read-write
			STATUS current
			DESCRIPTION
				"Remove a VLAN object from the VLAN."
			::= { ccVLANEntry 11 }

		
		-- 1.3.6.1.4.1.388.6.3.28
		ccSecurityTable OBJECT-TYPE
			SYNTAX SEQUENCE OF CcSecurityEntry
			MAX-ACCESS not-accessible
			STATUS current
			DESCRIPTION
				"A table of Security entries."
			::= { symbolCCMgmt 28 }

		
		-- 1.3.6.1.4.1.388.6.3.28.1
		ccSecurityEntry OBJECT-TYPE
			SYNTAX CcSecurityEntry
			MAX-ACCESS not-accessible
			STATUS current
			DESCRIPTION
				"A Security Object entry."
			INDEX { ccSecIndex }
			::= { ccSecurityTable 1 }

		
		CcSecurityEntry ::=
			SEQUENCE { 
				ccSecIndex
					INTEGER,
				ccSecName
					DisplayString,
				ccSecDesc
					DisplayString,
				ccSecBeaconEssid
					TruthValue,
				ccSecPreSharedAuthEnabled
					TruthValue,
				ccSecWEPEnabled
					TruthValue,
				ccSecWEPKeyBitSize
					INTEGER,
				ccSecWEPKey
					DisplayString,
				ccSecWEPKeyUse
					INTEGER,
				ccSecKerberosEnabled
					TruthValue,
				ccSecKerberosRealm
					DisplayString,
				ccSecKerberosServer1
					DisplayString,
				ccSecKerberosServer2
					DisplayString,
				ccSecKerberosServer3
					DisplayString,
				ccSecKerberosPort1
					INTEGER,
				ccSecKerberosPort2
					INTEGER,
				ccSecKerberosPort3
					INTEGER,
				ccSecRadiusServer1
					DisplayString,
				ccSecRadiusPort1
					INTEGER,
				ccSecRadiusSecret1
					DisplayString,
				ccSecRadiusServer2
					DisplayString,
				ccSecRadiusPort2
					INTEGER,
				ccSecRadiusSecret2
					DisplayString,
				ccSecRadiusHostname
					DisplayString,
				ccSecEapEnabled
					TruthValue,
				ccSecEapQuietPeriod
					INTEGER,
				ccSecEapTxPeriod
					INTEGER,
				ccSecEapReauth
					TruthValue,
				ccSecEapReauthPeriod
					INTEGER,
				ccSecEapReauthMaxRetries
					INTEGER,
				ccSecEapSupplTimeout
					INTEGER,
				ccSecEapMaxreqRetries
					INTEGER,
				ccSecGroupRekeyPeriod
					INTEGER,
				ccSecPreSharedKeyMaterial
					DisplayString,
				ccSecOpenEncryptEnabled
					TruthValue,
				ccSecKeyGuardEnabled
					TruthValue,
				ccSecTKIPEnabled
					TruthValue,
				ccSecBCMCEncrType
					EncrType,
				ccSecCheckValidity
					DisplayString,
				ccSecCCMPEnabled
					TruthValue,
				ccSecPreAuthentication
					TruthValue,
				ccSecPMKCaching
					TruthValue,
				ccSecVPNEnabled
					TruthValue
			 }

		-- 1.3.6.1.4.1.388.6.3.28.1.1
		ccSecIndex OBJECT-TYPE
			SYNTAX INTEGER (1..100)
			MAX-ACCESS read-only
			STATUS current
			DESCRIPTION
				"The index for this security object. "
			::= { ccSecurityEntry 1 }
-- Mower: changed range from 0.. to 1..
		
		-- 1.3.6.1.4.1.388.6.3.28.1.2
		ccSecName OBJECT-TYPE
			SYNTAX DisplayString (SIZE (1..50))
			MAX-ACCESS read-write
			STATUS current
			DESCRIPTION
				"The name of the security policy. The Maximum length of the Policy Name 
				can be 50 characters. Note that the following characters cannot be part 
				of Policy Name field - ',.,\,&,# and double quotes."
			::= { ccSecurityEntry 2 }

		
		-- 1.3.6.1.4.1.388.6.3.28.1.3
		ccSecDesc OBJECT-TYPE
			SYNTAX DisplayString (SIZE (0..128))
			MAX-ACCESS read-write
			STATUS current
			DESCRIPTION
				"The description of this security policy. The Maximum length of the description 
				can be 128 characters. Note that the following characters cannot be part 
				of description ',# and double quotes."
			::= { ccSecurityEntry 3 }

		
		-- 1.3.6.1.4.1.388.6.3.28.1.4
		ccSecBeaconEssid OBJECT-TYPE
			SYNTAX TruthValue
			MAX-ACCESS read-write
			STATUS deprecated
			DESCRIPTION
				"Enable/Disable the beacon Essid for this security policy. The default is TRUE."
			::= { ccSecurityEntry 4 }

		
		-- 1.3.6.1.4.1.388.6.3.28.1.5
		ccSecPreSharedAuthEnabled OBJECT-TYPE
			SYNTAX TruthValue
			MAX-ACCESS read-write
			STATUS current
			DESCRIPTION
				"Enable(true)/Disable(false) pre-shared WEP keys
				and/or WPA-PSK. Note that enabling this automatically disables
				Open Encryption"
			::= { ccSecurityEntry 5 }

		
		-- 1.3.6.1.4.1.388.6.3.28.1.6
		ccSecWEPEnabled OBJECT-TYPE
			SYNTAX TruthValue
			MAX-ACCESS read-write
			STATUS current
			DESCRIPTION
				"Enable(true)/Disable(false) WEP.
				Note that enabling this automatically disables Open Encryption"
			::= { ccSecurityEntry 6 }

		
		-- 1.3.6.1.4.1.388.6.3.28.1.7
		ccSecWEPKeyBitSize OBJECT-TYPE
			SYNTAX INTEGER (0..104)
			MAX-ACCESS read-write
			STATUS current
			DESCRIPTION
				"WEP Key size in bits - 40 or 104.
				Note that if you are planning to use Kerberos
				as the authentication mechanism, you cannot choose the
				WEP key size as 40 bits, because Kerberos authentication
				results in 104 bit keys.
				Also note that TKIP cannot be used along with 40 bit WEP encryption.
				If TKIP has to be used along with WEP, the WEP key size must be 
				104 bits.
				Further, if Keyguard has to be used along with WEP, then also
				the WEP key size must be 104 bits.
				"
			::= { ccSecurityEntry 7 }

		
		-- 1.3.6.1.4.1.388.6.3.28.1.8
		ccSecWEPKey OBJECT-TYPE
			SYNTAX DisplayString (SIZE (12..50))
			MAX-ACCESS read-write
			STATUS current
			DESCRIPTION
				"This value is used to derive an encryption key which could be 40 bit or 128 bit in size. It will be needed if Shared Key
				is enabled and encryption type is WEP40 or WEP128. Here's how to enter the values:
				If you want to input the keys yourself, the format is <<number,key>>, where number could be anyone of
				0,1,2, or 3, depending on which key you want to input. If the WEP key bit size is 40, the valid keylength
				is 10 characters, and if the WEP key bit size is 104, the valid keylength is 26 characters.
				If you want the Switch to generate and set all the keys for you,the format is <<'switchgenerate',string>>.
				The string length should be between 4 and 32.
				'switchgenerate' is a keyword here, and should be entered as such (without the single quote).
				As a further option, you could enter an ASCII string and the agent would convert the ASCII to a hex key.
				The format for entering this string is <<'agentgenerate',number,string>>. 'agentgenerate' is a keyword here.
				number is anyone of 0,1,2 or 3 depending on which WEP Key you want to set.
				The string length should be 5 characters if the hex key has to be 40 bit, and 13 characters if the hex
				key has to be 104 bit.
				Note that for all the three formats listed above, '<<' and '>>' are grammar delimiter and are not a part 
				of the input."
			::= { ccSecurityEntry 8 }

		
		-- 1.3.6.1.4.1.388.6.3.28.1.9
		ccSecWEPKeyUse OBJECT-TYPE
			SYNTAX INTEGER (0..3)
			MAX-ACCESS read-write
			STATUS current
			DESCRIPTION
				"Value of 0 to 3. 
				ex. 0 -- Currently use WEPKEY #1.
					1 -- Currently use WEPKEY #2.
					2 -- Currently use WEPKEY #3.
					3 -- Currently use WEPKEY #4.
				"
			::= { ccSecurityEntry 9 }

		
		-- 1.3.6.1.4.1.388.6.3.28.1.10
		ccSecKerberosEnabled OBJECT-TYPE
			SYNTAX TruthValue
			MAX-ACCESS read-write
			STATUS current
			DESCRIPTION
				"Enable(1)/Disable(2) Kerberos Authentication.
				Note that if you choose WEP as the encryption algorithm,
				you cannot choose the WEP key size to be 40 bits, since Kerberos 
				authentication results in 104 bit WEP keys.
				Also note that TKIP as the encryption algorithm is currently not supported
				with Kerberos authentication.
				Enabling this automatically disables
					Open Encryption"
			::= { ccSecurityEntry 10 }

		
		-- 1.3.6.1.4.1.388.6.3.28.1.11
		ccSecKerberosRealm OBJECT-TYPE
			SYNTAX DisplayString (SIZE (1..128))
			MAX-ACCESS read-write
			STATUS current
			DESCRIPTION
				"A Kerberos Realm Name. Needed if Kerberos enabled.
				ex. APFW.SYMBOL.COM.
				Note that the following characters are not allowed for realm:
				   ` @ # $ & ( ) = | \ ; double-quote ' < > / sp"
			::= { ccSecurityEntry 11 }

		
		-- 1.3.6.1.4.1.388.6.3.28.1.12
		ccSecKerberosServer1 OBJECT-TYPE
			SYNTAX DisplayString (SIZE (1..128))
			MAX-ACCESS read-write
			STATUS current
			DESCRIPTION
				"1st Kerberos server name or dotted-decimal IP address."
			::= { ccSecurityEntry 12 }

		
		-- 1.3.6.1.4.1.388.6.3.28.1.13
		ccSecKerberosServer2 OBJECT-TYPE
			SYNTAX DisplayString (SIZE (1..128))
			MAX-ACCESS read-write
			STATUS current
			DESCRIPTION
				"2nd Kerberos server name or dotted-decimal IP address."
			::= { ccSecurityEntry 13 }

		
		-- 1.3.6.1.4.1.388.6.3.28.1.14
		ccSecKerberosServer3 OBJECT-TYPE
			SYNTAX DisplayString (SIZE (1..128))
			MAX-ACCESS read-write
			STATUS current
			DESCRIPTION
				"3rd Kerberos server name or dotted-decimal IP address."
			::= { ccSecurityEntry 14 }

		
		-- 1.3.6.1.4.1.388.6.3.28.1.15
		ccSecKerberosPort1 OBJECT-TYPE
			SYNTAX INTEGER (1..65535)
			MAX-ACCESS read-write
			STATUS current
			DESCRIPTION
				"1st Kerberos Server port number"
			::= { ccSecurityEntry 15 }

		
		-- 1.3.6.1.4.1.388.6.3.28.1.16
		ccSecKerberosPort2 OBJECT-TYPE
			SYNTAX INTEGER (1..65535)
			MAX-ACCESS read-write
			STATUS current
			DESCRIPTION
				"2nd Kerberos Server port number"
			::= { ccSecurityEntry 16 }

		
		-- 1.3.6.1.4.1.388.6.3.28.1.17
		ccSecKerberosPort3 OBJECT-TYPE
			SYNTAX INTEGER (1..65535)
			MAX-ACCESS read-write
			STATUS current
			DESCRIPTION
				"3rd Kerberos Server port number"
			::= { ccSecurityEntry 17 }

		
--  ccSecKerberosNTPServer OBJECT-TYPE
-- SYNTAX		IpAddress
-- MAX-ACCESS	read-write
-- STATUS		current
-- DESCRIPTION
-- 	"The IP address of the NTP Time Server."
-- ::= {ccSecurityEntry 17 }
		-- 1.3.6.1.4.1.388.6.3.28.1.18
		ccSecRadiusServer1 OBJECT-TYPE
			SYNTAX DisplayString (SIZE (1..128))
			MAX-ACCESS read-write
			STATUS current
			DESCRIPTION
				"1st RADIUS Server Name/IP or dotted-decimal IP address."
			::= { ccSecurityEntry 18 }

		
		-- 1.3.6.1.4.1.388.6.3.28.1.19
		ccSecRadiusPort1 OBJECT-TYPE
			SYNTAX INTEGER (1..65535)
			MAX-ACCESS read-write
			STATUS current
			DESCRIPTION
				"1st RADIUS Server port number"
			::= { ccSecurityEntry 19 }

		
		-- 1.3.6.1.4.1.388.6.3.28.1.20
		ccSecRadiusSecret1 OBJECT-TYPE
			SYNTAX DisplayString (SIZE (1..32))
			MAX-ACCESS read-write
			STATUS current
			DESCRIPTION
				"1st RADIUS server shared secret."
			::= { ccSecurityEntry 20 }

		
		-- 1.3.6.1.4.1.388.6.3.28.1.21
		ccSecRadiusServer2 OBJECT-TYPE
			SYNTAX DisplayString (SIZE (1..128))
			MAX-ACCESS read-write
			STATUS current
			DESCRIPTION
				"2nd RADIUS Server Name/IP or dotted-decimal IP address."
			::= { ccSecurityEntry 21 }

		
		-- 1.3.6.1.4.1.388.6.3.28.1.22
		ccSecRadiusPort2 OBJECT-TYPE
			SYNTAX INTEGER (1..65535)
			MAX-ACCESS read-write
			STATUS current
			DESCRIPTION
				"2nd RADIUS Server port number"
			::= { ccSecurityEntry 22 }

		
		-- 1.3.6.1.4.1.388.6.3.28.1.23
		ccSecRadiusSecret2 OBJECT-TYPE
			SYNTAX DisplayString (SIZE (1..32))
			MAX-ACCESS read-write
			STATUS current
			DESCRIPTION
				"2nd RADIUS server shared secret."
			::= { ccSecurityEntry 23 }

		
		-- 1.3.6.1.4.1.388.6.3.28.1.24
		ccSecRadiusHostname OBJECT-TYPE
			SYNTAX DisplayString (SIZE (1..32))
			MAX-ACCESS read-write
			STATUS current
			DESCRIPTION
				"Hostname to use with RADIUS server."
			::= { ccSecurityEntry 24 }

		
		-- 1.3.6.1.4.1.388.6.3.28.1.25
		ccSecEapEnabled OBJECT-TYPE
			SYNTAX TruthValue
			MAX-ACCESS read-write
			STATUS current
			DESCRIPTION
				"Enable(1)/Disable(2) EAP Authentication.
				Note that enabling this automatically disables
					  Open Encryption"
			::= { ccSecurityEntry 25 }

		
		-- 1.3.6.1.4.1.388.6.3.28.1.26
		ccSecEapQuietPeriod OBJECT-TYPE
			SYNTAX INTEGER (1..99)
			MAX-ACCESS read-write
			STATUS current
			DESCRIPTION
				"EAP quiet period in seconds. Valid values lie
				between 1 and 99."
			::= { ccSecurityEntry 26 }

		
		-- 1.3.6.1.4.1.388.6.3.28.1.27
		ccSecEapTxPeriod OBJECT-TYPE
			SYNTAX INTEGER (1..99)
			MAX-ACCESS read-write
			STATUS current
			DESCRIPTION
				"EAP transmit period in seconds.
				Valid values are from 1 to 99 seconds"
			::= { ccSecurityEntry 27 }

		
		-- 1.3.6.1.4.1.388.6.3.28.1.28
		ccSecEapReauth OBJECT-TYPE
			SYNTAX TruthValue
			MAX-ACCESS read-write
			STATUS current
			DESCRIPTION
				"Enable(1)/Disable(2) forced EAP Re-Authentication."
			::= { ccSecurityEntry 28 }

		
		-- 1.3.6.1.4.1.388.6.3.28.1.29
		ccSecEapReauthPeriod OBJECT-TYPE
			SYNTAX INTEGER (30..65535)
			MAX-ACCESS read-write
			STATUS current
			DESCRIPTION
				"EAP Reauthentication period in seconds.
				Valid values are any value between 30
				and 65535."
			::= { ccSecurityEntry 29 }

		
		-- 1.3.6.1.4.1.388.6.3.28.1.30
		ccSecEapReauthMaxRetries OBJECT-TYPE
			SYNTAX INTEGER (1..99)
			MAX-ACCESS read-write
			STATUS current
			DESCRIPTION
				"Max retries for EAP re-authentication.
				Valid values are from 1 to 99."
			::= { ccSecurityEntry 30 }

		
		-- 1.3.6.1.4.1.388.6.3.28.1.31
		ccSecEapSupplTimeout OBJECT-TYPE
			SYNTAX INTEGER (1..99)
			MAX-ACCESS read-write
			STATUS current
			DESCRIPTION
				"EAP supplicant timeout in seconds.
				Valid values are from 1 to 99 seconds."
			::= { ccSecurityEntry 31 }

		
		-- 1.3.6.1.4.1.388.6.3.28.1.32
		ccSecEapMaxreqRetries OBJECT-TYPE
			SYNTAX INTEGER (1..10)
			MAX-ACCESS read-write
			STATUS current
			DESCRIPTION
				"Maximum retries for EAP requests.
				Valid values are from 1 to 10."
			::= { ccSecurityEntry 32 }

		
		-- 1.3.6.1.4.1.388.6.3.28.1.33
		ccSecGroupRekeyPeriod OBJECT-TYPE
			SYNTAX INTEGER (30..65535)
			MAX-ACCESS read-write
			STATUS current
			DESCRIPTION
				"Group key update period in seconds.
				Valid values are from 30 to 65535 seconds."
			::= { ccSecurityEntry 33 }

		
		-- 1.3.6.1.4.1.388.6.3.28.1.34
		ccSecPreSharedKeyMaterial OBJECT-TYPE
			SYNTAX DisplayString (SIZE (1..64))
			MAX-ACCESS read-write
			STATUS current
			DESCRIPTION
				"Preshared Key data, either 8-63 ASCII characters
				or 64 hex characters."
			::= { ccSecurityEntry 34 }

		
		-- 1.3.6.1.4.1.388.6.3.28.1.35
		ccSecOpenEncryptEnabled OBJECT-TYPE
			SYNTAX TruthValue
			MAX-ACCESS read-write
			STATUS current
			DESCRIPTION
				"Enable(true)/Disable(false) open encryption.
				Note that enabling open encryption also enables 
				open authentication."
			::= { ccSecurityEntry 35 }

		
		-- 1.3.6.1.4.1.388.6.3.28.1.36
		ccSecKeyGuardEnabled OBJECT-TYPE
			SYNTAX TruthValue
			MAX-ACCESS read-write
			STATUS current
			DESCRIPTION
				"Enable(true)/Disable(false) KeyGuard encryption.
				Note that Keyguard doesn't work along with WEP encryption, 
				if the WEP Key size is 40 bits. The WEP key size must be 104
				bits for Keyguard to work along with it.
				Also note that enabling this automatically disables
				Open Encryption"
			::= { ccSecurityEntry 36 }

		
		-- 1.3.6.1.4.1.388.6.3.28.1.37
		ccSecTKIPEnabled OBJECT-TYPE
			SYNTAX TruthValue
			MAX-ACCESS read-write
			STATUS current
			DESCRIPTION
				"Enable(true)/Disable(false) TKIP encryption.
				Note that in the current implementation, TKIP cannot
				co-exist with Kerberos.
				Also note that TKIP cannot co-exist with WEP key encryption,
				if the WEP key size is 40 bits. The WEP key size must be 104
				bits for it to work with TKIP. 
				Note that enabling this automatically disables
				Open Encryption"
			::= { ccSecurityEntry 37 }

		
		-- 1.3.6.1.4.1.388.6.3.28.1.38
		ccSecBCMCEncrType OBJECT-TYPE
			SYNTAX EncrType
			MAX-ACCESS read-only
			STATUS deprecated
			DESCRIPTION
				"The encryption type of broadcast/multicast."
			::= { ccSecurityEntry 38 }

		
		-- 1.3.6.1.4.1.388.6.3.28.1.39
		ccSecCheckValidity OBJECT-TYPE
			SYNTAX DisplayString (SIZE (1..1000))
			MAX-ACCESS read-only
			STATUS current
			DESCRIPTION
				"This OID can be used to find out
				whether this security policy is valid or not.
				If it is valid, an OK is returned in the response.
				If not, you get a description as to what the error is.
				Please note that unless the security policy is valid,
				it cannot be used anywhere, i.e it cannot be applied to a 
				WLAN."
			::= { ccSecurityEntry 39 }

		
--  1.3.6.1.4.1.388.6.3.28.1.40
		-- 1.3.6.1.4.1.388.6.3.28.1.40
		ccSecCCMPEnabled OBJECT-TYPE
			SYNTAX TruthValue
			MAX-ACCESS read-write
			STATUS current
			DESCRIPTION
				"Enable(true)/Disable(false)AES CCMP encryption.
				This OID is read-only for Default security policy.
				For all other instances, it is read-write."
			::= { ccSecurityEntry 40 }

		
		-- 1.3.6.1.4.1.388.6.3.28.1.41
		ccSecPreAuthentication OBJECT-TYPE
			SYNTAX TruthValue
			MAX-ACCESS read-write
			STATUS current
			DESCRIPTION
				"Enable(true)/Disable(false)Pre-Authentication.
				This OID is read-only for 'Default' instance.(ie 'Default' Security policy)"
			::= { ccSecurityEntry 41 }

		
		-- 1.3.6.1.4.1.388.6.3.28.1.42
		ccSecPMKCaching OBJECT-TYPE
			SYNTAX TruthValue
			MAX-ACCESS read-write
			STATUS current
			DESCRIPTION
				"Enable(true)/Disable(false)Opportunistic PMK Caching.
				This OID is read-only for 'Default' instance.(ie 'Default' security policy)"
			::= { ccSecurityEntry 42 }

		
		-- 1.3.6.1.4.1.388.6.3.28.1.43
		ccSecVPNEnabled OBJECT-TYPE
			SYNTAX TruthValue
			MAX-ACCESS read-write
			STATUS current
			DESCRIPTION
				"Enable(true)/Disable(false) VPN Authentication.
				This OID is read-only for 'Default' instance.
				(ie 'Default' security policy).This OID can be 
				enabled for only one security policy(ie only one
				instance). 
				
				Note: If you need to enable this oid for a particular
				security policy, make sure it is disabled for all
				other security policies.
				
				"
			::= { ccSecurityEntry 43 }

		
		-- 1.3.6.1.4.1.388.6.3.29
		ccACLTable OBJECT-TYPE
			SYNTAX SEQUENCE OF CcACLEntry
			MAX-ACCESS not-accessible
			STATUS current
			DESCRIPTION
				"A table for ACL entries."
			::= { symbolCCMgmt 29 }

		
		-- 1.3.6.1.4.1.388.6.3.29.1
		ccACLEntry OBJECT-TYPE
			SYNTAX CcACLEntry
			MAX-ACCESS not-accessible
			STATUS current
			DESCRIPTION
				"An ACL object entry."
			INDEX { ccACLIndex }
			::= { ccACLTable 1 }

		
		CcACLEntry ::=
			SEQUENCE { 
				ccACLIndex
					INTEGER,
				ccACLName
					DisplayString,
				ccACLDefaultAction
					DisplayString,
				ccACLAction
					DisplayString,
				ccACLGetItemCount
					INTEGER,
				ccACLGetItem
					DisplayString,
				ccACLAddItem
					DisplayString,
				ccACLRemItem
					DisplayString
			 }

		-- 1.3.6.1.4.1.388.6.3.29.1.1
		ccACLIndex OBJECT-TYPE
			SYNTAX INTEGER (1..1000)
			MAX-ACCESS not-accessible
			STATUS current
			DESCRIPTION
				"The index of this ACL object."
			::= { ccACLEntry 1 }
-- Mower: changed range from 0.. to 1..
		
		-- 1.3.6.1.4.1.388.6.3.29.1.2
		ccACLName OBJECT-TYPE
			SYNTAX DisplayString (SIZE (1..50))
			MAX-ACCESS read-write
			STATUS current
			DESCRIPTION
				"The name of the ACL. The Maximum length of the ACL Name can be 50 
				characters. Note that the following characters cannot be part of ACL 
				Name field - ',.,\,&,# and double quotes."
			::= { ccACLEntry 2 }

		
		-- 1.3.6.1.4.1.388.6.3.29.1.3
		ccACLDefaultAction OBJECT-TYPE
			SYNTAX DisplayString (SIZE (4..5))
			MAX-ACCESS read-write
			STATUS current
			DESCRIPTION
				"The default action for this ACL. 
				Is either 'allow' or 'deny'."
			::= { ccACLEntry 3 }

		
		-- 1.3.6.1.4.1.388.6.3.29.1.4
		ccACLAction OBJECT-TYPE
			SYNTAX DisplayString (SIZE (22..100))
			MAX-ACCESS read-write
			STATUS current
			DESCRIPTION
				"SET only.
				Setting a new action for an already existing MAC address.
				Syntax is 
				< allow/deny>,<new-MAC Address>,<old start MAC Address>
					        or
				<allow/deny>,<new start MAC Address>-<new end MAC Address>,<old start MAC Address>."
			::= { ccACLEntry 4 }

		
		-- 1.3.6.1.4.1.388.6.3.29.1.5
		ccACLGetItemCount OBJECT-TYPE
			SYNTAX INTEGER (1..1000)
			MAX-ACCESS read-only
			STATUS current
			DESCRIPTION
				"The number of items in the ACL."
			::= { ccACLEntry 5 }

		
		-- 1.3.6.1.4.1.388.6.3.29.1.6
		ccACLGetItem OBJECT-TYPE
			SYNTAX DisplayString (SIZE (1..1024))
			MAX-ACCESS read-only
			STATUS deprecated
			DESCRIPTION
				"Show the one item in the ACL list. Here's the format in which
				the reply is received: < MAC Addr,allow/deny >."
			::= { ccACLEntry 6 }

		
		-- 1.3.6.1.4.1.388.6.3.29.1.7
		ccACLAddItem OBJECT-TYPE
			SYNTAX DisplayString (SIZE (1..1024))
			MAX-ACCESS read-write
			STATUS current
			DESCRIPTION
				"SET only.
				Adding a new rule into the list.
				 Rules have to be added in the format <allow/deny,single MAC address>
				               Or <allow/deny,Start MAC,End MAC>. The former is to be used for configuring 
				 access for a single MAC address, while the latter configures a range of
				 MAC addresses.
				 
				 Note: AddItem with 0 or 1.0 or x.0 is invalid index number.
				 The index number has to be great than 0."
			::= { ccACLEntry 7 }

		
		-- 1.3.6.1.4.1.388.6.3.29.1.8
		ccACLRemItem OBJECT-TYPE
			SYNTAX DisplayString (SIZE (1..1024))
			MAX-ACCESS read-write
			STATUS current
			DESCRIPTION
				"SET only.
				Removing a rule from the ACL.
				You need to give only the MAC address to remove the rule 
				from the ACL. For rules which involve more than one
				MAC Addresses, just give the starting MAC Address."
			::= { ccACLEntry 8 }

		
		-- 1.3.6.1.4.1.388.6.3.30
		ccNPolicyMgmt OBJECT IDENTIFIER ::= { symbolCCMgmt 30 }

		
		-- 1.3.6.1.4.1.388.6.3.30.1
		ccNumNPRec OBJECT-TYPE
			SYNTAX INTEGER (0..100)
			MAX-ACCESS read-only
			STATUS current
			DESCRIPTION
				"The total number of NP records in the NP table."
			::= { ccNPolicyMgmt 1 }

		
		-- 1.3.6.1.4.1.388.6.3.30.2
		ccNumPORec OBJECT-TYPE
			SYNTAX INTEGER (0..100)
			MAX-ACCESS read-only
			STATUS current
			DESCRIPTION
				"The total number of Policy Objects in the Policy table."
			::= { ccNPolicyMgmt 2 }

		
		-- 1.3.6.1.4.1.388.6.3.30.3
		ccNumCGRec OBJECT-TYPE
			SYNTAX INTEGER (0..100)
			MAX-ACCESS read-only
			STATUS current
			DESCRIPTION
				"The total number of Classification Groups in the CG table."
			::= { ccNPolicyMgmt 3 }

		
		-- 1.3.6.1.4.1.388.6.3.30.4
		ccNumCFRec OBJECT-TYPE
			SYNTAX INTEGER (0..100)
			MAX-ACCESS read-only
			STATUS current
			DESCRIPTION
				"The total number of Classifiers in the CF table."
			::= { ccNPolicyMgmt 4 }

		
		-- 1.3.6.1.4.1.388.6.3.30.5
		ccCFAddObj OBJECT-TYPE
			SYNTAX DisplayString (SIZE (1..50))
			MAX-ACCESS read-write
			STATUS current
			DESCRIPTION
				"Add one new Classifier object into the table.
				The maximum number of characters allowed is 50, and the following
				characters cannot be part of the input string -
				',.,\,&, # and double quotes."
			::= { ccNPolicyMgmt 5 }

		
		-- 1.3.6.1.4.1.388.6.3.30.6
		ccCFRemObj OBJECT-TYPE
			SYNTAX DisplayString (SIZE (1..50))
			MAX-ACCESS read-write
			STATUS current
			DESCRIPTION
				"Remove one Classifier object from the table.
				The maximum number of characters allowed is 50, and the following
				characters cannot be part of the input string -
				',.,\,&, # and double quotes."
			::= { ccNPolicyMgmt 6 }

		
		-- 1.3.6.1.4.1.388.6.3.30.7
		ccCGAddObj OBJECT-TYPE
			SYNTAX DisplayString (SIZE (1..50))
			MAX-ACCESS read-write
			STATUS current
			DESCRIPTION
				"Add one Classification Group Object into the ccCGTable.
				The maximum number of characters allowed is 50, and the following
				characters cannot be part of the input string -
				',.,\,&, # and double quotes."
			::= { ccNPolicyMgmt 7 }

		
		-- 1.3.6.1.4.1.388.6.3.30.8
		ccCGRemObj OBJECT-TYPE
			SYNTAX DisplayString (SIZE (1..50))
			MAX-ACCESS read-write
			STATUS current
			DESCRIPTION
				"Remove one Classification Group Object from the ccCGTable.
				The maximum number of characters allowed is 50, and the following
				characters cannot be part of the input string -
				',.,\,&, # and double quotes."
			::= { ccNPolicyMgmt 8 }

		
		-- 1.3.6.1.4.1.388.6.3.30.9
		ccPOAddObj OBJECT-TYPE
			SYNTAX DisplayString (SIZE (1..50))
			MAX-ACCESS read-write
			STATUS current
			DESCRIPTION
				"Add one Policy Object into the ccPOTable.
				The 'type' of the Policy Object needs to be specified
				while adding. Here's the syntax:
				<PolicyObjectName, Type>. Type is an integer to be chosen according to
				the list below:
				
				1) 5 - Outbound AccessPort
				2) 6 - Inbound AccessPort
				3) 9 - Outbound NIC
				4) 10 - Inbound NIC
				5) 17 - Outbound Bluetooth
				6) 18 - Inbound Bluetooth
						
				Only the first two are supported in the current version of the
				Wireless Switch. Attempts to set other types of Policy Objects will
				result in an error.
				The maximum number of characters allowed is 50, and the following
				characters cannot be part of the input string -
				',.,\,&, # and double quotes."
			::= { ccNPolicyMgmt 9 }

		
		-- 1.3.6.1.4.1.388.6.3.30.10
		ccPORemObj OBJECT-TYPE
			SYNTAX DisplayString (SIZE (1..50))
			MAX-ACCESS read-write
			STATUS current
			DESCRIPTION
				"Remove one Policy Object from the ccPOTable.
				The maximum number of characters allowed is 50, and the following
				characters cannot be part of the input string -
				',.,\,&, # and double quotes."
			::= { ccNPolicyMgmt 10 }

		
		-- 1.3.6.1.4.1.388.6.3.30.11
		ccNPAddObj OBJECT-TYPE
			SYNTAX DisplayString (SIZE (1..50))
			MAX-ACCESS read-write
			STATUS current
			DESCRIPTION
				"Add one network policy object into the ccNPTable.
				The maximum number of characters allowed is 50, and the following
				characters cannot be part of the input string -
				',.,\,&, # and double quotes."
			::= { ccNPolicyMgmt 11 }

		
		-- 1.3.6.1.4.1.388.6.3.30.12
		ccNPRemObj OBJECT-TYPE
			SYNTAX DisplayString (SIZE (1..50))
			MAX-ACCESS read-write
			STATUS current
			DESCRIPTION
				"Remove one network policy object from the ccNPTable.
				The maximum number of characters allowed is 50, and the following
				characters cannot be part of the input string -
				',.,\,&, # and double quotes."
			::= { ccNPolicyMgmt 12 }

		
		-- 1.3.6.1.4.1.388.6.3.30.13
		ccNPTable OBJECT-TYPE
			SYNTAX SEQUENCE OF CcNPEntry
			MAX-ACCESS not-accessible
			STATUS current
			DESCRIPTION
				"A list of Network Policy entries."
			::= { ccNPolicyMgmt 13 }

		
		-- 1.3.6.1.4.1.388.6.3.30.13.1
		ccNPEntry OBJECT-TYPE
			SYNTAX CcNPEntry
			MAX-ACCESS not-accessible
			STATUS current
			DESCRIPTION
				"A Network policy table entry."
			INDEX { ccNPIndex }
			::= { ccNPTable 1 }

		
		CcNPEntry ::=
			SEQUENCE { 
				ccNPIndex
					INTEGER,
				ccNPName
					DisplayString,
				ccNPDesc
					DisplayString,
				ccNPInName
					DisplayString,
				ccNPOutName
					DisplayString
			 }

		-- 1.3.6.1.4.1.388.6.3.30.13.1.1
		ccNPIndex OBJECT-TYPE
			SYNTAX INTEGER (1..100)
			MAX-ACCESS read-only
			STATUS current
			DESCRIPTION
				"A Network policy index."
			::= { ccNPEntry 1 }

		
		-- 1.3.6.1.4.1.388.6.3.30.13.1.2
		ccNPName OBJECT-TYPE
			SYNTAX DisplayString (SIZE (1..50))
			MAX-ACCESS read-write
			STATUS current
			DESCRIPTION
				"The network policy name.
				The Maximum length of the input string can be 50 characters. 
				Note that the following characters cannot be part of the input string- 
				',.,\,&, # and double quotes"
			::= { ccNPEntry 2 }

		
		-- 1.3.6.1.4.1.388.6.3.30.13.1.3
		ccNPDesc OBJECT-TYPE
			SYNTAX DisplayString (SIZE (0..128))
			MAX-ACCESS read-write
			STATUS current
			DESCRIPTION
				"The description of the network policy name.
				The Maximum length of the description can be 128 characters. 
				Note that the following characters cannot be part of the input string- 
				',# and double quotes"
			::= { ccNPEntry 3 }

		
		-- 1.3.6.1.4.1.388.6.3.30.13.1.4
		ccNPInName OBJECT-TYPE
			SYNTAX DisplayString (SIZE (1..50))
			MAX-ACCESS read-write
			STATUS current
			DESCRIPTION
				"The Input network policy name.The Maximum length of the input string can be 50 characters. 
				Note that the following characters cannot be part of the input string- 
				',.,\,&, # and double quotes"
			::= { ccNPEntry 4 }

		
		-- 1.3.6.1.4.1.388.6.3.30.13.1.5
		ccNPOutName OBJECT-TYPE
			SYNTAX DisplayString (SIZE (1..50))
			MAX-ACCESS read-write
			STATUS current
			DESCRIPTION
				"The Output network policy name.The Maximum length of the input string can be 50 characters. 
				Note that the following characters cannot be part of the input string- 
				',.,\,&, # and double quotes"
			::= { ccNPEntry 5 }

		
		-- 1.3.6.1.4.1.388.6.3.30.14
		ccPOTable OBJECT-TYPE
			SYNTAX SEQUENCE OF CcPOEntry
			MAX-ACCESS not-accessible
			STATUS current
			DESCRIPTION
				"A list of Policy Object entries."
			::= { ccNPolicyMgmt 14 }

		
		-- 1.3.6.1.4.1.388.6.3.30.14.1
		ccPOEntry OBJECT-TYPE
			SYNTAX CcPOEntry
			MAX-ACCESS not-accessible
			STATUS current
			DESCRIPTION
				"A policy table entry."
			INDEX { ccPOIndex }
			::= { ccPOTable 1 }

		
		CcPOEntry ::=
			SEQUENCE { 
				ccPOIndex
					INTEGER,
				ccPOName
					DisplayString,
				ccPODesc
					DisplayString,
				ccPOCgCount
					INTEGER,
				ccPOAddCg
					DisplayString,
				ccPORemCg
					DisplayString,
				ccPOType
					INTEGER,
				ccPOPacketModifier
					DisplayString
			 }

		-- 1.3.6.1.4.1.388.6.3.30.14.1.1
		ccPOIndex OBJECT-TYPE
			SYNTAX INTEGER (1..100)
			MAX-ACCESS not-accessible
			STATUS current
			DESCRIPTION
				"A Network policy index."
			::= { ccPOEntry 1 }

		
		-- 1.3.6.1.4.1.388.6.3.30.14.1.2
		ccPOName OBJECT-TYPE
			SYNTAX DisplayString (SIZE (1..50))
			MAX-ACCESS read-write
			STATUS current
			DESCRIPTION
				"The network policy name.
				The Maximum length of the input string can be 50 characters.
				Note that the following characters cannot be part of the input string- 
				',.,\,&, # and double quotes"
			::= { ccPOEntry 2 }

		
		-- 1.3.6.1.4.1.388.6.3.30.14.1.3
		ccPODesc OBJECT-TYPE
			SYNTAX DisplayString (SIZE (0..128))
			MAX-ACCESS read-write
			STATUS current
			DESCRIPTION
				"A description of the network policy.
				The Maximum length of the description can be 128 characters. 
				Note that the following characters cannot be part of the input string-
				',# and double quotes."
			::= { ccPOEntry 3 }

		
		-- 1.3.6.1.4.1.388.6.3.30.14.1.4
		ccPOCgCount OBJECT-TYPE
			SYNTAX INTEGER (1..100)
			MAX-ACCESS read-only
			STATUS current
			DESCRIPTION
				"The count of CGs in the Policy object."
			::= { ccPOEntry 4 }

		
		-- 1.3.6.1.4.1.388.6.3.30.14.1.11
		ccPOAddCg OBJECT-TYPE
			SYNTAX DisplayString (SIZE (1..50))
			MAX-ACCESS read-write
			STATUS current
			DESCRIPTION
				"Add a classification group to the policy."
			::= { ccPOEntry 11 }

		
		-- 1.3.6.1.4.1.388.6.3.30.14.1.12
		ccPORemCg OBJECT-TYPE
			SYNTAX DisplayString (SIZE (1..50))
			MAX-ACCESS read-write
			STATUS current
			DESCRIPTION
				"Remove a classification group from the policy."
			::= { ccPOEntry 12 }

		
		-- 1.3.6.1.4.1.388.6.3.30.14.1.13
		ccPOType OBJECT-TYPE
			SYNTAX INTEGER (1..20)
			MAX-ACCESS read-only
			STATUS current
			DESCRIPTION
				"The type of the Policy Object. The returned value denotes one of the following:
				1) 5 - Outbound AccessPort
				2) 6 - Inbound AccessPort
				3) 9 - Outbound NIC
				4) 10 - Inbound NIC
				5) 17 - Outbound Bluetooth
				6) 18 - Inbound Bluetooth
				
				Only the first two are supported in the current version of the
				Wireless Switch."
			::= { ccPOEntry 13 }

		
		-- 1.3.6.1.4.1.388.6.3.30.14.1.14
		ccPOPacketModifier OBJECT-TYPE
			SYNTAX DisplayString (SIZE (1..100))
			MAX-ACCESS read-only
			STATUS deprecated
			DESCRIPTION
				"Denotes which of 'TOS','Priority', and 'IP-Redirect' are
				being used for modifying the packets."
			::= { ccPOEntry 14 }

		
		-- 1.3.6.1.4.1.388.6.3.30.15
		ccCGTable OBJECT-TYPE
			SYNTAX SEQUENCE OF CcCGEntry
			MAX-ACCESS not-accessible
			STATUS current
			DESCRIPTION
				"A table of Classification Group entries."
			::= { ccNPolicyMgmt 15 }

		
		-- 1.3.6.1.4.1.388.6.3.30.15.1
		ccCGEntry OBJECT-TYPE
			SYNTAX CcCGEntry
			MAX-ACCESS not-accessible
			STATUS current
			DESCRIPTION
				"A network classificaton group table entry."
			INDEX { ccCGIndex }
			::= { ccCGTable 1 }

		
		CcCGEntry ::=
			SEQUENCE { 
				ccCGIndex
					INTEGER,
				ccCGName
					DisplayString,
				ccCGDesc
					DisplayString,
				ccCGCfCount
					INTEGER,
				ccCGAddCf
					DisplayString,
				ccCGRemCf
					DisplayString
			 }

		-- 1.3.6.1.4.1.388.6.3.30.15.1.1
		ccCGIndex OBJECT-TYPE
			SYNTAX INTEGER (1..100)
			MAX-ACCESS not-accessible
			STATUS current
			DESCRIPTION
				"The index for the traffic classification group entry. "
			::= { ccCGEntry 1 }

		
		-- 1.3.6.1.4.1.388.6.3.30.15.1.2
		ccCGName OBJECT-TYPE
			SYNTAX DisplayString (SIZE (1..50))
			MAX-ACCESS read-write
			STATUS current
			DESCRIPTION
				"A Classification Group name.
				The Maximum length of the input string can be 50 characters. 
				Note that the following characters cannot be part of the input string- 
				',.,\,&, # and double quotes"
			::= { ccCGEntry 2 }

		
		-- 1.3.6.1.4.1.388.6.3.30.15.1.3
		ccCGDesc OBJECT-TYPE
			SYNTAX DisplayString (SIZE (0..128))
			MAX-ACCESS read-write
			STATUS current
			DESCRIPTION
				"A description of the CG.
				The Maximum length of the description can be 128 characters. 
				Note that the following characters cannot be part of description - 
				',# and double quotes"
			::= { ccCGEntry 3 }

		
		-- 1.3.6.1.4.1.388.6.3.30.15.1.4
		ccCGCfCount OBJECT-TYPE
			SYNTAX INTEGER (1..100)
			MAX-ACCESS read-only
			STATUS current
			DESCRIPTION
				"The number of Classifier included in the Classification Group."
			::= { ccCGEntry 4 }

		
		-- 1.3.6.1.4.1.388.6.3.30.15.1.7
		ccCGAddCf OBJECT-TYPE
			SYNTAX DisplayString (SIZE (1..50))
			MAX-ACCESS read-write
			STATUS current
			DESCRIPTION
				"Add a new classifier to the classification group."
			::= { ccCGEntry 7 }

		
		-- 1.3.6.1.4.1.388.6.3.30.15.1.8
		ccCGRemCf OBJECT-TYPE
			SYNTAX DisplayString (SIZE (1..50))
			MAX-ACCESS read-write
			STATUS current
			DESCRIPTION
				"Remove a classifier from the classification group."
			::= { ccCGEntry 8 }

		
		-- 1.3.6.1.4.1.388.6.3.30.16
		ccCFTable OBJECT-TYPE
			SYNTAX SEQUENCE OF CcCFEntry
			MAX-ACCESS not-accessible
			STATUS current
			DESCRIPTION
				"A table of Classifier entries. "
			::= { ccNPolicyMgmt 16 }

		
		-- 1.3.6.1.4.1.388.6.3.30.16.1
		ccCFEntry OBJECT-TYPE
			SYNTAX CcCFEntry
			MAX-ACCESS not-accessible
			STATUS current
			DESCRIPTION
				"A network traffic classifier table entry."
			INDEX { ccCFIndex }
			::= { ccCFTable 1 }

		
		CcCFEntry ::=
			SEQUENCE { 
				ccCFIndex
					INTEGER,
				ccCFName
					DisplayString,
				ccCFDesc
					DisplayString,
				ccCFMcCount
					INTEGER,
				ccCFAddMc
					MCValueOffset,
				ccCFRemMc
					MCValueOffset
			 }

		-- 1.3.6.1.4.1.388.6.3.30.16.1.1
		ccCFIndex OBJECT-TYPE
			SYNTAX INTEGER (1..100)
			MAX-ACCESS not-accessible
			STATUS current
			DESCRIPTION
				"The index of Network Traffic classifier."
			::= { ccCFEntry 1 }

		
		-- 1.3.6.1.4.1.388.6.3.30.16.1.2
		ccCFName OBJECT-TYPE
			SYNTAX DisplayString (SIZE (1..50))
			MAX-ACCESS read-write
			STATUS current
			DESCRIPTION
				"The name of the classifier.
				The maximum number of characters allowed is 50, and the following
				characters cannot be part of the input string -
				',.,\,&, # and double quotes."
			::= { ccCFEntry 2 }

		
		-- 1.3.6.1.4.1.388.6.3.30.16.1.3
		ccCFDesc OBJECT-TYPE
			SYNTAX DisplayString (SIZE (0..128))
			MAX-ACCESS read-write
			STATUS current
			DESCRIPTION
				"The description of a classifier entry.
				The maximum number of characters allowed is 128, and the following
				characters cannot be part of the input string -
				',# and double quotes."
			::= { ccCFEntry 3 }

		
		-- 1.3.6.1.4.1.388.6.3.30.16.1.4
		ccCFMcCount OBJECT-TYPE
			SYNTAX INTEGER (1..100)
			MAX-ACCESS read-only
			STATUS current
			DESCRIPTION
				"The number of Matching Criterion for the classifier."
			::= { ccCFEntry 4 }

		
		-- 1.3.6.1.4.1.388.6.3.30.16.1.10
		ccCFAddMc OBJECT-TYPE
			SYNTAX MCValueOffset
			MAX-ACCESS read-write
			STATUS current
			DESCRIPTION
				"Add one Matching Criteria to the Classifier.
				Choose from the following list of offsets:
				srcMacAddr(0),
				desMacAddr(1),
				etherType(2),
				vlanID(3),
				userPriority(4),
				protocol(5),
				tos(6),
				srcIPAddr(7),
				desIPAddr(8),
				srcPort(9),
				desPort(10),
				multicastMask(11)
				Note:
				This object is SET-only."
			::= { ccCFEntry 10 }

		
		-- 1.3.6.1.4.1.388.6.3.30.16.1.11
		ccCFRemMc OBJECT-TYPE
			SYNTAX MCValueOffset
			MAX-ACCESS read-write
			STATUS current
			DESCRIPTION
				"Remove one Matching Criteria from the Classifier.
				Choose from the following list of offsets:
				srcMacAddr(0),
				desMacAddr(1),
				etherType(2),
				vlanID(3),
				userPriority(4),
				protocol(5),
				tos(6),
				srcIPAddr(7),
				desIPAddr(8),
				srcPort(9),
				desPort(10),
				multicastMask(11)		
				Note:
				This object is SET-only."
			::= { ccCFEntry 11 }

		
		-- 1.3.6.1.4.1.388.6.3.30.17
		ccPOObjects OBJECT IDENTIFIER ::= { ccNPolicyMgmt 17 }

		
		-- 1.3.6.1.4.1.388.6.3.30.17.2
		ccPOCGTable OBJECT-TYPE
			SYNTAX SEQUENCE OF CcPOCGEntry
			MAX-ACCESS not-accessible
			STATUS current
			DESCRIPTION
				"A list of per Policy Object, per Classificatin Group entries."
			::= { ccPOObjects 2 }

		
		-- 1.3.6.1.4.1.388.6.3.30.17.2.1
		ccPOCGEntry OBJECT-TYPE
			SYNTAX CcPOCGEntry
			MAX-ACCESS not-accessible
			STATUS current
			DESCRIPTION
				"An entry of Policy Objects, per Classification Group."
			INDEX { ccPOCGIndex }
			::= { ccPOCGTable 1 }

		
		CcPOCGEntry ::=
			SEQUENCE { 
				ccPOCGIndex
					INTEGER,
				ccPOCGName
					DisplayString,
				ccPOCGNewIP
					DisplayString,
				ccPOCGVlanPriority
					DisplayString,
				ccPOCGTos
					DisplayString,
				ccPOCGBw
					INTEGER,
				ccPOCGTxProfile
					INTEGER,
				ccPOCGPacketModifier
					DisplayString
			 }

		-- 1.3.6.1.4.1.388.6.3.30.17.2.1.1
		ccPOCGIndex OBJECT-TYPE
			SYNTAX INTEGER (1..200)
			MAX-ACCESS not-accessible
			STATUS current
			DESCRIPTION
				"The index of this Classification Group, per Policy Object"
			::= { ccPOCGEntry 1 }

		
		-- 1.3.6.1.4.1.388.6.3.30.17.2.1.2
		ccPOCGName OBJECT-TYPE
			SYNTAX DisplayString (SIZE (1..50))
			MAX-ACCESS read-only
			STATUS current
			DESCRIPTION
				"The classification group name which belong to the policy object."
			::= { ccPOCGEntry 2 }

		
		-- 1.3.6.1.4.1.388.6.3.30.17.2.1.3
		ccPOCGNewIP OBJECT-TYPE
			SYNTAX DisplayString (SIZE (1..15))
			MAX-ACCESS read-write
			STATUS current
			DESCRIPTION
				"The new IP address used by the CG in the Policy Object
				for IP-Redirect. Valid only for Input Policy Objects.
				For disabling the use of IP-Redirect,use the string
				'disable' as input for this OID.Any valid IP address as
				the input automatically enables its usage."
			::= { ccPOCGEntry 3 }

		
		-- 1.3.6.1.4.1.388.6.3.30.17.2.1.4
		ccPOCGVlanPriority OBJECT-TYPE
			SYNTAX DisplayString (SIZE (1..32))
			MAX-ACCESS read-write
			STATUS current
			DESCRIPTION
				"The priority of the VLAN in the CG governed by the Policy Object.
				0 to 7 only. Valid only for Input Policy Objects (Trying to 
				SET for an Output Policy results in an error).
				For disabling the use of Vlan Priority, use the string 'disable'. 
				Any value from 0 through 7 automatically enables its usage."
			::= { ccPOCGEntry 4 }

		
		-- 1.3.6.1.4.1.388.6.3.30.17.2.1.5
		ccPOCGTos OBJECT-TYPE
			SYNTAX DisplayString (SIZE (1..32))
			MAX-ACCESS read-write
			STATUS current
			DESCRIPTION
				"The Type of Service in the Policy Object.
				This is specific to the enterprise in which
				the Wireless Switch is deployed.The user has to input
				a bit pattern of six bits.Valid for both Input and Output 
				Policies.For disabling the TOS, use 'disable' as the
				input for this OID. Any valid 6-bit sequence automatically 
				enables its usage."
			::= { ccPOCGEntry 5 }

		
		-- 1.3.6.1.4.1.388.6.3.30.17.2.1.6
		ccPOCGBw OBJECT-TYPE
			SYNTAX INTEGER (1..100)
			MAX-ACCESS read-write
			STATUS current
			DESCRIPTION
				"The Bandwidth in the CG of the Policy Object.
				Valid only for Output Policy (Trying to 
				SET for an Input Policy results in an error). A '-1' in the reply
				implies that the policy being queried was an Input Policy."
			::= { ccPOCGEntry 6 }

		
		-- 1.3.6.1.4.1.388.6.3.30.17.2.1.7
		ccPOCGTxProfile OBJECT-TYPE
			SYNTAX INTEGER (0..2)
			MAX-ACCESS read-write
			STATUS current
			DESCRIPTION
				"The TxProfile of the Policy Object.
				This controls how the AccessPort treats 
				a packet. Valid only for an Output policy (Trying to 
				SET for an Input Policy results in an error).
				Values are 0 & 2.
				0 is Data
				2 is Voice
				-1 in reply implies that the policy being queried was an Input Policy."
			::= { ccPOCGEntry 7 }

		
		-- 1.3.6.1.4.1.388.6.3.30.17.2.1.8
		ccPOCGPacketModifier OBJECT-TYPE
			SYNTAX DisplayString (SIZE (1..100))
			MAX-ACCESS read-only
			STATUS current
			DESCRIPTION
				"Denotes which of 'TOS','Priority', and 'IP-Redirect' are
				being used for modifying the packets."
			::= { ccPOCGEntry 8 }

		
		-- 1.3.6.1.4.1.388.6.3.30.18
		ccCGObjects OBJECT IDENTIFIER ::= { ccNPolicyMgmt 18 }

		
		-- 1.3.6.1.4.1.388.6.3.30.18.2
		ccCGCFTable OBJECT-TYPE
			SYNTAX SEQUENCE OF CcCGCFEntry
			MAX-ACCESS not-accessible
			STATUS current
			DESCRIPTION
				"A table of Classier Entries, per Classification Group."
			::= { ccCGObjects 2 }

		
		-- 1.3.6.1.4.1.388.6.3.30.18.2.1
		ccCGCFEntry OBJECT-TYPE
			SYNTAX CcCGCFEntry
			MAX-ACCESS not-accessible
			STATUS current
			DESCRIPTION
				"A Classifier entry, per Classification Group"
			INDEX { ccCGIndex, ccCGCFIndex }
			::= { ccCGCFTable 1 }

		
		CcCGCFEntry ::=
			SEQUENCE { 
				ccCGCFIndex
					INTEGER,
				ccCGCFAction
					DisplayString,
				ccCGCFName
					DisplayString
			 }

		-- 1.3.6.1.4.1.388.6.3.30.18.2.1.1
		ccCGCFIndex OBJECT-TYPE
			SYNTAX INTEGER (1..200)
			MAX-ACCESS not-accessible
			STATUS current
			DESCRIPTION
				"The index of this classifier, per Classification Group"
			::= { ccCGCFEntry 1 }

		
		-- 1.3.6.1.4.1.388.6.3.30.18.2.1.2
		ccCGCFAction OBJECT-TYPE
			SYNTAX DisplayString (SIZE (4..5))
			MAX-ACCESS read-write
			STATUS current
			DESCRIPTION
				"Indicates the allow/deny action for this Classifier belonging to this Classification Group."
			::= { ccCGCFEntry 2 }

		
		-- 1.3.6.1.4.1.388.6.3.30.18.2.1.3
		ccCGCFName OBJECT-TYPE
			SYNTAX DisplayString (SIZE (1..50))
			MAX-ACCESS read-only
			STATUS current
			DESCRIPTION
				"The name of the classifier in this CG."
			::= { ccCGCFEntry 3 }

		
		-- 1.3.6.1.4.1.388.6.3.30.19
		ccCFObjects OBJECT IDENTIFIER ::= { ccNPolicyMgmt 19 }

		
		-- 1.3.6.1.4.1.388.6.3.30.19.2
		ccCFMcTable OBJECT-TYPE
			SYNTAX SEQUENCE OF CcCFMcEntry
			MAX-ACCESS not-accessible
			STATUS current
			DESCRIPTION
				"A table of Matching Criteria per Classifier."
			::= { ccCFObjects 2 }

		
		-- 1.3.6.1.4.1.388.6.3.30.19.2.1
		ccCFMcEntry OBJECT-TYPE
			SYNTAX CcCFMcEntry
			MAX-ACCESS not-accessible
			STATUS current
			DESCRIPTION
				"A Matching Criteria table entry (per Classifier)."
			INDEX { ccCFIndex, ccCFMCIndex }
			::= { ccCFMcTable 1 }

		
		CcCFMcEntry ::=
			SEQUENCE { 
				ccCFMCIndex
					INTEGER,
				ccCFMCOffset
					MCValueOffset,
				ccCFMCValueCount
					INTEGER,
				ccCFAddMCValue
					DisplayString,
				ccCFRemMCValue
					DisplayString
			 }

		-- 1.3.6.1.4.1.388.6.3.30.19.2.1.1
		ccCFMCIndex OBJECT-TYPE
			SYNTAX INTEGER (1..200)
			MAX-ACCESS not-accessible
			STATUS current
			DESCRIPTION
				"The index of this Matching Criteria"
			::= { ccCFMcEntry 1 }

		
		-- 1.3.6.1.4.1.388.6.3.30.19.2.1.2
		ccCFMCOffset OBJECT-TYPE
			SYNTAX MCValueOffset
			MAX-ACCESS read-only
			STATUS current
			DESCRIPTION
				"The offset of the Matching Criterion.
				The offsets are:
				srcMacAddr(0),
				desMacAddr(1),
				etherType(2),
				vlanID(3),
				userPriority(4),
				protocol(5),
				tos(6),
				srcIPAddr(7),
				desIPAddr(8),
				srcPort(9),
				desPort(10),
				multicastMask(11)		
				A '-1' in the reply indicates no offset available.
				"
			::= { ccCFMcEntry 2 }

		
		-- 1.3.6.1.4.1.388.6.3.30.19.2.1.3
		ccCFMCValueCount OBJECT-TYPE
			SYNTAX INTEGER (1..100)
			MAX-ACCESS read-only
			STATUS current
			DESCRIPTION
				"The number of values in this Matching Criterion."
			::= { ccCFMcEntry 3 }

		
		-- 1.3.6.1.4.1.388.6.3.30.19.2.1.4
		ccCFAddMCValue OBJECT-TYPE
			SYNTAX DisplayString
			MAX-ACCESS read-write
			STATUS current
			DESCRIPTION
				"Add one value to the Matching Criteria. 
				For Source and Destination IP,
				Use syntax : <IPAddress:Net Mask>.
				             <IPAddress-IPAddress>.
				             <IPAddress>/<CIDR bits>.
				For Protocol, choose the number from the list:
				
				Protocol
				Number	   Keyword     Protocol                         References
				-------    -------     --------                         ----------
				    0     		HOPOPT      IPv6 Hop-by-Hop Option            [RFC1883]
				    1     		ICMP        Internet Control Message           [RFC792]
				    2     		IGMP        Internet Group Management         [RFC1112]
				    3     		GGP         Gateway-to-Gateway                 [RFC823]
				    4     		IP          IP in IP (encapsulation)          [RFC2003]
				    5     		ST          Stream                    [RFC1190,RFC1819]
				    6     		TCP         Transmission Control               [RFC793]
				    7     		CBT         CBT                             [Ballardie]
				    8     		EGP         Exterior Gateway Protocol     [RFC888,DLM1]
				    9     		IGP         any private interior gateway         [IANA]
				          		            (used by Cisco for their IGRP)
				   10     		BBN-RCC-MON BBN RCC Monitoring                    [SGC]
				   11     		NVP-II      Network Voice Protocol         [RFC741,SC3]
				   12     		PUP         PUP                             [PUP,XEROX]
				   13     		ARGUS       ARGUS                                [RWS4]
				   14     		EMCON       EMCON                                 [BN7]
				   15     		XNET        Cross Net Debugger            [IEN158,JFH2]
				   16     		CHAOS       Chaos                                 [NC3]
				   17     		UDP         User Datagram                  [RFC768,JBP]
				   18     		MUX         Multiplexing                    [IEN90,JBP]
				   19     		DCN-MEAS    DCN Measurement Subsystems           [DLM1]
				   20     		HMP         Host Monitoring                [RFC869,RH6]
				   21     		PRM         Packet Radio Measurement              [ZSU]
				   22     		XNS-IDP     XEROX NS IDP               [ETHERNET,XEROX]
				   23     		TRUNK-1     Trunk-1                              [BWB6]
				   24     		TRUNK-2     Trunk-2                              [BWB6]
				   25     		LEAF-1      Leaf-1                               [BWB6]
				   26     		LEAF-2      Leaf-2                               [BWB6]
				   27     		RDP         Reliable Data Protocol         [RFC908,RH6]
				   28     		IRTP        Internet Reliable Transaction  [RFC938,TXM]
				   29     		ISO-TP4     ISO Transport Protocol Class 4 [RFC905,RC77]
				   30     		NETBLT      Bulk Data Transfer Protocol    [RFC969,DDC1]
				   31     		MFE-NSP     MFE Network Services Protocol  [MFENET,BCH2]
				   32     		MERIT-INP   MERIT Internodal Protocol             [HWB]
				   33     		SEP         Sequential Exchange Protocol        [JC120]
				   34     		3PC         Third Party Connect Protocol         [SAF3]
				   35     		IDPR        Inter-Domain Policy Routing Protocol [MXS1] 
				   36     		XTP         XTP                                   [GXC]
				   37     		DDP         Datagram Delivery Protocol            [WXC]
				   38     		IDPR-CMTP   IDPR Control Message Transport Proto [MXS1]
				   39     		TP++        TP++ Transport Protocol               [DXF]
				   40     		IL          IL Transport Protocol            [Presotto]
				   41     		IPv6        Ipv6                              [Deering]    
				   42     		SDRP        Source Demand Routing Protocol       [DXE1]
				   43     		IPv6-Route  Routing Header for IPv6           [Deering]
				   44     		IPv6-Frag   Fragment Header for IPv6          [Deering]
				   45     		IDRP        Inter-Domain Routing Protocol   [Sue Hares]
				   46     		RSVP        Reservation Protocol           [Bob Braden]
				   47     		GRE         General Routing Encapsulation     [Tony Li]
				   48     		MHRP        Mobile Host Routing Protocol[David Johnson]
				   49     		BNA         BNA                          [Gary Salamon]
				   50     		ESP         Encapsulating Security Payload    [RFC1827]
				   51     		AH          Authentication Header             [RFC1826]
				   52     		I-NLSP      Integrated Net Layer Security  TUBA [GLENN]
				   53     		SWIPE       IP with Encryption                    [JI6]
				   54     		NARP        NBMA Address Resolution Protocol  [RFC1735]
				   55     		MOBILE      IP Mobility                       [Perkins]
				   56     		TLSP        Transport Layer Security Protocol   [Oberg]
				          		            using Kryptonet key management
				   57     		SKIP        SKIP                              [Markson]
				   58     		IPv6-ICMP   ICMP for IPv6                     [RFC1883]
				   59     		IPv6-NoNxt  No Next Header for IPv6           [RFC1883]
				   60     		IPv6-Opts   Destination Options for IPv6      [RFC1883]
				   61     		            any host internal protocol           [IANA]
				   62     		CFTP        CFTP                            [CFTP,HCF2]
				   63     		            any local network                    [IANA]
				   64     		SAT-EXPAK   SATNET and Backroom EXPAK             [SHB]
				   65     		KRYPTOLAN   Kryptolan                            [PXL1]
				   66     		RVD         MIT Remote Virtual Disk Protocol      [MBG]
				   67     		IPPC        Internet Pluribus Packet Core         [SHB]
				   68     		            any distributed file system          [IANA]
				   69     		SAT-MON     SATNET Monitoring                     [SHB]
				   70     		VISA        VISA Protocol                        [GXT1]
				   71     		IPCV        Internet Packet Core Utility          [SHB]
				   72     		CPNX        Computer Protocol Network Executive  [DXM2]
				   73     		CPHB        Computer Protocol Heart Beat         [DXM2]
				   74     		WSN         Wang Span Network                     [VXD]
				   75     		PVP         Packet Video Protocol                 [SC3]
				   76     		BR-SAT-MON  Backroom SATNET Monitoring            [SHB]
				   77     		SUN-ND      SUN ND PROTOCOL-Temporary             [WM3]
				   78     		WB-MON      WIDEBAND Monitoring                   [SHB]
				   79     		WB-EXPAK    WIDEBAND EXPAK                        [SHB]
				   80     		ISO-IP      ISO Internet Protocol                 [MTR]
				   81     		VMTP        VMTP                                 [DRC3]
				   82     		SECURE-VMTP SECURE-VMTP                          [DRC3]
				   83     		VINES       VINES                                 [BXH]
				   84     		TTP         TTP                                   [JXS]
				   85     		NSFNET-IGP  NSFNET-IGP                            [HWB]
				   86     		DGP         Dissimilar Gateway Protocol     [DGP,ML109]
				   87     		TCF         TCF                                  [GAL5]
				   88     		EIGRP       EIGRP                           [CISCO,GXS]
				   89     		OSPFIGP     OSPFIGP                      [RFC1583,JTM4]
				   90     		Sprite-RPC  Sprite RPC Protocol            [SPRITE,BXW] 
				   91     		LARP        Locus Address Resolution Protocol     [BXH]
				   92     		MTP         Multicast Transport Protocol          [SXA]
				   93     		AX.25       AX.25 Frames                         [BK29]         
				   94     		IPIP        IP-within-IP Encapsulation Protocol   [JI6]
				   95     		MICP        Mobile Internetworking Control Pro.   [JI6]
				   96     		SCC-SP      Semaphore Communications Sec. Pro.    [HXH]     
				   97     		ETHERIP     Ethernet-within-IP Encapsulation     [RDH1]
				   98     		ENCAP       Encapsulation Header         [RFC1241,RXB3]
				   99     		            any private encryption scheme        [IANA]
				  100     		GMTP        GMTP                                 [RXB5]
				  101     		IFMP        Ipsilon Flow Management Protocol   [Hinden]
				  102     		PNNI        PNNI over IP                       [Callon]
				  103     		PIM         Protocol Independent Multicast  [Farinacci]
				  104     		ARIS        ARIS                              [Feldman]
				  105     		SCPS	       SCPS				  				 [Durst]
				  106 	   		QNX	       QNX				  					[Hunter]
				  107	   		A/N	       Active Networks                    [Braden]
				  108	   		IPComp      IP Payload Compression Protocol   [RFC2393]
				  109	   		SNP	       Sitara Networks Protocol          [Sridhar]
				  110	   		Compaq-Peer Compaq Peer Protocol                [Volpe]
				  111	   		IPX-in-IP   IPX in IP		  	    			 [Lee]
				  112     		VRRP	       Virtual Router Redundancy Protocol [Hinden]
				  113     		PGM         PGM Reliable Transport Protocol  [Speakman]
				  114     		            any 0-hop protocol                   [IANA]
				  115	   		L2TP        Layer Two Tunneling Protocol        [Aboba]
				  116     		DDX	       D-II Data Exchange (DDX)           [Worley] 
				  117	   		IATP      Interactive Agent Transfer Protocol  [Murphy]
				  118     		STP         Schedule Transfer Protocol            [JMP]
				  119     		SRP	       SpectraLink Radio Protocol       [Hamilton]	
				  120     		UTI	       UTI								[Lothberg]	
				  121     		SMP	       Simple Message Protocol            [Ekblad]
				  122	   		SM		SM			       					[Crowcroft]
				  123	   		PTP         Performance Transparency Protocol   [Welzl]
				  124     		ISIS over IPv4			      				[Przygienda]
				  125     		FIRE					       					[Partridge]
				  126	   		CRTP		Combat Radio Transport Protocol  	[Sautter]
				  127	   		CRUDP	Combat Radio User Datagram	 		[Sautter]
				  128     		SSCOPMCE					  					 [Waber]
				  129     		IPLT											[Hollbach]
				  130     		SPS         Secure Packet Shield             [McIntosh] 
				  131     		PIPE   Private IP Encapsulation within IP       [Petri]
				  132     		SCTP   Stream Control Transmission Protocol   [Stewart]
				  133     		FC     Fibre Channel                        [Rajagopal]
				  134     		RSVP-E2E-IGNORE                               [RFC3175]
				  135-254 		            Unassigned                           [IANA]
				  255     		            Reserved                             [IANA]
				
				  This is Write only"
			::= { ccCFMcEntry 4 }

		
		-- 1.3.6.1.4.1.388.6.3.30.19.2.1.5
		ccCFRemMCValue OBJECT-TYPE
			SYNTAX DisplayString (SIZE (1..50))
			MAX-ACCESS read-write
			STATUS current
			DESCRIPTION
				"Remove one value from the Matching Criteria.
				The maximum number of characters allowed is 50, and the following
				characters cannot be part of the input string -
				',.,\,&, # and double quotes.
					 This is Write-only."
			::= { ccCFMcEntry 5 }

		
		-- 1.3.6.1.4.1.388.6.3.30.19.3
		ccCFMcValTable OBJECT-TYPE
			SYNTAX SEQUENCE OF CcCFMcValEntry
			MAX-ACCESS not-accessible
			STATUS current
			DESCRIPTION
				"A table of the values per Matching Criterion."
			::= { ccCFObjects 3 }

		
		-- 1.3.6.1.4.1.388.6.3.30.19.3.1
		ccCFMcValEntry OBJECT-TYPE
			SYNTAX CcCFMcValEntry
			MAX-ACCESS not-accessible
			STATUS current
			DESCRIPTION
				"An entry of Matching Criteria values (per Classifier, per Matching Criteria)."
			INDEX { ccCFIndex, ccCFMCIndex, ccCFMcValIndex }
			::= { ccCFMcValTable 1 }

		
		CcCFMcValEntry ::=
			SEQUENCE { 
				ccCFMcValIndex
					INTEGER,
				ccCFMCValue
					DisplayString
			 }

		-- 1.3.6.1.4.1.388.6.3.30.19.3.1.1
		ccCFMcValIndex OBJECT-TYPE
			SYNTAX INTEGER (1..200)
			MAX-ACCESS not-accessible
			STATUS current
			DESCRIPTION
				"The index of this value in the Matching Criteria."
			::= { ccCFMcValEntry 1 }

		
		-- 1.3.6.1.4.1.388.6.3.30.19.3.1.2
		ccCFMCValue OBJECT-TYPE
			SYNTAX DisplayString (SIZE (1..1024))
			MAX-ACCESS read-only
			STATUS current
			DESCRIPTION
				"The value of the Matching Criterion.
				For Source and Destination IP, 
				the returned value is of the format:
				 <IPAddress:Net Mask>
				 <IPAddress-IPAddress> 
				 <IPAddress>/<CIDR bits> 
				"
			::= { ccCFMcValEntry 2 }

		
		-- 1.3.6.1.4.1.388.6.3.31
		ccHSBConfigure OBJECT IDENTIFIER ::= { symbolCCMgmt 31 }

		
		-- 1.3.6.1.4.1.388.6.3.31.1
		ccHsbEnabled OBJECT-TYPE
			SYNTAX TruthValue
			MAX-ACCESS read-write
			STATUS current
			DESCRIPTION
				"Setting ccHsbEnabled to <true(1)> enables the Standby Management feature, 
				Setting ccHsbEnabled to <false(2)> disables the Standby Management feature 
				
				Mower: default value is FALSE."
			::= { ccHSBConfigure 1 }
-- Mower: removed defval=FALSE to eliminate info message;
-- added this fact to the description clause.
		
		-- 1.3.6.1.4.1.388.6.3.31.2
		ccHsbMode OBJECT-TYPE
			SYNTAX DisplayString (SIZE (1..32))
			MAX-ACCESS read-write
			STATUS current
			DESCRIPTION
				"Standby Mode of the wireless switch, Primary or Standby"
			::= { ccHSBConfigure 2 }

		
		-- 1.3.6.1.4.1.388.6.3.31.3
		ccHsbMacAddress1 OBJECT-TYPE
			SYNTAX DisplayString (SIZE (1..32))
			MAX-ACCESS read-write
			STATUS current
			DESCRIPTION
				"MAC address for establishing the heartbeat
				When the MAC address is set to 00:00:00:00:00:00
				it sets the option to Auto discovery Enabled
								
				Note:Disable ccHsbEnabled first to set this OID 
				"
			::= { ccHSBConfigure 3 }

		
		-- 1.3.6.1.4.1.388.6.3.31.4
		ccHsbMacAddress2 OBJECT-TYPE
			SYNTAX DisplayString (SIZE (1..32))
			MAX-ACCESS read-write
			STATUS current
			DESCRIPTION
				"Second Mac address for establishing the heartbeat
				When the MAC address is set to 00:00:00:00:00:00
				it sets the option to Auto discovery Enabled
								
				Note:Disable ccHsbEnabled first to set this OID
				 
				"
			::= { ccHSBConfigure 4 }

		
		-- 1.3.6.1.4.1.388.6.3.31.5
		ccHsbHeartbeatEnabledOnInterface1 OBJECT-TYPE
			SYNTAX TruthValue
			MAX-ACCESS read-write
			STATUS current
			DESCRIPTION
				"Setting to <true(1)> enables the heartbeat on interface 1, 
				Setting to <false(2)> enables the heartbeat on interface 1
				
				Mower: default value is TRUE.
				
				Note:Disable ccHsbEnabled first to set this OID
				"
			::= { ccHSBConfigure 5 }
-- Mower: removed defval=TRUE to eliminate info message;
-- added this fact to the description clause.
		
		-- 1.3.6.1.4.1.388.6.3.31.6
		ccHsbHeartbeatEnabledOnInterface2 OBJECT-TYPE
			SYNTAX TruthValue
			MAX-ACCESS read-write
			STATUS current
			DESCRIPTION
				"Setting to <true(1)> enables the heartbeat on interface 2, 
				Setting to <false(2)> enables the heartbeat on interface 2
				
				Mower: default value is FALSE.
				
				Note:Disable ccHsbEnabled first to set this OID
				"
			::= { ccHSBConfigure 6 }
-- Mower: removed defval=FALSE to eliminate info message;
-- added this fact to the description clause.
		
		-- 1.3.6.1.4.1.388.6.3.31.7
		ccHsbConnectivityFlag OBJECT-TYPE
			SYNTAX TruthValue
			MAX-ACCESS read-only
			STATUS current
			DESCRIPTION
				"Tells the user if connectivity (heartbeat) between the Primary and 
				Standby is established
				
				Mower: default value is FALSE."
			::= { ccHSBConfigure 7 }
-- Mower: removed defval=FALSE to eliminate info message;
-- added this fact to the description clause.
		
		-- 1.3.6.1.4.1.388.6.3.31.8
		ccHsbFailoverState OBJECT-TYPE
			SYNTAX HsbState
			MAX-ACCESS read-only
			STATUS current
			DESCRIPTION
				"This is the state of the Wireless switch. Here are the states
				1:  Startup                  
				2:  Find Standby             
				3:  Waiting for Connectivity 
				4:  Connected                
				5:  Halted                   
				6:  Monitoring               
				7:  Acting as Primary
				8:  Trying to Reconnect
				9:  Re-Connected
				10:  Auto-Reverting"
			::= { ccHSBConfigure 8 }

		
		-- 1.3.6.1.4.1.388.6.3.31.9
		ccHsbFailoverReason OBJECT-TYPE
			SYNTAX DisplayString (SIZE (1..200))
			MAX-ACCESS read-only
			STATUS current
			DESCRIPTION
				"This parameter tells the reason for failover."
			::= { ccHSBConfigure 9 }

		
		-- 1.3.6.1.4.1.388.6.3.31.10
		ccHsbResetCode OBJECT-TYPE
			SYNTAX INTEGER (1..8)
			MAX-ACCESS read-only
			STATUS current
			DESCRIPTION
				"This is a number set by the Wireless switch when it reboots."
			::= { ccHSBConfigure 10 }

		
		-- 1.3.6.1.4.1.388.6.3.31.11
		ccHsbRevert OBJECT-TYPE
			SYNTAX TruthValue
			MAX-ACCESS read-write
			STATUS current
			DESCRIPTION
				"This is a Boolean variable. When the manager sets this variable to true 
				the standby-active will revert to standby and disabled-primary will revert 
				to primary. Reading this value results in a -1 being returned.
				
				Mower: default value is FALSE."
			::= { ccHSBConfigure 11 }
-- Mower: removed defval=FALSE to eliminate info message;
-- added this fact to the description clause.
		
		-- 1.3.6.1.4.1.388.6.3.31.12
		ccHsbautorevert OBJECT-TYPE
			SYNTAX TruthValue
			MAX-ACCESS read-write
			STATUS current
			DESCRIPTION
				"State of the Auto Revert Function (Enabled/Disabled)
				
				
				Note:Disable ccHsbEnabled first to set this OID
				"
			::= { ccHSBConfigure 12 }

		
		-- 1.3.6.1.4.1.388.6.3.31.13
		ccHsbautorevertdelay OBJECT-TYPE
			SYNTAX INTEGER (0..9999)
			MAX-ACCESS read-write
			STATUS current
			DESCRIPTION
				"Number of Minutes to delay after re-connecting before autoreverting
				
				Note:Disable ccHsbEnabled first to set this OID
				"
			::= { ccHSBConfigure 13 }

		
		-- 1.3.6.1.4.1.388.6.3.32
		ccMUInfoTable OBJECT-TYPE
			SYNTAX SEQUENCE OF CcMUInfoEntry
			MAX-ACCESS not-accessible
			STATUS current
			DESCRIPTION
				"A table for MU Information entries."
			::= { symbolCCMgmt 32 }

		
		-- 1.3.6.1.4.1.388.6.3.32.1
		ccMUInfoEntry OBJECT-TYPE
			SYNTAX CcMUInfoEntry
			MAX-ACCESS not-accessible
			STATUS current
			DESCRIPTION
				"An MU information object entry."
			INDEX { ccMUInfoIndex }
			::= { ccMUInfoTable 1 }

		
		CcMUInfoEntry ::=
			SEQUENCE { 
				ccMUInfoIndex
					Integer32,
				ccMUInfoType
					MUDeviceType,
				ccMUInfoMac
					DisplayString,
				ccMUInfoIP
					DisplayString,
				ccMUInfoWlan
					DisplayString,
				ccMUInfoEssid
					DisplayString,
				ccMUInfoAP
					DisplayString,
				ccMUInfoAPState
					APStatus,
				ccMUInfoSecState
					MUSecurityStatus,
				ccMUInfoCurRate
					CurrentRate,
				ccMUInfoSupRates
					DisplayString,
				ccMUInfoRssi
					DisplayString,
				ccMUInfoPsp
					PSPowerMode,
				ccMUInfoIntf
					DisplayString,
				ccMUInfoAsscUptime
					DisplayString,
				ccMUInfoTktExp
					DisplayString,
				ccMUInfoUserName
					DisplayString,
				ccMUInfoPktTx
					DisplayString,
				ccMUInfoPktRx
					DisplayString,
				ccMUInfoBytesTx
					DisplayString,
				ccMUInfoBytesRx
					DisplayString,
				ccMUInfoLastAct
					DisplayString,
				ccMUInfoVlan
					DisplayString,
				ccMUInfoAuthState
					AuthState,
				ccMUInfoAuthMethod
					AuthMethod,
				ccMUInfoEncrMethod
					EncrType,
				ccMUInfoBCMCEncrType
					EncrType,
				ccMUInfoRoamCount
					Integer32
			 }

		-- 1.3.6.1.4.1.388.6.3.32.1.1
		ccMUInfoIndex OBJECT-TYPE
			SYNTAX Integer32 (1..2147483647)
			MAX-ACCESS read-only
			STATUS current
			DESCRIPTION
				"The index of MU Information Table."
			::= { ccMUInfoEntry 1 }
-- ??Mower: added a range 1..2**31 to eliminate an error,
-- but what range is correct?
		
		-- 1.3.6.1.4.1.388.6.3.32.1.2
		ccMUInfoType OBJECT-TYPE
			SYNTAX MUDeviceType
			MAX-ACCESS read-only
			STATUS current
			DESCRIPTION
				"Indicates the device type of this Mobile Unit. 
				0 = Data
				1 = Voice
				2 = Wireless AP."
			::= { ccMUInfoEntry 2 }

		
		-- 1.3.6.1.4.1.388.6.3.32.1.3
		ccMUInfoMac OBJECT-TYPE
			SYNTAX DisplayString (SIZE (1..20))
			MAX-ACCESS read-only
			STATUS current
			DESCRIPTION
				"MAC address for this MU.
				"
			::= { ccMUInfoEntry 3 }

		
		-- 1.3.6.1.4.1.388.6.3.32.1.4
		ccMUInfoIP OBJECT-TYPE
			SYNTAX DisplayString (SIZE (1..20))
			MAX-ACCESS read-only
			STATUS current
			DESCRIPTION
				"IP address for this MU.
				"
			::= { ccMUInfoEntry 4 }

		
		-- 1.3.6.1.4.1.388.6.3.32.1.5
		ccMUInfoWlan OBJECT-TYPE
			SYNTAX DisplayString (SIZE (1..35))
			MAX-ACCESS read-only
			STATUS current
			DESCRIPTION
				"WLAN name that the MU is on currently.
				"
			::= { ccMUInfoEntry 5 }

		
		-- 1.3.6.1.4.1.388.6.3.32.1.6
		ccMUInfoEssid OBJECT-TYPE
			SYNTAX DisplayString (SIZE (1..35))
			MAX-ACCESS read-only
			STATUS current
			DESCRIPTION
				"ESSID currently selected by this MU.
				"
			::= { ccMUInfoEntry 6 }

		
		-- 1.3.6.1.4.1.388.6.3.32.1.7
		ccMUInfoAP OBJECT-TYPE
			SYNTAX DisplayString
			MAX-ACCESS read-only
			STATUS current
			DESCRIPTION
				"Displays the AP name this MU is associated with."
			::= { ccMUInfoEntry 7 }

		
		-- 1.3.6.1.4.1.388.6.3.32.1.8
		ccMUInfoAPState OBJECT-TYPE
			SYNTAX APStatus
			MAX-ACCESS read-only
			STATUS current
			DESCRIPTION
				"Indicates the association status of the AccessPort.
				Association Status:
					0 = Away
					1 = Associated
				"
			::= { ccMUInfoEntry 8 }

		
		-- 1.3.6.1.4.1.388.6.3.32.1.9
		ccMUInfoSecState OBJECT-TYPE
			SYNTAX MUSecurityStatus
			MAX-ACCESS read-only
			STATUS current
			DESCRIPTION
				"The security status for this MU.
				0 = No Encryption
				1 = WEP (per MU Key)
				2 = WEP (Shared Key)
				3 = TKIP (Per MU Key)
				4 = TKIP (Shared Key)
				"
			::= { ccMUInfoEntry 9 }

		
		-- 1.3.6.1.4.1.388.6.3.32.1.10
		ccMUInfoCurRate OBJECT-TYPE
			SYNTAX CurrentRate
			MAX-ACCESS read-only
			STATUS current
			DESCRIPTION
				"Indicates the current communication rate on the MU.
				0 = 1 Mbps
				1 = 2 Mbps
				2 = 5.5 Mbps
				3 = 6 Mbps
				4 = 9 Mbps
				5 = 11 Mbps
				6 = 12 Mbps
				7 = 18 Mbps
				8 = 22 Mbps
				9 = 24 Mbps
				10 = 36 Mbps
				11 = 48 Mbps
				12 = 54 Mbps
				"
			::= { ccMUInfoEntry 10 }

		
		-- 1.3.6.1.4.1.388.6.3.32.1.11
		ccMUInfoSupRates OBJECT-TYPE
			SYNTAX DisplayString (SIZE (1..100))
			MAX-ACCESS read-only
			STATUS current
			DESCRIPTION
				"Indicates the current supported rates.
				This object meaning can be explained as the following:
				1_Mbps(1) --- 1 Mbit supported.
				2_Mbps(2) --- 2 Mbit supported.
				1_2_Mbps(3) --- 1,2 Mbit supported.
				5.5_Mbps(4) --- 5.5 Mbit supported.
				1_5.5_Mbps(5) --- 1, 5.5 Mbit supported.
				2_5.5_Mbps(6) --- 2, 5.5 Mbit supported.
				1_2_5.5_Mbps(7) --- 1,2,5.5 Mbit supported.
				11_Mbps(8) --- 11 Mbit supported.
				1_11_Mbps(9) --- 1,11 Mbit supported.
				2_11_Mbps(10) --- 2,11 Mbit supported.
				1_2_11_Mbps(11) --- 1,2,11 Mbit supported.
				5.5_11_Mbps(12) --- 5.5,11 Mbit supported.
				1_5.5_11_Mbps(13) --- 1,5.5,11 Mbit supported.
				2_5.5_11_Mbps(14) --- 2,5.5,11 Mbit supported.
				1_2_5.5_11_Mbps(15) --- 1,2,5.5,11 Mbit supported.
				"
			::= { ccMUInfoEntry 11 }

		
		-- 1.3.6.1.4.1.388.6.3.32.1.12
		ccMUInfoRssi OBJECT-TYPE
			SYNTAX DisplayString (SIZE (1..10))
			MAX-ACCESS read-only
			STATUS current
			DESCRIPTION
				"Receive signal strength indicator (RSSI) of this MU.
				"
			::= { ccMUInfoEntry 12 }

		
		-- 1.3.6.1.4.1.388.6.3.32.1.13
		ccMUInfoPsp OBJECT-TYPE
			SYNTAX PSPowerMode
			MAX-ACCESS read-only
			STATUS current
			DESCRIPTION
				"Indicates the current power mode setting on this MU.
				In PSP mode the radio receiver is configured to	conserve battery life.
				0 = Continuous Access Mode (CAM) mode
				1 = Power Save Polling Mode(PSP) mode
				"
			::= { ccMUInfoEntry 13 }

		
		-- 1.3.6.1.4.1.388.6.3.32.1.14
		ccMUInfoIntf OBJECT-TYPE
			SYNTAX DisplayString (SIZE (1..35))
			MAX-ACCESS read-only
			STATUS current
			DESCRIPTION
				"The interface type displayed on the associated AP GUI.
				Like: 'RF'.
				"
			::= { ccMUInfoEntry 14 }

		
		-- 1.3.6.1.4.1.388.6.3.32.1.15
		ccMUInfoAsscUptime OBJECT-TYPE
			SYNTAX DisplayString (SIZE (1..35))
			MAX-ACCESS read-only
			STATUS current
			DESCRIPTION
				"The number of seconds since the MU last associated.
				Value is zero if the MU is not associated and was
				aged-out.
				"
			::= { ccMUInfoEntry 15 }

		
		-- 1.3.6.1.4.1.388.6.3.32.1.16
		ccMUInfoTktExp OBJECT-TYPE
			SYNTAX DisplayString (SIZE (1..35))
			MAX-ACCESS read-only
			STATUS current
			DESCRIPTION
				"The number of seconds before the security ticket expiration.
				"
			::= { ccMUInfoEntry 16 }

		
		-- 1.3.6.1.4.1.388.6.3.32.1.17
		ccMUInfoUserName OBJECT-TYPE
			SYNTAX DisplayString (SIZE (1..35))
			MAX-ACCESS read-only
			STATUS current
			DESCRIPTION
				"User name this MU may have for loging processing, if available.
				"
			::= { ccMUInfoEntry 17 }

		
		-- 1.3.6.1.4.1.388.6.3.32.1.18
		ccMUInfoPktTx OBJECT-TYPE
			SYNTAX DisplayString (SIZE (1..35))
			MAX-ACCESS read-only
			STATUS current
			DESCRIPTION
				"This is sum of all good packets sent from different transmit
				speed.
				"
			::= { ccMUInfoEntry 18 }

		
		-- 1.3.6.1.4.1.388.6.3.32.1.19
		ccMUInfoPktRx OBJECT-TYPE
			SYNTAX DisplayString (SIZE (1..35))
			MAX-ACCESS read-only
			STATUS current
			DESCRIPTION
				"This is sum of all good packets received from different transmit speed.
				
				"
			::= { ccMUInfoEntry 19 }

		
		-- 1.3.6.1.4.1.388.6.3.32.1.20
		ccMUInfoBytesTx OBJECT-TYPE
			SYNTAX DisplayString (SIZE (1..35))
			MAX-ACCESS read-only
			STATUS current
			DESCRIPTION
				"Number of bytes sent out.
				"
			::= { ccMUInfoEntry 20 }

		
		-- 1.3.6.1.4.1.388.6.3.32.1.21
		ccMUInfoBytesRx OBJECT-TYPE
			SYNTAX DisplayString (SIZE (1..35))
			MAX-ACCESS read-only
			STATUS current
			DESCRIPTION
				"Number of bytes received.
				"
			::= { ccMUInfoEntry 21 }

		
		-- 1.3.6.1.4.1.388.6.3.32.1.22
		ccMUInfoLastAct OBJECT-TYPE
			SYNTAX DisplayString (SIZE (1..35))
			MAX-ACCESS read-only
			STATUS current
			DESCRIPTION
				"Number of seconds since the last MU activity.
				"
			::= { ccMUInfoEntry 22 }

		
		-- 1.3.6.1.4.1.388.6.3.32.1.23
		ccMUInfoVlan OBJECT-TYPE
			SYNTAX DisplayString (SIZE (1..35))
			MAX-ACCESS read-only
			STATUS current
			DESCRIPTION
				"Value of 0, if not in used. Otherwise it's the VLAN ID.
				"
			::= { ccMUInfoEntry 23 }

		
		-- 1.3.6.1.4.1.388.6.3.32.1.24
		ccMUInfoAuthState OBJECT-TYPE
			SYNTAX AuthState
			MAX-ACCESS read-only
			STATUS current
			DESCRIPTION
				"Informs whether the MU is authenticated or not"
			::= { ccMUInfoEntry 24 }

		
		-- 1.3.6.1.4.1.388.6.3.32.1.25
		ccMUInfoAuthMethod OBJECT-TYPE
			SYNTAX AuthMethod
			MAX-ACCESS read-only
			STATUS current
			DESCRIPTION
				"The authentication method being used by the MU."
			::= { ccMUInfoEntry 25 }

		
		-- 1.3.6.1.4.1.388.6.3.32.1.26
		ccMUInfoEncrMethod OBJECT-TYPE
			SYNTAX EncrType
			MAX-ACCESS read-only
			STATUS current
			DESCRIPTION
				"The Unicast encryption type being used by the MU."
			::= { ccMUInfoEntry 26 }

		
		-- 1.3.6.1.4.1.388.6.3.32.1.27
		ccMUInfoBCMCEncrType OBJECT-TYPE
			SYNTAX EncrType
			MAX-ACCESS read-only
			STATUS current
			DESCRIPTION
				"The BroadCast encryption type being used by the MU."
			::= { ccMUInfoEntry 27 }

		
		-- 1.3.6.1.4.1.388.6.3.32.1.28
		ccMUInfoRoamCount OBJECT-TYPE
			SYNTAX Integer32
			MAX-ACCESS read-only
			STATUS current
			DESCRIPTION
				"Description."
			::= { ccMUInfoEntry 28 }

		
		-- 1.3.6.1.4.1.388.6.3.33
		ccACLObjects OBJECT IDENTIFIER ::= { symbolCCMgmt 33 }

		
		-- 1.3.6.1.4.1.388.6.3.33.2
		ccACLItemsTable OBJECT-TYPE
			SYNTAX SEQUENCE OF CcACLItemsEntry
			MAX-ACCESS not-accessible
			STATUS current
			DESCRIPTION
				"A table for individual entries per ACL"
			::= { ccACLObjects 2 }

		
		-- 1.3.6.1.4.1.388.6.3.33.2.1
		ccACLItemsEntry OBJECT-TYPE
			SYNTAX CcACLItemsEntry
			MAX-ACCESS not-accessible
			STATUS current
			DESCRIPTION
				"An ACL Item object entry.
				The instances in this table are the individual
				ACL entries within each ACL object"
			INDEX { ccACLIndex, ccACLItemIndex }
			::= { ccACLItemsTable 1 }

		
		CcACLItemsEntry ::=
			SEQUENCE { 
				ccACLItemIndex
					INTEGER,
				ccACLItem
					DisplayString
			 }

		-- 1.3.6.1.4.1.388.6.3.33.2.1.1
		ccACLItemIndex OBJECT-TYPE
			SYNTAX INTEGER (1..4096)
			MAX-ACCESS not-accessible
			STATUS current
			DESCRIPTION
				"The index of this specific entry per ACL"
			::= { ccACLItemsEntry 1 }

		
		-- 1.3.6.1.4.1.388.6.3.33.2.1.2
		ccACLItem OBJECT-TYPE
			SYNTAX DisplayString (SIZE (1..200))
			MAX-ACCESS read-only
			STATUS current
			DESCRIPTION
				"The individual ACL entry. The 
				format of the string returned is <MAC Addr,allow/deny>"
			::= { ccACLItemsEntry 2 }

		
		-- 1.3.6.1.4.1.388.6.3.34
		ccWVPNConfigure OBJECT IDENTIFIER ::= { symbolCCMgmt 34 }

		
		-- 1.3.6.1.4.1.388.6.3.34.1
		wvpnGeneralSettings OBJECT IDENTIFIER ::= { ccWVPNConfigure 1 }

		
		-- 1.3.6.1.4.1.388.6.3.34.1.1
		wvpnServerEnable OBJECT-TYPE
			SYNTAX DoActionNow
			MAX-ACCESS read-write
			STATUS current
			DESCRIPTION
				"This is a Boolean variable.  If set to true,
				the WVPN server will be enabled.  This is a 
				WRITE-ONLY value.  To enable the WVPN 
				server, use a MIB instance of 0 and write a 
				dummy value of 1 to write to this variable. 
				Use 'wvpnStatus' to query the current state.
				
				
				Note:If vpnsupport is not enabled then the walk over
				this table will not return anything and the set
				operation over any OID under ccWVPNConfigure will return an error
				message- No creation."
			::= { wvpnGeneralSettings 1 }

		
		-- 1.3.6.1.4.1.388.6.3.34.1.2
		wvpnServerDisable OBJECT-TYPE
			SYNTAX DoActionNow
			MAX-ACCESS read-write
			STATUS current
			DESCRIPTION
				"This is a Boolean variable. If set to true, 
				 	the WVPN server will be disabled.  This is a 
				 	WRITE-ONLY value.  To disable the WVPN 
				 	server, use a MIB instance of 0 and write a 
				 	dummy value of 1 to write to this variable. 
				 	Use 'wvpnStatus' to query the current state.
				"
			::= { wvpnGeneralSettings 2 }

		
		-- 1.3.6.1.4.1.388.6.3.34.1.3
		wvpnServerRestart OBJECT-TYPE
			SYNTAX DoActionNow
			MAX-ACCESS read-write
			STATUS current
			DESCRIPTION
				"This is a Boolean variable. If set to true, 
				 	the WVPN server will be re-started.  Setting 
				 	to true is the only option allowed.  This is 
				 	a WRITE-ONLY value.  To restart the WVPN 
				 	server, use a MIB instance of 0 and write a 
				 	dummy value of 1 to write to this variable. 
				 	Use 'wvpnStatus' to query the current state.
				"
			::= { wvpnGeneralSettings 3 }

		
		-- 1.3.6.1.4.1.388.6.3.34.1.4
		wvpnIpAddress OBJECT-TYPE
			SYNTAX DisplayString (SIZE (1..120))
			MAX-ACCESS read-only
			STATUS current
			DESCRIPTION
				"The IP address of the WVPN server.
				"
			::= { wvpnGeneralSettings 4 }

		
		-- 1.3.6.1.4.1.388.6.3.34.1.5
		wvpnPort OBJECT-TYPE
			SYNTAX INTEGER (1024..65535)
			MAX-ACCESS read-write
			STATUS current
			DESCRIPTION
				"The port number of the WVPN server.
				 	Default value is 9102.
				"
			::= { wvpnGeneralSettings 5 }

		
		-- 1.3.6.1.4.1.388.6.3.34.1.6
		wvpnUnusedTimeout OBJECT-TYPE
			SYNTAX Integer32
			MAX-ACCESS read-write
			STATUS current
			DESCRIPTION
				"The timeout value (seconds) for any idle 
				 	WVPN session."
			::= { wvpnGeneralSettings 6 }

		
		-- 1.3.6.1.4.1.388.6.3.34.1.7
		wvpnStatus OBJECT-TYPE
			SYNTAX DisplayString (SIZE (1..32))
			MAX-ACCESS read-only
			STATUS current
			DESCRIPTION
				"The current status of the WVPN server.
				"
			::= { wvpnGeneralSettings 7 }

		
		-- 1.3.6.1.4.1.388.6.3.34.1.8
		dosEnable OBJECT-TYPE
			SYNTAX TruthValue
			MAX-ACCESS read-write
			STATUS current
			DESCRIPTION
				"This is a Boolean variable to allow use of
				 	tiny reliable UDP.
				"
			::= { wvpnGeneralSettings 8 }

		
		-- 1.3.6.1.4.1.388.6.3.34.1.9
		dosPort OBJECT-TYPE
			SYNTAX INTEGER (1024..65535)
			MAX-ACCESS read-write
			STATUS current
			DESCRIPTION
				"The reliable UDP port number.  Default value 
				 	is 9103.
				"
			::= { wvpnGeneralSettings 9 }

		
		-- 1.3.6.1.4.1.388.6.3.34.1.10
		clientKeepAlive OBJECT-TYPE
			SYNTAX DisplayString (SIZE (1..32))
			UNITS "seconds"
			MAX-ACCESS read-write
			STATUS current
			DESCRIPTION
				"This parameter controls the keep alive 
				 	functionality that sends echo requests each 
				 	period when no data has passed through the 
				 	session.  If the WVPN server does not receive 
				 	any answers on two, subsequently sent, echos, 
				 	the client socket will be torn down.  However, 
				 	the actual session is still there and is 
				 	controlled by the wvpnUnusedTimeout parameter.  
				 	Output is in Hour:Minute:Second format.
				    Valid input values are: 1 to 65535 (in seconds)"
			::= { wvpnGeneralSettings 10 }

		
		-- 1.3.6.1.4.1.388.6.3.34.1.11
		vpnLicenseMax OBJECT-TYPE
			SYNTAX INTEGER (0..100)
			MAX-ACCESS read-only
			STATUS current
			DESCRIPTION
				"The maximum number of VPN sessions allowed
				 	with the current licensing.
				"
			::= { wvpnGeneralSettings 11 }

		
		-- 1.3.6.1.4.1.388.6.3.34.1.12
		vpnLicenseInUse OBJECT-TYPE
			SYNTAX INTEGER (0..100)
			MAX-ACCESS read-only
			STATUS current
			DESCRIPTION
				"The current number of VPN sessions actually
				 	in use.
				"
			::= { wvpnGeneralSettings 12 }

		
		-- 1.3.6.1.4.1.388.6.3.34.2
		wvpnWtlsSettings OBJECT IDENTIFIER ::= { ccWVPNConfigure 2 }

		
		-- 1.3.6.1.4.1.388.6.3.34.2.1
		maxClientRsaKeySize OBJECT-TYPE
			SYNTAX INTEGER (512..15360)
			MAX-ACCESS read-write
			STATUS current
			DESCRIPTION
				"The maximum number of bits that the client 
				 	certificate's public key is allowed to be.  If 
				 	the server receives a client certificate and 
				 	this condition is not true, the client's socket 
				 	will be closed.
				
				Valid values are: 512,768,1024,1536,2048,3072,4096,7680,15360.
				Note that the MAX value cannot be less than the MIN value 
				which is defined by minClientRsaKeySize.
				"
			::= { wvpnWtlsSettings 1 }

		
		-- 1.3.6.1.4.1.388.6.3.34.2.2
		minClientRsaKeySize OBJECT-TYPE
			SYNTAX INTEGER (512..15360)
			MAX-ACCESS read-write
			STATUS current
			DESCRIPTION
				"The minimum number of bits that the client 
				 	certificate's public key is allowed to be.  If 
				 	the server receives a client certificate and 
				 	this condition is not true, the client's socket 
				 	will be closed.
				
				Valid values are: 512,768,1024,1536,2048,3072,4096,7680,15360.
				Note that the MIN value cannot be greater than the MAX value 
				which is defined by maxClientRsaKeySize."
			::= { wvpnWtlsSettings 2 }

		
		-- 1.3.6.1.4.1.388.6.3.34.2.3
		maxRsaKeySize OBJECT-TYPE
			SYNTAX INTEGER (512..15360)
			MAX-ACCESS read-write
			STATUS current
			DESCRIPTION
				"The maximum number of bits that the server 
				 	certificate's key is allowed to be.  If a server 
				 	certificate is used that does not fulfill this 
				 	condition, the server is unusable.
				
				Valid values are: 512,768,1024,1536,2048,3072,4096,7680,15360.
				Note that the MAX value cannot be less than the MIN value 
				which is defined by minRsaKeySize.
				"
			::= { wvpnWtlsSettings 3 }

		
		-- 1.3.6.1.4.1.388.6.3.34.2.4
		minRsaKeySize OBJECT-TYPE
			SYNTAX INTEGER (512..15360)
			MAX-ACCESS read-write
			STATUS current
			DESCRIPTION
				"The minimum number of bits that the server 
				 	certificate's key is allowed to be.  If a server 
				 	certificate is used that does not fulfill this 
				 	condition, the server is unusable.
				
				Valid values are: 512,768,1024,1536,2048,3072,4096,7680,15360.
				Note that the MIN value cannot be greater than the MAX value 
				which is defined by maxRsaKeySize."
			::= { wvpnWtlsSettings 4 }

		
		-- 1.3.6.1.4.1.388.6.3.34.2.5
		cipher OBJECT-TYPE
			SYNTAX DisplayString (SIZE (1..10))
			MAX-ACCESS read-write
			STATUS current
			DESCRIPTION
				"A cipher for encrypting messages sent over the 
				 	VPN channel. 
				 	 Can be one of the following values:
				 	 AES256, AES192, AES128, 3DES, DES56.
				 	 Default value is AES128.
				"
			::= { wvpnWtlsSettings 5 }

		
		-- 1.3.6.1.4.1.388.6.3.34.2.6
		mac OBJECT-TYPE
			SYNTAX DisplayString (SIZE (1..10))
			MAX-ACCESS read-write
			STATUS current
			DESCRIPTION
				"A Message Authentication Code (MAC) algorithm 
				 	for verifying integrity of the messages sent over 
				 	the VPN. 
				 	Can be one of the following values:
				 	MD5_128, MD5_80, MD5_40, SHA_512, SHA_384,
				 	SHA_256, SHA_160, SHA_80, SHA_40, NO_MAC.
				 	Default value is SHA_256.
				"
			::= { wvpnWtlsSettings 6 }

		
		-- 1.3.6.1.4.1.388.6.3.34.2.7
		requireClientCertificate OBJECT-TYPE
			SYNTAX TruthValue
			MAX-ACCESS read-write
			STATUS current
			DESCRIPTION
				"This is a Boolean variable. WVPN server will 
				 	request client to present a certificate if the 
				 	value is set to true.
				"
			::= { wvpnWtlsSettings 7 }

		
		-- 1.3.6.1.4.1.388.6.3.34.2.8
		keyRefresh OBJECT-TYPE
			SYNTAX INTEGER (0..31)
			MAX-ACCESS read-write
			STATUS current
			DESCRIPTION
				"WTLS key refresh rate. The parties will refresh
				 	the session key after each 2^N (2 to the Nth
					power) exchanged packets, where N is the key 
					refresh rate value.
				        If N is 0, the key is refreshed after each packet"
			::= { wvpnWtlsSettings 8 }

		
		-- 1.3.6.1.4.1.388.6.3.34.2.9
		wantedFipsMode OBJECT-TYPE
			SYNTAX DisplayString (SIZE (1..32))
			MAX-ACCESS read-only
			STATUS current
			DESCRIPTION
				"If set to true, only FIPS 140-2 compliant
				cryptographic algorithms are used to establish
				a VPN session."
			::= { wvpnWtlsSettings 9 }

		
		-- 1.3.6.1.4.1.388.6.3.34.2.10
		securityMode OBJECT-TYPE
			SYNTAX DisplayString (SIZE (1..32))
			MAX-ACCESS read-write
			STATUS current
			DESCRIPTION
				"The current securityMode. Value can be  
				 	customSecurity or defaultSecurity. 
				 	Default security mode is defaultSecurity.
				"
			::= { wvpnWtlsSettings 10 }

		
		-- 1.3.6.1.4.1.388.6.3.34.2.11
		serverNumber OBJECT-TYPE
			SYNTAX INTEGER (1..15)
			MAX-ACCESS read-write
			STATUS current
			DESCRIPTION
				"A server number must be between 1 and 15.  
				 	This number is only relevant if there is a 
				 	cluster of servers.
				"
			::= { wvpnWtlsSettings 11 }

		
		-- 1.3.6.1.4.1.388.6.3.34.2.12
		handshakeTimeout OBJECT-TYPE
			SYNTAX DisplayString (SIZE (1..32))
			UNITS "seconds"
			MAX-ACCESS read-write
			STATUS current
			DESCRIPTION
				" The number of seconds that the WVPN server 
				  allows a client to perform the whole WTLS 
				  handshake.  If it times out, the client socket 
				  will be closed.  Default value is 90 seconds.
				  The valid range of Hand shake timeout  is 1 to
				  10000 (in seconds).
				"
			::= { wvpnWtlsSettings 12 }

		
		-- 1.3.6.1.4.1.388.6.3.34.2.13
		allowSessionResume OBJECT-TYPE
			SYNTAX TruthValue
			MAX-ACCESS read-write
			STATUS current
			DESCRIPTION
				"This is a Boolean variable.  If set to true,
				 	the WVPN server allows a client to do a session 
				 	resume (i.e., a secure abbreviated handshake).  
				 	If set to false, then only full handshakes are 
				 	allowed.
				"
			::= { wvpnWtlsSettings 13 }

		
		-- 1.3.6.1.4.1.388.6.3.34.3
		wvpnAuthServerSettings OBJECT IDENTIFIER ::= { ccWVPNConfigure 3 }

		
		-- 1.3.6.1.4.1.388.6.3.34.3.1
		useSimpleAuthentication OBJECT-TYPE
			SYNTAX TruthValue
			MAX-ACCESS read-write
			STATUS current
			DESCRIPTION
				"Specify whether Simple Authentication is used 
				 	or not.  Value could be true(1) or false(2).
				"
			::= { wvpnAuthServerSettings 1 }

		
		-- 1.3.6.1.4.1.388.6.3.34.3.2
		useRadiusAuthentication OBJECT-TYPE
			SYNTAX TruthValue
			MAX-ACCESS read-write
			STATUS current
			DESCRIPTION
				"This is a Boolean variable.  If set to true,
				 	RADIUS Authentication will be enabled.
				"
			::= { wvpnAuthServerSettings 2 }

		
		-- 1.3.6.1.4.1.388.6.3.34.3.3
		useLdapAuthentication OBJECT-TYPE
			SYNTAX TruthValue
			MAX-ACCESS read-only
			STATUS current
			DESCRIPTION
				"This is a Boolean variable.  If set to true, 
				 	LDAP Authentication will be enabled.  This
				 	feature is not implemented.
				"
			::= { wvpnAuthServerSettings 3 }

		
		-- 1.3.6.1.4.1.388.6.3.34.3.4
		useLocalDatabaseAuthentication OBJECT-TYPE
			SYNTAX TruthValue
			MAX-ACCESS read-only
			STATUS current
			DESCRIPTION
				"This is a Boolean variable.  If set to true, 
				 	Local Database Authentication will be enabled.
				 	This feature is not implemented.
				"
			::= { wvpnAuthServerSettings 4 }

		
		-- 1.3.6.1.4.1.388.6.3.34.3.5
		simpleAuthentication OBJECT IDENTIFIER ::= { wvpnAuthServerSettings 5 }

		
		-- 1.3.6.1.4.1.388.6.3.34.3.5.1
		simpleAuthUserName OBJECT-TYPE
			SYNTAX DisplayString (SIZE (1..120))
			MAX-ACCESS read-write
			STATUS current
			DESCRIPTION
				"The Simple Authentication user name.
				"
			::= { simpleAuthentication 1 }

		
		-- 1.3.6.1.4.1.388.6.3.34.3.5.2
		simpleAuthPassword OBJECT-TYPE
			SYNTAX DisplayString (SIZE (1..120))
			MAX-ACCESS read-write
			STATUS current
			DESCRIPTION
				"The Simple Authentication user password.
				"
			::= { simpleAuthentication 2 }

		
		-- 1.3.6.1.4.1.388.6.3.34.3.5.3
		simpleAuthDomain OBJECT-TYPE
			SYNTAX DisplayString (SIZE (1..120))
			MAX-ACCESS read-write
			STATUS current
			DESCRIPTION
				"The Simple Authentication domain.
				"
			::= { simpleAuthentication 3 }

		
		-- 1.3.6.1.4.1.388.6.3.34.3.6
		wvpnRadiusAuthentication OBJECT IDENTIFIER ::= { wvpnAuthServerSettings 6 }

		
		-- 1.3.6.1.4.1.388.6.3.34.3.6.1
		radiusAuthPrimaryServer OBJECT IDENTIFIER ::= { wvpnRadiusAuthentication 1 }

		
		-- 1.3.6.1.4.1.388.6.3.34.3.6.1.1
		radiusAuthPrimaryHost OBJECT-TYPE
			SYNTAX DisplayString (SIZE (1..120))
			MAX-ACCESS read-write
			STATUS current
			DESCRIPTION
				"The host name or IP address of the primary RADIUS server.
				"
			::= { radiusAuthPrimaryServer 1 }

		
		-- 1.3.6.1.4.1.388.6.3.34.3.6.1.2
		radiusAuthPrimaryPort OBJECT-TYPE
			SYNTAX Integer32 (0..65535)
			MAX-ACCESS read-write
			STATUS current
			DESCRIPTION
				"The UDP port the client is using to send requests to the
				 	primary RADIUS server.
				"
			::= { radiusAuthPrimaryServer 2 }

		
		-- 1.3.6.1.4.1.388.6.3.34.3.6.1.3
		radiusAuthPrimaryMaxRetries OBJECT-TYPE
			SYNTAX Integer32 (1..10)
			MAX-ACCESS read-write
			STATUS current
			DESCRIPTION
				"The maximum number of times a client is allowed to try 
				authenticating with the primary RADIUS server.
				Valid input values are from 1 to 10.
				"
			::= { radiusAuthPrimaryServer 3 }

		
		-- 1.3.6.1.4.1.388.6.3.34.3.6.1.4
		radiusAuthPrimaryTimeOut OBJECT-TYPE
			SYNTAX Integer32 (5..20)
			MAX-ACCESS read-write
			STATUS current
			DESCRIPTION
				"The number of seconds in between retries to the
				primary RADIUS server.
				Valid input values are from 5 to 20.
				"
			::= { radiusAuthPrimaryServer 4 }

		
		-- 1.3.6.1.4.1.388.6.3.34.3.6.1.5
		radiusAuthPrimaryUserPassword OBJECT-TYPE
			SYNTAX DisplayString (SIZE (1..120))
			MAX-ACCESS read-write
			STATUS current
			DESCRIPTION
				"Some RADIUS servers require a user password 
				 	to be set even though no password is required.
				 	If set, the WVPN server will send this password
				 	to the RADIUS server.
				"
			::= { radiusAuthPrimaryServer 5 }

		
		-- 1.3.6.1.4.1.388.6.3.34.3.6.1.6
		radiusAuthPrimarySecret OBJECT-TYPE
			SYNTAX DisplayString (SIZE (1..120))
			MAX-ACCESS read-write
			STATUS current
			DESCRIPTION
				"The value used to encrypt RADIUS traffic to and 
				 	from the RADIUS server.  A secret shared between
				 	the RADIUS server and the WVPN server.
				"
			::= { radiusAuthPrimaryServer 6 }

		
		-- 1.3.6.1.4.1.388.6.3.34.3.6.2
		radiusAuthSecondaryServer OBJECT IDENTIFIER ::= { wvpnRadiusAuthentication 2 }

		
		-- 1.3.6.1.4.1.388.6.3.34.3.6.2.1
		radiusAuthSecondaryHost OBJECT-TYPE
			SYNTAX DisplayString (SIZE (1..200))
			MAX-ACCESS read-write
			STATUS current
			DESCRIPTION
				"The host name or IP address of the secondary RADIUS server.
				"
			::= { radiusAuthSecondaryServer 1 }

		
		-- 1.3.6.1.4.1.388.6.3.34.3.6.2.2
		radiusAuthSecondaryPort OBJECT-TYPE
			SYNTAX Integer32 (0..65535)
			MAX-ACCESS read-write
			STATUS current
			DESCRIPTION
				"The UDP port the client is using to send requests to the
				 	secondary RADIUS server.
				"
			::= { radiusAuthSecondaryServer 2 }

		
		-- 1.3.6.1.4.1.388.6.3.34.3.6.2.3
		radiusAuthSecondaryMaxRetries OBJECT-TYPE
			SYNTAX Integer32 (1..10)
			MAX-ACCESS read-write
			STATUS current
			DESCRIPTION
				"The maximum number of times a client is allowed to try 
				authenticating with the secondary RADIUS server.
				Valid input values are from 1 to 10.
				"
			::= { radiusAuthSecondaryServer 3 }

		
		-- 1.3.6.1.4.1.388.6.3.34.3.6.2.4
		radiusAuthSecondaryTimeOut OBJECT-TYPE
			SYNTAX Integer32 (5..20)
			MAX-ACCESS read-write
			STATUS current
			DESCRIPTION
				"The number of seconds in between retries to the
				secondary RADIUS server.
				Valid input values are from 5 to 20
				"
			::= { radiusAuthSecondaryServer 4 }

		
		-- 1.3.6.1.4.1.388.6.3.34.3.6.2.5
		radiusAuthSecondaryUserPassword OBJECT-TYPE
			SYNTAX DisplayString (SIZE (1..120))
			MAX-ACCESS read-write
			STATUS current
			DESCRIPTION
				"Some RADIUS servers require a user password 
				 	to be set even though no password is required.
				 	If set, the WVPN server will send this password
				 	to the RADIUS server.
				"
			::= { radiusAuthSecondaryServer 5 }

		
		-- 1.3.6.1.4.1.388.6.3.34.3.6.2.6
		radiusAuthSecondarySecret OBJECT-TYPE
			SYNTAX DisplayString (SIZE (1..120))
			MAX-ACCESS read-write
			STATUS current
			DESCRIPTION
				"The value used to encrypt RADIUS traffic to and 
				 	from the RADIUS server.  A secret shared between
				 	the RADIUS server and the WVPN server.
				"
			::= { radiusAuthSecondaryServer 6 }

		
		-- 1.3.6.1.4.1.388.6.3.34.4
		wvpnIpPoolsSettings OBJECT IDENTIFIER ::= { ccWVPNConfigure 4 }

		
		-- 1.3.6.1.4.1.388.6.3.34.4.1
		wvpnAddIpPoolObj OBJECT-TYPE
			SYNTAX DisplayString (SIZE (1..100))
			MAX-ACCESS read-write
			STATUS current
			DESCRIPTION
				"Add an IP Pool object to the wvpnIpPoolsTable.
				 	Input string format: <pool_name,begin_ip,end_ip>.
				 	Max length of pool_name is 32 bytes, and begin_ip
				 	and end_ip are IP Addresses. 
				 	Characters not allowed in the pool_name:
				 	` @ # $ & ( ) | = \ ; double-quote ' < > / sp
				 	This is a WRITE-ONLY value.
				"
			::= { wvpnIpPoolsSettings 1 }

		
		-- 1.3.6.1.4.1.388.6.3.34.4.2
		wvpnRemIpPoolObj OBJECT-TYPE
			SYNTAX DisplayString (SIZE (1..32))
			MAX-ACCESS read-write
			STATUS current
			DESCRIPTION
				"Remove an IP Pool object from wvpnIpPoolsTable.
				 	Input string format: <pool_name>.
				 	Max length of pool_name is 32 bytes.
				 	Characters not allowed in the IPpool_name:
				 	` @ # $ & ( ) | = \ ; double-quote ' < > / sp
				 	This is a WRITE-ONLY value.
				"
			::= { wvpnIpPoolsSettings 2 }

		
		-- 1.3.6.1.4.1.388.6.3.34.4.3
		wvpnAddIpPoolRange OBJECT-TYPE
			SYNTAX DisplayString (SIZE (1..100))
			MAX-ACCESS read-write
			STATUS current
			DESCRIPTION
				"Add an IP address range to an IP Pool object 
				 	in the wvpnIpPoolsTable.
				 	Input string format: <pool_name,begin_ip,end_ip>.
				 	Max length of pool_name is 32 bytes, and begin_ip
				 	and end_ip are IP Addresses. 
				 	Characters not allowed in the IPpool_name: 
				 	` @ # $ & ( ) | = \ ; double-quote ' < > / sp
				 	This is a WRITE-ONLY value.
				"
			::= { wvpnIpPoolsSettings 3 }

		
		-- 1.3.6.1.4.1.388.6.3.34.4.4
		wvpnRemIpPoolRange OBJECT-TYPE
			SYNTAX DisplayString (SIZE (1..32))
			MAX-ACCESS read-write
			STATUS current
			DESCRIPTION
				"Remove an IP address range from an IP Pool object 
				 	in the wvpnIpPoolsTable.
				 	Input string format: <pool_name,begin_ip,end_ip>.
				 	Max length of pool_name is 32 bytes, and begin_ip
				 	and end_ip are IP Addresses.  
				 	Characters not allowed in the IPpool_name: 
				 	` @ # $ & ( ) | = \ ; double-quote ' < > / sp
				 	This is a WRITE-ONLY value.
				"
			::= { wvpnIpPoolsSettings 4 }

		
		-- 1.3.6.1.4.1.388.6.3.34.4.5
		useDhcpGateway OBJECT-TYPE
			SYNTAX TruthValue
			MAX-ACCESS read-write
			STATUS current
			DESCRIPTION
				"This is a Boolean variable.  If set to true, 
				DHCP is enabled.
				"
			::= { wvpnIpPoolsSettings 5 }

		
		-- 1.3.6.1.4.1.388.6.3.34.4.6
		wvpnIpPoolsTable OBJECT-TYPE
			SYNTAX SEQUENCE OF WvpnIpPoolsEntry
			MAX-ACCESS not-accessible
			STATUS current
			DESCRIPTION
				"The IP Pools Table"
			::= { wvpnIpPoolsSettings 6 }

		
		-- 1.3.6.1.4.1.388.6.3.34.4.6.1
		wvpnIpPoolsEntry OBJECT-TYPE
			SYNTAX WvpnIpPoolsEntry
			MAX-ACCESS not-accessible
			STATUS current
			DESCRIPTION
				"An IP Pool object."
			INDEX { wvpnIpPoolIndex }
			::= { wvpnIpPoolsTable 1 }

		
		WvpnIpPoolsEntry ::=
			SEQUENCE { 
				wvpnIpPoolIndex
					Integer32,
				clientIpPoolName
					DisplayString,
				clientNetMask
					IpAddress,
				clientDhcpServerAddress
					IpAddress,
				clientDefaultGatewayAddress
					IpAddress,
				clientDnsAddress
					IpAddress,
				clientWinsAddress
					IpAddress,
				clientDomainName
					DisplayString,
				clientNetBiosNodeType
					DisplayString,
				clientDhcpLeaseTime
					DisplayString,
				reuseAddrTime
					Integer32,
				ipRangeCount
					Integer32,
				clientIpRanges
					DisplayString
			 }

		-- 1.3.6.1.4.1.388.6.3.34.4.6.1.1
		wvpnIpPoolIndex OBJECT-TYPE
			SYNTAX Integer32 (1..100)
			MAX-ACCESS read-only
			STATUS current
			DESCRIPTION
				"An integer index for the wvpnIpPoolsTable to 
				 	access an IP Pool object.
				"
			::= { wvpnIpPoolsEntry 1 }

		
		-- 1.3.6.1.4.1.388.6.3.34.4.6.1.2
		clientIpPoolName OBJECT-TYPE
			SYNTAX DisplayString (SIZE (1..32))
			MAX-ACCESS read-write
			STATUS current
			DESCRIPTION
				"This is the client's IP Pool name.  
				 	Max length of pool name is 32 bytes.
				 	Characters not allowed in the pool name: 
				 	` @ # $ & ( ) | = \ ; double-quote ' < > / sp
				"
			::= { wvpnIpPoolsEntry 2 }

		
		-- 1.3.6.1.4.1.388.6.3.34.4.6.1.3
		clientNetMask OBJECT-TYPE
			SYNTAX IpAddress
			MAX-ACCESS read-write
			STATUS current
			DESCRIPTION
				"clientNetMask"
			::= { wvpnIpPoolsEntry 3 }

		
		-- 1.3.6.1.4.1.388.6.3.34.4.6.1.4
		clientDhcpServerAddress OBJECT-TYPE
			SYNTAX IpAddress
			MAX-ACCESS read-write
			STATUS current
			DESCRIPTION
				"This is the client's DHCP server IP address.
				"
			::= { wvpnIpPoolsEntry 4 }

		
		-- 1.3.6.1.4.1.388.6.3.34.4.6.1.5
		clientDefaultGatewayAddress OBJECT-TYPE
			SYNTAX IpAddress
			MAX-ACCESS read-write
			STATUS current
			DESCRIPTION
				"This is the client's default gateway address.
				"
			::= { wvpnIpPoolsEntry 5 }

		
		-- 1.3.6.1.4.1.388.6.3.34.4.6.1.6
		clientDnsAddress OBJECT-TYPE
			SYNTAX IpAddress
			MAX-ACCESS read-write
			STATUS current
			DESCRIPTION
				"This is the client's DNS server IP address.
				"
			::= { wvpnIpPoolsEntry 6 }

		
		-- 1.3.6.1.4.1.388.6.3.34.4.6.1.7
		clientWinsAddress OBJECT-TYPE
			SYNTAX IpAddress
			MAX-ACCESS read-write
			STATUS current
			DESCRIPTION
				"This is the client's WINS address.
				"
			::= { wvpnIpPoolsEntry 7 }

		
		-- 1.3.6.1.4.1.388.6.3.34.4.6.1.8
		clientDomainName OBJECT-TYPE
			SYNTAX DisplayString (SIZE (1..120))
			MAX-ACCESS read-write
			STATUS current
			DESCRIPTION
				"This is the client's domain name.
				"
			::= { wvpnIpPoolsEntry 8 }

		
		-- 1.3.6.1.4.1.388.6.3.34.4.6.1.9
		clientNetBiosNodeType OBJECT-TYPE
			SYNTAX DisplayString (SIZE (1..32))
			MAX-ACCESS read-write
			STATUS current
			DESCRIPTION
				"This is the client's Net Bios Node type.
				"
			::= { wvpnIpPoolsEntry 9 }

		
		-- 1.3.6.1.4.1.388.6.3.34.4.6.1.10
		clientDhcpLeaseTime OBJECT-TYPE
			SYNTAX DisplayString (SIZE (1..32))
			MAX-ACCESS read-only
			STATUS current
			DESCRIPTION
				"This is currently not supported in this version."
			::= { wvpnIpPoolsEntry 10 }

		
		-- 1.3.6.1.4.1.388.6.3.34.4.6.1.11
		reuseAddrTime OBJECT-TYPE
			SYNTAX Integer32 (0..2147483647)
			UNITS "seconds"
			MAX-ACCESS read-write
			STATUS current
			DESCRIPTION
				"When client's IP returns to DHCP IP pool, this 
				 	is the amount of time required before IP can be 
					reused.  Input required in seconds.  Output also is 
					in seconds."
			::= { wvpnIpPoolsEntry 11 }

		
		-- 1.3.6.1.4.1.388.6.3.34.4.6.1.12
		ipRangeCount OBJECT-TYPE
			SYNTAX Integer32
			MAX-ACCESS read-only
			STATUS current
			DESCRIPTION
				"The total number of IP address ranges that 
				 	exist for a particular IP pool object.
				"
			::= { wvpnIpPoolsEntry 12 }

		
		-- 1.3.6.1.4.1.388.6.3.34.4.6.1.13
		clientIpRanges OBJECT-TYPE
			SYNTAX DisplayString (SIZE (1..150))
			MAX-ACCESS read-only
			STATUS current
			DESCRIPTION
				"List of client's IP address ranges. Ranges are 
				 	separated by a comma, and the start and end of 
				 	each range is separated by a hyphen.
				"
			::= { wvpnIpPoolsEntry 13 }

		
		-- 1.3.6.1.4.1.388.6.3.34.4.7
		wvpnIpPoolsCount OBJECT-TYPE
			SYNTAX Integer32
			MAX-ACCESS read-only
			STATUS current
			DESCRIPTION
				"Total size of the IP Pool object list.
				"
			::= { wvpnIpPoolsSettings 7 }

		
		-- 1.3.6.1.4.1.388.6.3.34.4.8
		wvpnIpPoolsNames OBJECT-TYPE
			SYNTAX DisplayString (SIZE (1..200))
			MAX-ACCESS read-only
			STATUS current
			DESCRIPTION
				"Comma-separated list of client IP Pool names. 
				"
			::= { wvpnIpPoolsSettings 8 }

		
		-- 1.3.6.1.4.1.388.6.3.34.5
		wvpnCertificateSettings OBJECT IDENTIFIER ::= { ccWVPNConfigure 5 }

		
		-- 1.3.6.1.4.1.388.6.3.34.5.1
		wvpnServerCertificateTable OBJECT-TYPE
			SYNTAX SEQUENCE OF WvpnServerCertificateEntry
			MAX-ACCESS not-accessible
			STATUS current
			DESCRIPTION
				"Description."
			::= { wvpnCertificateSettings 1 }

		
		-- 1.3.6.1.4.1.388.6.3.34.5.1.1
		wvpnServerCertificateEntry OBJECT-TYPE
			SYNTAX WvpnServerCertificateEntry
			MAX-ACCESS not-accessible
			STATUS current
			DESCRIPTION
				"Description."
			INDEX { wvpnCertIndex }
			::= { wvpnServerCertificateTable 1 }

		
		WvpnServerCertificateEntry ::=
			SEQUENCE { 
				wvpnCertIndex
					Integer32,
				userName
					DisplayString,
				serialNumber
					DisplayString,
				subject
					DisplayString,
				version
					INTEGER,
				issuer
					DisplayString,
				keyLength
					INTEGER,
				validFrom
					DisplayString,
				validTo
					DisplayString,
				certificate
					DisplayString,
				binary
					DisplayString,
				fingerPrint
					DisplayString,
				authFingerPrint
					DisplayString
			 }

		-- 1.3.6.1.4.1.388.6.3.34.5.1.1.1
		wvpnCertIndex OBJECT-TYPE
			SYNTAX Integer32 (1..100)
			MAX-ACCESS read-only
			STATUS current
			DESCRIPTION
				"An integer index for wvpnServerCertificateTable 
				 	to access a certificate.
				"
			::= { wvpnServerCertificateEntry 1 }

		
		-- 1.3.6.1.4.1.388.6.3.34.5.1.1.2
		userName OBJECT-TYPE
			SYNTAX DisplayString (SIZE (1..32))
			MAX-ACCESS read-only
			STATUS current
			DESCRIPTION
				"The name that identifies the certificate.
				"
			::= { wvpnServerCertificateEntry 2 }

		
		-- 1.3.6.1.4.1.388.6.3.34.5.1.1.3
		serialNumber OBJECT-TYPE
			SYNTAX DisplayString (SIZE (1..32))
			MAX-ACCESS read-write
			STATUS current
			DESCRIPTION
				"The serial number of the certificate.
				"
			::= { wvpnServerCertificateEntry 3 }

		
		-- 1.3.6.1.4.1.388.6.3.34.5.1.1.4
		subject OBJECT-TYPE
			SYNTAX DisplayString (SIZE (1..32))
			MAX-ACCESS read-only
			STATUS current
			DESCRIPTION
				"The subject of the certificate.
				"
			::= { wvpnServerCertificateEntry 4 }

		
		-- 1.3.6.1.4.1.388.6.3.34.5.1.1.5
		version OBJECT-TYPE
			SYNTAX INTEGER (1..100)
			MAX-ACCESS read-write
			STATUS current
			DESCRIPTION
				"The version of the certificate format.
				"
			::= { wvpnServerCertificateEntry 5 }

		
		-- 1.3.6.1.4.1.388.6.3.34.5.1.1.6
		issuer OBJECT-TYPE
			SYNTAX DisplayString (SIZE (1..32))
			MAX-ACCESS read-only
			STATUS current
			DESCRIPTION
				"The issuer of the certificate.
				"
			::= { wvpnServerCertificateEntry 6 }

		
		-- 1.3.6.1.4.1.388.6.3.34.5.1.1.7
		keyLength OBJECT-TYPE
			SYNTAX INTEGER (512..4096)
			MAX-ACCESS read-only
			STATUS current
			DESCRIPTION
				"The key length of the certificate.
				"
			::= { wvpnServerCertificateEntry 7 }

		
		-- 1.3.6.1.4.1.388.6.3.34.5.1.1.8
		validFrom OBJECT-TYPE
			SYNTAX DisplayString (SIZE (1..32))
			MAX-ACCESS read-only
			STATUS current
			DESCRIPTION
				"The start validity date of the certificate.
				"
			::= { wvpnServerCertificateEntry 8 }

		
		-- 1.3.6.1.4.1.388.6.3.34.5.1.1.9
		validTo OBJECT-TYPE
			SYNTAX DisplayString (SIZE (1..32))
			MAX-ACCESS read-only
			STATUS current
			DESCRIPTION
				"The expiry date of the certificate.
				"
			::= { wvpnServerCertificateEntry 9 }

		
		-- 1.3.6.1.4.1.388.6.3.34.5.1.1.10
		certificate OBJECT-TYPE
			SYNTAX DisplayString (SIZE (1..120))
			MAX-ACCESS read-only
			STATUS current
			DESCRIPTION
				"Server certificate.
				"
			::= { wvpnServerCertificateEntry 10 }

		
		-- 1.3.6.1.4.1.388.6.3.34.5.1.1.11
		binary OBJECT-TYPE
			SYNTAX DisplayString (SIZE (1..150))
			MAX-ACCESS read-only
			STATUS current
			DESCRIPTION
				"The certificate in hex binary notation.
				"
			::= { wvpnServerCertificateEntry 11 }

		
		-- 1.3.6.1.4.1.388.6.3.34.5.1.1.12
		fingerPrint OBJECT-TYPE
			SYNTAX DisplayString (SIZE (1..150))
			MAX-ACCESS read-only
			STATUS current
			DESCRIPTION
				"A hash over the entire certificate that is
				 	statistically unique.  The hash algorithm is 
				 	SHA-1, and the binary hash is converted to hex 
				 	encoded representation.
				"
			::= { wvpnServerCertificateEntry 12 }

		
		-- 1.3.6.1.4.1.388.6.3.34.5.1.1.13
		authFingerPrint OBJECT-TYPE
			SYNTAX DisplayString (SIZE (1..150))
			MAX-ACCESS read-only
			STATUS current
			DESCRIPTION
				"This is not supported in the current version.
				"
			::= { wvpnServerCertificateEntry 13 }

		
		-- 1.3.6.1.4.1.388.6.3.34.5.2
		serverCertCount OBJECT-TYPE
			SYNTAX INTEGER (0..1)
			MAX-ACCESS read-only
			STATUS current
			DESCRIPTION
				"The total number of end users in the 
				 	wvpnServerCertificateTable.
				 	The value is either 0 or 1.
				"
			::= { wvpnCertificateSettings 2 }

		
		-- 1.3.6.1.4.1.388.6.3.34.5.3
		serverCertUserNames OBJECT-TYPE
			SYNTAX DisplayString (SIZE (1..32))
			MAX-ACCESS read-only
			STATUS current
			DESCRIPTION
				"A list of certificate user names.
				"
			::= { wvpnCertificateSettings 3 }

		
		-- 1.3.6.1.4.1.388.6.3.34.5.4
		wvpnCaCertificateTable OBJECT-TYPE
			SYNTAX SEQUENCE OF WvpnCaCertificateEntry
			MAX-ACCESS not-accessible
			STATUS current
			DESCRIPTION
				"A table of WVPN CA certificates.
				"
			::= { wvpnCertificateSettings 4 }

		
		-- 1.3.6.1.4.1.388.6.3.34.5.4.1
		wvpnCaCertificateEntry OBJECT-TYPE
			SYNTAX WvpnCaCertificateEntry
			MAX-ACCESS not-accessible
			STATUS current
			DESCRIPTION
				"Description."
			INDEX { wvpnCaCertIndex }
			::= { wvpnCaCertificateTable 1 }

		
		WvpnCaCertificateEntry ::=
			SEQUENCE { 
				wvpnCaCertIndex
					INTEGER,
				wvpnCaSerialNumber
					DisplayString,
				wvpnCaSubject
					DisplayString,
				wvpnCaVersion
					INTEGER,
				wvpnCaIssuer
					DisplayString,
				wvpnCaKeyLength
					DisplayString,
				wvpnCaValidFrom
					DisplayString,
				wvpnCaValidTo
					DisplayString,
				wvpnCaBinary
					DisplayString,
				wvpnCaFingerPrint
					DisplayString,
				wvpnCaAuthFingerPrint
					DisplayString
			 }

		-- 1.3.6.1.4.1.388.6.3.34.5.4.1.1
		wvpnCaCertIndex OBJECT-TYPE
			SYNTAX INTEGER (1..100)
			MAX-ACCESS read-write
			STATUS current
			DESCRIPTION
				"An integer index for wvpnCaCertificateTable 
				 	to access a CA certificate.
				"
			::= { wvpnCaCertificateEntry 1 }

		
		-- 1.3.6.1.4.1.388.6.3.34.5.4.1.2
		wvpnCaSerialNumber OBJECT-TYPE
			SYNTAX DisplayString (SIZE (1..32))
			MAX-ACCESS read-only
			STATUS current
			DESCRIPTION
				"The serial number of the CA certificate.
				"
			::= { wvpnCaCertificateEntry 2 }

		
		-- 1.3.6.1.4.1.388.6.3.34.5.4.1.3
		wvpnCaSubject OBJECT-TYPE
			SYNTAX DisplayString (SIZE (1..32))
			MAX-ACCESS read-only
			STATUS current
			DESCRIPTION
				"The subject of the CA certificate.
				"
			::= { wvpnCaCertificateEntry 3 }

		
		-- 1.3.6.1.4.1.388.6.3.34.5.4.1.4
		wvpnCaVersion OBJECT-TYPE
			SYNTAX INTEGER (1..100)
			MAX-ACCESS read-only
			STATUS current
			DESCRIPTION
				"The version of the CA certificate format.
				"
			::= { wvpnCaCertificateEntry 4 }

		
		-- 1.3.6.1.4.1.388.6.3.34.5.4.1.5
		wvpnCaIssuer OBJECT-TYPE
			SYNTAX DisplayString (SIZE (1..32))
			MAX-ACCESS read-only
			STATUS current
			DESCRIPTION
				"The issuer of the CA certificate.
				"
			::= { wvpnCaCertificateEntry 5 }

		
		-- 1.3.6.1.4.1.388.6.3.34.5.4.1.6
		wvpnCaKeyLength OBJECT-TYPE
			SYNTAX DisplayString (SIZE (1..32))
			MAX-ACCESS read-only
			STATUS current
			DESCRIPTION
				"The key length of the CA certificate.
				"
			::= { wvpnCaCertificateEntry 6 }

		
		-- 1.3.6.1.4.1.388.6.3.34.5.4.1.7
		wvpnCaValidFrom OBJECT-TYPE
			SYNTAX DisplayString (SIZE (1..32))
			MAX-ACCESS read-only
			STATUS current
			DESCRIPTION
				"The start validity date of the CA certificate.
				"
			::= { wvpnCaCertificateEntry 7 }

		
		-- 1.3.6.1.4.1.388.6.3.34.5.4.1.8
		wvpnCaValidTo OBJECT-TYPE
			SYNTAX DisplayString (SIZE (1..32))
			MAX-ACCESS read-only
			STATUS current
			DESCRIPTION
				"The expiry date of the CA certificate.
				"
			::= { wvpnCaCertificateEntry 8 }

		
		-- 1.3.6.1.4.1.388.6.3.34.5.4.1.9
		wvpnCaBinary OBJECT-TYPE
			SYNTAX DisplayString (SIZE (1..150))
			MAX-ACCESS read-only
			STATUS current
			DESCRIPTION
				"The CA certificate in Hex binary notation.
				"
			::= { wvpnCaCertificateEntry 9 }

		
		-- 1.3.6.1.4.1.388.6.3.34.5.4.1.10
		wvpnCaFingerPrint OBJECT-TYPE
			SYNTAX DisplayString (SIZE (1..150))
			MAX-ACCESS read-only
			STATUS current
			DESCRIPTION
				"A hash over the entire certificate that is
				 	statistically unique.  The hash algorithm is 
				 	SHA-1, and the binary hash is converted to hex 
				 	encoded representation.
				"
			::= { wvpnCaCertificateEntry 10 }

		
		-- 1.3.6.1.4.1.388.6.3.34.5.4.1.11
		wvpnCaAuthFingerPrint OBJECT-TYPE
			SYNTAX DisplayString (SIZE (1..150))
			MAX-ACCESS read-only
			STATUS current
			DESCRIPTION
				"This is not supported in the current version.
				"
			::= { wvpnCaCertificateEntry 11 }

		
		-- 1.3.6.1.4.1.388.6.3.34.5.5
		caCertCount OBJECT-TYPE
			SYNTAX INTEGER (0..1000)
			MAX-ACCESS read-only
			STATUS current
			DESCRIPTION
				"The total number of certificate serial numbers 
				 	in the wvpnCaCertificateTable.
				"
			::= { wvpnCertificateSettings 5 }

		
		-- 1.3.6.1.4.1.388.6.3.34.5.6
		certSerialNumbers OBJECT-TYPE
			SYNTAX DisplayString (SIZE (1..150))
			MAX-ACCESS read-only
			STATUS current
			DESCRIPTION
				"A list of certificate serial numbers.  
				 	Serial numbers are comma delimited.
				"
			::= { wvpnCertificateSettings 6 }

		
		-- 1.3.6.1.4.1.388.6.3.34.5.7
		importServerCert OBJECT-TYPE
			SYNTAX DisplayString (SIZE (1..150))
			MAX-ACCESS read-write
			STATUS current
			DESCRIPTION
				"Import a server certificate that is already
				 	residing on the local machine. 
				 	Input String format:
				 	<serverCertFile,password,certFileName>
				 	serverCertFile must be an absolute path to 
				 	the file.  Furthermore, the certificate file must be 
				 	specified if the serverCertFile does not have 
				 	an embedded certificate.  certFileName is 
				 	optional, but if specified, it must be an absolute 
				 	path to the file.
				 	Characters not allowed in both serverCertFile 
				 	and certFileName:
				 	` @ # $ & | = ; double-quote ' < > / sp
				 	This is a WRITE-ONLY value.
				"
			::= { wvpnCertificateSettings 7 }

		
		-- 1.3.6.1.4.1.388.6.3.34.5.8
		removeServerCert OBJECT-TYPE
			SYNTAX DisplayString (SIZE (1..120))
			MAX-ACCESS read-write
			STATUS current
			DESCRIPTION
				"Remove a server certificate from the 
				 	wvpnServerCertificateTable.
				 	Input string format: <UserName>
				 	Characters not allowed in UserName:
				 	` @ # $ & | = ; double-quote ' < > / sp
				 	This is a WRITE-ONLY value.
				"
			::= { wvpnCertificateSettings 8 }

		
		-- 1.3.6.1.4.1.388.6.3.34.5.9
		importCaCert OBJECT-TYPE
			SYNTAX DisplayString (SIZE (1..120))
			MAX-ACCESS read-write
			STATUS current
			DESCRIPTION
				"Import a CA certificate that is already
				 	residing on the local machine.
				 	Input String format: <caCertFile>
				 	caCertFile must be an absolute path to the file.
				 	Characters not allowed in caCertFile:
				 	` @ # $ & | = ; double-quote ' < > / sp
				 	This is a WRITE-ONLY value.
				"
			::= { wvpnCertificateSettings 9 }

		
		-- 1.3.6.1.4.1.388.6.3.34.5.10
		removeCaCert OBJECT-TYPE
			SYNTAX INTEGER (1..1000)
			MAX-ACCESS read-write
			STATUS current
			DESCRIPTION
				"Remove a CA certificate at a given index 
				 	from the wvpnCaCertificateTable.  This is a 
				 	WRITE-ONLY value.
				"
			::= { wvpnCertificateSettings 10 }

		
		-- 1.3.6.1.4.1.388.6.3.34.5.11
		importTftpServerCert OBJECT-TYPE
			SYNTAX DisplayString (SIZE (1..150))
			MAX-ACCESS read-write
			STATUS current
			DESCRIPTION
				"Import a server certificate from a remote machine 
				 	via TFTP.  
				 	Input String format: 
				 	<hostIPaddr,serverCertFile,password,certFileName>
				 	certFileName is optional, but if specified, 
				 	it must be an absolute path to the file.
				 	serverCertFile must be an absolute path to the 
				 	file.  The certificate file must be specified if 
				 	the serverCertFile does not have an embedded 
				 	certificate. 
				 	Characters not allowed in both serverCertFile 
				 	and certFileName:
				 	` @ # $ & | = ; double-quote ' < > / sp
				 	This is a WRITE-ONLY value.
				"
			::= { wvpnCertificateSettings 11 }

		
		-- 1.3.6.1.4.1.388.6.3.34.5.12
		importTftpCaCert OBJECT-TYPE
			SYNTAX DisplayString (SIZE (1..150))
			MAX-ACCESS read-write
			STATUS current
			DESCRIPTION
				"Import a CA certificate from a remote machine 
				 	via TFTP.
				 	Input String format: <hostIPaddr,caCertFile>
				 	caCertFile must be an absolute path to the file.
				 	Characters not allowed in caCertFile:
				 	` @ # $ & | = ; double-quote ' < > / sp
				 	This is a WRITE-ONLY value.
				"
			::= { wvpnCertificateSettings 12 }

		
		-- 1.3.6.1.4.1.388.6.3.34.5.13
		dirCert OBJECT-TYPE
			SYNTAX DisplayString (SIZE (1..1000))
			MAX-ACCESS read-only
			STATUS current
			DESCRIPTION
				"Dumps a list of certificate files.  This 
				 	diagnostic tool lists the certificate files 
				 	left over from upload operations - it does 
				 	not display or affect certificates installed 
				 	in the WVPN server.  The files are given in
				 	a comma-separated list.
				 	
				 	The 'dumpCert' object can be used to examine
				 	any of the listed certificate files in further
				 	detail.
				 	
				 	This is a READ-ONLY value.
				"
			::= { wvpnCertificateSettings 13 }

		
		-- 1.3.6.1.4.1.388.6.3.34.5.14
		dumpCert OBJECT-TYPE
			SYNTAX DisplayString (SIZE (1..120))
			MAX-ACCESS read-write
			STATUS current
			DESCRIPTION
				"Dumps the contents of a certificate
				 	file.  This diagnostic tool dumps the
				 	certificate files left over from upload
				 	operations - it does not dump or affect
				 	certificates installed in the WVPN server.
				 	
				 	Using this variable is a two-step
				 	process: first a SET request must be
				 	used to feed in the name of the
				 	certificate file to be decoded, then
				 	a GET request will retrieve the decoded
				 	contents of the certificate file.
				 	
				 	The input for the SET command is the
				 	relative path of a file containing a 
				 	certificate.
				 	
				 	Example: wtls_ca.cer
				 	
				 	The certificate file must be in the
				 	internal upload directory (/upload/wvpn).
				"
			::= { wvpnCertificateSettings 14 }

		
		-- 1.3.6.1.4.1.388.6.3.34.6
		wvpnDDNSSettings OBJECT IDENTIFIER ::= { ccWVPNConfigure 6 }

		
		-- 1.3.6.1.4.1.388.6.3.34.6.1
		clearClientDNS OBJECT-TYPE
			SYNTAX DoActionNow
			MAX-ACCESS read-write
			STATUS current
			DESCRIPTION
				"Remove all client IP addresses registered in 
				 	the DNS server by the WVPN server.  This is a 
				 	WRITE-ONLY value.  To set it, use a MIB
				 	instance value of 0.
				"
			::= { wvpnDDNSSettings 1 }

		
		-- 1.3.6.1.4.1.388.6.3.34.6.2
		updateClientDNS OBJECT-TYPE
			SYNTAX DoActionNow
			MAX-ACCESS read-write
			STATUS current
			DESCRIPTION
				"Re-register in the DNS server all client IP 
				 	addresses owned by the WVPN server.  This is a 
				 	WRITE-ONLY value.  To set it, use a MIB
				 	instance value of 0.
				"
			::= { wvpnDDNSSettings 2 }

		
		-- 1.3.6.1.4.1.388.6.3.34.6.3
		addDNSAddr OBJECT-TYPE
			SYNTAX IpAddress
			MAX-ACCESS read-write
			STATUS current
			DESCRIPTION
				"Add a DNS server IP address.  This is a 
				 	WRITE-ONLY value.  To set it, use a MIB
				 	instance value of 0.
				"
			::= { wvpnDDNSSettings 3 }

		
		-- 1.3.6.1.4.1.388.6.3.34.6.4
		deleteDNSAddr OBJECT-TYPE
			SYNTAX IpAddress
			MAX-ACCESS read-write
			STATUS current
			DESCRIPTION
				"Remove a DNS server IP address.  This is a 
				 	WRITE-ONLY value.  To set it, use a MIB
				 	instance value of 0.
				"
			::= { wvpnDDNSSettings 4 }

		
		-- 1.3.6.1.4.1.388.6.3.34.6.5
		enable OBJECT-TYPE
			SYNTAX TruthValue
			MAX-ACCESS read-write
			STATUS current
			DESCRIPTION
				"Enable or disable DDNS service, or query the 
				 	DDNS status.  To get or set it, use a MIB
				 	instance value of 0.
				"
			::= { wvpnDDNSSettings 5 }

		
		-- 1.3.6.1.4.1.388.6.3.34.6.6
		ttl OBJECT-TYPE
			SYNTAX INTEGER (0..100)
			MAX-ACCESS read-write
			STATUS current
			DESCRIPTION
				"The time-to-live (ttl) value for a resource 
				 	record stored in the DNS server.  TTL is 
				 	expressed as a percentage of the unused session 
				 	timeout.  To set it, use a MIB instance value 
				 	of 0.
				"
			::= { wvpnDDNSSettings 6 }

		
		-- 1.3.6.1.4.1.388.6.3.34.6.7
		forwardZone OBJECT-TYPE
			SYNTAX DisplayString (SIZE (1..120))
			MAX-ACCESS read-write
			STATUS current
			DESCRIPTION
				"The forward zone name of the DNS server.  To 
				 	set it, use a MIB instance value of 0.
				"
			::= { wvpnDDNSSettings 7 }

		
		-- 1.3.6.1.4.1.388.6.3.34.6.8
		reverseZone OBJECT-TYPE
			SYNTAX DisplayString (SIZE (1..120))
			MAX-ACCESS read-write
			STATUS current
			DESCRIPTION
				"The reverse zone name of the DNS server.  To 
				 	set it, use a MIB instance value of 0.
				"
			::= { wvpnDDNSSettings 8 }

		
		-- 1.3.6.1.4.1.388.6.3.34.6.9
		clientNameString OBJECT-TYPE
			SYNTAX DisplayString (SIZE (1..120))
			MAX-ACCESS read-write
			STATUS current
			DESCRIPTION
				"A format string used by the WVPN server to 
				 	construct client FQDN.  To set it, use a MIB 
				 	instance value of 0.
				"
			::= { wvpnDDNSSettings 9 }

		
		-- 1.3.6.1.4.1.388.6.3.34.6.10
		wvpnDDNSAddressTable OBJECT-TYPE
			SYNTAX SEQUENCE OF WvpnDDNSAddressEntry
			MAX-ACCESS not-accessible
			STATUS current
			DESCRIPTION
				"A table of DDNS IP addresses.
				"
			::= { wvpnDDNSSettings 10 }

		
		-- 1.3.6.1.4.1.388.6.3.34.6.10.1
		wvpnDDNSAddressEntry OBJECT-TYPE
			SYNTAX WvpnDDNSAddressEntry
			MAX-ACCESS not-accessible
			STATUS current
			DESCRIPTION
				"Description."
			INDEX { wvpnDDNSAddressIndex }
			::= { wvpnDDNSAddressTable 1 }

		
		WvpnDDNSAddressEntry ::=
			SEQUENCE { 
				wvpnDDNSAddressIndex
					INTEGER,
				wvpnDDNSipAddress
					IpAddress
			 }

		-- 1.3.6.1.4.1.388.6.3.34.6.10.1.1
		wvpnDDNSAddressIndex OBJECT-TYPE
			SYNTAX INTEGER (1..100)
			MAX-ACCESS read-only
			STATUS current
			DESCRIPTION
				"An integer index for the wvpnDDNSAddressTable 
				 	to access a DNS server IP address.
				"
			::= { wvpnDDNSAddressEntry 1 }

		
		-- 1.3.6.1.4.1.388.6.3.34.6.10.1.2
		wvpnDDNSipAddress OBJECT-TYPE
			SYNTAX IpAddress
			MAX-ACCESS read-write
			STATUS current
			DESCRIPTION
				"The IP address of the DNS server.
				"
			::= { wvpnDDNSAddressEntry 2 }

		
		-- 1.3.6.1.4.1.388.6.3.34.6.11
		cleanupTimeout OBJECT-TYPE
			SYNTAX INTEGER (0..10000)
			MAX-ACCESS read-write
			STATUS current
			DESCRIPTION
				"Duration of cleanup timeout in sec."
			::= { wvpnDDNSSettings 11 }

		
		-- 1.3.6.1.4.1.388.6.3.34.6.12
		reverseZoneList OBJECT-TYPE
			SYNTAX DisplayString (SIZE (1..255))
			MAX-ACCESS read-only
			STATUS current
			DESCRIPTION
				"List reverse zones of the DNS server."
			::= { wvpnDDNSSettings 12 }

		
		-- 1.3.6.1.4.1.388.6.3.34.6.13
		reverseZoneAdd OBJECT-TYPE
			SYNTAX DisplayString (SIZE (1..255))
			MAX-ACCESS read-write
			STATUS current
			DESCRIPTION
				"Add new reverse zones for the DNS server."
			::= { wvpnDDNSSettings 13 }

		
		-- 1.3.6.1.4.1.388.6.3.34.6.14
		reverseZoneDel OBJECT-TYPE
			SYNTAX DisplayString (SIZE (1..255))
			MAX-ACCESS read-write
			STATUS current
			DESCRIPTION
				"Delete a reverse zone from a list of
				reverse zones of the DNS Server."
			::= { wvpnDDNSSettings 14 }

		
		-- 1.3.6.1.4.1.388.6.3.34.7
		wvpnRuntimeStats OBJECT IDENTIFIER ::= { ccWVPNConfigure 7 }

		
		-- 1.3.6.1.4.1.388.6.3.34.7.1
		wvpnSessionTable OBJECT-TYPE
			SYNTAX SEQUENCE OF WvpnSessionEntry
			MAX-ACCESS not-accessible
			STATUS current
			DESCRIPTION
				"Description."
			::= { wvpnRuntimeStats 1 }

		
		-- 1.3.6.1.4.1.388.6.3.34.7.1.1
		wvpnSessionEntry OBJECT-TYPE
			SYNTAX WvpnSessionEntry
			MAX-ACCESS not-accessible
			STATUS current
			DESCRIPTION
				"Description."
			INDEX { wvpnSessionIndex }
			::= { wvpnSessionTable 1 }

		
		WvpnSessionEntry ::=
			SEQUENCE { 
				wvpnSessionIndex
					Integer32,
				wvpnSessionId
					DisplayString,
				wvpnVpnIp
					DisplayString,
				wvpnRealIp
					DisplayString,
				wvpnLoginTime
					DisplayString,
				wvpnRoamTime
					DisplayString,
				wvpnLastActive
					DisplayString,
				wvpnPoolName
					DisplayString,
				wvpnMacAddr
					DisplayString
			 }

		-- 1.3.6.1.4.1.388.6.3.34.7.1.1.1
		wvpnSessionIndex OBJECT-TYPE
			SYNTAX Integer32 (1..4096)
			MAX-ACCESS read-only
			STATUS current
			DESCRIPTION
				"An integer index for wvpnSessionTable to access
				a VPN session"
			::= { wvpnSessionEntry 1 }

		
		-- 1.3.6.1.4.1.388.6.3.34.7.1.1.2
		wvpnSessionId OBJECT-TYPE
			SYNTAX DisplayString (SIZE (1..32))
			MAX-ACCESS read-only
			STATUS current
			DESCRIPTION
				"The internal ID number by which the WVPN
				server identifies the session."
			::= { wvpnSessionEntry 2 }

		
		-- 1.3.6.1.4.1.388.6.3.34.7.1.1.3
		wvpnVpnIp OBJECT-TYPE
			SYNTAX DisplayString (SIZE (1..32))
			MAX-ACCESS read-only
			STATUS current
			DESCRIPTION
				"The private IP address assigned to the VPN
				client."
			::= { wvpnSessionEntry 3 }

		
		-- 1.3.6.1.4.1.388.6.3.34.7.1.1.4
		wvpnRealIp OBJECT-TYPE
			SYNTAX DisplayString (SIZE (1..32))
			MAX-ACCESS read-only
			STATUS current
			DESCRIPTION
				"The public IP address of the client prior
				to connecting to the VPN server."
			::= { wvpnSessionEntry 4 }

		
		-- 1.3.6.1.4.1.388.6.3.34.7.1.1.5
		wvpnLoginTime OBJECT-TYPE
			SYNTAX DisplayString (SIZE (1..32))
			MAX-ACCESS read-only
			STATUS current
			DESCRIPTION
				"The login time of the client"
			::= { wvpnSessionEntry 5 }

		
		-- 1.3.6.1.4.1.388.6.3.34.7.1.1.6
		wvpnRoamTime OBJECT-TYPE
			SYNTAX DisplayString (SIZE (1..32))
			MAX-ACCESS read-only
			STATUS current
			DESCRIPTION
				"Description."
			::= { wvpnSessionEntry 6 }

		
		-- 1.3.6.1.4.1.388.6.3.34.7.1.1.7
		wvpnLastActive OBJECT-TYPE
			SYNTAX DisplayString (SIZE (1..32))
			MAX-ACCESS read-only
			STATUS current
			DESCRIPTION
				"The last time that the client was active."
			::= { wvpnSessionEntry 7 }

		
		-- 1.3.6.1.4.1.388.6.3.34.7.1.1.8
		wvpnPoolName OBJECT-TYPE
			SYNTAX DisplayString (SIZE (1..32))
			MAX-ACCESS read-only
			STATUS current
			DESCRIPTION
				"The IP Pool from which the client got its' VPN
				IP address."
			::= { wvpnSessionEntry 8 }

		
		-- 1.3.6.1.4.1.388.6.3.34.7.1.1.9
		wvpnMacAddr OBJECT-TYPE
			SYNTAX DisplayString (SIZE (1..32))
			MAX-ACCESS read-only
			STATUS current
			DESCRIPTION
				"The MAC address of the client."
			::= { wvpnSessionEntry 9 }

		
		-- 1.3.6.1.4.1.388.6.3.34.7.2
		wvpnSessionCount OBJECT-TYPE
			SYNTAX Integer32
			MAX-ACCESS read-only
			STATUS current
			DESCRIPTION
				"The number of VPN sessions.
				This is a READ-ONLY value."
			::= { wvpnRuntimeStats 2 }

		
		-- 1.3.6.1.4.1.388.6.3.34.7.3
		wvpnRefreshSession OBJECT-TYPE
			SYNTAX DisplayString (SIZE (1..1000))
			MAX-ACCESS read-only
			STATUS current
			DESCRIPTION
				"Refreshes the VPN session info. Returns a blank string
				
				This is a READ-ONLY value."
			::= { wvpnRuntimeStats 3 }

		
		-- 1.3.6.1.4.1.388.6.3.34.7.4
		wvpnKillSession OBJECT-TYPE
			SYNTAX INTEGER (0..65535)
			MAX-ACCESS read-write
			STATUS current
			DESCRIPTION
				"Kills the VPN session specified by the written
				index number. For Example: setting this value to 
				4 would kill the fourth VPN session in the current
				list.
				This is a WRITE-ONLY value. Reading it will 
				always return 0."
			::= { wvpnRuntimeStats 4 }

		
		-- 1.3.6.1.4.1.388.6.4
		symbolCCPerformance OBJECT IDENTIFIER ::= { symbolCC 4 }

		
--  1.3.6.1.4.1.388.6.5
		-- 1.3.6.1.4.1.388.6.5
		symbolCCFault OBJECT IDENTIFIER ::= { symbolCC 5 }

		
--  1.3.6.1.4.1.388.6.5.1
		-- 1.3.6.1.4.1.388.6.5.1
		ccTargetObjects OBJECT IDENTIFIER ::= { symbolCCFault 1 }

		
--  1.3.6.1.4.1.388.6.5.1.1
		-- 1.3.6.1.4.1.388.6.5.1.1
		ccTargetTrapString OBJECT-TYPE
			SYNTAX DisplayString (SIZE (0..512))
			MAX-ACCESS accessible-for-notify
			STATUS current
			DESCRIPTION
				"String that varies based on the trap that is being sent."
			::= { ccTargetObjects 1 }

		
--  1.3.6.1.4.1.388.6.5.1.2
		-- 1.3.6.1.4.1.388.6.5.1.2
		ccTargetAddrTable OBJECT-TYPE
			SYNTAX SEQUENCE OF CcTargetAddrEntry
			MAX-ACCESS not-accessible
			STATUS current
			DESCRIPTION
				"A table of transport addresses to be used in the generation
				of SNMP messages.
				
				Note: After make changes for this table objects, in order to
				make those modifications effective immediately, there are two 
				operations which should be performed in the following order:
				
				1. SET ccSnmpOpers object to 3 (Update Configuration).
							
				2. SET ccSNMPFlag object to 'true'.
						 
				Both ccSnmpOpers and ccSNMPFlag objects are under
				ccSysCfg tree.
				"
			::= { ccTargetObjects 2 }

		
--  1.3.6.1.4.1.388.6.5.1.2.1
		-- 1.3.6.1.4.1.388.6.5.1.2.1
		ccTargetAddrEntry OBJECT-TYPE
			SYNTAX CcTargetAddrEntry
			MAX-ACCESS not-accessible
			STATUS current
			DESCRIPTION
				"A transport address to be used in the generation
				of SNMP operations.
				
				Entries in the ccTargetAddrTable are created and
				deleted using the ccTargetAddrRowStatus object."
			INDEX { ccTargetAddrName }
			::= { ccTargetAddrTable 1 }

		
		CcTargetAddrEntry ::=
			SEQUENCE { 
				ccTargetAddrName
					Integer32,
				ccTargetAddrSecName
					DisplayString,
				ccTargetAddrHost
					DisplayString,
				ccTargetAddrCommunity
					DisplayString,
				ccTargetAddrPort
					Integer32,
				ccTargetAddrStorageType
					StorageType,
				ccTargetAddrRowStatus
					RowStatus,
				ccTargetAddrOption
					TargetOptions
			 }

--  1.3.6.1.4.1.388.6.5.1.2.1.1
		-- 1.3.6.1.4.1.388.6.5.1.2.1.1
		ccTargetAddrName OBJECT-TYPE
			SYNTAX Integer32 (1..16)
			MAX-ACCESS not-accessible
			STATUS current
			DESCRIPTION
				"The locally arbitrary, but unique identifier associated
				with this ccTargetAddrEntry."
			::= { ccTargetAddrEntry 1 }

		
--  1.3.6.1.4.1.388.6.5.1.2.1.2
		-- 1.3.6.1.4.1.388.6.5.1.2.1.2
		ccTargetAddrSecName OBJECT-TYPE
			SYNTAX DisplayString (SIZE (1..32))
			MAX-ACCESS read-create
			STATUS current
			DESCRIPTION
				"This object contains a target(such as a snmp manager) secName."
			::= { ccTargetAddrEntry 2 }

		
--  1.3.6.1.4.1.388.6.5.1.2.1.3
		-- 1.3.6.1.4.1.388.6.5.1.2.1.3
		ccTargetAddrHost OBJECT-TYPE
			SYNTAX DisplayString (SIZE (1..32))
			MAX-ACCESS read-create
			STATUS current
			DESCRIPTION
				"This object contains a target(such as a snmp manager) ip address."
			::= { ccTargetAddrEntry 3 }

		
--  1.3.6.1.4.1.388.6.5.1.2.1.4
		-- 1.3.6.1.4.1.388.6.5.1.2.1.4
		ccTargetAddrCommunity OBJECT-TYPE
			SYNTAX DisplayString (SIZE (1..32))
			MAX-ACCESS read-create
			STATUS current
			DESCRIPTION
				"This object contains a community name."
			::= { ccTargetAddrEntry 4 }

		
--  1.3.6.1.4.1.388.6.5.1.2.1.5
		-- 1.3.6.1.4.1.388.6.5.1.2.1.5
		ccTargetAddrPort OBJECT-TYPE
			SYNTAX Integer32 (0..20000)
			MAX-ACCESS read-create
			STATUS current
			DESCRIPTION
				"This object specifies a port number for remote manager receiving the trap."
			DEFVAL { 162 }
			::= { ccTargetAddrEntry 5 }

		
--  1.3.6.1.4.1.388.6.5.1.2.1.6
		-- 1.3.6.1.4.1.388.6.5.1.2.1.6
		ccTargetAddrStorageType OBJECT-TYPE
			SYNTAX StorageType
			MAX-ACCESS read-create
			STATUS current
			DESCRIPTION
				"The storage type for this conceptual row."
			DEFVAL { nonVolatile }
			::= { ccTargetAddrEntry 6 }

		
--  1.3.6.1.4.1.388.6.5.1.2.1.7
		-- 1.3.6.1.4.1.388.6.5.1.2.1.7
		ccTargetAddrRowStatus OBJECT-TYPE
			SYNTAX RowStatus
			MAX-ACCESS read-create
			STATUS current
			DESCRIPTION
				"The status of this conceptual row.
				
				To create a row in this table, a manager must
				set this object to either createAndGo(4) or
				createAndWait(5).
				
				Until instances of all corresponding columns are
				appropriately configured, the value of the
				corresponding instance of the ccTargetAddrRowStatus
				column is 'notReady'.
				
				In particular, a newly created row cannot be made
				active until the corresponding instances of
				ccTargetAddrTDomain, ccTargetAddrTAddress, and
				ccTargetAddrParams have all been set.
				
				The following objects may not be modified while the
				value of this object is active(1):
				    - ccTargetAddrTDomain
				    - ccTargetAddrTAddress
				An attempt to set these objects while the value of
				ccTargetAddrRowStatus is active(1) will result in
				an inconsistentValue error.
				
					Note:While destroying a row set the manager's 
					     re-transmission value as zero as the agent is
					     re-started and there is no response from agent
					     fot this request and the manager keeps on 
					     re-transmitting resulting into multiple row 
					     deletion depending on the value of re-transmission."
			::= { ccTargetAddrEntry 7 }

		
--  1.3.6.1.4.1.388.6.5.1.2.1.8
		-- 1.3.6.1.4.1.388.6.5.1.2.1.8
		ccTargetAddrOption OBJECT-TYPE
			SYNTAX TargetOptions
			MAX-ACCESS read-create
			STATUS current
			DESCRIPTION
				"The write option for this conceptual row.
				com2sec(0),					for setting up remote manager address.
				trap2sink(1),				for setting up V2c trap target address.
				trapsink(2),				for setting up V1 trap target address.
				com2secAndtrap2sink(3),		write the row record to both <com2sec>,
											and <trap2sink> section in snmpd.conf.
				all(4)
				"
			DEFVAL { com2sec }
			::= { ccTargetAddrEntry 8 }

		
--  1.3.6.1.4.1.388.6.5.2
		-- 1.3.6.1.4.1.388.6.5.2
		ccTrapInfos OBJECT IDENTIFIER ::= { symbolCCFault 2 }

		
--  1.3.6.1.4.1.388.6.5.2.1
		-- 1.3.6.1.4.1.388.6.5.2.1
		ccTrapInfoEnableTrap OBJECT-TYPE
			SYNTAX TruthValue
			MAX-ACCESS read-only
			STATUS current
			DESCRIPTION
				"(true) implies that the traps subsystem is enabled.
				(false) implies that the traps subsystem is disabled."
			::= { ccTrapInfos 1 }

		
--  1.3.6.1.4.1.388.6.5.2.2
		-- 1.3.6.1.4.1.388.6.5.2.2
		ccTrapInfoMaxNumSendOneTrap OBJECT-TYPE
			SYNTAX INTEGER (1..10)
			MAX-ACCESS read-write
			STATUS current
			DESCRIPTION
				"The maximum number of times for sending one trap
				over the interval specified in ccTrapInfoInterval."
			::= { ccTrapInfos 2 }

		
--  1.3.6.1.4.1.388.6.5.2.3
		-- 1.3.6.1.4.1.388.6.5.2.3
		ccTrapInfoInterval OBJECT-TYPE
			SYNTAX INTEGER (1..120)
			MAX-ACCESS read-write
			STATUS current
			DESCRIPTION
				"No more than ccTrapInfoMaxNumSendOneTrap traps of
				same kind may be sent within this interval(in seconds)."
			::= { ccTrapInfos 3 }

		
--  1.3.6.1.4.1.388.6.5.2.4
		-- 1.3.6.1.4.1.388.6.5.2.4
		ccTrapInfoAclViolation OBJECT-TYPE
			SYNTAX TruthValue
			MAX-ACCESS read-write
			STATUS current
			DESCRIPTION
				"Enable(true)/Disable(false) this trap.
				MU assoc failed [ACL violation]"
			::= { ccTrapInfos 4 }

		
--  1.3.6.1.4.1.388.6.5.2.5
		-- 1.3.6.1.4.1.388.6.5.2.5
		ccTrapInfoDenyAdoption OBJECT-TYPE
			SYNTAX TruthValue
			MAX-ACCESS read-write
			STATUS current
			DESCRIPTION
				"Enable(true)/Disable(false) this trap.
				AP adopt failure [general]"
			::= { ccTrapInfos 5 }

		
--  1.3.6.1.4.1.388.6.5.2.6
		-- 1.3.6.1.4.1.388.6.5.2.6
		ccTrapInfoAPMUMaxExceed OBJECT-TYPE
			SYNTAX TruthValue
			MAX-ACCESS read-write
			STATUS current
			DESCRIPTION
				"Enable(true)/Disable(false) this trap.
				AP max MU count reached"
			::= { ccTrapInfos 6 }

		
--  1.3.6.1.4.1.388.6.5.2.7
		-- 1.3.6.1.4.1.388.6.5.2.7
		ccTrapInfoWLANMUMaxExceed OBJECT-TYPE
			SYNTAX TruthValue
			MAX-ACCESS read-write
			STATUS current
			DESCRIPTION
				"Enable(true)/Disable(false) this trap.
				WLAN max MU count reached"
			::= { ccTrapInfos 7 }

		
--  1.3.6.1.4.1.388.6.5.2.8
		-- 1.3.6.1.4.1.388.6.5.2.8
		ccTrapInfoApDetected OBJECT-TYPE
			SYNTAX TruthValue
			MAX-ACCESS read-write
			STATUS current
			DESCRIPTION
				"Enable(true)/Disable(false) this trap.
				AP detected"
			::= { ccTrapInfos 8 }

		
--  1.3.6.1.4.1.388.6.5.2.9
		-- 1.3.6.1.4.1.388.6.5.2.9
		ccTrapInfoApAdopted OBJECT-TYPE
			SYNTAX TruthValue
			MAX-ACCESS read-write
			STATUS current
			DESCRIPTION
				"Enable(true)/Disable(false) this trap.
				AP status [adopted]"
			::= { ccTrapInfos 9 }

		
--  1.3.6.1.4.1.388.6.5.2.10
		-- 1.3.6.1.4.1.388.6.5.2.10
		ccTrapInfoApReset OBJECT-TYPE
			SYNTAX TruthValue
			MAX-ACCESS read-write
			STATUS current
			DESCRIPTION
				"Enable(true)/Disable(false) this trap.
				AP status [reset]"
			::= { ccTrapInfos 10 }

		
--  1.3.6.1.4.1.388.6.5.2.11
		-- 1.3.6.1.4.1.388.6.5.2.11
		ccTrapInfoApUnavailable OBJECT-TYPE
			SYNTAX TruthValue
			MAX-ACCESS read-write
			STATUS current
			DESCRIPTION
				"Enable(true)/Disable(false) this trap.
				AP status [offline]"
			::= { ccTrapInfos 11 }

		
--  1.3.6.1.4.1.388.6.5.2.13
		-- 1.3.6.1.4.1.388.6.5.2.13
		ccTrapInfoKDCUserAuthFail OBJECT-TYPE
			SYNTAX TruthValue
			MAX-ACCESS read-write
			STATUS current
			DESCRIPTION
				"Enable(true)/Disable(false) this trap.
				MU Kerberos auth failed"
			::= { ccTrapInfos 13 }

		
--  1.3.6.1.4.1.388.6.5.2.14
		-- 1.3.6.1.4.1.388.6.5.2.14
		ccTrapInfoRadiusAuthFail OBJECT-TYPE
			SYNTAX TruthValue
			MAX-ACCESS read-write
			STATUS current
			DESCRIPTION
				"Enable(true)/Disable(false) this trap.
				Mgt user auth failed  [radius]"
			::= { ccTrapInfos 14 }

		
--  1.3.6.1.4.1.388.6.5.2.16
		-- 1.3.6.1.4.1.388.6.5.2.16
		ccTrapInfoLowFlashSpace OBJECT-TYPE
			SYNTAX TruthValue
			MAX-ACCESS read-write
			STATUS current
			DESCRIPTION
				"Enable(true)/Disable(false) this trap.
				Low flash space on switch"
			::= { ccTrapInfos 16 }

		
--  1.3.6.1.4.1.388.6.5.2.17
		-- 1.3.6.1.4.1.388.6.5.2.17
		ccTrapInfoNicDropping OBJECT-TYPE
			SYNTAX TruthValue
			MAX-ACCESS read-write
			STATUS current
			DESCRIPTION
				"Enable(true)/Disable(false) this trap.
				Ether port disconnected"
			::= { ccTrapInfos 17 }

		
--  1.3.6.1.4.1.388.6.5.2.19
		-- 1.3.6.1.4.1.388.6.5.2.19
		ccTrapInfoApAlert OBJECT-TYPE
			SYNTAX TruthValue
			MAX-ACCESS read-write
			STATUS current
			DESCRIPTION
				"Enable(true)/Disable(false) this trap.
				AP status [alert]"
			::= { ccTrapInfos 19 }

		
--  1.3.6.1.4.1.388.6.5.2.20
		-- 1.3.6.1.4.1.388.6.5.2.20
		ccTrapInfoUserAuthFail OBJECT-TYPE
			SYNTAX TruthValue
			MAX-ACCESS read-write
			STATUS current
			DESCRIPTION
				"Enable(true)/Disable(false) this trap.
				Mgt user auth rejected"
			::= { ccTrapInfos 20 }

		
--  1.3.6.1.4.1.388.6.5.2.21
		-- 1.3.6.1.4.1.388.6.5.2.21
		ccTrapInfoHsbPrimaryNoHeartbeat OBJECT-TYPE
			SYNTAX TruthValue
			MAX-ACCESS read-write
			STATUS current
			DESCRIPTION
				"Enable(true)/Disable(false) this trap.
				Primary lost heartbeat"
			::= { ccTrapInfos 21 }

		
--  1.3.6.1.4.1.388.6.5.2.22
		-- 1.3.6.1.4.1.388.6.5.2.22
		ccTrapInfoHsbStandbyEntersFailover OBJECT-TYPE
			SYNTAX TruthValue
			MAX-ACCESS read-write
			STATUS current
			DESCRIPTION
				"Enable(true)/Disable(false) this trap.
				Standby active"
			::= { ccTrapInfos 22 }

		
--  1.3.6.1.4.1.388.6.5.2.23
		-- 1.3.6.1.4.1.388.6.5.2.23
		ccTrapInfoPrimaryFailedResetting OBJECT-TYPE
			SYNTAX TruthValue
			MAX-ACCESS read-write
			STATUS current
			DESCRIPTION
				"Enable(true)/Disable(false) this trap.
				Primary internal failure [reset]"
			::= { ccTrapInfos 23 }

		
--  1.3.6.1.4.1.388.6.5.2.25
		-- 1.3.6.1.4.1.388.6.5.2.25
		ccTrapInfoKDCPropagationFail OBJECT-TYPE
			SYNTAX TruthValue
			MAX-ACCESS read-write
			STATUS current
			DESCRIPTION
				"Enable(true)/Disable(false) this trap.
				KDC propagation failure"
			::= { ccTrapInfos 25 }

		
--  1.3.6.1.4.1.388.6.5.2.26
		-- 1.3.6.1.4.1.388.6.5.2.26
		ccTrapInfoHighDecryptFail OBJECT-TYPE
			SYNTAX TruthValue
			MAX-ACCESS read-write
			STATUS current
			DESCRIPTION
				"Enable(true)/Disable(false) this trap.
				MU TKIP [decrypt failure]"
			::= { ccTrapInfos 26 }

		
--  1.3.6.1.4.1.388.6.5.2.27
		-- 1.3.6.1.4.1.388.6.5.2.27
		ccTrapInfoHighReplyFail OBJECT-TYPE
			SYNTAX TruthValue
			MAX-ACCESS read-write
			STATUS current
			DESCRIPTION
				"Enable(true)/Disable(false) this trap.
				MU TKIP [replay failure]"
			::= { ccTrapInfos 27 }

		
--  1.3.6.1.4.1.388.6.5.2.28
		-- 1.3.6.1.4.1.388.6.5.2.28
		ccTrapInfoTKIPMICFail OBJECT-TYPE
			SYNTAX TruthValue
			MAX-ACCESS read-write
			STATUS current
			DESCRIPTION
				"Enable(true)/Disable(false) this trap.
				MU TKIP [MIC error]"
			::= { ccTrapInfos 28 }

		
--  1.3.6.1.4.1.388.6.5.2.29
		-- 1.3.6.1.4.1.388.6.5.2.29
		ccTrapInfoWPACounterMeasureStart OBJECT-TYPE
			SYNTAX TruthValue
			MAX-ACCESS read-write
			STATUS current
			DESCRIPTION
				"Enable(true)/Disable(false) this trap.
				WPA counter-measures [active]"
			::= { ccTrapInfos 29 }

		
--  1.3.6.1.4.1.388.6.5.2.31
		-- 1.3.6.1.4.1.388.6.5.2.31
		licenseChangedControl OBJECT-TYPE
			SYNTAX TruthValue
			MAX-ACCESS read-write
			STATUS current
			DESCRIPTION
				"Enable(true)/Disable(false) this trap.
				License number change
				"
			::= { ccTrapInfos 31 }

		
--  1.3.6.1.4.1.388.6.5.2.32
		-- 1.3.6.1.4.1.388.6.5.2.32
		clockChangedControl OBJECT-TYPE
			SYNTAX TruthValue
			MAX-ACCESS read-write
			STATUS current
			DESCRIPTION
				"Enable(true)/Disable(false) this trap.
				Clock change
				"
			::= { ccTrapInfos 32 }

		
--  1.3.6.1.4.1.388.6.5.2.33
		-- 1.3.6.1.4.1.388.6.5.2.33
		pktDiscWrongNICControl OBJECT-TYPE
			SYNTAX TruthValue
			MAX-ACCESS read-write
			STATUS current
			DESCRIPTION
				"Enable(true)/Disable(false) this trap.
				Packet discard [wrong NIC]
				"
			::= { ccTrapInfos 33 }

		
--  1.3.6.1.4.1.388.6.5.2.34
		-- 1.3.6.1.4.1.388.6.5.2.34
		pktDiscWrongVLANControl OBJECT-TYPE
			SYNTAX TruthValue
			MAX-ACCESS read-write
			STATUS current
			DESCRIPTION
				"Enable(true)/Disable(false) this trap.
				Packet discard [wrong VLAN]
				"
			::= { ccTrapInfos 34 }

		
--  1.3.6.1.4.1.388.6.5.2.35
		-- 1.3.6.1.4.1.388.6.5.2.35
		apAdoptFailPolControl OBJECT-TYPE
			SYNTAX TruthValue
			MAX-ACCESS read-write
			STATUS current
			DESCRIPTION
				"Enable(true)/Disable(false) this trap.
				AP adopt failure [policy disallow]
				"
			::= { ccTrapInfos 35 }

		
--  1.3.6.1.4.1.388.6.5.2.36
		-- 1.3.6.1.4.1.388.6.5.2.36
		apAdoptFailACLControl OBJECT-TYPE
			SYNTAX TruthValue
			MAX-ACCESS read-write
			STATUS current
			DESCRIPTION
				"Enable(true)/Disable(false) this trap.
				AP adopt failure [acl disallow]
				"
			::= { ccTrapInfos 36 }

		
--  1.3.6.1.4.1.388.6.5.2.37
		-- 1.3.6.1.4.1.388.6.5.2.37
		apAdoptFailLimitControl OBJECT-TYPE
			SYNTAX TruthValue
			MAX-ACCESS read-write
			STATUS current
			DESCRIPTION
				"Enable(true)/Disable(false) this trap.
				AP adopt failure [limit exceeded]
				"
			::= { ccTrapInfos 37 }

		
--  1.3.6.1.4.1.388.6.5.2.38
		-- 1.3.6.1.4.1.388.6.5.2.38
		apAdoptFailLicControl OBJECT-TYPE
			SYNTAX TruthValue
			MAX-ACCESS read-write
			STATUS current
			DESCRIPTION
				"Enable(true)/Disable(false) this trap.
				AP adopt failure [license disallow]
				"
			::= { ccTrapInfos 38 }

		
--  1.3.6.1.4.1.388.6.5.2.39
		-- 1.3.6.1.4.1.388.6.5.2.39
		apAdoptFailNoImgControl OBJECT-TYPE
			SYNTAX TruthValue
			MAX-ACCESS read-write
			STATUS current
			DESCRIPTION
				"Enable(true)/Disable(false) this trap.
				AP adopt failure [no image]
				"
			::= { ccTrapInfos 39 }

		
--  1.3.6.1.4.1.388.6.5.2.40
		-- 1.3.6.1.4.1.388.6.5.2.40
		apCfgFailESSControl OBJECT-TYPE
			SYNTAX TruthValue
			MAX-ACCESS read-write
			STATUS current
			DESCRIPTION
				"Enable(true)/Disable(false) this trap.
				AP config failed [wrong ESS]
				"
			::= { ccTrapInfos 40 }

		
--  1.3.6.1.4.1.388.6.5.2.41
		-- 1.3.6.1.4.1.388.6.5.2.41
		devDropInfoMsgControl OBJECT-TYPE
			SYNTAX TruthValue
			MAX-ACCESS read-write
			STATUS current
			DESCRIPTION
				"Enable(true)/Disable(false) this trap.
				Device msg dropped [info]
				"
			::= { ccTrapInfos 41 }

		
--  1.3.6.1.4.1.388.6.5.2.42
		-- 1.3.6.1.4.1.388.6.5.2.42
		devdropLoadmeMsgControl OBJECT-TYPE
			SYNTAX TruthValue
			MAX-ACCESS read-write
			STATUS current
			DESCRIPTION
				"Enable(true)/Disable(false) this trap.
				Device msg dropped [loadme]
				"
			::= { ccTrapInfos 42 }

		
--  1.3.6.1.4.1.388.6.5.2.43
		-- 1.3.6.1.4.1.388.6.5.2.43
		etherConnectControl OBJECT-TYPE
			SYNTAX TruthValue
			MAX-ACCESS read-write
			STATUS current
			DESCRIPTION
				"Enable(true)/Disable(false) this trap.
				Ether port connected
				"
			::= { ccTrapInfos 43 }

		
--  1.3.6.1.4.1.388.6.5.2.44
		-- 1.3.6.1.4.1.388.6.5.2.44
		muAssocFailControl OBJECT-TYPE
			SYNTAX TruthValue
			MAX-ACCESS read-write
			STATUS current
			DESCRIPTION
				"Enable(true)/Disable(false) this trap.
				MU assoc failed
				"
			::= { ccTrapInfos 44 }

		
--  1.3.6.1.4.1.388.6.5.2.45
		-- 1.3.6.1.4.1.388.6.5.2.45
		muAssocOKControl OBJECT-TYPE
			SYNTAX TruthValue
			MAX-ACCESS read-write
			STATUS current
			DESCRIPTION
				"Enable(true)/Disable(false) this trap.
				MU status [associated]
				"
			::= { ccTrapInfos 45 }

		
--  1.3.6.1.4.1.388.6.5.2.46
		-- 1.3.6.1.4.1.388.6.5.2.46
		muRoamedControl OBJECT-TYPE
			SYNTAX TruthValue
			MAX-ACCESS read-write
			STATUS current
			DESCRIPTION
				"Enable(true)/Disable(false) this trap.
				MU status [roamed]
				"
			::= { ccTrapInfos 46 }

		
--  1.3.6.1.4.1.388.6.5.2.47
		-- 1.3.6.1.4.1.388.6.5.2.47
		muDisassocControl OBJECT-TYPE
			SYNTAX TruthValue
			MAX-ACCESS read-write
			STATUS current
			DESCRIPTION
				"Enable(true)/Disable(false) this trap.
				MU status [disassociated]
				"
			::= { ccTrapInfos 47 }

		
--  1.3.6.1.4.1.388.6.5.2.48
		-- 1.3.6.1.4.1.388.6.5.2.48
		muEAPAuthFailControl OBJECT-TYPE
			SYNTAX TruthValue
			MAX-ACCESS read-write
			STATUS current
			DESCRIPTION
				"Enable(true)/Disable(false) this trap.
				MU EAP auth failed
				"
			::= { ccTrapInfos 48 }

		
--  1.3.6.1.4.1.388.6.5.2.49
		-- 1.3.6.1.4.1.388.6.5.2.49
		muEAPAuthOKControl OBJECT-TYPE
			SYNTAX TruthValue
			MAX-ACCESS read-write
			STATUS current
			DESCRIPTION
				"Enable(true)/Disable(false) this trap.
				MU EAP auth success
				"
			::= { ccTrapInfos 49 }

		
--  1.3.6.1.4.1.388.6.5.2.50
		-- 1.3.6.1.4.1.388.6.5.2.50
		muKDCAuthOKControl OBJECT-TYPE
			SYNTAX TruthValue
			MAX-ACCESS read-write
			STATUS current
			DESCRIPTION
				"Enable(true)/Disable(false) this trap.
				MU Kerberos auth success
				"
			::= { ccTrapInfos 50 }

		
--  1.3.6.1.4.1.388.6.5.2.51
		-- 1.3.6.1.4.1.388.6.5.2.51
		wlanAuthOKControl OBJECT-TYPE
			SYNTAX TruthValue
			MAX-ACCESS read-write
			STATUS current
			DESCRIPTION
				"Enable(true)/Disable(false) this trap.
				WLAN auth success
				"
			::= { ccTrapInfos 51 }

		
--  1.3.6.1.4.1.388.6.5.2.52
		-- 1.3.6.1.4.1.388.6.5.2.52
		wlanAuthFailControl OBJECT-TYPE
			SYNTAX TruthValue
			MAX-ACCESS read-write
			STATUS current
			DESCRIPTION
				"Enable(true)/Disable(false) this trap.
				WLAN auth failed
				"
			::= { ccTrapInfos 52 }

		
--  1.3.6.1.4.1.388.6.5.2.53
		-- 1.3.6.1.4.1.388.6.5.2.53
		userAuthOKControl OBJECT-TYPE
			SYNTAX TruthValue
			MAX-ACCESS read-write
			STATUS current
			DESCRIPTION
				"Enable(true)/Disable(false) this trap.
				Mgt user auth success [radius]
				"
			::= { ccTrapInfos 53 }

		
--  1.3.6.1.4.1.388.6.5.2.54
		-- 1.3.6.1.4.1.388.6.5.2.54
		radiusSrvTimeoutControl OBJECT-TYPE
			SYNTAX TruthValue
			MAX-ACCESS read-write
			STATUS current
			DESCRIPTION
				"Enable(true)/Disable(false) this trap.
				Radius server timeout
				"
			::= { ccTrapInfos 54 }

		
--  1.3.6.1.4.1.388.6.5.2.55
		-- 1.3.6.1.4.1.388.6.5.2.55
		kdcPrincAddControl OBJECT-TYPE
			SYNTAX TruthValue
			MAX-ACCESS read-write
			STATUS current
			DESCRIPTION
				"Enable(true)/Disable(false) this trap.
				KDC user [added]
				"
			::= { ccTrapInfos 55 }

		
--  1.3.6.1.4.1.388.6.5.2.56
		-- 1.3.6.1.4.1.388.6.5.2.56
		kdcPrincChgdControl OBJECT-TYPE
			SYNTAX TruthValue
			MAX-ACCESS read-write
			STATUS current
			DESCRIPTION
				"Enable(true)/Disable(false) this trap.
				KDC user [changed]
				"
			::= { ccTrapInfos 56 }

		
--  1.3.6.1.4.1.388.6.5.2.57
		-- 1.3.6.1.4.1.388.6.5.2.57
		kdcPrincDelControl OBJECT-TYPE
			SYNTAX TruthValue
			MAX-ACCESS read-write
			STATUS current
			DESCRIPTION
				"Enable(true)/Disable(false) this trap.
				KDC user [deleted]
				"
			::= { ccTrapInfos 57 }

		
--  1.3.6.1.4.1.388.6.5.2.58
		-- 1.3.6.1.4.1.388.6.5.2.58
		kdcDBReplacedControl OBJECT-TYPE
			SYNTAX TruthValue
			MAX-ACCESS read-write
			STATUS current
			DESCRIPTION
				"Enable(true)/Disable(false) this trap.
				KDC DB replaced
				"
			::= { ccTrapInfos 58 }

		
--  1.3.6.1.4.1.388.6.5.2.59
		-- 1.3.6.1.4.1.388.6.5.2.59
		hsbStdbyAutoRevControl OBJECT-TYPE
			SYNTAX TruthValue
			MAX-ACCESS read-write
			STATUS current
			DESCRIPTION
				"Enable(true)/Disable(false) this trap.
				Standy auto-revert
				"
			::= { ccTrapInfos 59 }

		
--  1.3.6.1.4.1.388.6.5.2.60
		-- 1.3.6.1.4.1.388.6.5.2.60
		hsbPrimAutoRevControl OBJECT-TYPE
			SYNTAX TruthValue
			MAX-ACCESS read-write
			STATUS current
			DESCRIPTION
				"Enable(true)/Disable(false) this trap.
				Primary auto-revert
				"
			::= { ccTrapInfos 60 }

		
--  1.3.6.1.4.1.388.6.5.2.61
		-- 1.3.6.1.4.1.388.6.5.2.61
		acsErrorControl OBJECT-TYPE
			SYNTAX TruthValue
			MAX-ACCESS read-write
			STATUS current
			DESCRIPTION
				"Enable(true)/Disable(false) this trap.
				Auto channel select error
				"
			::= { ccTrapInfos 61 }

		
--  1.3.6.1.4.1.388.6.5.2.62
		-- 1.3.6.1.4.1.388.6.5.2.62
		eopActiveControl OBJECT-TYPE
			SYNTAX TruthValue
			MAX-ACCESS read-write
			STATUS current
			DESCRIPTION
				"Enable(true)/Disable(false) this trap.
				Emergency Policy [active]
				"
			::= { ccTrapInfos 62 }

		
--  1.3.6.1.4.1.388.6.5.2.63
		-- 1.3.6.1.4.1.388.6.5.2.63
		eopInactiveControl OBJECT-TYPE
			SYNTAX TruthValue
			MAX-ACCESS read-write
			STATUS current
			DESCRIPTION
				"Enable(true)/Disable(false) this trap.
				Emergency Policy [deactivated]
				"
			::= { ccTrapInfos 63 }

		
--  1.3.6.1.4.1.388.6.5.2.64
		-- 1.3.6.1.4.1.388.6.5.2.64
		debugEventControl OBJECT-TYPE
			SYNTAX TruthValue
			MAX-ACCESS read-only
			STATUS current
			DESCRIPTION
				"This trap is read only.
				Miscellaneous debug events
				"
			::= { ccTrapInfos 64 }

		
--  1.3.6.1.4.1.388.6.5.2.65
		-- 1.3.6.1.4.1.388.6.5.2.65
		hsbStartUpControl OBJECT-TYPE
			SYNTAX TruthValue
			MAX-ACCESS read-write
			STATUS current
			DESCRIPTION
				"Enable(true)/Disable(false) this trap.
				HSB Starts Up
				"
			::= { ccTrapInfos 65 }

		
--  1.3.6.1.4.1.388.6.5.2.66
		-- 1.3.6.1.4.1.388.6.5.2.66
		hsbPeerConnectControl OBJECT-TYPE
			SYNTAX TruthValue
			MAX-ACCESS read-write
			STATUS current
			DESCRIPTION
				"Enable(true)/Disable(false) this trap.
				HSB Peer Connect
				"
			::= { ccTrapInfos 66 }

		
--  1.3.6.1.4.1.388.6.5.2.67
		-- 1.3.6.1.4.1.388.6.5.2.67
		ccFanAndTempControl OBJECT-TYPE
			SYNTAX TruthValue
			MAX-ACCESS read-write
			STATUS current
			DESCRIPTION
				"Enable(true)/Disable(false) this trap.
				Fan and Temp Notification.
				"
			::= { ccTrapInfos 67 }

		
--  Mower: added.
-- 1.3.6.1.4.1.388.6.5.2.68
		-- 1.3.6.1.4.1.388.6.5.2.68
		ccAccessChangedControl OBJECT-TYPE
			SYNTAX TruthValue
			MAX-ACCESS read-write
			STATUS current
			DESCRIPTION
				"Enable(true)/Disable(false) this trap.
				Access Changed Notification.
				"
			::= { ccTrapInfos 68 }

		
--  Mower: added.
		-- 1.3.6.1.4.1.388.6.5.2.69
		tpcPowerReducedControl OBJECT-TYPE
			SYNTAX TruthValue
			MAX-ACCESS read-write
			STATUS current
			DESCRIPTION
				"Enable(true)/Disable(false) this trap.
				Radio power is reduced [TPC]
				"
			::= { ccTrapInfos 69 }

		
		-- 1.3.6.1.4.1.388.6.5.2.70
		dfsRadarDetectControl OBJECT-TYPE
			SYNTAX TruthValue
			MAX-ACCESS read-write
			STATUS current
			DESCRIPTION
				"Enable(true)/Disable(false) this trap.
				Radar is detected [DFS]
				"
			::= { ccTrapInfos 70 }

		
		-- 1.3.6.1.4.1.388.6.5.2.71
		dfsChannelSelectControl OBJECT-TYPE
			SYNTAX TruthValue
			MAX-ACCESS read-write
			STATUS current
			DESCRIPTION
				"Enable(true)/Disable(false) this trap.
				Channel selected to avoid radar [DFS]
				"
			::= { ccTrapInfos 71 }

		
		-- 1.3.6.1.4.1.388.6.5.2.72
		dfsChannelSwitchControl OBJECT-TYPE
			SYNTAX TruthValue
			MAX-ACCESS read-write
			STATUS current
			DESCRIPTION
				"Enable(true)/Disable(false) this trap.
				Switch to new channel [DFS]
				"
			::= { ccTrapInfos 72 }

		
		-- 1.3.6.1.4.1.388.6.5.2.73
		dfsChannelRevertControl OBJECT-TYPE
			SYNTAX TruthValue
			MAX-ACCESS read-write
			STATUS current
			DESCRIPTION
				"Enable(true)/Disable(false) this trap.
				Revert back to original channel [DFS]
				"
			::= { ccTrapInfos 73 }

		
		-- 1.3.6.1.4.1.388.6.5.2.74
		radioSuspendControl OBJECT-TYPE
			SYNTAX TruthValue
			MAX-ACCESS read-write
			STATUS current
			DESCRIPTION
				"Enable(true)/Disable(false) this trap.
				Radio is suspended - no available channels
				"
			::= { ccTrapInfos 74 }

		
		-- 1.3.6.1.4.1.388.6.5.2.75
		radioResumeControl OBJECT-TYPE
			SYNTAX TruthValue
			MAX-ACCESS read-write
			STATUS current
			DESCRIPTION
				"Enable(true)/Disable(false) this trap.
				Radio is resumed
				"
			::= { ccTrapInfos 75 }

		
		-- 1.3.6.1.4.1.388.6.5.2.76
		radioRandomChannelControl OBJECT-TYPE
			SYNTAX TruthValue
			MAX-ACCESS read-write
			STATUS current
			DESCRIPTION
				"Enable(true)/Disable(false) this trap.
				Radio is moved to random channel
				"
			::= { ccTrapInfos 76 }

		
		-- 1.3.6.1.4.1.388.6.5.2.77
		ccRapNewRogueApControl OBJECT-TYPE
			SYNTAX TruthValue
			MAX-ACCESS read-write
			STATUS current
			DESCRIPTION
				"Description."
			::= { ccTrapInfos 77 }

		
		-- 1.3.6.1.4.1.388.6.5.2.78
		ccRapNewApprovedApControl OBJECT-TYPE
			SYNTAX TruthValue
			MAX-ACCESS read-write
			STATUS current
			DESCRIPTION
				"Description."
			::= { ccTrapInfos 78 }

		
		-- 1.3.6.1.4.1.388.6.5.2.79
		ccTrapInfoWVPNAlert OBJECT-TYPE
			SYNTAX TruthValue
			MAX-ACCESS read-write
			STATUS current
			DESCRIPTION
				"Enable(1)/Disable(2) this trap.
				This trap is sent when there are any
				anomalies with the client/server certificates.
				"
			::= { ccTrapInfos 79 }

		
		-- 1.3.6.1.4.1.388.6.5.2.80
		ccTrapInfoWVPNInfo OBJECT-TYPE
			SYNTAX TruthValue
			MAX-ACCESS read-write
			STATUS current
			DESCRIPTION
				"Enable(1)/Disable(2) this trap.
				This trap is sent when there are any client/server
				configuration changes or connection establishments."
			::= { ccTrapInfos 80 }

		
		-- 1.3.6.1.4.1.388.6.5.2.81
		ccTrapInfoRadiusAcct OBJECT-TYPE
			SYNTAX TruthValue
			MAX-ACCESS read-write
			STATUS current
			DESCRIPTION
				"Enable(1)/Disable(2) the trap for Radius Accounting Log.
				This trap is not supported."
			::= { ccTrapInfos 81 }

		
		-- 1.3.6.1.4.1.388.6.5.2.82
		ccInfoRadiusServerControl OBJECT-TYPE
			SYNTAX TruthValue
			MAX-ACCESS read-write
			STATUS current
			DESCRIPTION
				"Enable(1)/Disable(2) this trap.
				"
			::= { ccTrapInfos 82 }

		
		-- 1.3.6.1.4.1.388.6.5.2.83
		configChangeUpdateControl OBJECT-TYPE
			SYNTAX TruthValue
			MAX-ACCESS read-write
			STATUS current
			DESCRIPTION
				"Enable(1)/Disable(2) this trap.
				This trap is sent whenever there is a configuration
				change in the switch.
				"
			::= { ccTrapInfos 83 }

		
		-- 1.3.6.1.4.1.388.6.5.2.84
		tunnelStatusChangedControl OBJECT-TYPE
			SYNTAX TruthValue
			MAX-ACCESS read-write
			STATUS current
			DESCRIPTION
				"Enable(1)/Disable(2) this trap.
				This trap is sent whenever there is a Tuneel Status Change"
			::= { ccTrapInfos 84 }

		
		-- 1.3.6.1.4.1.388.6.5.2.85
		tunnelUnknownProtocolControl OBJECT-TYPE
			SYNTAX TruthValue
			MAX-ACCESS read-write
			STATUS current
			DESCRIPTION
				"Enable(1)/Disable(2) this trap.
				This trap is sent whenever there is a non Ip packet received on Tunnel"
			::= { ccTrapInfos 85 }

		
		-- 1.3.6.1.4.1.388.6.5.2.86
		ccSumStatsApControl OBJECT-TYPE
			SYNTAX TruthValue
			MAX-ACCESS read-write
			STATUS current
			DESCRIPTION
				"Description."
			::= { ccTrapInfos 86 }

		
		-- 1.3.6.1.4.1.388.6.5.2.87
		ccSumStatsMuControl OBJECT-TYPE
			SYNTAX TruthValue
			MAX-ACCESS read-write
			STATUS current
			DESCRIPTION
				"Description."
			::= { ccTrapInfos 87 }

		
		-- 1.3.6.1.4.1.388.6.5.2.88
		ccSumStatsWlanControl OBJECT-TYPE
			SYNTAX TruthValue
			MAX-ACCESS read-write
			STATUS current
			DESCRIPTION
				"Description."
			::= { ccTrapInfos 88 }

		
		-- 1.3.6.1.4.1.388.6.5.2.89
		ccSumStatsSwitchControl OBJECT-TYPE
			SYNTAX TruthValue
			MAX-ACCESS read-write
			STATUS current
			DESCRIPTION
				"Description."
			::= { ccTrapInfos 89 }

		
		-- 1.3.6.1.4.1.388.6.5.2.90
		sensorConvertControl OBJECT-TYPE
			SYNTAX TruthValue
			MAX-ACCESS read-write
			STATUS current
			DESCRIPTION
				"Enable(1)/Disable(2) this trap.
				This trap is sent when 
				AP is converted to sensor"
			::= { ccTrapInfos 90 }

		
		-- 1.3.6.1.4.1.388.6.5.2.91
		sensorRevertControl OBJECT-TYPE
			SYNTAX TruthValue
			MAX-ACCESS read-write
			STATUS current
			DESCRIPTION
				"Enable(1)/Disable(2) this trap.
				This trap is sent when Sensor is reverted back to AP"
			::= { ccTrapInfos 91 }

		
		-- 1.3.6.1.4.1.388.6.5.2.92
		sensorFailureControl OBJECT-TYPE
			SYNTAX TruthValue
			MAX-ACCESS read-write
			STATUS current
			DESCRIPTION
				"Enable(1)/Disable(2) this trap.
				This trap is sent when Failed to communicate to a sensor"
			::= { ccTrapInfos 92 }

		
		-- 1.3.6.1.4.1.388.6.5.2.93
		sensorOfflineControl OBJECT-TYPE
			SYNTAX TruthValue
			MAX-ACCESS read-write
			STATUS current
			DESCRIPTION
				"Enable(1)/Disable(2) this trap.
				This trap is sent when Sensor is no longer responding to ping"
			::= { ccTrapInfos 93 }

		
--  1.3.6.1.4.1.388.6.5.3
		-- 1.3.6.1.4.1.388.6.5.3
		symbolCCTraps OBJECT IDENTIFIER ::= { symbolCCFault 3 }

		
--  ??Mower: this NOTIFICATION, and all others in this group 
-- have been slightly re-defined since v1.2 to include a 
-- string as an included var-bind: "ccTargetTrapString", 
-- which I am told is in the actual NOTIFICATION.
-- 
-- I created this DisplayString as 
-- accessible-for-notify at an arbitrary OID.  I need someone
-- to tell me the actual OID for this string.
-- 
-- I am told that the string actually has the same OID as the
-- notification itself.  This is wrong.
-- 
-- 1.3.6.1.4.1.388.6.5.3.1
		-- 1.3.6.1.4.1.388.6.5.3.1
		ccTrapLowFlashSpace NOTIFICATION-TYPE
			OBJECTS { ccTargetTrapString }
			STATUS current
			DESCRIPTION 
				"Low flash space on switch
				
				This is a 1.1.4.30SP1 trap and corresponds to the 1.2 event -
				sysLowFlashSpace "
			::= { symbolCCTraps 1 }

		
--  1.3.6.1.4.1.388.6.5.3.3
		-- 1.3.6.1.4.1.388.6.5.3.3
		ccTrapNicDropping NOTIFICATION-TYPE
			OBJECTS { ccTargetTrapString }
			STATUS current
			DESCRIPTION 
				"Ether port disconnected
				
				This is a 1.1.4.30SP1 trap and corresponds to the 1.2 event -
				etherDisconnect "
			::= { symbolCCTraps 3 }

		
--  1.3.6.1.4.1.388.6.5.3.6
		-- 1.3.6.1.4.1.388.6.5.3.6
		ccTrapAPMUMaxExceed NOTIFICATION-TYPE
			OBJECTS { ccTargetTrapString }
			STATUS current
			DESCRIPTION 
				"AP max MU count reached
				
				This is a 1.1.4.30SP1 trap and corresponds to the 1.2 event -
				apMaxMU "
			::= { symbolCCTraps 6 }

		
--  1.3.6.1.4.1.388.6.5.3.7
		-- 1.3.6.1.4.1.388.6.5.3.7
		ccTrapWLANMUMaxExceed NOTIFICATION-TYPE
			OBJECTS { ccTargetTrapString }
			STATUS current
			DESCRIPTION 
				"WLAN max MU count reached
				
				This is a 1.1.4.30SP1 trap and corresponds to the 1.2 event -
				wlanMaxMUCount "
			::= { symbolCCTraps 7 }

		
--  1.3.6.1.4.1.388.6.5.3.8
		-- 1.3.6.1.4.1.388.6.5.3.8
		ccTrapAPDetected NOTIFICATION-TYPE
			OBJECTS { ccTargetTrapString }
			STATUS current
			DESCRIPTION 
				"AP detected
				
				This is a 1.1.4.30SP1 trap and corresponds to the 1.2 event -
				apDetected "
			::= { symbolCCTraps 8 }

		
--  1.3.6.1.4.1.388.6.5.3.9
		-- 1.3.6.1.4.1.388.6.5.3.9
		ccTrapAPAdopted NOTIFICATION-TYPE
			OBJECTS { ccTargetTrapString }
			STATUS current
			DESCRIPTION 
				"AP status [adopted]
				
				This is a 1.1.4.30SP1 trap and corresponds to the 1.2 event -
				apAdopted "
			::= { symbolCCTraps 9 }

		
--  1.3.6.1.4.1.388.6.5.3.10
		-- 1.3.6.1.4.1.388.6.5.3.10
		ccTrapAPReset NOTIFICATION-TYPE
			OBJECTS { ccTargetTrapString }
			STATUS current
			DESCRIPTION 
				"AP status [reset]
				
				This is a 1.1.4.30SP1 trap and corresponds to the 1.2 event -
				apReset "
			::= { symbolCCTraps 10 }

		
--  1.3.6.1.4.1.388.6.5.3.11
		-- 1.3.6.1.4.1.388.6.5.3.11
		ccTrapAPUnavailable NOTIFICATION-TYPE
			OBJECTS { ccTargetTrapString }
			STATUS current
			DESCRIPTION 
				"AP status [offline]
				
				This is a 1.1.4.30SP1 trap and corresponds to the 1.2 event -
				apOffline "
			::= { symbolCCTraps 11 }

		
--  1.3.6.1.4.1.388.6.5.3.12
		-- 1.3.6.1.4.1.388.6.5.3.12
		ccTrapAPAlert NOTIFICATION-TYPE
			OBJECTS { ccTargetTrapString }
			STATUS current
			DESCRIPTION 
				"AP status [alert]
				
				This is a 1.1.4.30SP1 trap and corresponds to the 1.2 event -
				apAlert "
			::= { symbolCCTraps 12 }

		
--  1.3.6.1.4.1.388.6.5.3.13
		-- 1.3.6.1.4.1.388.6.5.3.13
		ccTrapUserAuthFail NOTIFICATION-TYPE
			OBJECTS { ccTargetTrapString }
			STATUS current
			DESCRIPTION 
				"Mgt user auth rejected
				
				This is a 1.1.4.30SP1 trap and corresponds to the 1.2 event -
				userAuthRejected "
			::= { symbolCCTraps 13 }

		
--  1.3.6.1.4.1.388.6.5.3.14
		-- 1.3.6.1.4.1.388.6.5.3.14
		ccTrapRadiusAuthFail NOTIFICATION-TYPE
			OBJECTS { ccTargetTrapString }
			STATUS current
			DESCRIPTION 
				"Mgt user auth failed  [radius]
				
				This is a 1.1.4.30SP1 trap and corresponds to the 1.2 event -
				userAuthFail "
			::= { symbolCCTraps 14 }

		
--  1.3.6.1.4.1.388.6.5.3.16
		-- 1.3.6.1.4.1.388.6.5.3.16
		ccTrapACLViolation NOTIFICATION-TYPE
			OBJECTS { ccTargetTrapString }
			STATUS current
			DESCRIPTION 
				"MU assoc failed [ACL violation]
				
				This is a 1.1.4.30SP1 trap and corresponds to the 1.2 event -
				muAssocFailACL "
			::= { symbolCCTraps 16 }

		
--  1.3.6.1.4.1.388.6.5.3.18
		-- 1.3.6.1.4.1.388.6.5.3.18
		ccTrapDenyAPAdoption NOTIFICATION-TYPE
			OBJECTS { ccTargetTrapString }
			STATUS current
			DESCRIPTION 
				"AP adopt failure [general]
				
				This is a 1.1.4.30SP1 trap and corresponds to the 1.2 event -
				apAdoptFail "
			::= { symbolCCTraps 18 }

		
--  1.3.6.1.4.1.388.6.5.3.20
		-- 1.3.6.1.4.1.388.6.5.3.20
		ccTrapHsbPrimaryNoHeartbeat NOTIFICATION-TYPE
			OBJECTS { ccTargetTrapString }
			STATUS current
			DESCRIPTION 
				"Primary lost heartbeat
				
				This is a 1.1.4.30SP1 trap and corresponds to the 1.2 event -
				hsbPrimHBLoss "
			::= { symbolCCTraps 20 }

		
--  1.3.6.1.4.1.388.6.5.3.21
		-- 1.3.6.1.4.1.388.6.5.3.21
		ccTrapHsbStandbyEntersFailover NOTIFICATION-TYPE
			OBJECTS { ccTargetTrapString }
			STATUS current
			DESCRIPTION 
				"Standby active
				
				This is a 1.1.4.30SP1 trap and corresponds to the 1.2 event -
				hsbFailover "
			::= { symbolCCTraps 21 }

		
--  1.3.6.1.4.1.388.6.5.3.22
		-- 1.3.6.1.4.1.388.6.5.3.22
		ccTrapHsbPrimaryFailedResetting NOTIFICATION-TYPE
			OBJECTS { ccTargetTrapString }
			STATUS current
			DESCRIPTION 
				"Primary internal failure [reset]
				
				This is a 1.1.4.30SP1 trap and corresponds to the 1.2 event -
				hsbPrimFail "
			::= { symbolCCTraps 22 }

		
--  1.3.6.1.4.1.388.6.5.3.23
		-- 1.3.6.1.4.1.388.6.5.3.23
		ccTrapHsbStandbyFailedResetting NOTIFICATION-TYPE
			OBJECTS { ccTargetTrapString }
			STATUS current
			DESCRIPTION 
				"Standby internal failure [reset]
				
				This is a 1.1.4.30SP1 trap and corresponds to the 1.2 event -
				hsbStdbyFail "
			::= { symbolCCTraps 23 }

		
--  1.3.6.1.4.1.388.6.5.3.24
		-- 1.3.6.1.4.1.388.6.5.3.24
		ccTrapKDCUserAuthFail NOTIFICATION-TYPE
			OBJECTS { ccTargetTrapString }
			STATUS current
			DESCRIPTION 
				"MU Kerberos auth failed
				
				This is a 1.1.4.30SP1 trap and corresponds to the 1.2 event -
				muKDCAuthFail "
			::= { symbolCCTraps 24 }

		
--  1.3.6.1.4.1.388.6.5.3.25
		-- 1.3.6.1.4.1.388.6.5.3.25
		ccTrapKDCPropagationFail NOTIFICATION-TYPE
			OBJECTS { ccTargetTrapString }
			STATUS current
			DESCRIPTION 
				"KDC propagation failure
				
				This is a 1.1.4.30SP1 trap and corresponds to the 1.2 event -
				kdcPropFail "
			::= { symbolCCTraps 25 }

		
--  1.3.6.1.4.1.388.6.5.3.26
		-- 1.3.6.1.4.1.388.6.5.3.26
		ccTrapHighDecryptFail NOTIFICATION-TYPE
			OBJECTS { ccTargetTrapString }
			STATUS current
			DESCRIPTION 
				"MU TKIP [decrypt failure]
				
				This is a 1.1.4.30SP1 trap and corresponds to the 1.2 event -
				muTKIPDecyptFail "
			::= { symbolCCTraps 26 }

		
--  1.3.6.1.4.1.388.6.5.3.27
		-- 1.3.6.1.4.1.388.6.5.3.27
		ccTrapHighReplyFail NOTIFICATION-TYPE
			OBJECTS { ccTargetTrapString }
			STATUS current
			DESCRIPTION 
				"MU TKIP [replay failure]
				
				This is a 1.1.4.30SP1 trap and corresponds to the 1.2 event -
				muTKIPReplayFail "
			::= { symbolCCTraps 27 }

		
--  1.3.6.1.4.1.388.6.5.3.28
		-- 1.3.6.1.4.1.388.6.5.3.28
		ccTrapTKIPMICFail NOTIFICATION-TYPE
			OBJECTS { ccTargetTrapString }
			STATUS current
			DESCRIPTION 
				"MU TKIP [MIC error]
				
				This is a 1.1.4.30SP1 trap and corresponds to the 1.2 event -
				muTKIPMicError "
			::= { symbolCCTraps 28 }

		
--  1.3.6.1.4.1.388.6.5.3.29
		-- 1.3.6.1.4.1.388.6.5.3.29
		ccTrapWPACounterMeasureStart NOTIFICATION-TYPE
			OBJECTS { ccTargetTrapString }
			STATUS current
			DESCRIPTION 
				"WPA counter-measures [active]
				
				This is a 1.1.4.30SP1 trap and corresponds to the 1.2 event -
				wpaCntrMsrAct "
			::= { symbolCCTraps 29 }

		
--  1.3.6.1.4.1.388.6.5.3.31
		-- 1.3.6.1.4.1.388.6.5.3.31
		licenseChanged NOTIFICATION-TYPE
			OBJECTS { ccTargetTrapString }
			STATUS current
			DESCRIPTION 
				"License number change
				
				"
			::= { symbolCCTraps 31 }

		
--  1.3.6.1.4.1.388.6.5.3.32
		-- 1.3.6.1.4.1.388.6.5.3.32
		clockChanged NOTIFICATION-TYPE
			OBJECTS { ccTargetTrapString }
			STATUS current
			DESCRIPTION 
				"Clock change
				
				"
			::= { symbolCCTraps 32 }

		
--  1.3.6.1.4.1.388.6.5.3.33
		-- 1.3.6.1.4.1.388.6.5.3.33
		pktDiscWrongNIC NOTIFICATION-TYPE
			OBJECTS { ccTargetTrapString }
			STATUS current
			DESCRIPTION 
				"Packet discard [wrong NIC]
				
				"
			::= { symbolCCTraps 33 }

		
--  1.3.6.1.4.1.388.6.5.3.34
		-- 1.3.6.1.4.1.388.6.5.3.34
		pktDiscWrongVLAN NOTIFICATION-TYPE
			OBJECTS { ccTargetTrapString }
			STATUS current
			DESCRIPTION 
				"Packet discard [wrong VLAN]
				
				"
			::= { symbolCCTraps 34 }

		
--  1.3.6.1.4.1.388.6.5.3.35
		-- 1.3.6.1.4.1.388.6.5.3.35
		apAdoptFailPol NOTIFICATION-TYPE
			OBJECTS { ccTargetTrapString }
			STATUS current
			DESCRIPTION 
				"AP adopt failure [policy disallow]
				
				"
			::= { symbolCCTraps 35 }

		
--  1.3.6.1.4.1.388.6.5.3.36
		-- 1.3.6.1.4.1.388.6.5.3.36
		apAdoptFailACL NOTIFICATION-TYPE
			OBJECTS { ccTargetTrapString }
			STATUS current
			DESCRIPTION 
				"AP adopt failure [acl disallow]
				
				"
			::= { symbolCCTraps 36 }

		
--  1.3.6.1.4.1.388.6.5.3.37
		-- 1.3.6.1.4.1.388.6.5.3.37
		apAdoptFailLimit NOTIFICATION-TYPE
			OBJECTS { ccTargetTrapString }
			STATUS current
			DESCRIPTION 
				"AP adopt failure [limit exceeded]
				
				"
			::= { symbolCCTraps 37 }

		
--  1.3.6.1.4.1.388.6.5.3.38
		-- 1.3.6.1.4.1.388.6.5.3.38
		apAdoptFailLic NOTIFICATION-TYPE
			OBJECTS { ccTargetTrapString }
			STATUS current
			DESCRIPTION 
				"AP adopt failure [license disallow]
				
				"
			::= { symbolCCTraps 38 }

		
--  1.3.6.1.4.1.388.6.5.3.39
		-- 1.3.6.1.4.1.388.6.5.3.39
		apAdoptFailNoImg NOTIFICATION-TYPE
			OBJECTS { ccTargetTrapString }
			STATUS current
			DESCRIPTION 
				"AP adopt failure [no image]
				
				"
			::= { symbolCCTraps 39 }

		
--  1.3.6.1.4.1.388.6.5.3.40
		-- 1.3.6.1.4.1.388.6.5.3.40
		apCfgFailESS NOTIFICATION-TYPE
			OBJECTS { ccTargetTrapString }
			STATUS current
			DESCRIPTION 
				"AP config failed [wrong ESS]
				
				"
			::= { symbolCCTraps 40 }

		
--  1.3.6.1.4.1.388.6.5.3.41
		-- 1.3.6.1.4.1.388.6.5.3.41
		devDropInfoMsg NOTIFICATION-TYPE
			OBJECTS { ccTargetTrapString }
			STATUS current
			DESCRIPTION 
				"Device msg dropped [info]
				
				"
			::= { symbolCCTraps 41 }

		
--  1.3.6.1.4.1.388.6.5.3.42
		-- 1.3.6.1.4.1.388.6.5.3.42
		devdropLoadmeMsg NOTIFICATION-TYPE
			OBJECTS { ccTargetTrapString }
			STATUS current
			DESCRIPTION 
				"Device msg dropped [loadme]
				
				"
			::= { symbolCCTraps 42 }

		
--  1.3.6.1.4.1.388.6.5.3.43
		-- 1.3.6.1.4.1.388.6.5.3.43
		etherConnect NOTIFICATION-TYPE
			OBJECTS { ccTargetTrapString }
			STATUS current
			DESCRIPTION 
				"Ether port connected
				
				"
			::= { symbolCCTraps 43 }

		
--  1.3.6.1.4.1.388.6.5.3.44
		-- 1.3.6.1.4.1.388.6.5.3.44
		muAssocFail NOTIFICATION-TYPE
			OBJECTS { ccTargetTrapString }
			STATUS current
			DESCRIPTION 
				"MU assoc failed
				
				"
			::= { symbolCCTraps 44 }

		
--  1.3.6.1.4.1.388.6.5.3.45
		-- 1.3.6.1.4.1.388.6.5.3.45
		muAssocOK NOTIFICATION-TYPE
			OBJECTS { ccTargetTrapString }
			STATUS current
			DESCRIPTION 
				"MU status [associated]
				
				"
			::= { symbolCCTraps 45 }

		
--  1.3.6.1.4.1.388.6.5.3.46
		-- 1.3.6.1.4.1.388.6.5.3.46
		muRoamed NOTIFICATION-TYPE
			OBJECTS { ccTargetTrapString }
			STATUS current
			DESCRIPTION 
				"MU status [roamed]
				
				"
			::= { symbolCCTraps 46 }

		
--  1.3.6.1.4.1.388.6.5.3.47
		-- 1.3.6.1.4.1.388.6.5.3.47
		muDisassoc NOTIFICATION-TYPE
			OBJECTS { ccTargetTrapString }
			STATUS current
			DESCRIPTION 
				"MU status [disassociated]
				
				"
			::= { symbolCCTraps 47 }

		
--  1.3.6.1.4.1.388.6.5.3.48
		-- 1.3.6.1.4.1.388.6.5.3.48
		muEAPAuthFail NOTIFICATION-TYPE
			OBJECTS { ccTargetTrapString }
			STATUS current
			DESCRIPTION 
				"MU EAP auth failed
				
				"
			::= { symbolCCTraps 48 }

		
--  1.3.6.1.4.1.388.6.5.3.49
		-- 1.3.6.1.4.1.388.6.5.3.49
		muEAPAuthOK NOTIFICATION-TYPE
			OBJECTS { ccTargetTrapString }
			STATUS current
			DESCRIPTION 
				"MU EAP auth success
				
				"
			::= { symbolCCTraps 49 }

		
--  1.3.6.1.4.1.388.6.5.3.50
		-- 1.3.6.1.4.1.388.6.5.3.50
		muKDCAuthOK NOTIFICATION-TYPE
			OBJECTS { ccTargetTrapString }
			STATUS current
			DESCRIPTION 
				"MU Kerberos auth success
				
				"
			::= { symbolCCTraps 50 }

		
--  1.3.6.1.4.1.388.6.5.3.51
		-- 1.3.6.1.4.1.388.6.5.3.51
		wlanAuthOK NOTIFICATION-TYPE
			OBJECTS { ccTargetTrapString }
			STATUS current
			DESCRIPTION 
				"WLAN auth success
				
				"
			::= { symbolCCTraps 51 }

		
--  1.3.6.1.4.1.388.6.5.3.52
		-- 1.3.6.1.4.1.388.6.5.3.52
		wlanAuthFail NOTIFICATION-TYPE
			OBJECTS { ccTargetTrapString }
			STATUS current
			DESCRIPTION 
				"WLAN auth failed
				
				"
			::= { symbolCCTraps 52 }

		
--  1.3.6.1.4.1.388.6.5.3.53
		-- 1.3.6.1.4.1.388.6.5.3.53
		userAuthOK NOTIFICATION-TYPE
			OBJECTS { ccTargetTrapString }
			STATUS current
			DESCRIPTION 
				"Mgt user auth success [radius]
				
				"
			::= { symbolCCTraps 53 }

		
--  1.3.6.1.4.1.388.6.5.3.54
		-- 1.3.6.1.4.1.388.6.5.3.54
		radiusSrvTimeout NOTIFICATION-TYPE
			OBJECTS { ccTargetTrapString }
			STATUS current
			DESCRIPTION 
				"Radius server timeout
				
				"
			::= { symbolCCTraps 54 }

		
--  1.3.6.1.4.1.388.6.5.3.55
		-- 1.3.6.1.4.1.388.6.5.3.55
		kdcPrincAdd NOTIFICATION-TYPE
			OBJECTS { ccTargetTrapString }
			STATUS current
			DESCRIPTION 
				"KDC user [added]
				
				"
			::= { symbolCCTraps 55 }

		
--  1.3.6.1.4.1.388.6.5.3.56
		-- 1.3.6.1.4.1.388.6.5.3.56
		kdcPrincChgd NOTIFICATION-TYPE
			OBJECTS { ccTargetTrapString }
			STATUS current
			DESCRIPTION 
				"KDC user [changed]
				
				"
			::= { symbolCCTraps 56 }

		
--  1.3.6.1.4.1.388.6.5.3.57
		-- 1.3.6.1.4.1.388.6.5.3.57
		kdcPrincDel NOTIFICATION-TYPE
			OBJECTS { ccTargetTrapString }
			STATUS current
			DESCRIPTION 
				"KDC user [deleted]
				
				"
			::= { symbolCCTraps 57 }

		
--  1.3.6.1.4.1.388.6.5.3.58
		-- 1.3.6.1.4.1.388.6.5.3.58
		kdcDBReplaced NOTIFICATION-TYPE
			OBJECTS { ccTargetTrapString }
			STATUS current
			DESCRIPTION 
				"KDC DB replaced
				
				"
			::= { symbolCCTraps 58 }

		
--  1.3.6.1.4.1.388.6.5.3.59
		-- 1.3.6.1.4.1.388.6.5.3.59
		hsbStdbyAutoRev NOTIFICATION-TYPE
			OBJECTS { ccTargetTrapString }
			STATUS current
			DESCRIPTION 
				"Standy auto-revert
				
				"
			::= { symbolCCTraps 59 }

		
--  1.3.6.1.4.1.388.6.5.3.60
		-- 1.3.6.1.4.1.388.6.5.3.60
		hsbPrimAutoRev NOTIFICATION-TYPE
			OBJECTS { ccTargetTrapString }
			STATUS current
			DESCRIPTION 
				"Primary auto-revert
				
				"
			::= { symbolCCTraps 60 }

		
--  1.3.6.1.4.1.388.6.5.3.61
		-- 1.3.6.1.4.1.388.6.5.3.61
		acsError NOTIFICATION-TYPE
			OBJECTS { ccTargetTrapString }
			STATUS current
			DESCRIPTION 
				"Auto channel select error
				
				"
			::= { symbolCCTraps 61 }

		
--  1.3.6.1.4.1.388.6.5.3.62
		-- 1.3.6.1.4.1.388.6.5.3.62
		eopActive NOTIFICATION-TYPE
			OBJECTS { ccTargetTrapString }
			STATUS current
			DESCRIPTION 
				"Emergency Policy [active]
				
				"
			::= { symbolCCTraps 62 }

		
--  1.3.6.1.4.1.388.6.5.3.63
		-- 1.3.6.1.4.1.388.6.5.3.63
		eopInactive NOTIFICATION-TYPE
			OBJECTS { ccTargetTrapString }
			STATUS current
			DESCRIPTION 
				"Emergency Policy [deactivated]
				
				"
			::= { symbolCCTraps 63 }

		
--  1.3.6.1.4.1.388.6.5.3.64
		-- 1.3.6.1.4.1.388.6.5.3.64
		debugEvent NOTIFICATION-TYPE
			OBJECTS { ccTargetTrapString }
			STATUS current
			DESCRIPTION 
				"Miscellaneous debug events
				
				"
			::= { symbolCCTraps 64 }

		
--  1.3.6.1.4.1.388.6.5.3.65
		-- 1.3.6.1.4.1.388.6.5.3.65
		hsbStartUp NOTIFICATION-TYPE
			OBJECTS { ccTargetTrapString }
			STATUS current
			DESCRIPTION 
				"HSB Starts Up
				
				"
			::= { symbolCCTraps 65 }

		
--  1.3.6.1.4.1.388.6.5.3.66
		-- 1.3.6.1.4.1.388.6.5.3.66
		hsbPeerConnect NOTIFICATION-TYPE
			OBJECTS { ccTargetTrapString }
			STATUS current
			DESCRIPTION 
				"HSB Peer Connect
				
				"
			::= { symbolCCTraps 66 }

		
--  1.3.6.1.4.1.388.6.5.3.67
		-- 1.3.6.1.4.1.388.6.5.3.67
		ccFanAndTempNotification NOTIFICATION-TYPE
			OBJECTS { ccTargetTrapString }
			STATUS current
			DESCRIPTION 
				"Notification sent if the given threshold has been exceeded."
			::= { symbolCCTraps 67 }

		
--  Mower: added.
-- 1.3.6.1.4.1.388.6.5.3.68
		-- 1.3.6.1.4.1.388.6.5.3.68
		ccAccessChangedNotification NOTIFICATION-TYPE
			OBJECTS { ccTargetTrapString }
			STATUS current
			DESCRIPTION 
				"This notification is sent if the permitted methods of
				access has changed.  Note that each change to the access
				methods permitted generates a separate notification."
			::= { symbolCCTraps 68 }

		
--  Mower: added.
-- 
-- Take caution when implementing this notification: be
-- careful to not disable the SNMP deamon before sending the
-- notification.  Likewise, you may need to ensure the SNMP
-- deamon is up and stable before immediately sending this
-- notification.
-- 
		-- 1.3.6.1.4.1.388.6.5.3.69
		tpcPowerReduced NOTIFICATION-TYPE
			OBJECTS { ccTargetTrapString }
			STATUS current
			DESCRIPTION 
				"Radio power is reduced [TPC]"
			::= { symbolCCTraps 69 }

		
		-- 1.3.6.1.4.1.388.6.5.3.70
		dfsRadarDetect NOTIFICATION-TYPE
			OBJECTS { ccTargetTrapString }
			STATUS current
			DESCRIPTION 
				"Radar is detected [DFS]"
			::= { symbolCCTraps 70 }

		
		-- 1.3.6.1.4.1.388.6.5.3.71
		dfsChannelSelect NOTIFICATION-TYPE
			OBJECTS { ccTargetTrapString }
			STATUS current
			DESCRIPTION 
				"Channel selected to avoid radar [DFS]"
			::= { symbolCCTraps 71 }

		
		-- 1.3.6.1.4.1.388.6.5.3.72
		dfsChannelSwitch NOTIFICATION-TYPE
			OBJECTS { ccTargetTrapString }
			STATUS current
			DESCRIPTION 
				"Switch to new channel [DFS]"
			::= { symbolCCTraps 72 }

		
		-- 1.3.6.1.4.1.388.6.5.3.73
		dfsChannelRevert NOTIFICATION-TYPE
			OBJECTS { ccTargetTrapString }
			STATUS current
			DESCRIPTION 
				"Revert back to original channel [DFS]"
			::= { symbolCCTraps 73 }

		
		-- 1.3.6.1.4.1.388.6.5.3.74
		radioSuspend NOTIFICATION-TYPE
			OBJECTS { ccTargetTrapString }
			STATUS current
			DESCRIPTION 
				"Radio is suspended - no available channels"
			::= { symbolCCTraps 74 }

		
		-- 1.3.6.1.4.1.388.6.5.3.75
		radioResume NOTIFICATION-TYPE
			OBJECTS { ccTargetTrapString }
			STATUS current
			DESCRIPTION 
				"Radio is resumed"
			::= { symbolCCTraps 75 }

		
		-- 1.3.6.1.4.1.388.6.5.3.76
		radioRandomChannel NOTIFICATION-TYPE
			OBJECTS { ccTargetTrapString }
			STATUS current
			DESCRIPTION 
				"Radio is moved to random channel"
			::= { symbolCCTraps 76 }

		
		-- 1.3.6.1.4.1.388.6.5.3.77
		ccRapNewRogueAp NOTIFICATION-TYPE
			OBJECTS { ccTargetTrapString }
			STATUS current
			DESCRIPTION 
				"A new AP has been heard that was NOT authorized.
				"
			::= { symbolCCTraps 77 }

		
		-- 1.3.6.1.4.1.388.6.5.3.78
		ccRapNewApprovedAp NOTIFICATION-TYPE
			OBJECTS { ccTargetTrapString }
			STATUS current
			DESCRIPTION 
				"A new AP has been heard that was in some manner
				 	authorized.
				"
			::= { symbolCCTraps 78 }

		
		-- 1.3.6.1.4.1.388.6.5.3.79
		ccTrapWVPNAlert NOTIFICATION-TYPE
			OBJECTS { ccTargetTrapString }
			STATUS current
			DESCRIPTION 
				"ccTrapWVPNAlert trap.
				This trap is sent when there are any anomalies with
				the client/server certificates."
			::= { symbolCCTraps 79 }

		
		-- 1.3.6.1.4.1.388.6.5.3.80
		ccTrapWVPNInfo NOTIFICATION-TYPE
			OBJECTS { ccTargetTrapString }
			STATUS current
			DESCRIPTION 
				"ccTrapWVPNInfo Trap.
				This trap is sent when there are any client/server
				configuration changes or connection establishments."
			::= { symbolCCTraps 80 }

		
		-- 1.3.6.1.4.1.388.6.5.3.81
		ccTrapInfoRadiusAcctInfo NOTIFICATION-TYPE
			OBJECTS { ccTargetTrapString }
			STATUS current
			DESCRIPTION 
				"ccTrapInfoRadiusAcct: This trap is not supported.
				"
			::= { symbolCCTraps 81 }

		
		-- 1.3.6.1.4.1.388.6.5.3.82
		ccInfoRadiusServer NOTIFICATION-TYPE
			OBJECTS { ccTargetTrapString }
			STATUS current
			DESCRIPTION 
				"This trap is sent when ccRadiusServer
				is enabled/disabled or it's configuration 
				changes are saved."
			::= { symbolCCTraps 82 }

		
		-- 1.3.6.1.4.1.388.6.5.3.83
		configChangeUpdate NOTIFICATION-TYPE
			OBJECTS { ccTargetTrapString }
			STATUS current
			DESCRIPTION 
				"A trap for every configuration change happening
				in the switch.
				"
			::= { symbolCCTraps 83 }

		
		-- 1.3.6.1.4.1.388.6.5.3.84
		tunnelStatusChanged NOTIFICATION-TYPE
			OBJECTS { ccTargetTrapString }
			STATUS current
			DESCRIPTION 
				"This trap is sent whenever there is a Tuneel Status Change"
			::= { symbolCCTraps 84 }

		
		-- 1.3.6.1.4.1.388.6.5.3.85
		tunnelUnknownProtocol NOTIFICATION-TYPE
			OBJECTS { ccTargetTrapString }
			STATUS current
			DESCRIPTION 
				"This trap is sent whenever there is a non Ip packet received on Tunnel"
			::= { symbolCCTraps 85 }

		
		-- 1.3.6.1.4.1.388.6.5.3.86
		ccSumStatsAp NOTIFICATION-TYPE
			OBJECTS { ccTargetTrapString }
			STATUS current
			DESCRIPTION 
				"A summary statistic has crossed the prescribed threshold 
				by a Portal.
				 	
				Example:
				Threshold #%s1 of value %s2 (units:%s3) has been crossed
				by Portal index=%s4 with MAC=%s5."
			::= { symbolCCTraps 86 }

		
		-- 1.3.6.1.4.1.388.6.5.3.87
		ccSumStatsMu NOTIFICATION-TYPE
			OBJECTS { ccTargetTrapString }
			STATUS current
			DESCRIPTION 
				"A summary statistic has crossed the prescribed threshold 
				by an MU.
					
				Example:
				Threshold '%s1' of value %s2 (units:%s3) has been crossed
				by MU MAC=%s4 with IP-addr=%s5."
			::= { symbolCCTraps 87 }

		
		-- 1.3.6.1.4.1.388.6.5.3.88
		ccSumStatsWlan NOTIFICATION-TYPE
			OBJECTS { ccTargetTrapString }
			STATUS current
			DESCRIPTION 
				"A summary statistic has crossed the prescribed threshold 
				by a WLAN.
				 	
				Example:
				Threshold #%s1 of value %s2 (units:%s3) has been crossed
				by WLAN index=%s4 with name=%s5.
				"
			::= { symbolCCTraps 88 }

		
		-- 1.3.6.1.4.1.388.6.5.3.89
		ccSumStatsSwitch NOTIFICATION-TYPE
			OBJECTS { ccTargetTrapString }
			STATUS current
			DESCRIPTION 
				"A summary statistic has crossed the prescribed threshold 
				by the entire Switch.
				 	
				Example:
				Threshold %s1 of value %s2 (units:%s3) has been crossed
				by the entire switch.
				"
			::= { symbolCCTraps 89 }

		
		-- 1.3.6.1.4.1.388.6.5.3.90
		sensorConvert NOTIFICATION-TYPE
			OBJECTS { ccTargetTrapString }
			STATUS current
			DESCRIPTION 
				"Enable(1)/Disable(2) this trap.
				This trap is sent when AP is converted to sensor"
			::= { symbolCCTraps 90 }

		
		-- 1.3.6.1.4.1.388.6.5.3.91
		sensorRevert NOTIFICATION-TYPE
			OBJECTS { ccTargetTrapString }
			STATUS current
			DESCRIPTION 
				"Enable(1)/Disable(2) this trap.
				This trap is sent when Sensor is reverted back to AP"
			::= { symbolCCTraps 91 }

		
		-- 1.3.6.1.4.1.388.6.5.3.92
		sensorFailure NOTIFICATION-TYPE
			OBJECTS { ccTargetTrapString }
			STATUS current
			DESCRIPTION 
				"Enable(1)/Disable(2) this trap.
				This trap is sent when Failed to communicate to a sensor"
			::= { symbolCCTraps 92 }

		
		-- 1.3.6.1.4.1.388.6.5.3.93
		sensorOffline NOTIFICATION-TYPE
			OBJECTS { ccTargetTrapString }
			STATUS current
			DESCRIPTION 
				"Enable(1)/Disable(2) this trap.
				This trap is sent when Sensor is no longer responding to ping"
			::= { symbolCCTraps 93 }

		
		-- 1.3.6.1.4.1.388.6.6
		symbolCCNewInV1dot2dot5 OBJECT IDENTIFIER ::= { symbolCC 6 }
-- This group contains MIB variables that are new as of v1.3.
		
-- MIB scalars used to identify the different version info
-- contained within sysDescr.
		-- 1.3.6.1.4.1.388.6.6.1
		ccIdentfication OBJECT IDENTIFIER ::= { symbolCCNewInV1dot2dot5 1 }
-- This group contains MIB variables that identify the versions
-- of various components of the switch.
-- 
-- sysDescr is ALSO overloaded for this purpose.  The 'terms'
-- reported in sysDescr occur in the same order as the MIB
-- values in this group.
-- 
-- (Separate MIB scalars report each term separately to make
-- it easy for SNMP scripts to find the given information.  The
-- infomation is also retained in an overloaded sysDescr since
-- many NMS platforms show this one value prominently).
-- 
-- In sysDescr, each term is marked with a 'label':
--   'HW=', 'FW=', 'SW=', 'MIB=', 'CLI=', 'XML='.
-- Each label in sysDescr is followed, (without a space), by
-- a sub-string (which itself contains no spaces), that 
-- describes the version of that entity.  Each term, (except 
-- the last), is followed by a ',' and a space before the next
-- term.
-- 
-- If a device does not have a particular item, (for
-- example no XML interface), that term and its lablel 
-- will be entirely missing from sysDescr, and the 
-- corresponding MIB scalar will be either a zero-length 
-- string, or will return a NO-SUCH.
-- 
-- The MIB version substring is a two-digit number (with a
-- leading zero if needed), followed by a lower-case letter.  
-- The letter is increased if only comments or descriptions 
-- are changed.  If any other change is made, the number 
-- increases.
-- 
-- The CLI version substring is a three-digit number,  (with 
-- leading zeros if needed).  There is no letter.  Any change
-- in CLI commands, parameters, or outputs results in this
-- value incrementing.
-- 
-- The XML version substring has the same format as the MIB
-- version sub-string.
-- 
-- SerialNumber is included here for convenience;  it is not
-- displayed in sysDescr.
		
		-- 1.3.6.1.4.1.388.6.6.1.1
		ccIdHwVersion OBJECT-TYPE
			SYNTAX DisplayString
			MAX-ACCESS read-only
			STATUS current
			DESCRIPTION
				"The same text that follows 'HW=' in sysDescr, EXCLUDING the
				'HW='."
			::= { ccIdentfication 1 }

		
		-- 1.3.6.1.4.1.388.6.6.1.2
		ccIdFwVersion OBJECT-TYPE
			SYNTAX DisplayString
			MAX-ACCESS read-only
			STATUS current
			DESCRIPTION
				"The same text that follows 'FW=' in sysDescr, EXCLUDING the
				'FW='.  (The bootcode version)."
			::= { ccIdentfication 2 }

		
		-- 1.3.6.1.4.1.388.6.6.1.3
		ccIdSwVersion OBJECT-TYPE
			SYNTAX DisplayString
			MAX-ACCESS read-only
			STATUS current
			DESCRIPTION
				"The same text that follows 'SW=' in sysDescr, EXCLUDING the
				'SW='."
			::= { ccIdentfication 3 }

		
		-- 1.3.6.1.4.1.388.6.6.1.4
		ccIdMibVersion OBJECT-TYPE
			SYNTAX DisplayString
			MAX-ACCESS read-only
			STATUS current
			DESCRIPTION
				"The same text that follows 'MIB=' in sysDescr, EXCLUDING the
				'MIB='.
				
				The MIB version is identified by a two-digit number and a
				single letter.  For example, '07a'.
				
				The number is incremented when the MIB changes in any 
				substantive way;  (any way that a person with a MIB browser
				could tell a device implementing one version from another
				device at a different MIB level).  The letter is incremented
				when only undetectable changes are made, such as changes to
				comments or descriptions.
				
				A given version of network management software will accurately
				manage all device versions that have the same numeric MIB
				version number."
			::= { ccIdentfication 4 }

		
		-- 1.3.6.1.4.1.388.6.6.1.5
		ccIdCliVersion OBJECT-TYPE
			SYNTAX DisplayString
			MAX-ACCESS read-only
			STATUS current
			DESCRIPTION
				"The same text that follows 'CLI=' in sysDescr, EXCLUDING the
				'CLI='."
			::= { ccIdentfication 5 }

		
		-- 1.3.6.1.4.1.388.6.6.1.6
		ccIdXmlVersion OBJECT-TYPE
			SYNTAX DisplayString
			MAX-ACCESS read-only
			STATUS current
			DESCRIPTION
				"Version of XML template implemented on this switch.  (Much 
				like MIB version - read details there)."
			::= { ccIdentfication 6 }

		
		-- 1.3.6.1.4.1.388.6.6.1.7
		ccIdSerialNumber OBJECT-TYPE
			SYNTAX DisplayString
			MAX-ACCESS read-only
			STATUS current
			DESCRIPTION
				"The serial number of the switch.  This value is unique for each
				instance of a given switch type."
			::= { ccIdentfication 7 }

		
		-- 1.3.6.1.4.1.388.6.6.1.8
		ccIdSwBuildDate OBJECT-TYPE
			SYNTAX DisplayString
			MAX-ACCESS read-only
			STATUS current
			DESCRIPTION
				"The date & time the software was built;  (corresponding to
				'ccIdSwVersion' - there is no corresponding value for
				'ccIdFwVersion').
				
				The format of this data is not specified,  (and so net mgmt
				software cannot assume how to parse date, month, year, hour,
				etc)."
			::= { ccIdentfication 8 }

		
		-- 1.3.6.1.4.1.388.6.6.1.9
		ccIdSwBuildInfo OBJECT-TYPE
			SYNTAX DisplayString
			MAX-ACCESS read-only
			STATUS current
			DESCRIPTION
				"Additional information about the particular build of the
				software running on the switch;  (corresponding to
				'ccIdSwVersion' - there is no corresponding value for
				'ccIdFwVersion').
				
				(No format for the characters in this DisplayString is
				specified)."
			::= { ccIdentfication 9 }

		
		-- 1.3.6.1.4.1.388.6.6.1.10
		ccIdProductFamily OBJECT-TYPE
			SYNTAX DisplayString
			MAX-ACCESS read-only
			STATUS current
			DESCRIPTION
				"Describes the product family.
				
				For all Butterfly implementations, this will be 'WS5000'.
				"
			::= { ccIdentfication 10 }

		
		-- 1.3.6.1.4.1.388.6.6.1.11
		ccIdProductModel OBJECT-TYPE
			SYNTAX DisplayString
			MAX-ACCESS read-only
			STATUS current
			DESCRIPTION
				"Describes the product model.
				
				For Butterfly, this will be '5000' or '5100'.
				"
			::= { ccIdentfication 11 }

		
		-- 1.3.6.1.4.1.388.6.6.2
		ccHwSensors OBJECT IDENTIFIER ::= { symbolCCNewInV1dot2dot5 2 }
-- MIB values to describe the fans and temp sensors in the
-- switch.
-- 
-- The WS5000 switch, (compared to the WS5100), does NOT have
-- temp sensors nor fans.  On that platform, all items in this
-- group will return NO-SUCH.
-- 
		
		-- 1.3.6.1.4.1.388.6.6.2.1
		ccHwSensorsReset OBJECT-TYPE
			SYNTAX DoActionNow
			MAX-ACCESS read-write
			STATUS current
			DESCRIPTION
				"Set to TRUE to reset the max values seen so far."
			::= { ccHwSensors 1 }

		
		-- 1.3.6.1.4.1.388.6.6.2.2
		ccHwSensorsTable OBJECT-TYPE
			SYNTAX SEQUENCE OF CcHwSensorsEntry
			MAX-ACCESS not-accessible
			STATUS current
			DESCRIPTION
				"A table of fan and temp sensors for this switch.
				
				(A table was used rather than a collection of scalars, so
				that one table could describe numerous different
				configurations of different numbers/types of fan and temp
				sensors on different types of switches)."
			::= { ccHwSensors 2 }

		
		-- 1.3.6.1.4.1.388.6.6.2.2.1
		ccHwSensorsEntry OBJECT-TYPE
			SYNTAX CcHwSensorsEntry
			MAX-ACCESS not-accessible
			STATUS current
			DESCRIPTION
				" "
			INDEX { ccHwSensorsIndex }
			::= { ccHwSensorsTable 1 }

		
		CcHwSensorsEntry ::=
			SEQUENCE { 
				ccHwSensorsIndex
					INTEGER,
				ccHwSensorsType
					INTEGER,
				ccHwSensorsDescr
					DisplayString,
				ccHwSensorsCurrentReading
					Integer32,
				ccHwSensorsMinimum
					Gauge32,
				ccHwSensorsMaximum
					Gauge32,
				ccHwSensorsNotifyIfAbove
					Integer32
			 }

		-- 1.3.6.1.4.1.388.6.6.2.2.1.1
		ccHwSensorsIndex OBJECT-TYPE
			SYNTAX INTEGER (1..2147483647)
			MAX-ACCESS accessible-for-notify
			STATUS current
			DESCRIPTION
				"Simple index."
			::= { ccHwSensorsEntry 1 }
-- ??Mower: added a range 0..1..2**31 to eliminate an error,
-- but what range is correct?
		
		-- 1.3.6.1.4.1.388.6.6.2.2.1.2
		ccHwSensorsType OBJECT-TYPE
			SYNTAX INTEGER
				{
				tempInDegC(2),
				variableSpeedFanInRpm(3),
				onOffFanInDutyCycle(4)
				}
			MAX-ACCESS read-only
			STATUS current
			DESCRIPTION
				"Tells the type of the fan or temp sensor, and the 
				corresponding units for the readings.
				
				Note that any given temp sensors appears in this table only
				once;  (NOT twice - once for deg-F and once for deg-C).
				The choice of implementing a temp sensor as deg-F or deg-C
				is left to the convenience of the switch developer.
				"
			::= { ccHwSensorsEntry 2 }

		
		-- 1.3.6.1.4.1.388.6.6.2.2.1.3
		ccHwSensorsDescr OBJECT-TYPE
			SYNTAX DisplayString
			MAX-ACCESS read-only
			STATUS current
			DESCRIPTION
				"A short, text description of the sensor.
				
				For example:
				  'system fan'
				  'CPU fan/blower'
				  'CPU temperature'
				  'ambient temperature - near CPU'
				  'ambient temperature - system'
				"
			::= { ccHwSensorsEntry 3 }

		
		-- 1.3.6.1.4.1.388.6.6.2.2.1.4
		ccHwSensorsCurrentReading OBJECT-TYPE
			SYNTAX Integer32
			MAX-ACCESS read-only
			STATUS current
			DESCRIPTION
				"The current, live reading for that sensor.
				
				For sensors of type onOffFanInDutyCycle, this value will be 
				0 if the fan is currently not running, and 1 if the fan is
				running."
			::= { ccHwSensorsEntry 4 }

		
		-- 1.3.6.1.4.1.388.6.6.2.2.1.5
		ccHwSensorsMinimum OBJECT-TYPE
			SYNTAX Gauge32
			MAX-ACCESS read-only
			STATUS current
			DESCRIPTION
				"The minimum reading observed since system reboot, (or since
				the fan/temp readings were reset).
				
				For sensors of type onOffFanInDutyCycle, this value will be 
				the minimum 'duty' cycle of the fan, (ranging 0..100).  The
				time interval over which the duty cycle is calculated is up
				to the switch, but shall be long enough as to provide a
				meaningful result."
			::= { ccHwSensorsEntry 5 }

		
		-- 1.3.6.1.4.1.388.6.6.2.2.1.6
		ccHwSensorsMaximum OBJECT-TYPE
			SYNTAX Gauge32
			MAX-ACCESS read-only
			STATUS current
			DESCRIPTION
				"The maximum observed since system reboot, (or since
				the fan/temp readings were reset).
				
				For sensors of type onOffFanInDutyCycle, this value will be 
				the maximum 'duty' cycle of the fan, (ranging 0..100).  The
				time interval over which the duty cycle is calculated is up
				to the switch, but shall be long enough as to provide a
				meaningful result."
			::= { ccHwSensorsEntry 6 }

		
		-- 1.3.6.1.4.1.388.6.6.2.2.1.7
		ccHwSensorsNotifyIfAbove OBJECT-TYPE
			SYNTAX Integer32
			MAX-ACCESS read-write
			STATUS current
			DESCRIPTION
				"When the given sensor's reading exceeds this threshold, a
				notification is generated.
				
				If no notifications are desired for this sensor, set this
				threshold to 0.
				
				(No corresponding _NotifyIfBelow has been provided, as such
				a function is not anticipated to be useful.  We don't
				forsee low temps or infrequently/slowly operating fans to
				be interesting events to send notifications on).
				
				(Note that the corresponding notification is NOT defined
				here since such notifications are defined in the ccFault
				group).
				
				The WS5100 switch does NOT support any thresholds on fans.
				(It is retained here in expectation that other platforms 
				will allow such thresholds).  If this value is SET on a
				WS5000, (for a row that represents a fan), a SET-FAILED,
				(bad value) will be returned."
			::= { ccHwSensorsEntry 7 }

		
-- This node reserved for sysOIDs of devices produced 
-- by WSD.
-- 
		-- 1.3.6.1.4.1.388.6.6.3
		ccSsh OBJECT IDENTIFIER ::= { symbolCCNewInV1dot2dot5 3 }
-- Values to control SSH connection to the switch.
		
		-- 1.3.6.1.4.1.388.6.6.3.1
		ccSshEnabled OBJECT-TYPE
			SYNTAX TruthValue
			MAX-ACCESS read-write
			STATUS current
			DESCRIPTION
				"Set to TRUE to enable SSH access to switch."
			::= { ccSsh 1 }

		
		-- 1.3.6.1.4.1.388.6.6.3.2
		ccSshProtocolVersion OBJECT-TYPE
			SYNTAX INTEGER
				{
				sshV1orV2(1),
				sshV2(2)
				}
			MAX-ACCESS read-write
			STATUS current
			DESCRIPTION
				"The version of SSH to use in communicating with the 
				switch."
			::= { ccSsh 2 }

		
		-- 1.3.6.1.4.1.388.6.6.3.3
		ccSshPort OBJECT-TYPE
			SYNTAX Integer32
			MAX-ACCESS read-write
			STATUS current
			DESCRIPTION
				"Port number to use in talking SSH to the switch.
				
				Factory-default value is 22.The valid ranges are
				1025-65535, 22."
			::= { ccSsh 3 }

		
		-- 1.3.6.1.4.1.388.6.6.3.4
		ccSshAuthenticationTimeout OBJECT-TYPE
			SYNTAX Integer32
			UNITS "seconds"
			MAX-ACCESS read-only
			STATUS deprecated
			DESCRIPTION
				"If the SSH user has not been re-authenticated
				within this period of time, the connection will be
				dropped."
			::= { ccSsh 4 }

		
		-- 1.3.6.1.4.1.388.6.6.3.5
		ccSshInactivityTimeout OBJECT-TYPE
			SYNTAX Integer32
			UNITS "minutes"
			MAX-ACCESS read-only
			STATUS deprecated
			DESCRIPTION
				"If there has been no activity on the connection for
				this period of time, the connection will be dropped.
				
				Factory-default value is 5min."
			::= { ccSsh 5 }

		
		-- 1.3.6.1.4.1.388.6.6.4
		ccAccessMethods OBJECT IDENTIFIER ::= { symbolCCNewInV1dot2dot5 4 }
-- This group is used to indicate the current allowed methods
-- of management access to the switch, and send a notification
-- if that access changes.
		
		-- 1.3.6.1.4.1.388.6.6.4.1
		ccAccessMethodsPermitted OBJECT-TYPE
			SYNTAX BITS
				{
				accessViaTelnetAllowed(0),
				accessViaSshAllowed(1),
				accessViaXmlAllowed(2),
				accessViaSnmpV12Allowed(3),
				accessViaSnmpV3Allowed(4)
				}
			MAX-ACCESS read-write
			STATUS deprecated
			DESCRIPTION
				"A BITs value that indicates which management methods are
				currently permitted to the switch."
			::= { ccAccessMethods 1 }

		
		-- 1.3.6.1.4.1.388.6.6.1000
		ccV1dot2dot5Groups OBJECT IDENTIFIER ::= { symbolCCNewInV1dot2dot5 1000 }

		
		-- 1.3.6.1.4.1.388.6.6.1000.2
		v1dot2dot5Group OBJECT-GROUP
			OBJECTS { ccPolicyAPPolicyCount, ccEPCFGMode, ccEPDuplex, ccEPMode, ccMUInfoEncrMethod, 
				ccTargetTrapString, ccTrapInfoEnableTrap, ccTrapInfoMaxNumSendOneTrap, ccTrapInfoInterval, ccTrapInfoAclViolation, 
				ccTrapInfoDenyAdoption, ccTrapInfoAPMUMaxExceed, ccTrapInfoWLANMUMaxExceed, ccTrapInfoApDetected, ccTrapInfoApAdopted, 
				ccTrapInfoApReset, ccTrapInfoApUnavailable, ccTrapInfoKDCUserAuthFail, ccTrapInfoRadiusAuthFail, ccTrapInfoLowFlashSpace, 
				ccTrapInfoNicDropping, ccTrapInfoApAlert, ccTrapInfoUserAuthFail, ccTrapInfoHsbPrimaryNoHeartbeat, ccTrapInfoHsbStandbyEntersFailover, 
				ccTrapInfoPrimaryFailedResetting, ccTrapInfoKDCPropagationFail, ccTrapInfoHighDecryptFail, ccTrapInfoHighReplyFail, ccTrapInfoTKIPMICFail, 
				ccTrapInfoWPACounterMeasureStart, hsbStartUpControl, hsbPeerConnectControl, ccModuleName, ccModuleDesc, 
				ccManufacture, ccCopyright, ccModuleVer, ccMaxNumAP, ccMaxNumMu, 
				ccActivePolicy, ccTaf, ccSnmpOpers, ccUptime, ccFTP, 
				ccTelnet, ccWeb, ccSNMPFlag, ccTime, ccSNMPKdc, 
				ccCliKdc, ccPolicyAddObj, ccPolicyRemObj, ccLicenseCount, ccEmergencyPolicy, 
				ccEmergencyMode, ccRunACS, ccEnableSNMPTrap, ccPolicyName, ccPolicyDesc, 
				ccPolicyCountry, ccPolicyAddAPPolicy, ccPolicyRmvAPPolicy, ccPolicyExcludeInfo, ccPolicyExcludeEdit, 
				ccPolicyExcludeRmv, ccPolicyIncludeInfo, ccPolicyIncludeEdit, ccPolicyIncludeRmv, ccPolicyEtherPolicy, 
				ccPolicyTrap, ccPolicyChannel11a, ccPolicyPower11a, ccPolicyChannel11b, ccPolicyPower11b, 
				ccPolicyDSCoExistence, ccPolicyDefAdoptAPPolicy11a, ccPolicyDefAdoptAPPolicy11b, ccPolicyDefAdoptAPPolicyFH, ccCCIndex, 
				ccCCode, ccFullName, cc11aChannels, cc11bChannels, ccFHTableNum, 
				ccFHChannels, ccFHAlgorithm, ccFHContiguous, ccFHHopSequence, kdcType, 
				masterHost, masterIPAddress, createMsKdc, delMsKdc, createSlvKdc, 
				delSlvKdc, kdcRealm, interfaceNumber, addSlave, delSlave, 
				slaveCount, hostName, realM, ipAddress, domainName, 
				syncDB, prefTimeServer, firstAltTimeServer, secondAltTimeServer, groupSetTimeServer, 
				delAll, kdcUserName, kdcUserTlife, kdcWLANName, kdcWLANTlife, 
				radiusAuthClientInvalidServerAddresses, radiusAuthServerAddress, radiusAuthClientServerPortNumber, radiusAuthClientRoundTripTime, radiusAuthClientAccessRequests, 
				radiusAuthClientAccessRetransmissions, radiusAuthClientAccessAccepts, radiusAuthClientAccessRejects, radiusAuthClientAccessChallenges, radiusAuthClientMalformedAccessResponses, 
				radiusAuthClientBadAuthenticators, radiusAuthClientPendingRequests, radiusAuthClientTimeouts, radiusAuthClientUnknownTypes, radiusAuthClientPacketsDropped, 
				radiusAuthClientIdentifier, ccEventsAllLocalLog, ccEventsAllSNMPTrap, ccEventsAllSyslog, ccEventsAllDefault, 
				ccEventDescr, ccEventDefault, ccEventSyslog, ccEventSNMPTrap, ccEventLocalLog, 
				ccSysLogStatus, ccSyslogAddHost, ccSyslogRemHost, ccSyslogHostName, ccSyslogHostIPAddr, 
				ccSyslogHostDomain, ccSyslogHostSetSeverity, ccSyslogHostSeverityList, ccSystemAddHost, ccSystemRemHost, 
				ccSystemHostName, ccSystemHostIPAddr, ccSystemHostDomain, ccPolicyRCAdd, ccPolicyRCRem, 
				ccPolicyRCChannelDescr, ccPolicyAPPolicyName, ccAPPolicyAddObj, ccAPPolicyRemObj, ccEPPAddObj, 
				ccEPPRemObj, ccAccessPortAddObj, ccAccessPortRemObj, ccRadioName, ccRadioDesc, 
				ccRadioOnlineStatus, ccRadioMAC, ccDeviceMAC, ccDeviceLocation, ccRadioType, 
				ccRadioChannel, ccRadioPolicy, ccDeviceNic, ccDeviceType, ccRadioCCAmode, 
				ccRadioCCAthresh, ccRadioDiversity, ccDeviceVlanid, ccDeviceVlanTagsSeen, ccRadioUptime, 
				ccRadioTxpps, ccRadioMUs, ccRadioGatherStatistics, ccRadioReset, ccDeviceReset, 
				ccAPPolicyDesc, ccAPPolicyPreAmble, ccAPPolicyBeaconInterval, ccAPPolicyRTSThreshold, ccAPPolicyDTIM, 
				ccAPPolicyBasicRates11a, ccAPPolicySupportedRates11a, ccAPPolicyBasicRates11b, ccAPPolicySupportedRates11b, ccAPPolicyBasicRatesFH, 
				ccAPPolicySupportedRatesFH, ccEPIndex, ccEPNic, ccEPName, ccEPDesc, 
				ccEPMacAddr, ccEPEnable, ccEPEnableDHCP, ccEPIPAddr, ccEPNetMask, 
				ccEPDnsCount, ccEPDnsList, ccEPPrimaryVid, ccEPOnline, ccEPDisplayName, 
				ccEPUptime, ccEPTx, ccEPRx, ccEPDomain, ccEPGateway, 
				ccEPPIndex, ccEPPName, ccEPPAlias, ccEPPDesc, ccEPPRonnic, 
				ccEPPVlanCount, ccEPPVlanList, ccEPPCreateNewVlan, ccEPPRemVlan, ccEPPDropVlan, 
				ccdot11FHHopTime, ccdot11FHCurrentChannelNumber, ccdot11FHMaxDwellTime, ccdot11FHCurrentDwellTime, ccdot11FHCurrentSet, 
				ccdot11FHCurrentPattern, ccdot11FHCurrentIndex, ccAPPolicyWLAN, ccAPPolicyWLANBW, ccAPPolicyWLANNP, 
				ccAPPolicyWLANBSS, ccAPPolicyPrimaryWLAN, ccWLANAddObj, ccWLANRemObj, ccUserAddObj, 
				ccUserRemObj, ccGraphAddObj, ccGraphRemObj, ccSecAddObj, ccSecRemObj, 
				ccACLAddObj, ccACLRemObj, ccUserID, ccUserFullName, ccUserPwd, 
				ccUserProfileMgmtRight, ccUserSysAdminRight, ccUserSNMPAdminRight, ccUserSecurityAdminRight, ccWLANIndex, 
				ccWLANName, ccESSID, ccSecurity, ccACLEnabled, ccMaxMus, 
				ccKerberosAuthName, ccKerberosAuthPass, ccWLANACL, ccWLANIsAuthenticated, ccWLANMUTraffic, 
				ccWLANSecuredBeacon, ccWLANCurrentMU, ccWLANNetMask, ccWLANDefaultRoute, ccWLANBCMC11A, 
				ccWLANBCMC11B, ccWLANBCMCFH, ccBroadcastEss, ccWLANDesc, ccKnownCCIndex, 
				ccKnownCCName, ccKnownCCMac, ccKnownAPIndex, ccKnownAPMac, ccKnownAPVer, 
				ccKnownAPIP, ccKnownAPPriority, ccKnownAPMus, ccKnownAPType, ccKnownAPAPVer, 
				ccKnownAPEssid, ccGraphIndex, ccGraphName, ccGraphWlanId, ccVLANIndex, 
				ccVLANName, ccVLANDesc, ccVLANVid, ccVLANPriority, ccVLANPorts, 
				ccVLANEtherPolicy, ccVLANWlan, ccVLANWlanList, ccVLANAddWlan, ccVLANRemWlan, 
				ccSecIndex, ccSecName, ccSecDesc, ccSecPreSharedAuthEnabled, ccSecWEPEnabled, 
				ccSecWEPKeyBitSize, ccSecWEPKey, ccSecWEPKeyUse, ccSecKerberosEnabled, ccSecKerberosRealm, 
				ccSecKerberosServer1, ccSecKerberosServer2, ccSecKerberosServer3, ccSecKerberosPort1, ccSecKerberosPort2, 
				ccSecKerberosPort3, ccSecRadiusServer1, ccSecRadiusPort1, ccSecRadiusSecret1, ccSecRadiusServer2, 
				ccSecRadiusPort2, ccSecRadiusSecret2, ccSecRadiusHostname, ccSecEapEnabled, ccSecEapQuietPeriod, 
				ccSecEapTxPeriod, ccSecEapReauth, ccSecEapReauthPeriod, ccSecEapReauthMaxRetries, ccSecEapSupplTimeout, 
				ccSecEapMaxreqRetries, ccSecGroupRekeyPeriod, ccSecPreSharedKeyMaterial, ccSecOpenEncryptEnabled, ccSecKeyGuardEnabled, 
				ccSecTKIPEnabled, ccSecCheckValidity, ccACLName, ccACLDefaultAction, ccACLAction, 
				ccACLGetItemCount, ccACLAddItem, ccACLRemItem, ccNumNPRec, ccNumPORec, 
				ccNumCGRec, ccNumCFRec, ccCFAddObj, ccCFRemObj, ccCGAddObj, 
				ccCGRemObj, ccPOAddObj, ccPORemObj, ccNPAddObj, ccNPRemObj, 
				ccNPIndex, ccNPName, ccNPDesc, ccNPInName, ccNPOutName, 
				ccPOName, ccPODesc, ccPOCgCount, ccPOAddCg, ccPORemCg, 
				ccPOType, ccCGName, ccCGDesc, ccCGCfCount, ccCGAddCf, 
				ccCGRemCf, ccCFName, ccCFDesc, ccCFMcCount, ccCFAddMc, 
				ccCFRemMc, ccPOCGName, ccPOCGNewIP, ccPOCGVlanPriority, ccPOCGTos, 
				ccPOCGBw, ccPOCGTxProfile, ccPOCGPacketModifier, ccCGCFAction, ccCGCFName, 
				ccCFMCOffset, ccCFMCValueCount, ccCFAddMCValue, ccCFRemMCValue, ccCFMCValue, 
				ccHsbEnabled, ccHsbMode, ccHsbMacAddress1, ccHsbMacAddress2, ccHsbHeartbeatEnabledOnInterface1, 
				ccHsbHeartbeatEnabledOnInterface2, ccHsbConnectivityFlag, ccHsbFailoverState, ccHsbFailoverReason, ccHsbResetCode, 
				ccHsbRevert, ccHsbautorevert, ccHsbautorevertdelay, ccMUInfoIndex, ccMUInfoType, 
				ccMUInfoMac, ccMUInfoIP, ccMUInfoWlan, ccMUInfoEssid, ccMUInfoAP, 
				ccMUInfoAPState, ccMUInfoSecState, ccMUInfoCurRate, ccMUInfoSupRates, ccMUInfoRssi, 
				ccMUInfoPsp, ccMUInfoIntf, ccMUInfoAsscUptime, ccMUInfoTktExp, ccMUInfoUserName, 
				ccMUInfoPktTx, ccMUInfoPktRx, ccMUInfoBytesTx, ccMUInfoBytesRx, ccMUInfoLastAct, 
				ccMUInfoVlan, ccMUInfoAuthState, ccMUInfoAuthMethod, ccMUInfoBCMCEncrType, ccACLItem, 
				ccTargetAddrSecName, ccTargetAddrHost, ccTargetAddrCommunity, ccTargetAddrPort, ccTargetAddrStorageType, 
				ccTargetAddrRowStatus, ccTargetAddrOption, licenseChangedControl, clockChangedControl, pktDiscWrongNICControl, 
				pktDiscWrongVLANControl, apAdoptFailPolControl, apAdoptFailACLControl, apAdoptFailLimitControl, apAdoptFailLicControl, 
				apAdoptFailNoImgControl, apCfgFailESSControl, devDropInfoMsgControl, devdropLoadmeMsgControl, etherConnectControl, 
				muAssocFailControl, muAssocOKControl, muRoamedControl, muDisassocControl, muEAPAuthFailControl, 
				muEAPAuthOKControl, muKDCAuthOKControl, wlanAuthOKControl, wlanAuthFailControl, userAuthOKControl, 
				radiusSrvTimeoutControl, kdcPrincAddControl, kdcPrincChgdControl, kdcPrincDelControl, kdcDBReplacedControl, 
				hsbStdbyAutoRevControl, hsbPrimAutoRevControl, acsErrorControl, eopActiveControl, eopInactiveControl, 
				debugEventControl, ccIdHwVersion, ccIdFwVersion, ccIdSwVersion, ccIdMibVersion, 
				ccIdCliVersion, ccIdXmlVersion, ccIdSerialNumber, ccSshEnabled, ccSshProtocolVersion, 
				ccSshPort, ccAPPolicyName, ccAccessChangedControl, ccFanAndTempControl, ccIdSwBuildInfo, 
				ccIdSwBuildDate, ccIdProductModel, ccIdProductFamily, cc11gChannels, ccPolicyPower11g, 
				ccPolicyChannel11g, ccPolicyDefAdoptAPPolicy11g, ccRadioAllPower, ccRadioCurrentPower, ccRadioPowerdBm, 
				ccRadioAllChannels, ccRadioCurrentChannel, ccRadioAntenna, ccRadioShortSlot, ccRadioProtection, 
				ccRadioRadarChannels, ccRadioTPC, ccRadioDFS, ccRadioIndoor, ccRadioAntCorrection, 
				ccRadioMUPowerdBm, ccAPPolicyRemAllWlan, ccAPPolicyAddAllWlan, ccAPPolicyNonSpectrumMgmt, ccAPPolicySupportedRates11g, 
				ccAPPolicyBasicRates11g, ccAPPolicyUnselectWLAN, ccAPPolicySelectWLAN, radioRandomChannelControl, radioResumeControl, 
				radioSuspendControl, dfsChannelRevertControl, dfsChannelSwitchControl, dfsChannelSelectControl, dfsRadarDetectControl, 
				ccSecCCMPEnabled, ccSecPreAuthentication, ccSecPMKCaching, tpcPowerReducedControl, ccPolicyAPNameOfPolicy, 
				ccHwSensorsReset, ccHwSensorsIndex, ccHwSensorsType, ccHwSensorsDescr, ccHwSensorsCurrentReading, 
				ccHwSensorsMinimum, ccHwSensorsMaximum, ccHwSensorsNotifyIfAbove }
			STATUS current
			DESCRIPTION 
				"Description."
			::= { ccV1dot2dot5Groups 2 }

		
		-- 1.3.6.1.4.1.388.6.6.1000.3
		v1dot2dot5NotificationGroup NOTIFICATION-GROUP
			NOTIFICATIONS { ccTrapLowFlashSpace, ccTrapNicDropping, ccTrapAPMUMaxExceed, ccTrapWLANMUMaxExceed, ccTrapAPDetected, 
				ccTrapAPAdopted, ccTrapAPReset, ccTrapAPUnavailable, ccTrapAPAlert, ccTrapUserAuthFail, 
				ccTrapRadiusAuthFail, ccTrapACLViolation, ccTrapDenyAPAdoption, ccTrapHsbPrimaryNoHeartbeat, ccTrapHsbStandbyEntersFailover, 
				ccTrapHsbPrimaryFailedResetting, ccTrapHsbStandbyFailedResetting, ccTrapKDCUserAuthFail, ccTrapKDCPropagationFail, ccTrapHighDecryptFail, 
				ccTrapHighReplyFail, ccTrapTKIPMICFail, ccTrapWPACounterMeasureStart, hsbStartUp, ccFanAndTempNotification, 
				ccAccessChangedNotification, radioRandomChannel, radioResume, radioSuspend, dfsChannelRevert, 
				dfsChannelSwitch, dfsChannelSelect, dfsRadarDetect, tpcPowerReduced, hsbPeerConnect, 
				licenseChanged, clockChanged, pktDiscWrongNIC, pktDiscWrongVLAN, apAdoptFailPol, 
				apAdoptFailACL, apAdoptFailLimit, apAdoptFailLic, apAdoptFailNoImg, apCfgFailESS, 
				devDropInfoMsg, devdropLoadmeMsg, etherConnect, muAssocFail, muAssocOK, 
				muRoamed, muDisassoc, muEAPAuthFail, muEAPAuthOK, muKDCAuthOK, 
				wlanAuthOK, wlanAuthFail, userAuthOK, radiusSrvTimeout, kdcPrincAdd, 
				kdcPrincChgd, kdcPrincDel, kdcDBReplaced, hsbStdbyAutoRev, hsbPrimAutoRev, 
				acsError, eopActive, eopInactive, debugEvent }
			STATUS current
			DESCRIPTION 
				"Description."
			::= { ccV1dot2dot5Groups 3 }

		
		-- 1.3.6.1.4.1.388.6.6.1000.4
		v1dot2dot5GroupOfDepricated OBJECT-GROUP
			OBJECTS { ccPolicyDefAdoptAPPolicy, ccPolicyDefChannel, ccPolicyDefPower, ccEPSpeed, ccSecBeaconEssid, 
				ccSecBCMCEncrType, ccACLGetItem, ccRadioPower, ccRadioMUPower, ccRadioAuto, 
				ccAPPolicyRemWLAN, ccAPPolicyAddWLAN, ccSshAuthenticationTimeout, ccSshInactivityTimeout, ccUserAdminRight, 
				ccDeviceClearSeenVlanTags, ccPOPacketModifier, delTimeServer }
			STATUS deprecated
			DESCRIPTION 
				"Description."
			::= { ccV1dot2dot5Groups 4 }

		
		-- 1.3.6.1.4.1.388.6.9
		ccRadiusServer OBJECT IDENTIFIER ::= { symbolCC 9 }

		
		-- 1.3.6.1.4.1.388.6.9.1
		ccRadius OBJECT IDENTIFIER ::= { ccRadiusServer 1 }

		
		-- 1.3.6.1.4.1.388.6.9.1.1
		ccRadiusDataSource OBJECT-TYPE
			SYNTAX INTEGER
				{
				local(1),
				ldap(2)
				}
			MAX-ACCESS read-write
			STATUS current
			DESCRIPTION
				"Description."
			::= { ccRadius 1 }

		
		-- 1.3.6.1.4.1.388.6.9.1.2
		ccRadiusDefaultEapType OBJECT-TYPE
			SYNTAX INTEGER
				{
				ttls(1),
				peap(2)
				}
			MAX-ACCESS read-write
			STATUS current
			DESCRIPTION
				"Description.
				Deafult EAP type advertised by the radius server.
				"
			::= { ccRadius 2 }

		
		-- 1.3.6.1.4.1.388.6.9.1.3
		ccRadiusAuthTypePeap OBJECT-TYPE
			SYNTAX INTEGER
				{
				gtc(1),
				mschapv2(2)
				}
			MAX-ACCESS read-write
			STATUS current
			DESCRIPTION
				"Description.
				Type of EAP type within PEAP"
			::= { ccRadius 3 }

		
		-- 1.3.6.1.4.1.388.6.9.1.4
		ccRadiusAuthTypeTtls OBJECT-TYPE
			SYNTAX INTEGER
				{
				md5(1),
				pap(2),
				mschapv2(3)
				}
			MAX-ACCESS read-write
			STATUS current
			DESCRIPTION
				"Description.
				Type of EAP type within TTLS"
			::= { ccRadius 4 }

		
		-- 1.3.6.1.4.1.388.6.9.1.5
		ccRadiusServerCertificate OBJECT-TYPE
			SYNTAX DisplayString (SIZE (0..10))
			MAX-ACCESS read-write
			STATUS current
			DESCRIPTION
				"This OID is used to import the server certificate 
				syntax:-  /image/<server certificate file name>
					             or
				        <file path>/<server certificate file name>
				Note:- user can copy the certificates from a ftp server 
				       using ccFtp OID in ccImageDload Table which copies
				       the downloaded file in /image directory
				       Before importing server certificate user has to set 
				       the Private key password (OID;- ccRadiusEapPasswd) 
				       which was given while genrating the server certificate
				       If no password is used to genrate the certificate then no
				       need to set the Private key password
				
				"
			::= { ccRadius 5 }

		
		-- 1.3.6.1.4.1.388.6.9.1.6
		ccRadiusCACertificate OBJECT-TYPE
			SYNTAX DisplayString (SIZE (0..10))
			MAX-ACCESS read-write
			STATUS current
			DESCRIPTION
				"This OID is used to import the CA certificate 
				syntax:-  /image/<CA certificate file name>
				             or
				<file path>/<CA certificate file name>
				Note:- user can copy the certificates from a ftp server 
				       using ccFtp OID in ccImageDload Table which copies
				       the downloaded file in /image directory
				"
			::= { ccRadius 6 }

		
		-- 1.3.6.1.4.1.388.6.9.1.7
		ccRadiusClientAuthTable OBJECT-TYPE
			SYNTAX SEQUENCE OF CcRadiusClientAuthEntry
			MAX-ACCESS not-accessible
			STATUS current
			DESCRIPTION
				"Description."
			::= { ccRadius 7 }

		
		-- 1.3.6.1.4.1.388.6.9.1.7.1
		ccRadiusClientAuthEntry OBJECT-TYPE
			SYNTAX CcRadiusClientAuthEntry
			MAX-ACCESS not-accessible
			STATUS current
			DESCRIPTION
				"Description."
			INDEX { ccRadiusClientAuthIndex }
			::= { ccRadiusClientAuthTable 1 }

		
		CcRadiusClientAuthEntry ::=
			SEQUENCE { 
				ccRadiusClientAuthIndex
					DisplayString,
				ccRadiusClientAuthIpAddr
					DisplayString,
				ccRadiusClientAuthMask
					DisplayString,
				ccRadiusClientAuthSharedSecret
					DisplayString,
				ccRadiusClientAuthRowStatus
					AbbrevRowStatus
			 }

		-- 1.3.6.1.4.1.388.6.9.1.7.1.1
		ccRadiusClientAuthIndex OBJECT-TYPE
			SYNTAX DisplayString
			MAX-ACCESS read-create
			STATUS current
			DESCRIPTION
				"This table(ccRadiusClientAuthTable) is indexed by the 
				radius client name.Therefore this OID contains the Client Name.
				When this table is created, the client name has to be specified
				here. 
				"
			::= { ccRadiusClientAuthEntry 1 }

		
		-- 1.3.6.1.4.1.388.6.9.1.7.1.2
		ccRadiusClientAuthIpAddr OBJECT-TYPE
			SYNTAX DisplayString
			MAX-ACCESS read-create
			STATUS current
			DESCRIPTION
				"The client IP address."
			::= { ccRadiusClientAuthEntry 2 }

		
		-- 1.3.6.1.4.1.388.6.9.1.7.1.3
		ccRadiusClientAuthMask OBJECT-TYPE
			SYNTAX DisplayString
			MAX-ACCESS read-create
			STATUS current
			DESCRIPTION
				"Mask of the client's IP address"
			::= { ccRadiusClientAuthEntry 3 }

		
		-- 1.3.6.1.4.1.388.6.9.1.7.1.4
		ccRadiusClientAuthSharedSecret OBJECT-TYPE
			SYNTAX DisplayString (SIZE (1..32))
			MAX-ACCESS read-create
			STATUS current
			DESCRIPTION
				"Shared secret between the client and the radius server
				"
			::= { ccRadiusClientAuthEntry 4 }

		
		-- 1.3.6.1.4.1.388.6.9.1.7.1.5
		ccRadiusClientAuthRowStatus OBJECT-TYPE
			SYNTAX AbbrevRowStatus
			MAX-ACCESS read-create
			STATUS current
			DESCRIPTION
				"Create/destroy a Row"
			::= { ccRadiusClientAuthEntry 5 }

		
		-- 1.3.6.1.4.1.388.6.9.1.8
		ccRadiusServerEnable OBJECT-TYPE
			SYNTAX TruthValue
			MAX-ACCESS read-write
			STATUS current
			DESCRIPTION
				"Enable(1) or disable(2) the radius server.
				
				Note:Before enabling or disabling radius server
				     save the radius server status to make 
				     effect of the modifications done
				     Enabling the radius server may fail
				     if certificates are not imported or 
				     Private key password set does not match
				     certificates or no radius client is
				     added. Use ccRadiusEapPasswd to set
				     Private key password
				
				"
			::= { ccRadius 8 }

		
		-- 1.3.6.1.4.1.388.6.9.1.9
		ccRadiusSaveStatus OBJECT-TYPE
			SYNTAX INTEGER (0..1)
			MAX-ACCESS read-write
			STATUS current
			DESCRIPTION
				"Save the configuration info for the radius server.
				You can only enable (1) this OID.
				Disable(2) is not a valid input.This OID is SET only."
			::= { ccRadius 9 }

		
		-- 1.3.6.1.4.1.388.6.9.1.10
		ccRadiusEapPasswd OBJECT-TYPE
			SYNTAX OCTET STRING (SIZE (1..16))
			MAX-ACCESS read-write
			STATUS current
			DESCRIPTION
				"Enter the Private Key Password for Eap which was used to 
				generate the certificates."
			::= { ccRadius 10 }

		
		-- 1.3.6.1.4.1.388.6.9.2
		ccRadiusProxy OBJECT IDENTIFIER ::= { ccRadiusServer 2 }

		
		-- 1.3.6.1.4.1.388.6.9.2.1
		ccRadiusProxyRetryCount OBJECT-TYPE
			SYNTAX INTEGER (5..10)
			MAX-ACCESS read-write
			STATUS current
			DESCRIPTION
				"Description.
				Number of retries for sending messages to a proxy
				"
			::= { ccRadiusProxy 1 }

		
		-- 1.3.6.1.4.1.388.6.9.2.2
		ccRadiusProxyTimeout OBJECT-TYPE
			SYNTAX INTEGER (3..6)
			UNITS "seconds"
			MAX-ACCESS read-write
			STATUS current
			DESCRIPTION
				"Description.
				Timeout in seconds before retrying to a proxy"
			::= { ccRadiusProxy 2 }

		
		-- 1.3.6.1.4.1.388.6.9.2.3
		ccRadiusProxyServerTable OBJECT-TYPE
			SYNTAX SEQUENCE OF CcRadiusProxyServerEntry
			MAX-ACCESS not-accessible
			STATUS current
			DESCRIPTION
				"Description."
			::= { ccRadiusProxy 3 }

		
		-- 1.3.6.1.4.1.388.6.9.2.3.1
		ccRadiusProxyServerEntry OBJECT-TYPE
			SYNTAX CcRadiusProxyServerEntry
			MAX-ACCESS not-accessible
			STATUS current
			DESCRIPTION
				"Description."
			INDEX { ccRadiusProxyServerIndex }
			::= { ccRadiusProxyServerTable 1 }

		
		CcRadiusProxyServerEntry ::=
			SEQUENCE { 
				ccRadiusProxyServerIndex
					DisplayString,
				ccRadiusProxyServerPrefixOrSuffix
					DisplayString,
				ccRadiusProxyServerIp
					IpAddress,
				ccRadiusProxyServerPort
					Integer32,
				ccRadiusProxyServerSharedSecret
					DisplayString,
				ccRadiusProxyServerRowStatus
					AbbrevRowStatus
			 }

		-- 1.3.6.1.4.1.388.6.9.2.3.1.1
		ccRadiusProxyServerIndex OBJECT-TYPE
			SYNTAX DisplayString (SIZE (1..50))
			MAX-ACCESS read-create
			STATUS current
			DESCRIPTION
				"Description.
				 A get operation  on this OID displays the Proxy 
				 Server Name.
				 This table is indexed by this name hence user 
				 has to give the Proxy server name as input to 
				 this OID."
			::= { ccRadiusProxyServerEntry 1 }

		
		-- 1.3.6.1.4.1.388.6.9.2.3.1.2
		ccRadiusProxyServerPrefixOrSuffix OBJECT-TYPE
			SYNTAX DisplayString (SIZE (1..50))
			MAX-ACCESS read-create
			STATUS current
			DESCRIPTION
				"Description.
				Prefix  of suffix used for proxying radius request to a 
				 	proxy server
				Note:The value of this OID has to be unique 
				  among existing proxy server.If the row creation gives
				  commit fail while creation of a row then the suffix
				  given as input for new row creation may be existing
				  in some other row also. "
			::= { ccRadiusProxyServerEntry 2 }

		
		-- 1.3.6.1.4.1.388.6.9.2.3.1.3
		ccRadiusProxyServerIp OBJECT-TYPE
			SYNTAX IpAddress
			MAX-ACCESS read-create
			STATUS current
			DESCRIPTION
				"Description.
				IP address of the proxy server"
			::= { ccRadiusProxyServerEntry 3 }

		
		-- 1.3.6.1.4.1.388.6.9.2.3.1.4
		ccRadiusProxyServerPort OBJECT-TYPE
			SYNTAX Integer32 (1..65535)
			MAX-ACCESS read-create
			STATUS current
			DESCRIPTION
				"Description.
				Port of proxy server
				"
			::= { ccRadiusProxyServerEntry 4 }

		
		-- 1.3.6.1.4.1.388.6.9.2.3.1.5
		ccRadiusProxyServerSharedSecret OBJECT-TYPE
			SYNTAX DisplayString (SIZE (1..32))
			MAX-ACCESS read-create
			STATUS current
			DESCRIPTION
				"Description.
				Shared secret between radius server and proxy server
				"
			::= { ccRadiusProxyServerEntry 5 }

		
		-- 1.3.6.1.4.1.388.6.9.2.3.1.6
		ccRadiusProxyServerRowStatus OBJECT-TYPE
			SYNTAX AbbrevRowStatus
			MAX-ACCESS read-create
			STATUS current
			DESCRIPTION
				"Description.
				status"
			::= { ccRadiusProxyServerEntry 6 }

		
		-- 1.3.6.1.4.1.388.6.9.3
		ccRadiusLdap OBJECT IDENTIFIER ::= { ccRadiusServer 3 }

		
		-- 1.3.6.1.4.1.388.6.9.3.1
		ccRadiusLdap1Server OBJECT IDENTIFIER ::= { ccRadiusLdap 1 }

		
		-- 1.3.6.1.4.1.388.6.9.3.1.1
		ccRadiusLdap1ServerIp OBJECT-TYPE
			SYNTAX IpAddress
			MAX-ACCESS read-write
			STATUS current
			DESCRIPTION
				"IP address of the LDAP server"
			::= { ccRadiusLdap1Server 1 }

		
		-- 1.3.6.1.4.1.388.6.9.3.1.2
		ccRadiusLdap1ServerPort OBJECT-TYPE
			SYNTAX INTEGER (1..65535)
			MAX-ACCESS read-write
			STATUS current
			DESCRIPTION
				"Port of the LDAP server
				"
			::= { ccRadiusLdap1Server 2 }

		
		-- 1.3.6.1.4.1.388.6.9.3.1.3
		ccRadiusLdap1LoginAttribute OBJECT-TYPE
			SYNTAX DisplayString (SIZE (1..128))
			MAX-ACCESS read-write
			STATUS current
			DESCRIPTION
				"Name of the login attribute used by LDAP for 
				authenticating the user.
				"
			::= { ccRadiusLdap1Server 3 }

		
		-- 1.3.6.1.4.1.388.6.9.3.1.4
		ccRadiusLdap1PasswordAttribute OBJECT-TYPE
			SYNTAX Password (SIZE (1..64))
			MAX-ACCESS read-write
			STATUS current
			DESCRIPTION
				"Password attribute used by LDAP for authenticating the user.
				The maximum length for the password is 64 chars.
				"
			::= { ccRadiusLdap1Server 4 }

		
		-- 1.3.6.1.4.1.388.6.9.3.1.5
		ccRadiusLdap1BindDistinguishedName OBJECT-TYPE
			SYNTAX DisplayString (SIZE (1..128))
			MAX-ACCESS read-write
			STATUS current
			DESCRIPTION
				"Bind DN used the LDAP client on the WS5000 to connect to
				a LDAP server"
			::= { ccRadiusLdap1Server 5 }

		
		-- 1.3.6.1.4.1.388.6.9.3.1.6
		ccRadiusLdap1BindDistinguishedPassword OBJECT-TYPE
			SYNTAX Password (SIZE (1..32))
			MAX-ACCESS read-write
			STATUS current
			DESCRIPTION
				" Bind password used the LDAP client on the WS5000 
				 to connect to a LDAP server. 
				 The maximum length for the password is 32 chars."
			::= { ccRadiusLdap1Server 6 }

		
		-- 1.3.6.1.4.1.388.6.9.3.1.7
		ccRadiusLdap1BaseDistinguishedName OBJECT-TYPE
			SYNTAX DisplayString (SIZE (1..128))
			MAX-ACCESS read-write
			STATUS current
			DESCRIPTION
				"LDAP1 Distinguished Name."
			::= { ccRadiusLdap1Server 7 }

		
		-- 1.3.6.1.4.1.388.6.9.3.1.8
		ccRadiusLdap1GroupAttribute OBJECT-TYPE
			SYNTAX DisplayString (SIZE (1..32))
			MAX-ACCESS read-write
			STATUS current
			DESCRIPTION
				"  Name of the group attribute used by LDAP for 
				   retrieving the group associated with a user.
				"
			::= { ccRadiusLdap1Server 8 }

		
		-- 1.3.6.1.4.1.388.6.9.3.1.9
		ccRadiusLdap1GroupFilter OBJECT-TYPE
			SYNTAX DisplayString (SIZE (1..256))
			MAX-ACCESS read-write
			STATUS current
			DESCRIPTION
				"Filter specification used by the LDAP client to retrieve
				 	the groups associated with a user.The maximum of 256
					characters can be in the input for GroupFilter."
			::= { ccRadiusLdap1Server 9 }

		
		-- 1.3.6.1.4.1.388.6.9.3.1.10
		ccRadiusLdap1GroupMembershipAttribute OBJECT-TYPE
			SYNTAX DisplayString (SIZE (1..64))
			MAX-ACCESS read-write
			STATUS current
			DESCRIPTION
				"Name  of the attribute in the user schema 
				  which specifies groups associated with 
				  the user. This is used if the	group filter 
				  specified by ccRadiusGroupFilter return 
				  an error.
				"
			::= { ccRadiusLdap1Server 10 }

		
		-- 1.3.6.1.4.1.388.6.9.3.2
		ccRadiusLdap2Server OBJECT IDENTIFIER ::= { ccRadiusLdap 2 }

		
		-- 1.3.6.1.4.1.388.6.9.3.2.1
		ccRadiusLdap2ServerIp OBJECT-TYPE
			SYNTAX DisplayString
			MAX-ACCESS read-write
			STATUS current
			DESCRIPTION
				" LDAP2 is not supported at present.Hence this OID 
				  will not support any fuctionality."
			::= { ccRadiusLdap2Server 1 }

		
		-- 1.3.6.1.4.1.388.6.9.3.2.2
		ccRadiusLdap2ServerPort OBJECT-TYPE
			SYNTAX INTEGER (1..6)
			MAX-ACCESS read-write
			STATUS current
			DESCRIPTION
				" Port of the LDAP server2.
				  LDAP2 is not supported at present.Hence this OID 
				  will not support any fuctionality."
			::= { ccRadiusLdap2Server 2 }

		
		-- 1.3.6.1.4.1.388.6.9.3.2.3
		ccRadiusLdap2LoginAttribute OBJECT-TYPE
			SYNTAX DisplayString (SIZE (0..64))
			MAX-ACCESS read-write
			STATUS current
			DESCRIPTION
				" Name of the login attribute used by LDAP for 
				  authenticating the user.
				  LDAP2 is not supported at present.Hence this OID 
				  will not support any fuctionality."
			::= { ccRadiusLdap2Server 3 }

		
		-- 1.3.6.1.4.1.388.6.9.3.2.4
		ccRadiusLdap2PasswordATtribute OBJECT-TYPE
			SYNTAX Password (SIZE (1..64))
			MAX-ACCESS read-write
			STATUS current
			DESCRIPTION
				" Name of the login attribute used by LDAP for 
				  authenticating the user. 
				  The maximum length for the password is 64.   
				  LDAP2 is not supported at present.Hence this OID 
				  will not support any fuctionality."
			::= { ccRadiusLdap2Server 4 }

		
		-- 1.3.6.1.4.1.388.6.9.3.2.5
		ccRadiusLdap2BindDistinguishedName OBJECT-TYPE
			SYNTAX DisplayString (SIZE (0..128))
			MAX-ACCESS read-write
			STATUS current
			DESCRIPTION
				" Bind DN used the LDAP client on the WS5000 
				  to connect to a LDAP server.
				  LDAP2 is not supported at present.Hence this OID 
				  will not support any fuctionality."
			::= { ccRadiusLdap2Server 5 }

		
		-- 1.3.6.1.4.1.388.6.9.3.2.6
		ccRadiusLdap2BindDistinguishedPassword OBJECT-TYPE
			SYNTAX Password (SIZE (1..32))
			MAX-ACCESS read-write
			STATUS current
			DESCRIPTION
				"  Bind password used the LDAP client on the 
				   WS5000 to connect to a LDAP server.
				   The maximum length for the password is 32.   
				   LDAP2 is not supported at present.Hence this OID 
				   will not support any fuctionality."
			::= { ccRadiusLdap2Server 6 }

		
		-- 1.3.6.1.4.1.388.6.9.3.2.7
		ccRadiusLdap2BaseDistinguishedName OBJECT-TYPE
			SYNTAX DisplayString (SIZE (0..128))
			MAX-ACCESS read-write
			STATUS current
			DESCRIPTION
				" LDAP2 is not supported at present.Hence this OID 
				  will not support any fuctionality."
			::= { ccRadiusLdap2Server 7 }

		
		-- 1.3.6.1.4.1.388.6.9.3.2.8
		ccRadiusLdap2GroupAttribute OBJECT-TYPE
			SYNTAX DisplayString (SIZE (0..16))
			MAX-ACCESS read-write
			STATUS current
			DESCRIPTION
				"Name of the group attribute used by LDAP for retrieving the
				 	group associated with a user.
				LDAP2 is not supported at present.Hence this OID 
				will not support any fuctionality."
			::= { ccRadiusLdap2Server 8 }

		
		-- 1.3.6.1.4.1.388.6.9.3.2.9
		ccRadiusLdap2GroupFilter OBJECT-TYPE
			SYNTAX DisplayString (SIZE (0..128))
			MAX-ACCESS read-write
			STATUS current
			DESCRIPTION
				"Filter specification used by the LDAP client to retrieve
				 	the groups associated with a user.
				LDAP2 is not supported at present.Hence this OID 
				will not support any fuctionality."
			::= { ccRadiusLdap2Server 9 }

		
		-- 1.3.6.1.4.1.388.6.9.3.2.10
		ccRadiusLdap2GroupMembershipAttribute OBJECT-TYPE
			SYNTAX DisplayString (SIZE (0..32))
			MAX-ACCESS read-write
			STATUS current
			DESCRIPTION
				" Name of the attribute in the user schema 
				  which specifies groups associated with 
				  the user. This is used if the group 
				  filter specified by ccRadiusGroupFilter 
				  return an error.
				     LDAP2 is not supported at present.Hence this OID 
				  will not support any fuctionality."
			::= { ccRadiusLdap2Server 10 }

		
		-- 1.3.6.1.4.1.388.6.9.4
		ccRadiusUsers OBJECT IDENTIFIER ::= { ccRadiusServer 4 }

		
		-- 1.3.6.1.4.1.388.6.9.4.1
		ccRadiusGroupsTable OBJECT-TYPE
			SYNTAX SEQUENCE OF CcRadiusGroupsEntry
			MAX-ACCESS not-accessible
			STATUS current
			DESCRIPTION
				"Description."
			::= { ccRadiusUsers 1 }

		
		-- 1.3.6.1.4.1.388.6.9.4.1.1
		ccRadiusGroupsEntry OBJECT-TYPE
			SYNTAX CcRadiusGroupsEntry
			MAX-ACCESS not-accessible
			STATUS current
			DESCRIPTION
				"Description."
			INDEX { ccRadiusGroup }
			::= { ccRadiusGroupsTable 1 }

		
		CcRadiusGroupsEntry ::=
			SEQUENCE { 
				ccRadiusGroup
					DisplayString,
				ccRadiusGroupRowStatus
					AbbrevRowStatus
			 }

		-- 1.3.6.1.4.1.388.6.9.4.1.1.1
		ccRadiusGroup OBJECT-TYPE
			SYNTAX DisplayString (SIZE (0..8))
			MAX-ACCESS read-create
			STATUS current
			DESCRIPTION
				"Description.
				Name of the group"
			::= { ccRadiusGroupsEntry 1 }

		
		-- 1.3.6.1.4.1.388.6.9.4.1.1.2
		ccRadiusGroupRowStatus OBJECT-TYPE
			SYNTAX AbbrevRowStatus
			MAX-ACCESS read-create
			STATUS current
			DESCRIPTION
				"Row status shows the existence of the particular group.
				The valid input is 4 for Row creation and 6 for deletion
				of an existing row.
				"
			::= { ccRadiusGroupsEntry 2 }

		
		-- 1.3.6.1.4.1.388.6.9.4.2
		ccRadiusUsersTable OBJECT-TYPE
			SYNTAX SEQUENCE OF CcRadiusUsersEntry
			MAX-ACCESS not-accessible
			STATUS current
			DESCRIPTION
				"Description."
			::= { ccRadiusUsers 2 }

		
		-- 1.3.6.1.4.1.388.6.9.4.2.1
		ccRadiusUsersEntry OBJECT-TYPE
			SYNTAX CcRadiusUsersEntry
			MAX-ACCESS not-accessible
			STATUS current
			DESCRIPTION
				"Description."
			INDEX { ccRadiusUsersId }
			::= { ccRadiusUsersTable 1 }

		
		CcRadiusUsersEntry ::=
			SEQUENCE { 
				ccRadiusUsersId
					DisplayString,
				ccRadiusUsersPassword
					Password,
				ccRadiusUsersGroups
					BITS,
				ccRadiusUsersRowStatus
					AbbrevRowStatus
			 }

		-- 1.3.6.1.4.1.388.6.9.4.2.1.1
		ccRadiusUsersId OBJECT-TYPE
			SYNTAX DisplayString (SIZE (1..8))
			MAX-ACCESS read-create
			STATUS current
			DESCRIPTION
				"This OID is used to add a user. The user name can not be
				 greater 64 characters"
			::= { ccRadiusUsersEntry 1 }

		
		-- 1.3.6.1.4.1.388.6.9.4.2.1.2
		ccRadiusUsersPassword OBJECT-TYPE
			SYNTAX Password (SIZE (6..64))
			MAX-ACCESS read-create
			STATUS current
			DESCRIPTION
				"Set the password for the created UserID
								
				Note:User can also reset the password after the
				     creation of the UserID. "
			::= { ccRadiusUsersEntry 2 }

		
		-- 1.3.6.1.4.1.388.6.9.4.2.1.3
		ccRadiusUsersGroups OBJECT-TYPE
			SYNTAX BITS
				{
				null(0),
				g1(1),
				g2(2),
				g3(3),
				g4(4),
				g5(5),
				g6(6),
				g7(7),
				g8(8),
				g9(9),
				g10(10),
				g11(11),
				g12(12),
				g13(13),
				g14(14),
				g15(15),
				g16(16),
				g17(17),
				g18(18),
				g19(19),
				g20(20),
				g21(21),
				g22(22),
				g23(23),
				g24(24),
				g25(25),
				g26(26),
				g27(27),
				g28(28),
				g29(29),
				g30(30),
				g31(31),
				g32(32),
				g33(33),
				g34(34),
				g35(35),
				g36(36),
				g37(37),
				g38(38),
				g39(39),
				g40(40),
				g41(41),
				g42(42),
				g43(43),
				g44(44),
				g45(45),
				g46(46),
				g47(47),
				g48(48),
				g49(49),
				g50(50),
				g51(51),
				g52(52),
				g53(53),
				g54(54),
				g55(55),
				g56(56),
				g57(57),
				g58(58),
				g59(59),
				g60(60),
				g61(61),
				g62(62),
				g63(63),
				g64(64),
				g65(65),
				g66(66),
				g67(67),
				g68(68),
				g69(69),
				g70(70),
				g71(71),
				g72(72),
				g73(73),
				g74(74),
				g75(75),
				g76(76),
				g77(77),
				g78(78),
				g79(79),
				g80(80),
				g81(81),
				g82(82),
				g83(83),
				g84(84),
				g85(85),
				g86(86),
				g87(87),
				g88(88),
				g89(89),
				g90(90),
				g91(91),
				g92(92),
				g93(93),
				g94(94),
				g95(95),
				g96(96),
				g97(97),
				g98(98),
				g99(99),
				g100(100)
				}
			MAX-ACCESS read-create
			STATUS current
			DESCRIPTION
				" "
			::= { ccRadiusUsersEntry 3 }

		
		-- 1.3.6.1.4.1.388.6.9.4.2.1.4
		ccRadiusUsersRowStatus OBJECT-TYPE
			SYNTAX AbbrevRowStatus
			MAX-ACCESS read-create
			STATUS current
			DESCRIPTION
				"Description."
			::= { ccRadiusUsersEntry 4 }

		
		-- 1.3.6.1.4.1.388.6.9.5
		ccRadiusAccess OBJECT IDENTIFIER ::= { ccRadiusServer 5 }

		
		-- 1.3.6.1.4.1.388.6.9.5.1
		ccRadiusAccessTable OBJECT-TYPE
			SYNTAX SEQUENCE OF CcRadiusAccessEntry
			MAX-ACCESS not-accessible
			STATUS current
			DESCRIPTION
				"Description."
			::= { ccRadiusAccess 1 }

		
		-- 1.3.6.1.4.1.388.6.9.5.1.1
		ccRadiusAccessEntry OBJECT-TYPE
			SYNTAX CcRadiusAccessEntry
			MAX-ACCESS not-accessible
			STATUS current
			DESCRIPTION
				"Description."
			INDEX { ccRadiusGroup }
			::= { ccRadiusAccessTable 1 }

		
		CcRadiusAccessEntry ::=
			SEQUENCE { 
				ccRadiusAccessGroupId
					DisplayString,
				ccRadiusAccessWlanPtrs
					BITS
			 }

		-- 1.3.6.1.4.1.388.6.9.5.1.1.1
		ccRadiusAccessGroupId OBJECT-TYPE
			SYNTAX DisplayString
			MAX-ACCESS read-only
			STATUS current
			DESCRIPTION
				"Displays the GroupId for which coressponding
				 WLAN mapping is being dispalyed."
			::= { ccRadiusAccessEntry 1 }

		
		-- 1.3.6.1.4.1.388.6.9.5.1.1.2
		ccRadiusAccessWlanPtrs OBJECT-TYPE
			SYNTAX BITS
				{
				null(0),
				wlan1(1),
				wlan2(2),
				wlan3(3),
				wlan4(4),
				wlan5(5),
				wlan6(6),
				wlan7(7),
				wlan8(8),
				wlan9(9),
				wlan10(10),
				wlan11(11),
				wlan12(12),
				wlan13(13),
				wlan14(14),
				wlan15(15),
				wlan16(16),
				wlan17(17),
				wlan18(18),
				wlan19(19),
				wlan20(20),
				wlan21(21),
				wlan22(22),
				wlan23(23),
				wlan24(24),
				wlan25(25),
				wlan26(26),
				wlan27(27),
				wlan28(28),
				wlan29(29),
				wlan30(30),
				wlan31(31),
				wlan32(32),
				wlan33(33),
				wlan34(34),
				wlan35(35),
				wlan36(36),
				wlan37(37),
				wlan38(38),
				wlan39(39),
				wlan40(40),
				wlan41(41),
				wlan42(42),
				wlan43(43),
				wlan44(44),
				wlan45(45),
				wlan46(46),
				wlan47(47),
				wlan48(48),
				wlan49(49),
				wlan50(50),
				wlan51(51),
				wlan52(52),
				wlan53(53),
				wlan54(54),
				wlan55(55),
				wlan56(56),
				wlan57(57),
				wlan58(58),
				wlan59(59),
				wlan60(60),
				wlan61(61),
				wlan62(62),
				wlan63(63),
				wlan64(64),
				wlan65(65),
				wlan66(66),
				wlan67(67),
				wlan68(68),
				wlan69(69),
				wlan70(70),
				wlan71(71),
				wlan72(72),
				wlan73(73),
				wlan74(74),
				wlan75(75),
				wlan76(76),
				wlan77(77),
				wlan78(78),
				wlan79(79),
				wlan80(80)
				}
			MAX-ACCESS read-write
			STATUS current
			DESCRIPTION
				"
				"
			::= { ccRadiusAccessEntry 2 }

		
		-- 1.3.6.1.4.1.388.6.9.6
		ccRadiusAcct OBJECT IDENTIFIER ::= { ccRadiusServer 6 }

		
		-- 1.3.6.1.4.1.388.6.9.6.1
		ccRadiusAcctIPAddress OBJECT-TYPE
			SYNTAX IpAddress
			MAX-ACCESS read-write
			STATUS current
			DESCRIPTION
				"Description."
			::= { ccRadiusAcct 1 }

		
		-- 1.3.6.1.4.1.388.6.9.6.2
		ccRadiusAcctPort OBJECT-TYPE
			SYNTAX INTEGER (1..6)
			MAX-ACCESS read-write
			STATUS current
			DESCRIPTION
				"Description."
			::= { ccRadiusAcct 2 }

		
		-- 1.3.6.1.4.1.388.6.9.6.3
		ccRadiusAcctTimeout OBJECT-TYPE
			SYNTAX INTEGER (5..10)
			UNITS "seconds"
			MAX-ACCESS read-write
			STATUS current
			DESCRIPTION
				"Description."
			::= { ccRadiusAcct 3 }

		
		-- 1.3.6.1.4.1.388.6.9.6.4
		ccRadiusAcctMaxRetry OBJECT-TYPE
			SYNTAX Integer32
			MAX-ACCESS read-write
			STATUS current
			DESCRIPTION
				"Description."
			::= { ccRadiusAcct 4 }

		
		-- 1.3.6.1.4.1.388.6.9.6.5
		ccRadiusAcctSharedSecret OBJECT-TYPE
			SYNTAX OCTET STRING
			MAX-ACCESS read-write
			STATUS current
			DESCRIPTION
				"Description."
			::= { ccRadiusAcct 5 }

		
		-- 1.3.6.1.4.1.388.6.9.8
		ccRadiusTimeRestriction OBJECT IDENTIFIER ::= { ccRadiusServer 8 }

		
		-- 1.3.6.1.4.1.388.6.9.8.1
		ccRadiusTimeRestrictionTable OBJECT-TYPE
			SYNTAX SEQUENCE OF CcRadiusTimeRestrictionEntry
			MAX-ACCESS not-accessible
			STATUS current
			DESCRIPTION
				"A table for Radius Time Restrictions."
			::= { ccRadiusTimeRestriction 1 }

		
		-- 1.3.6.1.4.1.388.6.9.8.1.1
		ccRadiusTimeRestrictionEntry OBJECT-TYPE
			SYNTAX CcRadiusTimeRestrictionEntry
			MAX-ACCESS not-accessible
			STATUS current
			DESCRIPTION
				"Description."
			INDEX { ccRadiusGroup }
			::= { ccRadiusTimeRestrictionTable 1 }

		
		CcRadiusTimeRestrictionEntry ::=
			SEQUENCE { 
				ccRadiusTimeRestrictionStart
					DisplayString,
				ccRadiusTimeRestrictionEnd
					DisplayString,
				ccRadiusTimeRestrictionDays
					DisplayString
			 }

		-- 1.3.6.1.4.1.388.6.9.8.1.1.1
		ccRadiusTimeRestrictionStart OBJECT-TYPE
			SYNTAX DisplayString (SIZE (0..4))
			MAX-ACCESS read-write
			STATUS current
			DESCRIPTION
				"Radius Time Restriction's Start time"
			::= { ccRadiusTimeRestrictionEntry 1 }

		
		-- 1.3.6.1.4.1.388.6.9.8.1.1.2
		ccRadiusTimeRestrictionEnd OBJECT-TYPE
			SYNTAX DisplayString (SIZE (0..4))
			MAX-ACCESS read-write
			STATUS current
			DESCRIPTION
				"Radius Time Restriction's End time"
			::= { ccRadiusTimeRestrictionEntry 2 }

		
		-- 1.3.6.1.4.1.388.6.9.8.1.1.3
		ccRadiusTimeRestrictionDays OBJECT-TYPE
			SYNTAX DisplayString (SIZE (2..3))
			MAX-ACCESS read-write
			STATUS current
			DESCRIPTION
				"Radius Time Restriction in Days.
				Valid values are:
				Sa, Su, Mo, Tu, We, Th, Fr, All, Wk(weekdays).
				These values are Case sensitive.
				"
			::= { ccRadiusTimeRestrictionEntry 3 }

		
		-- 1.3.6.1.4.1.388.6.10
		ccRap OBJECT IDENTIFIER ::= { symbolCC 10 }

		
		-- 1.3.6.1.4.1.388.6.10.1
		ccRapControl OBJECT IDENTIFIER ::= { ccRap 1 }

		
		-- 1.3.6.1.4.1.388.6.10.1.1
		ccRapControlPollSymbolMus OBJECT IDENTIFIER ::= { ccRapControl 1 }

		
		-- 1.3.6.1.4.1.388.6.10.1.1.1
		ccRapPollSymbolMusEnable OBJECT-TYPE
			SYNTAX TruthValue
			MAX-ACCESS read-write
			STATUS current
			DESCRIPTION
				"Description.
				Enable/disable polling MUs for their lists of known
				 	APs.
				 	
				 	The state of this variable persists across reboots.
				 	The factory-default state is disabled.
				"
			::= { ccRapControlPollSymbolMus 1 }

		
		-- 1.3.6.1.4.1.388.6.10.1.1.2
		ccRapPollSymbolMusInterval OBJECT-TYPE
			SYNTAX Integer32
			UNITS "minutes"
			MAX-ACCESS read-write
			STATUS current
			DESCRIPTION
				"Description.
				Amount of time to wait before polling the same MU
				 	for its known AP list again.
				 	
				 	Assuming the MU is disrupted for 3sec when it is
				 	polled, a value of 5min or more would interrupt MUs
				 	less than 1% of the time.
				 	
				 	The state of this variable persists across reboots.
				 	The factory-default state is 20 (minutes).
				"
			::= { ccRapControlPollSymbolMus 2 }

		
		-- 1.3.6.1.4.1.388.6.10.1.2
		ccRapControlOnChannel OBJECT IDENTIFIER ::= { ccRapControl 2 }

		
		-- 1.3.6.1.4.1.388.6.10.1.2.1
		ccRapOnChannelEnable OBJECT-TYPE
			SYNTAX TruthValue
			MAX-ACCESS read-write
			STATUS current
			DESCRIPTION
				"Enable/disable polling MUs for their lists of known
				 	APs.
				 	
				 	The state of this variable persists across reboots.
				 	The factory-default state is disabled.
				"
			::= { ccRapControlOnChannel 1 }

		
		-- 1.3.6.1.4.1.388.6.10.1.2.2
		ccRapOnChannelInterval OBJECT-TYPE
			SYNTAX Integer32
			UNITS "minutes"
			MAX-ACCESS read-write
			STATUS current
			DESCRIPTION
				"Description.
				Amount of time to wait before polling the same MU
				 	for its known AP list again.
				 	
				 	Assuming the MU is disrupted for 3sec when it is
				 	polled, a value of 5min or more would interrupt MUs
				 	less than 1% of the time.
				 	
				 	The state of this variable persists across reboots.
				 	The factory-default state is 40 (minutes).
				"
			::= { ccRapControlOnChannel 2 }

		
		-- 1.3.6.1.4.1.388.6.10.1.3
		ccRapControlDetectors OBJECT IDENTIFIER ::= { ccRapControl 3 }

		
		-- 1.3.6.1.4.1.388.6.10.1.3.1
		ccRapDetectorsEnable OBJECT-TYPE
			SYNTAX TruthValue
			MAX-ACCESS read-write
			STATUS current
			DESCRIPTION
				"Enable/disable the entire 'detector' sub-system.
				 	
				 	On the true-to-false transition, any portals 
				 	previously claimed as listeners will be released
				 	and reset.  Once reset, they will appear to the
				 	switch as if just newly installed, (and thus
				 	may or may not be adopted depending on settings
				 	in the switch).
				 	
				 	The state of this variable persists across reboots.
				 	The factory-default state is disabled.
				"
			::= { ccRapControlDetectors 1 }

		
		-- 1.3.6.1.4.1.388.6.10.1.3.2
		ccRapDetectorsInterval OBJECT-TYPE
			SYNTAX Integer32
			UNITS "minutes"
			MAX-ACCESS read-write
			STATUS current
			DESCRIPTION
				"Description.
				Amount of time to wait before polling the same MU
				 	for its known AP list again.
				 	
				 	Assuming the MU is disrupted for 3sec when it is
				 	polled, a value of 5min or more would interrupt MUs
				 	less than 1% of the time.
				 	
				 	The state of this variable persists across reboots.
				 	The factory-default state is 60 (minutes).
				"
			::= { ccRapControlDetectors 2 }

		
		-- 1.3.6.1.4.1.388.6.10.2
		ccRapAuth OBJECT IDENTIFIER ::= { ccRap 2 }

		
		-- 1.3.6.1.4.1.388.6.10.2.1
		ccRapAuthList OBJECT IDENTIFIER ::= { ccRapAuth 1 }

		
		-- 1.3.6.1.4.1.388.6.10.2.1.1
		ccRapAuthAllSymbolMac OBJECT-TYPE
			SYNTAX TruthValue
			MAX-ACCESS read-write
			STATUS current
			DESCRIPTION
				"Description.
				If TRUE, any newly-discovered AP that has a MAC address
				 	with a Symbol vendor prefix is authorized, regardless
				 	of the ESSID.
				"
			::= { ccRapAuthList 1 }

		
		-- 1.3.6.1.4.1.388.6.10.2.1.2
		ccRapAuthTable OBJECT-TYPE
			SYNTAX SEQUENCE OF CcRapAuthEntry
			MAX-ACCESS not-accessible
			STATUS current
			DESCRIPTION
				"Description."
			::= { ccRapAuthList 2 }

		
		-- 1.3.6.1.4.1.388.6.10.2.1.2.1
		ccRapAuthEntry OBJECT-TYPE
			SYNTAX CcRapAuthEntry
			MAX-ACCESS not-accessible
			STATUS current
			DESCRIPTION
				"Description."
			INDEX { ccRapAuthIndex }
			::= { ccRapAuthTable 1 }

		
		CcRapAuthEntry ::=
			SEQUENCE { 
				ccRapAuthIndex
					Unsigned32,
				ccRapAuthMacFilter
					DisplayString,
				ccRapAuthEssidFilter
					DisplayString,
				ccRapAuthRowExists
					TruthValue
			 }

		-- 1.3.6.1.4.1.388.6.10.2.1.2.1.1
		ccRapAuthIndex OBJECT-TYPE
			SYNTAX Unsigned32 (1..24)
			MAX-ACCESS accessible-for-notify
			STATUS current
			DESCRIPTION
				"Description.
				Index"
			::= { ccRapAuthEntry 1 }

		
		-- 1.3.6.1.4.1.388.6.10.2.1.2.1.2
		ccRapAuthMacFilter OBJECT-TYPE
			SYNTAX DisplayString
			MAX-ACCESS read-write
			STATUS current
			DESCRIPTION
				"Description.
				MAC address of AP to consider 'authorized'.
				 	
				 	To specify the entire MAC address as a wildcard, 
				 	(match any MAC address), use FF:FF:FF:FF:FF:FF.
				 	
				 	(While it had been considered, it is NOT possible to
				 	wildcard just the vendor portion of the MAC).
				         
				         An individual SET is not supported. Created only thru'
				        a row create.
				"
			::= { ccRapAuthEntry 2 }

		
		-- 1.3.6.1.4.1.388.6.10.2.1.2.1.3
		ccRapAuthEssidFilter OBJECT-TYPE
			SYNTAX DisplayString
			MAX-ACCESS read-write
			STATUS current
			DESCRIPTION
				"Description.
				ESSID of AP to consider 'authorized'.
				 	
				 	Set to 33 '*' characters for wildcard, (to match 
				 	any ESSID).  (ESSIDs must be 32ch or less).
				"
			::= { ccRapAuthEntry 3 }

		
		-- 1.3.6.1.4.1.388.6.10.2.1.2.1.4
		ccRapAuthRowExists OBJECT-TYPE
			SYNTAX TruthValue
			MAX-ACCESS read-write
			STATUS current
			DESCRIPTION
				"Description.
				A kludge to avoid RowStatus and save development
				 	time.
				 	
				 	Set this value to true when creating the row.  Set
				 	this value to false to destroy the row.
				 	
				 	??- better name.
				"
			::= { ccRapAuthEntry 4 }

		
		-- 1.3.6.1.4.1.388.6.10.2.1.3
		ccRapAuthErase OBJECT-TYPE
			SYNTAX DoActionNow
			MAX-ACCESS read-write
			STATUS current
			DESCRIPTION
				"Setting this value to TRUE erases all AuthTable entries."
			::= { ccRapAuthList 3 }

		
		-- 1.3.6.1.4.1.388.6.10.2.1.4
		ccRapAuthCopyAllApproved OBJECT-TYPE
			SYNTAX DoActionNow
			MAX-ACCESS read-write
			STATUS current
			DESCRIPTION
				"Causes all ccRapResultsApprovedTable entries to be
				 	immediately copied to the ccRapAuthTable.
				"
			::= { ccRapAuthList 4 }

		
		-- 1.3.6.1.4.1.388.6.10.2.1.5
		ccRapAuthCopyAllRogue OBJECT-TYPE
			SYNTAX DoActionNow
			MAX-ACCESS read-write
			STATUS current
			DESCRIPTION
				"Description."
			::= { ccRapAuthList 5 }

		
		-- 1.3.6.1.4.1.388.6.10.3
		ccRapResults OBJECT IDENTIFIER ::= { ccRap 3 }

		
		-- 1.3.6.1.4.1.388.6.10.3.1
		ccRapResultsApproved OBJECT IDENTIFIER ::= { ccRapResults 1 }

		
		-- 1.3.6.1.4.1.388.6.10.3.1.1
		ccRapResultsApprovedAgeOut OBJECT-TYPE
			SYNTAX Integer32
			UNITS "minutes"
			MAX-ACCESS read-write
			STATUS current
			DESCRIPTION
				"Description.
				If an entry in the _ResultsApproved table is not heard
				 	by any means for this number of minutes, is elligable 
				 	to be removed from the table by the switch;  (the
				 	switch, however, might not remove the entry until 
				 	it gets around to it).
				 	
				 	A value of 0 indicates that entries will never be
				 	'aged-out' of the table.
				 	
				 	The state of this variable persists across reboots.
				 	The factory-default state is 1 week, (10080 min).
				"
			::= { ccRapResultsApproved 1 }

		
		-- 1.3.6.1.4.1.388.6.10.3.1.2
		ccRapResultsApprovedTable OBJECT-TYPE
			SYNTAX SEQUENCE OF CcRapResultsApprovedEntry
			MAX-ACCESS not-accessible
			STATUS current
			DESCRIPTION
				"Description."
			::= { ccRapResultsApproved 2 }

		
		-- 1.3.6.1.4.1.388.6.10.3.1.2.1
		ccRapResultsApprovedEntry OBJECT-TYPE
			SYNTAX CcRapResultsApprovedEntry
			MAX-ACCESS not-accessible
			STATUS current
			DESCRIPTION
				"Description."
			INDEX { ccRapResultsApprovedIndex }
			::= { ccRapResultsApprovedTable 1 }

		
		CcRapResultsApprovedEntry ::=
			SEQUENCE { 
				ccRapResultsApprovedIndex
					Unsigned32,
				ccRapResultsApprovedApMac
					DisplayString,
				ccRapResultsApprovedEssid
					DisplayString,
				ccRapResultsApprovedCopyToAuthTable
					DoActionNow,
				ccRapResultsApprovedFirstHeard
					DisplayString,
				ccRapResultsApprovedLastHeard
					DisplayString,
				ccRapResultsApprovedPortalPtr
					MultiPointer255,
				ccRapResultsApprovedHowFound
					DisplayString,
				ccRapResultsApprovedHowAuth
					DisplayString,
				ccRapResultsApprovedRowErase
					DoActionNow
			 }

		-- 1.3.6.1.4.1.388.6.10.3.1.2.1.1
		ccRapResultsApprovedIndex OBJECT-TYPE
			SYNTAX Unsigned32 (1..50)
			MAX-ACCESS accessible-for-notify
			STATUS current
			DESCRIPTION
				"Description."
			::= { ccRapResultsApprovedEntry 1 }

		
		-- 1.3.6.1.4.1.388.6.10.3.1.2.1.2
		ccRapResultsApprovedApMac OBJECT-TYPE
			SYNTAX DisplayString
			MAX-ACCESS read-only
			STATUS current
			DESCRIPTION
				"Description.
				MAC address of the heard AP."
			::= { ccRapResultsApprovedEntry 2 }

		
		-- 1.3.6.1.4.1.388.6.10.3.1.2.1.3
		ccRapResultsApprovedEssid OBJECT-TYPE
			SYNTAX DisplayString
			MAX-ACCESS read-only
			STATUS current
			DESCRIPTION
				"Description.
				ESSID of the heard AP"
			::= { ccRapResultsApprovedEntry 3 }

		
		-- 1.3.6.1.4.1.388.6.10.3.1.2.1.4
		ccRapResultsApprovedCopyToAuthTable OBJECT-TYPE
			SYNTAX DoActionNow
			MAX-ACCESS read-write
			STATUS current
			DESCRIPTION
				"Description.
				When set to TRUE, this entry is copied to the RuleTable.
				"
			::= { ccRapResultsApprovedEntry 4 }

		
		-- 1.3.6.1.4.1.388.6.10.3.1.2.1.5
		ccRapResultsApprovedFirstHeard OBJECT-TYPE
			SYNTAX DisplayString
			MAX-ACCESS read-only
			STATUS current
			DESCRIPTION
				"Description.
				Snapshot of sysUpTime the first time this AP 
				 	MAC/ESSID combination was heard by any Symbol MU.
				"
			::= { ccRapResultsApprovedEntry 5 }

		
		-- 1.3.6.1.4.1.388.6.10.3.1.2.1.6
		ccRapResultsApprovedLastHeard OBJECT-TYPE
			SYNTAX DisplayString
			MAX-ACCESS read-only
			STATUS current
			DESCRIPTION
				"Description.
				Snapshot of sysUpTime the most recent time this AP 
				 	MAC/ESSID combination was heard by any Symbol MU.
				"
			::= { ccRapResultsApprovedEntry 6 }

		
		-- 1.3.6.1.4.1.388.6.10.3.1.2.1.7
		ccRapResultsApprovedPortalPtr OBJECT-TYPE
			SYNTAX MultiPointer255
			MAX-ACCESS read-only
			STATUS current
			DESCRIPTION
				"Description.
				A mask of Portal table entries.  Those Portal
				 	entries indicated by a '1' in this mask were at one
				 	time the servicing Portal for an MU that reported 
				 	hearing this AP.
				 	
				 	For a rogue of limited range in the parking lot on 
				 	the north side of a store, it would be expected that
				 	only the Portals located in the north end of the 
				 	store would be indicated by this mask, thus giving
				 	a rough indication of general direction of the
				 	rogue.
				
				        This is currently not-supported.
				"
			::= { ccRapResultsApprovedEntry 7 }

		
		-- 1.3.6.1.4.1.388.6.10.3.1.2.1.8
		ccRapResultsApprovedHowFound OBJECT-TYPE
			SYNTAX DisplayString
			MAX-ACCESS read-only
			STATUS current
			DESCRIPTION
				"Description.
				Describes the status of this AP.
				 	
				 	??- I don't think we would report adoptedAp on the 
				 	results table, so don't need this enum value.
				"
			::= { ccRapResultsApprovedEntry 8 }

		
		-- 1.3.6.1.4.1.388.6.10.3.1.2.1.9
		ccRapResultsApprovedHowAuth OBJECT-TYPE
			SYNTAX DisplayString
			MAX-ACCESS read-only
			STATUS current
			DESCRIPTION
				"Description.
				Describes how this AP was authorized, (or not).
				 	
				 	The order in which the various methods of authorizing APs
				 	is attempted is exactly the numerical order of the enums.
				 	
				 	??- I deleted adoptedAp, since it seems to me that there
				 	is no good reason to report APs that this switch has
				 	adopted.
				"
			::= { ccRapResultsApprovedEntry 9 }

		
		-- 1.3.6.1.4.1.388.6.10.3.1.2.1.10
		ccRapResultsApprovedRowErase OBJECT-TYPE
			SYNTAX DoActionNow
			MAX-ACCESS read-write
			STATUS current
			DESCRIPTION
				"Set this to 1 to erase this row. In Idle state it returns 2."
			::= { ccRapResultsApprovedEntry 10 }

		
		-- 1.3.6.1.4.1.388.6.10.3.1.3
		ccRapResultsApprovedErase OBJECT-TYPE
			SYNTAX DoActionNow
			MAX-ACCESS read-write
			STATUS current
			DESCRIPTION
				"Description.
				Setting this value to TRUE erases all Results entries.
				 	
				 	Any APs heard after that event will be treated as newly
				 	heard;  (which means they will also generate notifications,
				 	if enabled).
				 	
				 	??- need 2nd scalar.
				"
			::= { ccRapResultsApproved 3 }

		
		-- 1.3.6.1.4.1.388.6.10.3.2
		ccRapResultsRogue OBJECT IDENTIFIER ::= { ccRapResults 2 }

		
		-- 1.3.6.1.4.1.388.6.10.3.2.1
		ccRapResultsRogueAgeOut OBJECT-TYPE
			SYNTAX Integer32
			UNITS "minutes"
			MAX-ACCESS read-write
			STATUS current
			DESCRIPTION
				"Description.
				If an entry in the _ResultsRogue table is not heard
				 	by any means for this number of minutes, is elligable 
				 	to be removed from the table by the switch;  (the
				 	switch, however, might not remove the entry until 
				 	it gets around to it).
				 	
				 	A value of 0 indicates that entries will never be
				 	'aged-out' of the table.
				 	
				 	The state of this variable persists across reboots.
				 	The factory-default state is 1 week, (10080 min).
				"
			::= { ccRapResultsRogue 1 }

		
		-- 1.3.6.1.4.1.388.6.10.3.2.2
		ccRapResultsRogueTable OBJECT-TYPE
			SYNTAX SEQUENCE OF CcRapResultsRogueEntry
			MAX-ACCESS not-accessible
			STATUS current
			DESCRIPTION
				"Description."
			::= { ccRapResultsRogue 2 }

		
		-- 1.3.6.1.4.1.388.6.10.3.2.2.1
		ccRapResultsRogueEntry OBJECT-TYPE
			SYNTAX CcRapResultsRogueEntry
			MAX-ACCESS not-accessible
			STATUS current
			DESCRIPTION
				"Description."
			INDEX { ccRapResultsRogueIndex }
			::= { ccRapResultsRogueTable 1 }

		
		CcRapResultsRogueEntry ::=
			SEQUENCE { 
				ccRapResultsRogueIndex
					Unsigned32,
				ccRapResultsRogueApMac
					DisplayString,
				ccRapResultsRogueEssid
					DisplayString,
				ccRapResultsRogueCopyToAuthTable
					DoActionNow,
				ccRapResultsRogueFirstHeard
					DisplayString,
				ccRapResultsRogueLastHeard
					DisplayString,
				ccRapResultsRoguePortalPtr
					MultiPointer255,
				ccRapResultsRogueHowFound
					DisplayString,
				ccRapResultsRogueClosestPortalPtr
					DisplayString,
				ccRapResultsRogueClosestPortalRssi
					Integer32
			 }

		-- 1.3.6.1.4.1.388.6.10.3.2.2.1.1
		ccRapResultsRogueIndex OBJECT-TYPE
			SYNTAX Unsigned32 (1..50)
			MAX-ACCESS accessible-for-notify
			STATUS current
			DESCRIPTION
				"Description."
			::= { ccRapResultsRogueEntry 1 }

		
		-- 1.3.6.1.4.1.388.6.10.3.2.2.1.2
		ccRapResultsRogueApMac OBJECT-TYPE
			SYNTAX DisplayString
			MAX-ACCESS read-only
			STATUS current
			DESCRIPTION
				"Description.
				MAC address of the heard AP"
			::= { ccRapResultsRogueEntry 2 }

		
		-- 1.3.6.1.4.1.388.6.10.3.2.2.1.3
		ccRapResultsRogueEssid OBJECT-TYPE
			SYNTAX DisplayString
			MAX-ACCESS read-only
			STATUS current
			DESCRIPTION
				"Description.
				ESSID of the heard AP"
			::= { ccRapResultsRogueEntry 3 }

		
		-- 1.3.6.1.4.1.388.6.10.3.2.2.1.4
		ccRapResultsRogueCopyToAuthTable OBJECT-TYPE
			SYNTAX DoActionNow
			MAX-ACCESS read-write
			STATUS current
			DESCRIPTION
				"Description.
				When set to TRUE, this entry is copied to the RuleTable.
				"
			::= { ccRapResultsRogueEntry 4 }

		
		-- 1.3.6.1.4.1.388.6.10.3.2.2.1.5
		ccRapResultsRogueFirstHeard OBJECT-TYPE
			SYNTAX DisplayString
			MAX-ACCESS read-only
			STATUS current
			DESCRIPTION
				"Description.
				Snapshot of sysUpTime the first time this AP 
				 	MAC/ESSID combination was heard by any Symbol MU.
				"
			::= { ccRapResultsRogueEntry 5 }

		
		-- 1.3.6.1.4.1.388.6.10.3.2.2.1.6
		ccRapResultsRogueLastHeard OBJECT-TYPE
			SYNTAX DisplayString
			MAX-ACCESS read-only
			STATUS current
			DESCRIPTION
				"Description.
				Snapshot of sysUpTime the most recent time this AP 
				 	MAC/ESSID combination was heard by any Symbol MU.
				"
			::= { ccRapResultsRogueEntry 6 }

		
		-- 1.3.6.1.4.1.388.6.10.3.2.2.1.7
		ccRapResultsRoguePortalPtr OBJECT-TYPE
			SYNTAX MultiPointer255
			MAX-ACCESS read-only
			STATUS current
			DESCRIPTION
				"Description.
				A mask of Portal table entries.  Those Portal
				 	entries indicated by a '1' in this mask were at one
				 	time the servicing Portal for an MU that reported 
				 	hearing this AP.
				 	
				 	For a rogue of limited range in the parking lot on 
				 	the north side of a store, it would be expected that
				 	only the Portals located in the north end of the 
				 	store would be indicated by this mask, thus giving
				 	a rough indication of general direction of the
				 	rogue.
				
				        This is currently not supported.
				"
			::= { ccRapResultsRogueEntry 7 }

		
		-- 1.3.6.1.4.1.388.6.10.3.2.2.1.8
		ccRapResultsRogueHowFound OBJECT-TYPE
			SYNTAX DisplayString
			MAX-ACCESS read-only
			STATUS current
			DESCRIPTION
				"Description.
				Describes the status of this AP.
				 	
				 	??- I don't think we would report adoptedAp on the 
				 	results table, so don't need this enum value.
				"
			::= { ccRapResultsRogueEntry 8 }

		
		-- 1.3.6.1.4.1.388.6.10.3.2.2.1.9
		ccRapResultsRogueClosestPortalPtr OBJECT-TYPE
			SYNTAX DisplayString
			MAX-ACCESS read-only
			STATUS current
			DESCRIPTION
				"A pointer to closest reporting Portal to the Rogue AP,
				 	(where 'closest' is defined as greatest RSSI value
				 	among all Portals reporting this AP).
				"
			::= { ccRapResultsRogueEntry 9 }

		
		-- 1.3.6.1.4.1.388.6.10.3.2.2.1.10
		ccRapResultsRogueClosestPortalRssi OBJECT-TYPE
			SYNTAX Integer32
			MAX-ACCESS read-only
			STATUS current
			DESCRIPTION
				"Description.
				RSSI reported by the closest Portal.
				"
			::= { ccRapResultsRogueEntry 10 }

		
		-- 1.3.6.1.4.1.388.6.10.3.2.3
		ccRapResultsRogueErase OBJECT-TYPE
			SYNTAX DoActionNow
			MAX-ACCESS read-write
			STATUS current
			DESCRIPTION
				"Description.
				Setting this value to TRUE erases all Results entries.
				 	
				 	Any APs heard after that event will be treated as newly
				 	heard;  (which means they will also generate notifications,
				 	if enabled).
				 	
				 	??- need 2nd scalar.
				"
			::= { ccRapResultsRogue 3 }

		
		-- 1.3.6.1.4.1.388.6.11
		ccImageDload OBJECT IDENTIFIER ::= { symbolCC 11 }

		
		-- 1.3.6.1.4.1.388.6.11.1
		ccRestore OBJECT-TYPE
			SYNTAX DisplayString
			MAX-ACCESS read-write
			STATUS current
			DESCRIPTION
				"Restore a new system image, a new configuration or a standby configuration on the switch.
				 	The syntax is :
				 	<system/config/standby>,<filename>
				 	
				 	system:  Restore system image. The corresponding <filename> should be a image file.
				 	config:  Restore a new configuration. the corresponding <filename> should be a .cfg file.
				 	standby: Restore a standby configuration.
				
				A GET on this oid will give the current status of the SET operation.
				The restore operation may take upto 10 minutes and hence the manager may not
				be able to contact the switch during this process.
				
				 	
				"
			::= { ccImageDload 1 }

		
		-- 1.3.6.1.4.1.388.6.11.2
		ccFtp OBJECT-TYPE
			SYNTAX DisplayString
			MAX-ACCESS read-write
			STATUS current
			DESCRIPTION
				"FTP an image file, configuration file to the switch from an external server 
				on a SET operation.
				 	The files will be transferred to the default directory in the switch ie /image.
				 	Syntax:
				 	<FtpServer IPAddr>,<username>,<password>,<directory path>,<filename>
				
				        The time taken to finish the file transfer will depend on the 
				        size of the file.
				        
				        A GET on this OID will show the previous status for this operation."
			::= { ccImageDload 2 }

		
		-- 1.3.6.1.4.1.388.6.11.3
		ccTftp OBJECT-TYPE
			SYNTAX DisplayString
			MAX-ACCESS read-write
			STATUS current
			DESCRIPTION
				"Transfer files thru' tftp on a SET operation.
				 	
				 	TFTP a image file, configuration file to the switch from an external server.
				 	The files will be transferred to the default directory in the switch ie /image.
				 	Syntax:
				 	    <TftpServer IPAddr>,<filename>
				 	Files will be picked-up from the default /tftpboot directory or 
				        from the directory configured by the tftp server.
				
				        A GET will show the previous status of this operation.
				 	
				"
			::= { ccImageDload 3 }

		
		-- 1.3.6.1.4.1.388.6.11.4
		ccListFiles OBJECT-TYPE
			SYNTAX DisplayString
			MAX-ACCESS read-only
			STATUS current
			DESCRIPTION
				"Do a GET to list all the files present in the /image directory.
				"
			::= { ccImageDload 4 }

		
		-- 1.3.6.1.4.1.388.6.11.5
		ccDeleteFiles OBJECT-TYPE
			SYNTAX DisplayString
			MAX-ACCESS read-write
			STATUS current
			DESCRIPTION
				"A SET will delete files in the /image directory.
				 	Syntax: <filename>
				 	See ccListFiles to see a list of files in /image directory.
				
				A GET will return the status of the previous operation.
				"
			::= { ccImageDload 5 }

		
--  1.3.6.1.4.1.388.6.16
		-- 1.3.6.1.4.1.388.6.16
		ccRFStatistics OBJECT IDENTIFIER ::= { symbolCC 16 }

		
--  1.3.6.1.4.1.388.6.16.1
		-- 1.3.6.1.4.1.388.6.16.1
		ccAp OBJECT IDENTIFIER ::= { ccRFStatistics 1 }

		
--  1.3.6.1.4.1.388.6.12.1.1
		-- 1.3.6.1.4.1.388.6.16.1.1
		ccApTable OBJECT-TYPE
			SYNTAX SEQUENCE OF CcApEntry
			MAX-ACCESS not-accessible
			STATUS current
			DESCRIPTION
				"Description."
			::= { ccAp 1 }

		
--  1.3.6.1.4.1.388.6.12.1.1.1
		-- 1.3.6.1.4.1.388.6.16.1.1.1
		ccApEntry OBJECT-TYPE
			SYNTAX CcApEntry
			MAX-ACCESS not-accessible
			STATUS current
			DESCRIPTION
				"Description."
			INDEX { ccApIndex }
			::= { ccApTable 1 }

		
		CcApEntry ::=
			SEQUENCE { 
				ccApIndex
					Integer32,
				ccApNicMac
					DisplayString,
				ccApModelNumber
					DisplayString,
				ccApSerialNumber
					DisplayString,
				ccApPcbRevision
					DisplayString,
				ccApBootLoaderRev
					DisplayString,
				ccApWispVersion
					DisplayString,
				ccApRuntimeFwVersion
					DisplayString,
				ccApNumPortals
					Unsigned32,
				ccApPointersToPortals
					MultiPointer255
			 }

--  1.3.6.1.4.1.388.6.12.1.1.1.1
		-- 1.3.6.1.4.1.388.6.16.1.1.1.1
		ccApIndex OBJECT-TYPE
			SYNTAX Integer32 (1..255)
			MAX-ACCESS accessible-for-notify
			STATUS current
			DESCRIPTION
				"Small, arbitrary integer index"
			::= { ccApEntry 1 }

		
--  1.3.6.1.4.1.388.6.12.1.1.1.2
		-- 1.3.6.1.4.1.388.6.16.1.1.1.2
		ccApNicMac OBJECT-TYPE
			SYNTAX DisplayString
			MAX-ACCESS read-only
			STATUS current
			DESCRIPTION
				"MAC Address of this Access Port"
			::= { ccApEntry 2 }

		
--  1.3.6.1.4.1.388.6.12.1.1.1.3
		-- 1.3.6.1.4.1.388.6.16.1.1.1.3
		ccApModelNumber OBJECT-TYPE
			SYNTAX DisplayString
			MAX-ACCESS read-only
			STATUS current
			DESCRIPTION
				"Model number of Access Port"
			::= { ccApEntry 3 }

		
--  1.3.6.1.4.1.388.6.12.1.1.1.4
		-- 1.3.6.1.4.1.388.6.16.1.1.1.4
		ccApSerialNumber OBJECT-TYPE
			SYNTAX DisplayString
			MAX-ACCESS read-only
			STATUS current
			DESCRIPTION
				"Serial Number of this Access Port"
			::= { ccApEntry 4 }

		
--  1.3.6.1.4.1.388.6.12.1.1.1.5
		-- 1.3.6.1.4.1.388.6.16.1.1.1.5
		ccApPcbRevision OBJECT-TYPE
			SYNTAX DisplayString
			MAX-ACCESS read-only
			STATUS current
			DESCRIPTION
				"Revision of the printed circuit board for this Access Port"
			::= { ccApEntry 5 }

		
--  1.3.6.1.4.1.388.6.12.1.1.1.6
		-- 1.3.6.1.4.1.388.6.16.1.1.1.6
		ccApBootLoaderRev OBJECT-TYPE
			SYNTAX DisplayString
			MAX-ACCESS read-only
			STATUS current
			DESCRIPTION
				"Revision of the boot loader code in this Access Port."
			::= { ccApEntry 6 }

		
--  1.3.6.1.4.1.388.6.12.1.1.1.7
		-- 1.3.6.1.4.1.388.6.16.1.1.1.7
		ccApWispVersion OBJECT-TYPE
			SYNTAX DisplayString
			MAX-ACCESS read-only
			STATUS current
			DESCRIPTION
				"Version of the WISP (AP-Switch) protocol implemented by this Access Port."
			::= { ccApEntry 7 }

		
--  1.3.6.1.4.1.388.6.12.1.1.1.8
		-- 1.3.6.1.4.1.388.6.16.1.1.1.8
		ccApRuntimeFwVersion OBJECT-TYPE
			SYNTAX DisplayString
			MAX-ACCESS read-only
			STATUS current
			DESCRIPTION
				"Version of run-time code on this Access Port."
			::= { ccApEntry 8 }

		
--  1.3.6.1.4.1.388.6.12.1.1.1.9
		-- 1.3.6.1.4.1.388.6.16.1.1.1.9
		ccApNumPortals OBJECT-TYPE
			SYNTAX Unsigned32
			MAX-ACCESS read-only
			STATUS current
			DESCRIPTION
				"The number of Portals implemented on this Access Port."
			::= { ccApEntry 9 }

		
--  1.3.6.1.4.1.388.6.12.1.1.1.10
		-- 1.3.6.1.4.1.388.6.16.1.1.1.10
		ccApPointersToPortals OBJECT-TYPE
			SYNTAX MultiPointer255
			MAX-ACCESS read-only
			STATUS current
			DESCRIPTION
				"If bit <n> of this value is set, this ApTable entry 'points' to entry <n> in the Portal Table.
				
				Such a reference conveys that the Portal entry pointed-to represents a Portal contained in the Access Port
				represented by this entry.
				
				Note that since one Access Port can implement 1, 2, (and in the future possibly more), Portals, 
				this 'pointer' field had to be a bit-mask."
			::= { ccApEntry 10 }

		
--  1.3.6.1.4.1.388.6.12.2
		-- 1.3.6.1.4.1.388.6.16.2
		ccPortal OBJECT IDENTIFIER ::= { ccRFStatistics 2 }

		
--  1.3.6.1.4.1.388.6.12.2.1
		-- 1.3.6.1.4.1.388.6.16.2.1
		ccPortalTable OBJECT-TYPE
			SYNTAX SEQUENCE OF CcPortalEntry
			MAX-ACCESS not-accessible
			STATUS current
			DESCRIPTION
				"This Table gives general information about the Radio."
			::= { ccPortal 1 }

		
--  1.3.6.1.4.1.388.6.12.2.1.1
		-- 1.3.6.1.4.1.388.6.16.2.1.1
		ccPortalEntry OBJECT-TYPE
			SYNTAX CcPortalEntry
			MAX-ACCESS not-accessible
			STATUS current
			DESCRIPTION
				"Description."
			INDEX { ccPortalIndex }
			::= { ccPortalTable 1 }

		
		CcPortalEntry ::=
			SEQUENCE { 
				ccPortalIndex
					INTEGER,
				ccPortalPointerToAp
					SinglePointer,
				ccPortalPointersToWlans
					MultiPointer63,
				ccPortalName
					DisplayString,
				ccPortalLocation
					DisplayString,
				ccPortalOptions
					BITS,
				ccPortalMac
					DisplayString,
				ccPortalNumberofEss
					Integer32,
				ccPortalNumberOfBss
					Integer32,
				ccPortalAssociatedMus
					Integer32,
				ccPortalRadioType
					RadioType,
				ccPortalChannel
					INTEGER,
				ccPortalTxPowerLevel
					Integer32,
				ccPortalLastAdoption
					TimeTicks,
				ccPortalState
					INTEGER,
				ccPortalBackgroundNoiseNumSamples
					Counter32,
				ccPortalBackgroundNoiseBest
					Integer32,
				ccPortalBackgroundNoiseWorst
					Integer32,
				ccPortalBackgroundNoiseSum
					Integer32,
				ccPortalBackgroundNoiseSumSquares
					Counter64
			 }

--  1.3.6.1.4.1.388.6.12.2.1.1.1
		-- 1.3.6.1.4.1.388.6.16.2.1.1.1
		ccPortalIndex OBJECT-TYPE
			SYNTAX INTEGER (1..255)
			MAX-ACCESS accessible-for-notify
			STATUS current
			DESCRIPTION
				"Small, arbitrary integer index."
			::= { ccPortalEntry 1 }

		
--  1.3.6.1.4.1.388.6.12.2.1.1.2
		-- 1.3.6.1.4.1.388.6.16.2.1.1.2
		ccPortalPointerToAp OBJECT-TYPE
			SYNTAX SinglePointer
			MAX-ACCESS read-only
			STATUS current
			DESCRIPTION
				"This value is the index in the ApTable for the
				entry representing the Access Port that contains
				this Radio
				
				Since each Portal has one and only one Access Port
				as 'Parent', this value is a simple integer, not a bit-mask."
			::= { ccPortalEntry 2 }

		
--  1.3.6.1.4.1.388.6.12.2.1.1.3
		-- 1.3.6.1.4.1.388.6.16.2.1.1.3
		ccPortalPointersToWlans OBJECT-TYPE
			SYNTAX MultiPointer63
			MAX-ACCESS read-only
			STATUS current
			DESCRIPTION
				"(Reserved for future implementation)."
			::= { ccPortalEntry 3 }

		
--  1.3.6.1.4.1.388.6.12.2.1.1.4
		-- 1.3.6.1.4.1.388.6.16.2.1.1.4
		ccPortalName OBJECT-TYPE
			SYNTAX DisplayString
			MAX-ACCESS read-only
			STATUS current
			DESCRIPTION
				"Name of this Radio, as assigned by the Web UI
				or CLI."
			::= { ccPortalEntry 4 }

		
--  1.3.6.1.4.1.388.6.12.2.1.1.5
		-- 1.3.6.1.4.1.388.6.16.2.1.1.5
		ccPortalLocation OBJECT-TYPE
			SYNTAX DisplayString
			MAX-ACCESS read-only
			STATUS current
			DESCRIPTION
				"Location string for this Radio, as assigned by
				the Web UI or CLI"
			::= { ccPortalEntry 5 }

		
--  1.3.6.1.4.1.388.6.12.2.1.1.6
		-- 1.3.6.1.4.1.388.6.16.2.1.1.6
		ccPortalOptions OBJECT-TYPE
			SYNTAX BITS
				{
				undefined00(0),
				undefined01(1),
				undefined02(2),
				undefined03(3),
				undefined04(4),
				undefined05(5),
				undefined06(6),
				undefined07(7),
				undefined08(8),
				undefined09(9),
				undefined10(10),
				undefined11(11),
				externalSecondaryAntInstalled(12),
				internalSecondaryAntInstalled(13),
				externalPrimaryAntInstalled(14),
				internalPrimaryAntInstalled(15)
				}
			MAX-ACCESS read-only
			STATUS current
			DESCRIPTION
				"This value describes the presence/absence of 
				internal and/or external primary and/or secondary antennas."
			::= { ccPortalEntry 6 }

		
--  1.3.6.1.4.1.388.6.12.2.1.1.7
		-- 1.3.6.1.4.1.388.6.16.2.1.1.7
		ccPortalMac OBJECT-TYPE
			SYNTAX DisplayString
			MAX-ACCESS read-only
			STATUS current
			DESCRIPTION
				"MAC address of the Radio."
			::= { ccPortalEntry 7 }

		
--  1.3.6.1.4.1.388.6.12.2.1.1.8
		-- 1.3.6.1.4.1.388.6.16.2.1.1.8
		ccPortalNumberofEss OBJECT-TYPE
			SYNTAX Integer32
			MAX-ACCESS read-only
			STATUS current
			DESCRIPTION
				"The number of ESSs implemented by this Radio"
			::= { ccPortalEntry 8 }

		
--  1.3.6.1.4.1.388.6.12.2.1.1.9
		-- 1.3.6.1.4.1.388.6.16.2.1.1.9
		ccPortalNumberOfBss OBJECT-TYPE
			SYNTAX Integer32
			MAX-ACCESS read-only
			STATUS current
			DESCRIPTION
				"The number of BSSs implemented by this Radio"
			::= { ccPortalEntry 9 }

		
--  1.3.6.1.4.1.388.6.12.2.1.1.10
		-- 1.3.6.1.4.1.388.6.16.2.1.1.10
		ccPortalAssociatedMus OBJECT-TYPE
			SYNTAX Integer32
			MAX-ACCESS read-only
			STATUS current
			DESCRIPTION
				"The number of MUs currently associated to this Radio"
			::= { ccPortalEntry 10 }

		
--  1.3.6.1.4.1.388.6.12.2.1.1.11
		-- 1.3.6.1.4.1.388.6.16.2.1.1.11
		ccPortalRadioType OBJECT-TYPE
			SYNTAX RadioType
			MAX-ACCESS read-only
			STATUS current
			DESCRIPTION
				"Radio type of the Radio"
			::= { ccPortalEntry 11 }

		
--  1.3.6.1.4.1.388.6.12.2.1.1.12
		-- 1.3.6.1.4.1.388.6.16.2.1.1.12
		ccPortalChannel OBJECT-TYPE
			SYNTAX INTEGER
				{
				ieee802dot11bChannel01(1),
				ieee802dot11bChannel02(2),
				ieee802dot11bChannel03(3),
				ieee802dot11bChannel04(4),
				ieee802dot11bChannel05(5),
				ieee802dot11bChannel06(6),
				ieee802dot11bChannel07(7),
				ieee802dot11bChannel08(8),
				ieee802dot11bChannel09(9),
				ieee802dot11bChannel10(10),
				ieee802dot11bChannel11(11),
				ieee802dot11bChannel12(12),
				ieee802dot11bChannel13(13),
				ieee802dot11bChannel14(14),
				ieee802dot11aChannel036(36),
				ieee802dot11aChannel040(40),
				ieee802dot11aChannel044(44),
				ieee802dot11aChannel048(48),
				ieee802dot11aChannel052(52),
				ieee802dot11aChannel056(56),
				ieee802dot11aChannel060(60),
				ieee802dot11aChannel064(64),
				ieee802dot11aChannel149(149),
				ieee802dot11aChannel153(153),
				ieee802dot11aChannel157(157),
				ieee802dot11aChannel161(161)
				}
			MAX-ACCESS read-only
			STATUS current
			DESCRIPTION
				"The value describes the channel the Radio is currently operating on."
			::= { ccPortalEntry 12 }

		
--  1.3.6.1.4.1.388.6.12.2.1.1.13
		-- 1.3.6.1.4.1.388.6.16.2.1.1.13
		ccPortalTxPowerLevel OBJECT-TYPE
			SYNTAX Integer32 (0..255)
			UNITS "milli-Watts"
			MAX-ACCESS read-only
			STATUS current
			DESCRIPTION
				"Output power level for the Radio"
			::= { ccPortalEntry 13 }

		
--  1.3.6.1.4.1.388.6.12.2.1.1.14
		-- 1.3.6.1.4.1.388.6.16.2.1.1.14
		ccPortalLastAdoption OBJECT-TYPE
			SYNTAX TimeTicks
			MAX-ACCESS read-only
			STATUS current
			DESCRIPTION
				"A snapshot of the WS5000's sysUpTime when this Radio was last adopted."
			::= { ccPortalEntry 14 }

		
--  1.3.6.1.4.1.388.6.12.2.1.1.15
		-- 1.3.6.1.4.1.388.6.16.2.1.1.15
		ccPortalState OBJECT-TYPE
			SYNTAX INTEGER
				{
				offline(0),
				active(1),
				alert(3),
				reset(4)
				}
			MAX-ACCESS read-only
			STATUS current
			DESCRIPTION
				"This value describes the state of the Radio
				A healthy Portal would power-on, and quickly advance from 
				   portalUpAndWaitingForConfig and then on to
				   portalReceivingConfig and then on to
				   portalUpAndAdopted.
				
				A Portal that is denied adoption due to ACLs would show:
				   portalDeniedAdoptionDueToAcl.
				
				A Portal that does not 'handshake' with the switch properly
				would be found in state:
				   portalBroken."
			::= { ccPortalEntry 15 }

		
--  1.3.6.1.4.1.388.6.12.2.1.1.16
		-- 1.3.6.1.4.1.388.6.16.2.1.1.16
		ccPortalBackgroundNoiseNumSamples OBJECT-TYPE
			SYNTAX Counter32
			MAX-ACCESS read-only
			STATUS current
			DESCRIPTION
				"Total packets received via the Radio included in 
				all the other countries reported in this row."
			::= { ccPortalEntry 16 }

		
--  1.3.6.1.4.1.388.6.12.2.1.1.17
		-- 1.3.6.1.4.1.388.6.16.2.1.1.17
		ccPortalBackgroundNoiseBest OBJECT-TYPE
			SYNTAX Integer32
			UNITS "dBm"
			MAX-ACCESS read-only
			STATUS current
			DESCRIPTION
				"The best Signal value seen from the Radio so far. 
				(Remember that a -20dBm Signal is better than -60dBm).
				
				This value is initialized to 500dBm."
			::= { ccPortalEntry 17 }

		
--  1.3.6.1.4.1.388.6.12.2.1.1.18
		-- 1.3.6.1.4.1.388.6.16.2.1.1.18
		ccPortalBackgroundNoiseWorst OBJECT-TYPE
			SYNTAX Integer32
			UNITS "dBm"
			MAX-ACCESS read-only
			STATUS current
			DESCRIPTION
				"The worst Signal value seen from the Radio so far.
				(Remember that a -80dBm Signal is worse than -60dBm).
				
				This value is initialized to -500dBm."
			::= { ccPortalEntry 18 }

		
--  1.3.6.1.4.1.388.6.12.2.1.1.19
		-- 1.3.6.1.4.1.388.6.16.2.1.1.19
		ccPortalBackgroundNoiseSum OBJECT-TYPE
			SYNTAX Integer32
			UNITS "dBm"
			MAX-ACCESS read-only
			STATUS current
			DESCRIPTION
				"A running sum of all Signal values calculated by the 
				switch (using reported RSSI values), for packets received
				via this Radio.
				
				Note that this value is normally a negative value 
				ranging from -10dBm to -80dBm. It is possible for this
				value to be positive, but that would be rare, and would
				signal an exceptionally strong signal.
				
				(This value divided by ccPortalRxRssiNumPkts yields the average
				Signal value for all packets received from this Radio)."
			::= { ccPortalEntry 19 }

		
--  1.3.6.1.4.1.388.6.12.2.1.1.20
		-- 1.3.6.1.4.1.388.6.16.2.1.1.20
		ccPortalBackgroundNoiseSumSquares OBJECT-TYPE
			SYNTAX Counter64
			UNITS "dBm"
			MAX-ACCESS read-only
			STATUS current
			DESCRIPTION
				"A sum of the squares of each Signal value calculated
				for packets received via this Radio
				Unlike _SignalSum, this value is never negative, since the square
				of a negative number is a positive.
				
				(This value can be used to calculate the standard
				deviation for Signal values calculated for packets
				from this Radio)."
			::= { ccPortalEntry 20 }

		
--  1.3.6.1.4.1.388.6.12.2.2
		-- 1.3.6.1.4.1.388.6.16.2.2
		ccPortalLastMac OBJECT-TYPE
			SYNTAX DisplayString
			MAX-ACCESS read-only
			STATUS current
			DESCRIPTION
				"This scalar records the MAC address of the most
				recent Radio to be Adopted, UnAdopted, or Denied."
			::= { ccPortal 2 }

		
--  1.3.6.1.4.1.388.6.12.2.3
		-- 1.3.6.1.4.1.388.6.16.2.3
		ccPortalLastReason OBJECT-TYPE
			SYNTAX INTEGER
				{
				success(1),
				aclViolation(2),
				timeout(3)
				}
			MAX-ACCESS read-only
			STATUS current
			DESCRIPTION
				"This value notes the reason for the most-recent
				Radio UnAdoption or Denial."
			::= { ccPortal 3 }

		
--  1.3.6.1.4.1.388.6.12.2.5
		-- 1.3.6.1.4.1.388.6.16.2.5
		ccPortalSystemStatsTable OBJECT-TYPE
			SYNTAX SEQUENCE OF CcPortalSystemStatsEntry
			MAX-ACCESS not-accessible
			STATUS current
			DESCRIPTION
				"The table contains information about various management packets.
				Transmitted/Receieved by a Radio"
			::= { ccPortal 5 }

		
--  1.3.6.1.4.1.388.6.12.2.5.1
		-- 1.3.6.1.4.1.388.6.16.2.5.1
		ccPortalSystemStatsEntry OBJECT-TYPE
			SYNTAX CcPortalSystemStatsEntry
			MAX-ACCESS not-accessible
			STATUS current
			DESCRIPTION
				"Description."
			INDEX { ccPortalIndex }
			::= { ccPortalSystemStatsTable 1 }

		
		CcPortalSystemStatsEntry ::=
			SEQUENCE { 
				ccPortalSystemStatsBeaconTx
					Integer32,
				ccPortalSystemStatsBeaconsTxOctets
					Unsigned32,
				ccPortalSystemStatsProbeReqRx
					Unsigned32,
				ccPortalSystemStatsProbeReqRxOctets
					Unsigned32,
				ccPortalSystemStatsProbeRespRetriesNone
					Unsigned32,
				ccPortalSystemStatsProbeRespRetries1
					Unsigned32,
				ccPortalSystemStatsProbeRespRetries2
					Unsigned32,
				ccPortalSystemStatsProbeRespRetries3OrMore
					Unsigned32,
				ccPortalSystemStatsProbeRespRetriesFailed
					Unsigned32,
				ccPortalSystemStatsProbeRespTxOctets
					Unsigned32
			 }

--  1.3.6.1.4.1.388.6.12.2.5.1.1
		-- 1.3.6.1.4.1.388.6.16.2.5.1.1
		ccPortalSystemStatsBeaconTx OBJECT-TYPE
			SYNTAX Integer32
			MAX-ACCESS read-only
			STATUS current
			DESCRIPTION
				"The number of Beacons sent."
			::= { ccPortalSystemStatsEntry 1 }

		
--  1.3.6.1.4.1.388.6.12.2.5.1.2
		-- 1.3.6.1.4.1.388.6.16.2.5.1.2
		ccPortalSystemStatsBeaconsTxOctets OBJECT-TYPE
			SYNTAX Unsigned32
			MAX-ACCESS read-only
			STATUS current
			DESCRIPTION
				"The number of octets sent in Beacons."
			::= { ccPortalSystemStatsEntry 2 }

		
--  1.3.6.1.4.1.388.6.12.2.5.1.3
		-- 1.3.6.1.4.1.388.6.16.2.5.1.3
		ccPortalSystemStatsProbeReqRx OBJECT-TYPE
			SYNTAX Unsigned32
			MAX-ACCESS read-only
			STATUS current
			DESCRIPTION
				"The number of Probe Request packets received."
			::= { ccPortalSystemStatsEntry 3 }

		
--  1.3.6.1.4.1.388.6.12.2.5.1.4
		-- 1.3.6.1.4.1.388.6.16.2.5.1.4
		ccPortalSystemStatsProbeReqRxOctets OBJECT-TYPE
			SYNTAX Unsigned32
			MAX-ACCESS read-only
			STATUS current
			DESCRIPTION
				"The number of octets received in Probe Request packets."
			::= { ccPortalSystemStatsEntry 4 }

		
--  1.3.6.1.4.1.388.6.12.2.5.1.5
		-- 1.3.6.1.4.1.388.6.16.2.5.1.5
		ccPortalSystemStatsProbeRespRetriesNone OBJECT-TYPE
			SYNTAX Unsigned32
			MAX-ACCESS read-only
			STATUS current
			DESCRIPTION
				"The number of Probe Response packets sent with no retries."
			::= { ccPortalSystemStatsEntry 5 }

		
--  1.3.6.1.4.1.388.6.12.2.5.1.6
		-- 1.3.6.1.4.1.388.6.16.2.5.1.6
		ccPortalSystemStatsProbeRespRetries1 OBJECT-TYPE
			SYNTAX Unsigned32
			MAX-ACCESS read-only
			STATUS current
			DESCRIPTION
				"The number of Probe Response packets sent with exactly
				1 retry"
			::= { ccPortalSystemStatsEntry 6 }

		
--  1.3.6.1.4.1.388.6.12.2.5.1.7
		-- 1.3.6.1.4.1.388.6.16.2.5.1.7
		ccPortalSystemStatsProbeRespRetries2 OBJECT-TYPE
			SYNTAX Unsigned32
			MAX-ACCESS read-only
			STATUS current
			DESCRIPTION
				"The number of Probe Response packets sent with exactly
				2 retries."
			::= { ccPortalSystemStatsEntry 7 }

		
--  1.3.6.1.4.1.388.6.12.2.5.1.8
		-- 1.3.6.1.4.1.388.6.16.2.5.1.8
		ccPortalSystemStatsProbeRespRetries3OrMore OBJECT-TYPE
			SYNTAX Unsigned32
			MAX-ACCESS read-only
			STATUS current
			DESCRIPTION
				"The number of Probe Response packets sent with exactly
				3 retries or more retries."
			::= { ccPortalSystemStatsEntry 8 }

		
--  1.3.6.1.4.1.388.6.12.2.5.1.9
		-- 1.3.6.1.4.1.388.6.16.2.5.1.9
		ccPortalSystemStatsProbeRespRetriesFailed OBJECT-TYPE
			SYNTAX Unsigned32
			MAX-ACCESS read-only
			STATUS current
			DESCRIPTION
				"The number of Probe Response packets that were never
				successfully transmitted because the max retry count was
				reached."
			::= { ccPortalSystemStatsEntry 9 }

		
--  1.3.6.1.4.1.388.6.12.2.5.1.10
		-- 1.3.6.1.4.1.388.6.16.2.5.1.10
		ccPortalSystemStatsProbeRespTxOctets OBJECT-TYPE
			SYNTAX Unsigned32
			MAX-ACCESS read-only
			STATUS current
			DESCRIPTION
				"The number of octets successfully transmitted in Probe
				Response packets. (For example, the octets in a Probe 
				Response that is transmitted twice - one retry - only counts
				once in this sum)."
			::= { ccPortalSystemStatsEntry 10 }

		
--   !!- OID: .100
-- 1.3.6.1.4.1.388.11.2.4.2.100
-- 1.3.6.1.4.1.388.6.12.2.6
		-- 1.3.6.1.4.1.388.6.16.2.6
		ccPortalRfSum OBJECT IDENTIFIER ::= { ccPortal 6 }

		
--   1.3.6.1.4.1.388.11.2.4.2.100.1
-- 1.3.6.1.4.1.388.6.12.2.6.1
		-- 1.3.6.1.4.1.388.6.16.2.6.1
		ccPortalStatsTable OBJECT-TYPE
			SYNTAX SEQUENCE OF CcPortalStatsEntry
			MAX-ACCESS not-accessible
			STATUS current
			DESCRIPTION
				"This table describes general statistics about
				packets sent/recieved via each Portal on the switch."
			::= { ccPortalRfSum 1 }

		
--   1.3.6.1.4.1.388.11.2.4.2.100.1.1
-- 1.3.6.1.4.1.388.6.12.2.6.1.1
		-- 1.3.6.1.4.1.388.6.16.2.6.1.1
		ccPortalStatsEntry OBJECT-TYPE
			SYNTAX CcPortalStatsEntry
			MAX-ACCESS not-accessible
			STATUS current
			DESCRIPTION
				" "
			INDEX { ccPortalIndex }
			::= { ccPortalStatsTable 1 }

		
		CcPortalStatsEntry ::=
			SEQUENCE { 
				ccPortalTxPktsUcast
					Counter32,
				ccPortalRxPktsUcast
					Counter32,
				ccPortalRxPktsNUcast
					Counter32,
				ccPortalTxOctetsUcast
					Counter32,
				ccPortalRxOctetsUcast
					Counter32,
				ccPortalRxOctetsNUcast
					Counter32,
				ccPortalRxUndecryptablePkts
					Counter32,
				ccPortalLastActivity
					TimeTicks
			 }

--   1.3.6.1.4.1.388.11.2.4.2.100.1.1.1
-- 1.3.6.1.4.1.388.6.12.2.6.1.1.1
		-- 1.3.6.1.4.1.388.6.16.2.6.1.1.1
		ccPortalTxPktsUcast OBJECT-TYPE
			SYNTAX Counter32
			MAX-ACCESS read-only
			STATUS current
			DESCRIPTION
				"Count of unicast packets sent via the Radio"
			::= { ccPortalStatsEntry 1 }

		
--   1.3.6.1.4.1.388.11.2.4.2.100.1.1.2
-- 1.3.6.1.4.1.388.6.12.2.6.1.1.2
		-- 1.3.6.1.4.1.388.6.16.2.6.1.1.2
		ccPortalRxPktsUcast OBJECT-TYPE
			SYNTAX Counter32
			MAX-ACCESS read-only
			STATUS current
			DESCRIPTION
				"Count of unicast packets received via the Radio."
			::= { ccPortalStatsEntry 2 }

		
--   1.3.6.1.4.1.388.11.2.4.2.100.1.1.3
-- 1.3.6.1.4.1.388.6.12.2.6.1.1.3
		-- 1.3.6.1.4.1.388.6.16.2.6.1.1.3
		ccPortalRxPktsNUcast OBJECT-TYPE
			SYNTAX Counter32
			MAX-ACCESS read-only
			STATUS current
			DESCRIPTION
				"Count of non-unicast (broadcast & multicast) 
				packets received via the Radio"
			::= { ccPortalStatsEntry 3 }

		
--   1.3.6.1.4.1.388.11.2.4.2.100.1.1.4
-- 1.3.6.1.4.1.388.6.12.2.6.1.1.4
		-- 1.3.6.1.4.1.388.6.16.2.6.1.1.4
		ccPortalTxOctetsUcast OBJECT-TYPE
			SYNTAX Counter32
			MAX-ACCESS read-only
			STATUS current
			DESCRIPTION
				"Count of unicast octets sent via the Radio"
			::= { ccPortalStatsEntry 4 }

		
--   1.3.6.1.4.1.388.11.2.4.2.100.1.1.5
-- 1.3.6.1.4.1.388.6.12.2.6.1.1.5
		-- 1.3.6.1.4.1.388.6.16.2.6.1.1.5
		ccPortalRxOctetsUcast OBJECT-TYPE
			SYNTAX Counter32
			MAX-ACCESS read-only
			STATUS current
			DESCRIPTION
				"Count of unicast octets received via the Radio"
			::= { ccPortalStatsEntry 5 }

		
--   1.3.6.1.4.1.388.11.2.4.2.100.1.1.6
-- 1.3.6.1.4.1.388.6.12.2.6.1.1.6
		-- 1.3.6.1.4.1.388.6.16.2.6.1.1.6
		ccPortalRxOctetsNUcast OBJECT-TYPE
			SYNTAX Counter32
			MAX-ACCESS read-only
			STATUS current
			DESCRIPTION
				"Count of non-unicast (broadcast & multicast) 
				octets received via the Radio"
			::= { ccPortalStatsEntry 6 }

		
--   1.3.6.1.4.1.388.11.2.4.2.100.1.1.7
-- 1.3.6.1.4.1.388.6.12.2.6.1.1.7
		-- 1.3.6.1.4.1.388.6.16.2.6.1.1.7
		ccPortalRxUndecryptablePkts OBJECT-TYPE
			SYNTAX Counter32
			MAX-ACCESS read-only
			STATUS current
			DESCRIPTION
				"Count of packets received via the Radio that could
				not be decrypted."
			::= { ccPortalStatsEntry 7 }

		
--   1.3.6.1.4.1.388.11.2.4.2.100.1.1.8
-- 1.3.6.1.4.1.388.6.12.2.6.1.1.8
		-- 1.3.6.1.4.1.388.6.16.2.6.1.1.8
		ccPortalLastActivity OBJECT-TYPE
			SYNTAX TimeTicks
			MAX-ACCESS read-only
			STATUS current
			DESCRIPTION
				"A snapshot of the switch's sysUpTime at the time
				of the last activity (packet sent or received)
				via the Radio"
			::= { ccPortalStatsEntry 8 }

		
--   1.3.6.1.4.1.388.11.2.4.2.100.2
-- 1.3.6.1.4.1.388.6.12.2.6.2
		-- 1.3.6.1.4.1.388.6.16.2.6.2
		ccPortalRxPktsTable OBJECT-TYPE
			SYNTAX SEQUENCE OF CcPortalRxPktsEntry
			MAX-ACCESS not-accessible
			STATUS current
			DESCRIPTION
				"For each MU serviced by the switch, this table 
				describes counts of packets received at each 
				possible speed, (1Mb, 2Mb, 5.5Mb, 6Mb...)."
			::= { ccPortalRfSum 2 }

		
--   1.3.6.1.4.1.388.11.2.4.2.100.2.1
-- 1.3.6.1.4.1.388.6.12.2.6.2.1
		-- 1.3.6.1.4.1.388.6.16.2.6.2.1
		ccPortalRxPktsEntry OBJECT-TYPE
			SYNTAX CcPortalRxPktsEntry
			MAX-ACCESS not-accessible
			STATUS current
			DESCRIPTION
				" "
			INDEX { ccPortalIndex }
			::= { ccPortalRxPktsTable 1 }

		
		CcPortalRxPktsEntry ::=
			SEQUENCE { 
				ccPortalRxPktsAt1Mb
					Counter32,
				ccPortalRxPktsAt2Mb
					Counter32,
				ccPortalRxPktsAt5pt5Mb
					Counter32,
				ccPortalRxPktsAt6Mb
					Counter32,
				ccPortalRxPktsAt9Mb
					Counter32,
				ccPortalRxPktsAt11Mb
					Counter32,
				ccPortalRxPktsAt12Mb
					Counter32,
				ccPortalRxPktsAt18Mb
					Counter32,
				ccPortalRxPktsAt22Mb
					Counter32,
				ccPortalRxPktsAt24Mb
					Counter32,
				ccPortalRxPktsAt36Mb
					Counter32,
				ccPortalRxPktsAt48Mb
					Counter32,
				ccPortalRxPktsAt54Mb
					Counter32
			 }

--   1.3.6.1.4.1.388.11.2.4.2.100.2.1.1
-- 1.3.6.1.4.1.388.6.12.2.6.2.1.1
		-- 1.3.6.1.4.1.388.6.16.2.6.2.1.1
		ccPortalRxPktsAt1Mb OBJECT-TYPE
			SYNTAX Counter32
			MAX-ACCESS read-only
			STATUS current
			DESCRIPTION
				"Number of pkts received via this Radio at 1 Mbps."
			::= { ccPortalRxPktsEntry 1 }

		
--   1.3.6.1.4.1.388.11.2.4.2.100.2.1.2
-- 1.3.6.1.4.1.388.6.12.2.6.2.1.2
		-- 1.3.6.1.4.1.388.6.16.2.6.2.1.2
		ccPortalRxPktsAt2Mb OBJECT-TYPE
			SYNTAX Counter32
			MAX-ACCESS read-only
			STATUS current
			DESCRIPTION
				"Number of pkts received via this Radio at 2 Mbps."
			::= { ccPortalRxPktsEntry 2 }

		
--   1.3.6.1.4.1.388.11.2.4.2.100.2.1.3
-- 1.3.6.1.4.1.388.6.12.2.6.2.1.3
		-- 1.3.6.1.4.1.388.6.16.2.6.2.1.3
		ccPortalRxPktsAt5pt5Mb OBJECT-TYPE
			SYNTAX Counter32
			MAX-ACCESS read-only
			STATUS current
			DESCRIPTION
				"Number of pkts received via this Radio at 5.5 Mbps."
			::= { ccPortalRxPktsEntry 3 }

		
--   1.3.6.1.4.1.388.11.2.4.2.100.2.1.4
-- 1.3.6.1.4.1.388.6.12.2.6.2.1.4
		-- 1.3.6.1.4.1.388.6.16.2.6.2.1.4
		ccPortalRxPktsAt6Mb OBJECT-TYPE
			SYNTAX Counter32
			MAX-ACCESS read-only
			STATUS current
			DESCRIPTION
				"Number of pkts received via this Radio at 6 Mbps."
			::= { ccPortalRxPktsEntry 4 }

		
--   1.3.6.1.4.1.388.11.2.4.2.100.2.1.5
-- 1.3.6.1.4.1.388.6.12.2.6.2.1.5
		-- 1.3.6.1.4.1.388.6.16.2.6.2.1.5
		ccPortalRxPktsAt9Mb OBJECT-TYPE
			SYNTAX Counter32
			MAX-ACCESS read-only
			STATUS current
			DESCRIPTION
				"Number of pkts received via this Portal at 9 Mbps."
			::= { ccPortalRxPktsEntry 5 }

		
--   1.3.6.1.4.1.388.11.2.4.2.100.2.1.6
-- 1.3.6.1.4.1.388.6.12.2.6.2.1.6
		-- 1.3.6.1.4.1.388.6.16.2.6.2.1.6
		ccPortalRxPktsAt11Mb OBJECT-TYPE
			SYNTAX Counter32
			MAX-ACCESS read-only
			STATUS current
			DESCRIPTION
				"Number of pkts received via this Radio at 11 Mbps."
			::= { ccPortalRxPktsEntry 6 }

		
--   1.3.6.1.4.1.388.11.2.4.2.100.2.1.7
-- 1.3.6.1.4.1.388.6.12.2.6.2.1.7
		-- 1.3.6.1.4.1.388.6.16.2.6.2.1.7
		ccPortalRxPktsAt12Mb OBJECT-TYPE
			SYNTAX Counter32
			MAX-ACCESS read-only
			STATUS current
			DESCRIPTION
				"Number of pkts received via this Radio at 12 Mbps."
			::= { ccPortalRxPktsEntry 7 }

		
--   1.3.6.1.4.1.388.11.2.4.2.100.2.1.8
-- 1.3.6.1.4.1.388.6.12.2.6.2.1.8
		-- 1.3.6.1.4.1.388.6.16.2.6.2.1.8
		ccPortalRxPktsAt18Mb OBJECT-TYPE
			SYNTAX Counter32
			MAX-ACCESS read-only
			STATUS current
			DESCRIPTION
				"Number of pkts received via this Radio at 18 Mbps."
			::= { ccPortalRxPktsEntry 8 }

		
--   1.3.6.1.4.1.388.11.2.4.2.100.2.1.9
-- 1.3.6.1.4.1.388.6.12.2.6.2.1.9
		-- 1.3.6.1.4.1.388.6.16.2.6.2.1.9
		ccPortalRxPktsAt22Mb OBJECT-TYPE
			SYNTAX Counter32
			MAX-ACCESS read-only
			STATUS current
			DESCRIPTION
				"Number of pkts received via this Radio at 22 Mbps."
			::= { ccPortalRxPktsEntry 9 }

		
--   1.3.6.1.4.1.388.11.2.4.2.100.2.1.10
-- 1.3.6.1.4.1.388.6.12.2.6.2.1.10
		-- 1.3.6.1.4.1.388.6.16.2.6.2.1.10
		ccPortalRxPktsAt24Mb OBJECT-TYPE
			SYNTAX Counter32
			MAX-ACCESS read-only
			STATUS current
			DESCRIPTION
				"Number of pkts received via this Radio at 24 Mbps."
			::= { ccPortalRxPktsEntry 10 }

		
--   1.3.6.1.4.1.388.11.2.4.2.100.2.1.11
-- 1.3.6.1.4.1.388.6.12.2.6.2.1.11
		-- 1.3.6.1.4.1.388.6.16.2.6.2.1.11
		ccPortalRxPktsAt36Mb OBJECT-TYPE
			SYNTAX Counter32
			MAX-ACCESS read-only
			STATUS current
			DESCRIPTION
				"Number of pkts received via this Radio at 36 Mbps."
			::= { ccPortalRxPktsEntry 11 }

		
--   1.3.6.1.4.1.388.11.2.4.2.100.2.1.12
-- 1.3.6.1.4.1.388.6.12.2.6.2.1.12
		-- 1.3.6.1.4.1.388.6.16.2.6.2.1.12
		ccPortalRxPktsAt48Mb OBJECT-TYPE
			SYNTAX Counter32
			MAX-ACCESS read-only
			STATUS current
			DESCRIPTION
				"Number of pkts received via this Radio at 48 Mbps."
			::= { ccPortalRxPktsEntry 12 }

		
--   1.3.6.1.4.1.388.11.2.4.2.100.2.1.13
-- 1.3.6.1.4.1.388.6.12.2.6.2.1.13
		-- 1.3.6.1.4.1.388.6.16.2.6.2.1.13
		ccPortalRxPktsAt54Mb OBJECT-TYPE
			SYNTAX Counter32
			MAX-ACCESS read-only
			STATUS current
			DESCRIPTION
				"Number of pkts received via this Radio at 54 Mbps."
			::= { ccPortalRxPktsEntry 13 }

		
--   1.3.6.1.4.1.388.11.2.4.2.100.3
-- 1.3.6.1.4.1.388.6.12.2.6.3
		-- 1.3.6.1.4.1.388.6.16.2.6.3
		ccPortalTxPktsTable OBJECT-TYPE
			SYNTAX SEQUENCE OF CcPortalTxPktsEntry
			MAX-ACCESS not-accessible
			STATUS current
			DESCRIPTION
				"For each MU serviced by the switch, this table 
				describes counts of packets received at each 
				possible speed, (1Mb, 2Mb, 5.5Mb, 6Mb...)."
			::= { ccPortalRfSum 3 }

		
--   1.3.6.1.4.1.388.11.2.4.2.100.3.1
-- 1.3.6.1.4.1.388.6.12.2.6.3.1
		-- 1.3.6.1.4.1.388.6.16.2.6.3.1
		ccPortalTxPktsEntry OBJECT-TYPE
			SYNTAX CcPortalTxPktsEntry
			MAX-ACCESS not-accessible
			STATUS current
			DESCRIPTION
				" "
			INDEX { ccPortalIndex }
			::= { ccPortalTxPktsTable 1 }

		
		CcPortalTxPktsEntry ::=
			SEQUENCE { 
				ccPortalTxPktsAt1Mb
					Counter32,
				ccPortalTxPktsAt2Mb
					Counter32,
				ccPortalTxPktsAt5pt5Mb
					Counter32,
				ccPortalTxPktsAt6Mb
					Counter32,
				ccPortalTxPktsAt9Mb
					Counter32,
				ccPortalTxPktsAt11Mb
					Counter32,
				ccPortalTxPktsAt12Mb
					Counter32,
				ccPortalTxPktsAt18Mb
					Counter32,
				ccPortalTxPktsAt22Mb
					Counter32,
				ccPortalTxPktsAt24Mb
					Counter32,
				ccPortalTxPktsAt36Mb
					Counter32,
				ccPortalTxPktsAt48Mb
					Counter32,
				ccPortalTxPktsAt54Mb
					Counter32
			 }

--   1.3.6.1.4.1.388.11.2.4.2.100.3.1.1
-- 1.3.6.1.4.1.388.6.12.2.6.3.1.1
		-- 1.3.6.1.4.1.388.6.16.2.6.3.1.1
		ccPortalTxPktsAt1Mb OBJECT-TYPE
			SYNTAX Counter32
			MAX-ACCESS read-only
			STATUS current
			DESCRIPTION
				"Number of pkts transmitted via this Radio at 1 Mbps."
			::= { ccPortalTxPktsEntry 1 }

		
--   1.3.6.1.4.1.388.11.2.4.2.100.3.1.2
-- 1.3.6.1.4.1.388.6.12.2.6.3.1.2
		-- 1.3.6.1.4.1.388.6.16.2.6.3.1.2
		ccPortalTxPktsAt2Mb OBJECT-TYPE
			SYNTAX Counter32
			MAX-ACCESS read-only
			STATUS current
			DESCRIPTION
				"Number of pkts transmitted via this Radio at 2 Mbps."
			::= { ccPortalTxPktsEntry 2 }

		
--   1.3.6.1.4.1.388.11.2.4.2.100.3.1.3
-- 1.3.6.1.4.1.388.6.12.2.6.3.1.3
		-- 1.3.6.1.4.1.388.6.16.2.6.3.1.3
		ccPortalTxPktsAt5pt5Mb OBJECT-TYPE
			SYNTAX Counter32
			MAX-ACCESS read-only
			STATUS current
			DESCRIPTION
				"Number of pkts transmitted via this Radio at 5.5 Mbps."
			::= { ccPortalTxPktsEntry 3 }

		
--   1.3.6.1.4.1.388.11.2.4.2.100.3.1.4
-- 1.3.6.1.4.1.388.6.12.2.6.3.1.4
		-- 1.3.6.1.4.1.388.6.16.2.6.3.1.4
		ccPortalTxPktsAt6Mb OBJECT-TYPE
			SYNTAX Counter32
			MAX-ACCESS read-only
			STATUS current
			DESCRIPTION
				"Number of pkts transmitted via this Radio at 6 Mbps."
			::= { ccPortalTxPktsEntry 4 }

		
--   1.3.6.1.4.1.388.11.2.4.2.100.3.1.5
-- 1.3.6.1.4.1.388.6.12.2.6.3.1.5
		-- 1.3.6.1.4.1.388.6.16.2.6.3.1.5
		ccPortalTxPktsAt9Mb OBJECT-TYPE
			SYNTAX Counter32
			MAX-ACCESS read-only
			STATUS current
			DESCRIPTION
				"Number of pkts transmitted via this Radio at 9 Mbps."
			::= { ccPortalTxPktsEntry 5 }

		
--   1.3.6.1.4.1.388.11.2.4.2.100.3.1.6
-- 1.3.6.1.4.1.388.6.12.2.6.3.1.6
		-- 1.3.6.1.4.1.388.6.16.2.6.3.1.6
		ccPortalTxPktsAt11Mb OBJECT-TYPE
			SYNTAX Counter32
			MAX-ACCESS read-only
			STATUS current
			DESCRIPTION
				"Number of pkts transmitted via this Radio at 11 Mbps."
			::= { ccPortalTxPktsEntry 6 }

		
--   1.3.6.1.4.1.388.11.2.4.2.100.3.1.7
-- 1.3.6.1.4.1.388.6.12.2.6.3.1.7
		-- 1.3.6.1.4.1.388.6.16.2.6.3.1.7
		ccPortalTxPktsAt12Mb OBJECT-TYPE
			SYNTAX Counter32
			MAX-ACCESS read-only
			STATUS current
			DESCRIPTION
				"Number of pkts transmitted via this Radio at 12 Mbps."
			::= { ccPortalTxPktsEntry 7 }

		
--   1.3.6.1.4.1.388.11.2.4.2.100.3.1.8
-- 1.3.6.1.4.1.388.6.12.2.6.3.1.8
		-- 1.3.6.1.4.1.388.6.16.2.6.3.1.8
		ccPortalTxPktsAt18Mb OBJECT-TYPE
			SYNTAX Counter32
			MAX-ACCESS read-only
			STATUS current
			DESCRIPTION
				"Number of pkts transmitted via this Radio at 18 Mbps."
			::= { ccPortalTxPktsEntry 8 }

		
--   1.3.6.1.4.1.388.11.2.4.2.100.3.1.9
-- 1.3.6.1.4.1.388.6.12.2.6.3.1.9
		-- 1.3.6.1.4.1.388.6.16.2.6.3.1.9
		ccPortalTxPktsAt22Mb OBJECT-TYPE
			SYNTAX Counter32
			MAX-ACCESS read-only
			STATUS current
			DESCRIPTION
				"Number of pkts transmitted via this Radio at 22 Mbps."
			::= { ccPortalTxPktsEntry 9 }

		
--   1.3.6.1.4.1.388.11.2.4.2.100.3.1.10
-- 1.3.6.1.4.1.388.6.12.2.6.3.1.10
		-- 1.3.6.1.4.1.388.6.16.2.6.3.1.10
		ccPortalTxPktsAt24Mb OBJECT-TYPE
			SYNTAX Counter32
			MAX-ACCESS read-only
			STATUS current
			DESCRIPTION
				"Number of pkts transmitted via this Radio at 24 Mbps."
			::= { ccPortalTxPktsEntry 10 }

		
--   1.3.6.1.4.1.388.11.2.4.2.100.3.1.11
-- 1.3.6.1.4.1.388.6.12.2.6.3.1.11
		-- 1.3.6.1.4.1.388.6.16.2.6.3.1.11
		ccPortalTxPktsAt36Mb OBJECT-TYPE
			SYNTAX Counter32
			MAX-ACCESS read-only
			STATUS current
			DESCRIPTION
				"Number of pkts transmitted via this Radio at 36 Mbps."
			::= { ccPortalTxPktsEntry 11 }

		
--   1.3.6.1.4.1.388.11.2.4.2.100.3.1.12
-- 1.3.6.1.4.1.388.6.12.2.6.3.1.12
		-- 1.3.6.1.4.1.388.6.16.2.6.3.1.12
		ccPortalTxPktsAt48Mb OBJECT-TYPE
			SYNTAX Counter32
			MAX-ACCESS read-only
			STATUS current
			DESCRIPTION
				"Number of pkts transmitted via this Radio at 48 Mbps."
			::= { ccPortalTxPktsEntry 12 }

		
--   1.3.6.1.4.1.388.11.2.4.2.100.3.1.13
-- 1.3.6.1.4.1.388.6.12.2.6.3.1.13
		-- 1.3.6.1.4.1.388.6.16.2.6.3.1.13
		ccPortalTxPktsAt54Mb OBJECT-TYPE
			SYNTAX Counter32
			MAX-ACCESS read-only
			STATUS current
			DESCRIPTION
				"Number of pkts transmitted via this Radio at 54 Mbps."
			::= { ccPortalTxPktsEntry 13 }

		
--   1.3.6.1.4.1.388.11.2.4.2.100.4
-- 1.3.6.1.4.1.388.6.12.2.6.4
		-- 1.3.6.1.4.1.388.6.16.2.6.4
		ccPortalRxOctetsTable OBJECT-TYPE
			SYNTAX SEQUENCE OF CcPortalRxOctetsEntry
			MAX-ACCESS not-accessible
			STATUS current
			DESCRIPTION
				"For each Portal on this switch, this table 
				describes counts of octets received at each 
				possible speed, (1Mb, 2Mb, 5.5Mb, 6Mb...)."
			::= { ccPortalRfSum 4 }

		
--   1.3.6.1.4.1.388.11.2.4.2.100.4.1
-- 1.3.6.1.4.1.388.6.12.2.6.4.1
		-- 1.3.6.1.4.1.388.6.16.2.6.4.1
		ccPortalRxOctetsEntry OBJECT-TYPE
			SYNTAX CcPortalRxOctetsEntry
			MAX-ACCESS not-accessible
			STATUS current
			DESCRIPTION
				" "
			INDEX { ccPortalIndex }
			::= { ccPortalRxOctetsTable 1 }

		
		CcPortalRxOctetsEntry ::=
			SEQUENCE { 
				ccPortalRxOctetsAt1Mb
					Counter32,
				ccPortalRxOctetsAt2Mb
					Counter32,
				ccPortalRxOctetsAt5pt5Mb
					Counter32,
				ccPortalRxOctetsAt6Mb
					Counter32,
				ccPortalRxOctetsAt9Mb
					Counter32,
				ccPortalRxOctetsAt11Mb
					Counter32,
				ccPortalRxOctetsAt12Mb
					Counter32,
				ccPortalRxOctetsAt18Mb
					Counter32,
				ccPortalRxOctetsAt22Mb
					Counter32,
				ccPortalRxOctetsAt24Mb
					Counter32,
				ccPortalRxOctetsAt36Mb
					Counter32,
				ccPortalRxOctetsAt48Mb
					Counter32,
				ccPortalRxOctetsAt54Mb
					Counter32
			 }

--   1.3.6.1.4.1.388.11.2.4.2.100.4.1.1
-- 1.3.6.1.4.1.388.6.12.2.6.4.1.1
		-- 1.3.6.1.4.1.388.6.16.2.6.4.1.1
		ccPortalRxOctetsAt1Mb OBJECT-TYPE
			SYNTAX Counter32
			MAX-ACCESS read-only
			STATUS current
			DESCRIPTION
				"Number of octets received via this Radio at 1 Mbps."
			::= { ccPortalRxOctetsEntry 1 }

		
--   1.3.6.1.4.1.388.11.2.4.2.100.4.1.2
-- 1.3.6.1.4.1.388.6.12.2.6.4.1.2
		-- 1.3.6.1.4.1.388.6.16.2.6.4.1.2
		ccPortalRxOctetsAt2Mb OBJECT-TYPE
			SYNTAX Counter32
			MAX-ACCESS read-only
			STATUS current
			DESCRIPTION
				"Number of octets received via this Radio at 2 Mbps."
			::= { ccPortalRxOctetsEntry 2 }

		
--   1.3.6.1.4.1.388.11.2.4.2.100.4.1.3
-- 1.3.6.1.4.1.388.6.12.2.6.4.1.3
		-- 1.3.6.1.4.1.388.6.16.2.6.4.1.3
		ccPortalRxOctetsAt5pt5Mb OBJECT-TYPE
			SYNTAX Counter32
			MAX-ACCESS read-only
			STATUS current
			DESCRIPTION
				"Number of octets received via this Radio at 5.5 Mbps."
			::= { ccPortalRxOctetsEntry 3 }

		
--   1.3.6.1.4.1.388.11.2.4.2.100.4.1.4
-- 1.3.6.1.4.1.388.6.12.2.6.4.1.4
		-- 1.3.6.1.4.1.388.6.16.2.6.4.1.4
		ccPortalRxOctetsAt6Mb OBJECT-TYPE
			SYNTAX Counter32
			MAX-ACCESS read-only
			STATUS current
			DESCRIPTION
				"Number of octets received via this Radio at 6 Mbps."
			::= { ccPortalRxOctetsEntry 4 }

		
--   1.3.6.1.4.1.388.11.2.4.2.100.4.1.5
-- 1.3.6.1.4.1.388.6.12.2.6.4.1.5
		-- 1.3.6.1.4.1.388.6.16.2.6.4.1.5
		ccPortalRxOctetsAt9Mb OBJECT-TYPE
			SYNTAX Counter32
			MAX-ACCESS read-only
			STATUS current
			DESCRIPTION
				"Number of octets received via this Radio at 9 Mbps."
			::= { ccPortalRxOctetsEntry 5 }

		
--   1.3.6.1.4.1.388.11.2.4.2.100.4.1.6
-- 1.3.6.1.4.1.388.6.12.2.6.4.1.6
		-- 1.3.6.1.4.1.388.6.16.2.6.4.1.6
		ccPortalRxOctetsAt11Mb OBJECT-TYPE
			SYNTAX Counter32
			MAX-ACCESS read-only
			STATUS current
			DESCRIPTION
				"Number of octets received via this Radio at 11 Mbps."
			::= { ccPortalRxOctetsEntry 6 }

		
--   1.3.6.1.4.1.388.11.2.4.2.100.4.1.7
-- 1.3.6.1.4.1.388.6.12.2.6.4.1.7
		-- 1.3.6.1.4.1.388.6.16.2.6.4.1.7
		ccPortalRxOctetsAt12Mb OBJECT-TYPE
			SYNTAX Counter32
			MAX-ACCESS read-only
			STATUS current
			DESCRIPTION
				"Number of octets received via this Radio at 12 Mbps."
			::= { ccPortalRxOctetsEntry 7 }

		
--   1.3.6.1.4.1.388.11.2.4.2.100.4.1.8
-- 1.3.6.1.4.1.388.6.12.2.6.4.1.8
		-- 1.3.6.1.4.1.388.6.16.2.6.4.1.8
		ccPortalRxOctetsAt18Mb OBJECT-TYPE
			SYNTAX Counter32
			MAX-ACCESS read-only
			STATUS current
			DESCRIPTION
				"Number of octets received via this Radio at 18 Mbps."
			::= { ccPortalRxOctetsEntry 8 }

		
--   1.3.6.1.4.1.388.11.2.4.2.100.4.1.9
-- 1.3.6.1.4.1.388.6.12.2.6.4.1.9
		-- 1.3.6.1.4.1.388.6.16.2.6.4.1.9
		ccPortalRxOctetsAt22Mb OBJECT-TYPE
			SYNTAX Counter32
			MAX-ACCESS read-only
			STATUS current
			DESCRIPTION
				"Number of octets received via this Radio at 22 Mbps."
			::= { ccPortalRxOctetsEntry 9 }

		
--   1.3.6.1.4.1.388.11.2.4.2.100.4.1.10
-- 1.3.6.1.4.1.388.6.12.2.6.4.1.10
		-- 1.3.6.1.4.1.388.6.16.2.6.4.1.10
		ccPortalRxOctetsAt24Mb OBJECT-TYPE
			SYNTAX Counter32
			MAX-ACCESS read-only
			STATUS current
			DESCRIPTION
				"Number of octets received via this Radio at 24 Mbps."
			::= { ccPortalRxOctetsEntry 10 }

		
--   1.3.6.1.4.1.388.11.2.4.2.100.4.1.11
-- 1.3.6.1.4.1.388.6.12.2.6.4.1.11
		-- 1.3.6.1.4.1.388.6.16.2.6.4.1.11
		ccPortalRxOctetsAt36Mb OBJECT-TYPE
			SYNTAX Counter32
			MAX-ACCESS read-only
			STATUS current
			DESCRIPTION
				"Number of octets received via this Radio at 36 Mbps."
			::= { ccPortalRxOctetsEntry 11 }

		
--   1.3.6.1.4.1.388.11.2.4.2.100.4.1.12
-- 1.3.6.1.4.1.388.6.12.2.6.4.1.12
		-- 1.3.6.1.4.1.388.6.16.2.6.4.1.12
		ccPortalRxOctetsAt48Mb OBJECT-TYPE
			SYNTAX Counter32
			MAX-ACCESS read-only
			STATUS current
			DESCRIPTION
				"Number of octets received via this Radio at 48 Mbps."
			::= { ccPortalRxOctetsEntry 12 }

		
--   1.3.6.1.4.1.388.11.2.4.2.100.4.1.13
-- 1.3.6.1.4.1.388.6.12.2.6.4.1.13
		-- 1.3.6.1.4.1.388.6.16.2.6.4.1.13
		ccPortalRxOctetsAt54Mb OBJECT-TYPE
			SYNTAX Counter32
			MAX-ACCESS read-only
			STATUS current
			DESCRIPTION
				"Number of octets received via this Radio at 54 Mbps."
			::= { ccPortalRxOctetsEntry 13 }

		
--   1.3.6.1.4.1.388.11.2.4.2.100.5
-- 1.3.6.1.4.1.388.6.12.2.6.5
		-- 1.3.6.1.4.1.388.6.16.2.6.5
		ccPortalTxOctetsTable OBJECT-TYPE
			SYNTAX SEQUENCE OF CcPortalTxOctetsEntry
			MAX-ACCESS not-accessible
			STATUS current
			DESCRIPTION
				"For each Portal on this switch, this table 
				describes counts of octets received at each 
				possible speed, (1Mb, 2Mb, 5.5Mb, 6Mb...)."
			::= { ccPortalRfSum 5 }

		
--   1.3.6.1.4.1.388.11.2.4.2.100.5.1
-- 1.3.6.1.4.1.388.6.12.2.6.5.1
		-- 1.3.6.1.4.1.388.6.16.2.6.5.1
		ccPortalTxOctetsEntry OBJECT-TYPE
			SYNTAX CcPortalTxOctetsEntry
			MAX-ACCESS not-accessible
			STATUS current
			DESCRIPTION
				" "
			INDEX { ccPortalIndex }
			::= { ccPortalTxOctetsTable 1 }

		
		CcPortalTxOctetsEntry ::=
			SEQUENCE { 
				ccPortalTxOctetsAt1Mb
					Counter32,
				ccPortalTxOctetsAt2Mb
					Counter32,
				ccPortalTxOctetsAt5pt5Mb
					Counter32,
				ccPortalTxOctetsAt6Mb
					Counter32,
				ccPortalTxOctetsAt9Mb
					Counter32,
				ccPortalTxOctetsAt11Mb
					Counter32,
				ccPortalTxOctetsAt12Mb
					Counter32,
				ccPortalTxOctetsAt18Mb
					Counter32,
				ccPortalTxOctetsAt22Mb
					Counter32,
				ccPortalTxOctetsAt24Mb
					Counter32,
				ccPortalTxOctetsAt36Mb
					Counter32,
				ccPortalTxOctetsAt48Mb
					Counter32,
				ccPortalTxOctetsAt54Mb
					Counter32
			 }

--   1.3.6.1.4.1.388.11.2.4.2.100.5.1.1
-- 1.3.6.1.4.1.388.6.12.2.6.5.1.1
		-- 1.3.6.1.4.1.388.6.16.2.6.5.1.1
		ccPortalTxOctetsAt1Mb OBJECT-TYPE
			SYNTAX Counter32
			MAX-ACCESS read-only
			STATUS current
			DESCRIPTION
				"Number octets transmitted via this Radio at 1 Mbps."
			::= { ccPortalTxOctetsEntry 1 }

		
--   1.3.6.1.4.1.388.11.2.4.2.100.5.1.2
-- 1.3.6.1.4.1.388.6.12.2.6.5.1.2
		-- 1.3.6.1.4.1.388.6.16.2.6.5.1.2
		ccPortalTxOctetsAt2Mb OBJECT-TYPE
			SYNTAX Counter32
			MAX-ACCESS read-only
			STATUS current
			DESCRIPTION
				"Number octets transmitted via this Radio at 2 Mbps."
			::= { ccPortalTxOctetsEntry 2 }

		
--   1.3.6.1.4.1.388.11.2.4.2.100.5.1.3
-- 1.3.6.1.4.1.388.6.12.2.6.5.1.3
		-- 1.3.6.1.4.1.388.6.16.2.6.5.1.3
		ccPortalTxOctetsAt5pt5Mb OBJECT-TYPE
			SYNTAX Counter32
			MAX-ACCESS read-only
			STATUS current
			DESCRIPTION
				"Number octets transmitted via this Radio at 5.5 Mbps."
			::= { ccPortalTxOctetsEntry 3 }

		
--   1.3.6.1.4.1.388.11.2.4.2.100.5.1.4
-- 1.3.6.1.4.1.388.6.12.2.6.5.1.4
		-- 1.3.6.1.4.1.388.6.16.2.6.5.1.4
		ccPortalTxOctetsAt6Mb OBJECT-TYPE
			SYNTAX Counter32
			MAX-ACCESS read-only
			STATUS current
			DESCRIPTION
				"Number octets transmitted via this Radio at 6 Mbps."
			::= { ccPortalTxOctetsEntry 4 }

		
--   1.3.6.1.4.1.388.11.2.4.2.100.5.1.5
-- 1.3.6.1.4.1.388.6.12.2.6.5.1.5
		-- 1.3.6.1.4.1.388.6.16.2.6.5.1.5
		ccPortalTxOctetsAt9Mb OBJECT-TYPE
			SYNTAX Counter32
			MAX-ACCESS read-only
			STATUS current
			DESCRIPTION
				"Number octets transmitted via this Radio at 9 Mbps."
			::= { ccPortalTxOctetsEntry 5 }

		
--   1.3.6.1.4.1.388.11.2.4.2.100.5.1.6
-- 1.3.6.1.4.1.388.6.12.2.6.5.1.6
		-- 1.3.6.1.4.1.388.6.16.2.6.5.1.6
		ccPortalTxOctetsAt11Mb OBJECT-TYPE
			SYNTAX Counter32
			MAX-ACCESS read-only
			STATUS current
			DESCRIPTION
				"Number octets transmitted via this Radio at 11 Mbps."
			::= { ccPortalTxOctetsEntry 6 }

		
--   1.3.6.1.4.1.388.11.2.4.2.100.5.1.7
-- 1.3.6.1.4.1.388.6.12.2.6.5.1.7
		-- 1.3.6.1.4.1.388.6.16.2.6.5.1.7
		ccPortalTxOctetsAt12Mb OBJECT-TYPE
			SYNTAX Counter32
			MAX-ACCESS read-only
			STATUS current
			DESCRIPTION
				"Number octets transmitted via this Radio at 12 Mbps."
			::= { ccPortalTxOctetsEntry 7 }

		
--   1.3.6.1.4.1.388.11.2.4.2.100.5.1.8
-- 1.3.6.1.4.1.388.6.12.2.6.5.1.8
		-- 1.3.6.1.4.1.388.6.16.2.6.5.1.8
		ccPortalTxOctetsAt18Mb OBJECT-TYPE
			SYNTAX Counter32
			MAX-ACCESS read-only
			STATUS current
			DESCRIPTION
				"Number octets transmitted via this Radio at 18 Mbps."
			::= { ccPortalTxOctetsEntry 8 }

		
--   1.3.6.1.4.1.388.11.2.4.2.100.5.1.9
-- 1.3.6.1.4.1.388.6.12.2.6.5.1.9
		-- 1.3.6.1.4.1.388.6.16.2.6.5.1.9
		ccPortalTxOctetsAt22Mb OBJECT-TYPE
			SYNTAX Counter32
			MAX-ACCESS read-only
			STATUS current
			DESCRIPTION
				"Number octets transmitted via this Radio at 22 Mbps."
			::= { ccPortalTxOctetsEntry 9 }

		
--   1.3.6.1.4.1.388.11.2.4.2.100.5.1.10
-- 1.3.6.1.4.1.388.6.12.2.6.5.1.10
		-- 1.3.6.1.4.1.388.6.16.2.6.5.1.10
		ccPortalTxOctetsAt24Mb OBJECT-TYPE
			SYNTAX Counter32
			MAX-ACCESS read-only
			STATUS current
			DESCRIPTION
				"Number octets transmitted via this Radio at 24 Mbps."
			::= { ccPortalTxOctetsEntry 10 }

		
--   1.3.6.1.4.1.388.11.2.4.2.100.5.1.11
-- 1.3.6.1.4.1.388.6.12.2.6.5.1.11
		-- 1.3.6.1.4.1.388.6.16.2.6.5.1.11
		ccPortalTxOctetsAt36Mb OBJECT-TYPE
			SYNTAX Counter32
			MAX-ACCESS read-only
			STATUS current
			DESCRIPTION
				"Number octets transmitted via this Radio at 36 Mbps."
			::= { ccPortalTxOctetsEntry 11 }

		
--   1.3.6.1.4.1.388.11.2.4.2.100.5.1.12
-- 1.3.6.1.4.1.388.6.12.2.6.5.1.12
		-- 1.3.6.1.4.1.388.6.16.2.6.5.1.12
		ccPortalTxOctetsAt48Mb OBJECT-TYPE
			SYNTAX Counter32
			MAX-ACCESS read-only
			STATUS current
			DESCRIPTION
				"Number octets transmitted via this Radio at 48 Mbps."
			::= { ccPortalTxOctetsEntry 12 }

		
--   1.3.6.1.4.1.388.11.2.4.2.100.5.1.13
-- 1.3.6.1.4.1.388.6.12.2.6.5.1.13
		-- 1.3.6.1.4.1.388.6.16.2.6.5.1.13
		ccPortalTxOctetsAt54Mb OBJECT-TYPE
			SYNTAX Counter32
			MAX-ACCESS read-only
			STATUS current
			DESCRIPTION
				"Number octets transmitted via this Radio at 54 Mbps."
			::= { ccPortalTxOctetsEntry 13 }

		
--   1.3.6.1.4.1.388.11.2.4.2.100.6
-- 1.3.6.1.4.1.388.6.12.2.6.6
		-- 1.3.6.1.4.1.388.6.16.2.6.6
		ccPortalTxRetriesPktsTable OBJECT-TYPE
			SYNTAX SEQUENCE OF CcPortalTxRetriesPktsEntry
			MAX-ACCESS not-accessible
			STATUS current
			DESCRIPTION
				"For each Portal on the switch, this table describes 
				counts of the number of octets affected by transmit 
				retries, (no retries, 1 retry, 2 retries,... gave-up)."
			::= { ccPortalRfSum 6 }

		
--   1.3.6.1.4.1.388.11.2.4.2.100.6.1
-- 1.3.6.1.4.1.388.6.12.2.6.6.1
		-- 1.3.6.1.4.1.388.6.16.2.6.6.1
		ccPortalTxRetriesPktsEntry OBJECT-TYPE
			SYNTAX CcPortalTxRetriesPktsEntry
			MAX-ACCESS not-accessible
			STATUS current
			DESCRIPTION
				" "
			INDEX { ccPortalIndex }
			::= { ccPortalTxRetriesPktsTable 1 }

		
		CcPortalTxRetriesPktsEntry ::=
			SEQUENCE { 
				ccPortalTxRetriesPktsNone
					Counter32,
				ccPortalTxRetriesPkts01
					Counter32,
				ccPortalTxRetriesPkts02
					Counter32,
				ccPortalTxRetriesPkts03
					Counter32,
				ccPortalTxRetriesPkts04
					Counter32,
				ccPortalTxRetriesPkts05
					Counter32,
				ccPortalTxRetriesPkts06
					Counter32,
				ccPortalTxRetriesPkts07
					Counter32,
				ccPortalTxRetriesPkts08
					Counter32,
				ccPortalTxRetriesPkts09
					Counter32,
				ccPortalTxRetriesPkts10
					Counter32,
				ccPortalTxRetriesPkts11
					Counter32,
				ccPortalTxRetriesPkts12
					Counter32,
				ccPortalTxRetriesPkts13
					Counter32,
				ccPortalTxRetriesPkts14
					Counter32,
				ccPortalTxRetriesPkts15
					Counter32,
				ccPortalTxRetriesPktsFailed
					Counter32
			 }

--   1.3.6.1.4.1.388.11.2.4.2.100.6.1.1
-- 1.3.6.1.4.1.388.6.12.2.6.6.1.1
		-- 1.3.6.1.4.1.388.6.16.2.6.6.1.1
		ccPortalTxRetriesPktsNone OBJECT-TYPE
			SYNTAX Counter32
			MAX-ACCESS read-only
			STATUS current
			DESCRIPTION
				"Number of pkts successfully transmitted via this
				Radio with no retries."
			::= { ccPortalTxRetriesPktsEntry 1 }

		
--   1.3.6.1.4.1.388.11.2.4.2.100.6.1.2
-- 1.3.6.1.4.1.388.6.12.2.6.6.1.2
		-- 1.3.6.1.4.1.388.6.16.2.6.6.1.2
		ccPortalTxRetriesPkts01 OBJECT-TYPE
			SYNTAX Counter32
			MAX-ACCESS read-only
			STATUS current
			DESCRIPTION
				"Number of pkts successfully transmitted via this
				Radio with exactly 1 retry."
			::= { ccPortalTxRetriesPktsEntry 2 }

		
--   1.3.6.1.4.1.388.11.2.4.2.100.6.1.3
-- 1.3.6.1.4.1.388.6.12.2.6.6.1.3
		-- 1.3.6.1.4.1.388.6.16.2.6.6.1.3
		ccPortalTxRetriesPkts02 OBJECT-TYPE
			SYNTAX Counter32
			MAX-ACCESS read-only
			STATUS current
			DESCRIPTION
				"Number of pkts successfully transmitted via this
				Radio with exactly 2 retries."
			::= { ccPortalTxRetriesPktsEntry 3 }

		
--   1.3.6.1.4.1.388.11.2.4.2.100.6.1.4
-- 1.3.6.1.4.1.388.6.12.2.6.6.1.4
		-- 1.3.6.1.4.1.388.6.16.2.6.6.1.4
		ccPortalTxRetriesPkts03 OBJECT-TYPE
			SYNTAX Counter32
			MAX-ACCESS read-only
			STATUS current
			DESCRIPTION
				"Number of pkts successfully transmitted via this
				Radio with exactly 3 retries."
			::= { ccPortalTxRetriesPktsEntry 4 }

		
--   1.3.6.1.4.1.388.11.2.4.2.100.6.1.5
-- 1.3.6.1.4.1.388.6.12.2.6.6.1.5
		-- 1.3.6.1.4.1.388.6.16.2.6.6.1.5
		ccPortalTxRetriesPkts04 OBJECT-TYPE
			SYNTAX Counter32
			MAX-ACCESS read-only
			STATUS current
			DESCRIPTION
				"Number of pkts successfully transmitted via this
				Radio with exactly 4 retries."
			::= { ccPortalTxRetriesPktsEntry 5 }

		
--   1.3.6.1.4.1.388.11.2.4.2.100.6.1.6
-- 1.3.6.1.4.1.388.6.12.2.6.6.1.6
		-- 1.3.6.1.4.1.388.6.16.2.6.6.1.6
		ccPortalTxRetriesPkts05 OBJECT-TYPE
			SYNTAX Counter32
			MAX-ACCESS read-only
			STATUS current
			DESCRIPTION
				"Number of pkts successfully transmitted via this
				Radio with exactly 5 retries."
			::= { ccPortalTxRetriesPktsEntry 6 }

		
--   1.3.6.1.4.1.388.11.2.4.2.100.6.1.7
-- 1.3.6.1.4.1.388.6.12.2.6.6.1.7
		-- 1.3.6.1.4.1.388.6.16.2.6.6.1.7
		ccPortalTxRetriesPkts06 OBJECT-TYPE
			SYNTAX Counter32
			MAX-ACCESS read-only
			STATUS current
			DESCRIPTION
				"Number of pkts successfully transmitted via this
				Radio with exactly 6 retries."
			::= { ccPortalTxRetriesPktsEntry 7 }

		
--   1.3.6.1.4.1.388.11.2.4.2.100.6.1.8
-- 1.3.6.1.4.1.388.6.12.2.6.6.1.8
		-- 1.3.6.1.4.1.388.6.16.2.6.6.1.8
		ccPortalTxRetriesPkts07 OBJECT-TYPE
			SYNTAX Counter32
			MAX-ACCESS read-only
			STATUS current
			DESCRIPTION
				"Number of pkts successfully transmitted via this
				Radio with exactly 7 retries."
			::= { ccPortalTxRetriesPktsEntry 8 }

		
--   1.3.6.1.4.1.388.11.2.4.2.100.6.1.9
-- 1.3.6.1.4.1.388.6.12.2.6.6.1.9
		-- 1.3.6.1.4.1.388.6.16.2.6.6.1.9
		ccPortalTxRetriesPkts08 OBJECT-TYPE
			SYNTAX Counter32
			MAX-ACCESS read-only
			STATUS current
			DESCRIPTION
				"Number of pkts successfully transmitted via this
				Radio with exactly 8 retries."
			::= { ccPortalTxRetriesPktsEntry 9 }

		
--   1.3.6.1.4.1.388.11.2.4.2.100.6.1.10
-- 1.3.6.1.4.1.388.6.12.2.6.6.1.10
		-- 1.3.6.1.4.1.388.6.16.2.6.6.1.10
		ccPortalTxRetriesPkts09 OBJECT-TYPE
			SYNTAX Counter32
			MAX-ACCESS read-only
			STATUS current
			DESCRIPTION
				"Number of pkts successfully transmitted via this
				Radio with exactly 9 retries."
			::= { ccPortalTxRetriesPktsEntry 10 }

		
--   1.3.6.1.4.1.388.11.2.4.2.100.6.1.11
-- 1.3.6.1.4.1.388.6.12.2.6.6.1.11
		-- 1.3.6.1.4.1.388.6.16.2.6.6.1.11
		ccPortalTxRetriesPkts10 OBJECT-TYPE
			SYNTAX Counter32
			MAX-ACCESS read-only
			STATUS current
			DESCRIPTION
				"Number of pkts successfully transmitted via this
				Radio with exactly 10 retries."
			::= { ccPortalTxRetriesPktsEntry 11 }

		
--   1.3.6.1.4.1.388.11.2.4.2.100.6.1.12
-- 1.3.6.1.4.1.388.6.12.2.6.6.1.12
		-- 1.3.6.1.4.1.388.6.16.2.6.6.1.12
		ccPortalTxRetriesPkts11 OBJECT-TYPE
			SYNTAX Counter32
			MAX-ACCESS read-only
			STATUS current
			DESCRIPTION
				"Number of pkts successfully transmitted via this
				Radio with exactly 11 retries."
			::= { ccPortalTxRetriesPktsEntry 12 }

		
--   1.3.6.1.4.1.388.11.2.4.2.100.6.1.13
-- 1.3.6.1.4.1.388.6.12.2.6.6.1.13
		-- 1.3.6.1.4.1.388.6.16.2.6.6.1.13
		ccPortalTxRetriesPkts12 OBJECT-TYPE
			SYNTAX Counter32
			MAX-ACCESS read-only
			STATUS current
			DESCRIPTION
				"Number of pkts successfully transmitted via this
				Radio with exactly 12 retries."
			::= { ccPortalTxRetriesPktsEntry 13 }

		
--   1.3.6.1.4.1.388.11.2.4.2.100.6.1.14
-- 1.3.6.1.4.1.388.6.12.2.6.6.1.14
		-- 1.3.6.1.4.1.388.6.16.2.6.6.1.14
		ccPortalTxRetriesPkts13 OBJECT-TYPE
			SYNTAX Counter32
			MAX-ACCESS read-only
			STATUS current
			DESCRIPTION
				"Number of pkts successfully transmitted via this
				Radio with exactly 13 retries."
			::= { ccPortalTxRetriesPktsEntry 14 }

		
--   1.3.6.1.4.1.388.11.2.4.2.100.6.1.15
-- 1.3.6.1.4.1.388.6.12.2.6.6.1.15
		-- 1.3.6.1.4.1.388.6.16.2.6.6.1.15
		ccPortalTxRetriesPkts14 OBJECT-TYPE
			SYNTAX Counter32
			MAX-ACCESS read-only
			STATUS current
			DESCRIPTION
				"Number of pkts successfully transmitted via this
				Radio with exactly 14 retries."
			::= { ccPortalTxRetriesPktsEntry 15 }

		
--   1.3.6.1.4.1.388.11.2.4.2.100.6.1.16
-- 1.3.6.1.4.1.388.6.12.2.6.6.1.16
		-- 1.3.6.1.4.1.388.6.16.2.6.6.1.16
		ccPortalTxRetriesPkts15 OBJECT-TYPE
			SYNTAX Counter32
			MAX-ACCESS read-only
			STATUS deprecated
			DESCRIPTION
				"Number of pkts successfully transmitted via this
				Radio with exactly 15 retries."
			::= { ccPortalTxRetriesPktsEntry 16 }

		
--   1.3.6.1.4.1.388.11.2.4.2.100.6.1.17
-- 1.3.6.1.4.1.388.6.12.2.6.6.1.17
		-- 1.3.6.1.4.1.388.6.16.2.6.6.1.17
		ccPortalTxRetriesPktsFailed OBJECT-TYPE
			SYNTAX Counter32
			MAX-ACCESS read-only
			STATUS current
			DESCRIPTION
				"Number of pkts that never were successfully 
				transmitted to via this Portal because the max retry
				count was exceeded."
			::= { ccPortalTxRetriesPktsEntry 17 }

		
--   1.3.6.1.4.1.388.11.2.4.2.100.7
-- 1.3.6.1.4.1.388.6.12.2.6.7
		-- 1.3.6.1.4.1.388.6.16.2.6.7
		ccPortalTxRetriesOctetsTable OBJECT-TYPE
			SYNTAX SEQUENCE OF CcPortalTxRetriesOctetsEntry
			MAX-ACCESS not-accessible
			STATUS current
			DESCRIPTION
				"For each Portal on the switch, this table describes 
				counts of the number of octets affected by transmit 
				retries, (no retries, 1 retry, 2 retries,... gave-up)."
			::= { ccPortalRfSum 7 }

		
--   1.3.6.1.4.1.388.11.2.4.2.100.7.1
-- 1.3.6.1.4.1.388.6.12.2.6.7.1
		-- 1.3.6.1.4.1.388.6.16.2.6.7.1
		ccPortalTxRetriesOctetsEntry OBJECT-TYPE
			SYNTAX CcPortalTxRetriesOctetsEntry
			MAX-ACCESS not-accessible
			STATUS current
			DESCRIPTION
				" "
			INDEX { ccPortalIndex }
			::= { ccPortalTxRetriesOctetsTable 1 }

		
		CcPortalTxRetriesOctetsEntry ::=
			SEQUENCE { 
				ccPortalTxRetriesOctetsNone
					Counter32,
				ccPortalTxRetriesOctets01
					Counter32,
				ccPortalTxRetriesOctets02
					Counter32,
				ccPortalTxRetriesOctets03
					Counter32,
				ccPortalTxRetriesOctets04
					Counter32,
				ccPortalTxRetriesOctets05
					Counter32,
				ccPortalTxRetriesOctets06
					Counter32,
				ccPortalTxRetriesOctets07
					Counter32,
				ccPortalTxRetriesOctets08
					Counter32,
				ccPortalTxRetriesOctets09
					Counter32,
				ccPortalTxRetriesOctets10
					Counter32,
				ccPortalTxRetriesOctets11
					Counter32,
				ccPortalTxRetriesOctets12
					Counter32,
				ccPortalTxRetriesOctets13
					Counter32,
				ccPortalTxRetriesOctets14
					Counter32,
				ccPortalTxRetriesOctets15
					Counter32,
				ccPortalTxRetriesOctetsFailed
					Counter32
			 }

--   1.3.6.1.4.1.388.11.2.4.2.100.7.1.1
-- 1.3.6.1.4.1.388.6.12.2.6.7.1.1
		-- 1.3.6.1.4.1.388.6.16.2.6.7.1.1
		ccPortalTxRetriesOctetsNone OBJECT-TYPE
			SYNTAX Counter32
			MAX-ACCESS read-only
			STATUS current
			DESCRIPTION
				"Number of octets successfully transmitted via this
				Radio with no retries."
			::= { ccPortalTxRetriesOctetsEntry 1 }

		
--   1.3.6.1.4.1.388.11.2.4.2.100.7.1.2
-- 1.3.6.1.4.1.388.6.12.2.6.7.1.2
		-- 1.3.6.1.4.1.388.6.16.2.6.7.1.2
		ccPortalTxRetriesOctets01 OBJECT-TYPE
			SYNTAX Counter32
			MAX-ACCESS read-only
			STATUS current
			DESCRIPTION
				"Number of octets successfully transmitted via this
				Radio with exactly 1 retry."
			::= { ccPortalTxRetriesOctetsEntry 2 }

		
--   1.3.6.1.4.1.388.11.2.4.2.100.7.1.3
-- 1.3.6.1.4.1.388.6.12.2.6.7.1.3
		-- 1.3.6.1.4.1.388.6.16.2.6.7.1.3
		ccPortalTxRetriesOctets02 OBJECT-TYPE
			SYNTAX Counter32
			MAX-ACCESS read-only
			STATUS current
			DESCRIPTION
				"Number of octets successfully transmitted via this
				Radio with exactly 2 retries."
			::= { ccPortalTxRetriesOctetsEntry 3 }

		
--   1.3.6.1.4.1.388.11.2.4.2.100.7.1.4
-- 1.3.6.1.4.1.388.6.12.2.6.7.1.4
		-- 1.3.6.1.4.1.388.6.16.2.6.7.1.4
		ccPortalTxRetriesOctets03 OBJECT-TYPE
			SYNTAX Counter32
			MAX-ACCESS read-only
			STATUS current
			DESCRIPTION
				"Number of octets successfully transmitted via this
				Radio with exactly 3 retries."
			::= { ccPortalTxRetriesOctetsEntry 4 }

		
--   1.3.6.1.4.1.388.11.2.4.2.100.7.1.5
-- 1.3.6.1.4.1.388.6.12.2.6.7.1.5
		-- 1.3.6.1.4.1.388.6.16.2.6.7.1.5
		ccPortalTxRetriesOctets04 OBJECT-TYPE
			SYNTAX Counter32
			MAX-ACCESS read-only
			STATUS current
			DESCRIPTION
				"Number of octets successfully transmitted via this
				Radio with exactly 4 retries."
			::= { ccPortalTxRetriesOctetsEntry 5 }

		
--   1.3.6.1.4.1.388.11.2.4.2.100.7.1.6
-- 1.3.6.1.4.1.388.6.12.2.6.7.1.6
		-- 1.3.6.1.4.1.388.6.16.2.6.7.1.6
		ccPortalTxRetriesOctets05 OBJECT-TYPE
			SYNTAX Counter32
			MAX-ACCESS read-only
			STATUS current
			DESCRIPTION
				"Number of octets successfully transmitted via this
				Radio with exactly 5 retries."
			::= { ccPortalTxRetriesOctetsEntry 6 }

		
--   1.3.6.1.4.1.388.11.2.4.2.100.7.1.7
-- 1.3.6.1.4.1.388.6.12.2.6.7.1.7
		-- 1.3.6.1.4.1.388.6.16.2.6.7.1.7
		ccPortalTxRetriesOctets06 OBJECT-TYPE
			SYNTAX Counter32
			MAX-ACCESS read-only
			STATUS current
			DESCRIPTION
				"Number of octets successfully transmitted via this
				Radio with exactly 6 retries."
			::= { ccPortalTxRetriesOctetsEntry 7 }

		
--   1.3.6.1.4.1.388.11.2.4.2.100.7.1.8
-- 1.3.6.1.4.1.388.6.12.2.6.7.1.8
		-- 1.3.6.1.4.1.388.6.16.2.6.7.1.8
		ccPortalTxRetriesOctets07 OBJECT-TYPE
			SYNTAX Counter32
			MAX-ACCESS read-only
			STATUS current
			DESCRIPTION
				"Number of octets successfully transmitted via this
				Radio with exactly 7 retries."
			::= { ccPortalTxRetriesOctetsEntry 8 }

		
--   1.3.6.1.4.1.388.11.2.4.2.100.7.1.9
-- 1.3.6.1.4.1.388.6.12.2.6.7.1.9
		-- 1.3.6.1.4.1.388.6.16.2.6.7.1.9
		ccPortalTxRetriesOctets08 OBJECT-TYPE
			SYNTAX Counter32
			MAX-ACCESS read-only
			STATUS current
			DESCRIPTION
				"Number of octets successfully transmitted via this
				Radio with exactly 8 retries."
			::= { ccPortalTxRetriesOctetsEntry 9 }

		
--   1.3.6.1.4.1.388.11.2.4.2.100.7.1.10
-- 1.3.6.1.4.1.388.6.12.2.6.7.1.10
		-- 1.3.6.1.4.1.388.6.16.2.6.7.1.10
		ccPortalTxRetriesOctets09 OBJECT-TYPE
			SYNTAX Counter32
			MAX-ACCESS read-only
			STATUS current
			DESCRIPTION
				"Number of octets successfully transmitted via this
				Radio with exactly 9 retries."
			::= { ccPortalTxRetriesOctetsEntry 10 }

		
--   1.3.6.1.4.1.388.11.2.4.2.100.7.1.11
-- 1.3.6.1.4.1.388.6.12.2.6.7.1.11
		-- 1.3.6.1.4.1.388.6.16.2.6.7.1.11
		ccPortalTxRetriesOctets10 OBJECT-TYPE
			SYNTAX Counter32
			MAX-ACCESS read-only
			STATUS current
			DESCRIPTION
				"Number of octets successfully transmitted via this
				Radio with exactly 10 retries."
			::= { ccPortalTxRetriesOctetsEntry 11 }

		
--   1.3.6.1.4.1.388.11.2.4.2.100.7.1.12
-- 1.3.6.1.4.1.388.6.12.2.6.7.1.12
		-- 1.3.6.1.4.1.388.6.16.2.6.7.1.12
		ccPortalTxRetriesOctets11 OBJECT-TYPE
			SYNTAX Counter32
			MAX-ACCESS read-only
			STATUS current
			DESCRIPTION
				"Number of octets successfully transmitted via this
				Radio with exactly 11 retries."
			::= { ccPortalTxRetriesOctetsEntry 12 }

		
--   1.3.6.1.4.1.388.11.2.4.2.100.7.1.13
-- 1.3.6.1.4.1.388.6.12.2.6.7.1.13
		-- 1.3.6.1.4.1.388.6.16.2.6.7.1.13
		ccPortalTxRetriesOctets12 OBJECT-TYPE
			SYNTAX Counter32
			MAX-ACCESS read-only
			STATUS current
			DESCRIPTION
				"Number of octets successfully transmitted via this
				Radio with exactly 12 retries."
			::= { ccPortalTxRetriesOctetsEntry 13 }

		
--   1.3.6.1.4.1.388.11.2.4.2.100.7.1.14
-- 1.3.6.1.4.1.388.6.12.2.6.7.1.14
		-- 1.3.6.1.4.1.388.6.16.2.6.7.1.14
		ccPortalTxRetriesOctets13 OBJECT-TYPE
			SYNTAX Counter32
			MAX-ACCESS read-only
			STATUS current
			DESCRIPTION
				"Number of octets successfully transmitted via this
				Radio with exactly 13 retries."
			::= { ccPortalTxRetriesOctetsEntry 14 }

		
--   1.3.6.1.4.1.388.11.2.4.2.100.7.1.15
-- 1.3.6.1.4.1.388.6.12.2.6.7.1.15
		-- 1.3.6.1.4.1.388.6.16.2.6.7.1.15
		ccPortalTxRetriesOctets14 OBJECT-TYPE
			SYNTAX Counter32
			MAX-ACCESS read-only
			STATUS current
			DESCRIPTION
				"Number of octets successfully transmitted via this
				Radio with exactly 14 retries."
			::= { ccPortalTxRetriesOctetsEntry 15 }

		
--   1.3.6.1.4.1.388.11.2.4.2.100.7.1.16
-- 1.3.6.1.4.1.388.6.12.2.6.7.1.16
		-- 1.3.6.1.4.1.388.6.16.2.6.7.1.16
		ccPortalTxRetriesOctets15 OBJECT-TYPE
			SYNTAX Counter32
			MAX-ACCESS read-only
			STATUS deprecated
			DESCRIPTION
				"Number of octets successfully transmitted via this
				Radio with exactly 15 retries."
			::= { ccPortalTxRetriesOctetsEntry 16 }

		
--   1.3.6.1.4.1.388.11.2.4.2.100.7.1.17
-- 1.3.6.1.4.1.388.6.12.2.6.7.1.17
		-- 1.3.6.1.4.1.388.6.16.2.6.7.1.17
		ccPortalTxRetriesOctetsFailed OBJECT-TYPE
			SYNTAX Counter32
			MAX-ACCESS read-only
			STATUS current
			DESCRIPTION
				"Number of octets that never were successfully 
				transmitted to via this Portal because the max retry
				count was exceeded."
			::= { ccPortalTxRetriesOctetsEntry 17 }

		
--   ??-TW: Note that these values have been split-out from the
-- _StatsTable for Portal/MU/WLAN.  The resulting new tables
-- _SigStatsTable for Portal/MU/WLAN are symmetrical, but they
-- have been added before other v1.5 tables, and so have 
-- caused their location to move.
-- 
-- Also, note that the four RSSI values still remain in the 
-- ccMuStats table, since to delete them would be an 
-- inconsistant change.  For symmetry, they have been 
-- duplicated.
-- 1.3.6.1.4.1.388.11.2.4.2.100.8
-- 1.3.6.1.4.1.388.6.12.2.6.8
		-- 1.3.6.1.4.1.388.6.16.2.6.8
		ccPortalSigStatsTable OBJECT-TYPE
			SYNTAX SEQUENCE OF CcPortalSigStatsEntry
			MAX-ACCESS not-accessible
			STATUS current
			DESCRIPTION
				"This table describes statistics about RSSI, Signal, Noise,
				and SNR for packets recieved via each Portal on the switch."
			::= { ccPortalRfSum 8 }

		
--   1.3.6.1.4.1.388.11.2.4.2.100.8.1
-- 1.3.6.1.4.1.388.6.12.2.6.8.1
		-- 1.3.6.1.4.1.388.6.16.2.6.8.1
		ccPortalSigStatsEntry OBJECT-TYPE
			SYNTAX CcPortalSigStatsEntry
			MAX-ACCESS not-accessible
			STATUS current
			DESCRIPTION
				" "
			INDEX { ccPortalIndex }
			::= { ccPortalSigStatsTable 1 }

		
		CcPortalSigStatsEntry ::=
			SEQUENCE { 
				ccPortalSigStatsNumPkts
					Counter32,
				ccPortalSigStatsSignalBest
					Integer32,
				ccPortalSigStatsSignalWorst
					Integer32,
				ccPortalSigStatsSignalSum
					Integer32,
				ccPortalSigStatsSignalSumSquares
					Counter64,
				ccPortalSigStatsSignalMostRecent
					Integer32,
				ccPortalSigStatsNoiseBest
					Integer32,
				ccPortalSigStatsNoiseWorst
					Integer32,
				ccPortalSigStatsNoiseSum
					Integer32,
				ccPortalSigStatsNoiseSumSquares
					Counter64,
				ccPortalSigStatsNoiseMostRecent
					Integer32,
				ccPortalSigStatsSnrBest
					Integer32,
				ccPortalSigStatsSnrWorst
					Integer32,
				ccPortalSigStatsSnrSum
					Counter64,
				ccPortalSigStatsSnrSumSquares
					Counter64,
				ccPortalSigStatsSnrMostRecent
					Integer32
			 }

--   1.3.6.1.4.1.388.11.2.4.2.100.8.1.1
-- 1.3.6.1.4.1.388.6.12.2.6.8.1.1
		-- 1.3.6.1.4.1.388.6.16.2.6.8.1.1
		ccPortalSigStatsNumPkts OBJECT-TYPE
			SYNTAX Counter32
			MAX-ACCESS read-only
			STATUS current
			DESCRIPTION
				"Total packets received via the Radio included in
				all the other counters reported in this row."
			::= { ccPortalSigStatsEntry 1 }

		
--   1.3.6.1.4.1.388.11.2.4.2.100.8.1.2
-- 1.3.6.1.4.1.388.6.12.2.6.8.1.2
		-- 1.3.6.1.4.1.388.6.16.2.6.8.1.2
		ccPortalSigStatsSignalBest OBJECT-TYPE
			SYNTAX Integer32
			UNITS "dBm"
			MAX-ACCESS read-only
			STATUS current
			DESCRIPTION
				"The best Signal value seen from the Radio so far.
				(Remember that a -20dBm Signal is better than -60dBm).
				
				This value is initialized to -500dBm.
				"
			::= { ccPortalSigStatsEntry 2 }

		
--   1.3.6.1.4.1.388.11.2.4.2.100.8.1.3
-- 1.3.6.1.4.1.388.6.12.2.6.8.1.3
		-- 1.3.6.1.4.1.388.6.16.2.6.8.1.3
		ccPortalSigStatsSignalWorst OBJECT-TYPE
			SYNTAX Integer32
			UNITS "dBm"
			MAX-ACCESS read-only
			STATUS current
			DESCRIPTION
				"The worst Signal value seen from the Radio so far.
				(Remember that a -80dBm Signal is worse than -60dBm).
				
				This value is initialized to 500dBm."
			::= { ccPortalSigStatsEntry 3 }

		
--   1.3.6.1.4.1.388.11.2.4.2.100.8.1.4
-- 1.3.6.1.4.1.388.6.12.2.6.8.1.4
		-- 1.3.6.1.4.1.388.6.16.2.6.8.1.4
		ccPortalSigStatsSignalSum OBJECT-TYPE
			SYNTAX Integer32
			UNITS "dBm"
			MAX-ACCESS read-only
			STATUS current
			DESCRIPTION
				"A running sum of all Signal values calculated by the
				switch (using reported RSSI values), for packets 
				received via this Radio
				
				Note that this value is normally a negative value
				ranging from -10dBm to -80dBm.  It is possible for this
				value to be positive, but that would be rare, and would
				signal an exceptionally strong signal.
				
				(This value divided by ccPortalSigStatsNumPkts yields
				the average Signal value for all packets received
				from this MU)."
			::= { ccPortalSigStatsEntry 4 }

		
--   1.3.6.1.4.1.388.11.2.4.2.100.8.1.5
-- 1.3.6.1.4.1.388.6.12.2.6.8.1.5
		-- 1.3.6.1.4.1.388.6.16.2.6.8.1.5
		ccPortalSigStatsSignalSumSquares OBJECT-TYPE
			SYNTAX Counter64
			UNITS "dBm"
			MAX-ACCESS read-only
			STATUS current
			DESCRIPTION
				"A sum of the squares of each Signal value calculated
				for packets received via this Radio
				
				Unlike _SignalSum, this value is never negative, since
				the square of a negative number is a positive.
				
				(This value can be used to calculate the standard
				deviation for Signal values calculated for packets
				from this Portal)."
			::= { ccPortalSigStatsEntry 5 }

		
--   1.3.6.1.4.1.388.11.2.4.2.100.8.1.6
-- 1.3.6.1.4.1.388.6.12.2.6.8.1.6
		-- 1.3.6.1.4.1.388.6.16.2.6.8.1.6
		ccPortalSigStatsSignalMostRecent OBJECT-TYPE
			SYNTAX Integer32
			UNITS "dBm"
			MAX-ACCESS read-only
			STATUS current
			DESCRIPTION
				"The best Signal value seen from the Radio so far.
				(Remember that a -20dBm Signal is better than -60dBm).
				
				This value does not make sense when ccPortalSigStatsNumPkts 
				equals to 0."
			::= { ccPortalSigStatsEntry 6 }

		
--   1.3.6.1.4.1.388.11.2.4.2.100.8.1.7
-- 1.3.6.1.4.1.388.6.12.2.6.8.1.7
		-- 1.3.6.1.4.1.388.6.16.2.6.8.1.7
		ccPortalSigStatsNoiseBest OBJECT-TYPE
			SYNTAX Integer32
			UNITS "dBm"
			MAX-ACCESS read-only
			STATUS current
			DESCRIPTION
				"The best Noise value seen from the Radio so far.
				(Remember that -80dBm Noise is better than -70dBm).
				
				This value is initialized to 500dBm."
			::= { ccPortalSigStatsEntry 7 }

		
--   1.3.6.1.4.1.388.11.2.4.2.100.8.1.8
-- 1.3.6.1.4.1.388.6.12.2.6.8.1.8
		-- 1.3.6.1.4.1.388.6.16.2.6.8.1.8
		ccPortalSigStatsNoiseWorst OBJECT-TYPE
			SYNTAX Integer32
			UNITS "dBm"
			MAX-ACCESS read-only
			STATUS current
			DESCRIPTION
				"The worst Noise value seen from the Radio so far.
				(Remember that -50dBm Noise is worse than -60dBm).
				
				This value is initialized to -500dBm."
			::= { ccPortalSigStatsEntry 8 }

		
--   1.3.6.1.4.1.388.11.2.4.2.100.8.1.9
-- 1.3.6.1.4.1.388.6.12.2.6.8.1.9
		-- 1.3.6.1.4.1.388.6.16.2.6.8.1.9
		ccPortalSigStatsNoiseSum OBJECT-TYPE
			SYNTAX Integer32
			UNITS "dBm"
			MAX-ACCESS read-only
			STATUS current
			DESCRIPTION
				"A running sum of all Noise values calculated by the
				switch (using reported RSSI values), for packets
				received via this Radio
				
				Like _SignalSum, this value is normally a negative value.
				
				(This value divided by ccPortalSigStatsNumPkts yields
				the average Noise value for all packets received
				from this MU)."
			::= { ccPortalSigStatsEntry 9 }

		
--   1.3.6.1.4.1.388.11.2.4.2.100.8.1.10
-- 1.3.6.1.4.1.388.6.12.2.6.8.1.10
		-- 1.3.6.1.4.1.388.6.16.2.6.8.1.10
		ccPortalSigStatsNoiseSumSquares OBJECT-TYPE
			SYNTAX Counter64
			UNITS "dBm"
			MAX-ACCESS read-only
			STATUS current
			DESCRIPTION
				"A sum of the squares of each Noise value calculated
				for packets received via this Radio
				
				As with _SignalSumSquares, this value is never negative.
				
				(This value can be used to calculate the standard
				deviation for Noise values calculated for packets
				from this Portal)."
			::= { ccPortalSigStatsEntry 10 }

		
--   1.3.6.1.4.1.388.11.2.4.2.100.8.1.11
-- 1.3.6.1.4.1.388.6.12.2.6.8.1.11
		-- 1.3.6.1.4.1.388.6.16.2.6.8.1.11
		ccPortalSigStatsNoiseMostRecent OBJECT-TYPE
			SYNTAX Integer32
			UNITS "dBm"
			MAX-ACCESS read-only
			STATUS current
			DESCRIPTION
				"The best Noise value seen from the Radio so far.
				(Remember that -80dBm Noise is better than -70dBm).
				
				This value does not make sense when ccPortalSigStatsNumPkts 
				equals to 0."
			::= { ccPortalSigStatsEntry 11 }

		
--   1.3.6.1.4.1.388.11.2.4.2.100.8.1.12
-- 1.3.6.1.4.1.388.6.12.2.6.8.1.12
		-- 1.3.6.1.4.1.388.6.16.2.6.8.1.12
		ccPortalSigStatsSnrBest OBJECT-TYPE
			SYNTAX Integer32
			UNITS "dB"
			MAX-ACCESS read-only
			STATUS current
			DESCRIPTION
				"The best SNR value seen from the Radio so far.
				(Remember that +30dBm SNR is better than +20dBm).
				
				This value is initialized to -500dB."
			::= { ccPortalSigStatsEntry 12 }

		
--   1.3.6.1.4.1.388.11.2.4.2.100.8.1.13
-- 1.3.6.1.4.1.388.6.12.2.6.8.1.13
		-- 1.3.6.1.4.1.388.6.16.2.6.8.1.13
		ccPortalSigStatsSnrWorst OBJECT-TYPE
			SYNTAX Integer32
			UNITS "dB"
			MAX-ACCESS read-only
			STATUS current
			DESCRIPTION
				"The worst SNR value seen from the Radio so far.
				(Remember that +10dBm SNR is worse than +20dBm).
				
				This value is initialized to 500dB."
			::= { ccPortalSigStatsEntry 13 }

		
--   1.3.6.1.4.1.388.11.2.4.2.100.8.1.14
-- 1.3.6.1.4.1.388.6.12.2.6.8.1.14
		-- 1.3.6.1.4.1.388.6.16.2.6.8.1.14
		ccPortalSigStatsSnrSum OBJECT-TYPE
			SYNTAX Counter64
			UNITS "dB"
			MAX-ACCESS read-only
			STATUS current
			DESCRIPTION
				"A running sum of all SNR values calculated by the
				switch (using reported RSSI values), for packets 
				received via this Radio
				
				Unlike _Signal and _Noise, this value is never negative.
				
				(This value divided by ccPortalSigStatsNumPkts yields
				the average SNR value for all packets received
				from this MU)."
			::= { ccPortalSigStatsEntry 14 }

		
--   1.3.6.1.4.1.388.11.2.4.2.100.8.1.15
-- 1.3.6.1.4.1.388.6.12.2.6.8.1.15
		-- 1.3.6.1.4.1.388.6.16.2.6.8.1.15
		ccPortalSigStatsSnrSumSquares OBJECT-TYPE
			SYNTAX Counter64
			UNITS "dB"
			MAX-ACCESS read-only
			STATUS current
			DESCRIPTION
				"A sum of the squares of each SNR value calculated
				for packets received via this Radio
				
				This value is never negative.
				
				(This value can be used to calculate the standard
				deviation for SNR values calculated for packets
				from this Portal)."
			::= { ccPortalSigStatsEntry 15 }

		
--   1.3.6.1.4.1.388.11.2.4.2.100.8.1.16
-- 1.3.6.1.4.1.388.6.12.2.6.8.1.16
		-- 1.3.6.1.4.1.388.6.16.2.6.8.1.16
		ccPortalSigStatsSnrMostRecent OBJECT-TYPE
			SYNTAX Integer32
			UNITS "dB"
			MAX-ACCESS read-only
			STATUS current
			DESCRIPTION
				"The best SNR value seen from the Radio so far.
				(Remember that +30dBm SNR is better than +20dBm).
				
				This value does not make sense when ccPortalSigStatsNumPkts 
				equals to 0."
			::= { ccPortalSigStatsEntry 16 }

		
--   1.3.6.1.4.1.388.11.2.4.2.100.9
-- 1.3.6.1.4.1.388.6.12.2.6.9
		-- 1.3.6.1.4.1.388.6.16.2.6.9
		ccPortalSumStatsShortTable OBJECT-TYPE
			SYNTAX SEQUENCE OF CcPortalSumStatsShortEntry
			MAX-ACCESS not-accessible
			STATUS current
			DESCRIPTION
				"Averages and rates calculated over the SHORT window for
				each Portal."
			::= { ccPortalRfSum 9 }

		
--   1.3.6.1.4.1.388.11.2.4.2.100.9.1
-- 1.3.6.1.4.1.388.6.12.2.6.9.1
		-- 1.3.6.1.4.1.388.6.16.2.6.9.1
		ccPortalSumStatsShortEntry OBJECT-TYPE
			SYNTAX CcPortalSumStatsShortEntry
			MAX-ACCESS not-accessible
			STATUS current
			DESCRIPTION
				" "
			INDEX { ccPortalIndex }
			::= { ccPortalSumStatsShortTable 1 }

		
		CcPortalSumStatsShortEntry ::=
			SEQUENCE { 
				ccPortalSumStatsShortTimestamp
					TimeTicks,
				ccPortalSumStatsShortNumPkts
					Unsigned32,
				ccPortalSumStatsShortPktsPerSec100
					ScaleBy100,
				ccPortalSumStatsShortPktsPerSecTx100
					ScaleBy100,
				ccPortalSumStatsShortPktsPerSecRx100
					ScaleBy100,
				ccPortalSumStatsShortThroughput
					Unsigned32,
				ccPortalSumStatsShortThroughputTx
					Unsigned32,
				ccPortalSumStatsShortThroughputRx
					Unsigned32,
				ccPortalSumStatsShortAvgBitSpeed
					Unsigned32,
				ccPortalSumStatsShortAvgMuSignal
					Integer32,
				ccPortalSumStatsShortAvgMuNoise
					Integer32,
				ccPortalSumStatsShortAvgMuSnr
					Integer32,
				ccPortalSumStatsShortPp10kNUcastPkts
					PartsPer10k,
				ccPortalSumStatsShortPp10kTxWithRetries
					PartsPer10k,
				ccPortalSumStatsShortPp10kTxMaxRetries
					PartsPer10k,
				ccPortalSumStatsShortTxAvgRetries100
					ScaleBy100,
				ccPortalSumStatsShortPp10kRxUndecrypt
					PartsPer10k,
				ccPortalSumStatsShortTotalMus
					Unsigned32,
				ccPortalSumStatsShortPp10kRfUtil
					PartsPer10k,
				ccPortalSumStatsShortPp10kDropped
					PartsPer10k
			 }

--   1.3.6.1.4.1.388.11.2.4.2.100.9.1.1
-- 1.3.6.1.4.1.388.6.12.2.6.9.1.1
		-- 1.3.6.1.4.1.388.6.16.2.6.9.1.1
		ccPortalSumStatsShortTimestamp OBJECT-TYPE
			SYNTAX TimeTicks
			MAX-ACCESS read-only
			STATUS current
			DESCRIPTION
				"Snapshot of sysUpTime as of the END of the 'window' of 
				time that this entry of values represents."
			::= { ccPortalSumStatsShortEntry 1 }

		
--   1.3.6.1.4.1.388.11.2.4.2.100.9.1.2
-- 1.3.6.1.4.1.388.6.12.2.6.9.1.2
		-- 1.3.6.1.4.1.388.6.16.2.6.9.1.2
		ccPortalSumStatsShortNumPkts OBJECT-TYPE
			SYNTAX Unsigned32
			UNITS "packets"
			MAX-ACCESS read-only
			STATUS current
			DESCRIPTION
				"The number of packets used to calculate the statistics in
				this window."
			::= { ccPortalSumStatsShortEntry 2 }

		
--   1.3.6.1.4.1.388.11.2.4.2.100.9.1.3
-- 1.3.6.1.4.1.388.6.12.2.6.9.1.3
		-- 1.3.6.1.4.1.388.6.16.2.6.9.1.3
		ccPortalSumStatsShortPktsPerSec100 OBJECT-TYPE
			SYNTAX ScaleBy100
			UNITS "pkts per sec x100"
			MAX-ACCESS read-only
			STATUS current
			DESCRIPTION
				"Packets per second as averaged over the 'window'.
				
				For transmitted packets, each packet sucessfully sent 
				counts as 1, (not N, where N is the number of retries).
				
				Since SNMP does not convey decimal values, the result 
				is multiplied by 100."
			::= { ccPortalSumStatsShortEntry 3 }

		
--   1.3.6.1.4.1.388.11.2.4.2.100.9.1.4
-- 1.3.6.1.4.1.388.6.12.2.6.9.1.4
		-- 1.3.6.1.4.1.388.6.16.2.6.9.1.4
		ccPortalSumStatsShortPktsPerSecTx100 OBJECT-TYPE
			SYNTAX ScaleBy100
			UNITS "pkts per sec x100"
			MAX-ACCESS read-only
			STATUS current
			DESCRIPTION
				"Packets per second TX as averaged over the 'window'.
				
				Each packet sucessfully sent counts as 1, (not N, where N
				is the number of retries).
				
				Since SNMP does not convey decimal values, the result 
				is multiplied by 100."
			::= { ccPortalSumStatsShortEntry 4 }

		
--   1.3.6.1.4.1.388.11.2.4.2.100.9.1.5
-- 1.3.6.1.4.1.388.6.12.2.6.9.1.5
		-- 1.3.6.1.4.1.388.6.16.2.6.9.1.5
		ccPortalSumStatsShortPktsPerSecRx100 OBJECT-TYPE
			SYNTAX ScaleBy100
			UNITS "pkts per sec x100"
			MAX-ACCESS read-only
			STATUS current
			DESCRIPTION
				"Packets per second RX as averaged over the 'window'.
				
				Since SNMP does not convey decimal values, the result 
				is multiplied by 100."
			::= { ccPortalSumStatsShortEntry 5 }

		
--   1.3.6.1.4.1.388.11.2.4.2.100.9.1.6
-- 1.3.6.1.4.1.388.6.12.2.6.9.1.6
		-- 1.3.6.1.4.1.388.6.16.2.6.9.1.6
		ccPortalSumStatsShortThroughput OBJECT-TYPE
			SYNTAX Unsigned32
			UNITS "bits per second"
			MAX-ACCESS read-only
			STATUS current
			DESCRIPTION
				"Actual number of bits sent and received over the window,
				divided by the number of seconds in the window.
				
				For transmitted packets, each packet sucessfully sent 
				counts as 1, (not N, where N is the number of retries)."
			::= { ccPortalSumStatsShortEntry 6 }

		
--   1.3.6.1.4.1.388.11.2.4.2.100.9.1.7
-- 1.3.6.1.4.1.388.6.12.2.6.9.1.7
		-- 1.3.6.1.4.1.388.6.16.2.6.9.1.7
		ccPortalSumStatsShortThroughputTx OBJECT-TYPE
			SYNTAX Unsigned32
			UNITS "bits per second"
			MAX-ACCESS read-only
			STATUS current
			DESCRIPTION
				"Actual number of bits TX over the window,
				divided by the number of seconds in the window.
				
				Each packet sucessfully sent counts as 1, (not N, where N
				is the number of retries)."
			::= { ccPortalSumStatsShortEntry 7 }

		
--   1.3.6.1.4.1.388.11.2.4.2.100.9.1.8
-- 1.3.6.1.4.1.388.6.12.2.6.9.1.8
		-- 1.3.6.1.4.1.388.6.16.2.6.9.1.8
		ccPortalSumStatsShortThroughputRx OBJECT-TYPE
			SYNTAX Unsigned32
			UNITS "bits per second"
			MAX-ACCESS read-only
			STATUS current
			DESCRIPTION
				"Actual number of bits RX over the window,
				divided by the number of seconds in the window."
			::= { ccPortalSumStatsShortEntry 8 }

		
--   1.3.6.1.4.1.388.11.2.4.2.100.9.1.9
-- 1.3.6.1.4.1.388.6.12.2.6.9.1.9
		-- 1.3.6.1.4.1.388.6.16.2.6.9.1.9
		ccPortalSumStatsShortAvgBitSpeed OBJECT-TYPE
			SYNTAX Unsigned32
			UNITS "bits per second"
			MAX-ACCESS read-only
			STATUS current
			DESCRIPTION
				"An octet-weighted average of the speeds of all packets
				sent/received.  (For each possible speed, multiply the
				number of octets sent/received by that speed;  divide the
				sum by the total number of octets;  multiply by 8).
				
				For transmitted packets, each packet sucessfully sent 
				counts as 1, (not N, where N is the number of retries).
				
				This can be said in more plain english as: the average
				bit-speed at which packets were sent/received."
			::= { ccPortalSumStatsShortEntry 9 }

		
--   1.3.6.1.4.1.388.11.2.4.2.100.9.1.10
-- 1.3.6.1.4.1.388.6.12.2.6.9.1.10
		-- 1.3.6.1.4.1.388.6.16.2.6.9.1.10
		ccPortalSumStatsShortAvgMuSignal OBJECT-TYPE
			SYNTAX Integer32
			UNITS "dBm"
			MAX-ACCESS read-only
			STATUS current
			DESCRIPTION
				"The average of all signal values over the window.
				
				NOTE: dBm are normally negative.  Here the NEGATIVE values
				are reported as POSITIVE values.  PO"
			::= { ccPortalSumStatsShortEntry 10 }

		
--   1.3.6.1.4.1.388.11.2.4.2.100.9.1.11
-- 1.3.6.1.4.1.388.6.12.2.6.9.1.11
		-- 1.3.6.1.4.1.388.6.16.2.6.9.1.11
		ccPortalSumStatsShortAvgMuNoise OBJECT-TYPE
			SYNTAX Integer32
			UNITS "dBm"
			MAX-ACCESS read-only
			STATUS current
			DESCRIPTION
				"The average of all noise values over the window."
			::= { ccPortalSumStatsShortEntry 11 }

		
--   1.3.6.1.4.1.388.11.2.4.2.100.9.1.12
-- 1.3.6.1.4.1.388.6.12.2.6.9.1.12
		-- 1.3.6.1.4.1.388.6.16.2.6.9.1.12
		ccPortalSumStatsShortAvgMuSnr OBJECT-TYPE
			SYNTAX Integer32
			UNITS "dB"
			MAX-ACCESS read-only
			STATUS current
			DESCRIPTION
				"The average of all SNR values over the window."
			::= { ccPortalSumStatsShortEntry 12 }

		
--   1.3.6.1.4.1.388.11.2.4.2.100.9.1.13
-- 1.3.6.1.4.1.388.6.12.2.6.9.1.13
		-- 1.3.6.1.4.1.388.6.16.2.6.9.1.13
		ccPortalSumStatsShortPp10kNUcastPkts OBJECT-TYPE
			SYNTAX PartsPer10k
			UNITS "parts-per-10000"
			MAX-ACCESS read-only
			STATUS current
			DESCRIPTION
				"Ratio of packets that were NOT unicast.
				
				Expressed as parts-per-10000.
				"
			::= { ccPortalSumStatsShortEntry 13 }

		
--   1.3.6.1.4.1.388.11.2.4.2.100.9.1.14
-- 1.3.6.1.4.1.388.6.12.2.6.9.1.14
		-- 1.3.6.1.4.1.388.6.16.2.6.9.1.14
		ccPortalSumStatsShortPp10kTxWithRetries OBJECT-TYPE
			SYNTAX PartsPer10k
			UNITS "parts-per-10000"
			MAX-ACCESS read-only
			STATUS current
			DESCRIPTION
				"Ratio of TX packets that experienced one or more retries.
				
				Expressed as parts-per-10000.
				"
			::= { ccPortalSumStatsShortEntry 14 }

		
--   1.3.6.1.4.1.388.11.2.4.2.100.9.1.15
-- 1.3.6.1.4.1.388.6.12.2.6.9.1.15
		-- 1.3.6.1.4.1.388.6.16.2.6.9.1.15
		ccPortalSumStatsShortPp10kTxMaxRetries OBJECT-TYPE
			SYNTAX PartsPer10k
			UNITS "parts-per-10000"
			MAX-ACCESS read-only
			STATUS current
			DESCRIPTION
				"Ratio of TX packets that were dropped due to excessive.
				
				Expressed as parts-per-10000.
				"
			::= { ccPortalSumStatsShortEntry 15 }

		
--   1.3.6.1.4.1.388.11.2.4.2.100.9.1.16
-- 1.3.6.1.4.1.388.6.12.2.6.9.1.16
		-- 1.3.6.1.4.1.388.6.16.2.6.9.1.16
		ccPortalSumStatsShortTxAvgRetries100 OBJECT-TYPE
			SYNTAX ScaleBy100
			UNITS "average x100"
			MAX-ACCESS read-only
			STATUS current
			DESCRIPTION
				"For all transmit packets (those that experienced some 
				retries, those that were successfully transmitted with
				only 1 transmission, and those that attempted max times
				and gave-up), the average number of RE-transmission 
				attempts.
				
				Said another (though identical) way: the sum of all 
				tranmission attempts divided by the number of unique 
				packets attempted to be sent.
				
				Since SNMP does not convey decimal values, the result 
				above is multiplied by 100.
				
				If there were no RE-transmissions, this value would be 0.
				If every single packet required exactly two tranmissions,
				this value would be 100, (representing 1.00)."
			::= { ccPortalSumStatsShortEntry 16 }

		
--   1.3.6.1.4.1.388.11.2.4.2.100.9.1.17
-- 1.3.6.1.4.1.388.6.12.2.6.9.1.17
		-- 1.3.6.1.4.1.388.6.16.2.6.9.1.17
		ccPortalSumStatsShortPp10kRxUndecrypt OBJECT-TYPE
			SYNTAX PartsPer10k
			UNITS "parts-per-10000"
			MAX-ACCESS read-only
			STATUS current
			DESCRIPTION
				"Ratio of RX packets that were undecryptable.
				
				Expressed as parts-per-10000.
				"
			::= { ccPortalSumStatsShortEntry 17 }

		
--   1.3.6.1.4.1.388.11.2.4.2.100.9.1.18
-- 1.3.6.1.4.1.388.6.12.2.6.9.1.18
		-- 1.3.6.1.4.1.388.6.16.2.6.9.1.18
		ccPortalSumStatsShortTotalMus OBJECT-TYPE
			SYNTAX Unsigned32 (0..100)
			UNITS "number of MUs"
			MAX-ACCESS read-only
			STATUS current
			DESCRIPTION
				"The total number of MUs associated to the given Radio"
			::= { ccPortalSumStatsShortEntry 18 }

		
--   1.3.6.1.4.1.388.11.2.4.2.100.9.1.19
-- 1.3.6.1.4.1.388.6.12.2.6.9.1.19
		-- 1.3.6.1.4.1.388.6.16.2.6.9.1.19
		ccPortalSumStatsShortPp10kRfUtil OBJECT-TYPE
			SYNTAX PartsPer10k
			UNITS "parts-per-10000"
			MAX-ACCESS read-only
			STATUS current
			DESCRIPTION
				"The approximate utilization of the Portal's RF port.  
				Calculated as Throughput divided by AvgBitSpeed.
				
				Expressed as parts-per-10000.
				"
			::= { ccPortalSumStatsShortEntry 19 }

		
--   1.3.6.1.4.1.388.11.2.4.2.100.9.1.20
-- 1.3.6.1.4.1.388.6.12.2.6.9.1.20
		-- 1.3.6.1.4.1.388.6.16.2.6.9.1.20
		ccPortalSumStatsShortPp10kDropped OBJECT-TYPE
			SYNTAX PartsPer10k
			MAX-ACCESS read-only
			STATUS current
			DESCRIPTION
				"Packets dropped divided by packets sent.  Dropped here 
				means dropped intentionally due to the appropriate QoS 
				queue being full.  Other reasons for dropped packets are 
				not counted in this ratio.
				
				Calculated as an average for all WLANs implemented on 
				this Portal.
				
				Expressed as parts-per-10000.
				"
			::= { ccPortalSumStatsShortEntry 20 }

		
--   1.3.6.1.4.1.388.11.2.4.2.100.10
-- 1.3.6.1.4.1.388.6.12.2.6.10
		-- 1.3.6.1.4.1.388.6.16.2.6.10
		ccPortalSumStatsLongTable OBJECT-TYPE
			SYNTAX SEQUENCE OF CcPortalSumStatsLongEntry
			MAX-ACCESS not-accessible
			STATUS current
			DESCRIPTION
				"Averages and rates calculated over the LONG window for
				each Portal.
				
				(Refer to ccPortalSumStatsShortTable for descriptions)."
			::= { ccPortalRfSum 10 }

		
--   1.3.6.1.4.1.388.11.2.4.2.100.10.1
-- 1.3.6.1.4.1.388.6.12.2.6.10.1
		-- 1.3.6.1.4.1.388.6.16.2.6.10.1
		ccPortalSumStatsLongEntry OBJECT-TYPE
			SYNTAX CcPortalSumStatsLongEntry
			MAX-ACCESS not-accessible
			STATUS current
			DESCRIPTION
				" "
			INDEX { ccPortalIndex }
			::= { ccPortalSumStatsLongTable 1 }

		
		CcPortalSumStatsLongEntry ::=
			SEQUENCE { 
				ccPortalSumStatsLongTimestamp
					TimeTicks,
				ccPortalSumStatsLongNumPkts
					Unsigned32,
				ccPortalSumStatsLongPktsPerSec100
					ScaleBy100,
				ccPortalSumStatsLongPktsPerSecTx100
					ScaleBy100,
				ccPortalSumStatsLongPktsPerSecRx100
					ScaleBy100,
				ccPortalSumStatsLongThroughput
					Unsigned32,
				ccPortalSumStatsLongThroughputTx
					Unsigned32,
				ccPortalSumStatsLongThroughputRx
					Unsigned32,
				ccPortalSumStatsLongAvgBitSpeed
					Unsigned32,
				ccPortalSumStatsLongAvgMuSignal
					Integer32,
				ccPortalSumStatsLongAvgMuNoise
					Integer32,
				ccPortalSumStatsLongAvgMuSnr
					Integer32,
				ccPortalSumStatsLongPp10kNUcastPkts
					PartsPer10k,
				ccPortalSumStatsLongPp10kTxWithRetries
					PartsPer10k,
				ccPortalSumStatsLongPp10kTxMaxRetries
					PartsPer10k,
				ccPortalSumStatsLongTxAvgRetries100
					ScaleBy100,
				ccPortalSumStatsLongPp10kRxUndecrypt
					PartsPer10k,
				ccPortalSumStatsLongTotalMus
					Unsigned32,
				ccPortalSumStatsLongPp10kRfUtil
					PartsPer10k,
				ccPortalSumStatsLongPp10kDropped
					PartsPer10k
			 }

--   1.3.6.1.4.1.388.11.2.4.2.100.10.1.1
-- 1.3.6.1.4.1.388.6.12.2.6.10.1.1
		-- 1.3.6.1.4.1.388.6.16.2.6.10.1.1
		ccPortalSumStatsLongTimestamp OBJECT-TYPE
			SYNTAX TimeTicks
			MAX-ACCESS read-only
			STATUS current
			DESCRIPTION
				" Snapshot of sysUpTime as of the END of the 'window' of 
				time that this entry of values represents."
			::= { ccPortalSumStatsLongEntry 1 }

		
--   1.3.6.1.4.1.388.11.2.4.2.100.10.1.2
-- 1.3.6.1.4.1.388.6.12.2.6.10.1.2
		-- 1.3.6.1.4.1.388.6.16.2.6.10.1.2
		ccPortalSumStatsLongNumPkts OBJECT-TYPE
			SYNTAX Unsigned32
			UNITS "packets"
			MAX-ACCESS read-only
			STATUS current
			DESCRIPTION
				" The number of packets used to calculate the statistics in
				this window"
			::= { ccPortalSumStatsLongEntry 2 }

		
--   1.3.6.1.4.1.388.11.2.4.2.100.10.1.3
-- 1.3.6.1.4.1.388.6.12.2.6.10.1.3
		-- 1.3.6.1.4.1.388.6.16.2.6.10.1.3
		ccPortalSumStatsLongPktsPerSec100 OBJECT-TYPE
			SYNTAX ScaleBy100
			UNITS "pkts per sec x100"
			MAX-ACCESS read-only
			STATUS current
			DESCRIPTION
				" Packets per second as averaged over the 'window'.
								
				For transmitted packets, each packet sucessfully sent 
				counts as 1, (not N, where N is the number of retries).
								
				Since SNMP does not convey decimal values, the result 
				is multiplied by 100."
			::= { ccPortalSumStatsLongEntry 3 }

		
--   1.3.6.1.4.1.388.11.2.4.2.100.10.1.4
-- 1.3.6.1.4.1.388.6.12.2.6.10.1.4
		-- 1.3.6.1.4.1.388.6.16.2.6.10.1.4
		ccPortalSumStatsLongPktsPerSecTx100 OBJECT-TYPE
			SYNTAX ScaleBy100
			UNITS "pkts per sec x100"
			MAX-ACCESS read-only
			STATUS current
			DESCRIPTION
				" Packets per second TX as averaged over the 'window'.
								
				Each packet sucessfully sent counts as 1, (not N, where N
				is the number of retries).
								
				Since SNMP does not convey decimal values, the result 
				is multiplied by 100."
			::= { ccPortalSumStatsLongEntry 4 }

		
--   1.3.6.1.4.1.388.11.2.4.2.100.10.1.5
-- 1.3.6.1.4.1.388.6.12.2.6.10.1.5
		-- 1.3.6.1.4.1.388.6.16.2.6.10.1.5
		ccPortalSumStatsLongPktsPerSecRx100 OBJECT-TYPE
			SYNTAX ScaleBy100
			UNITS "pkts per sec x100"
			MAX-ACCESS read-only
			STATUS current
			DESCRIPTION
				"Packets per second RX as averaged over the 'window'.
								
				Since SNMP does not convey decimal values, the result 
				is multiplied by 100."
			::= { ccPortalSumStatsLongEntry 5 }

		
--   1.3.6.1.4.1.388.11.2.4.2.100.10.1.6
-- 1.3.6.1.4.1.388.6.12.2.6.10.1.6
		-- 1.3.6.1.4.1.388.6.16.2.6.10.1.6
		ccPortalSumStatsLongThroughput OBJECT-TYPE
			SYNTAX Unsigned32
			UNITS "bits per second"
			MAX-ACCESS read-only
			STATUS current
			DESCRIPTION
				"Actual number of bits sent and received over the window,
				divided by the number of seconds in the window.
								
				For transmitted packets, each packet sucessfully sent 
				counts as 1, (not N, where N is the number of retries)"
			::= { ccPortalSumStatsLongEntry 6 }

		
--   1.3.6.1.4.1.388.11.2.4.2.100.10.1.7
-- 1.3.6.1.4.1.388.6.12.2.6.10.1.7
		-- 1.3.6.1.4.1.388.6.16.2.6.10.1.7
		ccPortalSumStatsLongThroughputTx OBJECT-TYPE
			SYNTAX Unsigned32
			UNITS "bits per second"
			MAX-ACCESS read-only
			STATUS current
			DESCRIPTION
				"Actual number of bits TX over the window,
				divided by the number of seconds in the window.
							
				Each packet sucessfully sent counts as 1, (not N, where N
				is the number of retries)."
			::= { ccPortalSumStatsLongEntry 7 }

		
--   1.3.6.1.4.1.388.11.2.4.2.100.10.1.8
-- 1.3.6.1.4.1.388.6.12.2.6.10.1.8
		-- 1.3.6.1.4.1.388.6.16.2.6.10.1.8
		ccPortalSumStatsLongThroughputRx OBJECT-TYPE
			SYNTAX Unsigned32
			UNITS "bits per second"
			MAX-ACCESS read-only
			STATUS current
			DESCRIPTION
				"Actual number of bits RX over the window,
				divided by the number of seconds in the window."
			::= { ccPortalSumStatsLongEntry 8 }

		
--   1.3.6.1.4.1.388.11.2.4.2.100.10.1.9
-- 1.3.6.1.4.1.388.6.12.2.6.10.1.9
		-- 1.3.6.1.4.1.388.6.16.2.6.10.1.9
		ccPortalSumStatsLongAvgBitSpeed OBJECT-TYPE
			SYNTAX Unsigned32
			UNITS "bits per second"
			MAX-ACCESS read-only
			STATUS current
			DESCRIPTION
				" An octet-weighted average of the speeds of all packets
				 sent/received.  (For each possible speed, multiply the
				 number of octets sent/received by that speed;  divide the
				 sum by the total number of octets;  multiply by 8).
								
				 For transmitted packets, each packet sucessfully sent 
				 counts as 1, (not N, where N is the number of retries).
								
				 This can be said in more plain english as: the average
				 bit-speed at which packets were sent/received."
			::= { ccPortalSumStatsLongEntry 9 }

		
--   1.3.6.1.4.1.388.11.2.4.2.100.10.1.10
-- 1.3.6.1.4.1.388.6.12.2.6.10.1.10
		-- 1.3.6.1.4.1.388.6.16.2.6.10.1.10
		ccPortalSumStatsLongAvgMuSignal OBJECT-TYPE
			SYNTAX Integer32
			UNITS "dBm"
			MAX-ACCESS read-only
			STATUS current
			DESCRIPTION
				" The average of all signal values over the window.
								
				 NOTE: dBm are normally negative.  Here the NEGATIVE values
				 are reported as POSITIVE values.  PO"
			::= { ccPortalSumStatsLongEntry 10 }

		
--   1.3.6.1.4.1.388.11.2.4.2.100.10.1.11
-- 1.3.6.1.4.1.388.6.12.2.6.10.1.11
		-- 1.3.6.1.4.1.388.6.16.2.6.10.1.11
		ccPortalSumStatsLongAvgMuNoise OBJECT-TYPE
			SYNTAX Integer32
			UNITS "dBm"
			MAX-ACCESS read-only
			STATUS current
			DESCRIPTION
				" The average of all noise values over the window."
			::= { ccPortalSumStatsLongEntry 11 }

		
--   1.3.6.1.4.1.388.11.2.4.2.100.10.1.12
-- 1.3.6.1.4.1.388.6.12.2.6.10.1.12
		-- 1.3.6.1.4.1.388.6.16.2.6.10.1.12
		ccPortalSumStatsLongAvgMuSnr OBJECT-TYPE
			SYNTAX Integer32
			UNITS "dB"
			MAX-ACCESS read-only
			STATUS current
			DESCRIPTION
				" The average of all SNR values over the window."
			::= { ccPortalSumStatsLongEntry 12 }

		
--   1.3.6.1.4.1.388.11.2.4.2.100.10.1.13
-- 1.3.6.1.4.1.388.6.12.2.6.10.1.13
		-- 1.3.6.1.4.1.388.6.16.2.6.10.1.13
		ccPortalSumStatsLongPp10kNUcastPkts OBJECT-TYPE
			SYNTAX PartsPer10k
			UNITS "parts-per-10000"
			MAX-ACCESS read-only
			STATUS current
			DESCRIPTION
				" Ratio of packets that were NOT unicast.
								
				 Expressed as parts-per-10000.
				"
			::= { ccPortalSumStatsLongEntry 13 }

		
--   1.3.6.1.4.1.388.11.2.4.2.100.10.1.14
-- 1.3.6.1.4.1.388.6.12.2.6.10.1.14
		-- 1.3.6.1.4.1.388.6.16.2.6.10.1.14
		ccPortalSumStatsLongPp10kTxWithRetries OBJECT-TYPE
			SYNTAX PartsPer10k
			UNITS "parts-per-10000"
			MAX-ACCESS read-only
			STATUS current
			DESCRIPTION
				"Ratio of TX packets that experienced one or more retries.
								
				  Expressed as parts-per-10000.
				"
			::= { ccPortalSumStatsLongEntry 14 }

		
--   1.3.6.1.4.1.388.11.2.4.2.100.10.1.15
-- 1.3.6.1.4.1.388.6.12.2.6.10.1.15
		-- 1.3.6.1.4.1.388.6.16.2.6.10.1.15
		ccPortalSumStatsLongPp10kTxMaxRetries OBJECT-TYPE
			SYNTAX PartsPer10k
			UNITS "parts-per-10000"
			MAX-ACCESS read-only
			STATUS current
			DESCRIPTION
				" Ratio of TX packets that were dropped due to excessive.
								
				 Expressed as parts-per-10000.
				"
			::= { ccPortalSumStatsLongEntry 15 }

		
--   1.3.6.1.4.1.388.11.2.4.2.100.10.1.16
-- 1.3.6.1.4.1.388.6.12.2.6.10.1.16
		-- 1.3.6.1.4.1.388.6.16.2.6.10.1.16
		ccPortalSumStatsLongTxAvgRetries100 OBJECT-TYPE
			SYNTAX ScaleBy100
			UNITS "average x100"
			MAX-ACCESS read-only
			STATUS current
			DESCRIPTION
				" For all transmit packets (those that experienced some 
				 retries, those that were successfully transmitted with
				 only 1 transmission, and those that attempted max times
				 and gave-up), the average number of RE-transmission 
				 attempts.
								
				 Said another (though identical) way: the sum of all 
				 tranmission attempts divided by the number of unique 
				 packets attempted to be sent.
								
				 Since SNMP does not convey decimal values, the result 
				 above is multiplied by 100.
								
				 If there were no RE-transmissions, this value would be 0.
				 If every single packet required exactly two tranmissions,
				 this value would be 100, (representing 1.00)"
			::= { ccPortalSumStatsLongEntry 16 }

		
--   1.3.6.1.4.1.388.11.2.4.2.100.10.1.17
-- 1.3.6.1.4.1.388.6.12.2.6.10.1.17
		-- 1.3.6.1.4.1.388.6.16.2.6.10.1.17
		ccPortalSumStatsLongPp10kRxUndecrypt OBJECT-TYPE
			SYNTAX PartsPer10k
			UNITS "parts-per-10000"
			MAX-ACCESS read-only
			STATUS current
			DESCRIPTION
				" Ratio of RX packets that were undecryptable.
								
				 Expressed as parts-per-10000.
				"
			::= { ccPortalSumStatsLongEntry 17 }

		
--   1.3.6.1.4.1.388.11.2.4.2.100.10.1.18
-- 1.3.6.1.4.1.388.6.12.2.6.10.1.18
		-- 1.3.6.1.4.1.388.6.16.2.6.10.1.18
		ccPortalSumStatsLongTotalMus OBJECT-TYPE
			SYNTAX Unsigned32 (0..100)
			UNITS "number of MUs"
			MAX-ACCESS read-only
			STATUS current
			DESCRIPTION
				" The total number of MUs associated to the given Radio"
			::= { ccPortalSumStatsLongEntry 18 }

		
--   1.3.6.1.4.1.388.11.2.4.2.100.10.1.19
-- 1.3.6.1.4.1.388.6.12.2.6.10.1.19
		-- 1.3.6.1.4.1.388.6.16.2.6.10.1.19
		ccPortalSumStatsLongPp10kRfUtil OBJECT-TYPE
			SYNTAX PartsPer10k
			UNITS "parts-per-10000"
			MAX-ACCESS read-only
			STATUS current
			DESCRIPTION
				" The approximate utilization of the Portal's RF port.  
				 Calculated as Throughput divided by AvgBitSpeed.
							
				 Expressed as parts-per-10000.
				"
			::= { ccPortalSumStatsLongEntry 19 }

		
--   1.3.6.1.4.1.388.11.2.4.2.100.10.1.20
-- 1.3.6.1.4.1.388.6.12.2.6.10.1.20
		-- 1.3.6.1.4.1.388.6.16.2.6.10.1.20
		ccPortalSumStatsLongPp10kDropped OBJECT-TYPE
			SYNTAX PartsPer10k
			MAX-ACCESS read-only
			STATUS current
			DESCRIPTION
				" Packets dropped divided by packets sent.  Dropped here 
				 means dropped intentionally due to the appropriate QoS 
				 queue being full.  Other reasons for dropped packets are 
				 not counted in this ratio.
								
				 Calculated as an average for all WLANs implemented on 
				 this Portal.
								
				 Expressed as parts-per-10000.
				"
			::= { ccPortalSumStatsLongEntry 20 }

		
--   This group contains MIB values that describe the
-- MUs (Mobile Units) known to this WS5000.
-- 1.3.6.1.4.1.388.11.2.4.4
-- 1.3.6.1.4.1.388.6.12.3
		-- 1.3.6.1.4.1.388.6.16.3
		ccMus OBJECT IDENTIFIER ::= { ccRFStatistics 3 }

		
--   1.3.6.1.4.1.388.11.2.4.4.1
-- 1.3.6.1.4.1.388.6.12.3.1
		-- 1.3.6.1.4.1.388.6.16.3.1
		ccMuInfoTable OBJECT-TYPE
			SYNTAX SEQUENCE OF CcMuInfoEntry
			MAX-ACCESS not-accessible
			STATUS current
			DESCRIPTION
				"This table describes general information about
				each MU serviced by the switch."
			::= { ccMus 1 }

		
--   1.3.6.1.4.1.388.11.2.4.4.1.1
-- 1.3.6.1.4.1.388.6.12.3.1.1
		-- 1.3.6.1.4.1.388.6.16.3.1.1
		ccMuInfoEntry OBJECT-TYPE
			SYNTAX CcMuInfoEntry
			MAX-ACCESS not-accessible
			STATUS current
			DESCRIPTION
				" "
			INDEX { ccMuMac }
			::= { ccMuInfoTable 1 }

		
		CcMuInfoEntry ::=
			SEQUENCE { 
				ccMuMac
					DisplayString,
				ccMuWlanIndex
					Integer32,
				ccMuWlanName
					DisplayString,
				ccMuIsDataReady
					TruthValue,
				ccMuPortalIndex
					Integer32,
				ccMuPortalMac
					DisplayString,
				ccMuSymbolRogueApEna
					TruthValue,
				ccMuIpAddr
					IpAddress,
				ccMuType
					INTEGER,
				ccMuRadioType
					RadioType,
				ccMuSupportedRates
					BITS,
				ccMuPowerMode
					INTEGER,
				ccMuAuthenticationMethod
					INTEGER,
				ccMuEncryptionMethod
					INTEGER,
				ccMuVlanId
					Unsigned32
			 }

--   1.3.6.1.4.1.388.11.2.4.4.1.1.1
-- 1.3.6.1.4.1.388.6.12.3.1.1.1
		-- 1.3.6.1.4.1.388.6.16.3.1.1.1
		ccMuMac OBJECT-TYPE
			SYNTAX DisplayString
			MAX-ACCESS accessible-for-notify
			STATUS current
			DESCRIPTION
				"MAC address of the MU."
			::= { ccMuInfoEntry 1 }

		
--   1.3.6.1.4.1.388.11.2.4.4.1.1.2
-- 1.3.6.1.4.1.388.6.12.3.1.1.2
		-- 1.3.6.1.4.1.388.6.16.3.1.1.2
		ccMuWlanIndex OBJECT-TYPE
			SYNTAX Integer32 (0..63)
			MAX-ACCESS read-only
			STATUS current
			DESCRIPTION
				"(Reserved for future implementation)."
			::= { ccMuInfoEntry 2 }

		
--   1.3.6.1.4.1.388.11.2.4.4.1.1.3
-- 1.3.6.1.4.1.388.6.12.3.1.1.3
		-- 1.3.6.1.4.1.388.6.16.3.1.1.3
		ccMuWlanName OBJECT-TYPE
			SYNTAX DisplayString
			MAX-ACCESS read-only
			STATUS current
			DESCRIPTION
				"The name of the WLAN this MU is associated to."
			::= { ccMuInfoEntry 3 }

		
--   1.3.6.1.4.1.388.11.2.4.4.1.1.4
-- 1.3.6.1.4.1.388.6.12.3.1.1.4
		-- 1.3.6.1.4.1.388.6.16.3.1.1.4
		ccMuIsDataReady OBJECT-TYPE
			SYNTAX TruthValue
			MAX-ACCESS read-only
			STATUS current
			DESCRIPTION
				"This value is true if the WS5000 is ready to
				forward/switch packets to/from this MU,
				(internally called the 'data ready' state).
				Otherwise this value is false."
			::= { ccMuInfoEntry 4 }

		
--   1.3.6.1.4.1.388.11.2.4.4.1.1.5
-- 1.3.6.1.4.1.388.6.12.3.1.1.5
		-- 1.3.6.1.4.1.388.6.16.3.1.1.5
		ccMuPortalIndex OBJECT-TYPE
			SYNTAX Integer32 (0..63)
			MAX-ACCESS read-only
			STATUS current
			DESCRIPTION
				"The index of the entry in the PortalTable to
				which this MU is associated."
			::= { ccMuInfoEntry 5 }

		
--   1.3.6.1.4.1.388.11.2.4.4.1.1.6
-- 1.3.6.1.4.1.388.6.12.3.1.1.6
		-- 1.3.6.1.4.1.388.6.16.3.1.1.6
		ccMuPortalMac OBJECT-TYPE
			SYNTAX DisplayString
			MAX-ACCESS read-only
			STATUS current
			DESCRIPTION
				"The MAC address of the Portal to which this MU is
				associated."
			::= { ccMuInfoEntry 6 }

		
--   1.3.6.1.4.1.388.11.2.4.4.1.1.7
-- 1.3.6.1.4.1.388.6.12.3.1.1.7
		-- 1.3.6.1.4.1.388.6.16.3.1.1.7
		ccMuSymbolRogueApEna OBJECT-TYPE
			SYNTAX TruthValue
			MAX-ACCESS read-only
			STATUS current
			DESCRIPTION
				"If true, this MU supports Symbol's Rogue AP
				detection assist algorithm."
			::= { ccMuInfoEntry 7 }

		
--   1.3.6.1.4.1.388.11.2.4.4.1.1.8
-- 1.3.6.1.4.1.388.6.12.3.1.1.8
		-- 1.3.6.1.4.1.388.6.16.3.1.1.8
		ccMuIpAddr OBJECT-TYPE
			SYNTAX IpAddress
			MAX-ACCESS read-only
			STATUS current
			DESCRIPTION
				"IP address of the MU."
			::= { ccMuInfoEntry 8 }

		
--   1.3.6.1.4.1.388.11.2.4.4.1.1.9
-- 1.3.6.1.4.1.388.6.12.3.1.1.9
		-- 1.3.6.1.4.1.388.6.16.3.1.1.9
		ccMuType OBJECT-TYPE
			SYNTAX INTEGER
				{
				data(1),
				voice(2),
				accessPoint(3)
				}
			MAX-ACCESS read-only
			STATUS current
			DESCRIPTION
				"Type of the MU."
			::= { ccMuInfoEntry 9 }

		
--   1.3.6.1.4.1.388.11.2.4.4.1.1.10
-- 1.3.6.1.4.1.388.6.12.3.1.1.10
		-- 1.3.6.1.4.1.388.6.16.3.1.1.10
		ccMuRadioType OBJECT-TYPE
			SYNTAX RadioType
			MAX-ACCESS read-only
			STATUS current
			DESCRIPTION
				"Radio type of the MU."
			::= { ccMuInfoEntry 10 }

		
--   1.3.6.1.4.1.388.11.2.4.4.1.1.11
-- 1.3.6.1.4.1.388.6.12.3.1.1.11
		-- 1.3.6.1.4.1.388.6.16.3.1.1.11
		ccMuSupportedRates OBJECT-TYPE
			SYNTAX BITS
				{
				supports1Mb(0),
				supports2Mb(1),
				supports5dot5Mb(2),
				supports6Mb(3),
				supports9Mb(4),
				supports11Mb(5),
				supports12Mb(6),
				supports18Mb(7),
				supports22Mb(8),
				supports24Mb(9),
				supports36Mb(10),
				supports48Mb(11),
				supports54Mb(12)
				}
			MAX-ACCESS read-only
			STATUS current
			DESCRIPTION
				"A bit-mask of rates supported by this MU."
			::= { ccMuInfoEntry 11 }

		
--   1.3.6.1.4.1.388.11.2.4.4.1.1.12
-- 1.3.6.1.4.1.388.6.12.3.1.1.12
		-- 1.3.6.1.4.1.388.6.16.3.1.1.12
		ccMuPowerMode OBJECT-TYPE
			SYNTAX INTEGER
				{
				continuousAccessMode(1),
				powerSavePolling(2)
				}
			MAX-ACCESS read-only
			STATUS current
			DESCRIPTION
				"Power-mode implemented by the MU.
				
				A MU's status will constantly switch between PSP and 
				CAM mode when it is in PSP mode.  
				 "
			::= { ccMuInfoEntry 12 }

		
--   1.3.6.1.4.1.388.11.2.4.4.1.1.13
-- 1.3.6.1.4.1.388.6.12.3.1.1.13
		-- 1.3.6.1.4.1.388.6.16.3.1.1.13
		ccMuAuthenticationMethod OBJECT-TYPE
			SYNTAX INTEGER
				{
				none(1),
				eap802dot1x(2),
				kerberos(3)
				}
			MAX-ACCESS read-only
			STATUS current
			DESCRIPTION
				"Authentication method implemented by the MU."
			::= { ccMuInfoEntry 13 }

		
--   1.3.6.1.4.1.388.11.2.4.4.1.1.14
-- 1.3.6.1.4.1.388.6.12.3.1.1.14
		-- 1.3.6.1.4.1.388.6.16.3.1.1.14
		ccMuEncryptionMethod OBJECT-TYPE
			SYNTAX INTEGER
				{
				none(1),
				wep40(2),
				wep128(3),
				keyGuardMCM(4),
				wpaTKIP(5),
				wpa2AesCcmp(6)
				}
			MAX-ACCESS read-only
			STATUS current
			DESCRIPTION
				"Encryption method implemented by the MU."
			::= { ccMuInfoEntry 14 }

		
--   1.3.6.1.4.1.388.11.2.4.4.1.1.15
-- 1.3.6.1.4.1.388.6.12.3.1.1.15
		-- 1.3.6.1.4.1.388.6.16.3.1.1.15
		ccMuVlanId OBJECT-TYPE
			SYNTAX Unsigned32 (1..31)
			MAX-ACCESS read-only
			STATUS current
			DESCRIPTION
				"The VLAN that this MU is assigned to.
				"
			::= { ccMuInfoEntry 15 }

		
--   1.3.6.1.4.1.388.11.2.4.4.2
-- 1.3.6.1.4.1.388.6.12.3.2
		-- 1.3.6.1.4.1.388.6.16.3.2
		ccMuStatsTable OBJECT-TYPE
			SYNTAX SEQUENCE OF CcMuStatsEntry
			MAX-ACCESS not-accessible
			STATUS current
			DESCRIPTION
				" "
			::= { ccMus 2 }

		
--   All 
-- 1.3.6.1.4.1.388.11.2.4.4.2.1
-- 1.3.6.1.4.1.388.6.12.3.2.1
		-- 1.3.6.1.4.1.388.6.16.3.2.1
		ccMuStatsEntry OBJECT-TYPE
			SYNTAX CcMuStatsEntry
			MAX-ACCESS not-accessible
			STATUS current
			DESCRIPTION
				" "
			INDEX { ccMuMac }
			::= { ccMuStatsTable 1 }

		
		CcMuStatsEntry ::=
			SEQUENCE { 
				ccMuTxPktsUcast
					Counter32,
				ccMuRxPktsUcast
					Counter32,
				ccMuRxPktsNUcast
					Counter32,
				ccMuTxOctetsUcast
					Counter32,
				ccMuRxOctetsUcast
					Counter32,
				ccMuRxOctetsNUcast
					Counter32,
				ccMuRxUndecryptablePkts
					Counter32,
				ccMuRxRssiNumPkts
					Counter32,
				ccMuRxRssiSum
					Integer32,
				ccMuRxRssiSumSquares
					Counter64,
				ccMuRxRssiMostRecent
					INTEGER,
				ccMuLastActivity
					TimeTicks
			 }

--   1.3.6.1.4.1.388.11.2.4.4.2.1.1
-- 1.3.6.1.4.1.388.6.12.3.2.1.1
		-- 1.3.6.1.4.1.388.6.16.3.2.1.1
		ccMuTxPktsUcast OBJECT-TYPE
			SYNTAX Counter32
			MAX-ACCESS read-only
			STATUS current
			DESCRIPTION
				" The number of Unicast packets transmitted to the MU"
			::= { ccMuStatsEntry 1 }

		
--   1.3.6.1.4.1.388.11.2.4.4.2.1.2
-- 1.3.6.1.4.1.388.6.12.3.2.1.2
		-- 1.3.6.1.4.1.388.6.16.3.2.1.2
		ccMuRxPktsUcast OBJECT-TYPE
			SYNTAX Counter32
			MAX-ACCESS read-only
			STATUS current
			DESCRIPTION
				" The number of Unicast packets received from the MU"
			::= { ccMuStatsEntry 2 }

		
--   1.3.6.1.4.1.388.11.2.4.4.2.1.3
-- 1.3.6.1.4.1.388.6.12.3.2.1.3
		-- 1.3.6.1.4.1.388.6.16.3.2.1.3
		ccMuRxPktsNUcast OBJECT-TYPE
			SYNTAX Counter32
			MAX-ACCESS read-only
			STATUS current
			DESCRIPTION
				" The number of Non unicast packets received from a MU"
			::= { ccMuStatsEntry 3 }

		
--   This value existed in WS2000 v1.0, but never incremented
-- from 0.  This variable should never have been defined,
-- since there is no such thing as a non-unicast packet 
-- moving from a MU to a Portal, (Rx at the Portal).
-- 1.3.6.1.4.1.388.11.2.4.4.2.1.4
-- 1.3.6.1.4.1.388.6.12.3.2.1.4
		-- 1.3.6.1.4.1.388.6.16.3.2.1.4
		ccMuTxOctetsUcast OBJECT-TYPE
			SYNTAX Counter32
			MAX-ACCESS read-only
			STATUS current
			DESCRIPTION
				" The number of unicast bytes transmitted to the MU"
			::= { ccMuStatsEntry 4 }

		
--   1.3.6.1.4.1.388.11.2.4.4.2.1.5
-- 1.3.6.1.4.1.388.6.12.3.2.1.5
		-- 1.3.6.1.4.1.388.6.16.3.2.1.5
		ccMuRxOctetsUcast OBJECT-TYPE
			SYNTAX Counter32
			MAX-ACCESS read-only
			STATUS current
			DESCRIPTION
				" The number of unicast bytes received from an MU"
			::= { ccMuStatsEntry 5 }

		
--   1.3.6.1.4.1.388.11.2.4.4.2.1.6
-- 1.3.6.1.4.1.388.6.12.3.2.1.6
		-- 1.3.6.1.4.1.388.6.16.3.2.1.6
		ccMuRxOctetsNUcast OBJECT-TYPE
			SYNTAX Counter32
			MAX-ACCESS read-only
			STATUS current
			DESCRIPTION
				" The number of Non Unicast Bytes received from an MU"
			::= { ccMuStatsEntry 6 }

		
--   This value existed in WS2000 v1.0, but never incremented
-- from 0.  This variable should never have been defined,
-- since there is no such thing as a non-unicast packet 
-- moving from a MU to a Portal, (Rx at the Portal).
-- 1.3.6.1.4.1.388.11.2.4.4.2.1.7
-- 1.3.6.1.4.1.388.6.12.3.2.1.7
		-- 1.3.6.1.4.1.388.6.16.3.2.1.7
		ccMuRxUndecryptablePkts OBJECT-TYPE
			SYNTAX Counter32
			MAX-ACCESS read-only
			STATUS current
			DESCRIPTION
				" The number of undecryptable packets received from an MU"
			::= { ccMuStatsEntry 7 }

		
--   This value is duplicated by ccMuSigStatsNumPkts, but this
-- one is retained for backwards-compatibility.
-- 1.3.6.1.4.1.388.11.2.4.4.2.1.8
-- 1.3.6.1.4.1.388.6.12.3.2.1.8
		-- 1.3.6.1.4.1.388.6.16.3.2.1.8
		ccMuRxRssiNumPkts OBJECT-TYPE
			SYNTAX Counter32
			MAX-ACCESS read-only
			STATUS current
			DESCRIPTION
				" The number of packets received from an MU for which all the signal related claculations in this table are done"
			::= { ccMuStatsEntry 8 }

		
--   This value is duplicated by ccMuSigStatsRssiSum, but this
-- one is retained for backwards-compatibility.
-- 1.3.6.1.4.1.388.11.2.4.4.2.1.9
-- 1.3.6.1.4.1.388.6.12.3.2.1.9
		-- 1.3.6.1.4.1.388.6.16.3.2.1.9
		ccMuRxRssiSum OBJECT-TYPE
			SYNTAX Integer32
			MAX-ACCESS read-only
			STATUS current
			DESCRIPTION
				" The sum of Signal strength values of all the packets received from this MU"
			::= { ccMuStatsEntry 9 }

		
--   This value is duplicated by ccMuSigStatsRssiSumSquares, 
-- but this one is retained for backwards-compatibility.
-- 1.3.6.1.4.1.388.11.2.4.4.2.1.10
-- 1.3.6.1.4.1.388.6.12.3.2.1.10
		-- 1.3.6.1.4.1.388.6.16.3.2.1.10
		ccMuRxRssiSumSquares OBJECT-TYPE
			SYNTAX Counter64
			MAX-ACCESS read-only
			STATUS current
			DESCRIPTION
				" The sumsq of Signal strength of all the packets received from this MU"
			::= { ccMuStatsEntry 10 }

		
--   This value is duplicated by ccMuSigStatsRssiMostRecent, 
-- but this one is retained for backwards-compatibility.
-- 
-- ??-CM: this should be Uint32 - would chaning this be an
-- incompatible change?  Any diff on wire Int32 vs Unit32 ?
-- 1.3.6.1.4.1.388.11.2.4.4.2.1.11
-- 1.3.6.1.4.1.388.6.12.3.2.1.11
		-- 1.3.6.1.4.1.388.6.16.3.2.1.11
		ccMuRxRssiMostRecent OBJECT-TYPE
			SYNTAX INTEGER (0..255)
			MAX-ACCESS read-only
			STATUS current
			DESCRIPTION
				" The most recent value of the signal strength received from this MU"
			::= { ccMuStatsEntry 11 }

		
--   1.3.6.1.4.1.388.11.2.4.4.2.1.12
-- 1.3.6.1.4.1.388.6.12.3.2.1.12
		-- 1.3.6.1.4.1.388.6.16.3.2.1.12
		ccMuLastActivity OBJECT-TYPE
			SYNTAX TimeTicks
			MAX-ACCESS read-only
			STATUS current
			DESCRIPTION
				" The time stamp at which the last activity was seen fromn this MU
				"
			::= { ccMuStatsEntry 12 }

		
--   1.3.6.1.4.1.388.11.2.4.4.3
-- 1.3.6.1.4.1.388.6.12.3.3
		-- 1.3.6.1.4.1.388.6.16.3.3
		ccMuRxPktsTable OBJECT-TYPE
			SYNTAX SEQUENCE OF CcMuRxPktsEntry
			MAX-ACCESS not-accessible
			STATUS current
			DESCRIPTION
				" The Number of Packets received at various rates from the Moblie Unit"
			::= { ccMus 3 }

		
--   1.3.6.1.4.1.388.11.2.4.4.3.1
-- 1.3.6.1.4.1.388.6.12.3.3.1
		-- 1.3.6.1.4.1.388.6.16.3.3.1
		ccMuRxPktsEntry OBJECT-TYPE
			SYNTAX CcMuRxPktsEntry
			MAX-ACCESS not-accessible
			STATUS current
			DESCRIPTION
				" "
			INDEX { ccMuMac }
			::= { ccMuRxPktsTable 1 }

		
		CcMuRxPktsEntry ::=
			SEQUENCE { 
				ccMuRxPktsAt1Mb
					Counter32,
				ccMuRxPktsAt2Mb
					Counter32,
				ccMuRxPktsAt5pt5Mb
					Counter32,
				ccMuRxPktsAt6Mb
					Counter32,
				ccMuRxPktsAt9Mb
					Counter32,
				ccMuRxPktsAt11Mb
					Counter32,
				ccMuRxPktsAt12Mb
					Counter32,
				ccMuRxPktsAt18Mb
					Counter32,
				ccMuRxPktsAt22Mb
					Counter32,
				ccMuRxPktsAt24Mb
					Counter32,
				ccMuRxPktsAt36Mb
					Counter32,
				ccMuRxPktsAt48Mb
					Counter32,
				ccMuRxPktsAt54Mb
					Counter32
			 }

--   1.3.6.1.4.1.388.11.2.4.4.3.1.1
-- 1.3.6.1.4.1.388.6.12.3.3.1.1
		-- 1.3.6.1.4.1.388.6.16.3.3.1.1
		ccMuRxPktsAt1Mb OBJECT-TYPE
			SYNTAX Counter32
			MAX-ACCESS read-only
			STATUS current
			DESCRIPTION
				"The number of packets received from the Mobile Unit at 1 Mbps"
			::= { ccMuRxPktsEntry 1 }

		
--   1.3.6.1.4.1.388.11.2.4.4.3.1.2
-- 1.3.6.1.4.1.388.6.12.3.3.1.2
		-- 1.3.6.1.4.1.388.6.16.3.3.1.2
		ccMuRxPktsAt2Mb OBJECT-TYPE
			SYNTAX Counter32
			MAX-ACCESS read-only
			STATUS current
			DESCRIPTION
				"The number of packets received from the Mobile Unit at 2 Mbps"
			::= { ccMuRxPktsEntry 2 }

		
--   1.3.6.1.4.1.388.11.2.4.4.3.1.3
-- 1.3.6.1.4.1.388.6.12.3.3.1.3
		-- 1.3.6.1.4.1.388.6.16.3.3.1.3
		ccMuRxPktsAt5pt5Mb OBJECT-TYPE
			SYNTAX Counter32
			MAX-ACCESS read-only
			STATUS current
			DESCRIPTION
				"The number of packets received from the Mobile Unit at 5.5 Mbps"
			::= { ccMuRxPktsEntry 3 }

		
--   1.3.6.1.4.1.388.11.2.4.4.3.1.4
-- 1.3.6.1.4.1.388.6.12.3.3.1.4
		-- 1.3.6.1.4.1.388.6.16.3.3.1.4
		ccMuRxPktsAt6Mb OBJECT-TYPE
			SYNTAX Counter32
			MAX-ACCESS read-only
			STATUS current
			DESCRIPTION
				"The number of packets received from the Mobile Unit at 6 Mbps"
			::= { ccMuRxPktsEntry 4 }

		
--   1.3.6.1.4.1.388.11.2.4.4.3.1.5
-- 1.3.6.1.4.1.388.6.12.3.3.1.5
		-- 1.3.6.1.4.1.388.6.16.3.3.1.5
		ccMuRxPktsAt9Mb OBJECT-TYPE
			SYNTAX Counter32
			MAX-ACCESS read-only
			STATUS current
			DESCRIPTION
				"The number of packets received from the Mobile Unit at 9 Mbps"
			::= { ccMuRxPktsEntry 5 }

		
--   1.3.6.1.4.1.388.11.2.4.4.3.1.6
-- 1.3.6.1.4.1.388.6.12.3.3.1.6
		-- 1.3.6.1.4.1.388.6.16.3.3.1.6
		ccMuRxPktsAt11Mb OBJECT-TYPE
			SYNTAX Counter32
			MAX-ACCESS read-only
			STATUS current
			DESCRIPTION
				"The number of packets received from the Mobile Unit at 11 Mbps"
			::= { ccMuRxPktsEntry 6 }

		
--   1.3.6.1.4.1.388.11.2.4.4.3.1.7
-- 1.3.6.1.4.1.388.6.12.3.3.1.7
		-- 1.3.6.1.4.1.388.6.16.3.3.1.7
		ccMuRxPktsAt12Mb OBJECT-TYPE
			SYNTAX Counter32
			MAX-ACCESS read-only
			STATUS current
			DESCRIPTION
				" The number of packets received from the Mobile Unit at 12 Mbps"
			::= { ccMuRxPktsEntry 7 }

		
--   1.3.6.1.4.1.388.11.2.4.4.3.1.8
-- 1.3.6.1.4.1.388.6.12.3.3.1.8
		-- 1.3.6.1.4.1.388.6.16.3.3.1.8
		ccMuRxPktsAt18Mb OBJECT-TYPE
			SYNTAX Counter32
			MAX-ACCESS read-only
			STATUS current
			DESCRIPTION
				" The number of packets received from the Mobile Unit at 18 Mbps"
			::= { ccMuRxPktsEntry 8 }

		
--   1.3.6.1.4.1.388.11.2.4.4.3.1.9
-- 1.3.6.1.4.1.388.6.12.3.3.1.9
		-- 1.3.6.1.4.1.388.6.16.3.3.1.9
		ccMuRxPktsAt22Mb OBJECT-TYPE
			SYNTAX Counter32
			MAX-ACCESS read-only
			STATUS current
			DESCRIPTION
				" The number of packets received from the Mobile Unit at 22 Mbps"
			::= { ccMuRxPktsEntry 9 }

		
--   1.3.6.1.4.1.388.11.2.4.4.3.1.10
-- 1.3.6.1.4.1.388.6.12.3.3.1.10
		-- 1.3.6.1.4.1.388.6.16.3.3.1.10
		ccMuRxPktsAt24Mb OBJECT-TYPE
			SYNTAX Counter32
			MAX-ACCESS read-only
			STATUS current
			DESCRIPTION
				" The number of packets received from the Mobile Unit at 24 Mbps"
			::= { ccMuRxPktsEntry 10 }

		
--   1.3.6.1.4.1.388.11.2.4.4.3.1.11
-- 1.3.6.1.4.1.388.6.12.3.3.1.11
		-- 1.3.6.1.4.1.388.6.16.3.3.1.11
		ccMuRxPktsAt36Mb OBJECT-TYPE
			SYNTAX Counter32
			MAX-ACCESS read-only
			STATUS current
			DESCRIPTION
				" The number of packets received from the Mobile Unit at 36 Mbps"
			::= { ccMuRxPktsEntry 11 }

		
--   1.3.6.1.4.1.388.11.2.4.4.3.1.12
-- 1.3.6.1.4.1.388.6.12.3.3.1.12
		-- 1.3.6.1.4.1.388.6.16.3.3.1.12
		ccMuRxPktsAt48Mb OBJECT-TYPE
			SYNTAX Counter32
			MAX-ACCESS read-only
			STATUS current
			DESCRIPTION
				" The number of packets received from the Mobile Unit at 48 Mbps"
			::= { ccMuRxPktsEntry 12 }

		
--   1.3.6.1.4.1.388.11.2.4.4.3.1.13
-- 1.3.6.1.4.1.388.6.12.3.3.1.13
		-- 1.3.6.1.4.1.388.6.16.3.3.1.13
		ccMuRxPktsAt54Mb OBJECT-TYPE
			SYNTAX Counter32
			MAX-ACCESS read-only
			STATUS current
			DESCRIPTION
				" The number of packets received from the Mobile Unit at 54 Mbps"
			::= { ccMuRxPktsEntry 13 }

		
--   1.3.6.1.4.1.388.11.2.4.4.4
-- 1.3.6.1.4.1.388.6.12.3.4
		-- 1.3.6.1.4.1.388.6.16.3.4
		ccMuTxPktsTable OBJECT-TYPE
			SYNTAX SEQUENCE OF CcMuTxPktsEntry
			MAX-ACCESS not-accessible
			STATUS current
			DESCRIPTION
				" The Number of Packets transmitted to the Moblie Unit at various rates"
			::= { ccMus 4 }

		
--   1.3.6.1.4.1.388.11.2.4.4.4.1
-- 1.3.6.1.4.1.388.6.12.3.4.1
		-- 1.3.6.1.4.1.388.6.16.3.4.1
		ccMuTxPktsEntry OBJECT-TYPE
			SYNTAX CcMuTxPktsEntry
			MAX-ACCESS not-accessible
			STATUS current
			DESCRIPTION
				" "
			INDEX { ccMuMac }
			::= { ccMuTxPktsTable 1 }

		
		CcMuTxPktsEntry ::=
			SEQUENCE { 
				ccMuTxPktsAt1Mb
					Counter32,
				ccMuTxPktsAt2Mb
					Counter32,
				ccMuTxPktsAt5pt5Mb
					Counter32,
				ccMuTxPktsAt6Mb
					Counter32,
				ccMuTxPktsAt9Mb
					Counter32,
				ccMuTxPktsAt11Mb
					Counter32,
				ccMuTxPktsAt12Mb
					Counter32,
				ccMuTxPktsAt18Mb
					Counter32,
				ccMuTxPktsAt22Mb
					Counter32,
				ccMuTxPktsAt24Mb
					Counter32,
				ccMuTxPktsAt36Mb
					Counter32,
				ccMuTxPktsAt48Mb
					Counter32,
				ccMuTxPktsAt54Mb
					Counter32
			 }

--   1.3.6.1.4.1.388.11.2.4.4.4.1.1
-- 1.3.6.1.4.1.388.6.12.3.4.1.1
		-- 1.3.6.1.4.1.388.6.16.3.4.1.1
		ccMuTxPktsAt1Mb OBJECT-TYPE
			SYNTAX Counter32
			MAX-ACCESS read-only
			STATUS current
			DESCRIPTION
				"The number of packets transmitted to the Mobile Unit at 1 Mbps"
			::= { ccMuTxPktsEntry 1 }

		
--   1.3.6.1.4.1.388.11.2.4.4.4.1.2
-- 1.3.6.1.4.1.388.6.12.3.4.1.2
		-- 1.3.6.1.4.1.388.6.16.3.4.1.2
		ccMuTxPktsAt2Mb OBJECT-TYPE
			SYNTAX Counter32
			MAX-ACCESS read-only
			STATUS current
			DESCRIPTION
				" The number of packets transmitted to the Mobile Unit at 2 Mbps"
			::= { ccMuTxPktsEntry 2 }

		
--   1.3.6.1.4.1.388.11.2.4.4.4.1.3
-- 1.3.6.1.4.1.388.6.12.3.4.1.3
		-- 1.3.6.1.4.1.388.6.16.3.4.1.3
		ccMuTxPktsAt5pt5Mb OBJECT-TYPE
			SYNTAX Counter32
			MAX-ACCESS read-only
			STATUS current
			DESCRIPTION
				" The number of packets transmitted to the Mobile Unit at 5.5 Mbps"
			::= { ccMuTxPktsEntry 3 }

		
--   1.3.6.1.4.1.388.11.2.4.4.4.1.4
-- 1.3.6.1.4.1.388.6.12.3.4.1.4
		-- 1.3.6.1.4.1.388.6.16.3.4.1.4
		ccMuTxPktsAt6Mb OBJECT-TYPE
			SYNTAX Counter32
			MAX-ACCESS read-only
			STATUS current
			DESCRIPTION
				" The number of packets transmitted to the Mobile Unit at 6 Mbps"
			::= { ccMuTxPktsEntry 4 }

		
--   1.3.6.1.4.1.388.11.2.4.4.4.1.5
-- 1.3.6.1.4.1.388.6.12.3.4.1.5
		-- 1.3.6.1.4.1.388.6.16.3.4.1.5
		ccMuTxPktsAt9Mb OBJECT-TYPE
			SYNTAX Counter32
			MAX-ACCESS read-only
			STATUS current
			DESCRIPTION
				" The number of packets transmitted to the Mobile Unit at 9 Mbps"
			::= { ccMuTxPktsEntry 5 }

		
--   1.3.6.1.4.1.388.11.2.4.4.4.1.6
-- 1.3.6.1.4.1.388.6.12.3.4.1.8
		-- 1.3.6.1.4.1.388.6.16.3.4.1.6
		ccMuTxPktsAt11Mb OBJECT-TYPE
			SYNTAX Counter32
			MAX-ACCESS read-only
			STATUS current
			DESCRIPTION
				" The number of packets transmitted to the Mobile Unit at 11 Mbps"
			::= { ccMuTxPktsEntry 6 }

		
--   1.3.6.1.4.1.388.11.2.4.4.4.1.7
-- 1.3.6.1.4.1.388.6.12.3.4.1.7
		-- 1.3.6.1.4.1.388.6.16.3.4.1.7
		ccMuTxPktsAt12Mb OBJECT-TYPE
			SYNTAX Counter32
			MAX-ACCESS read-only
			STATUS current
			DESCRIPTION
				" The number of packets transmitted to the Mobile Unit at 12 Mbps"
			::= { ccMuTxPktsEntry 7 }

		
--   1.3.6.1.4.1.388.11.2.4.4.4.1.8
-- 1.3.6.1.4.1.388.6.12.3.4.1.9
		-- 1.3.6.1.4.1.388.6.16.3.4.1.8
		ccMuTxPktsAt18Mb OBJECT-TYPE
			SYNTAX Counter32
			MAX-ACCESS read-only
			STATUS current
			DESCRIPTION
				" The number of packets transmitted to the Mobile Unit at 18 Mbps"
			::= { ccMuTxPktsEntry 8 }

		
--   1.3.6.1.4.1.388.11.2.4.4.4.1.9
-- 1.3.6.1.4.1.388.6.12.3.4.1.12
		-- 1.3.6.1.4.1.388.6.16.3.4.1.9
		ccMuTxPktsAt22Mb OBJECT-TYPE
			SYNTAX Counter32
			MAX-ACCESS read-only
			STATUS current
			DESCRIPTION
				" The number of packets transmitted to the Mobile Unit at 22 Mbps"
			::= { ccMuTxPktsEntry 9 }

		
--   1.3.6.1.4.1.388.11.2.4.4.4.1.10
-- 1.3.6.1.4.1.388.6.12.3.4.1.11
		-- 1.3.6.1.4.1.388.6.16.3.4.1.10
		ccMuTxPktsAt24Mb OBJECT-TYPE
			SYNTAX Counter32
			MAX-ACCESS read-only
			STATUS current
			DESCRIPTION
				" The number of packets transmitted to the Mobile Unit at 24 Mbps"
			::= { ccMuTxPktsEntry 10 }

		
--   1.3.6.1.4.1.388.11.2.4.4.4.1.11
-- 1.3.6.1.4.1.388.6.12.3.4.1.13
		-- 1.3.6.1.4.1.388.6.16.3.4.1.11
		ccMuTxPktsAt36Mb OBJECT-TYPE
			SYNTAX Counter32
			MAX-ACCESS read-only
			STATUS current
			DESCRIPTION
				" The number of packets transmitted to the Mobile Unit at 36 Mbps"
			::= { ccMuTxPktsEntry 11 }

		
--   1.3.6.1.4.1.388.11.2.4.4.4.1.12
-- 1.3.6.1.4.1.388.6.12.3.4.1.14
		-- 1.3.6.1.4.1.388.6.16.3.4.1.12
		ccMuTxPktsAt48Mb OBJECT-TYPE
			SYNTAX Counter32
			MAX-ACCESS read-only
			STATUS current
			DESCRIPTION
				" The number of packets transmitted to the Mobile Unit at 48 Mbps"
			::= { ccMuTxPktsEntry 12 }

		
--   1.3.6.1.4.1.388.11.2.4.4.4.1.13
-- 1.3.6.1.4.1.388.6.12.3.4.1.15
		-- 1.3.6.1.4.1.388.6.16.3.4.1.13
		ccMuTxPktsAt54Mb OBJECT-TYPE
			SYNTAX Counter32
			MAX-ACCESS read-only
			STATUS current
			DESCRIPTION
				" The number of packets transmitted to the Mobile Unit at 54 Mbps"
			::= { ccMuTxPktsEntry 13 }

		
--   1.3.6.1.4.1.388.11.2.4.4.5
-- 1.3.6.1.4.1.388.6.12.3.5
		-- 1.3.6.1.4.1.388.6.16.3.5
		ccMuRxOctetsTable OBJECT-TYPE
			SYNTAX SEQUENCE OF CcMuRxOctetsEntry
			MAX-ACCESS not-accessible
			STATUS current
			DESCRIPTION
				" The number of Bytes received from the mU at various rates"
			::= { ccMus 5 }

		
--   1.3.6.1.4.1.388.11.2.4.4.5.1
-- 1.3.6.1.4.1.388.6.12.3.5.1
		-- 1.3.6.1.4.1.388.6.16.3.5.1
		ccMuRxOctetsEntry OBJECT-TYPE
			SYNTAX CcMuRxOctetsEntry
			MAX-ACCESS not-accessible
			STATUS current
			DESCRIPTION
				" "
			INDEX { ccMuMac }
			::= { ccMuRxOctetsTable 1 }

		
		CcMuRxOctetsEntry ::=
			SEQUENCE { 
				ccMuRxOctetsAt1Mb
					Counter32,
				ccMuRxOctetsAt2Mb
					Counter32,
				ccMuRxOctetsAt5pt5Mb
					Counter32,
				ccMuRxOctetsAt6Mb
					Counter32,
				ccMuRxOctetsAt9Mb
					Counter32,
				ccMuRxOctetsAt11Mb
					Counter32,
				ccMuRxOctetsAt12Mb
					Counter32,
				ccMuRxOctetsAt18Mb
					Counter32,
				ccMuRxOctetsAt22Mb
					Counter32,
				ccMuRxOctetsAt24Mb
					Counter32,
				ccMuRxOctetsAt36Mb
					Counter32,
				ccMuRxOctetsAt48Mb
					Counter32,
				ccMuRxOctetsAt54Mb
					Counter32
			 }

--   1.3.6.1.4.1.388.11.2.4.4.5.1.1
-- 1.3.6.1.4.1.388.6.12.3.5.1.1
		-- 1.3.6.1.4.1.388.6.16.3.5.1.1
		ccMuRxOctetsAt1Mb OBJECT-TYPE
			SYNTAX Counter32
			MAX-ACCESS read-only
			STATUS current
			DESCRIPTION
				"The number of bytes received from the Mobile Unit at 1 Mbps"
			::= { ccMuRxOctetsEntry 1 }

		
--   1.3.6.1.4.1.388.11.2.4.4.5.1.2
-- 1.3.6.1.4.1.388.6.12.3.5.1.2
		-- 1.3.6.1.4.1.388.6.16.3.5.1.2
		ccMuRxOctetsAt2Mb OBJECT-TYPE
			SYNTAX Counter32
			MAX-ACCESS read-only
			STATUS current
			DESCRIPTION
				" The number of bytes received from the Mobile Unit at 2 Mbps"
			::= { ccMuRxOctetsEntry 2 }

		
--   1.3.6.1.4.1.388.11.2.4.4.5.1.3
-- 1.3.6.1.4.1.388.6.12.3.5.1.3
		-- 1.3.6.1.4.1.388.6.16.3.5.1.3
		ccMuRxOctetsAt5pt5Mb OBJECT-TYPE
			SYNTAX Counter32
			MAX-ACCESS read-only
			STATUS current
			DESCRIPTION
				" The number of bytes received from the Mobile Unit at 5.5 Mbps"
			::= { ccMuRxOctetsEntry 3 }

		
--   1.3.6.1.4.1.388.11.2.4.4.5.1.4
-- 1.3.6.1.4.1.388.6.12.3.5.1.4
		-- 1.3.6.1.4.1.388.6.16.3.5.1.4
		ccMuRxOctetsAt6Mb OBJECT-TYPE
			SYNTAX Counter32
			MAX-ACCESS read-only
			STATUS current
			DESCRIPTION
				" The number of bytes received from the Mobile Unit at 6 Mbps"
			::= { ccMuRxOctetsEntry 4 }

		
--   1.3.6.1.4.1.388.11.2.4.4.5.1.5
-- 1.3.6.1.4.1.388.6.12.3.5.1.5
		-- 1.3.6.1.4.1.388.6.16.3.5.1.5
		ccMuRxOctetsAt9Mb OBJECT-TYPE
			SYNTAX Counter32
			MAX-ACCESS read-only
			STATUS current
			DESCRIPTION
				" The number of bytes received from the Mobile Unit at 9 Mbps"
			::= { ccMuRxOctetsEntry 5 }

		
--   1.3.6.1.4.1.388.11.2.4.4.5.1.6
-- 1.3.6.1.4.1.388.6.12.3.5.1.6
		-- 1.3.6.1.4.1.388.6.16.3.5.1.6
		ccMuRxOctetsAt11Mb OBJECT-TYPE
			SYNTAX Counter32
			MAX-ACCESS read-only
			STATUS current
			DESCRIPTION
				" The number of bytes received from the Mobile Unit at 11 Mbps"
			::= { ccMuRxOctetsEntry 6 }

		
--   1.3.6.1.4.1.388.11.2.4.4.5.1.7
-- 1.3.6.1.4.1.388.6.12.3.5.1.7
		-- 1.3.6.1.4.1.388.6.16.3.5.1.7
		ccMuRxOctetsAt12Mb OBJECT-TYPE
			SYNTAX Counter32
			MAX-ACCESS read-only
			STATUS current
			DESCRIPTION
				" The number of bytes received from the Mobile Unit at 12 Mbps"
			::= { ccMuRxOctetsEntry 7 }

		
--   1.3.6.1.4.1.388.11.2.4.4.5.1.8
-- 1.3.6.1.4.1.388.6.12.3.5.1.8
		-- 1.3.6.1.4.1.388.6.16.3.5.1.8
		ccMuRxOctetsAt18Mb OBJECT-TYPE
			SYNTAX Counter32
			MAX-ACCESS read-only
			STATUS current
			DESCRIPTION
				" The number of bytes received from the Mobile Unit at 18 Mbps"
			::= { ccMuRxOctetsEntry 8 }

		
--   1.3.6.1.4.1.388.11.2.4.4.5.1.9
-- 1.3.6.1.4.1.388.6.12.3.5.1.9
		-- 1.3.6.1.4.1.388.6.16.3.5.1.9
		ccMuRxOctetsAt22Mb OBJECT-TYPE
			SYNTAX Counter32
			MAX-ACCESS read-only
			STATUS current
			DESCRIPTION
				" The number of bytes received from the Mobile Unit at 22 Mbps"
			::= { ccMuRxOctetsEntry 9 }

		
--   1.3.6.1.4.1.388.11.2.4.4.5.1.10
-- 1.3.6.1.4.1.388.6.12.3.5.1.10
		-- 1.3.6.1.4.1.388.6.16.3.5.1.10
		ccMuRxOctetsAt24Mb OBJECT-TYPE
			SYNTAX Counter32
			MAX-ACCESS read-only
			STATUS current
			DESCRIPTION
				" The number of bytes received from the Mobile Unit at 24 Mbps"
			::= { ccMuRxOctetsEntry 10 }

		
--   1.3.6.1.4.1.388.11.2.4.4.5.1.11
-- 1.3.6.1.4.1.388.6.12.3.5.1.11
		-- 1.3.6.1.4.1.388.6.16.3.5.1.11
		ccMuRxOctetsAt36Mb OBJECT-TYPE
			SYNTAX Counter32
			MAX-ACCESS read-only
			STATUS current
			DESCRIPTION
				" The number of bytes received from the Mobile Unit at 36 Mbps"
			::= { ccMuRxOctetsEntry 11 }

		
--   1.3.6.1.4.1.388.11.2.4.4.5.1.12
-- 1.3.6.1.4.1.388.6.12.3.5.1.12
		-- 1.3.6.1.4.1.388.6.16.3.5.1.12
		ccMuRxOctetsAt48Mb OBJECT-TYPE
			SYNTAX Counter32
			MAX-ACCESS read-only
			STATUS current
			DESCRIPTION
				" The number of bytes received from the Mobile Unit at  48 Mbps"
			::= { ccMuRxOctetsEntry 12 }

		
--   1.3.6.1.4.1.388.11.2.4.4.5.1.13
-- 1.3.6.1.4.1.388.6.12.3.5.1.13
		-- 1.3.6.1.4.1.388.6.16.3.5.1.13
		ccMuRxOctetsAt54Mb OBJECT-TYPE
			SYNTAX Counter32
			MAX-ACCESS read-only
			STATUS current
			DESCRIPTION
				" The number of bytes received from the Mobile Unit at 54 Mbps"
			::= { ccMuRxOctetsEntry 13 }

		
--   1.3.6.1.4.1.388.11.2.4.4.6
-- 1.3.6.1.4.1.388.6.12.3.6
		-- 1.3.6.1.4.1.388.6.16.3.6
		ccMuTxOctetsTable OBJECT-TYPE
			SYNTAX SEQUENCE OF CcMuTxOctetsEntry
			MAX-ACCESS not-accessible
			STATUS current
			DESCRIPTION
				" The number of bytes transmitted to the MU at various rate"
			::= { ccMus 6 }

		
--   1.3.6.1.4.1.388.11.2.4.4.6.1
-- 1.3.6.1.4.1.388.6.12.3.6.1
		-- 1.3.6.1.4.1.388.6.16.3.6.1
		ccMuTxOctetsEntry OBJECT-TYPE
			SYNTAX CcMuTxOctetsEntry
			MAX-ACCESS not-accessible
			STATUS current
			DESCRIPTION
				" "
			INDEX { ccMuMac }
			::= { ccMuTxOctetsTable 1 }

		
		CcMuTxOctetsEntry ::=
			SEQUENCE { 
				ccMuTxOctetsAt1Mb
					Counter32,
				ccMuTxOctetsAt2Mb
					Counter32,
				ccMuTxOctetsAt5pt5Mb
					Counter32,
				ccMuTxOctetsAt6Mb
					Counter32,
				ccMuTxOctetsAt9Mb
					Counter32,
				ccMuTxOctetsAt11Mb
					Counter32,
				ccMuTxOctetsAt12Mb
					Counter32,
				ccMuTxOctetsAt18Mb
					Counter32,
				ccMuTxOctetsAt22Mb
					Counter32,
				ccMuTxOctetsAt24Mb
					Counter32,
				ccMuTxOctetsAt36Mb
					Counter32,
				ccMuTxOctetsAt48Mb
					Counter32,
				ccMuTxOctetsAt54Mb
					Counter32
			 }

--   1.3.6.1.4.1.388.11.2.4.4.6.1.1
-- 1.3.6.1.4.1.388.6.12.3.6.1.1
		-- 1.3.6.1.4.1.388.6.16.3.6.1.1
		ccMuTxOctetsAt1Mb OBJECT-TYPE
			SYNTAX Counter32
			MAX-ACCESS read-only
			STATUS current
			DESCRIPTION
				"The number of bytes transmitted to the Mobile Unit at 1 Mbps (does not include
				
				re-tries)
				"
			::= { ccMuTxOctetsEntry 1 }

		
--   1.3.6.1.4.1.388.11.2.4.4.6.1.2
-- 1.3.6.1.4.1.388.6.12.3.6.1.2
		-- 1.3.6.1.4.1.388.6.16.3.6.1.2
		ccMuTxOctetsAt2Mb OBJECT-TYPE
			SYNTAX Counter32
			MAX-ACCESS read-only
			STATUS current
			DESCRIPTION
				" The number of bytes transmitted to the Mobile Unit at 2 Mbps (does not include
				
				re-tries)
				"
			::= { ccMuTxOctetsEntry 2 }

		
--   1.3.6.1.4.1.388.11.2.4.4.6.1.3
-- 1.3.6.1.4.1.388.6.12.3.6.1.3
		-- 1.3.6.1.4.1.388.6.16.3.6.1.3
		ccMuTxOctetsAt5pt5Mb OBJECT-TYPE
			SYNTAX Counter32
			MAX-ACCESS read-only
			STATUS current
			DESCRIPTION
				" The number of bytes transmitted to the Mobile Unit at  5.5 Mbps (does not include
				
				re-tries)
				"
			::= { ccMuTxOctetsEntry 3 }

		
--   1.3.6.1.4.1.388.11.2.4.4.6.1.4
-- 1.3.6.1.4.1.388.6.12.3.6.1.4
		-- 1.3.6.1.4.1.388.6.16.3.6.1.4
		ccMuTxOctetsAt6Mb OBJECT-TYPE
			SYNTAX Counter32
			MAX-ACCESS read-only
			STATUS current
			DESCRIPTION
				" The number of bytes transmitted to the Mobile Unit at 6 Mbps (does not include
				
				re-tries)
				"
			::= { ccMuTxOctetsEntry 4 }

		
--   1.3.6.1.4.1.388.11.2.4.4.6.1.5
-- 1.3.6.1.4.1.388.6.12.3.6.1.5
		-- 1.3.6.1.4.1.388.6.16.3.6.1.5
		ccMuTxOctetsAt9Mb OBJECT-TYPE
			SYNTAX Counter32
			MAX-ACCESS read-only
			STATUS current
			DESCRIPTION
				" The number of bytes transmitted to the Mobile Unit at 9 Mbps (does not include
				
				re-tries)
				"
			::= { ccMuTxOctetsEntry 5 }

		
--   1.3.6.1.4.1.388.11.2.4.4.6.1.6
-- 1.3.6.1.4.1.388.6.12.3.6.1.6
		-- 1.3.6.1.4.1.388.6.16.3.6.1.6
		ccMuTxOctetsAt11Mb OBJECT-TYPE
			SYNTAX Counter32
			MAX-ACCESS read-only
			STATUS current
			DESCRIPTION
				" The number of bytes transmitted to the Mobile Unit at 11 Mbps (does not include
				
				re-tries)
				"
			::= { ccMuTxOctetsEntry 6 }

		
--   1.3.6.1.4.1.388.11.2.4.4.6.1.7
-- 1.3.6.1.4.1.388.6.12.3.6.1.7
		-- 1.3.6.1.4.1.388.6.16.3.6.1.7
		ccMuTxOctetsAt12Mb OBJECT-TYPE
			SYNTAX Counter32
			MAX-ACCESS read-only
			STATUS current
			DESCRIPTION
				" The number of bytes transmitted to the Mobile Unit at 12 Mbps (does not include
				
				re-tries)
				"
			::= { ccMuTxOctetsEntry 7 }

		
--   1.3.6.1.4.1.388.11.2.4.4.6.1.8
-- 1.3.6.1.4.1.388.6.12.3.6.1.8
		-- 1.3.6.1.4.1.388.6.16.3.6.1.8
		ccMuTxOctetsAt18Mb OBJECT-TYPE
			SYNTAX Counter32
			MAX-ACCESS read-only
			STATUS current
			DESCRIPTION
				" The number of bytes transmitted to the Mobile Unit at 18 Mbps (does not include
				
				re-tries)
				"
			::= { ccMuTxOctetsEntry 8 }

		
--   1.3.6.1.4.1.388.11.2.4.4.6.1.9
-- 1.3.6.1.4.1.388.6.12.3.6.1.9
		-- 1.3.6.1.4.1.388.6.16.3.6.1.9
		ccMuTxOctetsAt22Mb OBJECT-TYPE
			SYNTAX Counter32
			MAX-ACCESS read-only
			STATUS current
			DESCRIPTION
				" The number of bytes transmitted to the Mobile Unit at 22 Mbps (does not include
				
				re-tries)
				"
			::= { ccMuTxOctetsEntry 9 }

		
--   1.3.6.1.4.1.388.11.2.4.4.6.1.10
-- 1.3.6.1.4.1.388.6.12.3.6.1.10
		-- 1.3.6.1.4.1.388.6.16.3.6.1.10
		ccMuTxOctetsAt24Mb OBJECT-TYPE
			SYNTAX Counter32
			MAX-ACCESS read-only
			STATUS current
			DESCRIPTION
				" The number of bytes transmitted to the Mobile Unit at 24 Mbps (does not include
				
				re-tries)
				"
			::= { ccMuTxOctetsEntry 10 }

		
--   1.3.6.1.4.1.388.11.2.4.4.6.1.11
-- 1.3.6.1.4.1.388.6.12.3.6.1.11
		-- 1.3.6.1.4.1.388.6.16.3.6.1.11
		ccMuTxOctetsAt36Mb OBJECT-TYPE
			SYNTAX Counter32
			MAX-ACCESS read-only
			STATUS current
			DESCRIPTION
				" The number of bytes transmitted to the Mobile Unit at 36 Mbps (does not include
				
				re-tries)
				"
			::= { ccMuTxOctetsEntry 11 }

		
--   1.3.6.1.4.1.388.11.2.4.4.6.1.12
-- 1.3.6.1.4.1.388.6.12.3.6.1.12
		-- 1.3.6.1.4.1.388.6.16.3.6.1.12
		ccMuTxOctetsAt48Mb OBJECT-TYPE
			SYNTAX Counter32
			MAX-ACCESS read-only
			STATUS current
			DESCRIPTION
				" The number of bytes transmitted to the Mobile Unit at 48 Mbps (does not include
				
				re-tries)
				"
			::= { ccMuTxOctetsEntry 12 }

		
--   1.3.6.1.4.1.388.11.2.4.4.6.1.13
-- 1.3.6.1.4.1.388.6.12.3.6.1.13
		-- 1.3.6.1.4.1.388.6.16.3.6.1.13
		ccMuTxOctetsAt54Mb OBJECT-TYPE
			SYNTAX Counter32
			MAX-ACCESS read-only
			STATUS current
			DESCRIPTION
				" The number of bytes transmitted to the Mobile Unit at 54 Mbps (does not include
				
				re-tries)
				"
			::= { ccMuTxOctetsEntry 13 }

		
--   1.3.6.1.4.1.388.11.2.4.4.7
-- 1.3.6.1.4.1.388.6.12.3.7
		-- 1.3.6.1.4.1.388.6.16.3.7
		ccMuTxRetriesTable OBJECT-TYPE
			SYNTAX SEQUENCE OF CcMuTxRetriesEntry
			MAX-ACCESS not-accessible
			STATUS current
			DESCRIPTION
				" The number of packets transmitted to the MU at various retries"
			::= { ccMus 7 }

		
--   1.3.6.1.4.1.388.11.2.4.4.7.1
-- 1.3.6.1.4.1.388.6.12.3.7.1
		-- 1.3.6.1.4.1.388.6.16.3.7.1
		ccMuTxRetriesEntry OBJECT-TYPE
			SYNTAX CcMuTxRetriesEntry
			MAX-ACCESS not-accessible
			STATUS current
			DESCRIPTION
				" "
			INDEX { ccMuMac }
			::= { ccMuTxRetriesTable 1 }

		
		CcMuTxRetriesEntry ::=
			SEQUENCE { 
				ccMuTxRetriesNone
					Counter32,
				ccMuTxRetries01
					Counter32,
				ccMuTxRetries02
					Counter32,
				ccMuTxRetries03
					Counter32,
				ccMuTxRetries04
					Counter32,
				ccMuTxRetries05
					Counter32,
				ccMuTxRetries06
					Counter32,
				ccMuTxRetries07
					Counter32,
				ccMuTxRetries08
					Counter32,
				ccMuTxRetries09
					Counter32,
				ccMuTxRetries10
					Counter32,
				ccMuTxRetries11
					Counter32,
				ccMuTxRetries12
					Counter32,
				ccMuTxRetries13
					Counter32,
				ccMuTxRetries14
					Counter32,
				ccMuTxRetries15
					Counter32,
				ccMuTxRetriesFailed
					Counter32,
				ccMuTxRetriesTotal
					Counter32,
				ccMuTxRetriesMostRecent
					INTEGER
			 }

--   1.3.6.1.4.1.388.11.2.4.4.7.1.1
-- 1.3.6.1.4.1.388.6.12.3.7.1.1
		-- 1.3.6.1.4.1.388.6.16.3.7.1.1
		ccMuTxRetriesNone OBJECT-TYPE
			SYNTAX Counter32
			MAX-ACCESS read-only
			STATUS current
			DESCRIPTION
				" The number of bytes transmitted to the Mobile Unit with no retry"
			::= { ccMuTxRetriesEntry 1 }

		
--   1.3.6.1.4.1.388.11.2.4.4.7.1.2
-- 1.3.6.1.4.1.388.6.12.3.7.1.2
		-- 1.3.6.1.4.1.388.6.16.3.7.1.2
		ccMuTxRetries01 OBJECT-TYPE
			SYNTAX Counter32
			MAX-ACCESS read-only
			STATUS current
			DESCRIPTION
				"The number of bytes transmitted to the Mobile Unit with 1 retry"
			::= { ccMuTxRetriesEntry 2 }

		
--   1.3.6.1.4.1.388.11.2.4.4.7.1.3
-- 1.3.6.1.4.1.388.6.12.3.7.1.3
		-- 1.3.6.1.4.1.388.6.16.3.7.1.3
		ccMuTxRetries02 OBJECT-TYPE
			SYNTAX Counter32
			MAX-ACCESS read-only
			STATUS current
			DESCRIPTION
				" The number of bytes transmitted to the Mobile Unit with 2 retries"
			::= { ccMuTxRetriesEntry 3 }

		
--   1.3.6.1.4.1.388.11.2.4.4.7.1.4
-- 1.3.6.1.4.1.388.6.12.3.7.1.4
		-- 1.3.6.1.4.1.388.6.16.3.7.1.4
		ccMuTxRetries03 OBJECT-TYPE
			SYNTAX Counter32
			MAX-ACCESS read-only
			STATUS current
			DESCRIPTION
				"  The number of bytes transmitted to the Mobile Unit with 3 retries"
			::= { ccMuTxRetriesEntry 4 }

		
--   1.3.6.1.4.1.388.11.2.4.4.7.1.5
-- 1.3.6.1.4.1.388.6.12.3.7.1.5
		-- 1.3.6.1.4.1.388.6.16.3.7.1.5
		ccMuTxRetries04 OBJECT-TYPE
			SYNTAX Counter32
			MAX-ACCESS read-only
			STATUS current
			DESCRIPTION
				"  The number of bytes transmitted to the Mobile Unit with 4 retries"
			::= { ccMuTxRetriesEntry 5 }

		
--   1.3.6.1.4.1.388.11.2.4.4.7.1.6
-- 1.3.6.1.4.1.388.6.12.3.7.1.6
		-- 1.3.6.1.4.1.388.6.16.3.7.1.6
		ccMuTxRetries05 OBJECT-TYPE
			SYNTAX Counter32
			MAX-ACCESS read-only
			STATUS current
			DESCRIPTION
				"  The number of bytes transmitted to the Mobile Unit with 5 retries"
			::= { ccMuTxRetriesEntry 6 }

		
--   1.3.6.1.4.1.388.11.2.4.4.7.1.7
-- 1.3.6.1.4.1.388.6.12.3.7.1.7
		-- 1.3.6.1.4.1.388.6.16.3.7.1.7
		ccMuTxRetries06 OBJECT-TYPE
			SYNTAX Counter32
			MAX-ACCESS read-only
			STATUS current
			DESCRIPTION
				"  The number of bytes transmitted to the Mobile Unit with 6 retries"
			::= { ccMuTxRetriesEntry 7 }

		
--   1.3.6.1.4.1.388.11.2.4.4.7.1.8
-- 1.3.6.1.4.1.388.6.12.3.7.1.8
		-- 1.3.6.1.4.1.388.6.16.3.7.1.8
		ccMuTxRetries07 OBJECT-TYPE
			SYNTAX Counter32
			MAX-ACCESS read-only
			STATUS current
			DESCRIPTION
				"  The number of bytes transmitted to the Mobile Unit with 7 retries"
			::= { ccMuTxRetriesEntry 8 }

		
--   1.3.6.1.4.1.388.11.2.4.4.7.1.9
-- 1.3.6.1.4.1.388.6.12.3.7.1.9
		-- 1.3.6.1.4.1.388.6.16.3.7.1.9
		ccMuTxRetries08 OBJECT-TYPE
			SYNTAX Counter32
			MAX-ACCESS read-only
			STATUS current
			DESCRIPTION
				"  The number of bytes transmitted to the Mobile Unit with 8 retries"
			::= { ccMuTxRetriesEntry 9 }

		
--   1.3.6.1.4.1.388.11.2.4.4.7.1.10
-- 1.3.6.1.4.1.388.6.12.3.7.1.10
		-- 1.3.6.1.4.1.388.6.16.3.7.1.10
		ccMuTxRetries09 OBJECT-TYPE
			SYNTAX Counter32
			MAX-ACCESS read-only
			STATUS current
			DESCRIPTION
				"  The number of bytes transmitted to the Mobile Unit with 9 retries"
			::= { ccMuTxRetriesEntry 10 }

		
--   1.3.6.1.4.1.388.11.2.4.4.7.1.11
-- 1.3.6.1.4.1.388.6.12.3.7.1.11
		-- 1.3.6.1.4.1.388.6.16.3.7.1.11
		ccMuTxRetries10 OBJECT-TYPE
			SYNTAX Counter32
			MAX-ACCESS read-only
			STATUS current
			DESCRIPTION
				"  The number of bytes transmitted to the Mobile Unit with 10 retries"
			::= { ccMuTxRetriesEntry 11 }

		
--   1.3.6.1.4.1.388.11.2.4.4.7.1.12
-- 1.3.6.1.4.1.388.6.12.3.7.1.12
		-- 1.3.6.1.4.1.388.6.16.3.7.1.12
		ccMuTxRetries11 OBJECT-TYPE
			SYNTAX Counter32
			MAX-ACCESS read-only
			STATUS current
			DESCRIPTION
				"  The number of bytes transmitted to the Mobile Unit with 11 retries"
			::= { ccMuTxRetriesEntry 12 }

		
--   1.3.6.1.4.1.388.11.2.4.4.7.1.13
-- 1.3.6.1.4.1.388.6.12.3.7.1.13
		-- 1.3.6.1.4.1.388.6.16.3.7.1.13
		ccMuTxRetries12 OBJECT-TYPE
			SYNTAX Counter32
			MAX-ACCESS read-only
			STATUS current
			DESCRIPTION
				"  The number of bytes transmitted to the Mobile Unit with 12 retries"
			::= { ccMuTxRetriesEntry 13 }

		
--   1.3.6.1.4.1.388.11.2.4.4.7.1.14
-- 1.3.6.1.4.1.388.6.12.3.7.1.14
		-- 1.3.6.1.4.1.388.6.16.3.7.1.14
		ccMuTxRetries13 OBJECT-TYPE
			SYNTAX Counter32
			MAX-ACCESS read-only
			STATUS current
			DESCRIPTION
				"  The number of bytes transmitted to the Mobile Unit with 13 retries"
			::= { ccMuTxRetriesEntry 14 }

		
--   1.3.6.1.4.1.388.11.2.4.4.7.1.15
-- 1.3.6.1.4.1.388.6.12.3.7.1.15
		-- 1.3.6.1.4.1.388.6.16.3.7.1.15
		ccMuTxRetries14 OBJECT-TYPE
			SYNTAX Counter32
			MAX-ACCESS read-only
			STATUS current
			DESCRIPTION
				"  The number of bytes transmitted to the Mobile Unit with 14 retries"
			::= { ccMuTxRetriesEntry 15 }

		
--   1.3.6.1.4.1.388.11.2.4.4.7.1.16
-- 1.3.6.1.4.1.388.6.12.3.7.1.16
		-- 1.3.6.1.4.1.388.6.16.3.7.1.16
		ccMuTxRetries15 OBJECT-TYPE
			SYNTAX Counter32
			MAX-ACCESS read-only
			STATUS deprecated
			DESCRIPTION
				"  The number of bytes transmitted to the Mobile Unit with 15 retries"
			::= { ccMuTxRetriesEntry 16 }

		
--   1.3.6.1.4.1.388.11.2.4.4.7.1.17
-- 1.3.6.1.4.1.388.6.12.3.7.1.17
		-- 1.3.6.1.4.1.388.6.16.3.7.1.17
		ccMuTxRetriesFailed OBJECT-TYPE
			SYNTAX Counter32
			MAX-ACCESS read-only
			STATUS current
			DESCRIPTION
				"    The number of bytes that were not sent due to excess retries"
			::= { ccMuTxRetriesEntry 17 }

		
--   1.3.6.1.4.1.388.11.2.4.4.7.1.18
-- 1.3.6.1.4.1.388.6.12.3.7.1.18
		-- 1.3.6.1.4.1.388.6.16.3.7.1.18
		ccMuTxRetriesTotal OBJECT-TYPE
			SYNTAX Counter32
			MAX-ACCESS read-only
			STATUS current
			DESCRIPTION
				"A total sum of all retries across all packets sent
				to this MU.
				
				For example, if 4 packets have been sent, with the
				following number of retires: 2, 0, 5, gave-up,
				this value would be 2+0+5+16 = 23."
			::= { ccMuTxRetriesEntry 18 }

		
--   1.3.6.1.4.1.388.11.2.4.4.7.1.19
-- 1.3.6.1.4.1.388.6.12.3.7.1.19
		-- 1.3.6.1.4.1.388.6.16.3.7.1.19
		ccMuTxRetriesMostRecent OBJECT-TYPE
			SYNTAX INTEGER (0..16)
			MAX-ACCESS read-only
			STATUS current
			DESCRIPTION
				" The number of retries of the most recent transmission"
			::= { ccMuTxRetriesEntry 19 }

		
--   1.3.6.1.4.1.388.11.2.4.4.8
-- 1.3.6.1.4.1.388.6.12.3.8
		-- 1.3.6.1.4.1.388.6.16.3.8
		ccMuLastMac OBJECT-TYPE
			SYNTAX DisplayString
			MAX-ACCESS read-only
			STATUS current
			DESCRIPTION
				"This scalar records the MAC address of the most 
				recent MU to be Adopted, UnAdopted, or Denied."
			::= { ccMus 8 }

		
--   1.3.6.1.4.1.388.11.2.4.4.9
-- 1.3.6.1.4.1.388.6.12.3.9
		-- 1.3.6.1.4.1.388.6.16.3.9
		ccMuLastReason OBJECT-TYPE
			SYNTAX INTEGER
				{
				success(1),
				aclViolation(2),
				timeout(3),
				associationFailed(4),
				authenticationFailedOn802dot1x(5),
				kerberosWrongUsername(6)
				}
			MAX-ACCESS read-only
			STATUS current
			DESCRIPTION
				"This value notes the reason for the most-recent 
				MU UnAdoption or Denial.
				
				Enum item associationFailed indicates that a key
				association field was missing, or a mismatch of
				supported rates, etc."
			::= { ccMus 9 }

		
--   1.3.6.1.4.1.388.11.2.4.4.10
-- 1.3.6.1.4.1.388.6.12.3.10
		-- 1.3.6.1.4.1.388.6.16.3.10
		ccMuLastPortal OBJECT-TYPE
			SYNTAX DisplayString
			MAX-ACCESS read-only
			STATUS current
			DESCRIPTION
				"This value notes the reason for the most-recent 
				MU UnAdoption or Denial."
			::= { ccMus 10 }

		
--   !!- OID: .100
-- 
-- (This group would have contained all the stats tables,
-- except that they were located above, before I created
-- matching groups and tables in ccPortal and ccWlan).
-- 1.3.6.1.4.1.388.11.2.4.4.100
-- 1.3.6.1.4.1.388.6.12.3.100
		-- 1.3.6.1.4.1.388.6.16.3.100
		ccMuRfSum OBJECT IDENTIFIER ::= { ccMus 100 }

		
--   1.3.6.1.4.1.388.11.2.4.4.100.1
-- 1.3.6.1.4.1.388.6.12.3.100.1
		-- 1.3.6.1.4.1.388.6.16.3.100.1
		ccMuTxRetriesOctetsTable OBJECT-TYPE
			SYNTAX SEQUENCE OF CcMuTxRetriesOctetsEntry
			MAX-ACCESS not-accessible
			STATUS current
			DESCRIPTION
				" The number of packets transmitted from the MU at various retries"
			::= { ccMuRfSum 1 }

		
--   1.3.6.1.4.1.388.11.2.4.4.100.1.1
-- 1.3.6.1.4.1.388.6.12.3.100.1.1
		-- 1.3.6.1.4.1.388.6.16.3.100.1.1
		ccMuTxRetriesOctetsEntry OBJECT-TYPE
			SYNTAX CcMuTxRetriesOctetsEntry
			MAX-ACCESS not-accessible
			STATUS current
			DESCRIPTION
				" "
			INDEX { ccMuMac }
			::= { ccMuTxRetriesOctetsTable 1 }

		
		CcMuTxRetriesOctetsEntry ::=
			SEQUENCE { 
				ccMuTxRetriesOctetsNone
					Counter32,
				ccMuTxRetriesOctets01
					Counter32,
				ccMuTxRetriesOctets02
					Counter32,
				ccMuTxRetriesOctets03
					Counter32,
				ccMuTxRetriesOctets04
					Counter32,
				ccMuTxRetriesOctets05
					Counter32,
				ccMuTxRetriesOctets06
					Counter32,
				ccMuTxRetriesOctets07
					Counter32,
				ccMuTxRetriesOctets08
					Counter32,
				ccMuTxRetriesOctets09
					Counter32,
				ccMuTxRetriesOctets10
					Counter32,
				ccMuTxRetriesOctets11
					Counter32,
				ccMuTxRetriesOctets12
					Counter32,
				ccMuTxRetriesOctets13
					Counter32,
				ccMuTxRetriesOctets14
					Counter32,
				ccMuTxRetriesOctets15
					Counter32,
				ccMuTxRetriesOctetsFailed
					Counter32
			 }

--   1.3.6.1.4.1.388.11.2.4.4.100.1.1.1
-- 1.3.6.1.4.1.388.6.12.3.100.1.1.1
		-- 1.3.6.1.4.1.388.6.16.3.100.1.1.1
		ccMuTxRetriesOctetsNone OBJECT-TYPE
			SYNTAX Counter32
			MAX-ACCESS read-only
			STATUS current
			DESCRIPTION
				" The number of packets  transmitted to the Mobile Unit with no retry"
			::= { ccMuTxRetriesOctetsEntry 1 }

		
--   1.3.6.1.4.1.388.11.2.4.4.100.1.1.2
-- 1.3.6.1.4.1.388.6.12.3.100.1.1.2
		-- 1.3.6.1.4.1.388.6.16.3.100.1.1.2
		ccMuTxRetriesOctets01 OBJECT-TYPE
			SYNTAX Counter32
			MAX-ACCESS read-only
			STATUS current
			DESCRIPTION
				"  The number of packets  transmitted to the Mobile Unit with 1 retry"
			::= { ccMuTxRetriesOctetsEntry 2 }

		
--   1.3.6.1.4.1.388.11.2.4.4.100.1.1.3
-- 1.3.6.1.4.1.388.6.12.3.100.1.1.3
		-- 1.3.6.1.4.1.388.6.16.3.100.1.1.3
		ccMuTxRetriesOctets02 OBJECT-TYPE
			SYNTAX Counter32
			MAX-ACCESS read-only
			STATUS current
			DESCRIPTION
				" The number of packets  transmitted to the Mobile Unit with 2 retries"
			::= { ccMuTxRetriesOctetsEntry 3 }

		
--   1.3.6.1.4.1.388.11.2.4.4.100.1.1.4
-- 1.3.6.1.4.1.388.6.12.3.100.1.1.4
		-- 1.3.6.1.4.1.388.6.16.3.100.1.1.4
		ccMuTxRetriesOctets03 OBJECT-TYPE
			SYNTAX Counter32
			MAX-ACCESS read-only
			STATUS current
			DESCRIPTION
				" The number of packets  transmitted to the Mobile Unit with 3 retries"
			::= { ccMuTxRetriesOctetsEntry 4 }

		
--   1.3.6.1.4.1.388.11.2.4.4.100.1.1.5
-- 1.3.6.1.4.1.388.6.12.3.100.1.1.5
		-- 1.3.6.1.4.1.388.6.16.3.100.1.1.5
		ccMuTxRetriesOctets04 OBJECT-TYPE
			SYNTAX Counter32
			MAX-ACCESS read-only
			STATUS current
			DESCRIPTION
				" The number of packets transmitted to the Mobile Unit with 4 retries"
			::= { ccMuTxRetriesOctetsEntry 5 }

		
--   1.3.6.1.4.1.388.11.2.4.4.100.1.1.6
-- 1.3.6.1.4.1.388.6.12.3.100.1.1.6
		-- 1.3.6.1.4.1.388.6.16.3.100.1.1.6
		ccMuTxRetriesOctets05 OBJECT-TYPE
			SYNTAX Counter32
			MAX-ACCESS read-only
			STATUS current
			DESCRIPTION
				" The number of packets  transmitted to the Mobile Unit with 5 retries"
			::= { ccMuTxRetriesOctetsEntry 6 }

		
--   1.3.6.1.4.1.388.11.2.4.4.100.1.1.7
-- 1.3.6.1.4.1.388.6.12.3.100.1.1.7
		-- 1.3.6.1.4.1.388.6.16.3.100.1.1.7
		ccMuTxRetriesOctets06 OBJECT-TYPE
			SYNTAX Counter32
			MAX-ACCESS read-only
			STATUS current
			DESCRIPTION
				"  The number of packets  transmitted to the Mobile Unit with 6 retries"
			::= { ccMuTxRetriesOctetsEntry 7 }

		
--   1.3.6.1.4.1.388.11.2.4.4.100.1.1.8
-- 1.3.6.1.4.1.388.6.12.3.100.1.1.8
		-- 1.3.6.1.4.1.388.6.16.3.100.1.1.8
		ccMuTxRetriesOctets07 OBJECT-TYPE
			SYNTAX Counter32
			MAX-ACCESS read-only
			STATUS current
			DESCRIPTION
				"  The number of packets  transmitted to the Mobile Unit with 7 retries"
			::= { ccMuTxRetriesOctetsEntry 8 }

		
--   1.3.6.1.4.1.388.11.2.4.4.100.1.1.9
-- 1.3.6.1.4.1.388.6.12.3.100.1.1.9
		-- 1.3.6.1.4.1.388.6.16.3.100.1.1.9
		ccMuTxRetriesOctets08 OBJECT-TYPE
			SYNTAX Counter32
			MAX-ACCESS read-only
			STATUS current
			DESCRIPTION
				"  The number of packets  transmitted to the Mobile Unit with 8 retries"
			::= { ccMuTxRetriesOctetsEntry 9 }

		
--   1.3.6.1.4.1.388.11.2.4.4.100.1.1.10
-- 1.3.6.1.4.1.388.6.12.3.100.1.1.10
		-- 1.3.6.1.4.1.388.6.16.3.100.1.1.10
		ccMuTxRetriesOctets09 OBJECT-TYPE
			SYNTAX Counter32
			MAX-ACCESS read-only
			STATUS current
			DESCRIPTION
				"  The number of packets  transmitted to the Mobile Unit with 9 retries"
			::= { ccMuTxRetriesOctetsEntry 10 }

		
--   1.3.6.1.4.1.388.11.2.4.4.100.1.1.11
-- 1.3.6.1.4.1.388.6.12.3.100.1.1.11
		-- 1.3.6.1.4.1.388.6.16.3.100.1.1.11
		ccMuTxRetriesOctets10 OBJECT-TYPE
			SYNTAX Counter32
			MAX-ACCESS read-only
			STATUS current
			DESCRIPTION
				"  The number of packets  transmitted to the Mobile Unit with 10 retries"
			::= { ccMuTxRetriesOctetsEntry 11 }

		
--   1.3.6.1.4.1.388.11.2.4.4.100.1.1.12
-- 1.3.6.1.4.1.388.6.12.3.100.1.1.12
		-- 1.3.6.1.4.1.388.6.16.3.100.1.1.12
		ccMuTxRetriesOctets11 OBJECT-TYPE
			SYNTAX Counter32
			MAX-ACCESS read-only
			STATUS current
			DESCRIPTION
				"  The number of packets  transmitted to the Mobile Unit with 11 retries"
			::= { ccMuTxRetriesOctetsEntry 12 }

		
--   1.3.6.1.4.1.388.11.2.4.4.100.1.1.13
-- 1.3.6.1.4.1.388.6.12.3.100.1.1.13
		-- 1.3.6.1.4.1.388.6.16.3.100.1.1.13
		ccMuTxRetriesOctets12 OBJECT-TYPE
			SYNTAX Counter32
			MAX-ACCESS read-only
			STATUS current
			DESCRIPTION
				"  The number of packets  transmitted to the Mobile Unit with 12 retries"
			::= { ccMuTxRetriesOctetsEntry 13 }

		
--   1.3.6.1.4.1.388.11.2.4.4.100.1.1.14
-- 1.3.6.1.4.1.388.6.12.3.100.1.1.14
		-- 1.3.6.1.4.1.388.6.16.3.100.1.1.14
		ccMuTxRetriesOctets13 OBJECT-TYPE
			SYNTAX Counter32
			MAX-ACCESS read-only
			STATUS current
			DESCRIPTION
				"  The number of packets  transmitted to the Mobile Unit with 13 retries"
			::= { ccMuTxRetriesOctetsEntry 14 }

		
--   1.3.6.1.4.1.388.11.2.4.4.100.1.1.15
-- 1.3.6.1.4.1.388.6.12.3.100.1.1.15
		-- 1.3.6.1.4.1.388.6.16.3.100.1.1.15
		ccMuTxRetriesOctets14 OBJECT-TYPE
			SYNTAX Counter32
			MAX-ACCESS read-only
			STATUS current
			DESCRIPTION
				"  The number of packets  transmitted to the Mobile Unit with 14 retries"
			::= { ccMuTxRetriesOctetsEntry 15 }

		
--   1.3.6.1.4.1.388.11.2.4.4.100.1.1.16
-- 1.3.6.1.4.1.388.6.12.3.100.1.1.16
		-- 1.3.6.1.4.1.388.6.16.3.100.1.1.16
		ccMuTxRetriesOctets15 OBJECT-TYPE
			SYNTAX Counter32
			MAX-ACCESS read-only
			STATUS deprecated
			DESCRIPTION
				"  The number of packets  transmitted to the Mobile Unit with 15 retries"
			::= { ccMuTxRetriesOctetsEntry 16 }

		
--   1.3.6.1.4.1.388.11.2.4.4.100.1.1.17
-- 1.3.6.1.4.1.388.6.12.3.100.1.1.17
		-- 1.3.6.1.4.1.388.6.16.3.100.1.1.17
		ccMuTxRetriesOctetsFailed OBJECT-TYPE
			SYNTAX Counter32
			MAX-ACCESS read-only
			STATUS current
			DESCRIPTION
				"  The number of packets that were not sent due to excess retries"
			::= { ccMuTxRetriesOctetsEntry 17 }

		
--   1.3.6.1.4.1.388.11.2.4.4.100.2
-- 1.3.6.1.4.1.388.6.12.3.100.2
		-- 1.3.6.1.4.1.388.6.16.3.100.2
		ccMuSigStatsTable OBJECT-TYPE
			SYNTAX SEQUENCE OF CcMuSigStatsEntry
			MAX-ACCESS not-accessible
			STATUS current
			DESCRIPTION
				" The various signal strength information for this MU"
			::= { ccMuRfSum 2 }

		
--   1.3.6.1.4.1.388.11.2.4.4.100.2.1
-- 1.3.6.1.4.1.388.6.12.3.100.2.1
		-- 1.3.6.1.4.1.388.6.16.3.100.2.1
		ccMuSigStatsEntry OBJECT-TYPE
			SYNTAX CcMuSigStatsEntry
			MAX-ACCESS not-accessible
			STATUS current
			DESCRIPTION
				" "
			INDEX { ccMuMac }
			::= { ccMuSigStatsTable 1 }

		
		CcMuSigStatsEntry ::=
			SEQUENCE { 
				ccMuSigStatsNumPkts
					Counter32,
				ccMuSigStatsSignalBest
					Integer32,
				ccMuSigStatsSignalWorst
					Integer32,
				ccMuSigStatsSignalSum
					Integer32,
				ccMuSigStatsSignalSumSquares
					Counter64,
				ccMuSigStatsSignalMostRecent
					Integer32,
				ccMuSigStatsNoiseBest
					Integer32,
				ccMuSigStatsNoiseWorst
					Integer32,
				ccMuSigStatsNoiseSum
					Integer32,
				ccMuSigStatsNoiseSumSquares
					Counter64,
				ccMuSigStatsNoiseMostRecent
					Integer32,
				ccMuSigStatsSnrBest
					Integer32,
				ccMuSigStatsSnrWorst
					Integer32,
				ccMuSigStatsSnrSum
					Counter64,
				ccMuSigStatsSnrSumSquares
					Counter64,
				ccMuSigStatsSnrMostRecent
					Integer32
			 }

--   1.3.6.1.4.1.388.11.2.4.4.100.2.1.1
-- 1.3.6.1.4.1.388.6.12.3.100.2.1.1
		-- 1.3.6.1.4.1.388.6.16.3.100.2.1.1
		ccMuSigStatsNumPkts OBJECT-TYPE
			SYNTAX Counter32
			MAX-ACCESS read-only
			STATUS current
			DESCRIPTION
				" The Number of Packets from the MU fro which the signal strength calculations shown in this table are done"
			::= { ccMuSigStatsEntry 1 }

		
--   1.3.6.1.4.1.388.11.2.4.4.100.2.1.2
-- 1.3.6.1.4.1.388.6.12.3.100.2.1.2
		-- 1.3.6.1.4.1.388.6.16.3.100.2.1.2
		ccMuSigStatsSignalBest OBJECT-TYPE
			SYNTAX Integer32
			UNITS "dBm"
			MAX-ACCESS read-only
			STATUS current
			DESCRIPTION
				" The best value of the signal strength in Dbm"
			::= { ccMuSigStatsEntry 2 }

		
--   1.3.6.1.4.1.388.11.2.4.4.100.2.1.3
-- 1.3.6.1.4.1.388.6.12.3.100.2.1.3
		-- 1.3.6.1.4.1.388.6.16.3.100.2.1.3
		ccMuSigStatsSignalWorst OBJECT-TYPE
			SYNTAX Integer32
			UNITS "dBm"
			MAX-ACCESS read-only
			STATUS current
			DESCRIPTION
				" The worst value of signal strength in dBm"
			::= { ccMuSigStatsEntry 3 }

		
--   1.3.6.1.4.1.388.11.2.4.4.100.2.1.4
-- 1.3.6.1.4.1.388.6.12.3.100.2.1.4
		-- 1.3.6.1.4.1.388.6.16.3.100.2.1.4
		ccMuSigStatsSignalSum OBJECT-TYPE
			SYNTAX Integer32
			UNITS "dBm"
			MAX-ACCESS read-only
			STATUS current
			DESCRIPTION
				" The sum of signal strength of all the packets received from the MU"
			::= { ccMuSigStatsEntry 4 }

		
--   1.3.6.1.4.1.388.11.2.4.4.100.2.1.5
-- 1.3.6.1.4.1.388.6.12.3.100.2.1.5
		-- 1.3.6.1.4.1.388.6.16.3.100.2.1.5
		ccMuSigStatsSignalSumSquares OBJECT-TYPE
			SYNTAX Counter64
			UNITS "dBm"
			MAX-ACCESS read-only
			STATUS current
			DESCRIPTION
				" The sum square of all the packets received from the MU"
			::= { ccMuSigStatsEntry 5 }

		
--   1.3.6.1.4.1.388.11.2.4.4.100.2.1.6
-- 1.3.6.1.4.1.388.6.12.3.100.2.1.6
		-- 1.3.6.1.4.1.388.6.16.3.100.2.1.6
		ccMuSigStatsSignalMostRecent OBJECT-TYPE
			SYNTAX Integer32
			UNITS "dBm"
			MAX-ACCESS read-only
			STATUS current
			DESCRIPTION
				" The most recent signal strength value received from the MU
				"
			::= { ccMuSigStatsEntry 6 }

		
--   1.3.6.1.4.1.388.11.2.4.4.100.2.1.7
-- 1.3.6.1.4.1.388.6.12.3.100.2.1.7
		-- 1.3.6.1.4.1.388.6.16.3.100.2.1.7
		ccMuSigStatsNoiseBest OBJECT-TYPE
			SYNTAX Integer32
			UNITS "dBm"
			MAX-ACCESS read-only
			STATUS current
			DESCRIPTION
				"The best noise value heard by the Radio to which this MU is associated.
				Here Best value of Noise implies the the least noise value.
				"
			::= { ccMuSigStatsEntry 7 }

		
--   1.3.6.1.4.1.388.11.2.4.4.100.2.1.8
-- 1.3.6.1.4.1.388.6.12.3.100.2.1.8
		-- 1.3.6.1.4.1.388.6.16.3.100.2.1.8
		ccMuSigStatsNoiseWorst OBJECT-TYPE
			SYNTAX Integer32
			UNITS "dBm"
			MAX-ACCESS read-only
			STATUS current
			DESCRIPTION
				" The worst value of the noise strength as received by the radio to which the MU is associated
				"
			::= { ccMuSigStatsEntry 8 }

		
--   1.3.6.1.4.1.388.11.2.4.4.100.2.1.9
-- 1.3.6.1.4.1.388.6.12.3.100.2.1.9
		-- 1.3.6.1.4.1.388.6.16.3.100.2.1.9
		ccMuSigStatsNoiseSum OBJECT-TYPE
			SYNTAX Integer32
			UNITS "dBm"
			MAX-ACCESS read-only
			STATUS current
			DESCRIPTION
				" The sum of all noise samples received from the Radio t which the MU is associsated
				"
			::= { ccMuSigStatsEntry 9 }

		
--   1.3.6.1.4.1.388.11.2.4.4.100.2.1.10
-- 1.3.6.1.4.1.388.6.12.3.100.2.1.10
		-- 1.3.6.1.4.1.388.6.16.3.100.2.1.10
		ccMuSigStatsNoiseSumSquares OBJECT-TYPE
			SYNTAX Counter64
			UNITS "dBm"
			MAX-ACCESS read-only
			STATUS current
			DESCRIPTION
				" The sumsq of all the noise samples received from the radio to which this MU is associated"
			::= { ccMuSigStatsEntry 10 }

		
--   1.3.6.1.4.1.388.11.2.4.4.100.2.1.11
-- 1.3.6.1.4.1.388.6.12.3.100.2.1.11
		-- 1.3.6.1.4.1.388.6.16.3.100.2.1.11
		ccMuSigStatsNoiseMostRecent OBJECT-TYPE
			SYNTAX Integer32
			UNITS "dBm"
			MAX-ACCESS read-only
			STATUS current
			DESCRIPTION
				" The strength of the most recent noise value heard from the radio
				to which this MU is associated"
			::= { ccMuSigStatsEntry 11 }

		
--   1.3.6.1.4.1.388.11.2.4.4.100.2.1.12
-- 1.3.6.1.4.1.388.6.12.3.100.2.1.12
		-- 1.3.6.1.4.1.388.6.16.3.100.2.1.12
		ccMuSigStatsSnrBest OBJECT-TYPE
			SYNTAX Integer32
			UNITS "dB"
			MAX-ACCESS read-only
			STATUS current
			DESCRIPTION
				" The best value of snr calculated for this MU"
			::= { ccMuSigStatsEntry 12 }

		
--   1.3.6.1.4.1.388.11.2.4.4.100.2.1.13
-- 1.3.6.1.4.1.388.6.12.3.100.2.1.13
		-- 1.3.6.1.4.1.388.6.16.3.100.2.1.13
		ccMuSigStatsSnrWorst OBJECT-TYPE
			SYNTAX Integer32
			UNITS "dB"
			MAX-ACCESS read-only
			STATUS current
			DESCRIPTION
				" The worst value of snr calculated for this MU
				"
			::= { ccMuSigStatsEntry 13 }

		
--   1.3.6.1.4.1.388.11.2.4.4.100.2.1.14
-- 1.3.6.1.4.1.388.6.12.3.100.2.1.14
		-- 1.3.6.1.4.1.388.6.16.3.100.2.1.14
		ccMuSigStatsSnrSum OBJECT-TYPE
			SYNTAX Counter64
			UNITS "dB"
			MAX-ACCESS read-only
			STATUS current
			DESCRIPTION
				" The sum of all the SNR values calculated for this MU"
			::= { ccMuSigStatsEntry 14 }

		
--   1.3.6.1.4.1.388.11.2.4.4.100.2.1.15
-- 1.3.6.1.4.1.388.6.12.3.100.2.1.15
		-- 1.3.6.1.4.1.388.6.16.3.100.2.1.15
		ccMuSigStatsSnrSumSquares OBJECT-TYPE
			SYNTAX Counter64
			UNITS "dB"
			MAX-ACCESS read-only
			STATUS current
			DESCRIPTION
				" The sum squqre of all the SNR values calculated for this MU
				"
			::= { ccMuSigStatsEntry 15 }

		
--   1.3.6.1.4.1.388.11.2.4.4.100.2.1.16
-- 1.3.6.1.4.1.388.6.12.3.100.2.1.16
		-- 1.3.6.1.4.1.388.6.16.3.100.2.1.16
		ccMuSigStatsSnrMostRecent OBJECT-TYPE
			SYNTAX Integer32
			UNITS "dB"
			MAX-ACCESS read-only
			STATUS current
			DESCRIPTION
				" The most recent value of the SNR calculated for this MU
				"
			::= { ccMuSigStatsEntry 16 }

		
--   1.3.6.1.4.1.388.11.2.4.4.100.3
-- 1.3.6.1.4.1.388.6.12.3.100.3
		-- 1.3.6.1.4.1.388.6.16.3.100.3
		ccMuSumStatsShortTable OBJECT-TYPE
			SYNTAX SEQUENCE OF CcMuSumStatsShortEntry
			MAX-ACCESS not-accessible
			STATUS current
			DESCRIPTION
				" "
			::= { ccMuRfSum 3 }

		
--   1.3.6.1.4.1.388.11.2.4.4.100.3.1
-- 1.3.6.1.4.1.388.6.12.3.100.3.1
		-- 1.3.6.1.4.1.388.6.16.3.100.3.1
		ccMuSumStatsShortEntry OBJECT-TYPE
			SYNTAX CcMuSumStatsShortEntry
			MAX-ACCESS not-accessible
			STATUS current
			DESCRIPTION
				" "
			INDEX { ccMuMac }
			::= { ccMuSumStatsShortTable 1 }

		
		CcMuSumStatsShortEntry ::=
			SEQUENCE { 
				ccMuSumStatsShortTimestamp
					TimeTicks,
				ccMuSumStatsShortNumPkts
					Unsigned32,
				ccMuSumStatsShortPktsPerSec100
					ScaleBy100,
				ccMuSumStatsShortPktsPerSecTx100
					ScaleBy100,
				ccMuSumStatsShortPktsPerSecRx100
					ScaleBy100,
				ccMuSumStatsShortThroughput
					Unsigned32,
				ccMuSumStatsShortThroughputTx
					Unsigned32,
				ccMuSumStatsShortThroughputRx
					Unsigned32,
				ccMuSumStatsShortAvgBitSpeed
					Unsigned32,
				ccMuSumStatsShortAvgMuSignal
					Integer32,
				ccMuSumStatsShortAvgMuNoise
					Integer32,
				ccMuSumStatsShortAvgMuSnr
					Integer32,
				ccMuSumStatsShortPp10kNUcastPkts
					PartsPer10k,
				ccMuSumStatsShortPp10kTxWithRetries
					PartsPer10k,
				ccMuSumStatsShortPp10kDropped
					PartsPer10k,
				ccMuSumStatsShortTxAvgRetries100
					ScaleBy100,
				ccMuSumStatsShortPp10kRxUndecrypt
					PartsPer10k
			 }

--   1.3.6.1.4.1.388.11.2.4.4.100.3.1.1
-- 1.3.6.1.4.1.388.6.12.3.100.3.1.1
		-- 1.3.6.1.4.1.388.6.16.3.100.3.1.1
		ccMuSumStatsShortTimestamp OBJECT-TYPE
			SYNTAX TimeTicks
			MAX-ACCESS read-only
			STATUS current
			DESCRIPTION
				" Snapshot of sysUpTime as of the END of the 'window' of time that this entry of values represents."
			::= { ccMuSumStatsShortEntry 1 }

		
--   1.3.6.1.4.1.388.11.2.4.4.100.3.1.2
-- 1.3.6.1.4.1.388.6.12.3.100.3.1.2
		-- 1.3.6.1.4.1.388.6.16.3.100.3.1.2
		ccMuSumStatsShortNumPkts OBJECT-TYPE
			SYNTAX Unsigned32
			UNITS "packets"
			MAX-ACCESS read-only
			STATUS current
			DESCRIPTION
				" The number of packets used to calculate the statistics in
								this window"
			::= { ccMuSumStatsShortEntry 2 }

		
--   1.3.6.1.4.1.388.11.2.4.4.100.3.1.3
-- 1.3.6.1.4.1.388.6.12.3.100.3.1.3
		-- 1.3.6.1.4.1.388.6.16.3.100.3.1.3
		ccMuSumStatsShortPktsPerSec100 OBJECT-TYPE
			SYNTAX ScaleBy100
			UNITS "pkts per sec x100"
			MAX-ACCESS read-only
			STATUS current
			DESCRIPTION
				" Packets per second as averaged over the 'window'.
								
								For transmitted packets, each packet sucessfully sent 
								counts as 1, (not N, where N is the number of retries).
								
								Since SNMP does not convey decimal values, the result 
								is multiplied by 100"
			::= { ccMuSumStatsShortEntry 3 }

		
--   1.3.6.1.4.1.388.11.2.4.4.100.3.1.4
-- 1.3.6.1.4.1.388.6.12.3.100.3.1.4
		-- 1.3.6.1.4.1.388.6.16.3.100.3.1.4
		ccMuSumStatsShortPktsPerSecTx100 OBJECT-TYPE
			SYNTAX ScaleBy100
			UNITS "pkts per sec x100"
			MAX-ACCESS read-only
			STATUS current
			DESCRIPTION
				" Packets per second TX as averaged over the 'window'.
								
								Each packet sucessfully sent counts as 1, (not N, where N
								is the number of retries).
								
								Since SNMP does not convey decimal values, the result 
								is multiplied by 100."
			::= { ccMuSumStatsShortEntry 4 }

		
--   1.3.6.1.4.1.388.11.2.4.4.100.3.1.5
-- 1.3.6.1.4.1.388.6.12.3.100.3.1.5
		-- 1.3.6.1.4.1.388.6.16.3.100.3.1.5
		ccMuSumStatsShortPktsPerSecRx100 OBJECT-TYPE
			SYNTAX ScaleBy100
			UNITS "pkts per sec x100"
			MAX-ACCESS read-only
			STATUS current
			DESCRIPTION
				" Packets per second RX as averaged over the 'window'.
								
								Since SNMP does not convey decimal values, the result 
								is multiplied by 100"
			::= { ccMuSumStatsShortEntry 5 }

		
--   1.3.6.1.4.1.388.11.2.4.4.100.3.1.6
-- 1.3.6.1.4.1.388.6.12.3.100.3.1.6
		-- 1.3.6.1.4.1.388.6.16.3.100.3.1.6
		ccMuSumStatsShortThroughput OBJECT-TYPE
			SYNTAX Unsigned32
			UNITS "bits per second"
			MAX-ACCESS read-only
			STATUS current
			DESCRIPTION
				" Actual number of bits sent and received over the window,
								divided by the number of seconds in the window.
								
								For transmitted packets, each packet sucessfully sent 
								counts as 1, (not N, where N is the number of retries)"
			::= { ccMuSumStatsShortEntry 6 }

		
--   1.3.6.1.4.1.388.11.2.4.4.100.3.1.7
-- 1.3.6.1.4.1.388.6.12.3.100.3.1.7
		-- 1.3.6.1.4.1.388.6.16.3.100.3.1.7
		ccMuSumStatsShortThroughputTx OBJECT-TYPE
			SYNTAX Unsigned32
			UNITS "bits per second"
			MAX-ACCESS read-only
			STATUS current
			DESCRIPTION
				" Actual number of bits TX over the window,
								divided by the number of seconds in the window.
								
								Each packet sucessfully sent counts as 1, (not N, where N
								is the number of retries)."
			::= { ccMuSumStatsShortEntry 7 }

		
--   1.3.6.1.4.1.388.11.2.4.4.100.3.1.8
-- 1.3.6.1.4.1.388.6.12.3.100.3.1.8
		-- 1.3.6.1.4.1.388.6.16.3.100.3.1.8
		ccMuSumStatsShortThroughputRx OBJECT-TYPE
			SYNTAX Unsigned32
			UNITS "bits per second"
			MAX-ACCESS read-only
			STATUS current
			DESCRIPTION
				" Actual number of bits RX over the window,
								divided by the number of seconds in the window"
			::= { ccMuSumStatsShortEntry 8 }

		
--   1.3.6.1.4.1.388.11.2.4.4.100.3.1.9
-- 1.3.6.1.4.1.388.6.12.3.100.3.1.9
		-- 1.3.6.1.4.1.388.6.16.3.100.3.1.9
		ccMuSumStatsShortAvgBitSpeed OBJECT-TYPE
			SYNTAX Unsigned32
			UNITS "bits per second"
			MAX-ACCESS read-only
			STATUS current
			DESCRIPTION
				" An octet-weighted average of the speeds of all packets
								sent/received.  (For each possible speed, multiply the
								number of octets sent/received by that speed;  divide the
								sum by the total number of octets;  multiply by 8).
								
								For transmitted packets, each packet sucessfully sent 
								counts as 1, (not N, where N is the number of retries).
								
								This can be said in more plain english as: the average
								bit-speed at which packets were sent/received"
			::= { ccMuSumStatsShortEntry 9 }

		
--   1.3.6.1.4.1.388.11.2.4.4.100.3.1.10
-- 1.3.6.1.4.1.388.6.12.3.100.3.1.10
		-- 1.3.6.1.4.1.388.6.16.3.100.3.1.10
		ccMuSumStatsShortAvgMuSignal OBJECT-TYPE
			SYNTAX Integer32
			UNITS "dBm"
			MAX-ACCESS read-only
			STATUS current
			DESCRIPTION
				" The average of all signal values over the window.
								
								NOTE: dBm are normally negative."
			::= { ccMuSumStatsShortEntry 10 }

		
--   1.3.6.1.4.1.388.11.2.4.4.100.3.1.11
-- 1.3.6.1.4.1.388.6.12.3.100.3.1.11
		-- 1.3.6.1.4.1.388.6.16.3.100.3.1.11
		ccMuSumStatsShortAvgMuNoise OBJECT-TYPE
			SYNTAX Integer32
			UNITS "dBm"
			MAX-ACCESS read-only
			STATUS current
			DESCRIPTION
				" The average of all noise values over the window"
			::= { ccMuSumStatsShortEntry 11 }

		
--   1.3.6.1.4.1.388.11.2.4.4.100.3.1.12
-- 1.3.6.1.4.1.388.6.12.3.100.3.1.12
		-- 1.3.6.1.4.1.388.6.16.3.100.3.1.12
		ccMuSumStatsShortAvgMuSnr OBJECT-TYPE
			SYNTAX Integer32
			UNITS "dB"
			MAX-ACCESS read-only
			STATUS current
			DESCRIPTION
				" The average of all SNR values over the window"
			::= { ccMuSumStatsShortEntry 12 }

		
--   1.3.6.1.4.1.388.11.2.4.4.100.3.1.13
-- 1.3.6.1.4.1.388.6.12.3.100.3.1.13
		-- 1.3.6.1.4.1.388.6.16.3.100.3.1.13
		ccMuSumStatsShortPp10kNUcastPkts OBJECT-TYPE
			SYNTAX PartsPer10k
			UNITS "parts-per-10000"
			MAX-ACCESS read-only
			STATUS current
			DESCRIPTION
				" Ratio of packets that were NOT unicast to the total number of packets sent/received.
								
								Expressed as parts-per-10000"
			::= { ccMuSumStatsShortEntry 13 }

		
--   1.3.6.1.4.1.388.11.2.4.4.100.3.1.14
-- 1.3.6.1.4.1.388.6.12.3.100.3.1.14
		-- 1.3.6.1.4.1.388.6.16.3.100.3.1.14
		ccMuSumStatsShortPp10kTxWithRetries OBJECT-TYPE
			SYNTAX PartsPer10k
			UNITS "parts-per-10000"
			MAX-ACCESS read-only
			STATUS current
			DESCRIPTION
				" Ratio of TX packets that experienced one or more retries to the total number of packets sent or received.
								
								Expressed as parts-per-10000"
			::= { ccMuSumStatsShortEntry 14 }

		
--   1.3.6.1.4.1.388.11.2.4.4.100.3.1.15
-- 1.3.6.1.4.1.388.6.12.3.100.3.1.15
		-- 1.3.6.1.4.1.388.6.16.3.100.3.1.15
		ccMuSumStatsShortPp10kDropped OBJECT-TYPE
			SYNTAX PartsPer10k
			UNITS "parts-per-10000"
			MAX-ACCESS read-only
			STATUS current
			DESCRIPTION
				" Ratio of TX packets that were dropped due to excessive retries.
								
								Expressed as parts-per-10000"
			::= { ccMuSumStatsShortEntry 15 }

		
--   1.3.6.1.4.1.388.11.2.4.4.100.3.1.16
-- 1.3.6.1.4.1.388.6.12.3.100.3.1.16
		-- 1.3.6.1.4.1.388.6.16.3.100.3.1.16
		ccMuSumStatsShortTxAvgRetries100 OBJECT-TYPE
			SYNTAX ScaleBy100
			UNITS "average x100"
			MAX-ACCESS read-only
			STATUS current
			DESCRIPTION
				" For all transmit packets (those that experienced some 
								retries, those that were successfully transmitted with
								only 1 transmission, and those that attempted max times
								and gave-up), the average number of RE-transmission 
								attempts.
								
								Said another (though identical) way: the sum of all 
								tranmission attempts divided by the number of unique 
								packets attempted to be sent.
								
								Since SNMP does not convey decimal values, the result 
								above is multiplied by 100.
								
								If there were no RE-transmissions, this value would be 0.
								If every single packet required exactly two tranmissions,
								this value would be 100, (representing 1.00)."
			::= { ccMuSumStatsShortEntry 16 }

		
--   1.3.6.1.4.1.388.11.2.4.4.100.3.1.17
-- 1.3.6.1.4.1.388.6.12.3.100.3.1.17
		-- 1.3.6.1.4.1.388.6.16.3.100.3.1.17
		ccMuSumStatsShortPp10kRxUndecrypt OBJECT-TYPE
			SYNTAX PartsPer10k
			UNITS "parts-per-10000"
			MAX-ACCESS read-only
			STATUS current
			DESCRIPTION
				"Ratio of RX packets that were undecryptable to the total number of packets received.
								
								Expressed as parts-per-10000"
			::= { ccMuSumStatsShortEntry 17 }

		
--   1.3.6.1.4.1.388.11.2.4.4.100.4
-- 1.3.6.1.4.1.388.6.12.3.100.4
		-- 1.3.6.1.4.1.388.6.16.3.100.4
		ccMuSumStatsLongTable OBJECT-TYPE
			SYNTAX SEQUENCE OF CcMuSumStatsLongEntry
			MAX-ACCESS not-accessible
			STATUS current
			DESCRIPTION
				" "
			::= { ccMuRfSum 4 }

		
--   1.3.6.1.4.1.388.11.2.4.4.100.4.1
-- 1.3.6.1.4.1.388.6.12.3.100.4.1
		-- 1.3.6.1.4.1.388.6.16.3.100.4.1
		ccMuSumStatsLongEntry OBJECT-TYPE
			SYNTAX CcMuSumStatsLongEntry
			MAX-ACCESS not-accessible
			STATUS current
			DESCRIPTION
				" "
			INDEX { ccMuMac }
			::= { ccMuSumStatsLongTable 1 }

		
		CcMuSumStatsLongEntry ::=
			SEQUENCE { 
				ccMuSumStatsLongTimestamp
					TimeTicks,
				ccMuSumStatsLongNumPkts
					Unsigned32,
				ccMuSumStatsLongPktsPerSec100
					ScaleBy100,
				ccMuSumStatsLongPktsPerSecTx100
					ScaleBy100,
				ccMuSumStatsLongPktsPerSecRx100
					ScaleBy100,
				ccMuSumStatsLongThroughput
					Unsigned32,
				ccMuSumStatsLongThroughputTx
					Unsigned32,
				ccMuSumStatsLongThroughputRx
					Unsigned32,
				ccMuSumStatsLongAvgBitSpeed
					Unsigned32,
				ccMuSumStatsLongAvgMuSignal
					Integer32,
				ccMuSumStatsLongAvgMuNoise
					Integer32,
				ccMuSumStatsLongAvgMuSnr
					Integer32,
				ccMuSumStatsLongPp10kNUcastPkts
					PartsPer10k,
				ccMuSumStatsLongPp10kTxWithRetries
					PartsPer10k,
				ccMuSumStatsLongPp10kDropped
					PartsPer10k,
				ccMuSumStatsLongTxAvgRetries100
					ScaleBy100,
				ccMuSumStatsLongPp10kRxUndecrypt
					PartsPer10k
			 }

--   1.3.6.1.4.1.388.11.2.4.4.100.4.1.1
-- 1.3.6.1.4.1.388.6.12.3.100.4.1.1
		-- 1.3.6.1.4.1.388.6.16.3.100.4.1.1
		ccMuSumStatsLongTimestamp OBJECT-TYPE
			SYNTAX TimeTicks
			MAX-ACCESS read-only
			STATUS current
			DESCRIPTION
				" Snapshot of sysUpTime as of the END of the 'window' of time that this entry of values represents."
			::= { ccMuSumStatsLongEntry 1 }

		
--   1.3.6.1.4.1.388.11.2.4.4.100.4.1.2
-- 1.3.6.1.4.1.388.6.12.3.100.4.1.2
		-- 1.3.6.1.4.1.388.6.16.3.100.4.1.2
		ccMuSumStatsLongNumPkts OBJECT-TYPE
			SYNTAX Unsigned32
			UNITS "packets"
			MAX-ACCESS read-only
			STATUS current
			DESCRIPTION
				"  The number of packets used to calculate the statistics in
				  this window"
			::= { ccMuSumStatsLongEntry 2 }

		
--   1.3.6.1.4.1.388.11.2.4.4.100.4.1.3
-- 1.3.6.1.4.1.388.6.12.3.100.4.1.3
		-- 1.3.6.1.4.1.388.6.16.3.100.4.1.3
		ccMuSumStatsLongPktsPerSec100 OBJECT-TYPE
			SYNTAX ScaleBy100
			UNITS "pkts per sec x100"
			MAX-ACCESS read-only
			STATUS current
			DESCRIPTION
				" Packets per second as averaged over the 'window'.
											
				 For transmitted packets, each packet sucessfully sent 
				 counts as 1, (not N, where N is the number of retries).
												
				 Since SNMP does not convey decimal values, the result 
				 is multiplied by 100"
			::= { ccMuSumStatsLongEntry 3 }

		
--   1.3.6.1.4.1.388.11.2.4.4.100.4.1.4
-- 1.3.6.1.4.1.388.6.12.3.100.4.1.4
		-- 1.3.6.1.4.1.388.6.16.3.100.4.1.4
		ccMuSumStatsLongPktsPerSecTx100 OBJECT-TYPE
			SYNTAX ScaleBy100
			UNITS "pkts per sec x100"
			MAX-ACCESS read-only
			STATUS current
			DESCRIPTION
				"  Packets per second TX as averaged over the 'window'.
												
				 Each packet sucessfully sent counts as 1, (not N, where N
				 is the number of retries).
												
				 Since SNMP does not convey decimal values, the result 
				 is multiplied by 100."
			::= { ccMuSumStatsLongEntry 4 }

		
--   1.3.6.1.4.1.388.11.2.4.4.100.4.1.5
-- 1.3.6.1.4.1.388.6.12.3.100.4.1.5
		-- 1.3.6.1.4.1.388.6.16.3.100.4.1.5
		ccMuSumStatsLongPktsPerSecRx100 OBJECT-TYPE
			SYNTAX ScaleBy100
			UNITS "pkts per sec x100"
			MAX-ACCESS read-only
			STATUS current
			DESCRIPTION
				"  Packets per second RX as averaged over the 'window'.
												
				 Since SNMP does not convey decimal values, the result 
				 is multiplied by 100"
			::= { ccMuSumStatsLongEntry 5 }

		
--   1.3.6.1.4.1.388.11.2.4.4.100.4.1.6
-- 1.3.6.1.4.1.388.6.12.3.100.4.1.6
		-- 1.3.6.1.4.1.388.6.16.3.100.4.1.6
		ccMuSumStatsLongThroughput OBJECT-TYPE
			SYNTAX Unsigned32
			UNITS "bits per second"
			MAX-ACCESS read-only
			STATUS current
			DESCRIPTION
				" Actual number of bits sent and received over the window,
				 divided by the number of seconds in the window.
												
				 For transmitted packets, each packet sucessfully sent 
				 counts as 1, (not N, where N is the number of retries)"
			::= { ccMuSumStatsLongEntry 6 }

		
--   1.3.6.1.4.1.388.11.2.4.4.100.4.1.7
-- 1.3.6.1.4.1.388.6.12.3.100.4.1.7
		-- 1.3.6.1.4.1.388.6.16.3.100.4.1.7
		ccMuSumStatsLongThroughputTx OBJECT-TYPE
			SYNTAX Unsigned32
			UNITS "bits per second"
			MAX-ACCESS read-only
			STATUS current
			DESCRIPTION
				" Actual number of bits TX over the window,
				 divided by the number of seconds in the window.
												
				 Each packet sucessfully sent counts as 1, (not N, where N
				 is the number of retries)."
			::= { ccMuSumStatsLongEntry 7 }

		
--   1.3.6.1.4.1.388.11.2.4.4.100.4.1.8
-- 1.3.6.1.4.1.388.6.12.3.100.4.1.8
		-- 1.3.6.1.4.1.388.6.16.3.100.4.1.8
		ccMuSumStatsLongThroughputRx OBJECT-TYPE
			SYNTAX Unsigned32
			UNITS "bits per second"
			MAX-ACCESS read-only
			STATUS current
			DESCRIPTION
				"  Actual number of bits RX over the window,
				  divided by the number of seconds in the window"
			::= { ccMuSumStatsLongEntry 8 }

		
--   1.3.6.1.4.1.388.11.2.4.4.100.4.1.9
-- 1.3.6.1.4.1.388.6.12.3.100.4.1.9
		-- 1.3.6.1.4.1.388.6.16.3.100.4.1.9
		ccMuSumStatsLongAvgBitSpeed OBJECT-TYPE
			SYNTAX Unsigned32
			UNITS "bits per second"
			MAX-ACCESS read-only
			STATUS current
			DESCRIPTION
				" An octet-weighted average of the speeds of all packets
				 sent/received.  (For each possible speed, multiply the
				 number of octets sent/received by that speed;  divide the
				 sum by the total number of octets;  multiply by 8).
												
				 For transmitted packets, each packet sucessfully sent 
				 counts as 1, (not N, where N is the number of retries).
												
				 This can be said in more plain english as: the average
				 bit-speed at which packets were sent/received"
			::= { ccMuSumStatsLongEntry 9 }

		
--   1.3.6.1.4.1.388.11.2.4.4.100.4.1.10
-- 1.3.6.1.4.1.388.6.12.3.100.4.1.10
		-- 1.3.6.1.4.1.388.6.16.3.100.4.1.10
		ccMuSumStatsLongAvgMuSignal OBJECT-TYPE
			SYNTAX Integer32
			UNITS "dBm"
			MAX-ACCESS read-only
			STATUS current
			DESCRIPTION
				"  The average of all signal values over the window.
												
				  NOTE: dBm are normally negative."
			::= { ccMuSumStatsLongEntry 10 }

		
--   1.3.6.1.4.1.388.11.2.4.4.100.4.1.11
-- 1.3.6.1.4.1.388.6.12.3.100.4.1.11
		-- 1.3.6.1.4.1.388.6.16.3.100.4.1.11
		ccMuSumStatsLongAvgMuNoise OBJECT-TYPE
			SYNTAX Integer32
			UNITS "dBm"
			MAX-ACCESS read-only
			STATUS current
			DESCRIPTION
				" The average of all noise values over the window"
			::= { ccMuSumStatsLongEntry 11 }

		
--   1.3.6.1.4.1.388.11.2.4.4.100.4.1.12
-- 1.3.6.1.4.1.388.6.12.3.100.4.1.12
		-- 1.3.6.1.4.1.388.6.16.3.100.4.1.12
		ccMuSumStatsLongAvgMuSnr OBJECT-TYPE
			SYNTAX Integer32
			UNITS "dB"
			MAX-ACCESS read-only
			STATUS current
			DESCRIPTION
				"  The average of all SNR values over the window"
			::= { ccMuSumStatsLongEntry 12 }

		
--   1.3.6.1.4.1.388.11.2.4.4.100.4.1.13
-- 1.3.6.1.4.1.388.6.12.3.100.4.1.13
		-- 1.3.6.1.4.1.388.6.16.3.100.4.1.13
		ccMuSumStatsLongPp10kNUcastPkts OBJECT-TYPE
			SYNTAX PartsPer10k
			UNITS "parts-per-10000"
			MAX-ACCESS read-only
			STATUS current
			DESCRIPTION
				" Ratio of packets that were NOT unicast to the total number of packets sent/received.
												
				 Expressed as parts-per-10000"
			::= { ccMuSumStatsLongEntry 13 }

		
--   1.3.6.1.4.1.388.11.2.4.4.100.4.1.14
-- 1.3.6.1.4.1.388.6.12.3.100.4.1.14
		-- 1.3.6.1.4.1.388.6.16.3.100.4.1.14
		ccMuSumStatsLongPp10kTxWithRetries OBJECT-TYPE
			SYNTAX PartsPer10k
			UNITS "parts-per-10000"
			MAX-ACCESS read-only
			STATUS current
			DESCRIPTION
				" Ratio of TX packets that experienced one or more retries to the total number of packets sent or received.
												
				 Expressed as parts-per-10000"
			::= { ccMuSumStatsLongEntry 14 }

		
--   1.3.6.1.4.1.388.11.2.4.4.100.4.1.15
-- 1.3.6.1.4.1.388.6.12.3.100.4.1.15
		-- 1.3.6.1.4.1.388.6.16.3.100.4.1.15
		ccMuSumStatsLongPp10kDropped OBJECT-TYPE
			SYNTAX PartsPer10k
			UNITS "parts-per-10000"
			MAX-ACCESS read-only
			STATUS current
			DESCRIPTION
				" Ratio of TX packets that were dropped due to excessive retries.
												
				 Expressed as parts-per-10000"
			::= { ccMuSumStatsLongEntry 15 }

		
--   1.3.6.1.4.1.388.11.2.4.4.100.4.1.16
-- 1.3.6.1.4.1.388.6.12.3.100.4.1.16
		-- 1.3.6.1.4.1.388.6.16.3.100.4.1.16
		ccMuSumStatsLongTxAvgRetries100 OBJECT-TYPE
			SYNTAX ScaleBy100
			UNITS "average x100"
			MAX-ACCESS read-only
			STATUS current
			DESCRIPTION
				" For all transmit packets (those that experienced some 
				 retries, those that were successfully transmitted with
				 only 1 transmission, and those that attempted max times
				 and gave-up), the average number of RE-transmission 
				 attempts.
												
				 Said another (though identical) way: the sum of all 
				 tranmission attempts divided by the number of unique 
				 packets attempted to be sent.
												
				 Since SNMP does not convey decimal values, the result 
				 above is multiplied by 100.
												
				 If there were no RE-transmissions, this value would be 0.
				 If every single packet required exactly two tranmissions,
				 this value would be 100, (representing 1.00)."
			::= { ccMuSumStatsLongEntry 16 }

		
--   1.3.6.1.4.1.388.11.2.4.4.100.4.1.17
-- 1.3.6.1.4.1.388.6.12.3.100.4.1.17
		-- 1.3.6.1.4.1.388.6.16.3.100.4.1.17
		ccMuSumStatsLongPp10kRxUndecrypt OBJECT-TYPE
			SYNTAX PartsPer10k
			UNITS "parts-per-10000"
			MAX-ACCESS read-only
			STATUS current
			DESCRIPTION
				" Ratio of RX packets that were undecryptable to the total number of packets received.
												
				 Expressed as parts-per-10000"
			::= { ccMuSumStatsLongEntry 17 }

		
		-- 1.3.6.1.4.1.388.6.18
		ccWME OBJECT IDENTIFIER ::= { symbolCC 18 }

		
		-- 1.3.6.1.4.1.388.6.18.5
		ccWMEprofileTable OBJECT-TYPE
			SYNTAX SEQUENCE OF CcWMEprofileEntry
			MAX-ACCESS not-accessible
			STATUS current
			DESCRIPTION
				"Description.
				 Table for WME Profiles."
			::= { ccWME 5 }

		
		-- 1.3.6.1.4.1.388.6.18.5.1
		ccWMEprofileEntry OBJECT-TYPE
			SYNTAX CcWMEprofileEntry
			MAX-ACCESS not-accessible
			STATUS current
			DESCRIPTION
				"Description."
			INDEX { ccWMEprofileIndex }
			::= { ccWMEprofileTable 1 }

		
		CcWMEprofileEntry ::=
			SEQUENCE { 
				ccWMEprofileIndex
					Integer32,
				ccWMEprofilename
					DisplayString,
				ccWMEprofileDesc
					DisplayString,
				ccWMEprofileAc1VoEcwmin
					Integer32,
				ccWMEprofileAc1VoEcwmax
					Integer32,
				ccWMEprofileAc1VoTxopLimit
					Integer32,
				ccWMEprofileAc1VoAgTxopLimit
					Integer32,
				ccWMEprofileAc1VoAifsn
					Integer32,
				ccWMEprofileAc2ViEcwmin
					Integer32,
				ccWMEprofileAc2ViEcwmax
					Integer32,
				ccWMEprofileAc2ViTxopLimit
					Integer32,
				ccWMEprofileAc2ViAgTxopLimit
					Integer32,
				ccWMEprofileAc2ViAifsn
					Integer32,
				ccWMEprofileAc3BeEcwmin
					Integer32,
				ccWMEprofileAc3BeEcwmax
					Integer32,
				ccWMEprofileAc3BeTxopLimit
					Integer32,
				ccWMEprofileAc3BeAgTxopLimit
					Integer32,
				ccWMEprofileAc3BeAifsn
					Integer32,
				ccWMEprofileAc4BkEcwmin
					Integer32,
				ccWMEprofileAc4BkEcwmax
					Integer32,
				ccWMEprofileAc4BkTxopLimit
					Integer32,
				ccWMEprofileAc4BkAgTxopLimit
					Integer32,
				ccWMEprofileAc4BkAifsn
					Integer32,
				ccWMEprofileQosParam
					Integer32,
				ccWMEprofileRowStatus
					AbbrevRowStatus
			 }

		-- 1.3.6.1.4.1.388.6.18.5.1.1
		ccWMEprofileIndex OBJECT-TYPE
			SYNTAX Integer32 (1..10)
			MAX-ACCESS accessible-for-notify
			STATUS current
			DESCRIPTION
				"Description.
				 Simple Index 1...10"
			::= { ccWMEprofileEntry 1 }

		
		-- 1.3.6.1.4.1.388.6.18.5.1.2
		ccWMEprofilename OBJECT-TYPE
			SYNTAX DisplayString
			MAX-ACCESS read-create
			STATUS current
			DESCRIPTION
				"Description.
				WME Profile Name."
			::= { ccWMEprofileEntry 2 }

		
		-- 1.3.6.1.4.1.388.6.18.5.1.3
		ccWMEprofileDesc OBJECT-TYPE
			SYNTAX DisplayString
			MAX-ACCESS read-create
			STATUS current
			DESCRIPTION
				"Description."
			::= { ccWMEprofileEntry 3 }

		
		-- 1.3.6.1.4.1.388.6.18.5.1.4
		ccWMEprofileAc1VoEcwmin OBJECT-TYPE
			SYNTAX Integer32 (0..15)
			MAX-ACCESS read-create
			STATUS current
			DESCRIPTION
				"Description.
				 WME Voice Access Category CWMin value."
			::= { ccWMEprofileEntry 4 }

		
		-- 1.3.6.1.4.1.388.6.18.5.1.5
		ccWMEprofileAc1VoEcwmax OBJECT-TYPE
			SYNTAX Integer32 (0..15)
			MAX-ACCESS read-create
			STATUS current
			DESCRIPTION
				"Description.
				WME Voice Access Category CWMax value."
			::= { ccWMEprofileEntry 5 }

		
		-- 1.3.6.1.4.1.388.6.18.5.1.6
		ccWMEprofileAc1VoTxopLimit OBJECT-TYPE
			SYNTAX Integer32 (0..65535)
			MAX-ACCESS read-create
			STATUS current
			DESCRIPTION
				"Description.
				 WME Voice Access Category Txopstime value.(B)"
			::= { ccWMEprofileEntry 6 }

		
		-- 1.3.6.1.4.1.388.6.18.5.1.7
		ccWMEprofileAc1VoAgTxopLimit OBJECT-TYPE
			SYNTAX Integer32 (0..65535)
			MAX-ACCESS read-create
			STATUS current
			DESCRIPTION
				"Description.
				 WME Voice Access Category Txopstime value.(A/G)"
			::= { ccWMEprofileEntry 7 }

		
		-- 1.3.6.1.4.1.388.6.18.5.1.8
		ccWMEprofileAc1VoAifsn OBJECT-TYPE
			SYNTAX Integer32 (0..15)
			MAX-ACCESS read-create
			STATUS current
			DESCRIPTION
				"Description.
				 WME Voice Access Category Aifsn value."
			::= { ccWMEprofileEntry 8 }

		
		-- 1.3.6.1.4.1.388.6.18.5.1.9
		ccWMEprofileAc2ViEcwmin OBJECT-TYPE
			SYNTAX Integer32 (0..15)
			MAX-ACCESS read-create
			STATUS current
			DESCRIPTION
				"Description.
				 WME Video Access Category CWMin value."
			::= { ccWMEprofileEntry 9 }

		
		-- 1.3.6.1.4.1.388.6.18.5.1.10
		ccWMEprofileAc2ViEcwmax OBJECT-TYPE
			SYNTAX Integer32 (0..15)
			MAX-ACCESS read-create
			STATUS current
			DESCRIPTION
				"Description.
				 WME Video Access Category CWMax value.
				 "
			::= { ccWMEprofileEntry 10 }

		
		-- 1.3.6.1.4.1.388.6.18.5.1.11
		ccWMEprofileAc2ViTxopLimit OBJECT-TYPE
			SYNTAX Integer32 (0..65535)
			MAX-ACCESS read-create
			STATUS current
			DESCRIPTION
				"Description.
				 WME Video Access Category Txopstime value.(B)"
			::= { ccWMEprofileEntry 11 }

		
		-- 1.3.6.1.4.1.388.6.18.5.1.12
		ccWMEprofileAc2ViAgTxopLimit OBJECT-TYPE
			SYNTAX Integer32 (0..65535)
			MAX-ACCESS read-create
			STATUS current
			DESCRIPTION
				"Description.
				 WME Video Access Category Txopstime value.(A/G)"
			::= { ccWMEprofileEntry 12 }

		
		-- 1.3.6.1.4.1.388.6.18.5.1.13
		ccWMEprofileAc2ViAifsn OBJECT-TYPE
			SYNTAX Integer32 (0..15)
			MAX-ACCESS read-create
			STATUS current
			DESCRIPTION
				"Description.
				 WME Video Access Category Aifsn value."
			::= { ccWMEprofileEntry 13 }

		
		-- 1.3.6.1.4.1.388.6.18.5.1.14
		ccWMEprofileAc3BeEcwmin OBJECT-TYPE
			SYNTAX Integer32 (0..15)
			MAX-ACCESS read-create
			STATUS current
			DESCRIPTION
				"Description.
				 WME Best Effort Access Category CWMin value"
			::= { ccWMEprofileEntry 14 }

		
		-- 1.3.6.1.4.1.388.6.18.5.1.15
		ccWMEprofileAc3BeEcwmax OBJECT-TYPE
			SYNTAX Integer32 (0..15)
			MAX-ACCESS read-create
			STATUS current
			DESCRIPTION
				"Description.
				 WME Best Effort Access Category CWMax value."
			::= { ccWMEprofileEntry 15 }

		
		-- 1.3.6.1.4.1.388.6.18.5.1.16
		ccWMEprofileAc3BeTxopLimit OBJECT-TYPE
			SYNTAX Integer32 (0..65535)
			MAX-ACCESS read-create
			STATUS current
			DESCRIPTION
				"Description.
				 WME Best Effort Access Category Txopstime value. (B)"
			::= { ccWMEprofileEntry 16 }

		
		-- 1.3.6.1.4.1.388.6.18.5.1.17
		ccWMEprofileAc3BeAgTxopLimit OBJECT-TYPE
			SYNTAX Integer32 (0..65535)
			MAX-ACCESS read-create
			STATUS current
			DESCRIPTION
				"Description.
				WME Best Effort Access Category Txopstime value.(A/G)"
			::= { ccWMEprofileEntry 17 }

		
		-- 1.3.6.1.4.1.388.6.18.5.1.18
		ccWMEprofileAc3BeAifsn OBJECT-TYPE
			SYNTAX Integer32 (0..15)
			MAX-ACCESS read-create
			STATUS current
			DESCRIPTION
				"Description.
				 WME Best Effort Access Category Aifsn value."
			::= { ccWMEprofileEntry 18 }

		
		-- 1.3.6.1.4.1.388.6.18.5.1.19
		ccWMEprofileAc4BkEcwmin OBJECT-TYPE
			SYNTAX Integer32 (0..15)
			MAX-ACCESS read-create
			STATUS current
			DESCRIPTION
				"Description.
				 WME Background Access Category CWMin value."
			::= { ccWMEprofileEntry 19 }

		
		-- 1.3.6.1.4.1.388.6.18.5.1.20
		ccWMEprofileAc4BkEcwmax OBJECT-TYPE
			SYNTAX Integer32 (0..15)
			MAX-ACCESS read-create
			STATUS current
			DESCRIPTION
				"Description.
				 WME Background Access Category CWMax value."
			::= { ccWMEprofileEntry 20 }

		
		-- 1.3.6.1.4.1.388.6.18.5.1.21
		ccWMEprofileAc4BkTxopLimit OBJECT-TYPE
			SYNTAX Integer32 (0..65535)
			MAX-ACCESS read-create
			STATUS current
			DESCRIPTION
				"Description.
				 WME Background Access Category Txopstime value.(B)"
			::= { ccWMEprofileEntry 21 }

		
		-- 1.3.6.1.4.1.388.6.18.5.1.22
		ccWMEprofileAc4BkAgTxopLimit OBJECT-TYPE
			SYNTAX Integer32 (0..65535)
			MAX-ACCESS read-create
			STATUS current
			DESCRIPTION
				"Description.
				WME Background Access Category Txopstime value.(A/G)"
			::= { ccWMEprofileEntry 22 }

		
		-- 1.3.6.1.4.1.388.6.18.5.1.23
		ccWMEprofileAc4BkAifsn OBJECT-TYPE
			SYNTAX Integer32 (0..15)
			MAX-ACCESS read-create
			STATUS current
			DESCRIPTION
				"Description.
				 WME Background Access Category Aifsn value."
			::= { ccWMEprofileEntry 23 }

		
		-- 1.3.6.1.4.1.388.6.18.5.1.24
		ccWMEprofileQosParam OBJECT-TYPE
			SYNTAX Integer32
			MAX-ACCESS read-create
			STATUS current
			DESCRIPTION
				"Description.
				WME profile QosParam
				This is Read Only."
			::= { ccWMEprofileEntry 24 }

		
		-- 1.3.6.1.4.1.388.6.18.5.1.25
		ccWMEprofileRowStatus OBJECT-TYPE
			SYNTAX AbbrevRowStatus
			MAX-ACCESS read-create
			STATUS current
			DESCRIPTION
				"Description.
				Used for row creation/deletion."
			::= { ccWMEprofileEntry 25 }

		
		-- 1.3.6.1.4.1.388.6.19
		ccPortalBeacon OBJECT IDENTIFIER ::= { symbolCC 19 }

		
		-- 1.3.6.1.4.1.388.6.19.5
		ccPortalBeaconRptTable OBJECT-TYPE
			SYNTAX SEQUENCE OF CcPortalBeaconRptEntry
			MAX-ACCESS not-accessible
			STATUS current
			DESCRIPTION
				"Description.
				This table describes the signal values (in dBm) of 
				beacons heard from other Portals
				Note that the 'neighbor' Portals reported may not be the
				geographically closest Portal, since other Portals which
				are nearer may not be on the same channel.
								
				This table is useful for determining if RF conditions
				between Portals have radically changed over time
				
				"
			::= { ccPortalBeacon 5 }

		
		-- 1.3.6.1.4.1.388.6.19.5.1
		ccPortalBeaconRptEntry OBJECT-TYPE
			SYNTAX CcPortalBeaconRptEntry
			MAX-ACCESS not-accessible
			STATUS current
			DESCRIPTION
				"Description."
			INDEX { ccRapResultsRogueIndex, ccPortalBeaconRptPortalIndex }
			::= { ccPortalBeaconRptTable 1 }

		
		CcPortalBeaconRptEntry ::=
			SEQUENCE { 
				ccPortalBeaconRptPortalIndex
					INTEGER,
				ccPortalBeaconRptNumBeaconsHeard
					Integer32,
				ccPortalBeaconRptBest
					Integer32,
				ccPortalBeaconRptWorst
					Integer32,
				ccPortalBeaconRptSum
					Integer32,
				ccPortalBeaconRptSumSquares
					Integer32,
				ccPortalBeaconRptMostRecent
					Integer32,
				ccPortalBeaconRptLastHeard
					DisplayString,
				ccPortalBeaconRpFinderMac
					DisplayString,
				ccPortalBeaconRpFoundMac
					DisplayString
			 }

		-- 1.3.6.1.4.1.388.6.19.5.1.1
		ccPortalBeaconRptPortalIndex OBJECT-TYPE
			SYNTAX INTEGER (1..255)
			MAX-ACCESS accessible-for-notify
			STATUS current
			DESCRIPTION
				"Description.
				The ccPortalTable:ccPortalIndex of the neighbor Portal
				that has been heard."
			::= { ccPortalBeaconRptEntry 1 }

		
		-- 1.3.6.1.4.1.388.6.19.5.1.2
		ccPortalBeaconRptNumBeaconsHeard OBJECT-TYPE
			SYNTAX Integer32
			MAX-ACCESS read-only
			STATUS current
			DESCRIPTION
				"Description.
				Number of beacons reported in this entry"
			::= { ccPortalBeaconRptEntry 2 }

		
		-- 1.3.6.1.4.1.388.6.19.5.1.3
		ccPortalBeaconRptBest OBJECT-TYPE
			SYNTAX Integer32
			UNITS "dBm"
			MAX-ACCESS read-only
			STATUS current
			DESCRIPTION
				"Description.
				The strongest beacon signal strength heard since boot"
			::= { ccPortalBeaconRptEntry 3 }

		
		-- 1.3.6.1.4.1.388.6.19.5.1.4
		ccPortalBeaconRptWorst OBJECT-TYPE
			SYNTAX Integer32
			UNITS "dBm"
			MAX-ACCESS read-only
			STATUS current
			DESCRIPTION
				"Description.
				The weakest beacon signal strength heard since boot"
			::= { ccPortalBeaconRptEntry 4 }

		
		-- 1.3.6.1.4.1.388.6.19.5.1.5
		ccPortalBeaconRptSum OBJECT-TYPE
			SYNTAX Integer32
			MAX-ACCESS read-only
			STATUS current
			DESCRIPTION
				"Description.
				The sum of all signal values heard"
			::= { ccPortalBeaconRptEntry 5 }

		
		-- 1.3.6.1.4.1.388.6.19.5.1.6
		ccPortalBeaconRptSumSquares OBJECT-TYPE
			SYNTAX Integer32
			MAX-ACCESS read-only
			STATUS current
			DESCRIPTION
				"Description.
				The sum of each signal value heard, squared before 
				summing"
			::= { ccPortalBeaconRptEntry 6 }

		
		-- 1.3.6.1.4.1.388.6.19.5.1.7
		ccPortalBeaconRptMostRecent OBJECT-TYPE
			SYNTAX Integer32
			MAX-ACCESS read-only
			STATUS current
			DESCRIPTION
				"Description.
				The most-recent value of signal heard for a beacon"
			::= { ccPortalBeaconRptEntry 7 }

		
		-- 1.3.6.1.4.1.388.6.19.5.1.8
		ccPortalBeaconRptLastHeard OBJECT-TYPE
			SYNTAX DisplayString
			MAX-ACCESS read-only
			STATUS current
			DESCRIPTION
				"Description.
				Snapshot of sysUpTime at the time the prior item(s) in
				this entry were last updated."
			::= { ccPortalBeaconRptEntry 8 }

		
		-- 1.3.6.1.4.1.388.6.19.5.1.9
		ccPortalBeaconRpFinderMac OBJECT-TYPE
			SYNTAX DisplayString
			MAX-ACCESS read-only
			STATUS current
			DESCRIPTION
				"Description."
			::= { ccPortalBeaconRptEntry 9 }

		
		-- 1.3.6.1.4.1.388.6.19.5.1.10
		ccPortalBeaconRpFoundMac OBJECT-TYPE
			SYNTAX DisplayString
			MAX-ACCESS read-only
			STATUS current
			DESCRIPTION
				"Description."
			::= { ccPortalBeaconRptEntry 10 }

		
		-- 1.3.6.1.4.1.388.6.19.6
		ccMuProbeRptTable OBJECT-TYPE
			SYNTAX SEQUENCE OF CcMuProbeRptEntry
			MAX-ACCESS not-accessible
			STATUS current
			DESCRIPTION
				"Description.
				This table reports the signal strength of ProbeRequest
				packets heard from each MU by each Portal that heard them"
			::= { ccPortalBeacon 6 }

		
		-- 1.3.6.1.4.1.388.6.19.6.1
		ccMuProbeRptEntry OBJECT-TYPE
			SYNTAX CcMuProbeRptEntry
			MAX-ACCESS not-accessible
			STATUS current
			DESCRIPTION
				"Description."
			INDEX { ccMuMac, ccPortalIndex }
			::= { ccMuProbeRptTable 1 }

		
		CcMuProbeRptEntry ::=
			SEQUENCE { 
				ccMuProbeRptSignalMostRecent
					Integer32,
				ccMuProbeRptLastHeard
					DisplayString,
				ccMuProbeRptFinderMac
					DisplayString,
				ccMuProbeRptFoundMac
					DisplayString
			 }

		-- 1.3.6.1.4.1.388.6.19.6.1.1
		ccMuProbeRptSignalMostRecent OBJECT-TYPE
			SYNTAX Integer32
			UNITS "dbm"
			MAX-ACCESS read-only
			STATUS current
			DESCRIPTION
				"Description.
				The signal strength, (in dBm), of the most-recently
				heard ProbeRequest from the given MU, (specified by the
				primary index: ccMuMac), from the given Portal,
				(specified by the secondary index: ccPortalIndex).
								
				In the event that the given Portal hears more than one
				ProbeRequest from the MU in a short period of time,
				(say, around 1-3sec), only the strongest value is
				reported.  (Such a case can occur when an MU is
				performing an active scan, and the Portal hears the 
				ProbeRequests from the MU sent on on adjacent channels)."
			::= { ccMuProbeRptEntry 1 }

		
		-- 1.3.6.1.4.1.388.6.19.6.1.2
		ccMuProbeRptLastHeard OBJECT-TYPE
			SYNTAX DisplayString
			MAX-ACCESS read-only
			STATUS current
			DESCRIPTION
				"Description.
				Snapshot of sysUpTime at the time the prior item(s) in
				this entry were last updated"
			::= { ccMuProbeRptEntry 2 }

		
		-- 1.3.6.1.4.1.388.6.19.6.1.3
		ccMuProbeRptFinderMac OBJECT-TYPE
			SYNTAX DisplayString
			MAX-ACCESS read-only
			STATUS current
			DESCRIPTION
				"Description."
			::= { ccMuProbeRptEntry 3 }

		
		-- 1.3.6.1.4.1.388.6.19.6.1.4
		ccMuProbeRptFoundMac OBJECT-TYPE
			SYNTAX DisplayString
			MAX-ACCESS read-only
			STATUS current
			DESCRIPTION
				"Description."
			::= { ccMuProbeRptEntry 4 }

		
		-- 1.3.6.1.4.1.388.6.20
		ccSensor OBJECT IDENTIFIER ::= { symbolCC 20 }

		
		-- 1.3.6.1.4.1.388.6.20.1
		ccSensorList OBJECT-TYPE
			SYNTAX DisplayString
			MAX-ACCESS read-only
			STATUS current
			DESCRIPTION
				"List of Mac Address of all discovered sensors"
			::= { ccSensor 1 }

		
		-- 1.3.6.1.4.1.388.6.20.2
		ccApList OBJECT-TYPE
			SYNTAX DisplayString
			MAX-ACCESS read-only
			STATUS current
			DESCRIPTION
				"List of AP300s "
			::= { ccSensor 2 }

		
		-- 1.3.6.1.4.1.388.6.20.3
		ccSensorRevert OBJECT-TYPE
			SYNTAX DisplayString
			MAX-ACCESS read-write
			STATUS current
			DESCRIPTION
				"syntax :  <Mac - Address>
				
				Mac address of AP300 of a sensor to revert"
			::= { ccSensor 3 }

		
		-- 1.3.6.1.4.1.388.6.20.4
		ccSensorConvert OBJECT-TYPE
			SYNTAX DisplayString
			MAX-ACCESS read-write
			STATUS current
			DESCRIPTION
				"syntax :  <Mac - Address>
				
				Mac address of AP300 that is to 
				be converted to a sensor"
			::= { ccSensor 4 }

		
		-- 1.3.6.1.4.1.388.6.20.5
		ccSensorEnable OBJECT-TYPE
			SYNTAX TruthValue
			MAX-ACCESS read-write
			STATUS current
			DESCRIPTION
				"syntax : Enable(1)/Disable(0)
				
				Enable/Disable Sensor "
			::= { ccSensor 5 }

		
		-- 1.3.6.1.4.1.388.6.20.6
		ccApSensorTable OBJECT-TYPE
			SYNTAX SEQUENCE OF CcApSensorEntry
			MAX-ACCESS not-accessible
			STATUS current
			DESCRIPTION
				"Description."
			::= { ccSensor 6 }

		
		-- 1.3.6.1.4.1.388.6.20.6.1
		ccApSensorEntry OBJECT-TYPE
			SYNTAX CcApSensorEntry
			MAX-ACCESS not-accessible
			STATUS current
			DESCRIPTION
				"Description."
			INDEX { ccApSensorIndex }
			::= { ccApSensorTable 1 }

		
		CcApSensorEntry ::=
			SEQUENCE { 
				ccApSensorIndex
					INTEGER,
				ccApSensorMask
					IpAddress,
				ccApSensorGateWay
					IpAddress,
				ccApSensorPrimary
					IpAddress,
				ccApSensorSecondary
					IpAddress,
				ccApSensorDhcp
					TruthValue,
				ccApSensorIpaddress
					IpAddress,
				ccApSensorMac
					DisplayString
			 }

		-- 1.3.6.1.4.1.388.6.20.6.1.1
		ccApSensorIndex OBJECT-TYPE
			SYNTAX INTEGER (1..30)
			MAX-ACCESS read-only
			STATUS current
			DESCRIPTION
				"Description."
			::= { ccApSensorEntry 1 }

		
		-- 1.3.6.1.4.1.388.6.20.6.1.2
		ccApSensorMask OBJECT-TYPE
			SYNTAX IpAddress
			MAX-ACCESS read-write
			STATUS current
			DESCRIPTION
				"syntax : <Subnet Mask >
				
				Subnet mask of the sensor "
			::= { ccApSensorEntry 2 }

		
		-- 1.3.6.1.4.1.388.6.20.6.1.3
		ccApSensorGateWay OBJECT-TYPE
			SYNTAX IpAddress
			MAX-ACCESS read-write
			STATUS current
			DESCRIPTION
				"syntax : <Gate Way>
				
				Gate Way of the sensor "
			::= { ccApSensorEntry 3 }

		
		-- 1.3.6.1.4.1.388.6.20.6.1.4
		ccApSensorPrimary OBJECT-TYPE
			SYNTAX IpAddress
			MAX-ACCESS read-write
			STATUS current
			DESCRIPTION
				"syntax : <Primary Server Ip>
				
				Primary Server of the sensor "
			::= { ccApSensorEntry 4 }

		
		-- 1.3.6.1.4.1.388.6.20.6.1.5
		ccApSensorSecondary OBJECT-TYPE
			SYNTAX IpAddress
			MAX-ACCESS read-write
			STATUS current
			DESCRIPTION
				"syntax : <Secondary Server Ip>
				
				Secondary Server of the sensor "
			::= { ccApSensorEntry 5 }

		
		-- 1.3.6.1.4.1.388.6.20.6.1.6
		ccApSensorDhcp OBJECT-TYPE
			SYNTAX TruthValue
			MAX-ACCESS read-write
			STATUS current
			DESCRIPTION
				"syntax : Enable(1)/Disable(0)
				
				Enable/Disable dhcp"
			::= { ccApSensorEntry 6 }

		
		-- 1.3.6.1.4.1.388.6.20.6.1.7
		ccApSensorIpaddress OBJECT-TYPE
			SYNTAX IpAddress
			MAX-ACCESS read-write
			STATUS current
			DESCRIPTION
				"syntax : < Ip Address>
				
				Ip Address of the sensor "
			::= { ccApSensorEntry 7 }

		
		-- 1.3.6.1.4.1.388.6.20.6.1.8
		ccApSensorMac OBJECT-TYPE
			SYNTAX DisplayString
			MAX-ACCESS read-only
			STATUS current
			DESCRIPTION
				"Mac of the Sensor ."
			::= { ccApSensorEntry 8 }

		
		-- 1.3.6.1.4.1.388.6.1000
		ccV2dot0Groups OBJECT IDENTIFIER ::= { symbolCC 1000 }

		
		-- 1.3.6.1.4.1.388.6.1000.1
		v2dot0Group OBJECT-GROUP
			OBJECTS { ccLANIndex, ccLANName, ccLANDesc, ccLANNATCount, ccLANAddNAT, 
				ccLANRemNAT, ccLANEp, ccLANNp, ccLANNATIndex, ccRouteIndex, 
				ccRouteDest, ccRouteGateway, ccRouteFlags, ccRouteRefs, ccRouteUse, 
				ccRouteInterface, ccRouteAddObj, ccRouteRemObj, ccRouteFlush, ccDhcp1Srv, 
				ccDhcp1Subnet, ccDhcp1Netmask, ccDhcp1BcastIP, ccDhcp1RouterIP, ccDhcp1PriDNSIP, 
				ccDhcp1SecDNSIP, ccDhcp1DomainName, ccDhcp1DefLease, ccDhcp1MaxLease, ccDhcp1RangeIndex, 
				ccDhcp1RangeStartIP, ccDhcp1RangeEndIP, ccDhcp1AddIPRangeObj, ccDhcp1RemIPRangeObj, ccDhcp1StaticIPIndex, 
				ccDhcp1StaticIP, ccDhcp1StaticMac, ccDhcp1StaticHost, ccDhcp1AddStaticIPObj, ccDhcp1RemStaticIPObj, 
				ccDhcp1OptionIndex, ccDhcp1OptionName, ccDhcp1OptionCode, ccDhcp1OptionType, ccDhcp1OptionValue, 
				ccDhcp1AddOptionObj, ccDhcp1RemOptionObj, ccDhcp1LeaseIndex, ccDhcp1LeaseIP, ccDhcp1LeaseMac, 
				ccDhcp1LeaseStartTime, ccDhcp1LeaseEndTime, ccDhcp1RemLeaseObj, ccDhcp2Srv, ccDhcp2Subnet, 
				ccDhcp2Netmask, ccDhcp2BcastIP, ccDhcp2RouterIP, ccDhcp2PriDNSIP, ccDhcp2SecDNSIP, 
				ccDhcp2DomainName, ccDhcp2DefLease, ccDhcp2MaxLease, ccDhcp2RangeIndex, ccDhcp2RangeStartIP, 
				ccDhcp2RangeEndIP, ccDhcp2AddIPRangeObj, ccDhcp2RemIPRangeObj, ccDhcp2StaticIPIndex, ccDhcp2StaticIP, 
				ccDhcp2StaticMac, ccDhcp2StaticHost, ccDhcp2AddStaticIPObj, ccDhcp2RemStaticIPObj, ccDhcp2OptionIndex, 
				ccDhcp2OptionName, ccDhcp2OptionCode, ccDhcp2OptionType, ccDhcp2OptionValue, ccDhcp2AddOptionObj, 
				ccDhcp2RemOptionObj, ccDhcp2LeaseIndex, ccDhcp2LeaseIP, ccDhcp2LeaseMac, ccDhcp2LeaseStartTime, 
				ccDhcp2LeaseEndTime, ccDhcp2RemLeaseObj, wvpnServerEnable, wvpnServerDisable, wvpnServerRestart, 
				wvpnIpAddress, wvpnPort, wvpnUnusedTimeout, wvpnStatus, dosEnable, 
				dosPort, clientKeepAlive, vpnLicenseMax, vpnLicenseInUse, maxClientRsaKeySize, 
				minClientRsaKeySize, maxRsaKeySize, minRsaKeySize, cipher, mac, 
				requireClientCertificate, keyRefresh, wantedFipsMode, securityMode, serverNumber, 
				handshakeTimeout, allowSessionResume, useSimpleAuthentication, useRadiusAuthentication, useLdapAuthentication, 
				useLocalDatabaseAuthentication, simpleAuthUserName, simpleAuthPassword, simpleAuthDomain, radiusAuthPrimaryHost, 
				radiusAuthPrimaryPort, radiusAuthPrimaryMaxRetries, radiusAuthPrimaryTimeOut, radiusAuthPrimaryUserPassword, radiusAuthPrimarySecret, 
				radiusAuthSecondaryHost, radiusAuthSecondaryPort, radiusAuthSecondaryMaxRetries, radiusAuthSecondaryTimeOut, radiusAuthSecondaryUserPassword, 
				radiusAuthSecondarySecret, wvpnAddIpPoolObj, wvpnRemIpPoolObj, wvpnAddIpPoolRange, wvpnRemIpPoolRange, 
				useDhcpGateway, wvpnIpPoolIndex, clientIpPoolName, clientNetMask, clientDhcpServerAddress, 
				clientDefaultGatewayAddress, clientDnsAddress, clientWinsAddress, clientDomainName, clientNetBiosNodeType, 
				clientDhcpLeaseTime, reuseAddrTime, ipRangeCount, clientIpRanges, wvpnIpPoolsCount, 
				wvpnIpPoolsNames, wvpnCertIndex, userName, serialNumber, subject, 
				version, issuer, keyLength, validFrom, validTo, 
				certificate, binary, fingerPrint, authFingerPrint, serverCertCount, 
				serverCertUserNames, wvpnCaCertIndex, wvpnCaSerialNumber, wvpnCaSubject, wvpnCaVersion, 
				wvpnCaIssuer, wvpnCaKeyLength, wvpnCaValidFrom, wvpnCaValidTo, wvpnCaBinary, 
				wvpnCaFingerPrint, wvpnCaAuthFingerPrint, caCertCount, certSerialNumbers, importServerCert, 
				removeServerCert, importCaCert, removeCaCert, importTftpServerCert, importTftpCaCert, 
				dirCert, dumpCert, clearClientDNS, updateClientDNS, addDNSAddr, 
				deleteDNSAddr, enable, ttl, forwardZone, reverseZone, 
				clientNameString, wvpnDDNSAddressIndex, wvpnDDNSipAddress, ccRadiusDataSource, ccRadiusDefaultEapType, 
				ccRadiusAuthTypePeap, ccRadiusAuthTypeTtls, ccRadiusServerCertificate, ccRadiusCACertificate, ccRadiusClientAuthIndex, 
				ccRadiusClientAuthIpAddr, ccRadiusClientAuthMask, ccRadiusClientAuthSharedSecret, ccRadiusClientAuthRowStatus, ccRadiusProxyRetryCount, 
				ccRadiusProxyTimeout, ccRadiusProxyServerIndex, ccRadiusProxyServerPrefixOrSuffix, ccRadiusProxyServerIp, ccRadiusProxyServerPort, 
				ccRadiusProxyServerSharedSecret, ccRadiusProxyServerRowStatus, ccRadiusLdap1ServerIp, ccRadiusLdap1ServerPort, ccRadiusLdap1LoginAttribute, 
				ccRadiusLdap1PasswordAttribute, ccRadiusLdap1BindDistinguishedName, ccRadiusLdap1BindDistinguishedPassword, ccRadiusLdap1BaseDistinguishedName, ccRadiusLdap1GroupAttribute, 
				ccRadiusLdap1GroupFilter, ccRadiusLdap1GroupMembershipAttribute, ccRadiusLdap2ServerIp, ccRadiusLdap2ServerPort, ccRadiusLdap2LoginAttribute, 
				ccRadiusLdap2PasswordATtribute, ccRadiusLdap2BindDistinguishedName, ccRadiusLdap2BindDistinguishedPassword, ccRadiusLdap2BaseDistinguishedName, ccRadiusLdap2GroupAttribute, 
				ccRadiusLdap2GroupFilter, ccRadiusLdap2GroupMembershipAttribute, ccRadiusUsersId, ccRadiusUsersPassword, ccRadiusUsersRowStatus, 
				ccRadiusAcctIPAddress, ccRadiusAcctPort, ccRadiusAcctTimeout, ccRadiusAcctMaxRetry, ccRadiusAcctSharedSecret, 
				ccRapPollSymbolMusEnable, ccRapPollSymbolMusInterval, ccRapOnChannelEnable, ccRapOnChannelInterval, ccRapDetectorsEnable, 
				ccRapDetectorsInterval, ccRapAuthAllSymbolMac, ccRapAuthIndex, ccRapAuthMacFilter, ccRapAuthEssidFilter, 
				ccRapAuthRowExists, ccRapAuthErase, ccRapAuthCopyAllApproved, ccRapAuthCopyAllRogue, ccRapResultsApprovedAgeOut, 
				ccRapResultsApprovedIndex, ccRapResultsApprovedApMac, ccRapResultsApprovedEssid, ccRapResultsApprovedCopyToAuthTable, ccRapResultsApprovedFirstHeard, 
				ccRapResultsApprovedLastHeard, ccRapResultsApprovedPortalPtr, ccRapResultsApprovedHowFound, ccRapResultsApprovedHowAuth, ccRapResultsApprovedErase, 
				ccRapResultsRogueAgeOut, ccRapResultsRogueIndex, ccRapResultsRogueApMac, ccRapResultsRogueEssid, ccRapResultsRogueCopyToAuthTable, 
				ccRapResultsRogueFirstHeard, ccRapResultsRogueLastHeard, ccRapResultsRoguePortalPtr, ccRapResultsRogueHowFound, ccRapResultsRogueClosestPortalPtr, 
				ccRapResultsRogueClosestPortalRssi, ccRapResultsRogueErase, ccRestore, ccFtp, ccTftp, 
				ccListFiles, ccRadiusTimeRestrictionStart, wvpnSessionIndex, wvpnSessionId, wvpnVpnIp, 
				wvpnRealIp, wvpnLoginTime, wvpnRoamTime, wvpnLastActive, wvpnPoolName, 
				wvpnMacAddr, wvpnSessionCount, wvpnRefreshSession, wvpnKillSession, ccTrapInfoWVPNAlert, 
				ccTrapInfoWVPNInfo, ccEnableWVPNSupport, cleanupTimeout, reverseZoneList, reverseZoneAdd, 
				reverseZoneDel, ccRadiusSaveStatus, ccRapResultsApprovedRowErase, ccDetectorAp, ccEnableRap, 
				ccDeleteFiles, ccRapNewRogueApControl, ccRapNewApprovedApControl, ccRadiusTimeRestrictionEnd, ccAvgSNR, 
				ccFWLanRemObj, ccFWLanAddObj, remkdcMu, addkdcMu, ccAvgRSSI, 
				ccAvgTxRetry, ccAPRxPPS, ccAPTxPPS, ccEPPrimaryVid, ccRadioUser802x, 
				ccSimulateRadar, ccRadioMaxMUs, ccRadioMUs, ccRadiusServerEnable, ccRadiusEapPasswd, 
				ccInfoRadiusServerControl, ccTrapInfoRadiusAcct, ccRouteGenMask, ccDhcp2RemStaticHost, ccDhcp1RemStaticHost, 
				ccRadiusAccessWlanPtrs, ccRadiusAccessGroupId, ccRadiusUsersGroups, ccRadiusGroupRowStatus, ccRadiusGroup, 
				ccLANPfDeny, ccLANPfAllow, ccRadiusTimeRestrictionDays, ccLANNATRemoteRealIP, ccLANNATLocalNatIP, 
				ccSecVPNEnabled }
			STATUS current
			DESCRIPTION 
				"Description."
			::= { ccV2dot0Groups 1 }

		
		-- 1.3.6.1.4.1.388.6.1000.2
		v2dot0NotificationGroup NOTIFICATION-GROUP
			NOTIFICATIONS { ccRapNewRogueAp, ccRapNewApprovedAp, ccTrapWVPNAlert, ccTrapWVPNInfo, ccTrapInfoRadiusAcctInfo, 
				ccInfoRadiusServer }
			STATUS current
			DESCRIPTION 
				"Description."
			::= { ccV2dot0Groups 2 }

		
		-- 1.3.6.1.4.1.388.6.1000.3
		v2dot0GroupOfDepricated OBJECT-GROUP
			OBJECTS { ccAccessMethodsPermitted }
			STATUS deprecated
			DESCRIPTION 
				"Description."
			::= { ccV2dot0Groups 3 }

		
		-- 1.3.6.1.4.1.388.6.1000.4
		v2dot1Group OBJECT-GROUP
			OBJECTS { ccWMEprofileQosParam, ccWMEprofileAc4BkAifsn, ccWMEprofileAc4BkAgTxopLimit, ccWMEprofileAc4BkTxopLimit, ccWMEprofileAc4BkEcwmax, 
				ccWMEprofileAc4BkEcwmin, ccWMEprofileAc3BeAifsn, ccWMEprofileAc3BeAgTxopLimit, ccWMEprofileAc3BeEcwmax, ccWMEprofileAc3BeEcwmin, 
				ccWMEprofileAc2ViAifsn, ccWMEprofileAc2ViAgTxopLimit, ccWMEprofileAc2ViTxopLimit, ccWMEprofileAc2ViEcwmax, ccWMEprofileAc2ViEcwmin, 
				ccWMEprofileAc1VoAifsn, ccWMEprofileAc1VoAgTxopLimit, ccWMEprofileAc1VoTxopLimit, ccWMEprofileAc1VoEcwmax, ccWMEprofileAc1VoEcwmin, 
				ccWMEprofileDesc, ccWMEprofilename, ccWMEprofileIndex, ccPortalBeaconRptSum, ccPortalBeaconRptWorst, 
				ccPortalBeaconRptBest, ccPortalBeaconRptNumBeaconsHeard, ccPortalBeaconRptPortalIndex, ccPortalBeaconRptSumSquares, ccPortalBeaconRptMostRecent, 
				ccPortalBeaconRptLastHeard, ccMuProbeRptSignalMostRecent, ccMuProbeRptLastHeard, ccAPPolicyWMEProfile, ccAPPolicyWMEEnable, 
				ccWlanWMEProfile, ccWlanWMEEnable, ccWMEprofileRowStatus, configChangeUpdateControl, ccNtpPrefTimeServer, 
				ccNtpFirstAltTimeServer, ccNtpSecondAltTimeServer, ccNtpGroupSetTimeServer, ccAPPolicyDTIM4, ccAPPolicyDTIM3, 
				ccAPPolicyDTIM2, tunnelUnknownProtocolControl, tunnelStatusChangedControl, ccApSensorDhcp, ccApSensorSecondary, 
				ccApSensorPrimary, ccApSensorGateWay, ccApSensorMask, ccApSensorIpaddress, ccSensorRevert, 
				ccSensorConvert, ccSensorList, ccApSensorIndex, ccSumStatsSwitchControl, ccSumStatsWlanControl, 
				ccSumStatsMuControl, ccApList, ccMuProbeRptFoundMac, ccMuProbeRptFinderMac, ccPortalBeaconRpFoundMac, 
				ccPortalBeaconRpFinderMac, ccEPDhcpPriVlan, sensorOfflineControl, sensorFailureControl, sensorRevertControl, 
				sensorConvertControl, ccSensorEnable, ccApSensorMac, ccEPDDNSUpdateAll, ccEPDDNSttl, 
				ccEPDDNSStatus, ccNtpDelAll, ccConfigChangeLast, ccEPDDNSDomainName, ccEPDDNSMUserStatus, 
				ccMUInfoRoamCount, ccWMEprofileAc3BeTxopLimit, ccSumStatsApControl }
			STATUS current
			DESCRIPTION 
				"Description."
			::= { ccV2dot0Groups 4 }

		
		-- 1.3.6.1.4.1.388.6.1000.5
		v2dot1NotificationGroup NOTIFICATION-GROUP
			NOTIFICATIONS { tunnelUnknownProtocol, tunnelStatusChanged, ccSumStatsSwitch, ccSumStatsWlan, ccSumStatsMu, 
				sensorOffline, sensorFailure, sensorRevert, sensorConvert, configChangeUpdate, 
				ccSumStatsAp }
			STATUS current
			DESCRIPTION 
				"Description."
			::= { ccV2dot0Groups 5 }

		
		-- 1.3.6.1.4.1.388.6.1000.6
		v2dot1StatsGroup OBJECT-GROUP
			OBJECTS { ccApIndex, ccApNicMac, ccApModelNumber, ccApSerialNumber, ccApPcbRevision, 
				ccApBootLoaderRev, ccApWispVersion, ccApRuntimeFwVersion, ccApNumPortals, ccApPointersToPortals, 
				ccPortalIndex, ccPortalPointerToAp, ccPortalPointersToWlans, ccPortalName, ccPortalLocation, 
				ccPortalOptions, ccPortalMac, ccPortalNumberofEss, ccPortalNumberOfBss, ccPortalAssociatedMus, 
				ccPortalRadioType, ccPortalChannel, ccPortalTxPowerLevel, ccPortalLastAdoption, ccPortalState, 
				ccPortalBackgroundNoiseNumSamples, ccPortalBackgroundNoiseBest, ccPortalBackgroundNoiseWorst, ccPortalBackgroundNoiseSum, ccPortalBackgroundNoiseSumSquares, 
				ccPortalLastMac, ccPortalLastReason, ccPortalSystemStatsBeaconTx, ccPortalSystemStatsBeaconsTxOctets, ccPortalSystemStatsProbeReqRx, 
				ccPortalSystemStatsProbeReqRxOctets, ccPortalSystemStatsProbeRespRetriesNone, ccPortalSystemStatsProbeRespRetries1, ccPortalSystemStatsProbeRespRetries2, ccPortalSystemStatsProbeRespRetries3OrMore, 
				ccPortalSystemStatsProbeRespRetriesFailed, ccPortalSystemStatsProbeRespTxOctets, ccPortalTxPktsUcast, ccPortalRxPktsUcast, ccPortalRxPktsNUcast, 
				ccPortalTxOctetsUcast, ccPortalRxOctetsUcast, ccPortalRxOctetsNUcast, ccPortalRxUndecryptablePkts, ccPortalLastActivity, 
				ccPortalRxPktsAt1Mb, ccPortalRxPktsAt2Mb, ccPortalRxPktsAt5pt5Mb, ccPortalRxPktsAt6Mb, ccPortalRxPktsAt9Mb, 
				ccPortalRxPktsAt11Mb, ccPortalRxPktsAt12Mb, ccPortalRxPktsAt18Mb, ccPortalRxPktsAt22Mb, ccPortalRxPktsAt24Mb, 
				ccPortalRxPktsAt36Mb, ccPortalRxPktsAt48Mb, ccPortalRxPktsAt54Mb, ccPortalTxPktsAt1Mb, ccPortalTxPktsAt2Mb, 
				ccPortalTxPktsAt5pt5Mb, ccPortalTxPktsAt6Mb, ccPortalTxPktsAt9Mb, ccPortalTxPktsAt11Mb, ccPortalTxPktsAt12Mb, 
				ccPortalTxPktsAt18Mb, ccPortalTxPktsAt22Mb, ccPortalTxPktsAt24Mb, ccPortalTxPktsAt36Mb, ccPortalTxPktsAt48Mb, 
				ccPortalTxPktsAt54Mb, ccPortalRxOctetsAt1Mb, ccPortalRxOctetsAt2Mb, ccPortalRxOctetsAt5pt5Mb, ccPortalRxOctetsAt6Mb, 
				ccPortalRxOctetsAt9Mb, ccPortalRxOctetsAt11Mb, ccPortalRxOctetsAt12Mb, ccPortalRxOctetsAt18Mb, ccPortalRxOctetsAt22Mb, 
				ccPortalRxOctetsAt24Mb, ccPortalRxOctetsAt36Mb, ccPortalRxOctetsAt48Mb, ccPortalRxOctetsAt54Mb, ccPortalTxOctetsAt1Mb, 
				ccPortalTxOctetsAt2Mb, ccPortalTxOctetsAt5pt5Mb, ccPortalTxOctetsAt6Mb, ccPortalTxOctetsAt9Mb, ccPortalTxOctetsAt11Mb, 
				ccPortalTxOctetsAt12Mb, ccPortalTxOctetsAt18Mb, ccPortalTxOctetsAt22Mb, ccPortalTxOctetsAt24Mb, ccPortalTxOctetsAt36Mb, 
				ccPortalTxOctetsAt48Mb, ccPortalTxOctetsAt54Mb, ccPortalTxRetriesPktsNone, ccPortalTxRetriesPkts01, ccPortalTxRetriesPkts02, 
				ccPortalTxRetriesPkts03, ccPortalTxRetriesPkts04, ccPortalTxRetriesPkts05, ccPortalTxRetriesPkts06, ccPortalTxRetriesPkts07, 
				ccPortalTxRetriesPkts08, ccPortalTxRetriesPkts09, ccPortalTxRetriesPkts10, ccPortalTxRetriesPkts11, ccPortalTxRetriesPkts12, 
				ccPortalTxRetriesPkts13, ccPortalTxRetriesPkts14, ccPortalTxRetriesPktsFailed, ccPortalTxRetriesOctetsNone, ccPortalTxRetriesOctets01, 
				ccPortalTxRetriesOctets02, ccPortalTxRetriesOctets03, ccPortalTxRetriesOctets04, ccPortalTxRetriesOctets05, ccPortalTxRetriesOctets06, 
				ccPortalTxRetriesOctets07, ccPortalTxRetriesOctets08, ccPortalTxRetriesOctets09, ccPortalTxRetriesOctets10, ccPortalTxRetriesOctets11, 
				ccPortalTxRetriesOctets12, ccPortalTxRetriesOctets13, ccPortalTxRetriesOctets14, ccPortalTxRetriesOctetsFailed, ccPortalSigStatsNumPkts, 
				ccPortalSigStatsSignalBest, ccPortalSigStatsSignalWorst, ccPortalSigStatsSignalSum, ccPortalSigStatsSignalSumSquares, ccPortalSigStatsSignalMostRecent, 
				ccPortalSigStatsNoiseBest, ccPortalSigStatsNoiseWorst, ccPortalSigStatsNoiseSum, ccPortalSigStatsNoiseSumSquares, ccPortalSigStatsNoiseMostRecent, 
				ccPortalSigStatsSnrBest, ccPortalSigStatsSnrWorst, ccPortalSigStatsSnrSum, ccPortalSigStatsSnrSumSquares, ccPortalSigStatsSnrMostRecent, 
				ccPortalSumStatsShortTimestamp, ccPortalSumStatsShortNumPkts, ccPortalSumStatsShortPktsPerSec100, ccPortalSumStatsShortPktsPerSecTx100, ccPortalSumStatsShortPktsPerSecRx100, 
				ccPortalSumStatsShortThroughput, ccPortalSumStatsShortThroughputTx, ccPortalSumStatsShortThroughputRx, ccPortalSumStatsShortAvgBitSpeed, ccPortalSumStatsShortAvgMuSignal, 
				ccPortalSumStatsShortAvgMuNoise, ccPortalSumStatsShortAvgMuSnr, ccPortalSumStatsShortPp10kNUcastPkts, ccPortalSumStatsShortPp10kTxWithRetries, ccPortalSumStatsShortPp10kTxMaxRetries, 
				ccPortalSumStatsShortTxAvgRetries100, ccPortalSumStatsShortPp10kRxUndecrypt, ccPortalSumStatsShortTotalMus, ccPortalSumStatsShortPp10kRfUtil, ccPortalSumStatsShortPp10kDropped, 
				ccPortalSumStatsLongTimestamp, ccPortalSumStatsLongNumPkts, ccPortalSumStatsLongPktsPerSec100, ccPortalSumStatsLongPktsPerSecTx100, ccPortalSumStatsLongPktsPerSecRx100, 
				ccPortalSumStatsLongThroughput, ccPortalSumStatsLongThroughputTx, ccPortalSumStatsLongThroughputRx, ccPortalSumStatsLongAvgBitSpeed, ccPortalSumStatsLongAvgMuSignal, 
				ccPortalSumStatsLongAvgMuNoise, ccPortalSumStatsLongAvgMuSnr, ccPortalSumStatsLongPp10kNUcastPkts, ccPortalSumStatsLongPp10kTxWithRetries, ccPortalSumStatsLongPp10kTxMaxRetries, 
				ccPortalSumStatsLongTxAvgRetries100, ccPortalSumStatsLongPp10kRxUndecrypt, ccPortalSumStatsLongTotalMus, ccPortalSumStatsLongPp10kRfUtil, ccPortalSumStatsLongPp10kDropped, 
				ccMuMac, ccMuWlanIndex, ccMuWlanName, ccMuIsDataReady, ccMuPortalIndex, 
				ccMuPortalMac, ccMuSymbolRogueApEna, ccMuIpAddr, ccMuType, ccMuRadioType, 
				ccMuSupportedRates, ccMuPowerMode, ccMuAuthenticationMethod, ccMuEncryptionMethod, ccMuVlanId, 
				ccMuTxPktsUcast, ccMuRxPktsUcast, ccMuRxPktsNUcast, ccMuTxOctetsUcast, ccMuRxOctetsUcast, 
				ccMuRxOctetsNUcast, ccMuRxUndecryptablePkts, ccMuRxRssiNumPkts, ccMuRxRssiSum, ccMuRxRssiSumSquares, 
				ccMuRxRssiMostRecent, ccMuLastActivity, ccMuRxPktsAt1Mb, ccMuRxPktsAt2Mb, ccMuRxPktsAt5pt5Mb, 
				ccMuRxPktsAt6Mb, ccMuRxPktsAt9Mb, ccMuRxPktsAt11Mb, ccMuRxPktsAt12Mb, ccMuRxPktsAt18Mb, 
				ccMuRxPktsAt22Mb, ccMuRxPktsAt24Mb, ccMuRxPktsAt36Mb, ccMuRxPktsAt48Mb, ccMuRxPktsAt54Mb, 
				ccMuTxPktsAt1Mb, ccMuTxPktsAt2Mb, ccMuTxPktsAt5pt5Mb, ccMuTxPktsAt6Mb, ccMuTxPktsAt9Mb, 
				ccMuTxPktsAt12Mb, ccMuTxPktsAt11Mb, ccMuTxPktsAt18Mb, ccMuTxPktsAt24Mb, ccMuTxPktsAt22Mb, 
				ccMuTxPktsAt36Mb, ccMuTxPktsAt48Mb, ccMuTxPktsAt54Mb, ccMuRxOctetsAt1Mb, ccMuRxOctetsAt2Mb, 
				ccMuRxOctetsAt5pt5Mb, ccMuRxOctetsAt6Mb, ccMuRxOctetsAt9Mb, ccMuRxOctetsAt11Mb, ccMuRxOctetsAt12Mb, 
				ccMuRxOctetsAt18Mb, ccMuRxOctetsAt22Mb, ccMuRxOctetsAt24Mb, ccMuRxOctetsAt36Mb, ccMuRxOctetsAt48Mb, 
				ccMuRxOctetsAt54Mb, ccMuTxOctetsAt1Mb, ccMuTxOctetsAt2Mb, ccMuTxOctetsAt5pt5Mb, ccMuTxOctetsAt6Mb, 
				ccMuTxOctetsAt9Mb, ccMuTxOctetsAt11Mb, ccMuTxOctetsAt12Mb, ccMuTxOctetsAt18Mb, ccMuTxOctetsAt22Mb, 
				ccMuTxOctetsAt24Mb, ccMuTxOctetsAt36Mb, ccMuTxOctetsAt48Mb, ccMuTxOctetsAt54Mb, ccMuTxRetriesNone, 
				ccMuTxRetries01, ccMuTxRetries02, ccMuTxRetries03, ccMuTxRetries04, ccMuTxRetries05, 
				ccMuTxRetries06, ccMuTxRetries07, ccMuTxRetries08, ccMuTxRetries09, ccMuTxRetries10, 
				ccMuTxRetries11, ccMuTxRetries12, ccMuTxRetries13, ccMuTxRetries14, ccMuTxRetriesFailed, 
				ccMuTxRetriesTotal, ccMuTxRetriesMostRecent, ccMuLastMac, ccMuLastReason, ccMuLastPortal, 
				ccMuTxRetriesOctetsNone, ccMuTxRetriesOctets01, ccMuTxRetriesOctets02, ccMuTxRetriesOctets03, ccMuTxRetriesOctets04, 
				ccMuTxRetriesOctets05, ccMuTxRetriesOctets06, ccMuTxRetriesOctets07, ccMuTxRetriesOctets08, ccMuTxRetriesOctets09, 
				ccMuTxRetriesOctets10, ccMuTxRetriesOctets11, ccMuTxRetriesOctets12, ccMuTxRetriesOctets13, ccMuTxRetriesOctets14, 
				ccMuTxRetriesOctetsFailed, ccMuSigStatsNumPkts, ccMuSigStatsSignalBest, ccMuSigStatsSignalWorst, ccMuSigStatsSignalSum, 
				ccMuSigStatsSignalSumSquares, ccMuSigStatsSignalMostRecent, ccMuSigStatsNoiseBest, ccMuSigStatsNoiseWorst, ccMuSigStatsNoiseSum, 
				ccMuSigStatsNoiseSumSquares, ccMuSigStatsNoiseMostRecent, ccMuSigStatsSnrBest, ccMuSigStatsSnrWorst, ccMuSigStatsSnrSum, 
				ccMuSigStatsSnrSumSquares, ccMuSigStatsSnrMostRecent, ccMuSumStatsShortTimestamp, ccMuSumStatsShortNumPkts, ccMuSumStatsShortPktsPerSec100, 
				ccMuSumStatsShortPktsPerSecTx100, ccMuSumStatsShortPktsPerSecRx100, ccMuSumStatsShortThroughput, ccMuSumStatsShortThroughputTx, ccMuSumStatsShortThroughputRx, 
				ccMuSumStatsShortAvgBitSpeed, ccMuSumStatsShortAvgMuSignal, ccMuSumStatsShortAvgMuNoise, ccMuSumStatsShortAvgMuSnr, ccMuSumStatsShortPp10kNUcastPkts, 
				ccMuSumStatsShortPp10kTxWithRetries, ccMuSumStatsShortPp10kDropped, ccMuSumStatsShortTxAvgRetries100, ccMuSumStatsShortPp10kRxUndecrypt, ccMuSumStatsLongTimestamp, 
				ccMuSumStatsLongNumPkts, ccMuSumStatsLongPktsPerSec100, ccMuSumStatsLongPktsPerSecTx100, ccMuSumStatsLongPktsPerSecRx100, ccMuSumStatsLongThroughput, 
				ccMuSumStatsLongThroughputTx, ccMuSumStatsLongThroughputRx, ccMuSumStatsLongAvgBitSpeed, ccMuSumStatsLongAvgMuSignal, ccMuSumStatsLongAvgMuNoise, 
				ccMuSumStatsLongAvgMuSnr, ccMuSumStatsLongPp10kNUcastPkts, ccMuSumStatsLongPp10kTxWithRetries, ccMuSumStatsLongPp10kDropped, ccMuSumStatsLongTxAvgRetries100, 
				ccMuSumStatsLongPp10kRxUndecrypt }
			STATUS current
			DESCRIPTION 
				"Description."
			::= { ccV2dot0Groups 6 }

		
		-- 1.3.6.1.4.1.388.6.1000.7
		v2dot0GroupOfDeprecated OBJECT-GROUP
			OBJECTS { ccPortalTxRetriesPkts15, ccPortalTxRetriesOctets15, ccMuTxRetries15, ccMuTxRetriesOctets15 }
			STATUS deprecated
			DESCRIPTION 
				"Description."
			::= { ccV2dot0Groups 7 }

		
	
	END
-- MIB-file-version: v24b08

--
-- SYMBOL-WS5000-MIB.mib
--
