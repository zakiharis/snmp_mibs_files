-- ----------------------------------------------------------------------------
--
--  SIAE MICROELETTRONICA s.p.a.
--                 
--  Via Michelangelo Buonarroti, 21
--  20093 - Cologno Monzese
--  Milano 
--  ITALY
--
-- ----------------------------------------------------------------------------
-- ----------------------------------------------------------------------------

SIAE-FEATUREKEYS-MIB
        DEFINITIONS ::= BEGIN

        IMPORTS
             MODULE-IDENTITY, OBJECT-TYPE,
             IpAddress
        FROM SNMPv2-SMI
             DisplayString
        FROM SNMPv2-TC
             siaeMib
        FROM SIAE-TREE-MIB;

    featureKeys MODULE-IDENTITY
        LAST-UPDATED "201402030000Z"
        ORGANIZATION "SIAE MICROELETTRONICA spa"
        CONTACT-INFO
            "SIAE MICROELETTONICA s.p.a.
             Via Michelangelo Buonarroti, 21
             20093 - Cologno Monzese
             Milano - ITALY
             Phone :  +39-02-27325-1
             E-mail: tbd@siaemic.com
            "
        DESCRIPTION
            "Protection by key of the SIAE's equipment features.
            "
        REVISION "201402030000Z"
        DESCRIPTION
            "Improved description of featureKeysMibVersion
            "
        REVISION "201304160000Z"
        DESCRIPTION 
            "Initial version 01.00.00
            "
    ::= { siaeMib 101 }

----------------------------------------------------------------------------------
--  SIAE feature keys GROUP
----------------------------------------------------------------------------------
--
--  The following listed objects are used to manage the feature keys of the
--  equipment. The feature keys can be modified by setting the specified objects
--  or downloading a SIAE certificate file.
--
----------------------------------------------------------------------------------

------ Beginning --------------------------------------------------------------


    featureKeysMibVersion  OBJECT-TYPE
        SYNTAX      INTEGER
        MAX-ACCESS  read-only
        STATUS      current
        DESCRIPTION
            "Numerical version of this module.
             The string version of this MIB have the following format:
                XX.YY.ZZ
             so, for example, the value 1 should be interpreted as 00.00.01
             and the value 10001 should be interpreted as 01.00.01."
        DEFVAL {1}
    ::= {featureKeys 1}

    featureKeysRadioMap  OBJECT-TYPE
        SYNTAX      OCTET STRING
        MAX-ACCESS  read-write
        STATUS      current
        DESCRIPTION
            "This object is the map of the radio feature keys (16 bits). The Get
             operation returns a map of 2 bytes. The value of the Set operation
             must be composed by the map of the 2 bytes and a 16 bytes signature
             from MD5 (the first 8 bytes as primary and the last 8 bytes as
             secondary)."
    ::= {featureKeys 2}

    featureKeysLineMap  OBJECT-TYPE
        SYNTAX      OCTET STRING
        MAX-ACCESS  read-write
        STATUS      current
        DESCRIPTION
            "This object is the map of the line feature keys (16 bits). The Get
             operation returns a map of 2 bytes. The value of the Set operation
             must be composed by the map of the 2 bytes and a 16 bytes signature
             from MD5 (the first 8 bytes as primary and the last 8 bytes as
             secondary)."
    ::= {featureKeys 3}

    featureKeysActionRequest  OBJECT-TYPE
        SYNTAX      INTEGER {
                              noAction    (1),
                              upload      (2)
                            }
        MAX-ACCESS  read-write
        STATUS      current
        DESCRIPTION
            "This objects is used to perform the action modifying feature key."
    ::= {featureKeys 4}

    featureKeysCertificateName  OBJECT-TYPE
        SYNTAX      DisplayString  (SIZE(0..255))
        MAX-ACCESS  read-write
        STATUS      current
        DESCRIPTION
            "This objects is the path filename of the certificate used to set the
             radio or line feature keys. The file is sent through FTP/SFTP."
    ::= {featureKeys 5}

    featureKeysCertificateRemoteIpAddress  OBJECT-TYPE
        SYNTAX      IpAddress
        MAX-ACCESS  read-write
        STATUS      current
        DESCRIPTION
            "This objects is the IP address of the FTP/SFTP server from which
             the certificate has to be downloaded to the equipment."
    ::= {featureKeys 6}

    featureKeysLastOperationState  OBJECT-TYPE
        SYNTAX      INTEGER   {
                                initial                (1),
                                downloadCompleted      (2),
                                downloadTransferring   (3),
                                downloadVerifying      (4),
                                downloadInterrupted    (5),
                                setSuccess             (6),
                                setFailure             (7)
                              }
        MAX-ACCESS  read-only
        STATUS      current
        DESCRIPTION
            "This objects is the state of the last operation (a SNMP set on radio/line
             map or a certificate transfer). The values mean:
             initial -> default state after a start-up
             downloadCompleted -> a certificate has been downloaded successfully
             downloadTransferring -> a download is running
             downloadVerifying -> the certificate has been checking
             downloadInterrupted -> the download of a certificate had a bad result
             setSuccess -> a success of a SMNP set on radio/line map
             setFailure -> a failure of a SMNP set on radio/line map."
    ::= {featureKeys 7}

    featureKeysLastOperationFailure  OBJECT-TYPE
        SYNTAX      INTEGER   {
                                noFailure        (1),
                                transfer         (2),
                                serialNo         (3),
                                verifySign       (4),
                                primaryDigest    (5),
                                secondaryDigest  (6)
                              }
        MAX-ACCESS  read-only
        STATUS      current
        DESCRIPTION
            "This objects is the failure code of the last operation (a SNMP set on
             radio/line map or a certificate transfer)."
    ::= {featureKeys 8}

------ End group -----------------------------------------------------------------

END
