-- 	$Id: shiva-conf.asn,v 1.8 1996/04/19 09:40:53 jas Exp $

--
-- 	Copyright 1992, 1993, 1995, 1996 Shiva Corporation
--

--	Shiva systems config MIB

SHIVA-CONF-MIB DEFINITIONS ::= BEGIN

IMPORTS
    	OBJECT-TYPE
    		FROM RFC-1212		-- Concise MIB Definitions
    	config
    		FROM SHIVA-MIB;


-- 1 thru 10 reserved for transplantation of fpConf group

    confName	OBJECT-TYPE
	SYNTAX	OCTET STRING
	ACCESS  read-write
	STATUS  mandatory
	DESCRIPTION
		"The system name currently in use.  Used to generate
		protocol specific service advertisements (ie; SAP and
		NBP) on startup."
	::= { config 11 }

    confRemoteBoot OBJECT-TYPE
	SYNTAX	INTEGER { disabled(1), enabled(2) }
	ACCESS  read-write
	STATUS  mandatory
	DESCRIPTION
		"If enabled, the system will fetch a new configuration
		and download on power-up or other cold restart."
	DEFVAL { disabled }
	::= { config 12 }

    confDialInTimeout OBJECT-TYPE
	SYNTAX	INTEGER
	ACCESS	read-write
	STATUS	mandatory
	DESCRIPTION
		"Default dial-in idle limit currently in use."
	::= { config 13 }

    confDialOutTimeout OBJECT-TYPE
	SYNTAX	INTEGER
	ACCESS	read-write
	STATUS	mandatory
	DESCRIPTION
		"Dial-out idle limit currently in use."
	::= { config 14 }

    confShellTimeout OBJECT-TYPE
	SYNTAX	INTEGER
	ACCESS	read-write
	STATUS	mandatory
	DESCRIPTION
		"Shell idle limit currently in use."
	::= { config 15 }

    confClear	OBJECT-TYPE
	SYNTAX	INTEGER { notClear(1), clear(2) }
	ACCESS	read-write
	STATUS	mandatory
	DESCRIPTION
		"When set to clear, discards the current config file."
	DEFVAL { notClear }
	::= { config 16 }

    confLanToLanTimeout OBJECT-TYPE
	SYNTAX	INTEGER
	ACCESS	read-write
	STATUS	mandatory
	DESCRIPTION
		"Default LAN-to-LAN idle limit currently in use."
	::= { config 17 }

-- Added at LanRover/E 3.0

    confModificationTime OBJECT-TYPE
  	SYNTAX  INTEGER
  	ACCESS  read-write
  	STATUS  mandatory
	DESCRIPTION
		"The date and time the configuration was last
		modified, represented as the number of seconds 
		elapsed since Midnight on January 1st, 1970 GMT."
	::= { config 18 }

-- Added at Release 4.3.1

    confNewHwStatus OBJECT-TYPE
	SYNTAX  INTEGER
	ACCESS  read-only
	STATUS  mandatory
	DESCRIPTION
		"This integer is a bit mask which holds the following flags:
		(not all bits are valid for all products)
			0x00000001 - Flash memory bank 0 is present
			0x00000002 - Flash memory bank 1 is present
			0x00000004 - Flash memory bank 2 is present
			0x00000008 - Flash memory bank 3 is present
			0x00000010 - SRAM bank 0 is present
			0x00000020 - SRAM bank 1 is present
			0x00000040 - SRAM bank 2 is present
			0x00000080 - RAM bank 0 is present
			0x00000100 - RAM bank 1 is present
			0x00000200 - RAM bank 2 is present"
	::= { config 19 }



END
