-- Revision 1.0.0
-- Copyright 1999 D-Link, Inc.
-- All rights reserved.

SW-SNIFF-MIB    DEFINITIONS ::= BEGIN
    IMPORTS
        OBJECT-TYPE     FROM RFC-1212
        enterprises     FROM RFC1155-SMI;
        
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }                

    marconi-mgmt    OBJECT IDENTIFIER ::= { golfcommon 2 }

    es2000Mgmt      OBJECT IDENTIFIER ::= { marconi-mgmt 28 }

    swL2Mgmt        OBJECT IDENTIFIER ::= { es2000Mgmt 2 }

    swPortSniff     OBJECT IDENTIFIER ::= { swL2Mgmt 5 }

-- *****************************************************************************
--  swSniffCtrlTable
-- *****************************************************************************
    swSniffCtrlTable OBJECT-TYPE
        SYNTAX  SEQUENCE OF SwSniffCtrlEntry
        ACCESS  not-accessible
        STATUS  mandatory
        DESCRIPTION
            "A list of port sniffing entries.Port Sniffing function provides an
             easy way to monitor traffic on any port. In this way any good packets
             appears on the source mirror port also shows up on the target mirror
             port without need to reconstruct the LAN."
        ::= { swPortSniff 1 }

    swSniffCtrlEntry OBJECT-TYPE
        SYNTAX  SwSniffCtrlEntry
        ACCESS  not-accessible
        STATUS  mandatory
        DESCRIPTION
            "Each entry contains a pair of sniff source port and target port."
        INDEX  { swSniffIndex }
        ::= { swSniffCtrlTable 1 }

    SwSniffCtrlEntry ::=
        SEQUENCE {
            swSniffIndex
                INTEGER,
            swSniffSourcePort
                INTEGER,
            swSniffTargetPort
                INTEGER,
            swSniffState
                INTEGER
        }

    swSniffIndex OBJECT-TYPE
        SYNTAX  INTEGER
        ACCESS  read-only
        STATUS  mandatory
        DESCRIPTION
            "A unique number to identify the sniff entry."
        ::= { swSniffCtrlEntry 1 }

    swSniffSourcePort OBJECT-TYPE
        SYNTAX  INTEGER (1..128)
        ACCESS  read-write
        STATUS  mandatory
        DESCRIPTION
            "Indicates the source port whose traffic will be sniffed."
        ::= { swSniffCtrlEntry 2 }

    swSniffTargetPort OBJECT-TYPE
        SYNTAX  INTEGER (1..128)
        ACCESS  read-write
        STATUS  mandatory
        DESCRIPTION
            "Indicates the target port which the traffic appears on the source
             sniffed port will be copied to. A trunk port member cannot be
             configured as a target Sniffing port"
        ::= { swSniffCtrlEntry 3 }

    swSniffState OBJECT-TYPE
        SYNTAX  INTEGER {
            other(1),
            disable(2),
            enable(3)
        }
        ACCESS  read-write
        STATUS  mandatory
        DESCRIPTION
            "This object indicates the status of this entry.
             other(1) - this entry is currently in use but the conditions under
                        which it will remain so are different from each of the
                        following values.
             disable(2) - Sniff funtion disable.
             enable(3) - Sniff funtion enable and Sniff received or transmit
                         packet by Sniff source port."
        ::= { swSniffCtrlEntry 4 }

END
