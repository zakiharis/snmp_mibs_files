-- extracted from draft-ietf-isms-transport-security-model-05.txt
-- at Tue Jul 10 06:08:47 2007

   SNMP-TRANSPORT-SM-MIB DEFINITIONS ::= BEGIN

   IMPORTS
       MODULE-IDENTITY, OBJECT-TYPE,
       snmpModules, Counter32
         FROM SNMPv2-SMI
       MODULE-COMPLIANCE, OBJECT-GROUP
         FROM SNMPv2-CONF
       ;

   tsmMIB MODULE-IDENTITY
       LAST-UPDATED "200707050000Z"
       ORGANIZATION "ISMS Working Group"
       CONTACT-INFO "WG-EMail:   isms@lists.ietf.org
                     Subscribe:  isms-request@lists.ietf.org

                  Chairs:
                    Juergen Quittek
                    NEC Europe Ltd.
                    Network Laboratories
                    Kurfuersten-Anlage 36
                    69115 Heidelberg
                    Germany
                    +49 6221 90511-15
                     quittek@netlab.nec.de

                     Juergen Schoenwaelder
                     Jacobs University Bremen
                     Campus Ring 1
                     28725 Bremen
                     Germany
                     +49 421 200-3587
                     j.schoenwaelder@iu-bremen.de

                  Editor:
                     David Harrington
                     Huawei Technologies USA
                     1700 Alma Dr.
                     Plano TX 75075
                     USA
                     +1 603-436-8634
                     ietfdbh@comcast.net
                       "
          DESCRIPTION  "The Transport Security Model MIB

                        Copyright (C) The IETF Trust (2007). This
                        version of this MIB module is part of RFC XXXX;
                        see the RFC itself for full legal notices.
   -- NOTE to RFC editor: replace XXXX with actual RFC number
   --                     for this document and remove this note
                       "

          REVISION     "200707050000Z"
          DESCRIPTION  "The initial version, published in RFC XXXX.
   -- NOTE to RFC editor: replace XXXX with actual RFC number
   --                     for this document and remove this note
                       "

       ::= { snmpModules 1 }

   -- RFC Ed.: replace xxxx with IANA-assigned number and
   --          remove this note

   -- ---------------------------------------------------------- --
   -- subtrees in the SNMP-TRANSPORT-SM-MIB
   -- ---------------------------------------------------------- --

   tsmNotifications OBJECT IDENTIFIER ::= { tsmMIB 0 }
   tsmMIBObjects       OBJECT IDENTIFIER ::= { tsmMIB 1 }
   tsmConformance   OBJECT IDENTIFIER ::= { tsmMIB 2 }

   -- -------------------------------------------------------------
   -- Objects
   -- -------------------------------------------------------------

   -- Statistics for the Transport Security Model


   tsmStats         OBJECT IDENTIFIER ::= { tsmMIBObjects 1 }

   tsmInvalidCache OBJECT-TYPE
       SYNTAX       Counter32
       MAX-ACCESS   read-only
       STATUS       current
       DESCRIPTION "The number of messages dropped because the
                    tmStateReference referred to an invalid cache.

                    This value is not persistent across reboots.
                   "
       ::= { tsmStats 1 }

   tsmInadequateSecurity OBJECT-TYPE
       SYNTAX       Counter32
       MAX-ACCESS   read-only
       STATUS       current
       DESCRIPTION "The number of incoming messages dropped because
                    the actual securityLevel provided was less than
                    the requested securityLevel.

                    This value is not persistent across reboots.
                   "
       ::= { tsmStats 2 }

   -- -------------------------------------------------------------
   -- tsmMIB - Conformance Information
   -- -------------------------------------------------------------

   tsmGroups OBJECT IDENTIFIER ::= { tsmConformance 1 }
   tsmCompliances OBJECT IDENTIFIER ::= { tsmConformance 2 }

   -- -------------------------------------------------------------
   -- Units of conformance
   -- -------------------------------------------------------------
   tsmGroup OBJECT-GROUP
       OBJECTS {
           tsmInvalidCache,
           tsmInadequateSecurity
       }
       STATUS      current
       DESCRIPTION "A collection of objects for maintaining
                    information of an SNMP engine which implements
                    the SNMP Transport Security Model.
                   "

       ::= { tsmGroups 2 }

   -- -------------------------------------------------------------
   -- Compliance statements
   -- -------------------------------------------------------------

   tsmCompliance MODULE-COMPLIANCE
       STATUS      current
       DESCRIPTION
           "The compliance statement for SNMP engines that support
            the SNMP-TRANSPORT-SM-MIB"
       MODULE
           MANDATORY-GROUPS { tsmGroup }
       ::= { tsmCompliances 1 }

   END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
