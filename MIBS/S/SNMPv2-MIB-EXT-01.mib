-- extracted from draft-schoenw-snmpv2-mib-ext-00.txt
-- at Mon Nov 15 17:11:09 1999

   SNMPv2-MIB-EXT-01 DEFINITIONS ::= BEGIN

   IMPORTS
       MODULE-IDENTITY, OBJECT-TYPE
           FROM SNMPv2-SMI
       system
           FROM SNMPv2-MIB
			DateAndTime
           FROM SNMPv2-TC;

   -- This module is not valid SMIv2. The author left out all the
   -- administrative stuff in order to keep it small.

   sysDateAndTime OBJECT-TYPE
       SYNTAX      DateAndTime
       MAX-ACCESS  read-write
       STATUS      current
       DESCRIPTION
           "The locally known date and time. The value '0000000000000000'H
            is returned on systems without a local clock until the local
            date and time is learned, either from a network time protocol
            such as NTP or a management set operations on this object."
       ::= { system 9 }

   END
