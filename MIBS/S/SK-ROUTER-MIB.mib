SK-ROUTER-MIB DEFINITIONS ::= BEGIN

-- Title:  SysKonnect SK-ROUTER-MIB Extension version 1.2
-- Date:   February, 1995
-- By:     Georg Klug <gklug@skd.de>

IMPORTS
    enterprises, OBJECT-TYPE, Counter,
    Gauge, TimeTicks, DisplayString      FROM RFC1155-SMI
    TRAP-TYPE                            FROM RFC-1215;


--***********************************************************************
--*   Global Definition of the enterprise
--***********************************************************************

	-- S&K private

	sk		OBJECT IDENTIFIER ::= { enterprises 179 }

	skSystems	OBJECT IDENTIFIER ::= { sk 1 }
	skMibs		OBJECT IDENTIFIER ::= { sk 2 }

--***********************************************************************
--*   Definition of the used sysObjectID
--***********************************************************************

	skRouter	OBJECT IDENTIFIER ::= { skSystems 1 }
	skConcentrator	OBJECT IDENTIFIER ::= { skSystems 2 }
	skSwitch	OBJECT IDENTIFIER ::= { skSystems 3 }

	skDLI		OBJECT IDENTIFIER ::= { skMibs 1 }

--***********************************************************************
--*   Definitions of private router-MIB objects
--***********************************************************************


--***********************************************************************
--*   Definition of private TRAPS
--***********************************************************************

END
