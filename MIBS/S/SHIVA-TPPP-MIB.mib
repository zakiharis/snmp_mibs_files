-- 	$Id: shiva-ppp.asn,v 1.6 1996/04/05 16:18:48 jas Exp $

--
-- 	Copyright 1994, 1995, 1996 Shiva Corporation
--

SHIVA-TPPP-MIB DEFINITIONS ::= BEGIN

IMPORTS
	OBJECT-TYPE
		FROM RFC-1212		-- Concise MIB Definitions
	tPPP
		FROM SHIVA-MIB;


-- Point-to-Point Protocol (PPP) port table

-- for the care and feeding of PPP ports 

    tpppPortTable OBJECT-TYPE
	SYNTAX	SEQUENCE OF TpppPortEntry
	ACCESS	not-accessible
	STATUS	mandatory
	DESCRIPTION
		"Table of PPP port initialization parameters and status.
		Instantiated only for dedicated serial ports where
		PPP configuration is done by unit number."
	::= { tPPP 1 }

    tpppPortEntry OBJECT-TYPE
	SYNTAX	TpppPortEntry
	ACCESS	not-accessible
	STATUS	mandatory
	DESCRIPTION
		"Initialization parameters and status for a PPP port."
	INDEX { tpppPortIndex }
	::= { tpppPortTable 1 }

    TpppPortEntry ::= SEQUENCE {
	tpppPortIndex		INTEGER,
	tpppPortRestartTimer	INTEGER,
	tpppCompTypes		INTEGER,
	tpppCompStacPerf	INTEGER, 
	tpppPortStatus		INTEGER
    }

    tpppPortIndex OBJECT-TYPE
	SYNTAX	INTEGER
	ACCESS	read-only
	STATUS	mandatory
	DESCRIPTION
		"Serial port number which corresponds to an
		instance of rs232PortIndex."
	::= { tpppPortEntry 1 }

    tpppPortRestartTimer OBJECT-TYPE
	SYNTAX	INTEGER
	ACCESS	read-only
	STATUS	mandatory
	DESCRIPTION
		"The PPP Restart Timer for this port."
	::= { tpppPortEntry 2 }

    tpppCompTypes OBJECT-TYPE
	SYNTAX	INTEGER
	ACCESS	read-only
	STATUS	mandatory
	DESCRIPTION
		"The PPP compression protocols that are available to
		be negotiated for this port, represented as a
		bitmask:
			0x00000001 - Stac LZS
			0x00000002 - Microsoft PPC."

	::= { tpppPortEntry 3 }

    tpppCompStacPerf OBJECT-TYPE
	SYNTAX	INTEGER (0..255)
	ACCESS	read-only
	STATUS	mandatory
	DESCRIPTION
		"The compression effectiveness ratio configured for
		the Stac LZS compression engine for this port.
		Applies to Stac LZS compression only."

	::= { tpppPortEntry 4 }

    tpppPortStatus OBJECT-TYPE
	SYNTAX	INTEGER {
		disabled(1),
		enabled(2)
	}
	ACCESS	read-only
	STATUS	mandatory
	DESCRIPTION
		"PPP port status."
	::= { tpppPortEntry 5 }

END
