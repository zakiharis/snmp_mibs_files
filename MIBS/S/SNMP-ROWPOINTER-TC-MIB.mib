-- extracted from draft-ietf-ops-rowpointer-tc-01.txt
-- at Wed Mar  7 06:04:48 2001

   SNMP-ROWPOINTER-TC-MIB DEFINITIONS ::= BEGIN


      IMPORTS
        MODULE-IDENTITY, mib-2 FROM SNMPv2-SMI
        TEXTUAL-CONVENTION     FROM SNMPv2-TC;


      snmpRowPointerTCMIB MODULE-IDENTITY
        LAST-UPDATED "200012180000Z" -- December 18, 2000
        ORGANIZATION
            "SNMP Configuration WG"
        CONTACT-INFO
            "Bob Moore
             IBM Corporation, BRQA/502
             PO Box 12195
             Research Triangle Park, NC 27709, USA
             Phone: +1 919 254 4436
             EMail: remoore@us.ibm.com

             Kwok Ho Chan
             Nortel Networks
             600 Technology Park Drive
             Billerica, MA 01821, USA
             E-mail: khchan@nortelnetworks.com

             Send comments to snmpconf@ops.ietf.org."

      DESCRIPTION
        "This MIB module defines textual conventions similar to the
        RowPointer textual convention, with additional sementics."

      REVISION     "200012180000Z" -- December 18, 2000
      DESCRIPTION
          "Initial version, published as RFCnnnn."
      ::= { mib-2 67890 } -- to be assigned by IANA


   StaticRowPointer ::= TEXTUAL-CONVENTION
       STATUS       current
       DESCRIPTION
               "Like a RowPointer, this textual convention
               represents a pointer to a conceptual row.
               The value is the name of the instance of the
               first accessible columnar object in the
               conceptual row.

               The additional semantics of this textual
               convention, relative to RowPointer, are
               related to the creation of instance-specific
               objects by cloning.  The objects being cloned
               may either be special ones that express
               configuration information at the
               mechanism-specific level, or simply
               instance-specific ones that already exist at
               the time the cloning is done.  When an object
               with the syntax StaticRowPointer is cloned, the
               StaticRowPointer in the newly cloned object is
               set to point to the same conceptual row that the
               StaticRowPointer in the cloned-from object
               pointed to. The cloning operations may be
               accomplished either with the script-based
               technique defined by SNMP Configuration, or by
               ordinary SNMP Get and Set operations.

               When cloning is not involved, this textual
               convention behaves identically to the RowPointer
               textual convention.  Specifically, once an object
               with this syntax has been created, either by
               cloning or by other means, its value may be
               updated in the same way that the value of any
               other object with read-write or read-create
               access may be updated."
       SYNTAX       OBJECT IDENTIFIER

   END

-- 
--    Copyright (C) The Internet Society (2001).  All Rights Reserved.
-- 
--    This document and translations of it may be copied and furnished to
--    others, and derivative works that comment on or otherwise explain it
--    or assist in its implementation may be prepared, copied, published and
--    distributed, in whole or in part, without restriction of any kind,
--    provided that the above copyright notice and this paragraph are
--    included on all such copies and derivative works.  However, this
--    document itself may not be modified in any way, such as by removing
--    the copyright notice or references to the Internet Society or other
--    Internet organizations, except as needed for the purpose of developing
--    Internet standards in which case the procedures for copyrights defined
--    in the Internet Standards process must be followed, or as required to
--    translate it into languages other than English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING BUT
--    NOT LIMITED TO ANY WARRANTY THAT THE USE OF THE INFORMATION HEREIN
--    WILL NOT INFRINGE ANY RIGHTS OR ANY IMPLIED WARRANTIES OF
--    MERCHANTABILITY OR FITNESS FOR A PARTICULAR PURPOSE.
